A10-AX-CGN-MIB DEFINITIONS ::= BEGIN
  IMPORTS

    DisplayString, PhysAddress
      FROM SNMPv2-TC

    InetAddressType
      FROM INET-ADDRESS-MIB

    a10Mgmt
      FROM A10-COMMON-MIB

	axIpNatLoggingStats, axIpNatLsnStats, axIpNatNat64Stats, axIpNatDsliteStats, axIpNatStatsDynamicMappingAclName,
	axFixedNatStats, axNetworkingStats, axDDoS
	  FROM A10-AX-MIB

    CounterBasedGauge64
      FROM HCNUM-TC

    MODULE-IDENTITY, OBJECT-TYPE, Counter32, Integer32, Counter64, OBJECT-IDENTITY, NOTIFICATION-TYPE
      FROM SNMPv2-SMI;


--==================================================================
-- axIpNatLsnStats               
--==================================================================

    axIpNatLsnGlobalStats                       OBJECT IDENTIFIER ::= { axIpNatLsnStats 1 }
    axIpNatLsnTop5PrivateIpAddrTotSessions     OBJECT IDENTIFIER ::= { axIpNatLsnStats 2 }
    axIpNatLsnTop5PrivateIpAddrTotTcpPorts     OBJECT IDENTIFIER ::= { axIpNatLsnStats 3 }
    axIpNatLsnTop5PrivateIpAddrTotUdpPorts     OBJECT IDENTIFIER ::= { axIpNatLsnStats 4 }
    axIpNatLsnTop5PrivateIpAddrTotIcmpPorts    OBJECT IDENTIFIER ::= { axIpNatLsnStats 5 }
    axIpNatLsnTop5UserPrivateIpAddrTotSessions     OBJECT IDENTIFIER ::= { axIpNatLsnStats 6 }
    axIpNatLsnTop5UserPrivateIpAddrTotTcpSessions  OBJECT IDENTIFIER ::= { axIpNatLsnStats 7 }
    axIpNatLsnTop5UserPrivateIpAddrTotUdpSessions  OBJECT IDENTIFIER ::= { axIpNatLsnStats 8 }
    axIpNatLsnTop5UserPrivateIpAddrTotIcmpSessions OBJECT IDENTIFIER ::= { axIpNatLsnStats 9 }
    axIpNatLsnTop5GlobalPoolIpAddrTotUsers         OBJECT IDENTIFIER ::= { axIpNatLsnStats 10 }
    axIpNatLsnTop5GlobalPoolIpAddrTotTcpPorts      OBJECT IDENTIFIER ::= { axIpNatLsnStats 11 }
    axIpNatLsnTop5GlobalPoolIpAddrTotUdpPorts      OBJECT IDENTIFIER ::= { axIpNatLsnStats 12 }
    
    axIpNatLsnAlgSipStats    OBJECT IDENTIFIER ::= { axIpNatLsnStats 13 }
    axIpNatLsnPoolStats      OBJECT IDENTIFIER ::= { axIpNatLsnStats 14 }
	axIpNatLsnRadiusStats    OBJECT IDENTIFIER ::= { axIpNatLsnStats 15 }

--==================================================================
-- axIpNatLsnGlobalStats
--==================================================================

    axIpNatLsnTotalUserQuotaSessions	OBJECT-TYPE	
	SYNTAX			Integer32
	MAX-ACCESS		read-only
	STATUS			current
	DESCRIPTION		
		"The total number of user-quota sessions."
	DEFVAL			{ 0 }
	::=  {  axIpNatLsnGlobalStats  1  }

    axIpNatLsnTotalIpAddrTranslated	OBJECT-TYPE	
	SYNTAX			Integer32
	MAX-ACCESS		read-only
	STATUS			current
	DESCRIPTION		
		"The total number of global (translated) Ip addresses which has at least 1 users."
	DEFVAL			{ 0 }
	::=  {  axIpNatLsnGlobalStats  2  }

    axIpNatLsnTotalFullConeSessions	OBJECT-TYPE	
	SYNTAX			Integer32
	MAX-ACCESS		read-only
	STATUS			current
	DESCRIPTION		
		"The total number of full cone sessions."
	DEFVAL			{ 0 }
	::=  {  axIpNatLsnGlobalStats  3  }

    axIpNatLsnTrafficStats  OBJECT IDENTIFIER ::= { axIpNatLsnGlobalStats 4 }

    axIpNatLsnTrafficFullConeSessionCreated OBJECT-TYPE 
	SYNTAX Integer32
	MAX-ACCESS read-only
	STATUS current
	DESCRIPTION
		"The total number of full-cone session created."
	::= { axIpNatLsnTrafficStats 1 } 

    axIpNatLsnTrafficFullConeSessionFreed OBJECT-TYPE 
	SYNTAX Integer32
	MAX-ACCESS read-only
	STATUS current
	DESCRIPTION
		"The total number of full-cone session freed."
	::= { axIpNatLsnTrafficStats 2 } 

    axIpNatLsnTrafficFailsInFullConeSessionCreation OBJECT-TYPE 
	SYNTAX Integer32
	MAX-ACCESS read-only
	STATUS current
	DESCRIPTION
		"The total number of full-cone session creation failure."
	::= { axIpNatLsnTrafficStats 3 } 

    axIpNatLsnTrafficHairpinSessionCreated OBJECT-TYPE 
	SYNTAX Integer32
	MAX-ACCESS read-only
	STATUS current
	DESCRIPTION
		"The total number of hairpin session created."
	::= { axIpNatLsnTrafficStats 4 } 

    axIpNatLsnTrafficEndpointIndepMapMatch OBJECT-TYPE 
	SYNTAX Integer32
	MAX-ACCESS read-only
	STATUS current
	DESCRIPTION
		"The total number of endpoint independent mapping match."
	::= { axIpNatLsnTrafficStats 5 } 

    axIpNatLsnTrafficEndpointIndepFilterMatch OBJECT-TYPE 
	SYNTAX Integer32
	MAX-ACCESS read-only
	STATUS current
	DESCRIPTION
		"The total number of endpoint independent filtering match."
	::= { axIpNatLsnTrafficStats 6 } 

    axIpNatLsnTrafficUserQuotasCreated OBJECT-TYPE 
	SYNTAX Integer32
	MAX-ACCESS read-only
	STATUS current
	DESCRIPTION
		"The total number of user-quotas created."
	::= { axIpNatLsnTrafficStats 7 } 

    axIpNatLsnTrafficUserQuotasFreed OBJECT-TYPE 
	SYNTAX Integer32
	MAX-ACCESS read-only
	STATUS current
	DESCRIPTION
		"The total number of user-quotas freed."
	::= { axIpNatLsnTrafficStats 8 } 

    axIpNatLsnTrafficFailsInUserQuotasCreation OBJECT-TYPE 
	SYNTAX Integer32
	MAX-ACCESS read-only
	STATUS current
	DESCRIPTION
		"The total number of user-quotas creation failure."
	::= { axIpNatLsnTrafficStats 9 } 

    axIpNatLsnTrafficIcmpUserQuotasExceeded OBJECT-TYPE 
	SYNTAX Integer32
	MAX-ACCESS read-only
	STATUS current
	DESCRIPTION
		"The total number of ICMP user-quotas exceeded."
	::= { axIpNatLsnTrafficStats 10 } 

    axIpNatLsnTrafficUdpUserQuotasExceeded OBJECT-TYPE 
	SYNTAX Integer32
	MAX-ACCESS read-only
	STATUS current
	DESCRIPTION
		"The total number of UDP user-quotas exceeded."
	::= { axIpNatLsnTrafficStats 11 } 

    axIpNatLsnTrafficTcpUserQuotasExceeded OBJECT-TYPE 
	SYNTAX Integer32
	MAX-ACCESS read-only
	STATUS current
	DESCRIPTION
		"The total number of TCP user-quotas exceeded."
	::= { axIpNatLsnTrafficStats 12 } 

    axIpNatLsnTrafficExtendedUserQuotasMatch OBJECT-TYPE 
	SYNTAX Integer32
	MAX-ACCESS read-only
	STATUS current
	DESCRIPTION
		"The total number of extended user-quotas matches."
	::= { axIpNatLsnTrafficStats 13 } 

    axIpNatLsnTrafficExtendedUserQuotasExceeded OBJECT-TYPE 
	SYNTAX Integer32
	MAX-ACCESS read-only
	STATUS current
	DESCRIPTION
		"The total number of extended user-quotas exceeded."
	::= { axIpNatLsnTrafficStats 14 } 

    axIpNatLsnTrafficNatPortUnavailable OBJECT-TYPE 
	SYNTAX Integer32
	MAX-ACCESS read-only
	STATUS current
	DESCRIPTION
		"The total number of NAT port unavailable."
	::= { axIpNatLsnTrafficStats 15 } 

    axIpNatLsnTrafficNewUserResourceUnavailable OBJECT-TYPE 
	SYNTAX Integer32
	MAX-ACCESS read-only
	STATUS current
	DESCRIPTION
		"The total number of NAT resource unavailable for new users."
	::= { axIpNatLsnTrafficStats 16 } 

--==================================================================
--  axIpNatLsnSessionStats
--==================================================================

    axIpNatLsnSessionStats       OBJECT IDENTIFIER ::= { axIpNatLsnGlobalStats 5 }

    axIpNatLsnSessionDataSessionsUsed OBJECT-TYPE
        SYNTAX CounterBasedGauge64
        MAX-ACCESS  read-only
        STATUS  current
        DESCRIPTION
        	"The number of data sessions used."
        ::= {axIpNatLsnSessionStats 1}

     axIpNatLsnSessionDataSessionsFree OBJECT-TYPE
         SYNTAX CounterBasedGauge64
         MAX-ACCESS  read-only
         STATUS  current
         DESCRIPTION
     		"The number of data sessions free."
         ::= {axIpNatLsnSessionStats 2}

     axIpNatLsnSessionSmpSessionsUsed OBJECT-TYPE
     	 SYNTAX CounterBasedGauge64
     	 MAX-ACCESS  read-only
     	 STATUS  current
     	 DESCRIPTION
     		"The number of SMP sessions used."
     	::= {axIpNatLsnSessionStats 3}

     axIpNatLsnSessionSmpSessionsFree OBJECT-TYPE
     	 SYNTAX CounterBasedGauge64
         MAX-ACCESS  read-only
         STATUS  current
         DESCRIPTION
         	"The number of SMP sessions free."
         ::= {axIpNatLsnSessionStats 4}

--=====================================================================
--  axIpNatLsnPortUsageStats
--=====================================================================

    axIpNatLsnNatPortUsageStats  OBJECT IDENTIFIER ::= { axIpNatLsnGlobalStats 6 }

    axIpNatLsnNatPortTcpNatPortUsed OBJECT-TYPE
        SYNTAX Counter64
     	MAX-ACCESS  read-only
     	STATUS  current
     	DESCRIPTION
     		"The number of TCP NAT ports used."
     	::= {axIpNatLsnNatPortUsageStats 1}

    axIpNatLsnNatPortTcpNatPortFree OBJECT-TYPE
     	SYNTAX Counter64
      	MAX-ACCESS  read-only
     	STATUS  current
     	DESCRIPTION
     		"The number of TCP NAT ports free."
     	::= {axIpNatLsnNatPortUsageStats 2}

    axIpNatLsnNatPortUdpNatPortUsed OBJECT-TYPE
        SYNTAX Counter64
     	MAX-ACCESS  read-only
     	STATUS  current
     	DESCRIPTION
     		"The number of UDP NAT ports used."
     	::= {axIpNatLsnNatPortUsageStats 3}

    axIpNatLsnNatPortUdpNatPortFree OBJECT-TYPE
     	SYNTAX Counter64
     	MAX-ACCESS  read-only
     	STATUS  current
     	DESCRIPTION
     		"The number of UDP NAT ports free."
     	::= {axIpNatLsnNatPortUsageStats 4}

--==================================================================
-- axIpNatLsnTop5PrivateIpAddrTotSessions
--==================================================================

    axIpNatLsnTop5PrivateIpAddrTotSessionTable OBJECT-TYPE
	SYNTAX SEQUENCE OF AxIpNatLsnTop5PrivateIpAddrTotSessionEntry
	MAX-ACCESS not-accessible
	STATUS current
	DESCRIPTION
		"A table containing Top 5 private IPs and total number of sessions(ports)."
	::= { axIpNatLsnTop5PrivateIpAddrTotSessions 1 } 

    axIpNatLsnTop5PrivateIpAddrTotSessionEntry OBJECT-TYPE
	SYNTAX  AxIpNatLsnTop5PrivateIpAddrTotSessionEntry
	MAX-ACCESS not-accessible
	STATUS current
	DESCRIPTION
		"Columns in the axIpNatLsnTop5PrivateIpAddrTotSessions Table"
	INDEX {
		axIpNatLsnTop5PrivateIpAddr
	}
	::= { axIpNatLsnTop5PrivateIpAddrTotSessionTable 1 } 

    AxIpNatLsnTop5PrivateIpAddrTotSessionEntry ::= 
	SEQUENCE {
        	axIpNatLsnTop5PrivateIpAddr                 DisplayString,
        	axIpNatLsnTop5PrivateIpAddrTotNumSessions   Integer32,
        	axIpNatLsnTop5PrivateIpAddrGlobalIpAddr     DisplayString
	}

    axIpNatLsnTop5PrivateIpAddr OBJECT-TYPE 
	SYNTAX DisplayString
	MAX-ACCESS read-only
	STATUS current
	DESCRIPTION
		"The private IP address in the Top 5 private IP address entry."
	::= { axIpNatLsnTop5PrivateIpAddrTotSessionEntry 1 } 

    axIpNatLsnTop5PrivateIpAddrTotNumSessions OBJECT-TYPE 
	SYNTAX Integer32
	MAX-ACCESS read-only
	STATUS current
	DESCRIPTION
		"The total number of sessions in the Top 5 private IP address entry."
	::= { axIpNatLsnTop5PrivateIpAddrTotSessionEntry 2 } 

    axIpNatLsnTop5PrivateIpAddrGlobalIpAddr OBJECT-TYPE 
	SYNTAX DisplayString
	MAX-ACCESS read-only
	STATUS current
	DESCRIPTION
		"The global IP address in the Top 5 private IP address entry."
	::= { axIpNatLsnTop5PrivateIpAddrTotSessionEntry 3 } 

--==================================================================
-- axIpNatLsnTop5PrivateIpAddrTotTcpPorts
--==================================================================

    axIpNatLsnTop5PrivateIpAddrTotTcpPortTable OBJECT-TYPE
        SYNTAX SEQUENCE OF AxIpNatLsnTop5PrivateIpAddrTotTcpPortEntry
        MAX-ACCESS not-accessible
        STATUS current
        DESCRIPTION
                "A table containing Top 5 private IPs and total number of TCP ports."
        ::= { axIpNatLsnTop5PrivateIpAddrTotTcpPorts 1 }

    axIpNatLsnTop5PrivateIpAddrTotTcpPortEntry OBJECT-TYPE
        SYNTAX  AxIpNatLsnTop5PrivateIpAddrTotTcpPortEntry
        MAX-ACCESS not-accessible
        STATUS current
        DESCRIPTION
                "Columns in the axIpNatLsnTop5PrivateIpAddrTotTcpPorts Table"
        INDEX {
                axIpNatLsnTop5PrivateIpAddrInTcpPort
        }
        ::= { axIpNatLsnTop5PrivateIpAddrTotTcpPortTable 1 }

    AxIpNatLsnTop5PrivateIpAddrTotTcpPortEntry ::=
        SEQUENCE {
                axIpNatLsnTop5PrivateIpAddrInTcpPort              DisplayString,
                axIpNatLsnTop5PrivateIpAddrTotNumTcpPorts         Integer32,
                axIpNatLsnTop5PrivateIpAddrGlobalIpAddrInTcpPort  DisplayString
        }

    axIpNatLsnTop5PrivateIpAddrInTcpPort OBJECT-TYPE
        SYNTAX DisplayString
        MAX-ACCESS read-only
        STATUS current
        DESCRIPTION
                "The private IP address in the Top 5 private IP address entry."
        ::= { axIpNatLsnTop5PrivateIpAddrTotTcpPortEntry 1 }

    axIpNatLsnTop5PrivateIpAddrTotNumTcpPorts OBJECT-TYPE
        SYNTAX Integer32
        MAX-ACCESS read-only
        STATUS current
        DESCRIPTION
                "The total number of TCP sessions in the Top 5 private IP address entry."
        ::= { axIpNatLsnTop5PrivateIpAddrTotTcpPortEntry 2 }

    axIpNatLsnTop5PrivateIpAddrGlobalIpAddrInTcpPort OBJECT-TYPE
        SYNTAX DisplayString
        MAX-ACCESS read-only
        STATUS current
        DESCRIPTION
                "The global IP address in the Top 5 private IP address entry."
        ::= { axIpNatLsnTop5PrivateIpAddrTotTcpPortEntry 3 }

--==================================================================
-- axIpNatLsnTop5PrivateIpAddrTotUdpPorts
--==================================================================

    axIpNatLsnTop5PrivateIpAddrTotUdpPortTable OBJECT-TYPE
        SYNTAX SEQUENCE OF AxIpNatLsnTop5PrivateIpAddrTotUdpPortEntry
        MAX-ACCESS not-accessible
        STATUS current
        DESCRIPTION
                "A table containing Top 5 private IPs and total number of UDP ports."
        ::= { axIpNatLsnTop5PrivateIpAddrTotUdpPorts 1 }

    axIpNatLsnTop5PrivateIpAddrTotUdpPortEntry OBJECT-TYPE
        SYNTAX  AxIpNatLsnTop5PrivateIpAddrTotUdpPortEntry
        MAX-ACCESS not-accessible
        STATUS current
        DESCRIPTION
                "Columns in the axIpNatLsnTop5PrivateIpAddrTotUdpPorts Table"
        INDEX {
                axIpNatLsnTop5PrivateIpAddrInUdpPort
        }
        ::= { axIpNatLsnTop5PrivateIpAddrTotUdpPortTable 1 }

    AxIpNatLsnTop5PrivateIpAddrTotUdpPortEntry ::=
        SEQUENCE {
                axIpNatLsnTop5PrivateIpAddrInUdpPort              DisplayString,
                axIpNatLsnTop5PrivateIpAddrTotNumUdpPorts         Integer32,
                axIpNatLsnTop5PrivateIpAddrGlobalIpAddrInUdpPort  DisplayString
        }

    axIpNatLsnTop5PrivateIpAddrInUdpPort OBJECT-TYPE
        SYNTAX DisplayString
        MAX-ACCESS read-only
        STATUS current
        DESCRIPTION
                "The private IP address in the Top 5 private IP address entry."
        ::= { axIpNatLsnTop5PrivateIpAddrTotUdpPortEntry 1 }

    axIpNatLsnTop5PrivateIpAddrTotNumUdpPorts OBJECT-TYPE
        SYNTAX Integer32
        MAX-ACCESS read-only
        STATUS current
        DESCRIPTION
                "The total number of UDP sessions in the Top 5 private IP address entry."
        ::= { axIpNatLsnTop5PrivateIpAddrTotUdpPortEntry 2 }

    axIpNatLsnTop5PrivateIpAddrGlobalIpAddrInUdpPort OBJECT-TYPE
        SYNTAX DisplayString
        MAX-ACCESS read-only
        STATUS current
        DESCRIPTION
                "The global IP address in the Top 5 private IP address entry."
        ::= { axIpNatLsnTop5PrivateIpAddrTotUdpPortEntry 3 }

--==================================================================
-- axIpNatLsnTop5PrivateIpAddrTotIcmpPorts
--==================================================================

    axIpNatLsnTop5PrivateIpAddrTotIcmpPortTable OBJECT-TYPE
        SYNTAX SEQUENCE OF AxIpNatLsnTop5PrivateIpAddrTotIcmpPortEntry
        MAX-ACCESS not-accessible
        STATUS current
        DESCRIPTION
                "A table containing Top 5 private IPs and total number of ICMP ports."
        ::= { axIpNatLsnTop5PrivateIpAddrTotIcmpPorts 1 }

    axIpNatLsnTop5PrivateIpAddrTotIcmpPortEntry OBJECT-TYPE
        SYNTAX  AxIpNatLsnTop5PrivateIpAddrTotIcmpPortEntry
        MAX-ACCESS not-accessible
        STATUS current
        DESCRIPTION
                "Columns in the axIpNatLsnTop5PrivateIpAddrTotIcmpPorts Table"
        INDEX {
                axIpNatLsnTop5PrivateIpAddrInIcmpPort
        }
        ::= { axIpNatLsnTop5PrivateIpAddrTotIcmpPortTable 1 }

    AxIpNatLsnTop5PrivateIpAddrTotIcmpPortEntry ::=
        SEQUENCE {
                axIpNatLsnTop5PrivateIpAddrInIcmpPort              DisplayString,
                axIpNatLsnTop5PrivateIpAddrTotNumIcmpPorts         Integer32,
                axIpNatLsnTop5PrivateIpAddrGlobalIpAddrInIcmpPort  DisplayString
        }

    axIpNatLsnTop5PrivateIpAddrInIcmpPort OBJECT-TYPE
        SYNTAX DisplayString
        MAX-ACCESS read-only
        STATUS current
        DESCRIPTION
                "The private IP address in the Top 5 private IP address entry."
        ::= { axIpNatLsnTop5PrivateIpAddrTotIcmpPortEntry 1 }

    axIpNatLsnTop5PrivateIpAddrTotNumIcmpPorts OBJECT-TYPE
        SYNTAX Integer32
        MAX-ACCESS read-only
        STATUS current
        DESCRIPTION
                "The total number of ICMP sessions in the Top 5 private IP address entry."
        ::= { axIpNatLsnTop5PrivateIpAddrTotIcmpPortEntry 2 }

    axIpNatLsnTop5PrivateIpAddrGlobalIpAddrInIcmpPort OBJECT-TYPE
        SYNTAX DisplayString
        MAX-ACCESS read-only
        STATUS current
        DESCRIPTION
                "The global IP address in the Top 5 private IP address entry."
        ::= { axIpNatLsnTop5PrivateIpAddrTotIcmpPortEntry 3 }

--==================================================================
-- axIpNatLsnTop5UserPrivateIpAddrTotSessions
--==================================================================

    axIpNatLsnTop5UserPrivateIpAddrTotSessionTable OBJECT-TYPE
	SYNTAX SEQUENCE OF AxIpNatLsnTop5UserPrivateIpAddrTotSessionEntry
	MAX-ACCESS not-accessible
	STATUS current
	DESCRIPTION
		"A table containing Top 5 users private IPs and total number of sessions. 
		 To monitor users who use most of resources: pick up global pool IP which
		 ports are most used total of TCP/UDP/ICMP sessions; 
		 then, find out the top 5 users who use the global pool most used total of TCP/UDP/ICMP sessions."
	::= { axIpNatLsnTop5UserPrivateIpAddrTotSessions 1 } 

    axIpNatLsnTop5UserPrivateIpAddrTotSessionEntry OBJECT-TYPE
	SYNTAX  AxIpNatLsnTop5UserPrivateIpAddrTotSessionEntry
	MAX-ACCESS not-accessible
	STATUS current
	DESCRIPTION
		"Columns in the axIpNatLsnTop5UserPrivateIpAddrTotSessions Table"
	INDEX {
		axIpNatLsnTop5UserPrivateIpAddr
	}
	::= { axIpNatLsnTop5UserPrivateIpAddrTotSessionTable 1 } 

    AxIpNatLsnTop5UserPrivateIpAddrTotSessionEntry ::= 
	SEQUENCE {
        	axIpNatLsnTop5UserPrivateIpAddr                 DisplayString,
        	axIpNatLsnTop5UserPrivateIpAddrTotNumSessions   Integer32,
        	axIpNatLsnTop5UserPrivateIpAddrGlobalIpAddr     DisplayString
	}

    axIpNatLsnTop5UserPrivateIpAddr OBJECT-TYPE 
	SYNTAX DisplayString
	MAX-ACCESS read-only
	STATUS current
	DESCRIPTION
		"The private IP address in the Top 5 user entry."
	::= { axIpNatLsnTop5UserPrivateIpAddrTotSessionEntry 1 } 

    axIpNatLsnTop5UserPrivateIpAddrTotNumSessions OBJECT-TYPE 
	SYNTAX Integer32
	MAX-ACCESS read-only
	STATUS current
	DESCRIPTION
		"The total number of TCP/UDP/ICMP sessions in the Top 5 user entry."
	::= { axIpNatLsnTop5UserPrivateIpAddrTotSessionEntry 2 } 

    axIpNatLsnTop5UserPrivateIpAddrGlobalIpAddr OBJECT-TYPE 
	SYNTAX DisplayString
	MAX-ACCESS read-only
	STATUS current
	DESCRIPTION
		"The global IP address in the Top 5 user entry."
	::= { axIpNatLsnTop5UserPrivateIpAddrTotSessionEntry 3 } 

--==================================================================
-- axIpNatLsnTop5UserPrivateIpAddrTotTcpSessions
--==================================================================

    axIpNatLsnTop5UserPrivateIpAddrTotTcpSessionTable OBJECT-TYPE
        SYNTAX SEQUENCE OF AxIpNatLsnTop5UserPrivateIpAddrTotTcpSessionEntry
        MAX-ACCESS not-accessible
        STATUS current
        DESCRIPTION
		"A table containing Top 5 users private IPs and total number of sessions. 
		 To monitor users who use most of resources: pick up global pool IP which
		 ports are most used total of TCP/UDP/ICMP sessions; 
		 then, find out the top 5 users who use the global pool most used total of TCP sessions."
        ::= { axIpNatLsnTop5UserPrivateIpAddrTotTcpSessions 1 }

    axIpNatLsnTop5UserPrivateIpAddrTotTcpSessionEntry OBJECT-TYPE
        SYNTAX  AxIpNatLsnTop5UserPrivateIpAddrTotTcpSessionEntry
        MAX-ACCESS not-accessible
        STATUS current
        DESCRIPTION
                "Columns in the axIpNatLsnTop5UserPrivateIpAddrTotTcpSessions Table"
        INDEX {
                axIpNatLsnTop5UserPrivateIpAddrInTcp
        }
        ::= { axIpNatLsnTop5UserPrivateIpAddrTotTcpSessionTable 1 }

    AxIpNatLsnTop5UserPrivateIpAddrTotTcpSessionEntry ::=
        SEQUENCE {
                axIpNatLsnTop5UserPrivateIpAddrInTcp              DisplayString,
                axIpNatLsnTop5UserPrivateIpAddrTotNumTcpSessions  Integer32,
                axIpNatLsnTop5UserPrivateIpAddrGlobalIpAddrInTcp  DisplayString
        }

    axIpNatLsnTop5UserPrivateIpAddrInTcp OBJECT-TYPE
        SYNTAX DisplayString
        MAX-ACCESS read-only
        STATUS current
        DESCRIPTION
                "The private IP address in the Top 5 user entry."
        ::= { axIpNatLsnTop5UserPrivateIpAddrTotTcpSessionEntry 1 }

    axIpNatLsnTop5UserPrivateIpAddrTotNumTcpSessions OBJECT-TYPE
        SYNTAX Integer32
        MAX-ACCESS read-only
        STATUS current
        DESCRIPTION
                "The total number of TCP sessions in the Top 5 user entry."
        ::= { axIpNatLsnTop5UserPrivateIpAddrTotTcpSessionEntry 2 }

    axIpNatLsnTop5UserPrivateIpAddrGlobalIpAddrInTcp OBJECT-TYPE
        SYNTAX DisplayString
        MAX-ACCESS read-only
        STATUS current
        DESCRIPTION
                "The global IP address in the Top 5 user entry."
        ::= { axIpNatLsnTop5UserPrivateIpAddrTotTcpSessionEntry 3 }

--==================================================================
-- axIpNatLsnTop5UserPrivateIpAddrTotUdpSessions
--==================================================================

    axIpNatLsnTop5UserPrivateIpAddrTotUdpSessionTable OBJECT-TYPE
        SYNTAX SEQUENCE OF AxIpNatLsnTop5UserPrivateIpAddrTotUdpSessionEntry
        MAX-ACCESS not-accessible
        STATUS current
        DESCRIPTION
		"A table containing Top 5 users private IPs and total number of sessions. 
		 To monitor users who use most of resources: pick up global pool IP which
		 ports are most used total of TCP/UDP/ICMP sessions; 
		 then, find out the top 5 users who use the global pool most used total of UDP sessions."
        ::= { axIpNatLsnTop5UserPrivateIpAddrTotUdpSessions 1 }

    axIpNatLsnTop5UserPrivateIpAddrTotUdpSessionEntry OBJECT-TYPE
        SYNTAX  AxIpNatLsnTop5UserPrivateIpAddrTotUdpSessionEntry
        MAX-ACCESS not-accessible
        STATUS current
        DESCRIPTION
                "Columns in the axIpNatLsnTop5UserPrivateIpAddrTotUdpSessions Table"
        INDEX {
                axIpNatLsnTop5UserPrivateIpAddrInUdp
        }
        ::= { axIpNatLsnTop5UserPrivateIpAddrTotUdpSessionTable 1 }

    AxIpNatLsnTop5UserPrivateIpAddrTotUdpSessionEntry ::=
        SEQUENCE {
                axIpNatLsnTop5UserPrivateIpAddrInUdp              DisplayString,
                axIpNatLsnTop5UserPrivateIpAddrTotNumUdpSessions  Integer32,
                axIpNatLsnTop5UserPrivateIpAddrGlobalIpAddrInUdp  DisplayString
        }

    axIpNatLsnTop5UserPrivateIpAddrInUdp OBJECT-TYPE
        SYNTAX DisplayString
        MAX-ACCESS read-only
        STATUS current
        DESCRIPTION
                "The private IP address in the Top 5 user entry."
        ::= { axIpNatLsnTop5UserPrivateIpAddrTotUdpSessionEntry 1 }

    axIpNatLsnTop5UserPrivateIpAddrTotNumUdpSessions OBJECT-TYPE
        SYNTAX Integer32
        MAX-ACCESS read-only
        STATUS current
        DESCRIPTION
                "The total number of UDP sessions in the Top 5 user entry."
        ::= { axIpNatLsnTop5UserPrivateIpAddrTotUdpSessionEntry 2 }

    axIpNatLsnTop5UserPrivateIpAddrGlobalIpAddrInUdp OBJECT-TYPE
        SYNTAX DisplayString
        MAX-ACCESS read-only
        STATUS current
        DESCRIPTION
                "The global IP address in the Top 5 user entry."
        ::= { axIpNatLsnTop5UserPrivateIpAddrTotUdpSessionEntry 3 }

--==================================================================
-- axIpNatLsnTop5UserPrivateIpAddrTotIcmpSessions
--==================================================================

    axIpNatLsnTop5UserPrivateIpAddrTotIcmpSessionTable OBJECT-TYPE
        SYNTAX SEQUENCE OF AxIpNatLsnTop5UserPrivateIpAddrTotIcmpSessionEntry
        MAX-ACCESS not-accessible
        STATUS current
        DESCRIPTION
		"A table containing Top 5 users private IPs and total number of sessions. 
		 To monitor users who use most of resources: pick up global pool IP which
		 ports are most used total of TCP/UDP/ICMP sessions; 
		 then, find out the top 5 users who use the global pool most used total of ICMP sessions."
        ::= { axIpNatLsnTop5UserPrivateIpAddrTotIcmpSessions 1 }

    axIpNatLsnTop5UserPrivateIpAddrTotIcmpSessionEntry OBJECT-TYPE
        SYNTAX  AxIpNatLsnTop5UserPrivateIpAddrTotIcmpSessionEntry
        MAX-ACCESS not-accessible
        STATUS current
        DESCRIPTION
                "Columns in the axIpNatLsnTop5UserPrivateIpAddrTotIcmpSessions Table"
        INDEX {
                axIpNatLsnTop5UserPrivateIpAddrInIcmp
        }
        ::= { axIpNatLsnTop5UserPrivateIpAddrTotIcmpSessionTable 1 }

    AxIpNatLsnTop5UserPrivateIpAddrTotIcmpSessionEntry ::=
        SEQUENCE {
                axIpNatLsnTop5UserPrivateIpAddrInIcmp              DisplayString,
                axIpNatLsnTop5UserPrivateIpAddrTotNumIcmpSessions  Integer32,
                axIpNatLsnTop5UserPrivateIpAddrGlobalIpAddrInIcmp  DisplayString
        }

    axIpNatLsnTop5UserPrivateIpAddrInIcmp OBJECT-TYPE
        SYNTAX DisplayString
        MAX-ACCESS read-only
        STATUS current
        DESCRIPTION
                "The private IP address in the Top 5 user entry."
        ::= { axIpNatLsnTop5UserPrivateIpAddrTotIcmpSessionEntry 1 }

    axIpNatLsnTop5UserPrivateIpAddrTotNumIcmpSessions OBJECT-TYPE
        SYNTAX Integer32
        MAX-ACCESS read-only
        STATUS current
        DESCRIPTION
                "The total number of ICMP sessions in the Top 5 user entry."
        ::= { axIpNatLsnTop5UserPrivateIpAddrTotIcmpSessionEntry 2 }

    axIpNatLsnTop5UserPrivateIpAddrGlobalIpAddrInIcmp OBJECT-TYPE
        SYNTAX DisplayString
        MAX-ACCESS read-only
        STATUS current
        DESCRIPTION
                "The global IP address in the Top 5 user entry."
        ::= { axIpNatLsnTop5UserPrivateIpAddrTotIcmpSessionEntry 3 }

--==================================================================
-- axIpNatLsnTop5GlobalPoolIpAddrTotUsers
--==================================================================
    axIpNatLsnTop5GlobalPoolIpAddrTotUserTable OBJECT-TYPE
	SYNTAX SEQUENCE OF AxIpNatLsnTop5GlobalPoolIpAddrTotUserEntry
	MAX-ACCESS not-accessible
	STATUS current
	DESCRIPTION
		"A table containing Top 5 global pool IPs and total number of users."
	::= { axIpNatLsnTop5GlobalPoolIpAddrTotUsers 1 } 

    axIpNatLsnTop5GlobalPoolIpAddrTotUserEntry OBJECT-TYPE
	SYNTAX  AxIpNatLsnTop5GlobalPoolIpAddrTotUserEntry
	MAX-ACCESS not-accessible
	STATUS current
	DESCRIPTION
		"Columns in the axIpNatLsnTop5GlobalPoolIpAddrTotUsers Table"
	INDEX {
		axIpNatLsnTop5GlobalPoolIpAddr
	}
	::= { axIpNatLsnTop5GlobalPoolIpAddrTotUserTable 1 } 

    AxIpNatLsnTop5GlobalPoolIpAddrTotUserEntry ::= 
	SEQUENCE {
        	axIpNatLsnTop5GlobalPoolIpAddr              DisplayString,
        	axIpNatLsnTop5GlobalPoolIpAddrTotNumUsers   Integer32
	}

    axIpNatLsnTop5GlobalPoolIpAddr OBJECT-TYPE 
	SYNTAX DisplayString
	MAX-ACCESS read-only
	STATUS current
	DESCRIPTION
		"The global pool IP address in the Top 5 global pool IPs entry."
	::= { axIpNatLsnTop5GlobalPoolIpAddrTotUserEntry 1 } 

    axIpNatLsnTop5GlobalPoolIpAddrTotNumUsers OBJECT-TYPE 
	SYNTAX Integer32
	MAX-ACCESS read-only
	STATUS current
	DESCRIPTION
		"The total number of users in the Top 5 global pool IPs entry."
	::= { axIpNatLsnTop5GlobalPoolIpAddrTotUserEntry 2 } 

--==================================================================
-- axIpNatLsnTop5GlobalPoolIpAddrTotTcpPorts
--==================================================================
    axIpNatLsnTop5GlobalPoolIpAddrTotTcpPortTable OBJECT-TYPE
        SYNTAX SEQUENCE OF AxIpNatLsnTop5GlobalPoolIpAddrTotTcpPortEntry
        MAX-ACCESS not-accessible
        STATUS current
        DESCRIPTION
                "A table containing Top 5 global pool IPs and total number of TCP ports."
        ::= { axIpNatLsnTop5GlobalPoolIpAddrTotTcpPorts 1 }

    axIpNatLsnTop5GlobalPoolIpAddrTotTcpPortEntry OBJECT-TYPE
        SYNTAX  AxIpNatLsnTop5GlobalPoolIpAddrTotTcpPortEntry
        MAX-ACCESS not-accessible
        STATUS current
        DESCRIPTION
                "Columns in the axIpNatLsnTop5GlobalPoolIpAddrTotTcpPorts Table"
        INDEX {
                axIpNatLsnTop5GlobalPoolIpAddrInTcp
        }
        ::= { axIpNatLsnTop5GlobalPoolIpAddrTotTcpPortTable 1 }

    AxIpNatLsnTop5GlobalPoolIpAddrTotTcpPortEntry ::=
        SEQUENCE {
                axIpNatLsnTop5GlobalPoolIpAddrInTcp            DisplayString,
                axIpNatLsnTop5GlobalPoolIpAddrTotNumTcpPorts   Integer32
        }

    axIpNatLsnTop5GlobalPoolIpAddrInTcp OBJECT-TYPE
        SYNTAX DisplayString
        MAX-ACCESS read-only
        STATUS current
        DESCRIPTION
                "The global pool IP address in the Top 5 global pool IPs entry."
        ::= { axIpNatLsnTop5GlobalPoolIpAddrTotTcpPortEntry 1 }

    axIpNatLsnTop5GlobalPoolIpAddrTotNumTcpPorts OBJECT-TYPE
        SYNTAX Integer32
        MAX-ACCESS read-only
        STATUS current
        DESCRIPTION
                "The total number of TCP ports in the Top 5 global pool IPs entry."
        ::= { axIpNatLsnTop5GlobalPoolIpAddrTotTcpPortEntry 2 }

--==================================================================
-- axIpNatLsnTop5GlobalPoolIpAddrTotUdpPorts
--==================================================================
    axIpNatLsnTop5GlobalPoolIpAddrTotUdpPortTable OBJECT-TYPE
        SYNTAX SEQUENCE OF AxIpNatLsnTop5GlobalPoolIpAddrTotUdpPortEntry
        MAX-ACCESS not-accessible
        STATUS current
        DESCRIPTION
                "A table containing Top 5 global pool IPs and total number of UDP ports."
        ::= { axIpNatLsnTop5GlobalPoolIpAddrTotUdpPorts 1 }

    axIpNatLsnTop5GlobalPoolIpAddrTotUdpPortEntry OBJECT-TYPE
        SYNTAX  AxIpNatLsnTop5GlobalPoolIpAddrTotUdpPortEntry
        MAX-ACCESS not-accessible
        STATUS current
        DESCRIPTION
                "Columns in the axIpNatLsnTop5GlobalPoolIpAddrTotUdpPorts Table"
        INDEX {
                axIpNatLsnTop5GlobalPoolIpAddrInUdp
        }
        ::= { axIpNatLsnTop5GlobalPoolIpAddrTotUdpPortTable 1 }

    AxIpNatLsnTop5GlobalPoolIpAddrTotUdpPortEntry ::=
        SEQUENCE {
                axIpNatLsnTop5GlobalPoolIpAddrInUdp            DisplayString,
                axIpNatLsnTop5GlobalPoolIpAddrTotNumUdpPorts   Integer32
        }

    axIpNatLsnTop5GlobalPoolIpAddrInUdp OBJECT-TYPE
        SYNTAX DisplayString
        MAX-ACCESS read-only
        STATUS current
        DESCRIPTION
                "The global pool IP address in the Top 5 global pool IPs entry."
        ::= { axIpNatLsnTop5GlobalPoolIpAddrTotUdpPortEntry 1 }

    axIpNatLsnTop5GlobalPoolIpAddrTotNumUdpPorts OBJECT-TYPE
        SYNTAX Integer32
        MAX-ACCESS read-only
        STATUS current
        DESCRIPTION
                "The total number of UDP ports in the Top 5 global pool IPs entry."
        ::= { axIpNatLsnTop5GlobalPoolIpAddrTotUdpPortEntry 2 }

--==================================================================
-- axIpNatLsnAlgSipStats
--==================================================================

    axIpNatLsnAlgSipStatMethodRegister OBJECT-TYPE
     SYNTAX Counter64
     MAX-ACCESS  read-only
     STATUS  current
     DESCRIPTION
     "The number of Sip method register on Ip Nat Lsn."
     ::= {axIpNatLsnAlgSipStats 1}

    axIpNatLsnAlgSipStatMethodInvite OBJECT-TYPE
     SYNTAX Counter64
     MAX-ACCESS  read-only
     STATUS  current
     DESCRIPTION
     "The number of Sip method invite on Ip Nat Lsn."
     ::= {axIpNatLsnAlgSipStats 2}

   axIpNatLsnAlgSipStatMethodAck OBJECT-TYPE
     SYNTAX Counter64
     MAX-ACCESS  read-only
     STATUS  current
     DESCRIPTION
     "The number of Sip method Ack on Ip Nat Lsn."
     ::= {axIpNatLsnAlgSipStats 3}

   axIpNatLsnAlgSipStatMethodCancel OBJECT-TYPE
     SYNTAX Counter64
     MAX-ACCESS  read-only
     STATUS  current
     DESCRIPTION
     "The number of Sip method cancel on Ip Nat Lsn."
     ::= {axIpNatLsnAlgSipStats 4}

   axIpNatLsnAlgSipStatMethodBye OBJECT-TYPE
     SYNTAX Counter64
     MAX-ACCESS  read-only
     STATUS  current
     DESCRIPTION
     "The number of Sip method bye on Ip Nat Lsn."
     ::= {axIpNatLsnAlgSipStats 5}

   axIpNatLsnAlgSipStatMethodOptions OBJECT-TYPE
     SYNTAX Counter64
     MAX-ACCESS  read-only
     STATUS  current
     DESCRIPTION
     "The number of Sip method options on Ip Nat Lsn."
     ::= {axIpNatLsnAlgSipStats 6}

   axIpNatLsnAlgSipStatMethodPrack OBJECT-TYPE
     SYNTAX Counter64
     MAX-ACCESS  read-only
     STATUS  current
     DESCRIPTION
     "The number of Sip method Prack on Ip Nat Lsn."
     ::= {axIpNatLsnAlgSipStats 7}

   axIpNatLsnAlgSipStatMethodSubscribe OBJECT-TYPE
     SYNTAX Counter64
     MAX-ACCESS  read-only
     STATUS  current
     DESCRIPTION
     "The number of Sip method subscribte on Ip Nat Lsn."
     ::= {axIpNatLsnAlgSipStats 8}

   axIpNatLsnAlgSipStatMethodNotify OBJECT-TYPE
     SYNTAX Counter64
     MAX-ACCESS  read-only
     STATUS  current
     DESCRIPTION
     "The number of Sip method notify on Ip Nat Lsn."
     ::= {axIpNatLsnAlgSipStats 9}

   axIpNatLsnAlgSipStatMethodPublish OBJECT-TYPE
     SYNTAX Counter64
     MAX-ACCESS  read-only
     STATUS  current
     DESCRIPTION
     "The number of Sip method publish on Ip Nat Lsn."
     ::= {axIpNatLsnAlgSipStats 10}

   axIpNatLsnAlgSipStatMethodInfo OBJECT-TYPE
     SYNTAX Counter64
     MAX-ACCESS  read-only
     STATUS  current
     DESCRIPTION
     "The number of Sip method info on Ip Nat Lsn."
     ::= {axIpNatLsnAlgSipStats 11}

   axIpNatLsnAlgSipStatMethodRefer OBJECT-TYPE
     SYNTAX Counter64
     MAX-ACCESS  read-only
     STATUS  current
     DESCRIPTION
     "The number of Sip method refer on Ip Nat Lsn."
     ::= {axIpNatLsnAlgSipStats 12}

   axIpNatLsnAlgSipStatMethodMessage OBJECT-TYPE
     SYNTAX Counter64
     MAX-ACCESS  read-only
     STATUS  current
     DESCRIPTION
     "The number of Sip method message on Ip Nat Lsn."
     ::= {axIpNatLsnAlgSipStats 13}

   axIpNatLsnAlgSipStatMethodUpdate OBJECT-TYPE
     SYNTAX Counter64
     MAX-ACCESS  read-only
     STATUS  current
     DESCRIPTION
     "The number of Sip method update on Ip Nat Lsn."
     ::= {axIpNatLsnAlgSipStats 14}

   axIpNatLsnAlgSipStatMethodUnknown OBJECT-TYPE
     SYNTAX Counter64
     MAX-ACCESS  read-only
     STATUS  current
     DESCRIPTION
     "The number of Sip method unknown on Ip Nat Lsn."
     ::= {axIpNatLsnAlgSipStats 15}

--==================================================================
-- axIpNatLsnPoolStats
--==================================================================

   axIpNatLsnDataSessionUsed OBJECT-TYPE
     SYNTAX CounterBasedGauge64
     MAX-ACCESS  read-only
     STATUS  deprecated
     DESCRIPTION
     "The total number of data sessions used on lsn."
     ::= {axIpNatLsnPoolStats 1}

   axIpNatLsnDataSessionFreed OBJECT-TYPE
     SYNTAX CounterBasedGauge64
     MAX-ACCESS  read-only
     STATUS  deprecated
     DESCRIPTION
     "The total number of data sessions freed on lsn."
     ::= {axIpNatLsnPoolStats 2}

   axIpNatLsnTCPNatPortUsed OBJECT-TYPE
     SYNTAX CounterBasedGauge64
     MAX-ACCESS  read-only
     STATUS  deprecated
     DESCRIPTION
     "The total number of tcp nat ports used on lsn."
     ::= {axIpNatLsnPoolStats 3}

   axIpNatLsnTCPNatPortFree OBJECT-TYPE
     SYNTAX CounterBasedGauge64
     MAX-ACCESS  read-only
     STATUS  deprecated
     DESCRIPTION
     "The total number of tcp nat ports freed on lsn."
     ::= {axIpNatLsnPoolStats 4}

   axIpNatLsnUDPNatPortUsed OBJECT-TYPE
     SYNTAX CounterBasedGauge64
     MAX-ACCESS  read-only
     STATUS  deprecated
     DESCRIPTION
     "The total number of udp nat ports used on lsn."
     ::= {axIpNatLsnPoolStats 5}

   axIpNatLsnUDPNatPortFree OBJECT-TYPE
     SYNTAX CounterBasedGauge64
     MAX-ACCESS  read-only
     STATUS  deprecated
     DESCRIPTION
     "The total number of udp nat ports freed onlsn."
     ::= {axIpNatLsnPoolStats 6}

   axIpNatLsnPoolStatTable OBJECT-TYPE
	 SYNTAX SEQUENCE OF AxIpNatLsnPoolStatEntry
	 MAX-ACCESS not-accessible
	 STATUS deprecated
	 DESCRIPTION
		"A table has information of IP NAT Lsn Pool Statistics.  It can only return the total pool entries up to 1000."
	 ::= { axIpNatLsnPoolStats 11 } 

   axIpNatLsnPoolStatEntry OBJECT-TYPE
	 SYNTAX  AxIpNatLsnPoolStatEntry
	 MAX-ACCESS not-accessible
	 STATUS current
	 DESCRIPTION
		"Columns in the axIpNatLsnPoolStats Table"
	 INDEX {
		axIpNatLsnPoolStatPoolName, axIpNatLsnPoolStatAddress
	 }
	 ::= { axIpNatLsnPoolStatTable 1 } 

   AxIpNatLsnPoolStatEntry ::= 
	 SEQUENCE {
        	axIpNatLsnPoolStatPoolName      DisplayString,
        	axIpNatLsnPoolStatAddress       DisplayString,
        	axIpNatLsnPoolStatUsers         CounterBasedGauge64,
        	axIpNatLsnPoolStatIcmpUsed      CounterBasedGauge64,
            axIpNatLsnPoolStatIcmpFreed     CounterBasedGauge64,
            axIpNatLsnPoolStatIcmpTotal     CounterBasedGauge64,
            axIpNatLsnPoolStatIcmpReserved  CounterBasedGauge64,
            axIpNatLsnPoolStatIcmpPeak      Counter64,
            axIpNatLsnPoolStatIcmpHitFull   CounterBasedGauge64,
        	axIpNatLsnPoolStatTcpUsed       CounterBasedGauge64,
            axIpNatLsnPoolStatTcpFreed      CounterBasedGauge64,
            axIpNatLsnPoolStatTcpTotal      CounterBasedGauge64,
            axIpNatLsnPoolStatTcpReserved   CounterBasedGauge64,
            axIpNatLsnPoolStatTcpPeak       Counter64,
            axIpNatLsnPoolStatTcpHitFull    CounterBasedGauge64,
        	axIpNatLsnPoolStatUdpUsed       CounterBasedGauge64,
            axIpNatLsnPoolStatUdpFreed      CounterBasedGauge64,
            axIpNatLsnPoolStatUdpTotal      CounterBasedGauge64,
            axIpNatLsnPoolStatUdpReserved   CounterBasedGauge64,
            axIpNatLsnPoolStatUdpPeak       Counter64,
            axIpNatLsnPoolStatUdpHitFull    CounterBasedGauge64
	} 

    axIpNatLsnPoolStatPoolName OBJECT-TYPE 
	  SYNTAX DisplayString
	  MAX-ACCESS read-only
	  STATUS current
	  DESCRIPTION
		"The name of the pool."
	  ::= { axIpNatLsnPoolStatEntry 1 } 

    axIpNatLsnPoolStatAddress OBJECT-TYPE 
	  SYNTAX DisplayString
	  MAX-ACCESS read-only
	  STATUS current
	  DESCRIPTION
		"The IP address of the server."
	  ::= { axIpNatLsnPoolStatEntry 2 } 

    axIpNatLsnPoolStatUsers OBJECT-TYPE 
	  SYNTAX CounterBasedGauge64
	  MAX-ACCESS read-only
	  STATUS current
	  DESCRIPTION
		"The number of users in the pool."
	  ::= { axIpNatLsnPoolStatEntry 3 } 

    axIpNatLsnPoolStatIcmpUsed OBJECT-TYPE 
	  SYNTAX CounterBasedGauge64
	  MAX-ACCESS read-only
	  STATUS current
	  DESCRIPTION
		"The number of port icmp used in the pool."
	  ::= { axIpNatLsnPoolStatEntry 4 } 

    axIpNatLsnPoolStatIcmpFreed OBJECT-TYPE 
	  SYNTAX CounterBasedGauge64
	  MAX-ACCESS read-only
	  STATUS current
	  DESCRIPTION
		"The number of port icmp freed in the pool."
	  ::= { axIpNatLsnPoolStatEntry 5 } 

    axIpNatLsnPoolStatIcmpTotal OBJECT-TYPE 
	  SYNTAX CounterBasedGauge64
	  MAX-ACCESS read-only
	  STATUS current
	  DESCRIPTION
		"The total number of icmp ports in the pool."
	  ::= { axIpNatLsnPoolStatEntry 6 } 

    axIpNatLsnPoolStatIcmpReserved OBJECT-TYPE 
	  SYNTAX CounterBasedGauge64
	  MAX-ACCESS read-only
	  STATUS current
	  DESCRIPTION
		"The number reserved icmp ports in the pool."
	  ::= { axIpNatLsnPoolStatEntry 7 } 

    axIpNatLsnPoolStatIcmpPeak OBJECT-TYPE 
	  SYNTAX Counter64
	  MAX-ACCESS read-only
	  STATUS current
	  DESCRIPTION
		"The number of icmp ports in the peak for the pool."
	  ::= { axIpNatLsnPoolStatEntry 8 } 

    axIpNatLsnPoolStatIcmpHitFull OBJECT-TYPE 
	  SYNTAX CounterBasedGauge64
	  MAX-ACCESS read-only
	  STATUS current
	  DESCRIPTION
		"The number of times port limit reached for ICMP port allocation in the pool."
	  ::= { axIpNatLsnPoolStatEntry 9 } 

    axIpNatLsnPoolStatTcpUsed OBJECT-TYPE 
	  SYNTAX CounterBasedGauge64
	  MAX-ACCESS read-only
	  STATUS current
	  DESCRIPTION
		"The number of port tcp used in the pool."
	  ::= { axIpNatLsnPoolStatEntry 10 } 

    axIpNatLsnPoolStatTcpFreed OBJECT-TYPE 
	  SYNTAX CounterBasedGauge64
	  MAX-ACCESS read-only
	  STATUS current
	  DESCRIPTION
		"The number of port tcp freed in the pool."
	  ::= { axIpNatLsnPoolStatEntry 11 } 

    axIpNatLsnPoolStatTcpTotal OBJECT-TYPE 
	  SYNTAX CounterBasedGauge64
	  MAX-ACCESS read-only
	  STATUS current
	  DESCRIPTION
		"The total number of tcp ports in the pool."
	  ::= { axIpNatLsnPoolStatEntry 12 } 

    axIpNatLsnPoolStatTcpReserved OBJECT-TYPE 
	  SYNTAX CounterBasedGauge64
	  MAX-ACCESS read-only
	  STATUS current
	  DESCRIPTION
		"The number reserved tcp ports in the pool."
	  ::= { axIpNatLsnPoolStatEntry 13 } 

    axIpNatLsnPoolStatTcpPeak OBJECT-TYPE 
	  SYNTAX Counter64
	  MAX-ACCESS read-only
	  STATUS current
	  DESCRIPTION
		"The number of tcp ports in the peak for the pool."
	  ::= { axIpNatLsnPoolStatEntry 14 } 

    axIpNatLsnPoolStatTcpHitFull OBJECT-TYPE 
	  SYNTAX CounterBasedGauge64
	  MAX-ACCESS read-only
	  STATUS current
	  DESCRIPTION
		"The number of times port limit reached for TCP port allocation in the pool."
	  ::= { axIpNatLsnPoolStatEntry 15 } 

    axIpNatLsnPoolStatUdpUsed OBJECT-TYPE 
	  SYNTAX CounterBasedGauge64
	  MAX-ACCESS read-only
	  STATUS current
	  DESCRIPTION
		"The number of port udp used in the pool."
	  ::= { axIpNatLsnPoolStatEntry 16 } 

    axIpNatLsnPoolStatUdpFreed OBJECT-TYPE 
	  SYNTAX CounterBasedGauge64
	  MAX-ACCESS read-only
	  STATUS current
	  DESCRIPTION
		"The number of port Udpicmp freed in the pool."
	  ::= { axIpNatLsnPoolStatEntry 17 } 

    axIpNatLsnPoolStatUdpTotal OBJECT-TYPE 
	  SYNTAX CounterBasedGauge64
	  MAX-ACCESS read-only
	  STATUS current
	  DESCRIPTION
		"The total number of icmp ports in the pool."
	  ::= { axIpNatLsnPoolStatEntry 18 } 

    axIpNatLsnPoolStatUdpReserved OBJECT-TYPE 
	  SYNTAX CounterBasedGauge64
	  MAX-ACCESS read-only
	  STATUS current
	  DESCRIPTION
		"The number reserved icmp ports in the pool."
	  ::= { axIpNatLsnPoolStatEntry 19 } 

    axIpNatLsnPoolStatUdpPeak OBJECT-TYPE 
	  SYNTAX Counter64
	  MAX-ACCESS read-only
	  STATUS current
	  DESCRIPTION
		"The number of udp ports in the peak for the pool."
	  ::= { axIpNatLsnPoolStatEntry 20 } 

    axIpNatLsnPoolStatUdpHitFull OBJECT-TYPE 
	  SYNTAX CounterBasedGauge64
	  MAX-ACCESS read-only
	  STATUS current
	  DESCRIPTION
		"The number of times port limit reached for UDP port allocation in the pool."
	  ::= { axIpNatLsnPoolStatEntry 21 } 

   axIpNatLsnPoolNameStatTable OBJECT-TYPE
	 SYNTAX SEQUENCE OF AxIpNatLsnPoolNameStatEntry
	 MAX-ACCESS not-accessible
	 STATUS current
	 DESCRIPTION
		"A table has information of IP NAT Lsn Pool Statistics group by the pool name."
	 ::= { axIpNatLsnPoolStats 12 } 

   axIpNatLsnPoolNameStatEntry OBJECT-TYPE
	 SYNTAX  AxIpNatLsnPoolNameStatEntry
	 MAX-ACCESS not-accessible
	 STATUS current
	 DESCRIPTION
		"Columns in the axIpNatLsnPoolNameStats Table"
	 INDEX {
		axIpNatLsnPoolNameStatPoolName
	 }
	 ::= { axIpNatLsnPoolNameStatTable 1 } 

   AxIpNatLsnPoolNameStatEntry ::= 
	 SEQUENCE {
        	axIpNatLsnPoolNameStatPoolName      DisplayString,
        	axIpNatLsnPoolNameStatAddress       DisplayString,
        	axIpNatLsnPoolNameEndAddress        DisplayString,
        	axIpNatLsnPoolNameStatUsers         CounterBasedGauge64,
        	axIpNatLsnPoolNameStatIcmpUsed      CounterBasedGauge64,
		axIpNatLsnPoolNameStatIcmpFreed     CounterBasedGauge64,
		axIpNatLsnPoolNameStatIcmpTotal     CounterBasedGauge64,
		axIpNatLsnPoolNameStatIcmpReserved  CounterBasedGauge64,
		axIpNatLsnPoolNameStatIcmpPeak      Counter64,
		axIpNatLsnPoolNameStatIcmpHitFull   CounterBasedGauge64,
        	axIpNatLsnPoolNameStatTcpUsed       CounterBasedGauge64,
		axIpNatLsnPoolNameStatTcpFreed      CounterBasedGauge64,
		axIpNatLsnPoolNameStatTcpTotal      CounterBasedGauge64,
		axIpNatLsnPoolNameStatTcpReserved   CounterBasedGauge64,
		axIpNatLsnPoolNameStatTcpPeak       Counter64,
		axIpNatLsnPoolNameStatTcpHitFull    CounterBasedGauge64,
        	axIpNatLsnPoolNameStatUdpUsed       CounterBasedGauge64,
		axIpNatLsnPoolNameStatUdpFreed      CounterBasedGauge64,
		axIpNatLsnPoolNameStatUdpTotal      CounterBasedGauge64,
		axIpNatLsnPoolNameStatUdpReserved   CounterBasedGauge64,
		axIpNatLsnPoolNameStatUdpPeak       Counter64,
		axIpNatLsnPoolNameStatUdpHitFull    CounterBasedGauge64
	} 

    axIpNatLsnPoolNameStatPoolName OBJECT-TYPE 
	  SYNTAX DisplayString
	  MAX-ACCESS read-only
	  STATUS current
	  DESCRIPTION
		"The name of the pool."
	  ::= { axIpNatLsnPoolNameStatEntry 1 } 

    axIpNatLsnPoolNameStatAddress OBJECT-TYPE 
	  SYNTAX DisplayString
	  MAX-ACCESS read-only
	  STATUS current
	  DESCRIPTION
		"The pool start IP address."
	  ::= { axIpNatLsnPoolNameStatEntry 2 } 

    axIpNatLsnPoolNameEndAddress OBJECT-TYPE 
	  SYNTAX DisplayString
	  MAX-ACCESS read-only
	  STATUS current
	  DESCRIPTION
		"The pool end IP address."
	  ::= { axIpNatLsnPoolNameStatEntry 3 } 

    axIpNatLsnPoolNameStatUsers OBJECT-TYPE 
	  SYNTAX CounterBasedGauge64
	  MAX-ACCESS read-only
	  STATUS current
	  DESCRIPTION
		"The number of users in the pool."
	  ::= { axIpNatLsnPoolNameStatEntry 4 } 

    axIpNatLsnPoolNameStatIcmpUsed OBJECT-TYPE 
	  SYNTAX CounterBasedGauge64
	  MAX-ACCESS read-only
	  STATUS current
	  DESCRIPTION
		"The number of port icmp used in the pool."
	  ::= { axIpNatLsnPoolNameStatEntry 5 } 

    axIpNatLsnPoolNameStatIcmpFreed OBJECT-TYPE 
	  SYNTAX CounterBasedGauge64
	  MAX-ACCESS read-only
	  STATUS current
	  DESCRIPTION
		"The number of port icmp freed in the pool."
	  ::= { axIpNatLsnPoolNameStatEntry 6 } 

    axIpNatLsnPoolNameStatIcmpTotal OBJECT-TYPE 
	  SYNTAX CounterBasedGauge64
	  MAX-ACCESS read-only
	  STATUS current
	  DESCRIPTION
		"The total number of icmp ports in the pool."
	  ::= { axIpNatLsnPoolNameStatEntry 7 } 

    axIpNatLsnPoolNameStatIcmpReserved OBJECT-TYPE 
	  SYNTAX CounterBasedGauge64
	  MAX-ACCESS read-only
	  STATUS current
	  DESCRIPTION
		"The number reserved icmp ports in the pool."
	  ::= { axIpNatLsnPoolNameStatEntry 8 } 

    axIpNatLsnPoolNameStatIcmpPeak OBJECT-TYPE 
	  SYNTAX Counter64
	  MAX-ACCESS read-only
	  STATUS current
	  DESCRIPTION
		"The number of icmp ports in the peak for the pool."
	  ::= { axIpNatLsnPoolNameStatEntry 9 } 

    axIpNatLsnPoolNameStatIcmpHitFull OBJECT-TYPE 
	  SYNTAX CounterBasedGauge64
	  MAX-ACCESS read-only
	  STATUS current
	  DESCRIPTION
		"The number of times port limit reached for ICMP port allocation in the pool."
	  ::= { axIpNatLsnPoolNameStatEntry 10 } 

    axIpNatLsnPoolNameStatTcpUsed OBJECT-TYPE 
	  SYNTAX CounterBasedGauge64
	  MAX-ACCESS read-only
	  STATUS current
	  DESCRIPTION
		"The number of port tcp used in the pool."
	  ::= { axIpNatLsnPoolNameStatEntry 11 } 

    axIpNatLsnPoolNameStatTcpFreed OBJECT-TYPE 
	  SYNTAX CounterBasedGauge64
	  MAX-ACCESS read-only
	  STATUS current
	  DESCRIPTION
		"The number of port tcp freed in the pool."
	  ::= { axIpNatLsnPoolNameStatEntry 12 } 

    axIpNatLsnPoolNameStatTcpTotal OBJECT-TYPE 
	  SYNTAX CounterBasedGauge64
	  MAX-ACCESS read-only
	  STATUS current
	  DESCRIPTION
		"The total number of tcp ports in the pool."
	  ::= { axIpNatLsnPoolNameStatEntry 13 } 

    axIpNatLsnPoolNameStatTcpReserved OBJECT-TYPE 
	  SYNTAX CounterBasedGauge64
	  MAX-ACCESS read-only
	  STATUS current
	  DESCRIPTION
		"The number reserved tcp ports in the pool."
	  ::= { axIpNatLsnPoolNameStatEntry 14 } 

    axIpNatLsnPoolNameStatTcpPeak OBJECT-TYPE 
	  SYNTAX Counter64
	  MAX-ACCESS read-only
	  STATUS current
	  DESCRIPTION
		"The number of tcp ports in the peak for the pool."
	  ::= { axIpNatLsnPoolNameStatEntry 15 } 

    axIpNatLsnPoolNameStatTcpHitFull OBJECT-TYPE 
	  SYNTAX CounterBasedGauge64
	  MAX-ACCESS read-only
	  STATUS current
	  DESCRIPTION
		"The number of times port limit reached for TCP port allocation in the pool."
	  ::= { axIpNatLsnPoolNameStatEntry 16 } 

    axIpNatLsnPoolNameStatUdpUsed OBJECT-TYPE 
	  SYNTAX CounterBasedGauge64
	  MAX-ACCESS read-only
	  STATUS current
	  DESCRIPTION
		"The number of port udp used in the pool."
	  ::= { axIpNatLsnPoolNameStatEntry 17 } 

    axIpNatLsnPoolNameStatUdpFreed OBJECT-TYPE 
	  SYNTAX CounterBasedGauge64
	  MAX-ACCESS read-only
	  STATUS current
	  DESCRIPTION
		"The number of port Udpicmp freed in the pool."
	  ::= { axIpNatLsnPoolNameStatEntry 18 } 

    axIpNatLsnPoolNameStatUdpTotal OBJECT-TYPE 
	  SYNTAX CounterBasedGauge64
	  MAX-ACCESS read-only
	  STATUS current
	  DESCRIPTION
		"The total number of icmp ports in the pool."
	  ::= { axIpNatLsnPoolNameStatEntry 19 } 

    axIpNatLsnPoolNameStatUdpReserved OBJECT-TYPE 
	  SYNTAX CounterBasedGauge64
	  MAX-ACCESS read-only
	  STATUS current
	  DESCRIPTION
		"The number reserved icmp ports in the pool."
	  ::= { axIpNatLsnPoolNameStatEntry 20 } 

    axIpNatLsnPoolNameStatUdpPeak OBJECT-TYPE 
	  SYNTAX Counter64
	  MAX-ACCESS read-only
	  STATUS current
	  DESCRIPTION
		"The number of udp ports in the peak for the pool."
	  ::= { axIpNatLsnPoolNameStatEntry 21 } 

    axIpNatLsnPoolNameStatUdpHitFull OBJECT-TYPE 
	  SYNTAX CounterBasedGauge64
	  MAX-ACCESS read-only
	  STATUS current
	  DESCRIPTION
		"The number of times port limit reached for UDP port allocation in the pool."
	  ::= { axIpNatLsnPoolNameStatEntry 22 } 

--======================axIpNatLsnPoolGroupIpUsageTable====================

   axIpNatLsnPoolGroup     OBJECT IDENTIFIER ::= { axIpNatLsnPoolStats 13 }

   axIpNatLsnPoolGroupCount OBJECT-TYPE 
	  SYNTAX INTEGER
	  MAX-ACCESS read-only
	  STATUS current
	  DESCRIPTION
		"The number of pool group in the system."
	  ::= { axIpNatLsnPoolGroup 1 } 

   axIpNatLsnPoolGroupTable OBJECT-TYPE
	 SYNTAX SEQUENCE OF AxIpNatLsnPoolGroupEntry
	 MAX-ACCESS not-accessible
	 STATUS current
	 DESCRIPTION
		"Table has information of IP NAT Lsn Pool group statistics indexed by the pool group name."
	 ::= { axIpNatLsnPoolGroup 2 } 

   axIpNatLsnPoolGroupEntry OBJECT-TYPE
	 SYNTAX  AxIpNatLsnPoolGroupEntry
	 MAX-ACCESS not-accessible
	 STATUS current
	 DESCRIPTION
		"Columns in the axIpNatLsnPoolGroup Table"
	 INDEX {
		axIpNatLsnPoolGroupName
	 }
	 ::= { axIpNatLsnPoolGroupTable 1 } 

   AxIpNatLsnPoolGroupEntry ::= 
	 SEQUENCE {
       	axIpNatLsnPoolGroupName   	    	DisplayString,
		axIpNatLsnPoolGroupUsers	 		CounterBasedGauge64,
       	axIpNatLsnPoolGroupIcmpUsed      	CounterBasedGauge64,
		axIpNatLsnPoolGroupIcmpFreed     	CounterBasedGauge64,
		axIpNatLsnPoolGroupIcmpTotal     	CounterBasedGauge64,
		axIpNatLsnPoolGroupIcmpReserved  	CounterBasedGauge64,
		axIpNatLsnPoolGroupIcmpPeak      	Counter64,
		axIpNatLsnPoolGroupIcmpHitFull   	CounterBasedGauge64,
       	axIpNatLsnPoolGroupTcpUsed       	CounterBasedGauge64,
		axIpNatLsnPoolGroupTcpFreed      	CounterBasedGauge64,
		axIpNatLsnPoolGroupTcpTotal      	CounterBasedGauge64,
		axIpNatLsnPoolGroupTcpReserved   	CounterBasedGauge64,
		axIpNatLsnPoolGroupTcpPeak       	Counter64,
		axIpNatLsnPoolGroupTcpHitFull  		CounterBasedGauge64,
       	axIpNatLsnPoolGroupUdpUsed       	CounterBasedGauge64,
		axIpNatLsnPoolGroupUdpFreed      	CounterBasedGauge64,
		axIpNatLsnPoolGroupUdpTotal      	CounterBasedGauge64,
		axIpNatLsnPoolGroupUdpReserved   	CounterBasedGauge64,
		axIpNatLsnPoolGroupUdpPeak       	Counter64,
		axIpNatLsnPoolGroupUdpHitFull     	CounterBasedGauge64,
		axIpNatLsnPoolGroupTotalIp     		CounterBasedGauge64,
		axIpNatLsnPoolGroupUsedIp     		CounterBasedGauge64,
		axIpNatLsnPoolGroupFreedIp     		CounterBasedGauge64
	} 

    axIpNatLsnPoolGroupName OBJECT-TYPE 
	  SYNTAX DisplayString
	  MAX-ACCESS read-only
	  STATUS current
	  DESCRIPTION
		"The name of the pool group."
	  ::= { axIpNatLsnPoolGroupEntry 1 } 

    axIpNatLsnPoolGroupUsers OBJECT-TYPE 
	  SYNTAX CounterBasedGauge64
	  MAX-ACCESS read-only
	  STATUS current
	  DESCRIPTION
		"The number of users in the pool group."
	  ::= { axIpNatLsnPoolGroupEntry 2 } 

    axIpNatLsnPoolGroupIcmpUsed OBJECT-TYPE 
	  SYNTAX CounterBasedGauge64
	  MAX-ACCESS read-only
	  STATUS current
	  DESCRIPTION
		"The number of port icmp used in the pool group."
	  ::= { axIpNatLsnPoolGroupEntry 3 } 

    axIpNatLsnPoolGroupIcmpFreed OBJECT-TYPE 
	  SYNTAX CounterBasedGauge64
	  MAX-ACCESS read-only
	  STATUS current
	  DESCRIPTION
		"The number of ICMP ports freed in the pool group."
	  ::= { axIpNatLsnPoolGroupEntry 4 } 

    axIpNatLsnPoolGroupIcmpTotal OBJECT-TYPE 
	  SYNTAX CounterBasedGauge64
	  MAX-ACCESS read-only
	  STATUS current
	  DESCRIPTION
		"The total number of ICMP ports in the pool group."
	  ::= { axIpNatLsnPoolGroupEntry 5 } 

    axIpNatLsnPoolGroupIcmpReserved OBJECT-TYPE 
	  SYNTAX CounterBasedGauge64
	  MAX-ACCESS read-only
	  STATUS current
	  DESCRIPTION
		"The number reserved ICMP ports in the pool group."
	  ::= { axIpNatLsnPoolGroupEntry 6 } 

    axIpNatLsnPoolGroupIcmpPeak OBJECT-TYPE 
	  SYNTAX Counter64
	  MAX-ACCESS read-only
	  STATUS current
	  DESCRIPTION
		"The peak number of ICMP ports for the pool group."
	  ::= { axIpNatLsnPoolGroupEntry 7 } 

    axIpNatLsnPoolGroupIcmpHitFull OBJECT-TYPE 
	  SYNTAX CounterBasedGauge64
	  MAX-ACCESS read-only
	  STATUS current
	  DESCRIPTION
		"The number of times port limit reached for ICMP port allocation in the pool group."
	  ::= { axIpNatLsnPoolGroupEntry 8 } 

    axIpNatLsnPoolGroupTcpUsed OBJECT-TYPE 
	  SYNTAX CounterBasedGauge64
	  MAX-ACCESS read-only
	  STATUS current
	  DESCRIPTION
		"The number of TCP ports used in the pool group."
	  ::= { axIpNatLsnPoolGroupEntry 9 } 

    axIpNatLsnPoolGroupTcpFreed OBJECT-TYPE 
	  SYNTAX CounterBasedGauge64
	  MAX-ACCESS read-only
	  STATUS current
	  DESCRIPTION
		"The number of TCP ports freed in the pool group."
	  ::= { axIpNatLsnPoolGroupEntry 10 } 

    axIpNatLsnPoolGroupTcpTotal OBJECT-TYPE 
	  SYNTAX CounterBasedGauge64
	  MAX-ACCESS read-only
	  STATUS current
	  DESCRIPTION
		"The total number of tcp ports in the pool group."
	  ::= { axIpNatLsnPoolGroupEntry 11 } 

    axIpNatLsnPoolGroupTcpReserved OBJECT-TYPE 
	  SYNTAX CounterBasedGauge64
	  MAX-ACCESS read-only
	  STATUS current
	  DESCRIPTION
		"The number of reserved TCP ports in the pool group."
	  ::= { axIpNatLsnPoolGroupEntry 12 } 

    axIpNatLsnPoolGroupTcpPeak OBJECT-TYPE 
	  SYNTAX Counter64
	  MAX-ACCESS read-only
	  STATUS current
	  DESCRIPTION
		"The peak number of TCP ports for the pool group."
	  ::= { axIpNatLsnPoolGroupEntry 13 } 

    axIpNatLsnPoolGroupTcpHitFull OBJECT-TYPE 
	  SYNTAX CounterBasedGauge64
	  MAX-ACCESS read-only
	  STATUS current
	  DESCRIPTION
		"The number of times port limit reached for TCP port allocation in the pool group."
	  ::= { axIpNatLsnPoolGroupEntry 14 } 

    axIpNatLsnPoolGroupUdpUsed OBJECT-TYPE 
	  SYNTAX CounterBasedGauge64
	  MAX-ACCESS read-only
	  STATUS current
	  DESCRIPTION
		"The number of UDP ports used in the pool group."
	  ::= { axIpNatLsnPoolGroupEntry 15 } 

    axIpNatLsnPoolGroupUdpFreed OBJECT-TYPE 
	  SYNTAX CounterBasedGauge64
	  MAX-ACCESS read-only
	  STATUS current
	  DESCRIPTION
		"The number of UDP ports freed in the pool group."
	  ::= { axIpNatLsnPoolGroupEntry 16 } 

    axIpNatLsnPoolGroupUdpTotal OBJECT-TYPE 
	  SYNTAX CounterBasedGauge64
	  MAX-ACCESS read-only
	  STATUS current
	  DESCRIPTION
		"The total number of UDP ports in the pool group."
	  ::= { axIpNatLsnPoolGroupEntry 17 } 

    axIpNatLsnPoolGroupUdpReserved OBJECT-TYPE 
	  SYNTAX CounterBasedGauge64
	  MAX-ACCESS read-only
	  STATUS current
	  DESCRIPTION
		"The number of reserved UDP ports in the pool group."
	  ::= { axIpNatLsnPoolGroupEntry 18 } 

    axIpNatLsnPoolGroupUdpPeak OBJECT-TYPE 
	  SYNTAX Counter64
	  MAX-ACCESS read-only
	  STATUS current
	  DESCRIPTION
		"The peak number of UDP ports for the pool group."
	  ::= { axIpNatLsnPoolGroupEntry 19 } 

    axIpNatLsnPoolGroupUdpHitFull OBJECT-TYPE 
	  SYNTAX CounterBasedGauge64
	  MAX-ACCESS read-only
	  STATUS current
	  DESCRIPTION
		"The number of times port limit reached for UDP port allocation in the pool group."
	  ::= { axIpNatLsnPoolGroupEntry 20 } 


    axIpNatLsnPoolGroupTotalIp OBJECT-TYPE 
	  SYNTAX CounterBasedGauge64
	  MAX-ACCESS read-only
	  STATUS current
	  DESCRIPTION
		"Total number of IP addressed in the pool group."
	  ::= { axIpNatLsnPoolGroupEntry 21 } 

    axIpNatLsnPoolGroupUsedIp OBJECT-TYPE 
	  SYNTAX CounterBasedGauge64
	  MAX-ACCESS read-only
	  STATUS current
	  DESCRIPTION
		"The number of IP addressed used in the pool group."
	  ::= { axIpNatLsnPoolGroupEntry 22 } 

    axIpNatLsnPoolGroupFreedIp OBJECT-TYPE 
	  SYNTAX CounterBasedGauge64
	  MAX-ACCESS read-only
	  STATUS current
	  DESCRIPTION
		"The number of ip freed in the pool group."
	  ::= { axIpNatLsnPoolGroupEntry 23 } 


--==================================================================
-- axIpNatLsnRadiusStats
--==================================================================

    axIpNatLsnMSISDNReceived OBJECT-TYPE
     SYNTAX CounterBasedGauge64
     MAX-ACCESS read-only
     STATUS  current
     DESCRIPTION
     "The MSISDN received on lsn radius server."
     ::= { axIpNatLsnRadiusStats 1 }

    axIpNatLsnRadiusIMEIReceived OBJECT-TYPE
     SYNTAX CounterBasedGauge64
     MAX-ACCESS read-only
     STATUS  current
     DESCRIPTION
     "The IMEI received on lsn radius server."
     ::= { axIpNatLsnRadiusStats 2 }

    axIpNatLsnRadiusIMSIReceived OBJECT-TYPE
     SYNTAX CounterBasedGauge64
     MAX-ACCESS read-only
     STATUS  current
     DESCRIPTION
     "The IMSI received on lsn radius server."
     ::= { axIpNatLsnRadiusStats 3 }

    axIpNatLsnCustAttrReceived OBJECT-TYPE
     SYNTAX CounterBasedGauge64
     MAX-ACCESS read-only
     STATUS  current
     DESCRIPTION
     "The custom attribute received on lsn radius server."
     ::= { axIpNatLsnRadiusStats 4 }

    axIpNatLsnRadiusRequestReceived OBJECT-TYPE
     SYNTAX CounterBasedGauge64
     MAX-ACCESS read-only
     STATUS  current
     DESCRIPTION
     "The radius request received on lsn radius server."
     ::= { axIpNatLsnRadiusStats 5 }

    axIpNatLsnRadiusRequestBadSecretDropped OBJECT-TYPE
     SYNTAX CounterBasedGauge64
     MAX-ACCESS read-only
     STATUS  current
     DESCRIPTION
     "The radius request bad secret dropped on lsn radius server."
     ::= { axIpNatLsnRadiusStats 6 }

    axIpNatLsnRadiusRequestNoKeyAttrDropped OBJECT-TYPE
     SYNTAX CounterBasedGauge64
     MAX-ACCESS read-only
     STATUS  current
     DESCRIPTION
     "The radius request no key attribute dropped on lsn radius server."
     ::= { axIpNatLsnRadiusStats 7 }

    axIpNatLsnRadiusRequestMalFormedDropped OBJECT-TYPE
     SYNTAX CounterBasedGauge64
     MAX-ACCESS read-only
     STATUS  current
     DESCRIPTION
     "The malformed radius request dropped on lsn radius server."
     ::= { axIpNatLsnRadiusStats 8 }

    axIpNatLsnRadiusRequestIgnored OBJECT-TYPE
     SYNTAX CounterBasedGauge64
     MAX-ACCESS read-only
     STATUS  current
     DESCRIPTION
     "The radius request ignored on lsn radius server."
     ::= { axIpNatLsnRadiusStats 9 }

    axIpNatLsnRadiusRequestTableFullDropped OBJECT-TYPE
     SYNTAX CounterBasedGauge64
     MAX-ACCESS read-only
     STATUS  current
     DESCRIPTION
     "The radius request table full dropped on lsn radius server."
     ::= { axIpNatLsnRadiusStats 10 }

    axIpNatLsnHAStandbyDropped OBJECT-TYPE
     SYNTAX CounterBasedGauge64
     MAX-ACCESS read-only
     STATUS  current
     DESCRIPTION
     "The HA standby dropped on lsn radius server."
     ::= { axIpNatLsnRadiusStats 11 }

    axIpNatLsnRadiusSecretNotConfigDropped OBJECT-TYPE
     SYNTAX CounterBasedGauge64
     MAX-ACCESS read-only
     STATUS  current
     DESCRIPTION
     "The non-configured secret dropped on lsn radius server."
     ::= { axIpNatLsnRadiusStats 12 }

--==================================================================
-- axNat64Stat
--==================================================================

    axIpNatNat64StatsGlobal            OBJECT IDENTIFIER ::= { axIpNatNat64Stats 1 }

    axIpNatNat64StatTotalTcpPortAlloc OBJECT-TYPE
     SYNTAX Counter64
     MAX-ACCESS read-only
     STATUS  current
     DESCRIPTION
     "The total TCP ports allocted for the NAT64."
     ::= { axIpNatNat64StatsGlobal 1 }

    axIpNatNat64StatTotalTcpPortFreed OBJECT-TYPE
     SYNTAX Counter64
     MAX-ACCESS read-only
     STATUS  current
     DESCRIPTION
     "The total TCP ports freed for the NAT64."
     ::= { axIpNatNat64StatsGlobal 2 }

    axIpNatNat64StatTotalUdpPortAlloc OBJECT-TYPE
     SYNTAX Counter64
     MAX-ACCESS read-only
     STATUS  current
     DESCRIPTION
     "The total UDP ports allocted for the NAT64."
     ::= { axIpNatNat64StatsGlobal 3 }

    axIpNatNat64StatTotalUdpPortFreed OBJECT-TYPE
     SYNTAX Counter64
     MAX-ACCESS read-only
     STATUS  current
     DESCRIPTION
     "The total UDP ports allocted for the NAT64."
     ::= { axIpNatNat64StatsGlobal 4 }

    axIpNatNat64StatTotalIcmpPortAlloc OBJECT-TYPE
     SYNTAX Counter64
     MAX-ACCESS read-only
     STATUS  current
     DESCRIPTION
     "The total ICMP ports allocted for the NAT64."
     ::= { axIpNatNat64StatsGlobal 5 }

    axIpNatNat64StatTotalIcmpPortFreed OBJECT-TYPE
     SYNTAX Counter64
     MAX-ACCESS read-only
     STATUS  current
     DESCRIPTION
     "The total ICMP ports allocted for the NAT64."
     ::= { axIpNatNat64StatsGlobal 6 }

    axIpNatNat64StatDataSessionCreated OBJECT-TYPE
     SYNTAX Counter64
     MAX-ACCESS read-only
     STATUS  current
     DESCRIPTION
     "The number of session created for the NAT64."
     ::= { axIpNatNat64StatsGlobal 7 }

    axIpNatNat64StatDataSessionFreed OBJECT-TYPE
     SYNTAX Counter64
     MAX-ACCESS read-only
     STATUS  current
     DESCRIPTION
     "The number of session freed for the NAT64."
     ::= { axIpNatNat64StatsGlobal 8 }

    axIpNatNat64UserQuotaCreated OBJECT-TYPE
     SYNTAX Counter64
     MAX-ACCESS read-only
     STATUS  current
     DESCRIPTION
     "The number of user quota created for the NAT64."
     ::= { axIpNatNat64StatsGlobal 9 }

    axIpNatNat64UserQuotaFreed OBJECT-TYPE
     SYNTAX Counter64
     MAX-ACCESS read-only
     STATUS  current
     DESCRIPTION
     "The number of user quota freed for the NAT64."
     ::= { axIpNatNat64StatsGlobal 10 }

    axIpNatNat64UserQuotaCreateFailed OBJECT-TYPE
     SYNTAX Counter64
     MAX-ACCESS read-only
     STATUS  current
     DESCRIPTION
     "The number of user quota creation failed for the NAT64."
     ::= { axIpNatNat64StatsGlobal 11 }

    axIpNatNat64StatTcpNatPortUnAvail OBJECT-TYPE
     SYNTAX Counter64
     MAX-ACCESS read-only
     STATUS  current
     DESCRIPTION
     "The number of unavailable TCP NAT ports NAT64."
     ::= { axIpNatNat64StatsGlobal 12 }

    axIpNatNat64StatUdpNatPortUnAvail OBJECT-TYPE
     SYNTAX Counter64
     MAX-ACCESS read-only
     STATUS  current
     DESCRIPTION
     "The number of unavailable UDP NAT ports for the NAT64."
     ::= { axIpNatNat64StatsGlobal 13 }
  
    axIpNatNat64StatIcmpNatPortUnavail OBJECT-TYPE
     SYNTAX Counter64
     MAX-ACCESS read-only
     STATUS  current
     DESCRIPTION
     "The number of unavailable ICM NAT ports for the NAT64."
     ::= { axIpNatNat64StatsGlobal 14 }

    axIpNatNat64StatNewUserResourceUnAvail OBJECT-TYPE
     SYNTAX Counter64
     MAX-ACCESS read-only
     STATUS  current
     DESCRIPTION
     "The number of unavailable new user resource for the NAT64."
     ::= { axIpNatNat64StatsGlobal 15 }

    axIpNatNat64StatTcpUserQuotaExceed OBJECT-TYPE
     SYNTAX Counter64
     MAX-ACCESS read-only
     STATUS  current
     DESCRIPTION
     "The number of exceeding TCP user quota for the NAT64."
     ::= { axIpNatNat64StatsGlobal 16 }
  
    axIpNatNat64StatUdpUserQuotaExceed OBJECT-TYPE
     SYNTAX Counter64
     MAX-ACCESS read-only
     STATUS  current
     DESCRIPTION
     "The number of exceeding UDP user quota for the NAT64."
     ::= { axIpNatNat64StatsGlobal 17 }

    axIpNatNat64StatIcmpUserQuotaExceed OBJECT-TYPE
     SYNTAX Counter64
     MAX-ACCESS read-only
     STATUS  current
     DESCRIPTION
     "The total ICMP ports allocted for the NAT64."
     ::= { axIpNatNat64StatsGlobal 18 }

    axIpNatNat64StatExtendedUserQuotaMatched OBJECT-TYPE
     SYNTAX Counter64
     MAX-ACCESS read-only
     STATUS  current
     DESCRIPTION
     "The number of Extended user quota matched for the NAT64."
     ::= { axIpNatNat64StatsGlobal 19 }
 
    axIpNatNat64StatExtendedUserQuotaExceeded OBJECT-TYPE
     SYNTAX Counter64
     MAX-ACCESS read-only
     STATUS  current
     DESCRIPTION
     "The number of exceeded extend user quota for the NAT64."
     ::= { axIpNatNat64StatsGlobal 20 }

    axIpNatNat64StatTcpFullConeSessionCreated OBJECT-TYPE
     SYNTAX Counter64
     MAX-ACCESS read-only
     STATUS  current
     DESCRIPTION
     "The number of created TCP full cone session for the NAT64."
     ::= { axIpNatNat64StatsGlobal 21 }

    axIpNatNat64StatTcpFullConeSessionFreed OBJECT-TYPE
     SYNTAX Counter64
     MAX-ACCESS read-only
     STATUS  current
     DESCRIPTION
     "The number of freed TCP full cone session for the NAT64."
     ::= { axIpNatNat64StatsGlobal 22 }

    axIpNatNat64StatUdpFullConeSessionCreated OBJECT-TYPE
     SYNTAX Counter64
     MAX-ACCESS read-only
     STATUS  current
     DESCRIPTION
     "The number of created UDP full cone session for the NAT64."
     ::= { axIpNatNat64StatsGlobal 23 }

    axIpNatNat64StatUdpFullConeSessionFreed OBJECT-TYPE
     SYNTAX Counter64
     MAX-ACCESS read-only
     STATUS  current
     DESCRIPTION
     "The total ICMP ports allocted for the NAT64."
     ::= { axIpNatNat64StatsGlobal 24 }

    axIpNatNat64StatFullConeSessionFailed OBJECT-TYPE
     SYNTAX Counter64
     MAX-ACCESS read-only
     STATUS  current
     DESCRIPTION
     "The number of failed full cone session for the NAT64."
     ::= { axIpNatNat64StatsGlobal 25 }

    axIpNatNat64StatHairpinSessionCreated OBJECT-TYPE
     SYNTAX Counter64
     MAX-ACCESS read-only
     STATUS  current
     DESCRIPTION
     "The number of created hairpin session for the NAT64."
     ::= { axIpNatNat64StatsGlobal 26 }

    axIpNatNat64StatSelfHairpinDrop OBJECT-TYPE
     SYNTAX Counter64
     MAX-ACCESS read-only
     STATUS  current
     DESCRIPTION
     "The number of self hairpin drop for the NAT64."
     ::= { axIpNatNat64StatsGlobal 27 }

    axIpNatNat64StatEndpointIndependentMapMatched OBJECT-TYPE
     SYNTAX Counter64
     MAX-ACCESS read-only
     STATUS  current
     DESCRIPTION
     "The number of  endpoint independent mapping for the NAT64."
     ::= { axIpNatNat64StatsGlobal 28 }

    axIpNatNat64StatEndpointIndependentFilterMatched OBJECT-TYPE
     SYNTAX Counter64
     MAX-ACCESS read-only
     STATUS  current
     DESCRIPTION
     "The number of endpoint indenpendent filtering matched for the NAT64."
     ::= { axIpNatNat64StatsGlobal 29 }

    axIpNatNat64StatEndpointDependentFilterDrop OBJECT-TYPE
     SYNTAX Counter64
     MAX-ACCESS read-only
     STATUS  current
     DESCRIPTION
     "The number of endpoint independent filtering drop for the NAT64."
     ::= { axIpNatNat64StatsGlobal 30 }

    axIpNatNat64StatLayer3ForwardPackets OBJECT-TYPE
     SYNTAX Counter64
     MAX-ACCESS read-only
     STATUS  current
     DESCRIPTION
     "The number of packets NAT64 layer 3 forwarded."
     ::= { axIpNatNat64StatsGlobal 31 }

    axIpNatNat64StatSourceAddrPrefixMatchDrop OBJECT-TYPE
     SYNTAX Counter64
     MAX-ACCESS read-only
     STATUS  current
     DESCRIPTION
     "The number of drop of source address prefix match for the NAT64."
     ::= { axIpNatNat64StatsGlobal 32 }

    axIpNatNat64StatLsnLidDrop  OBJECT-TYPE
     SYNTAX Counter64
     MAX-ACCESS read-only
     STATUS  current
     DESCRIPTION
     "The number of drop of lsn lid for the NAT64."
     ::= { axIpNatNat64StatsGlobal 33 }

    axIpNatNat64StatLsnLidPassThrough OBJECT-TYPE
     SYNTAX Counter64
     MAX-ACCESS read-only
     STATUS  current
     DESCRIPTION
     "The number of pass through of lsn lid for the NAT64."
     ::= { axIpNatNat64StatsGlobal 34 }

    axIpNatNat64StatNoClassListMatch OBJECT-TYPE
     SYNTAX Counter64
     MAX-ACCESS read-only
     STATUS  current
     DESCRIPTION
     "The number of no class list match for the NAT64."
     ::= { axIpNatNat64StatsGlobal 35 }

    axIpNatNat64StatNatPoolMismatchDrop OBJECT-TYPE
     SYNTAX Counter64
     MAX-ACCESS read-only
     STATUS  current
     DESCRIPTION
     "The number of nat pool mismatch drop for the NAT64."
     ::= { axIpNatNat64StatsGlobal 36 }

    axIpNatNat64StatDataSessionUserQuotaExceeded OBJECT-TYPE
     SYNTAX Counter64
     MAX-ACCESS read-only
     STATUS  current
     DESCRIPTION
     "The number of data session user-quota exceeded."
     ::= { axIpNatNat64StatsGlobal 37 }

    axIpNatNat64StatConnRateUserQuotaExceeded OBJECT-TYPE
     SYNTAX Counter64
     MAX-ACCESS read-only
     STATUS  current
     DESCRIPTION
     "The number of connection rate user-quota exceeded."
     ::= { axIpNatNat64StatsGlobal 38 }

    axIpNatNat64StatEndPointIndependentFilteringInboundLimitExceeded OBJECT-TYPE
     SYNTAX Counter64
     MAX-ACCESS read-only
     STATUS  current
     DESCRIPTION
     "The number of endpoint independent filtering inbound limit exceeded."
     ::= { axIpNatNat64StatsGlobal 39 }

    axIpNatNat64StatTcpPortOverloaded OBJECT-TYPE
     SYNTAX Counter64
     MAX-ACCESS read-only
     STATUS  current
     DESCRIPTION
     "The number of TCP port overloaded."
     ::= { axIpNatNat64StatsGlobal 40 }

    axIpNatNat64StatUdpPortOverloaded OBJECT-TYPE
     SYNTAX Counter64
     MAX-ACCESS read-only
     STATUS  current
     DESCRIPTION
     "The number of UDP port overloaded."
     ::= { axIpNatNat64StatsGlobal 41 }

    axIpNatNat64StatTcpPortOverloadingSessionCreated OBJECT-TYPE
     SYNTAX Counter64
     MAX-ACCESS read-only
     STATUS  current
     DESCRIPTION
     "The number of TCP port overloading session created."
     ::= { axIpNatNat64StatsGlobal 42 }

    axIpNatNat64StatUdpPortOverloadingSessionCreated OBJECT-TYPE
     SYNTAX Counter64
     MAX-ACCESS read-only
     STATUS  current
     DESCRIPTION
     "The number of UDP port overloading session created."
     ::= { axIpNatNat64StatsGlobal 43 }

    axIpNatNat64StatTcpPortOverloadingSessionFreed OBJECT-TYPE
     SYNTAX Counter64
     MAX-ACCESS read-only
     STATUS  current
     DESCRIPTION
     "The number of TCP port overloading session Freed."
     ::= { axIpNatNat64StatsGlobal 44 }

    axIpNatNat64StatUdpPortOverloadingSessionFreed OBJECT-TYPE
     SYNTAX Counter64
     MAX-ACCESS read-only
     STATUS  current
     DESCRIPTION
     "The number of UDP port overloading session Freed."
     ::= { axIpNatNat64StatsGlobal 45 }

    axIpNatNat64StatNatPoolUnusable OBJECT-TYPE
     SYNTAX Counter64
     MAX-ACCESS read-only
     STATUS  current
     DESCRIPTION
     "The number of nat pool unusable."
     ::= { axIpNatNat64StatsGlobal 46 }

    axIpNatNat64StatHANatPoolUnusable OBJECT-TYPE
     SYNTAX Counter64
     MAX-ACCESS read-only
     STATUS  current
     DESCRIPTION
     "The number of HA nat pool unusable."
     ::= { axIpNatNat64StatsGlobal 47 }

    axIpNatNat64StatNoRadiusProfileMatch OBJECT-TYPE
     SYNTAX Counter64
     MAX-ACCESS read-only
     STATUS  current
     DESCRIPTION
     "The number of no radius profile match."
     ::= { axIpNatNat64StatsGlobal 48 }

--==================================================================
-- axDsLiteStat
--==================================================================

axIpNatDsliteStatsGlobal            OBJECT IDENTIFIER ::= { axIpNatDsliteStats 1 }

    axIpNatDsliteStatTotalTcpPortAlloc OBJECT-TYPE
     SYNTAX Counter64
     MAX-ACCESS read-only
     STATUS  current
     DESCRIPTION
     "The total TCP ports allocted for the DsLite."
     ::= { axIpNatDsliteStatsGlobal 1 }

    axIpNatDsliteStatTotalTcpPortFreed OBJECT-TYPE
     SYNTAX Counter64
     MAX-ACCESS read-only
     STATUS  current
     DESCRIPTION
     "The total TCP ports freed for the DsLite."
     ::= { axIpNatDsliteStatsGlobal 2 }

    axIpNatDsliteStatTotalUdpPortAlloc OBJECT-TYPE
     SYNTAX Counter64
     MAX-ACCESS read-only
     STATUS  current
     DESCRIPTION
     "The total UDP ports allocted for the DsLite."
     ::= { axIpNatDsliteStatsGlobal 3 }

    axIpNatDsliteStatTotalUdpPortFreed OBJECT-TYPE
     SYNTAX Counter64
     MAX-ACCESS read-only
     STATUS  current
     DESCRIPTION
     "The total UDP ports allocted for the DsLite."
     ::= { axIpNatDsliteStatsGlobal 4 }

    axIpNatDsliteStatTotalIcmpPortAlloc OBJECT-TYPE
     SYNTAX Counter64
     MAX-ACCESS read-only
     STATUS  current
     DESCRIPTION
     "The total ICMP ports allocted for the DsLite."
     ::= { axIpNatDsliteStatsGlobal 5 }

    axIpNatDsliteStatTotalIcmpPortFreed OBJECT-TYPE
     SYNTAX Counter64
     MAX-ACCESS read-only
     STATUS  current
     DESCRIPTION
     "The total ICMP ports freed for the DsLite."
     ::= { axIpNatDsliteStatsGlobal 6 }

    axIpNatDsliteStatDataSessionCreated OBJECT-TYPE
     SYNTAX Counter64
     MAX-ACCESS read-only
     STATUS  current
     DESCRIPTION
     "The number of session created for the DsLite."
     ::= { axIpNatDsliteStatsGlobal 7 }

    axIpNatDsliteStatDataSessionFreed OBJECT-TYPE
     SYNTAX Counter64
     MAX-ACCESS read-only
     STATUS  current
     DESCRIPTION
     "The number of session freed for the DsLite."
     ::= { axIpNatDsliteStatsGlobal 8 }

    axIpNatDsliteUserQuotaCreated OBJECT-TYPE
     SYNTAX Counter64
     MAX-ACCESS read-only
     STATUS  current
     DESCRIPTION
     "The number of user quota created for the DsLite."
     ::= { axIpNatDsliteStatsGlobal 9 }

    axIpNatDsliteUserQuotaFreed OBJECT-TYPE
     SYNTAX Counter64
     MAX-ACCESS read-only
     STATUS  current
     DESCRIPTION
     "The number of user quota freed for the DsLite."
     ::= { axIpNatDsliteStatsGlobal 10 }

    axIpNatDsliteUserQuotaCreateFailed OBJECT-TYPE
     SYNTAX Counter64
     MAX-ACCESS read-only
     STATUS  current
     DESCRIPTION
     "The number of user quota creation failed for the DsLite."
     ::= { axIpNatDsliteStatsGlobal 11 }

    axIpNatDsliteStatTcpNatPortUnAvail OBJECT-TYPE
     SYNTAX Counter64
     MAX-ACCESS read-only
     STATUS  current
     DESCRIPTION
     "The number of unavailable TCP NAT ports DsLite."
     ::= { axIpNatDsliteStatsGlobal 12 }

    axIpNatDsliteStatUdpNatPortUnAvail OBJECT-TYPE
     SYNTAX Counter64
     MAX-ACCESS read-only
     STATUS  current
     DESCRIPTION
     "The number of unavailable UDP NAT ports for the DsLite."
     ::= { axIpNatDsliteStatsGlobal 13 }
  
    axIpNatDsliteStatIcmpNatPortUnavail OBJECT-TYPE
     SYNTAX Counter64
     MAX-ACCESS read-only
     STATUS  current
     DESCRIPTION
     "The number of unavailable ICM NAT ports for the DsLite."
     ::= { axIpNatDsliteStatsGlobal 14 }

    axIpNatDsliteStatNewUserResourceUnAvail OBJECT-TYPE
     SYNTAX Counter64
     MAX-ACCESS read-only
     STATUS  current
     DESCRIPTION
     "The number of unavailable new user resource for the DsLite."
     ::= { axIpNatDsliteStatsGlobal 15 }

    axIpNatDsliteStatTcpUserQuotaExceed OBJECT-TYPE
     SYNTAX Counter64
     MAX-ACCESS read-only
     STATUS  current
     DESCRIPTION
     "The number of exceeding TCP user quota for the DsLite."
     ::= { axIpNatDsliteStatsGlobal 16 }
  
    axIpNatDsliteStatUdpUserQuotaExceed OBJECT-TYPE
     SYNTAX Counter64
     MAX-ACCESS read-only
     STATUS  current
     DESCRIPTION
     "The number of exceeding UDP user quota for the DsLite."
     ::= { axIpNatDsliteStatsGlobal 17 }

    axIpNatDsliteStatIcmpUserQuotaExceed OBJECT-TYPE
     SYNTAX Counter64
     MAX-ACCESS read-only
     STATUS  current
     DESCRIPTION
     "The total ICMP ports allocted for the DsLite."
     ::= { axIpNatDsliteStatsGlobal 18 }

    axIpNatDsliteStatExtendedUserQuotaMatched OBJECT-TYPE
     SYNTAX Counter64
     MAX-ACCESS read-only
     STATUS  current
     DESCRIPTION
     "The number of Extended user quota matched for the DsLite."
     ::= { axIpNatDsliteStatsGlobal 19 }
 
    axIpNatDsliteStatExtendedUserQuotaExceeded OBJECT-TYPE
     SYNTAX Counter64
     MAX-ACCESS read-only
     STATUS  current
     DESCRIPTION
     "The number of exceeded extend user quota for the DsLite."
     ::= { axIpNatDsliteStatsGlobal 20 }

    axIpNatDsliteStatTcpFullConeSessionCreated OBJECT-TYPE
     SYNTAX Counter64
     MAX-ACCESS read-only
     STATUS  current
     DESCRIPTION
     "The number of created TCP full cone session for the DsLite."
     ::= { axIpNatDsliteStatsGlobal 21 }

    axIpNatDsliteStatTcpFullConeSessionFreed OBJECT-TYPE
     SYNTAX Counter64
     MAX-ACCESS read-only
     STATUS  current
     DESCRIPTION
     "The number of freed TCP full cone session for the DsLite."
     ::= { axIpNatDsliteStatsGlobal 22 }

    axIpNatDsliteStatUdpFullConeSessionCreated OBJECT-TYPE
     SYNTAX Counter64
     MAX-ACCESS read-only
     STATUS  current
     DESCRIPTION
     "The number of created UDP full cone session for the DsLite."
     ::= { axIpNatDsliteStatsGlobal 23 }

    axIpNatDsLiteStatUdpFullConeSessionFreed OBJECT-TYPE
     SYNTAX Counter64
     MAX-ACCESS read-only
     STATUS  current
     DESCRIPTION
     "The total ICMP ports allocted for the DsLite."
     ::= { axIpNatDsliteStatsGlobal 24 }

    axIpNatDsLiteStatFullConeSessionFailed OBJECT-TYPE
     SYNTAX Counter64
     MAX-ACCESS read-only
     STATUS  current
     DESCRIPTION
     "The number of failed full cone session for the DsLite."
     ::= { axIpNatDsliteStatsGlobal 25 }

    axIpNatDsliteStatHairpinSessionCreated OBJECT-TYPE
     SYNTAX Counter64
     MAX-ACCESS read-only
     STATUS  current
     DESCRIPTION
     "The number of created hairpin session for the DsLite."
     ::= { axIpNatDsliteStatsGlobal 26 }

    axIpNatDsliteStatSelfHairpinDrop OBJECT-TYPE
     SYNTAX Counter64
     MAX-ACCESS read-only
     STATUS  current
     DESCRIPTION
     "The number of self hairpin drop for the DsLite."
     ::= { axIpNatDsliteStatsGlobal 27 }

    axIpNatDsliteStatEndpointIndependentMapMatched OBJECT-TYPE
     SYNTAX Counter64
     MAX-ACCESS read-only
     STATUS  current
     DESCRIPTION
     "The number of  endpoint independent mapping for the DsLite."
     ::= { axIpNatDsliteStatsGlobal 28 }

    axIpNatDsliteStatEndpointIndependentFilterMatched OBJECT-TYPE
     SYNTAX Counter64
     MAX-ACCESS read-only
     STATUS  current
     DESCRIPTION
     "The number of endpoint indenpendent filtering matched for the DsLite."
     ::= { axIpNatDsliteStatsGlobal 29 }

    axIpNatDsliteStatEndpointDependentFilterDrop OBJECT-TYPE
     SYNTAX Counter64
     MAX-ACCESS read-only
     STATUS  current
     DESCRIPTION
     "The number of endpoint independent filtering drop for the DsLite."
     ::= { axIpNatDsliteStatsGlobal 30 }

    axIpNatDsliteStatTruncatedPacket OBJECT-TYPE
     SYNTAX Counter64
     MAX-ACCESS read-only
     STATUS  current
     DESCRIPTION
     "The number of truncated packets for the DsLite."
     ::= { axIpNatDsliteStatsGlobal 31 }

   axIpNatDsliteStatLsnLidDrop OBJECT-TYPE
     SYNTAX Counter64
     MAX-ACCESS read-only
     STATUS  current
     DESCRIPTION
     "The number of drop of lsn lid for the DsLite."
     ::= { axIpNatDsliteStatsGlobal 32 }

    axIpNatDsliteStatLsnLidPassThrough OBJECT-TYPE
     SYNTAX Counter64
     MAX-ACCESS read-only
     STATUS  current
     DESCRIPTION
     "The number of pass through of lsn lid for the DsLite."
     ::= { axIpNatDsliteStatsGlobal 33 }

    axIpNatDsliteStatNoClassListMatch OBJECT-TYPE
     SYNTAX Counter64
     MAX-ACCESS read-only
     STATUS  current
     DESCRIPTION
     "The number of no class list match for the DsLite."
     ::= { axIpNatDsliteStatsGlobal 34 }

    axIpNatDsliteStatPermitClassListDrop OBJECT-TYPE
     SYNTAX Counter64
     MAX-ACCESS read-only
     STATUS  current
     DESCRIPTION
     "The number of drop of permit class list for the DsLite."
     ::= { axIpNatDsliteStatsGlobal 35 }

    axIpNatDsliteStatDataSessionUserQuotaExceeded OBJECT-TYPE
     SYNTAX Counter64
     MAX-ACCESS read-only
     STATUS  current
     DESCRIPTION
     "The number of data session user quota exceeded for the DsLite."
     ::= { axIpNatDsliteStatsGlobal 36 }

    axIpNatDsliteStatConnRateUserQuotaExceeded OBJECT-TYPE
     SYNTAX Counter64
     MAX-ACCESS read-only
     STATUS  current
     DESCRIPTION
     "The number of connect rate user quota exceeded for the DsLite."
     ::= { axIpNatDsliteStatsGlobal 37 }

    axIpNatDsliteStatEndpointIndependentFilterInboundLimitExceeded OBJECT-TYPE
     SYNTAX Counter64
     MAX-ACCESS read-only
     STATUS  current
     DESCRIPTION
     "The number of endpoint independent filter inbound limit exceeded for the DsLite."
     ::= { axIpNatDsliteStatsGlobal 38 }

    axIpNatDsliteStatNatPoolMismatchDrop OBJECT-TYPE
     SYNTAX Counter64
     MAX-ACCESS read-only
     STATUS  current
     DESCRIPTION
     "The number of nat pool mismatch drop for the DsLite."
     ::= { axIpNatDsliteStatsGlobal 39 }

    axIpNatDsliteStatTcpPortOverloaded OBJECT-TYPE
     SYNTAX Counter64
     MAX-ACCESS read-only
     STATUS  current
     DESCRIPTION
     "The number of TCP port overloaded for the DsLite."
     ::= { axIpNatDsliteStatsGlobal 40 }

    axIpNatDsliteStatUdpPortOverloaded OBJECT-TYPE
     SYNTAX Counter64
     MAX-ACCESS read-only
     STATUS  current
     DESCRIPTION
     "The number of UDP port overloaded for the DsLite."
     ::= { axIpNatDsliteStatsGlobal 41 }

    axIpNatDsliteStatTcpPortOverloadingSessionCreated OBJECT-TYPE
     SYNTAX Counter64
     MAX-ACCESS read-only
     STATUS  current
     DESCRIPTION
     "The number of TCP port overloading session created for the DsLite."
     ::= { axIpNatDsliteStatsGlobal 42 }

    axIpNatDsliteStatUdpPortOverloadingSessionCreated OBJECT-TYPE
     SYNTAX Counter64
     MAX-ACCESS read-only
     STATUS  current
     DESCRIPTION
     "The number of UDP port overloading session created for the DsLite."
     ::= { axIpNatDsliteStatsGlobal 43 }

    axIpNatDsliteStatTcpPortOverloadingSessionFreed OBJECT-TYPE
     SYNTAX Counter64
     MAX-ACCESS read-only
     STATUS  current
     DESCRIPTION
     "The number of TCP port overloading session Freed for the DsLite."
     ::= { axIpNatDsliteStatsGlobal 44 }

    axIpNatDsliteStatUdpPortOverloadingSessionFreed OBJECT-TYPE
     SYNTAX Counter64
     MAX-ACCESS read-only
     STATUS  current
     DESCRIPTION
     "The number of UDP port overloading session freed for the DsLite."
     ::= { axIpNatDsliteStatsGlobal 45 }

    axIpNatDsliteStatNatPoolUnusable OBJECT-TYPE
     SYNTAX Counter64
     MAX-ACCESS read-only
     STATUS  current
     DESCRIPTION
     "The number of nat pool unusable for the DsLite."
     ::= { axIpNatDsliteStatsGlobal 46 }

    axIpNatDsliteStatNatHANatPoolUnusable OBJECT-TYPE
     SYNTAX Counter64
     MAX-ACCESS read-only
     STATUS  current
     DESCRIPTION
     "The number of HA nat pool unusable for the DsLite."
     ::= { axIpNatDsliteStatsGlobal 47 }

    axIpNatDsliteStatNoRadiusProfileMatch OBJECT-TYPE
     SYNTAX Counter64
     MAX-ACCESS read-only
     STATUS  current
     DESCRIPTION
     "The number of no radius profile match for the DsLite."
     ::= { axIpNatDsliteStatsGlobal 48 }

--==================================================================
-- axIpNatStatsDynamicMappingAclName
--==================================================================

    axIpNatStatsDynamicMappingAclNameTable OBJECT-TYPE
	SYNTAX SEQUENCE OF AxIpNatStatsDynamicMappingAclNameEntry
	MAX-ACCESS not-accessible
	STATUS current
	DESCRIPTION
		"A table has information of IP NAT interface inside/outside"
	::= { axIpNatStatsDynamicMappingAclName 1 } 

    axIpNatStatsDynamicMappingAclNameEntry OBJECT-TYPE
	SYNTAX  AxIpNatStatsDynamicMappingAclNameEntry
	MAX-ACCESS not-accessible
	STATUS deprecated
	DESCRIPTION
		"Columns in the axIpNatStatsDynamicMappingAclName Table"
	INDEX {
		axIpNatStatsDynamicMappingAclNameAccessListName
	}
	::= { axIpNatStatsDynamicMappingAclNameTable 1 } 

    AxIpNatStatsDynamicMappingAclNameEntry ::= 
	SEQUENCE {
        	axIpNatStatsDynamicMappingAclNameAccessListName     DisplayString,
        	axIpNatStatsDynamicMappingAclNameAccessListID       INTEGER,
        	axIpNatStatsDynamicMappingAclNamePoolName           DisplayString,
        	axIpNatStatsDynamicMappingAclNameStartAddress       DisplayString,
        	axIpNatStatsDynamicMappingAclNameEndAddress         DisplayString,
        	axIpNatStatsDynamicMappingAclNameTotalAddresses     INTEGER,
        	axIpNatStatsDynamicMappingAclNameAllocAddresses     INTEGER,
        	axIpNatStatsDynamicMappingAclNameMissAddresses      INTEGER,
		axIpNatStatsDynamicMappingAclNameStartAddressType   InetAddressType,
		axIpNatStatsDynamicMappingAclNameEndAddressType     InetAddressType
	} 

    axIpNatStatsDynamicMappingAclNameAccessListName OBJECT-TYPE 
	SYNTAX DisplayString
	MAX-ACCESS read-only
	STATUS current
	DESCRIPTION
		"The access list acl name."
	::= { axIpNatStatsDynamicMappingAclNameEntry 1 } 

    axIpNatStatsDynamicMappingAclNameAccessListID OBJECT-TYPE 
	SYNTAX INTEGER
	MAX-ACCESS read-only
	STATUS current
	DESCRIPTION
		"The access list id."
	::= { axIpNatStatsDynamicMappingAclNameEntry 2 } 

    axIpNatStatsDynamicMappingAclNamePoolName OBJECT-TYPE 
	SYNTAX DisplayString
	MAX-ACCESS read-only
	STATUS current
	DESCRIPTION
		"The IP source NAT pool name"
	::= { axIpNatStatsDynamicMappingAclNameEntry 3 } 

    axIpNatStatsDynamicMappingAclNameStartAddress OBJECT-TYPE 
	SYNTAX DisplayString
	MAX-ACCESS read-only
	STATUS current
	DESCRIPTION
		"The start adddress of the pool"
	::= { axIpNatStatsDynamicMappingAclNameEntry 4 } 

    axIpNatStatsDynamicMappingAclNameEndAddress OBJECT-TYPE 
	SYNTAX DisplayString
	MAX-ACCESS read-only
	STATUS current
	DESCRIPTION
		"The end address of the pool"
	::= { axIpNatStatsDynamicMappingAclNameEntry 5 } 

    axIpNatStatsDynamicMappingAclNameTotalAddresses OBJECT-TYPE 
	SYNTAX INTEGER
	MAX-ACCESS read-only
	STATUS current
	DESCRIPTION
		"The total addresses in the pool."
	::= { axIpNatStatsDynamicMappingAclNameEntry 6 } 

    axIpNatStatsDynamicMappingAclNameAllocAddresses OBJECT-TYPE 
	SYNTAX INTEGER
	MAX-ACCESS read-only
	STATUS current
	DESCRIPTION
		"The total allocated addresses in the pool"
	::= { axIpNatStatsDynamicMappingAclNameEntry 7 } 


    axIpNatStatsDynamicMappingAclNameMissAddresses OBJECT-TYPE 
	SYNTAX INTEGER
	MAX-ACCESS read-only
	STATUS current
	DESCRIPTION
		"The total misses in the pool"
	::= { axIpNatStatsDynamicMappingAclNameEntry 8 }

    axIpNatStatsDynamicMappingAclNameStartAddressType OBJECT-TYPE
	SYNTAX InetAddressType
	MAX-ACCESS read-only
	STATUS current
	DESCRIPTION
		"The type of axIpNatStatsDynamicMappingStartAddress:
		 	unknown(0), ipv4(1), ipv6(2)..."
	::= { axIpNatStatsDynamicMappingAclNameEntry 9 }

    axIpNatStatsDynamicMappingAclNameEndAddressType OBJECT-TYPE
	SYNTAX InetAddressType
	MAX-ACCESS read-only
	STATUS current
	DESCRIPTION
		"The type of axIpNatStatsDynamicMappingEndAddress:
		 	unknown(0), ipv4(1), ipv6(2)..."
	::= { axIpNatStatsDynamicMappingAclNameEntry 10 }

--==================================================================
-- axIpNatLoggingStats
--==================================================================

    axIpNatLoggingGlobalStats          OBJECT IDENTIFIER ::= { axIpNatLoggingStats 1 }

    axIpNatLoggingLogPktSent  OBJECT-TYPE 
      SYNTAX                  Counter64
      MAX-ACCESS        read-only
      STATUS                  current
      DESCRIPTION       
            "Total number of logging packets sent out."
      ::=  {  axIpNatLoggingGlobalStats  1  }

    axIpNatLoggingTcpSessCreated    OBJECT-TYPE 
      SYNTAX                  Counter64
      MAX-ACCESS        read-only
      STATUS                  current
      DESCRIPTION       
            "Total number of TCP sessions created."
      ::=  {  axIpNatLoggingGlobalStats  2  }

    axIpNatLoggingTcpSessDeleted    OBJECT-TYPE 
      SYNTAX                  Counter64
      MAX-ACCESS        read-only
      STATUS                  current
      DESCRIPTION       
            "Total number of TCP sessions deleted."
      ::=  {  axIpNatLoggingGlobalStats  3  }

    axIpNatLoggingTcpPortAllocated  OBJECT-TYPE 
      SYNTAX                  Counter64
      MAX-ACCESS        read-only
      STATUS                  current
      DESCRIPTION       
            "Total number of TCP ports allocated."
      ::=  {  axIpNatLoggingGlobalStats  4  }

    axIpNatLoggingTcpPortFreed      OBJECT-TYPE 
      SYNTAX                  Counter64
      MAX-ACCESS        read-only
      STATUS                  current
      DESCRIPTION       
            "Total number of TCP ports freed."
      ::=  {  axIpNatLoggingGlobalStats  5  }

    axIpNatLoggingTcpPortBatchAllocated   OBJECT-TYPE 
      SYNTAX                  Counter64
      MAX-ACCESS        read-only
      STATUS                  current
      DESCRIPTION       
            "Total number of TCP ports batch-allocated."
      ::=  {  axIpNatLoggingGlobalStats  6  }

    axIpNatLoggingTcpPortBatchFreed OBJECT-TYPE 
      SYNTAX                  Counter64
      MAX-ACCESS        read-only
      STATUS                  current
      DESCRIPTION       
            "Total number of TCP ports batch-freed."
      ::=  {  axIpNatLoggingGlobalStats  7  }

    axIpNatLoggingUdpSessCreated    OBJECT-TYPE 
      SYNTAX                  Counter64
      MAX-ACCESS        read-only
      STATUS                  current
      DESCRIPTION       
            "Total number of UDP sessions created."
      ::=  {  axIpNatLoggingGlobalStats  8  }

    axIpNatLoggingUdpSessDeleted    OBJECT-TYPE 
      SYNTAX                  Counter64
      MAX-ACCESS        read-only
      STATUS                  current
      DESCRIPTION       
            "Total number of UDP sessions deleted."
      ::=  {  axIpNatLoggingGlobalStats  9  }

    axIpNatLoggingUdpPortAllocated  OBJECT-TYPE 
      SYNTAX                  Counter64
      MAX-ACCESS        read-only
      STATUS                  current
      DESCRIPTION       
            "Total number of UDP ports allocated."
      ::=  {  axIpNatLoggingGlobalStats  10  }

    axIpNatLoggingUdpPortFreed      OBJECT-TYPE 
      SYNTAX                  Counter64
      MAX-ACCESS        read-only
      STATUS                  current
      DESCRIPTION       
            "Total number of UDP ports freed."
      ::=  {  axIpNatLoggingGlobalStats  11  }

    axIpNatLoggingUdpPortBatchAllocated   OBJECT-TYPE 
      SYNTAX                  Counter64
      MAX-ACCESS        read-only
      STATUS                  current
      DESCRIPTION       
            "Total number of UDP ports batch-allocated."
      ::=  {  axIpNatLoggingGlobalStats  12  }

    axIpNatLoggingUdpPortBatchFreed OBJECT-TYPE 
      SYNTAX                  Counter64
      MAX-ACCESS        read-only
      STATUS                  current
      DESCRIPTION       
            "Total number of UDP ports batch-freed."
      ::=  {  axIpNatLoggingGlobalStats  13  }

    axIpNatLoggingIcmpSessCreated   OBJECT-TYPE 
      SYNTAX                  Counter64
      MAX-ACCESS        read-only
      STATUS                  current
      DESCRIPTION       
            "Total number of ICMP sessions created."
      ::=  {  axIpNatLoggingGlobalStats  14  }

    axIpNatLoggingIcmpSessDeleted   OBJECT-TYPE 
      SYNTAX                  Counter64
      MAX-ACCESS        read-only
      STATUS                  current
      DESCRIPTION       
            "Total number of ICMP sessions deleted."
      ::=  {  axIpNatLoggingGlobalStats  15  }

    axIpNatLoggingIcmpResourceAllocated   OBJECT-TYPE 
      SYNTAX                  Counter64
      MAX-ACCESS        read-only
      STATUS                  current
      DESCRIPTION       
            "Total number of ICMP resource allocated."
      ::=  {  axIpNatLoggingGlobalStats  16  }

    axIpNatLoggingIcmpResourcetFreed      OBJECT-TYPE 
      SYNTAX                  Counter64
      MAX-ACCESS        read-only
      STATUS                  current
      DESCRIPTION       
            "Total number of ICMP resource freed."
      ::=  {  axIpNatLoggingGlobalStats  17  }

    axIpNatLoggingIcmpV6SessCreated OBJECT-TYPE 
      SYNTAX                  Counter64
      MAX-ACCESS        read-only
      STATUS                  current
      DESCRIPTION       
            "Total number of ICMPv6 sessions created."
      ::=  {  axIpNatLoggingGlobalStats  18  }

    axIpNatLoggingIcmpV6SessDeleted OBJECT-TYPE 
      SYNTAX                  Counter64
      MAX-ACCESS        read-only
      STATUS                  current
      DESCRIPTION       
            "Total number of ICMPv6 sessions deleted."
      ::=  {  axIpNatLoggingGlobalStats  19  }

    axIpNatLoggingIcmpV6ResourceAllocated OBJECT-TYPE 
      SYNTAX                  Counter64
      MAX-ACCESS        read-only
      STATUS                  current
      DESCRIPTION       
            "Total number of ICMPv6 resource allocated."
      ::=  {  axIpNatLoggingGlobalStats  20  }

    axIpNatLoggingIcmpV6ResourcetFreed    OBJECT-TYPE 
      SYNTAX                  Counter64
      MAX-ACCESS        read-only
      STATUS                  current
      DESCRIPTION       
            "Total number of ICMPv6 resource freed."
      ::=  {  axIpNatLoggingGlobalStats  21  }

    axIpNatLoggingGreSessCreated    OBJECT-TYPE 
      SYNTAX                  Counter64
      MAX-ACCESS        read-only
      STATUS                  current
      DESCRIPTION       
            "Total number of GRE sessions created."
      ::=  {  axIpNatLoggingGlobalStats  22  }

    axIpNatLoggingGreSessDeleted    OBJECT-TYPE 
      SYNTAX                  Counter64
      MAX-ACCESS        read-only
      STATUS                  current
      DESCRIPTION       
            "Total number of GRE sessions deleted."
      ::=  {  axIpNatLoggingGlobalStats  23  }

    axIpNatLoggingGreResourceAllocated    OBJECT-TYPE 
      SYNTAX                  Counter64
      MAX-ACCESS        read-only
      STATUS                  current
      DESCRIPTION       
            "Total number of GRE resource allocated."
      ::=  {  axIpNatLoggingGlobalStats  24  }

    axIpNatLoggingGreResourcetFreed OBJECT-TYPE 
      SYNTAX                  Counter64
      MAX-ACCESS        read-only
      STATUS                  current
      DESCRIPTION       
            "Total number of GRE resource freed."
      ::=  {  axIpNatLoggingGlobalStats  25  }

    axIpNatLoggingEspSessCreated    OBJECT-TYPE 
      SYNTAX                  Counter64
      MAX-ACCESS        read-only
      STATUS                  current
      DESCRIPTION       
            "Total number of ESP sessions created."
      ::=  {  axIpNatLoggingGlobalStats  26  }

    axIpNatLoggingEspSessDeleted    OBJECT-TYPE 
      SYNTAX                  Counter64
      MAX-ACCESS        read-only
      STATUS                  current
      DESCRIPTION       
            "Total number of ESP sessions deleted."
      ::=  {  axIpNatLoggingGlobalStats  27  }

    axIpNatLoggingEspResourceAllocated    OBJECT-TYPE 
      SYNTAX                  Counter64
      MAX-ACCESS        read-only
      STATUS                  current
      DESCRIPTION       
            "Total number of ESP resource allocated."
      ::=  {  axIpNatLoggingGlobalStats  28  }

    axIpNatLoggingEspResourcetFreed OBJECT-TYPE 
      SYNTAX                  Counter64
      MAX-ACCESS        read-only
      STATUS                  current
      DESCRIPTION       
            "Total number of ESP resource freed."
      ::=  {  axIpNatLoggingGlobalStats  29  }

    axIpNatLoggingFixedNatInsideUserPortMapping OBJECT-TYPE 
      SYNTAX                  Counter64
      MAX-ACCESS        read-only
      STATUS                  current
      DESCRIPTION       
            "Total number of Fixed NAT inside user port mappings."
      ::=  {  axIpNatLoggingGlobalStats  30  }

    axIpNatLoggingFixedNatDisabledConfigLogged  OBJECT-TYPE 
      SYNTAX                  Counter64
      MAX-ACCESS        read-only
      STATUS                  current
      DESCRIPTION       
            "Total number of Fixed NAT disabled configs logged."
      ::=  {  axIpNatLoggingGlobalStats  31  }

    axIpNatLoggingFixedNatDisabledConfigLogsSent      OBJECT-TYPE 
      SYNTAX                  Counter64
      MAX-ACCESS        read-only
      STATUS                  current
      DESCRIPTION       
            "Total number of Fixed NAT disabled config logs sent out."
      ::=  {  axIpNatLoggingGlobalStats  32  }

    axIpNatLoggingFixedNatPeriodicConfigLogsSent      OBJECT-TYPE 
      SYNTAX                  Counter64
      MAX-ACCESS        read-only
      STATUS                  current
      DESCRIPTION       
            "Total number of Fixed NAT periodic config logs sent."
      ::=  {  axIpNatLoggingGlobalStats  33  }

    axIpNatLoggingFixedNatPeriodicConfigLogged      OBJECT-TYPE 
      SYNTAX                  Counter64
      MAX-ACCESS        read-only
      STATUS                  current
      DESCRIPTION       
            "Total number of Fixed NAT periodic config logged."
      ::=  {  axIpNatLoggingGlobalStats  34  }

    axIpNatLoggingLogPacketsDrop      OBJECT-TYPE 
      SYNTAX                  Counter64
      MAX-ACCESS        read-only
      STATUS                  current
      DESCRIPTION       
            "Total number of log packets drop."
      ::=  {  axIpNatLoggingGlobalStats  35  }

    axIpNatTcpConnectionEstablished      OBJECT-TYPE 
      SYNTAX                  Counter64
      MAX-ACCESS        read-only
      STATUS                  current
      DESCRIPTION       
            "Total number of TCP connection established."
      ::=  {  axIpNatLoggingGlobalStats  36  }

    axIpNatTcpConnectionLost      OBJECT-TYPE 
      SYNTAX                  Counter64
      MAX-ACCESS        read-only
      STATUS                  current
      DESCRIPTION       
            "Total number of TCP connection lost."
      ::=  {  axIpNatLoggingGlobalStats  37  }

    axIpNatTcpPortOverloadingAllocated      OBJECT-TYPE 
      SYNTAX                  Counter64
      MAX-ACCESS        read-only
      STATUS                  current
      DESCRIPTION       
            "Total number of TCP port overloading allocated."
      ::=  {  axIpNatLoggingGlobalStats  38  }

    axIpNatTcpPortOverloadingFreed      OBJECT-TYPE 
      SYNTAX                  Counter64
      MAX-ACCESS        read-only
      STATUS                  current
      DESCRIPTION       
            "Total number of TCP port overloading freed."
      ::=  {  axIpNatLoggingGlobalStats  39  }

    axIpNatUdpPortOverloadingAllocated      OBJECT-TYPE 
      SYNTAX                  Counter64
      MAX-ACCESS        read-only
      STATUS                  current
      DESCRIPTION       
            "Total number of UDP port overloading allocated."
      ::=  {  axIpNatLoggingGlobalStats  40  }

    axIpNatUdpPortOverloadingFreed      OBJECT-TYPE 
      SYNTAX                  Counter64
      MAX-ACCESS        read-only
      STATUS                  current
      DESCRIPTION       
            "Total number of TCP port overloading freed."
      ::=  {  axIpNatLoggingGlobalStats  41  }

    axIpNatHttpRequestLogged      OBJECT-TYPE 
      SYNTAX                  Counter64
      MAX-ACCESS        read-only
      STATUS                  current
      DESCRIPTION       
            "Total number of HTTP request logged."
      ::=  {  axIpNatLoggingGlobalStats  42  }

--==================================================================
-- axFixedNatGlobalStats
--==================================================================

	axFixedNatGlobalStats		OBJECT IDENTIFIER ::= { axFixedNatStats 1 }
	axFixedNatAlgStats			OBJECT IDENTIFIER ::= { axFixedNatStats 2 }
    axFixedNatMapping    	  	OBJECT IDENTIFIER ::= { axFixedNatStats 3 }
    axFixedNatFullConeSess    	OBJECT IDENTIFIER ::= { axFixedNatStats 4 }
	axFixedNatTop5PrivateIpAddrTotSessions 	OBJECT IDENTIFIER ::= { axFixedNatStats 5}
	axFixedNatTop5PrivateIpAddrTotTcpPorts	OBJECT IDENTIFIER ::= { axFixedNatStats 6}
	axFixedNatTop5PrivateIpAddrTotUdpPorts	OBJECT IDENTIFIER ::= { axFixedNatStats 7}
	axFixedNatTop5PrivateIpAddrTotIcmpPorts	OBJECT IDENTIFIER ::= { axFixedNatStats 8}
	axFixedNatTop5UserPrivateIpAddrTotSessions 	OBJECT IDENTIFIER ::= { axFixedNatStats 9}
	axFixedNatTop5UserPrivateIpAddrTotTcpPorts	OBJECT IDENTIFIER ::= { axFixedNatStats 10}
	axFixedNatTop5UserPrivateIpAddrTotUdpPorts	OBJECT IDENTIFIER ::= { axFixedNatStats 11}
	axFixedNatTop5UserPrivateIpAddrTotIcmpPorts	OBJECT IDENTIFIER ::= { axFixedNatStats 12}
	axFixedNatTop5GlobalIpAddrTotUsers 		OBJECT IDENTIFIER ::= { axFixedNatStats 13}
	axFixedNatTop5GlobalIpAddrTotTcpPorts 	OBJECT IDENTIFIER ::= { axFixedNatStats 14}
	axFixedNatTop5GlobalIpAddrTotUdpPorts 	OBJECT IDENTIFIER ::= { axFixedNatStats 15}
	axFixedNatFile				OBJECT IDENTIFIER ::= { axFixedNatStats 16}

axFixedNatTotalNatAddressInUse    OBJECT-TYPE
    SYNTAX          CounterBasedGauge64
    MAX-ACCESS      read-only
    STATUS          current
    DESCRIPTION
        "The fixed nat total nat address in use."
    DEFVAL          { 0 }
    ::=  {  axFixedNatGlobalStats  1  }

axFixedNatTotalTcpPortsAllocated    OBJECT-TYPE
    SYNTAX          CounterBasedGauge64
    MAX-ACCESS      read-only
    STATUS          current
    DESCRIPTION
        "The fixed nat total tcp ports allocated."
    DEFVAL          { 0 }
    ::=  {  axFixedNatGlobalStats  2  }

axFixedNatTotalTcpPortsFreed    OBJECT-TYPE
    SYNTAX          CounterBasedGauge64
    MAX-ACCESS      read-only
    STATUS          current
    DESCRIPTION
        "The fixed nat total tcp ports freed."
    DEFVAL          { 0 }
    ::=  {  axFixedNatGlobalStats  3  }

axFixedNatTotalUdpPortsAllocated    OBJECT-TYPE
    SYNTAX          CounterBasedGauge64
    MAX-ACCESS      read-only
    STATUS          current
    DESCRIPTION
        "The fixed nat total udp ports allocated."
    DEFVAL          { 0 }
    ::=  {  axFixedNatGlobalStats  4  }

axFixedNatTotalUdpPortsFreed    OBJECT-TYPE
    SYNTAX          CounterBasedGauge64
    MAX-ACCESS      read-only
    STATUS          current
    DESCRIPTION
        "The fixed nat total udp ports freed."
    DEFVAL          { 0 }
    ::=  {  axFixedNatGlobalStats  5  }

axFixedNatTotalIcmpPortsAllocated    OBJECT-TYPE
    SYNTAX          CounterBasedGauge64
    MAX-ACCESS      read-only
    STATUS          current
    DESCRIPTION
        "The fixed nat total icmp ports allocated."
    DEFVAL          { 0 }
    ::=  {  axFixedNatGlobalStats  6  }

axFixedNatTotalIcmpPortsFreed    OBJECT-TYPE
    SYNTAX          CounterBasedGauge64
    MAX-ACCESS      read-only
    STATUS          current
    DESCRIPTION
        "The fixed nat total icmp ports freed."
    DEFVAL          { 0 }
    ::=  {  axFixedNatGlobalStats  7  }

axFixedNatTcpNatPortUnavailable    OBJECT-TYPE
    SYNTAX          CounterBasedGauge64
    MAX-ACCESS      read-only
    STATUS          current
    DESCRIPTION
        "The fixed nat tcp nat port unavailable."
    DEFVAL          { 0 }
    ::=  {  axFixedNatGlobalStats  8  }

axFixedNatUdpNatPortUnavailable    OBJECT-TYPE
    SYNTAX          CounterBasedGauge64
    MAX-ACCESS      read-only
    STATUS          current
    DESCRIPTION
        "The fixed nat udp nat port unavailable."
    DEFVAL          { 0 }
    ::=  {  axFixedNatGlobalStats  9  }

axFixedNatIcmpNatPortUnavailable    OBJECT-TYPE
    SYNTAX          CounterBasedGauge64
    MAX-ACCESS      read-only
    STATUS          current
    DESCRIPTION
        "The fixed nat icmp nat port unavailable."
    DEFVAL          { 0 }
    ::=  {  axFixedNatGlobalStats  10  }

axFixedNatSessionUserQuotaExceed    OBJECT-TYPE
    SYNTAX          CounterBasedGauge64
    MAX-ACCESS      read-only
    STATUS          current
    DESCRIPTION
        "The fixed nat session user quota exceed."
    DEFVAL          { 0 }
    ::=  {  axFixedNatGlobalStats  11  }

axFixedNatFullConeSessionCreationFailed    OBJECT-TYPE
    SYNTAX          CounterBasedGauge64
    MAX-ACCESS      read-only
    STATUS          current
    DESCRIPTION
        "The fixed nat full cone session creation failed."
    DEFVAL          { 0 }
    ::=  {  axFixedNatGlobalStats  12  }

axFixedNatLidStandbyDrop    OBJECT-TYPE
    SYNTAX          CounterBasedGauge64
    MAX-ACCESS      read-only
    STATUS          current
    DESCRIPTION
        "The fixed nat lid standby drop."
    DEFVAL          { 0 }
    ::=  {  axFixedNatGlobalStats  13  }

axFixedNatSelfHairpinningDrop    OBJECT-TYPE
    SYNTAX          CounterBasedGauge64
    MAX-ACCESS      read-only
    STATUS          current
    DESCRIPTION
        "The fixed nat self hairpining drop."
    DEFVAL          { 0 }
    ::=  {  axFixedNatGlobalStats  14  }

axFixedNatIpv6InIpv4PacketDrop    OBJECT-TYPE
    SYNTAX          CounterBasedGauge64
    MAX-ACCESS      read-only
    STATUS          current
    DESCRIPTION
        "The fixed nat ipv6 in ipv4 packet drop."
    DEFVAL          { 0 }
    ::=  {  axFixedNatGlobalStats  15  }

axFixedNatDestRuleListDrop    OBJECT-TYPE
    SYNTAX          CounterBasedGauge64
    MAX-ACCESS      read-only
    STATUS          current
    DESCRIPTION
        "The fixed nat destination rule list drop."
    DEFVAL          { 0 }
    ::=  {  axFixedNatGlobalStats  16  }

axFixedNatDestRuleListPassThrough    OBJECT-TYPE
    SYNTAX          CounterBasedGauge64
    MAX-ACCESS      read-only
    STATUS          current
    DESCRIPTION
        "The fixed nat destination rule list pass through."
    DEFVAL          { 0 }
    ::=  {  axFixedNatGlobalStats  17  }

--==================================================================
-- axFixedNatNat44GlobalStats
--==================================================================
	axFixedNatNat44GlobalStats		OBJECT IDENTIFIER ::= { axFixedNatGlobalStats 18 }
	axFixedNatNat64GlobalStats		OBJECT IDENTIFIER ::= { axFixedNatGlobalStats 19 }
	axFixedNatDsliteGlobalStats		OBJECT IDENTIFIER ::= { axFixedNatGlobalStats 20 }

axFixedNatNat44DataSessionsCreated    OBJECT-TYPE
    SYNTAX          CounterBasedGauge64
    MAX-ACCESS      read-only
    STATUS          current
    DESCRIPTION
        "The fixed nat nat44 data session created."
    DEFVAL          { 0 }
    ::=  {  axFixedNatNat44GlobalStats  1  }

axFixedNatNat44DataSessionsFreed    OBJECT-TYPE
    SYNTAX          CounterBasedGauge64
    MAX-ACCESS      read-only
    STATUS          current
    DESCRIPTION
        "The fixed nat nat44 data session freed."
    DEFVAL          { 0 }
    ::=  {  axFixedNatNat44GlobalStats  2  }

axFixedNatNat44TcpFullConeCreated    OBJECT-TYPE
    SYNTAX          CounterBasedGauge64
    MAX-ACCESS      read-only
    STATUS          current
    DESCRIPTION
        "The fixed nat nat44 tcp full cone created."
    DEFVAL          { 0 }
    ::=  {  axFixedNatNat44GlobalStats  3  }

axFixedNatNat44TcpFullConeFreed    OBJECT-TYPE
    SYNTAX          CounterBasedGauge64
    MAX-ACCESS      read-only
    STATUS          current
    DESCRIPTION
        "The fixed nat nat44 tcp full cone freed."
    DEFVAL          { 0 }
    ::=  {  axFixedNatNat44GlobalStats  4  }

axFixedNatNat44UdpFullConeCreated    OBJECT-TYPE
    SYNTAX          CounterBasedGauge64
    MAX-ACCESS      read-only
    STATUS          current
    DESCRIPTION
        "The fixed nat nat44 udp full cone created."
    DEFVAL          { 0 }
    ::=  {  axFixedNatNat44GlobalStats  5  }

axFixedNatNat44UdpFullConeFreed    OBJECT-TYPE
    SYNTAX          CounterBasedGauge64
    MAX-ACCESS      read-only
    STATUS          current
    DESCRIPTION
        "The fixed nat nat44 udp full cone freed."
    DEFVAL          { 0 }
    ::=  {  axFixedNatNat44GlobalStats  6  }

axFixedNatNat44UdpAlgFullConeCreated    OBJECT-TYPE
    SYNTAX          CounterBasedGauge64
    MAX-ACCESS      read-only
    STATUS          current
    DESCRIPTION
        "The fixed nat nat44 udp alg full cone created."
    DEFVAL          { 0 }
    ::=  {  axFixedNatNat44GlobalStats  7  }

axFixedNatNat44UdpAlgFullConeFreed    OBJECT-TYPE
    SYNTAX          CounterBasedGauge64
    MAX-ACCESS      read-only
    STATUS          current
    DESCRIPTION
        "The fixed nat nat44 udp alg full cone freed."
    DEFVAL          { 0 }
    ::=  {  axFixedNatNat44GlobalStats  8  }

axFixedNatNat44EndpointIndependentMappingMatched    OBJECT-TYPE
    SYNTAX          CounterBasedGauge64
    MAX-ACCESS      read-only
    STATUS          current
    DESCRIPTION
        "The fixed nat nat44 endpoint independent mapping matched."
    DEFVAL          { 0 }
    ::=  {  axFixedNatNat44GlobalStats  9  }

axFixedNatNat44EndpointIndependentFilteringMatched    OBJECT-TYPE
    SYNTAX          CounterBasedGauge64
    MAX-ACCESS      read-only
    STATUS          current
    DESCRIPTION
        "The fixed nat nat44 endpoint independent filtering matched."
    DEFVAL          { 0 }
    ::=  {  axFixedNatNat44GlobalStats  10  }

axFixedNatNat44EndpointIndependentFilteringDrop    OBJECT-TYPE
    SYNTAX          CounterBasedGauge64
    MAX-ACCESS      read-only
    STATUS          current
    DESCRIPTION
        "The fixed nat nat44 endpoint independent filtering matched."
    DEFVAL          { 0 }
    ::=  {  axFixedNatNat44GlobalStats  11  }

axFixedNatNat44EndpointIndependentFilteringLimitExceed    OBJECT-TYPE
    SYNTAX          CounterBasedGauge64
    MAX-ACCESS      read-only
    STATUS          current
    DESCRIPTION
        "The fixed nat nat44 endpoint independent filtering matched."
    DEFVAL          { 0 }
    ::=  {  axFixedNatNat44GlobalStats  12  }

axFixedNatNat44HairpinSessionCreated    OBJECT-TYPE
    SYNTAX          CounterBasedGauge64
    MAX-ACCESS      read-only
    STATUS          current
    DESCRIPTION
        "The fixed nat nat44 hairpin session created."
    DEFVAL          { 0 }
    ::=  {  axFixedNatNat44GlobalStats  13  }

--==================================================================
-- axFixedNatNat64GlobalStats
--==================================================================

axFixedNatNat64DataSessionsCreated    OBJECT-TYPE
    SYNTAX          CounterBasedGauge64
    MAX-ACCESS      read-only
    STATUS          current
    DESCRIPTION
        "The fixed nat nat64 data session created."
    DEFVAL          { 0 }
    ::=  {  axFixedNatNat64GlobalStats  1  }

axFixedNatNat64DataSessionsFreed    OBJECT-TYPE
    SYNTAX          CounterBasedGauge64
    MAX-ACCESS      read-only
    STATUS          current
    DESCRIPTION
        "The fixed nat nat64 data session freed."
    DEFVAL          { 0 }
    ::=  {  axFixedNatNat64GlobalStats  2  }

axFixedNatNat64TcpFullConeCreated    OBJECT-TYPE
    SYNTAX          CounterBasedGauge64
    MAX-ACCESS      read-only
    STATUS          current
    DESCRIPTION
        "The fixed nat nat64 tcp full cone created."
    DEFVAL          { 0 }
    ::=  {  axFixedNatNat64GlobalStats  3  }

axFixedNatNat64TcpFullConeFreed    OBJECT-TYPE
    SYNTAX          CounterBasedGauge64
    MAX-ACCESS      read-only
    STATUS          current
    DESCRIPTION
        "The fixed nat nat64 tcp full cone freed."
    DEFVAL          { 0 }
    ::=  {  axFixedNatNat64GlobalStats  4  }

axFixedNatNat64UdpFullConeCreated    OBJECT-TYPE
    SYNTAX          CounterBasedGauge64
    MAX-ACCESS      read-only
    STATUS          current
    DESCRIPTION
        "The fixed nat nat64 udp full cone created."
    DEFVAL          { 0 }
    ::=  {  axFixedNatNat64GlobalStats  5  }

axFixedNatNat64UdpFullConeFreed    OBJECT-TYPE
    SYNTAX          CounterBasedGauge64
    MAX-ACCESS      read-only
    STATUS          current
    DESCRIPTION
        "The fixed nat nat64 udp full cone freed."
    DEFVAL          { 0 }
    ::=  {  axFixedNatNat64GlobalStats  6  }

axFixedNatNat64UdpAlgFullConeCreated    OBJECT-TYPE
    SYNTAX          CounterBasedGauge64
    MAX-ACCESS      read-only
    STATUS          current
    DESCRIPTION
        "The fixed nat nat64 udp alg full cone created."
    DEFVAL          { 0 }
    ::=  {  axFixedNatNat64GlobalStats  7  }

axFixedNatNat64UdpAlgFullConeFreed    OBJECT-TYPE
    SYNTAX          CounterBasedGauge64
    MAX-ACCESS      read-only
    STATUS          current
    DESCRIPTION
        "The fixed nat nat64 udp alg full cone freed."
    DEFVAL          { 0 }
    ::=  {  axFixedNatNat64GlobalStats  8  }

axFixedNatNat64EndpointIndependentMappingMatched    OBJECT-TYPE
    SYNTAX          CounterBasedGauge64
    MAX-ACCESS      read-only
    STATUS          current
    DESCRIPTION
        "The fixed nat nat64 endpoint independent mapping matched."
    DEFVAL          { 0 }
    ::=  {  axFixedNatNat64GlobalStats  9  }

axFixedNatNat64EndpointIndependentFilteringMatched    OBJECT-TYPE
    SYNTAX          CounterBasedGauge64
    MAX-ACCESS      read-only
    STATUS          current
    DESCRIPTION
        "The fixed nat nat64 endpoint independent filtering matched."
    DEFVAL          { 0 }
    ::=  {  axFixedNatNat64GlobalStats  10  }

axFixedNatNat64EndpointIndependentFilteringDrop    OBJECT-TYPE
    SYNTAX          CounterBasedGauge64
    MAX-ACCESS      read-only
    STATUS          current
    DESCRIPTION
        "The fixed nat nat64 endpoint independent filtering matched."
    DEFVAL          { 0 }
    ::=  {  axFixedNatNat64GlobalStats  11  }

axFixedNatNat64EndpointIndependentFilteringLimitExceed    OBJECT-TYPE
    SYNTAX          CounterBasedGauge64
    MAX-ACCESS      read-only
    STATUS          current
    DESCRIPTION
        "The fixed nat nat64 endpoint independent filtering matched."
    DEFVAL          { 0 }
    ::=  {  axFixedNatNat64GlobalStats  12  }

axFixedNatNat64HairpinSessionCreated    OBJECT-TYPE
    SYNTAX          CounterBasedGauge64
    MAX-ACCESS      read-only
    STATUS          current
    DESCRIPTION
        "The fixed nat nat64 hairpin session created."
    DEFVAL          { 0 }
    ::=  {  axFixedNatNat64GlobalStats  13  }

--==================================================================
-- axFixedNatDsliteGlobalStats
--==================================================================

axFixedNatDsliteDataSessionsCreated    OBJECT-TYPE
    SYNTAX          CounterBasedGauge64
    MAX-ACCESS      read-only
    STATUS          current
    DESCRIPTION
        "The fixed nat dslite data session created."
    DEFVAL          { 0 }
    ::=  {  axFixedNatDsliteGlobalStats  1  }

axFixedNatDsliteDataSessionsFreed    OBJECT-TYPE
    SYNTAX          CounterBasedGauge64
    MAX-ACCESS      read-only
    STATUS          current
    DESCRIPTION
        "The fixed nat dslite data session freed."
    DEFVAL          { 0 }
    ::=  {  axFixedNatDsliteGlobalStats  2  }

axFixedNatDsliteTcpFullConeCreated    OBJECT-TYPE
    SYNTAX          CounterBasedGauge64
    MAX-ACCESS      read-only
    STATUS          current
    DESCRIPTION
        "The fixed nat dslite tcp full cone created."
    DEFVAL          { 0 }
    ::=  {  axFixedNatDsliteGlobalStats  3  }

axFixedNatDsliteTcpFullConeFreed    OBJECT-TYPE
    SYNTAX          CounterBasedGauge64
    MAX-ACCESS      read-only
    STATUS          current
    DESCRIPTION
        "The fixed nat dslite tcp full cone freed."
    DEFVAL          { 0 }
    ::=  {  axFixedNatDsliteGlobalStats  4  }

axFixedNatDsliteUdpFullConeCreated    OBJECT-TYPE
    SYNTAX          CounterBasedGauge64
    MAX-ACCESS      read-only
    STATUS          current
    DESCRIPTION
        "The fixed nat dslite udp full cone created."
    DEFVAL          { 0 }
    ::=  {  axFixedNatDsliteGlobalStats  5  }

axFixedNatDsliteUdpFullConeFreed    OBJECT-TYPE
    SYNTAX          CounterBasedGauge64
    MAX-ACCESS      read-only
    STATUS          current
    DESCRIPTION
        "The fixed nat dslite udp full cone freed."
    DEFVAL          { 0 }
    ::=  {  axFixedNatDsliteGlobalStats  6  }

axFixedNatDsliteUdpAlgFullConeCreated    OBJECT-TYPE
    SYNTAX          CounterBasedGauge64
    MAX-ACCESS      read-only
    STATUS          current
    DESCRIPTION
        "The fixed nat dslite udp alg full cone created."
    DEFVAL          { 0 }
    ::=  {  axFixedNatDsliteGlobalStats  7  }

axFixedNatDsliteUdpAlgFullConeFreed    OBJECT-TYPE
    SYNTAX          CounterBasedGauge64
    MAX-ACCESS      read-only
    STATUS          current
    DESCRIPTION
        "The fixed nat dslite udp alg full cone freed."
    DEFVAL          { 0 }
    ::=  {  axFixedNatDsliteGlobalStats  8  }

axFixedNatDsliteEndpointIndependentMappingMatched    OBJECT-TYPE
    SYNTAX          CounterBasedGauge64
    MAX-ACCESS      read-only
    STATUS          current
    DESCRIPTION
        "The fixed nat dslite endpoint independent mapping matched."
    DEFVAL          { 0 }
    ::=  {  axFixedNatDsliteGlobalStats  9  }

axFixedNatDsliteEndpointIndependentFilteringMatched    OBJECT-TYPE
    SYNTAX          CounterBasedGauge64
    MAX-ACCESS      read-only
    STATUS          current
    DESCRIPTION
        "The fixed nat dslite endpoint independent filtering matched."
    DEFVAL          { 0 }
    ::=  {  axFixedNatDsliteGlobalStats  10  }

axFixedNatDsliteEndpointIndependentFilteringDrop    OBJECT-TYPE
    SYNTAX          CounterBasedGauge64
    MAX-ACCESS      read-only
    STATUS          current
    DESCRIPTION
        "The fixed nat dslite endpoint independent filtering matched."
    DEFVAL          { 0 }
    ::=  {  axFixedNatDsliteGlobalStats  11  }

axFixedNatDsliteEndpointIndependentFilteringLimitExceed    OBJECT-TYPE
    SYNTAX          CounterBasedGauge64
    MAX-ACCESS      read-only
    STATUS          current
    DESCRIPTION
        "The fixed nat dslite endpoint independent filtering matched."
    DEFVAL          { 0 }
    ::=  {  axFixedNatDsliteGlobalStats  12  }

axFixedNatDsliteHairpinSessionCreated    OBJECT-TYPE
    SYNTAX          CounterBasedGauge64
    MAX-ACCESS      read-only
    STATUS          current
    DESCRIPTION
        "The fixed nat dslite hairpin session created."
    DEFVAL          { 0 }
    ::=  {  axFixedNatDsliteGlobalStats  13  }

--==================================================================
-- axFixedNatAlgEspStats
--==================================================================
	axFixedNatAlgEspStats			OBJECT IDENTIFIER ::= { axFixedNatAlgStats 1 }

axFixedNatAlgEspSessionCreated    OBJECT-TYPE
    SYNTAX          CounterBasedGauge64
    MAX-ACCESS      read-only
    STATUS          current
    DESCRIPTION
        "The fixed nat alg esp session created."
    DEFVAL          { 0 }
    ::=  {  axFixedNatAlgEspStats  1 }

--==================================================================
-- axFixedNatAlgFtpStats
--==================================================================
	axFixedNatAlgFtpStats			OBJECT IDENTIFIER ::= { axFixedNatAlgStats 2 }

axFixedNatAlgFtpPortReqFromClient    OBJECT-TYPE
    SYNTAX          CounterBasedGauge64
    MAX-ACCESS      read-only
    STATUS          current
    DESCRIPTION
        "The fixed nat alg ftp port requests from client."
    DEFVAL          { 0 }
    ::=  {  axFixedNatAlgFtpStats  1 }

axFixedNatAlgFtpEprtReqFromClient    OBJECT-TYPE
    SYNTAX          CounterBasedGauge64
    MAX-ACCESS      read-only
    STATUS          current
    DESCRIPTION
        "The fixed nat alg ftp eprt requests from client."
    DEFVAL          { 0 }
    ::=  {  axFixedNatAlgFtpStats  2 }

axFixedNatAlgFtpLprtReqFromClient    OBJECT-TYPE
    SYNTAX          CounterBasedGauge64
    MAX-ACCESS      read-only
    STATUS          current
    DESCRIPTION
        "The fixed nat alg ftp lprt requests from client."
    DEFVAL          { 0 }
    ::=  {  axFixedNatAlgFtpStats  3 }

axFixedNatAlgFtpPasvRepFromServer    OBJECT-TYPE
    SYNTAX          CounterBasedGauge64
    MAX-ACCESS      read-only
    STATUS          current
    DESCRIPTION
        "The fixed nat alg ftp pasv replies from server."
    DEFVAL          { 0 }
    ::=  {  axFixedNatAlgFtpStats  4 }

axFixedNatAlgFtpEpsvRepFromServer    OBJECT-TYPE
    SYNTAX          CounterBasedGauge64
    MAX-ACCESS      read-only
    STATUS          current
    DESCRIPTION
        "The fixed nat alg ftp epsv replies from server."
    DEFVAL          { 0 }
    ::=  {  axFixedNatAlgFtpStats  5 }

axFixedNatAlgFtpLpsvRepFromServer    OBJECT-TYPE
    SYNTAX          CounterBasedGauge64
    MAX-ACCESS      read-only
    STATUS          current
    DESCRIPTION
        "The fixed nat alg ftp lpsv replies from server."
    DEFVAL          { 0 }
    ::=  {  axFixedNatAlgFtpStats  6 }

--==================================================================
-- axFixedNatAlgH323Stats
--==================================================================
	axFixedNatAlgH323Stats			OBJECT IDENTIFIER ::= { axFixedNatAlgStats 3 }

axFixedNatAlgH323H225RasMsg    OBJECT-TYPE
    SYNTAX          CounterBasedGauge64
    MAX-ACCESS      read-only
    STATUS          current
    DESCRIPTION
        "The fixed nat alg H323 H225 Ras message."
    DEFVAL          { 0 }
    ::=  {  axFixedNatAlgH323Stats  1 }

axFixedNatAlgH323H225CallSigMsg    OBJECT-TYPE
    SYNTAX          CounterBasedGauge64
    MAX-ACCESS      read-only
    STATUS          current
    DESCRIPTION
        "The fixed nat alg H323 H225 Call Signaling Message."
    DEFVAL          { 0 }
    ::=  {  axFixedNatAlgH323Stats  2 }

axFixedNatAlgH323H245MedCtrMsg    OBJECT-TYPE
    SYNTAX          CounterBasedGauge64
    MAX-ACCESS      read-only
    STATUS          current
    DESCRIPTION
        "The fixed nat alg H323 H245 media control message."
    DEFVAL          { 0 }
    ::=  {  axFixedNatAlgH323Stats  3 }

axFixedNatAlgH323H245TunnelMsg    OBJECT-TYPE
    SYNTAX          CounterBasedGauge64
    MAX-ACCESS      read-only
    STATUS          current
    DESCRIPTION
        "The fixed nat alg H323 H245 Tunnelled message."
    DEFVAL          { 0 }
    ::=  {  axFixedNatAlgH323Stats  4 }

axFixedNatAlgH323FastStart    OBJECT-TYPE
    SYNTAX          CounterBasedGauge64
    MAX-ACCESS      read-only
    STATUS          current
    DESCRIPTION
        "The fixed nat alg H323 fast start."
    DEFVAL          { 0 }
    ::=  {  axFixedNatAlgH323Stats  5 }

--==================================================================
-- axFixedNatAlgPptpStats
--==================================================================
	axFixedNatAlgPptpStats			OBJECT IDENTIFIER ::= { axFixedNatAlgStats 4 }

axFixedNatAlgPptpCallEsp    OBJECT-TYPE
    SYNTAX          CounterBasedGauge64
    MAX-ACCESS      read-only
    STATUS          current
    DESCRIPTION
        "The fixed nat alg pptp calls established."
    DEFVAL          { 0 }
    ::=  {  axFixedNatAlgPptpStats  1 }

axFixedNatAlgPptpMismatchedPnsCallId    OBJECT-TYPE
    SYNTAX          CounterBasedGauge64
    MAX-ACCESS      read-only
    STATUS          current
    DESCRIPTION
        "The fixed nat alg pptp mismatched pns call id."
    DEFVAL          { 0 }
    ::=  {  axFixedNatAlgPptpStats  2 }

axFixedNatAlgPptpGreSessionCreated    OBJECT-TYPE
    SYNTAX          CounterBasedGauge64
    MAX-ACCESS      read-only
    STATUS          current
    DESCRIPTION
        "The fixed nat alg pptp gre sessions created."
    DEFVAL          { 0 }
    ::=  {  axFixedNatAlgPptpStats  3 }

axFixedNatAlgPptpGreSessionFreed    OBJECT-TYPE
    SYNTAX          CounterBasedGauge64
    MAX-ACCESS      read-only
    STATUS          current
    DESCRIPTION
        "The fixed nat alg pptp gre sessions freed."
    DEFVAL          { 0 }
    ::=  {  axFixedNatAlgPptpStats  4 }

axFixedNatAlgPptpGreNoMatchGreSession    OBJECT-TYPE
    SYNTAX          CounterBasedGauge64
    MAX-ACCESS      read-only
    STATUS          current
    DESCRIPTION
        "The fixed nat alg pptp no matching gre sessions."
    DEFVAL          { 0 }
    ::=  {  axFixedNatAlgPptpStats  5 }

--==================================================================
-- axFixedNatAlgRtspStats
--==================================================================
	axFixedNatAlgRtspStats			OBJECT IDENTIFIER ::= { axFixedNatAlgStats 5 }

axFixedNatAlgRtspStreamCreated    OBJECT-TYPE
    SYNTAX          CounterBasedGauge64
    MAX-ACCESS      read-only
    STATUS          current
    DESCRIPTION
        "The fixed nat alg rtsp stream created."
    DEFVAL          { 0 }
    ::=  {  axFixedNatAlgRtspStats  1 }

axFixedNatAlgRtspStreamFreed    OBJECT-TYPE
    SYNTAX          CounterBasedGauge64
    MAX-ACCESS      read-only
    STATUS          current
    DESCRIPTION
        "The fixed nat alg rtsp stream freed."
    DEFVAL          { 0 }
    ::=  {  axFixedNatAlgRtspStats  2 }

axFixedNatAlgRtspStreamCreationFailed    OBJECT-TYPE
    SYNTAX          CounterBasedGauge64
    MAX-ACCESS      read-only
    STATUS          current
    DESCRIPTION
        "The fixed nat alg rtsp stream creation failures."
    DEFVAL          { 0 }
    ::=  {  axFixedNatAlgRtspStats  3 }

axFixedNatAlgRtspStreamClientPortAllocated   OBJECT-TYPE
    SYNTAX          CounterBasedGauge64
    MAX-ACCESS      read-only
    STATUS          current
    DESCRIPTION
        "The fixed nat alg rtsp stream client ports allocated."
    DEFVAL          { 0 }
    ::=  {  axFixedNatAlgRtspStats  4 }

axFixedNatAlgRtspStreamClientPortFreed   OBJECT-TYPE
    SYNTAX          CounterBasedGauge64
    MAX-ACCESS      read-only
    STATUS          current
    DESCRIPTION
        "The fixed nat alg rtsp stream client ports freed."
    DEFVAL          { 0 }
    ::=  {  axFixedNatAlgRtspStats  5 }

axFixedNatAlgRtspStreamClientPortAllocationFailed   OBJECT-TYPE
    SYNTAX          CounterBasedGauge64
    MAX-ACCESS      read-only
    STATUS          current
    DESCRIPTION
        "The fixed nat alg rtsp stream client port allocation failures."
    DEFVAL          { 0 }
    ::=  {  axFixedNatAlgRtspStats  6 }

axFixedNatAlgRtspSrvRepWithUnknownClientPorts   OBJECT-TYPE
    SYNTAX          CounterBasedGauge64
    MAX-ACCESS      read-only
    STATUS          current
    DESCRIPTION
        "The fixed nat alg rtsp server replies with unknown client ports."
    DEFVAL          { 0 }
    ::=  {  axFixedNatAlgRtspStats  7 }

axFixedNatAlgRtspDataSessionCreated   OBJECT-TYPE
    SYNTAX          CounterBasedGauge64
    MAX-ACCESS      read-only
    STATUS          current
    DESCRIPTION
        "The fixed nat alg rtsp data session created."
    DEFVAL          { 0 }
    ::=  {  axFixedNatAlgRtspStats  8 }

axFixedNatAlgRtspDataSessionFreed   OBJECT-TYPE
    SYNTAX          CounterBasedGauge64
    MAX-ACCESS      read-only
    STATUS          current
    DESCRIPTION
        "The fixed nat alg rtsp data session freed."
    DEFVAL          { 0 }
    ::=  {  axFixedNatAlgRtspStats  9 }

axFixedNatAlgRtspDataSessionCreationFailed   OBJECT-TYPE
    SYNTAX          CounterBasedGauge64
    MAX-ACCESS      read-only
    STATUS          current
    DESCRIPTION
        "The fixed nat alg rtsp data session creation failures."
    DEFVAL          { 0 }
    ::=  {  axFixedNatAlgRtspStats  10 }

--==================================================================
-- axFixedNatAlgSipStats
--==================================================================
	axFixedNatAlgSipStats			OBJECT IDENTIFIER ::= { axFixedNatAlgStats 6 }

axFixedNatAlgSipMethodReg   OBJECT-TYPE
    SYNTAX          CounterBasedGauge64
    MAX-ACCESS      read-only
    STATUS          current
    DESCRIPTION
        "The fixed nat alg sip method register."
    DEFVAL          { 0 }
    ::=  {  axFixedNatAlgSipStats  1 }

axFixedNatAlgSipMethodInvite   OBJECT-TYPE
    SYNTAX          CounterBasedGauge64
    MAX-ACCESS      read-only
    STATUS          current
    DESCRIPTION
        "The fixed nat alg sip method invite."
    DEFVAL          { 0 }
    ::=  {  axFixedNatAlgSipStats  2 }

axFixedNatAlgSipMethodAck   OBJECT-TYPE
    SYNTAX          CounterBasedGauge64
    MAX-ACCESS      read-only
    STATUS          current
    DESCRIPTION
        "The fixed nat alg sip method ack."
    DEFVAL          { 0 }
    ::=  {  axFixedNatAlgSipStats  3 }

axFixedNatAlgSipMethodCancel   OBJECT-TYPE
    SYNTAX          CounterBasedGauge64
    MAX-ACCESS      read-only
    STATUS          current
    DESCRIPTION
        "The fixed nat alg sip method cancel."
    DEFVAL          { 0 }
    ::=  {  axFixedNatAlgSipStats  4 }


axFixedNatAlgSipMethodBye   OBJECT-TYPE
    SYNTAX          CounterBasedGauge64
    MAX-ACCESS      read-only
    STATUS          current
    DESCRIPTION
        "The fixed nat alg sip method bye."
    DEFVAL          { 0 }
    ::=  {  axFixedNatAlgSipStats  5 }

axFixedNatAlgSipMethodOptions   OBJECT-TYPE
    SYNTAX          CounterBasedGauge64
    MAX-ACCESS      read-only
    STATUS          current
    DESCRIPTION
        "The fixed nat alg sip method options."
    DEFVAL          { 0 }
    ::=  {  axFixedNatAlgSipStats  6 }

axFixedNatAlgSipMethodPrack   OBJECT-TYPE
    SYNTAX          CounterBasedGauge64
    MAX-ACCESS      read-only
    STATUS          current
    DESCRIPTION
        "The fixed nat alg sip method prack."
    DEFVAL          { 0 }
    ::=  {  axFixedNatAlgSipStats  7 }

axFixedNatAlgSipMethodSubscribe   OBJECT-TYPE
    SYNTAX          CounterBasedGauge64
    MAX-ACCESS      read-only
    STATUS          current
    DESCRIPTION
        "The fixed nat alg sip method subscribe."
    DEFVAL          { 0 }
    ::=  {  axFixedNatAlgSipStats  8 }

axFixedNatAlgSipMethodNotify   OBJECT-TYPE
    SYNTAX          CounterBasedGauge64
    MAX-ACCESS      read-only
    STATUS          current
    DESCRIPTION
        "The fixed nat alg sip method notify."
    DEFVAL          { 0 }
    ::=  {  axFixedNatAlgSipStats  9 }

axFixedNatAlgSipMethodPublish   OBJECT-TYPE
    SYNTAX          CounterBasedGauge64
    MAX-ACCESS      read-only
    STATUS          current
    DESCRIPTION
        "The fixed nat alg sip method publish."
    DEFVAL          { 0 }
    ::=  {  axFixedNatAlgSipStats  10 }

axFixedNatAlgSipMethodInfo   OBJECT-TYPE
    SYNTAX          CounterBasedGauge64
    MAX-ACCESS      read-only
    STATUS          current
    DESCRIPTION
        "The fixed nat alg sip method information."
    DEFVAL          { 0 }
    ::=  {  axFixedNatAlgSipStats  11 }

axFixedNatAlgSipMethodRefer   OBJECT-TYPE
    SYNTAX          CounterBasedGauge64
    MAX-ACCESS      read-only
    STATUS          current
    DESCRIPTION
        "The fixed nat alg sip method Refer."
    DEFVAL          { 0 }
    ::=  {  axFixedNatAlgSipStats  12 }

axFixedNatAlgSipMethodMessage   OBJECT-TYPE
    SYNTAX          CounterBasedGauge64
    MAX-ACCESS      read-only
    STATUS          current
    DESCRIPTION
        "The fixed nat alg sip method message."
    DEFVAL          { 0 }
    ::=  {  axFixedNatAlgSipStats  13 }

axFixedNatAlgSipMethodUpdate   OBJECT-TYPE
    SYNTAX          CounterBasedGauge64
    MAX-ACCESS      read-only
    STATUS          current
    DESCRIPTION
        "The fixed nat alg sip method update."
    DEFVAL          { 0 }
    ::=  {  axFixedNatAlgSipStats  14 }

axFixedNatAlgSipMethodUnknown   OBJECT-TYPE
    SYNTAX          CounterBasedGauge64
    MAX-ACCESS      read-only
    STATUS          current
    DESCRIPTION
        "The fixed nat alg sip method unknown."
    DEFVAL          { 0 }
    ::=  {  axFixedNatAlgSipStats  15 }

--==================================================================
-- axFixedNatAlgTftpStats
--==================================================================
	axFixedNatAlgTftpStats			OBJECT IDENTIFIER ::= { axFixedNatAlgStats 7 }

axFixedNatAlgTftpClientSessionCreated   OBJECT-TYPE
    SYNTAX          CounterBasedGauge64
    MAX-ACCESS      read-only
    STATUS          current
    DESCRIPTION
        "The fixed nat alg tftp client sessions created."
    DEFVAL          { 0 }
    ::=  {  axFixedNatAlgTftpStats  1 }

--==================================================================
-- axFixedNatTop5PrivateIpAddrTotSessions
--==================================================================

    axFixedNatTop5PrivateIpAddrTotSessionTable OBJECT-TYPE
	SYNTAX SEQUENCE OF AxFixedNatTop5PrivateIpAddrTotSessionEntry
	MAX-ACCESS not-accessible
	STATUS current
	DESCRIPTION
		"A table containing Top 5 fixed nat private IPs and total number of sessions(ports)."
	::= { axFixedNatTop5PrivateIpAddrTotSessions 1 } 

    axFixedNatTop5PrivateIpAddrTotSessionEntry OBJECT-TYPE
	SYNTAX  AxFixedNatTop5PrivateIpAddrTotSessionEntry
	MAX-ACCESS not-accessible
	STATUS current
	DESCRIPTION
		"Columns in the axFixedNatTop5PrivateIpAddrTotSessions Table"
	INDEX {
		axFixedNatTop5PrivateIpAddr
	}
	::= { axFixedNatTop5PrivateIpAddrTotSessionTable 1 } 

    AxFixedNatTop5PrivateIpAddrTotSessionEntry ::= 
	SEQUENCE {
        	axFixedNatTop5PrivateIpAddr                 DisplayString,
        	axFixedNatTop5PrivateIpAddrTotNumSessions   Integer32,
        	axFixedNatTop5PrivateIpAddrGlobalIpAddr     DisplayString
	}

    axFixedNatTop5PrivateIpAddr OBJECT-TYPE 
	SYNTAX DisplayString
	MAX-ACCESS read-only
	STATUS current
	DESCRIPTION
		"The private IP address in the Top 5 fixed nat private IP address entry."
	::= { axFixedNatTop5PrivateIpAddrTotSessionEntry 1 } 

    axFixedNatTop5PrivateIpAddrTotNumSessions OBJECT-TYPE 
	SYNTAX Integer32
	MAX-ACCESS read-only
	STATUS current
	DESCRIPTION
		"The total number of sessions in the Top 5 fixed nat private IP address entry."
	::= { axFixedNatTop5PrivateIpAddrTotSessionEntry 2 } 

    axFixedNatTop5PrivateIpAddrGlobalIpAddr OBJECT-TYPE 
	SYNTAX DisplayString
	MAX-ACCESS read-only
	STATUS current
	DESCRIPTION
		"The global IP address in the Top 5 fixed nat private IP address entry."
	::= { axFixedNatTop5PrivateIpAddrTotSessionEntry 3 } 

--==================================================================
-- axFixedNatTop5PrivateIpAddrTotTcpPorts
--==================================================================

    axFixedNatTop5PrivateIpAddrTotTcpPortTable OBJECT-TYPE
	SYNTAX SEQUENCE OF AxFixedNatTop5PrivateIpAddrTotTcpPortEntry
	MAX-ACCESS not-accessible
	STATUS current
	DESCRIPTION
		"A table containing Top 5 fixed nat private IPs and total number of tcp(ports)."
	::= { axFixedNatTop5PrivateIpAddrTotTcpPorts 1 } 

    axFixedNatTop5PrivateIpAddrTotTcpPortEntry OBJECT-TYPE
	SYNTAX  AxFixedNatTop5PrivateIpAddrTotTcpPortEntry
	MAX-ACCESS not-accessible
	STATUS current
	DESCRIPTION
		"Columns in the axFixedNatTop5PrivateIpAddrTotTcpPorts Table"
	INDEX {
		axFixedNatTop5PrivateIpAddrInTcpPort
	}
	::= { axFixedNatTop5PrivateIpAddrTotTcpPortTable 1 } 

    AxFixedNatTop5PrivateIpAddrTotTcpPortEntry ::= 
	SEQUENCE {
        	axFixedNatTop5PrivateIpAddrInTcpPort        		 DisplayString,
        	axFixedNatTop5PrivateIpAddrTotNumInTcpPort     		 Integer32,
        	axFixedNatTop5PrivateIpAddrGlobalIpAddrInTcpPort     DisplayString
	}

    axFixedNatTop5PrivateIpAddrInTcpPort OBJECT-TYPE 
	SYNTAX DisplayString
	MAX-ACCESS read-only
	STATUS current
	DESCRIPTION
		"The private IP address in the Top 5 fixed nat private IP address entry."
	::= { axFixedNatTop5PrivateIpAddrTotTcpPortEntry 1 } 

    axFixedNatTop5PrivateIpAddrTotNumInTcpPort OBJECT-TYPE 
	SYNTAX Integer32
	MAX-ACCESS read-only
	STATUS current
	DESCRIPTION
		"The total number of tcp ports in the Top 5 fixed nat private IP address entry."
	::= { axFixedNatTop5PrivateIpAddrTotTcpPortEntry 2 } 

    axFixedNatTop5PrivateIpAddrGlobalIpAddrInTcpPort OBJECT-TYPE 
	SYNTAX DisplayString
	MAX-ACCESS read-only
	STATUS current
	DESCRIPTION
		"The global IP address in the Top 5 fixed nat private IP address entry."
	::= { axFixedNatTop5PrivateIpAddrTotTcpPortEntry 3 } 

--==================================================================
-- axFixedNatTop5PrivateIpAddrTotUdpPorts
--==================================================================

    axFixedNatTop5PrivateIpAddrTotUdpPortTable OBJECT-TYPE
	SYNTAX SEQUENCE OF AxFixedNatTop5PrivateIpAddrTotUdpPortEntry
	MAX-ACCESS not-accessible
	STATUS current
	DESCRIPTION
		"A table containing Top 5 fixed nat private IPs and total number of udp(ports)."
	::= { axFixedNatTop5PrivateIpAddrTotUdpPorts 1 } 

    axFixedNatTop5PrivateIpAddrTotUdpPortEntry OBJECT-TYPE
	SYNTAX  AxFixedNatTop5PrivateIpAddrTotUdpPortEntry
	MAX-ACCESS not-accessible
	STATUS current
	DESCRIPTION
		"Columns in the axFixedNatTop5PrivateIpAddrTotUdpPorts Table"
	INDEX {
		axFixedNatTop5PrivateIpAddrInUdpPort
	}
	::= { axFixedNatTop5PrivateIpAddrTotUdpPortTable 1 } 

    AxFixedNatTop5PrivateIpAddrTotUdpPortEntry ::= 
	SEQUENCE {
        	axFixedNatTop5PrivateIpAddrInUdpPort        		 DisplayString,
        	axFixedNatTop5PrivateIpAddrTotNumInUdpPort     		 Integer32,
        	axFixedNatTop5PrivateIpAddrGlobalIpAddrInUdpPort     DisplayString
	}

    axFixedNatTop5PrivateIpAddrInUdpPort OBJECT-TYPE 
	SYNTAX DisplayString
	MAX-ACCESS read-only
	STATUS current
	DESCRIPTION
		"The private IP address in the Top 5 fixed nat private IP address entry."
	::= { axFixedNatTop5PrivateIpAddrTotUdpPortEntry 1 } 

    axFixedNatTop5PrivateIpAddrTotNumInUdpPort OBJECT-TYPE 
	SYNTAX Integer32
	MAX-ACCESS read-only
	STATUS current
	DESCRIPTION
		"The total number of tcp ports in the Top 5 fixed nat private IP address entry."
	::= { axFixedNatTop5PrivateIpAddrTotUdpPortEntry 2 } 

    axFixedNatTop5PrivateIpAddrGlobalIpAddrInUdpPort OBJECT-TYPE 
	SYNTAX DisplayString
	MAX-ACCESS read-only
	STATUS current
	DESCRIPTION
		"The global IP address in the Top 5 fixed nat private IP address entry."
	::= { axFixedNatTop5PrivateIpAddrTotUdpPortEntry 3 } 

--==================================================================
-- axFixedNatTop5PrivateIpAddrTotIcmpPorts
--==================================================================

    axFixedNatTop5PrivateIpAddrTotIcmpPortTable OBJECT-TYPE
	SYNTAX SEQUENCE OF AxFixedNatTop5PrivateIpAddrTotIcmpPortEntry
	MAX-ACCESS not-accessible
	STATUS current
	DESCRIPTION
		"A table containing Top 5 fixed nat private IPs and total number of icmp(ports)."
	::= { axFixedNatTop5PrivateIpAddrTotIcmpPorts 1 } 

    axFixedNatTop5PrivateIpAddrTotIcmpPortEntry OBJECT-TYPE
	SYNTAX  AxFixedNatTop5PrivateIpAddrTotIcmpPortEntry
	MAX-ACCESS not-accessible
	STATUS current
	DESCRIPTION
		"Columns in the axFixedNatTop5PrivateIpAddrTotIcmpPorts Table"
	INDEX {
		axFixedNatTop5PrivateIpAddrInIcmpPort
	}
	::= { axFixedNatTop5PrivateIpAddrTotIcmpPortTable 1 } 

    AxFixedNatTop5PrivateIpAddrTotIcmpPortEntry ::= 
	SEQUENCE {
        	axFixedNatTop5PrivateIpAddrInIcmpPort        		 DisplayString,
        	axFixedNatTop5PrivateIpAddrTotNumInIcmpPort   		 Integer32,
        	axFixedNatTop5PrivateIpAddrGlobalIpAddrInIcmpPort    DisplayString
	}

    axFixedNatTop5PrivateIpAddrInIcmpPort OBJECT-TYPE 
	SYNTAX DisplayString
	MAX-ACCESS read-only
	STATUS current
	DESCRIPTION
		"The private IP address in the Top 5 fixed nat private IP address entry."
	::= { axFixedNatTop5PrivateIpAddrTotIcmpPortEntry 1 } 

    axFixedNatTop5PrivateIpAddrTotNumInIcmpPort OBJECT-TYPE 
	SYNTAX Integer32
	MAX-ACCESS read-only
	STATUS current
	DESCRIPTION
		"The total number of tcp ports in the Top 5 fixed nat private IP address entry."
	::= { axFixedNatTop5PrivateIpAddrTotIcmpPortEntry 2 } 

    axFixedNatTop5PrivateIpAddrGlobalIpAddrInIcmpPort OBJECT-TYPE 
	SYNTAX DisplayString
	MAX-ACCESS read-only
	STATUS current
	DESCRIPTION
		"The global IP address in the Top 5 fixed nat private IP address entry."
	::= { axFixedNatTop5PrivateIpAddrTotIcmpPortEntry 3 } 

--==================================================================
-- axFixedNatTop5UserPrivateIpAddrTotSessions
--==================================================================

    axFixedNatTop5UserPrivateIpAddrTotSessionTable OBJECT-TYPE
	SYNTAX SEQUENCE OF AxFixedNatTop5UserPrivateIpAddrTotSessionEntry
	MAX-ACCESS not-accessible
	STATUS current
	DESCRIPTION
		"A table containing Top 5 fixed nat private IPs and total number of tcp(ports)."
	::= { axFixedNatTop5UserPrivateIpAddrTotSessions 1 } 

    axFixedNatTop5UserPrivateIpAddrTotSessionEntry OBJECT-TYPE
	SYNTAX  AxFixedNatTop5UserPrivateIpAddrTotSessionEntry
	MAX-ACCESS not-accessible
	STATUS current
	DESCRIPTION
		"Columns in the axFixedNatTop5UserPrivateIpAddrSession Table"
	INDEX {
		axFixedNatTop5UserPrivateIpAddr
	}
	::= { axFixedNatTop5UserPrivateIpAddrTotSessionTable 1 } 

    AxFixedNatTop5UserPrivateIpAddrTotSessionEntry ::= 
	SEQUENCE {
        	axFixedNatTop5UserPrivateIpAddr        	   	 	DisplayString,
        	axFixedNatTop5UserPrivateIpAddrTotNumSession 	Integer32,
        	axFixedNatTop5UserPrivateIpAddrGlobalIpAddr     DisplayString
	}

    axFixedNatTop5UserPrivateIpAddr OBJECT-TYPE 
	SYNTAX DisplayString
	MAX-ACCESS read-only
	STATUS current
	DESCRIPTION
		"The private IP address in the Top 5 fixed nat private IP address entry."
	::= { axFixedNatTop5UserPrivateIpAddrTotSessionEntry 1 } 

    axFixedNatTop5UserPrivateIpAddrTotNumSession OBJECT-TYPE 
	SYNTAX Integer32
	MAX-ACCESS read-only
	STATUS current
	DESCRIPTION
		"The total number of tcp ports in the Top 5 fixed nat private IP address entry."
	::= { axFixedNatTop5UserPrivateIpAddrTotSessionEntry 2 } 

    axFixedNatTop5UserPrivateIpAddrGlobalIpAddr OBJECT-TYPE 
	SYNTAX DisplayString
	MAX-ACCESS read-only
	STATUS current
	DESCRIPTION
		"The global IP address in the Top 5 fixed nat private IP address entry."
	::= { axFixedNatTop5UserPrivateIpAddrTotSessionEntry 3 } 

--==================================================================
-- axFixedNatTop5UserPrivateIpAddrTotTcpPorts
--==================================================================

    axFixedNatTop5UserPrivateIpAddrTotTcpPortTable OBJECT-TYPE
	SYNTAX SEQUENCE OF AxFixedNatTop5UserPrivateIpAddrTotTcpPortEntry
	MAX-ACCESS not-accessible
	STATUS current
	DESCRIPTION
		"A table containing Top 5 fixed nat private IPs and total number of tcp(ports)."
	::= { axFixedNatTop5UserPrivateIpAddrTotTcpPorts 1 } 

    axFixedNatTop5UserPrivateIpAddrTotTcpPortEntry OBJECT-TYPE
	SYNTAX  AxFixedNatTop5UserPrivateIpAddrTotTcpPortEntry
	MAX-ACCESS not-accessible
	STATUS current
	DESCRIPTION
		"Columns in the axFixedNatTop5UserPrivateIpAddrTotTcpPort Table"
	INDEX {
		axFixedNatTop5UserPrivateIpAddrInTcp
	}
	::= { axFixedNatTop5UserPrivateIpAddrTotTcpPortTable 1 } 

    AxFixedNatTop5UserPrivateIpAddrTotTcpPortEntry ::= 
	SEQUENCE {
        	axFixedNatTop5UserPrivateIpAddrInTcp        	   	DisplayString,
        	axFixedNatTop5UserPrivateIpAddrTotNumInTcp 			Integer32,
        	axFixedNatTop5UserPrivateIpAddrGlobalIpAddrInTcp    DisplayString
	}

    axFixedNatTop5UserPrivateIpAddrInTcp OBJECT-TYPE 
	SYNTAX DisplayString
	MAX-ACCESS read-only
	STATUS current
	DESCRIPTION
		"The private IP address in the Top 5 fixed nat private IP address entry."
	::= { axFixedNatTop5UserPrivateIpAddrTotTcpPortEntry 1 } 

    axFixedNatTop5UserPrivateIpAddrTotNumInTcp OBJECT-TYPE 
	SYNTAX Integer32
	MAX-ACCESS read-only
	STATUS current
	DESCRIPTION
		"The total number of tcp ports in the Top 5 fixed nat private IP address entry."
	::= { axFixedNatTop5UserPrivateIpAddrTotTcpPortEntry 2 } 

    axFixedNatTop5UserPrivateIpAddrGlobalIpAddrInTcp OBJECT-TYPE 
	SYNTAX DisplayString
	MAX-ACCESS read-only
	STATUS current
	DESCRIPTION
		"The global IP address in the Top 5 fixed nat private IP address entry."
	::= { axFixedNatTop5UserPrivateIpAddrTotTcpPortEntry 3 } 

--==================================================================
-- axFixedNatTop5UserPrivateIpAddrTotUdpPorts
--==================================================================

    axFixedNatTop5UserPrivateIpAddrTotUdpPortTable OBJECT-TYPE
	SYNTAX SEQUENCE OF AxFixedNatTop5UserPrivateIpAddrTotUdpPortEntry
	MAX-ACCESS not-accessible
	STATUS current
	DESCRIPTION
		"A table containing Top 5 fixed nat private IPs and total number of ucp(ports)."
	::= { axFixedNatTop5UserPrivateIpAddrTotUdpPorts 1 } 

    axFixedNatTop5UserPrivateIpAddrTotUdpPortEntry OBJECT-TYPE
	SYNTAX  AxFixedNatTop5UserPrivateIpAddrTotUdpPortEntry
	MAX-ACCESS not-accessible
	STATUS current
	DESCRIPTION
		"Columns in the axFixedNatTop5UserPrivateIpAddrTotUdpPort Table"
	INDEX {
		axFixedNatTop5UserPrivateIpAddrInUdp
	}
	::= { axFixedNatTop5UserPrivateIpAddrTotUdpPortTable 1 } 

    AxFixedNatTop5UserPrivateIpAddrTotUdpPortEntry ::= 
	SEQUENCE {
        	axFixedNatTop5UserPrivateIpAddrInUdp        	   	DisplayString,
        	axFixedNatTop5UserPrivateIpAddrTotNumInUdp 			Integer32,
        	axFixedNatTop5UserPrivateIpAddrGlobalIpAddrInUdp    DisplayString
	}

    axFixedNatTop5UserPrivateIpAddrInUdp OBJECT-TYPE 
	SYNTAX DisplayString
	MAX-ACCESS read-only
	STATUS current
	DESCRIPTION
		"The private IP address in the Top 5 fixed nat private IP address entry."
	::= { axFixedNatTop5UserPrivateIpAddrTotUdpPortEntry 1 } 

    axFixedNatTop5UserPrivateIpAddrTotNumInUdp OBJECT-TYPE 
	SYNTAX Integer32
	MAX-ACCESS read-only
	STATUS current
	DESCRIPTION
		"The total number of tcp ports in the Top 5 fixed nat private IP address entry."
	::= { axFixedNatTop5UserPrivateIpAddrTotUdpPortEntry 2 } 

    axFixedNatTop5UserPrivateIpAddrGlobalIpAddrInUdp OBJECT-TYPE 
	SYNTAX DisplayString
	MAX-ACCESS read-only
	STATUS current
	DESCRIPTION
		"The global IP address in the Top 5 fixed nat private IP address entry."
	::= { axFixedNatTop5UserPrivateIpAddrTotUdpPortEntry 3 } 

--==================================================================
-- axFixedNatTop5UserPrivateIpAddrTotIcmpPorts
--==================================================================

    axFixedNatTop5UserPrivateIpAddrTotIcmpPortTable OBJECT-TYPE
	SYNTAX SEQUENCE OF AxFixedNatTop5UserPrivateIpAddrTotIcmpPortEntry
	MAX-ACCESS not-accessible
	STATUS current
	DESCRIPTION
		"A table containing Top 5 fixed nat user private IPs and total number of icmp(ports)."
	::= { axFixedNatTop5UserPrivateIpAddrTotIcmpPorts 1 } 

    axFixedNatTop5UserPrivateIpAddrTotIcmpPortEntry OBJECT-TYPE
	SYNTAX  AxFixedNatTop5UserPrivateIpAddrTotIcmpPortEntry
	MAX-ACCESS not-accessible
	STATUS current
	DESCRIPTION
		"Columns in the axFixedNatTop5UserPrivateIpAddrTotIcmpPort Table"
	INDEX {
		axFixedNatTop5UserPrivateIpAddrInIcmp
	}
	::= { axFixedNatTop5UserPrivateIpAddrTotIcmpPortTable 1 } 

    AxFixedNatTop5UserPrivateIpAddrTotIcmpPortEntry ::= 
	SEQUENCE {
        	axFixedNatTop5UserPrivateIpAddrInIcmp        	   	DisplayString,
        	axFixedNatTop5UserPrivateIpAddrTotNumInIcmp 		Integer32,
        	axFixedNatTop5UserPrivateIpAddrGlobalIpAddrInIcmp   DisplayString
	}

    axFixedNatTop5UserPrivateIpAddrInIcmp OBJECT-TYPE 
	SYNTAX DisplayString
	MAX-ACCESS read-only
	STATUS current
	DESCRIPTION
		"The private IP address in the Top 5 fixed nat user private IP address entry."
	::= { axFixedNatTop5UserPrivateIpAddrTotIcmpPortEntry 1 } 

    axFixedNatTop5UserPrivateIpAddrTotNumInIcmp OBJECT-TYPE 
	SYNTAX Integer32
	MAX-ACCESS read-only
	STATUS current
	DESCRIPTION
		"The total number of icmp ports in the Top 5 fixed nat user private IP address entry."
	::= { axFixedNatTop5UserPrivateIpAddrTotIcmpPortEntry 2 } 

    axFixedNatTop5UserPrivateIpAddrGlobalIpAddrInIcmp OBJECT-TYPE 
	SYNTAX DisplayString
	MAX-ACCESS read-only
	STATUS current
	DESCRIPTION
		"The global IP address in the Top 5 fixed nat user private IP address entry."
	::= { axFixedNatTop5UserPrivateIpAddrTotIcmpPortEntry 3 } 

--==================================================================
-- axFixedNatTop5GlobalIpAddrTotUsers
--==================================================================

    axFixedNatTop5GlobalIpAddrTotUserTable OBJECT-TYPE
	SYNTAX SEQUENCE OF AxFixedNatTop5GlobalIpAddrTotUserEntry
	MAX-ACCESS not-accessible
	STATUS current
	DESCRIPTION
		"A table containing Top 5 fixed nat private IPs and total number of udp(ports)."
	::= { axFixedNatTop5GlobalIpAddrTotUsers 1 } 

    axFixedNatTop5GlobalIpAddrTotUserEntry OBJECT-TYPE
	SYNTAX  AxFixedNatTop5GlobalIpAddrTotUserEntry
	MAX-ACCESS not-accessible
	STATUS current
	DESCRIPTION
		"Columns in the axFixedNatTop5GlobalIpAddrTotUser Table"
	INDEX {
		axFixedNatTop5GlobalIpAddrUser
	}
	::= { axFixedNatTop5GlobalIpAddrTotUserTable 1 } 

    AxFixedNatTop5GlobalIpAddrTotUserEntry ::= 
	SEQUENCE {
        	axFixedNatTop5GlobalIpAddrUser			DisplayString,
        	axFixedNatTop5GlobalIpAddrTotNum		Integer32
	}

    axFixedNatTop5GlobalIpAddrUser OBJECT-TYPE 
	SYNTAX DisplayString
	MAX-ACCESS read-only
	STATUS current
	DESCRIPTION
		"The private IP address in the Top 5 fixed nat global IP address entry."
	::= { axFixedNatTop5GlobalIpAddrTotUserEntry 1 } 

    axFixedNatTop5GlobalIpAddrTotNum OBJECT-TYPE 
	SYNTAX Integer32
	MAX-ACCESS read-only
	STATUS current
	DESCRIPTION
		"The total number of tcp ports in the Top 5 fixed nat private IP address entry."
	::= { axFixedNatTop5GlobalIpAddrTotUserEntry 2 } 

--==================================================================
-- axFixedNatTop5GlobalIpAddrTotTcpPorts
--==================================================================

    axFixedNatTop5GlobalIpAddrTotTcpPortTable OBJECT-TYPE
	SYNTAX SEQUENCE OF AxFixedNatTop5GlobalIpAddrTotTcpPortEntry
	MAX-ACCESS not-accessible
	STATUS current
	DESCRIPTION
		"A table containing Top 5 fixed nat private IPs and total number of tcp(ports)."
	::= { axFixedNatTop5GlobalIpAddrTotTcpPorts 1 } 

    axFixedNatTop5GlobalIpAddrTotTcpPortEntry OBJECT-TYPE
	SYNTAX  AxFixedNatTop5GlobalIpAddrTotTcpPortEntry
	MAX-ACCESS not-accessible
	STATUS current
	DESCRIPTION
		"Columns in the axFixedNatTop5GlobalIpAddrTotTcpPort Table"
	INDEX {
		axFixedNatTop5GlobalIpAddrInTcp
	}
	::= { axFixedNatTop5GlobalIpAddrTotTcpPortTable 1 } 

    AxFixedNatTop5GlobalIpAddrTotTcpPortEntry ::= 
	SEQUENCE {
        	axFixedNatTop5GlobalIpAddrInTcp        	   	DisplayString,
        	axFixedNatTop5GlobalIpAddrTotNumInTcp 			Integer32,
	}

    axFixedNatTop5GlobalIpAddrInTcp OBJECT-TYPE 
	SYNTAX DisplayString
	MAX-ACCESS read-only
	STATUS current
	DESCRIPTION
		"The private IP address in the Top 5 fixed nat private IP address entry."
	::= { axFixedNatTop5GlobalIpAddrTotTcpPortEntry 1 } 

    axFixedNatTop5GlobalIpAddrTotNumInTcp OBJECT-TYPE 
	SYNTAX Integer32
	MAX-ACCESS read-only
	STATUS current
	DESCRIPTION
		"The total number of tcp ports in the Top 5 fixed nat private IP address entry."
	::= { axFixedNatTop5GlobalIpAddrTotTcpPortEntry 2 } 

--==================================================================
-- axFixedNatTop5GlobalIpAddrTotUdpPorts
--==================================================================

    axFixedNatTop5GlobalIpAddrTotUdpPortTable OBJECT-TYPE
	SYNTAX SEQUENCE OF AxFixedNatTop5GlobalIpAddrTotUdpPortEntry
	MAX-ACCESS not-accessible
	STATUS current
	DESCRIPTION
		"A table containing Top 5 fixed nat private IPs and total number of udp(ports)."
	::= { axFixedNatTop5GlobalIpAddrTotUdpPorts 1 } 

    axFixedNatTop5GlobalIpAddrTotUdpPortEntry OBJECT-TYPE
	SYNTAX  AxFixedNatTop5GlobalIpAddrTotUdpPortEntry
	MAX-ACCESS not-accessible
	STATUS current
	DESCRIPTION
		"Columns in the axFixedNatTop5GlobalIpAddrTotUdpPort Table"
	INDEX {
		axFixedNatTop5GlobalIpAddrInUdp
	}
	::= { axFixedNatTop5GlobalIpAddrTotUdpPortTable 1 } 

    AxFixedNatTop5GlobalIpAddrTotUdpPortEntry ::= 
	SEQUENCE {
        	axFixedNatTop5GlobalIpAddrInUdp        	     	DisplayString,
        	axFixedNatTop5GlobalIpAddrTotNumInUdp 			Integer32,
	}

    axFixedNatTop5GlobalIpAddrInUdp OBJECT-TYPE 
	SYNTAX DisplayString
	MAX-ACCESS read-only
	STATUS current
	DESCRIPTION
		"The private IP address in the Top 5 fixed nat global IP address entry."
	::= { axFixedNatTop5GlobalIpAddrTotUdpPortEntry 1 } 

    axFixedNatTop5GlobalIpAddrTotNumInUdp OBJECT-TYPE 
	SYNTAX Integer32
	MAX-ACCESS read-only
	STATUS current
	DESCRIPTION
		"The total number of tcp ports in the Top 5 fixed nat private IP address entry."
	::= { axFixedNatTop5GlobalIpAddrTotUdpPortEntry 2 } 

--==================================================================
-- axFixedNatFile
--==================================================================

    axFixedNatFileTable OBJECT-TYPE
	SYNTAX SEQUENCE OF AxFixedNatFileEntry
	MAX-ACCESS not-accessible
	STATUS current
	DESCRIPTION
		"A table containing fixed nat files."
	::= { axFixedNatFile 1 } 

    axFixedNatFileEntry OBJECT-TYPE
	SYNTAX  AxFixedNatFileEntry
	MAX-ACCESS not-accessible
	STATUS current
	DESCRIPTION
		"Columns in the axFixedNatFile Table"
	INDEX {
		axFixedNatFileName
	}
	::= { axFixedNatFileTable 1 } 

    AxFixedNatFileEntry ::= 
	SEQUENCE {
        	axFixedNatFileName        	     	DisplayString,
        	axFixedNatFileTimeStamp 			DisplayString,
	}

    axFixedNatFileName OBJECT-TYPE 
	SYNTAX DisplayString
	MAX-ACCESS read-only
	STATUS current
	DESCRIPTION
		"The file name in fixed nat file table entry."
	::= { axFixedNatFileEntry 1 } 


    axFixedNatFileTimeStamp OBJECT-TYPE 
	SYNTAX DisplayString
	MAX-ACCESS read-only
	STATUS current
	DESCRIPTION
		"The time stamp of fixed nat files."
	::= { axFixedNatFileEntry 2 } 

--==================================================================
-- axDDosStats
--==================================================================

	axDDosStats               OBJECT IDENTIFIER ::= { axDDoS 1 }

    axDDosStatsL3EntryAdded OBJECT-TYPE
     SYNTAX CounterBasedGauge64
     MAX-ACCESS read-only
     STATUS  current
     DESCRIPTION
     "The number of L3 entries added."
     ::= { axDDosStats 1 }

    axDDosStatsL3EntryDeleted OBJECT-TYPE
     SYNTAX CounterBasedGauge64
     MAX-ACCESS read-only
     STATUS  current
     DESCRIPTION
     "The number of L3 entries deleted."
     ::= { axDDosStats 2 }

    axDDosStatsL3EntryAddedToBGP OBJECT-TYPE
     SYNTAX CounterBasedGauge64
     MAX-ACCESS read-only
     STATUS  current
     DESCRIPTION
     "The number of L3 entries added to BGP."
     ::= { axDDosStats 3 }

    axDDosStatsL3EntryRemovedFromBGP OBJECT-TYPE
     SYNTAX CounterBasedGauge64
     MAX-ACCESS read-only
     STATUS  current
     DESCRIPTION
     "The number of L3 entries removed from BGP."
     ::= { axDDosStats 4 }

    axDDosStatsL3EntryAddedToHW OBJECT-TYPE
     SYNTAX CounterBasedGauge64
     MAX-ACCESS read-only
     STATUS  current
     DESCRIPTION
     "The number of L3 entries added to HW."
     ::= { axDDosStats 5 }

    axDDosStatsL3EntryRemovedFromHW OBJECT-TYPE
     SYNTAX CounterBasedGauge64
     MAX-ACCESS read-only
     STATUS  current
     DESCRIPTION
     "The number of L3 entries removed from HW."
     ::= { axDDosStats 6 }

    axDDosStatsTooManyL3Entries OBJECT-TYPE
     SYNTAX CounterBasedGauge64
     MAX-ACCESS read-only
     STATUS  current
     DESCRIPTION
     "The number of times L3 entries are exceeded."
     ::= { axDDosStats 7 }

    axDDosStatsL3EntryMatchDrop OBJECT-TYPE
     SYNTAX CounterBasedGauge64
     MAX-ACCESS read-only
     STATUS  current
     DESCRIPTION
     "The number of L3 entry match drops."
     ::= { axDDosStats 8 }

    axDDosStatsHWL3EntryMatchDrop OBJECT-TYPE
     SYNTAX CounterBasedGauge64
     MAX-ACCESS read-only
     STATUS  current
     DESCRIPTION
     "The number of HW L3 entry match drops."
     ::= { axDDosStats 9 }

    axDDosStatsL4EntryAdded OBJECT-TYPE
     SYNTAX CounterBasedGauge64
     MAX-ACCESS read-only
     STATUS  current
     DESCRIPTION
     "The number of L4 entries added."
     ::= { axDDosStats 10 }

    axDDosStatsL4EntryDeleted OBJECT-TYPE
     SYNTAX CounterBasedGauge64
     MAX-ACCESS read-only
     STATUS  current
     DESCRIPTION
     "The number of L4 entries deleted."
     ::= { axDDosStats 11 }

    axDDosStatsL4EntryAddedToHW OBJECT-TYPE
     SYNTAX CounterBasedGauge64
     MAX-ACCESS read-only
     STATUS  current
     DESCRIPTION
     "The number of L4 entries added to HW."
     ::= { axDDosStats 12 }

    axDDosStatsL4EntryRemovedFromHW OBJECT-TYPE
     SYNTAX CounterBasedGauge64
     MAX-ACCESS read-only
     STATUS  current
     DESCRIPTION
     "The number of L4 entries removed from HW."
     ::= { axDDosStats 13 }

    axDDosStatsHWOutOfL4Entries OBJECT-TYPE
     SYNTAX CounterBasedGauge64
     MAX-ACCESS read-only
     STATUS  current
     DESCRIPTION
     "The number of times HW is out of L4 entries."
     ::= { axDDosStats 14 }

    axDDosStatsL4EntryMatchDrop OBJECT-TYPE
     SYNTAX CounterBasedGauge64
     MAX-ACCESS read-only
     STATUS  current
     DESCRIPTION
     "The number of L4 entry match drops."
     ::= { axDDosStats 15 }

    axDDosStatsHWL4EntryMatchDrop OBJECT-TYPE
     SYNTAX CounterBasedGauge64
     MAX-ACCESS read-only
     STATUS  current
     DESCRIPTION
     "The number of HW L4 entry match drops."
     ::= { axDDosStats 16 }
--==================================================================
-- axFragmentStats
--==================================================================

    axFragmentStats       OBJECT IDENTIFIER ::= { axNetworkingStats 1 }

--==================================================================
-- axIpv4FragmentStats
--==================================================================

    axIpv4FragmentStats       OBJECT IDENTIFIER ::= { axFragmentStats 1 }

    axIpv4SessionInsert	OBJECT-TYPE	
	SYNTAX			CounterBasedGauge64
	MAX-ACCESS		read-only
	STATUS			current
	DESCRIPTION		
		"The count of l3 ipv4 session inserts."
	DEFVAL			{ 0 }
	::=  {  axIpv4FragmentStats  1  }

    axIpv4SessionExpired	OBJECT-TYPE	
	SYNTAX			CounterBasedGauge64
	MAX-ACCESS		read-only
	STATUS			current
	DESCRIPTION		
		"The count of l3 ipv4 session expired."
	DEFVAL			{ 0 }
	::=  {  axIpv4FragmentStats  2  }

    axIpv4IcmpReceived	OBJECT-TYPE	
	SYNTAX			CounterBasedGauge64
	MAX-ACCESS		read-only
	STATUS			current
	DESCRIPTION		
		"The count of l3 ipv4 ICMP Received."
	DEFVAL			{ 0 }
	::=  {  axIpv4FragmentStats  3  }
    
    axIpv4Icmpv6Received	OBJECT-TYPE	
	SYNTAX			CounterBasedGauge64
	MAX-ACCESS		read-only
	STATUS			current
	DESCRIPTION		
		"The count of l3 ipv4 ICMPv6 Received."
	DEFVAL			{ 0 }
	::=  {  axIpv4FragmentStats  4  }

    axIpv4UdpReceived	OBJECT-TYPE	
	SYNTAX			CounterBasedGauge64
	MAX-ACCESS		read-only
	STATUS			current
	DESCRIPTION		
		"The count of l3 ipv4 UDP Received."
	DEFVAL			{ 0 }
	::=  {  axIpv4FragmentStats  5  }

    axIpv4TcpReceived	OBJECT-TYPE	
	SYNTAX			CounterBasedGauge64
	MAX-ACCESS		read-only
	STATUS			current
	DESCRIPTION		
		"The count of l3 ipv4 Tcp Received."
	DEFVAL			{ 0 }
	::=  {  axIpv4FragmentStats  6  }

    axIpv4IpInIpReceived	OBJECT-TYPE	
	SYNTAX			CounterBasedGauge64
	MAX-ACCESS		read-only
	STATUS			current
	DESCRIPTION		
		"The count of l3 ipv4 Ip-In-Ip Received."
	DEFVAL			{ 0 }
	::=  {  axIpv4FragmentStats  7  }

    axIpv4Ipv6InIpReceived	OBJECT-TYPE	
	SYNTAX			CounterBasedGauge64
	MAX-ACCESS		read-only
	STATUS			current
	DESCRIPTION		
		"The count of l3 ipv4 Ipv6-In-Ip Received."
	DEFVAL			{ 0 }
	::=  {  axIpv4FragmentStats  8  }

    axIpv4OtherReceived	OBJECT-TYPE	
	SYNTAX			CounterBasedGauge64
	MAX-ACCESS		read-only
	STATUS			current
	DESCRIPTION		
		"The count of l3 ipv4 other Received."
	DEFVAL			{ 0 }
	::=  {  axIpv4FragmentStats  9  }

    axIpv4IcmpDropped	OBJECT-TYPE	
	SYNTAX			CounterBasedGauge64
	MAX-ACCESS		read-only
	STATUS			current
	DESCRIPTION		
		"The count of l3 ipv4 ICMP dropped."
	DEFVAL			{ 0 }
	::=  {  axIpv4FragmentStats  10  }

    axIpv4Icmpv6Dropped	OBJECT-TYPE	
	SYNTAX			CounterBasedGauge64
	MAX-ACCESS		read-only
	STATUS			current
	DESCRIPTION		
		"The count of l3 ipv4 ICMPv6 dropped."
	DEFVAL			{ 0 }
	::=  {  axIpv4FragmentStats  11  }

    axIpv4UdpDropped	OBJECT-TYPE	
	SYNTAX			CounterBasedGauge64
	MAX-ACCESS		read-only
	STATUS			current
	DESCRIPTION		
		"The count of l3 ipv4 UDP dropped."
	DEFVAL			{ 0 }
	::=  {  axIpv4FragmentStats  12  }

    axIpv4TcpDropped	OBJECT-TYPE	
	SYNTAX			CounterBasedGauge64
	MAX-ACCESS		read-only
	STATUS			current
	DESCRIPTION		
		"The count of l3 ipv4 TCP dropped."
	DEFVAL			{ 0 }
	::=  {  axIpv4FragmentStats  13  }

    axIpv4IpInIpDropped	OBJECT-TYPE	
	SYNTAX			CounterBasedGauge64
	MAX-ACCESS		read-only
	STATUS			current
	DESCRIPTION		
		"The count of l3 ipv4 Ip-In-Ip dropped."
	DEFVAL			{ 0 }
	::=  {  axIpv4FragmentStats  14  }

    axIpv4Ipv6InIpDropped	OBJECT-TYPE	
	SYNTAX			CounterBasedGauge64
	MAX-ACCESS		read-only
	STATUS			current
	DESCRIPTION		
		"The count of l3 ipv4 Ipv6-In-Ip dropped."
	DEFVAL			{ 0 }
	::=  {  axIpv4FragmentStats  15  }

    axIpv4OtherDropped	OBJECT-TYPE	
	SYNTAX			CounterBasedGauge64
	MAX-ACCESS		read-only
	STATUS			current
	DESCRIPTION		
		"The count of l3 ipv4 Other dropped."
	DEFVAL			{ 0 }
	::=  {  axIpv4FragmentStats  16  }

    axIpv4OverlappingFragmentDropped	OBJECT-TYPE	
	SYNTAX			CounterBasedGauge64
	MAX-ACCESS		read-only
	STATUS			current
	DESCRIPTION		
		"The count of l3 ipv4 overlapping fragment dropped."
	DEFVAL			{ 0 }
	::=  {  axIpv4FragmentStats  17  }

    axIpv4BadIpLength	OBJECT-TYPE	
	SYNTAX			CounterBasedGauge64
	MAX-ACCESS		read-only
	STATUS			current
	DESCRIPTION		
		"The count of l3 ipv4 bad ip length."
	DEFVAL			{ 0 }
	::=  {  axIpv4FragmentStats  18  }

    axIpv4FragmentTooSmallDrop	OBJECT-TYPE	
	SYNTAX			CounterBasedGauge64
	MAX-ACCESS		read-only
	STATUS			current
	DESCRIPTION		
		"The count of l3 ipv4 fragment too small drop."
	DEFVAL			{ 0 }
	::=  {  axIpv4FragmentStats  19  }

    axIpv4FirstTcpFragmentTooSmallDrop	OBJECT-TYPE	
	SYNTAX			CounterBasedGauge64
	MAX-ACCESS		read-only
	STATUS			current
	DESCRIPTION		
		"The count of l3 ipv4 first TCP fragment too small drop."
	DEFVAL			{ 0 }
	::=  {  axIpv4FragmentStats  20  }

    axIpv4FirstL4FragmentTooSmallDrop	OBJECT-TYPE	
	SYNTAX			CounterBasedGauge64
	MAX-ACCESS		read-only
	STATUS			current
	DESCRIPTION		
		"The count of l3 ipv4 first L4 fragment too small drop."
	DEFVAL			{ 0 }
	::=  {  axIpv4FragmentStats  21  }

    axIpv4TotalSessionsExceedDrop	OBJECT-TYPE	
	SYNTAX			CounterBasedGauge64
	MAX-ACCESS		read-only
	STATUS			current
	DESCRIPTION		
		"The count of l3 ipv4 total sessions exceed drop."
	DEFVAL			{ 0 }
	::=  {  axIpv4FragmentStats  22  }

    axIpv4OutOfSessionMemory OBJECT-TYPE	
	SYNTAX			CounterBasedGauge64
	MAX-ACCESS		read-only
	STATUS			current
	DESCRIPTION		
		"The count of l3 ipv4 out of session memory."
	DEFVAL			{ 0 }
	::=  {  axIpv4FragmentStats  23  }

    axIpv4FragmentationFastAgingSet OBJECT-TYPE	
	SYNTAX			CounterBasedGauge64
	MAX-ACCESS		read-only
	STATUS			current
	DESCRIPTION		
		"The count of l3 ipv4 fragmentation fast aging set."
	DEFVAL			{ 0 }
	::=  {  axIpv4FragmentStats  24  }

    axIpv4FragmentationFastAgingUnset OBJECT-TYPE	
	SYNTAX			CounterBasedGauge64
	MAX-ACCESS		read-only
	STATUS			current
	DESCRIPTION		
		"The count of l3 ipv4 fragmentation fast aging unset."
	DEFVAL			{ 0 }
	::=  {  axIpv4FragmentStats  25  }

    axIpv4FragmentQueueSuccess OBJECT-TYPE	
	SYNTAX			CounterBasedGauge64
	MAX-ACCESS		read-only
	STATUS			current
	DESCRIPTION		
		"The count of l3 ipv4 fragment queue success."
	DEFVAL			{ 0 }
	::=  {  axIpv4FragmentStats  26  }

    axIpv4PayloadLengthUnaligned OBJECT-TYPE	
	SYNTAX			CounterBasedGauge64
	MAX-ACCESS		read-only
	STATUS			current
	DESCRIPTION		
		"The count of l3 ipv4 payload length unaligned."
	DEFVAL			{ 0 }
	::=  {  axIpv4FragmentStats  27  }

    axIpv4PayloadLengthOutOfBounds OBJECT-TYPE	
	SYNTAX			CounterBasedGauge64
	MAX-ACCESS		read-only
	STATUS			current
	DESCRIPTION		
		"The count of l3 ipv4 payload length out of bounds."
	DEFVAL			{ 0 }
	::=  {  axIpv4FragmentStats  28  }

    axIpv4DuplicateFirstFragment OBJECT-TYPE	
	SYNTAX			CounterBasedGauge64
	MAX-ACCESS		read-only
	STATUS			current
	DESCRIPTION		
		"The count of l3 ipv4 duplicate first fragment."
	DEFVAL			{ 0 }
	::=  {  axIpv4FragmentStats  29  }

    axIpv4DuplicateLastFragment OBJECT-TYPE	
	SYNTAX			CounterBasedGauge64
	MAX-ACCESS		read-only
	STATUS			current
	DESCRIPTION		
		"The count of l3 ipv4 duplicate last fragment."
	DEFVAL			{ 0 }
	::=  {  axIpv4FragmentStats  30  }

    axIpv4TotalQueuedFragmentsExceed OBJECT-TYPE	
	SYNTAX			CounterBasedGauge64
	MAX-ACCESS		read-only
	STATUS			current
	DESCRIPTION		
		"The count of l3 ipv4 total queued fragments exceed."
	DEFVAL			{ 0 }
	::=  {  axIpv4FragmentStats  31  }

    axIpv4FragmentQueueFailure OBJECT-TYPE	
	SYNTAX			CounterBasedGauge64
	MAX-ACCESS		read-only
	STATUS			current
	DESCRIPTION		
		"The count of l3 ipv4 fragment queue failure."
	DEFVAL			{ 0 }
	::=  {  axIpv4FragmentStats  32  }

    axIpv4FragmentReassemblySuccess OBJECT-TYPE	
	SYNTAX			CounterBasedGauge64
	MAX-ACCESS		read-only
	STATUS			current
	DESCRIPTION		
		"The count of l3 ipv4 fragment reassembly success."
	DEFVAL			{ 0 }
	::=  {  axIpv4FragmentStats  33  }

    axIpv4FragmentMaxDataLengthExceed OBJECT-TYPE	
	SYNTAX			CounterBasedGauge64
	MAX-ACCESS		read-only
	STATUS			current
	DESCRIPTION		
		"The count of l3 ipv4 fragment max data length exceed."
	DEFVAL			{ 0 }
	::=  {  axIpv4FragmentStats  34  }

    axIpv4FragmentReassemblyFailure OBJECT-TYPE	
	SYNTAX			CounterBasedGauge64
	MAX-ACCESS		read-only
	STATUS			current
	DESCRIPTION		
		"The count of l3 ipv4 fragment reassembly failure."
	DEFVAL			{ 0 }
	::=  {  axIpv4FragmentStats  35  }

    axIpv4MtuExceedPolicyDrop OBJECT-TYPE	
	SYNTAX			CounterBasedGauge64
	MAX-ACCESS		read-only
	STATUS			current
	DESCRIPTION		
		"The count of l3 ipv4 MTU exceed policy drop."
	DEFVAL			{ 0 }
	::=  {  axIpv4FragmentStats  36  }

    axIpv4FragmentProcessingDrop OBJECT-TYPE	
	SYNTAX			CounterBasedGauge64
	MAX-ACCESS		read-only
	STATUS			current
	DESCRIPTION		
		"The count of l3 ipv4 fragment processing drop."
	DEFVAL			{ 0 }
	::=  {  axIpv4FragmentStats  37  }

    axIpv4TooManyPacketsPerReassemblyDrop OBJECT-TYPE	
	SYNTAX			CounterBasedGauge64
	MAX-ACCESS		read-only
	STATUS			current
	DESCRIPTION		
		"The count of l3 ipv4 fragment too many packets per reassembly drop."
	DEFVAL			{ 0 }
	::=  {  axIpv4FragmentStats  38  }

    axIpv4SessionMaxPacketsExceed OBJECT-TYPE	
	SYNTAX			CounterBasedGauge64
	MAX-ACCESS		read-only
	STATUS			current
	DESCRIPTION		
		"The count of l3 ipv4 fragment Session max packets exceed."
	DEFVAL			{ 0 }
	::=  {  axIpv4FragmentStats  39  }

    axIpv4HighCpuThresholdReached OBJECT-TYPE	
	SYNTAX			CounterBasedGauge64
	MAX-ACCESS		read-only
	STATUS			current
	DESCRIPTION		
		"The count of l3 ipv4 fragment high cpu threshold."
	DEFVAL			{ 0 }
	::=  {  axIpv4FragmentStats  40  }

    axIpv4LowCpuThresholdReached OBJECT-TYPE	
	SYNTAX			CounterBasedGauge64
	MAX-ACCESS		read-only
	STATUS			current
	DESCRIPTION		
		"The count of l3 ipv4 fragment low cpu threshold."
	DEFVAL			{ 0 }
	::=  {  axIpv4FragmentStats  41  }

    axIpv4HighCpuDrop OBJECT-TYPE	
	SYNTAX			CounterBasedGauge64
	MAX-ACCESS		read-only
	STATUS			current
	DESCRIPTION		
		"The count of l3 ipv4 fragment high cpu drop."
	DEFVAL			{ 0 }
	::=  {  axIpv4FragmentStats  42  }

    axIpv4DDoSProtectionDrop OBJECT-TYPE	
	SYNTAX			CounterBasedGauge64
	MAX-ACCESS		read-only
	STATUS			current
	DESCRIPTION		
		"The count of l3 ipv4 fragment DDoS protection drop."
	DEFVAL			{ 0 }
	::=  {  axIpv4FragmentStats  43  }

--==================================================================
-- axIpv6FragmentStats
--==================================================================
    axIpv6FragmentStats        OBJECT IDENTIFIER ::= { axFragmentStats 2 }

    axIpv6SessionInsert	OBJECT-TYPE	
	SYNTAX			CounterBasedGauge64
	MAX-ACCESS		read-only
	STATUS			current
	DESCRIPTION		
		"The count of l3 ipv6 session inserts."
	DEFVAL			{ 0 }
	::=  {  axIpv6FragmentStats  1  }

    axIpv6SessionExpired	OBJECT-TYPE	
	SYNTAX			CounterBasedGauge64
	MAX-ACCESS		read-only
	STATUS			current
	DESCRIPTION		
		"The count of l3 ipv6 session expired."
	DEFVAL			{ 0 }
	::=  {  axIpv6FragmentStats  2  }

    axIpv6IcmpReceived	OBJECT-TYPE	
	SYNTAX			CounterBasedGauge64
	MAX-ACCESS		read-only
	STATUS			current
	DESCRIPTION		
		"The count of l3 ipv6 ICMP Received."
	DEFVAL			{ 0 }
	::=  {  axIpv6FragmentStats  3  }
    
    axIpv6Icmpv6Received	OBJECT-TYPE	
	SYNTAX			CounterBasedGauge64
	MAX-ACCESS		read-only
	STATUS			current
	DESCRIPTION		
		"The count of l3 ipv6 ICMPv6 Received."
	DEFVAL			{ 0 }
	::=  {  axIpv6FragmentStats  4  }

    axIpv6UdpReceived	OBJECT-TYPE	
	SYNTAX			CounterBasedGauge64
	MAX-ACCESS		read-only
	STATUS			current
	DESCRIPTION		
		"The count of l3 ipv6 UDP Received."
	DEFVAL			{ 0 }
	::=  {  axIpv6FragmentStats  5  }

    axIpv6TcpReceived	OBJECT-TYPE	
	SYNTAX			CounterBasedGauge64
	MAX-ACCESS		read-only
	STATUS			current
	DESCRIPTION		
		"The count of l3 ipv6 Tcp Received."
	DEFVAL			{ 0 }
	::=  {  axIpv6FragmentStats  6  }

    axIpv6IpInIpReceived	OBJECT-TYPE	
	SYNTAX			CounterBasedGauge64
	MAX-ACCESS		read-only
	STATUS			current
	DESCRIPTION		
		"The count of l3 ipv6 Ip-In-Ip Received."
	DEFVAL			{ 0 }
	::=  {  axIpv6FragmentStats  7  }

    axIpv6Ipv6InIpReceived	OBJECT-TYPE	
	SYNTAX			CounterBasedGauge64
	MAX-ACCESS		read-only
	STATUS			current
	DESCRIPTION		
		"The count of l3 ipv6 Ipv6-In-Ip Received."
	DEFVAL			{ 0 }
	::=  {  axIpv6FragmentStats  8  }

    axIpv6OtherReceived	OBJECT-TYPE	
	SYNTAX			CounterBasedGauge64
	MAX-ACCESS		read-only
	STATUS			current
	DESCRIPTION		
		"The count of l3 ipv6 other Received."
	DEFVAL			{ 0 }
	::=  {  axIpv6FragmentStats  9  }

    axIpv6IcmpDropped	OBJECT-TYPE	
	SYNTAX			CounterBasedGauge64
	MAX-ACCESS		read-only
	STATUS			current
	DESCRIPTION		
		"The count of l3 ipv6 ICMP dropped."
	DEFVAL			{ 0 }
	::=  {  axIpv6FragmentStats  10  }

    axIpv6Icmpv6Dropped	OBJECT-TYPE	
	SYNTAX			CounterBasedGauge64
	MAX-ACCESS		read-only
	STATUS			current
	DESCRIPTION		
		"The count of l3 ipv6 ICMPv6 dropped."
	DEFVAL			{ 0 }
	::=  {  axIpv6FragmentStats  11  }

    axIpv6UdpDropped	OBJECT-TYPE	
	SYNTAX			CounterBasedGauge64
	MAX-ACCESS		read-only
	STATUS			current
	DESCRIPTION		
		"The count of l3 ipv6 UDP dropped."
	DEFVAL			{ 0 }
	::=  {  axIpv6FragmentStats  12  }

    axIpv6TcpDropped	OBJECT-TYPE	
	SYNTAX			CounterBasedGauge64
	MAX-ACCESS		read-only
	STATUS			current
	DESCRIPTION		
		"The count of l3 ipv6 TCP dropped."
	DEFVAL			{ 0 }
	::=  {  axIpv6FragmentStats  13  }

    axIpv6IpInIpDropped	OBJECT-TYPE	
	SYNTAX			CounterBasedGauge64
	MAX-ACCESS		read-only
	STATUS			current
	DESCRIPTION		
		"The count of l3 ipv6 Ip-In-Ip dropped."
	DEFVAL			{ 0 }
	::=  {  axIpv6FragmentStats  14  }

    axIpv6Ipv6InIpDropped	OBJECT-TYPE	
	SYNTAX			CounterBasedGauge64
	MAX-ACCESS		read-only
	STATUS			current
	DESCRIPTION		
		"The count of l3 ipv6 Ipv6-In-Ip dropped."
	DEFVAL			{ 0 }
	::=  {  axIpv6FragmentStats  15  }

    axIpv6OtherDropped	OBJECT-TYPE	
	SYNTAX			CounterBasedGauge64
	MAX-ACCESS		read-only
	STATUS			current
	DESCRIPTION		
		"The count of l3 ipv6 Other dropped."
	DEFVAL			{ 0 }
	::=  {  axIpv6FragmentStats  16  }

    axIpv6OverlappingFragmentDropped	OBJECT-TYPE	
	SYNTAX			CounterBasedGauge64
	MAX-ACCESS		read-only
	STATUS			current
	DESCRIPTION		
		"The count of l3 ipv6 overlapping fragment dropped."
	DEFVAL			{ 0 }
	::=  {  axIpv6FragmentStats  17  }

    axIpv6BadIpLength	OBJECT-TYPE	
	SYNTAX			CounterBasedGauge64
	MAX-ACCESS		read-only
	STATUS			current
	DESCRIPTION		
		"The count of l3 ipv6 bad ip length."
	DEFVAL			{ 0 }
	::=  {  axIpv6FragmentStats  18  }

    axIpv6FragmentTooSmallDrop	OBJECT-TYPE	
	SYNTAX			CounterBasedGauge64
	MAX-ACCESS		read-only
	STATUS			current
	DESCRIPTION		
		"The count of l3 ipv6 fragment too small drop."
	DEFVAL			{ 0 }
	::=  {  axIpv6FragmentStats  19  }

    axIpv6FirstTcpFragmentTooSmallDrop	OBJECT-TYPE	
	SYNTAX			CounterBasedGauge64
	MAX-ACCESS		read-only
	STATUS			current
	DESCRIPTION		
		"The count of l3 ipv6 first TCP fragment too small drop."
	DEFVAL			{ 0 }
	::=  {  axIpv6FragmentStats  20  }

    axIpv6FirstL4FragmentTooSmallDrop	OBJECT-TYPE	
	SYNTAX			CounterBasedGauge64
	MAX-ACCESS		read-only
	STATUS			current
	DESCRIPTION		
		"The count of l3 ipv6 first L4 fragment too small drop."
	DEFVAL			{ 0 }
	::=  {  axIpv6FragmentStats  21  }

    axIpv6TotalSessionsExceedDrop	OBJECT-TYPE	
	SYNTAX			CounterBasedGauge64
	MAX-ACCESS		read-only
	STATUS			current
	DESCRIPTION		
		"The count of l3 ipv6 total sessions exceed drop."
	DEFVAL			{ 0 }
	::=  {  axIpv6FragmentStats  22  }

    axIpv6OutOfSessionMemory OBJECT-TYPE	
	SYNTAX			CounterBasedGauge64
	MAX-ACCESS		read-only
	STATUS			current
	DESCRIPTION		
		"The count of l3 ipv6 out of session memory."
	DEFVAL			{ 0 }
	::=  {  axIpv6FragmentStats  23  }

    axIpv6FragmentationFastAgingSet OBJECT-TYPE	
	SYNTAX			CounterBasedGauge64
	MAX-ACCESS		read-only
	STATUS			current
	DESCRIPTION		
		"The count of l3 ipv6 fragmentation fast aging set."
	DEFVAL			{ 0 }
	::=  {  axIpv6FragmentStats  24  }

    axIpv6FragmentationFastAgingUnset OBJECT-TYPE	
	SYNTAX			CounterBasedGauge64
	MAX-ACCESS		read-only
	STATUS			current
	DESCRIPTION		
		"The count of l3 ipv6 fragmentation fast aging unset."
	DEFVAL			{ 0 }
	::=  {  axIpv6FragmentStats  25  }

    axIpv6FragmentQueueSuccess OBJECT-TYPE	
	SYNTAX			CounterBasedGauge64
	MAX-ACCESS		read-only
	STATUS			current
	DESCRIPTION		
		"The count of l3 ipv6 fragment queue success."
	DEFVAL			{ 0 }
	::=  {  axIpv6FragmentStats  26  }

    axIpv6PayloadLengthUnaligned OBJECT-TYPE	
	SYNTAX			CounterBasedGauge64
	MAX-ACCESS		read-only
	STATUS			current
	DESCRIPTION		
		"The count of l3 ipv6 payload length unaligned."
	DEFVAL			{ 0 }
	::=  {  axIpv6FragmentStats  27  }

    axIpv6PayloadLengthOutOfBounds OBJECT-TYPE	
	SYNTAX			CounterBasedGauge64
	MAX-ACCESS		read-only
	STATUS			current
	DESCRIPTION		
		"The count of l3 ipv6 payload length out of bounds."
	DEFVAL			{ 0 }
	::=  {  axIpv6FragmentStats  28  }

    axIpv6DuplicateFirstFragment OBJECT-TYPE	
	SYNTAX			CounterBasedGauge64
	MAX-ACCESS		read-only
	STATUS			current
	DESCRIPTION		
		"The count of l3 ipv6 duplicate first fragment."
	DEFVAL			{ 0 }
	::=  {  axIpv6FragmentStats  29  }

    axIpv6DuplicateLastFragment OBJECT-TYPE	
	SYNTAX			CounterBasedGauge64
	MAX-ACCESS		read-only
	STATUS			current
	DESCRIPTION		
		"The count of l3 ipv6 duplicate last fragment."
	DEFVAL			{ 0 }
	::=  {  axIpv6FragmentStats  30  }

    axIpv6TotalQueuedFragmentsExceed OBJECT-TYPE	
	SYNTAX			CounterBasedGauge64
	MAX-ACCESS		read-only
	STATUS			current
	DESCRIPTION		
		"The count of l3 ipv6 total queued fragments exceed."
	DEFVAL			{ 0 }
	::=  {  axIpv6FragmentStats  31  }

    axIpv6FragmentQueueFailure OBJECT-TYPE	
	SYNTAX			CounterBasedGauge64
	MAX-ACCESS		read-only
	STATUS			current
	DESCRIPTION		
		"The count of l3 ipv6 fragment queue failure."
	DEFVAL			{ 0 }
	::=  {  axIpv6FragmentStats  32  }

    axIpv6FragmentReassemblySuccess OBJECT-TYPE	
	SYNTAX			CounterBasedGauge64
	MAX-ACCESS		read-only
	STATUS			current
	DESCRIPTION		
		"The count of l3 ipv6 fragment reassembly success."
	DEFVAL			{ 0 }
	::=  {  axIpv6FragmentStats  33  }

    axIpv6FragmentMaxDataLengthExceed OBJECT-TYPE	
	SYNTAX			CounterBasedGauge64
	MAX-ACCESS		read-only
	STATUS			current
	DESCRIPTION		
		"The count of l3 ipv6 fragment max data length exceed."
	DEFVAL			{ 0 }
	::=  {  axIpv6FragmentStats  34  }

    axIpv6FragmentReassemblyFailure OBJECT-TYPE	
	SYNTAX			CounterBasedGauge64
	MAX-ACCESS		read-only
	STATUS			current
	DESCRIPTION		
		"The count of l3 ipv6 fragment reassembly failure."
	DEFVAL			{ 0 }
	::=  {  axIpv6FragmentStats  35  }

    axIpv6MtuExceedPolicyDrop OBJECT-TYPE	
	SYNTAX			CounterBasedGauge64
	MAX-ACCESS		read-only
	STATUS			current
	DESCRIPTION		
		"The count of l3 ipv6 MTU exceed policy drop."
	DEFVAL			{ 0 }
	::=  {  axIpv6FragmentStats  36  }

    axIpv6FragmentProcessingDrop OBJECT-TYPE	
	SYNTAX			CounterBasedGauge64
	MAX-ACCESS		read-only
	STATUS			current
	DESCRIPTION		
		"The count of l3 ipv6 fragment processing drop."
	DEFVAL			{ 0 }
	::=  {  axIpv6FragmentStats  37  }

    axIpv6TooManyPacketsPerReassemblyDrop OBJECT-TYPE	
	SYNTAX			CounterBasedGauge64
	MAX-ACCESS		read-only
	STATUS			current
	DESCRIPTION		
		"The count of l3 ipv6 fragment too many packets per reassembly drop."
	DEFVAL			{ 0 }
	::=  {  axIpv6FragmentStats  38  }

    axIpv6SessionMaxPacketsExceed OBJECT-TYPE	
	SYNTAX			CounterBasedGauge64
	MAX-ACCESS		read-only
	STATUS			current
	DESCRIPTION		
		"The count of l3 ipv6 fragment Session max packets exceed."
	DEFVAL			{ 0 }
	::=  {  axIpv6FragmentStats  39  }


--==================================================================
-- axIpv4InIpv6FragmentStats
--==================================================================

    axIpv4InIpv6FragmentStats        OBJECT IDENTIFIER ::= { axFragmentStats 3 }

    axIpv4InIpv6SessionInsert	OBJECT-TYPE	
	SYNTAX			CounterBasedGauge64
	MAX-ACCESS		read-only
	STATUS			current
	DESCRIPTION		
		"The count of l3 ipv4 in ipv6 session inserts."
	DEFVAL			{ 0 }
	::=  {  axIpv4InIpv6FragmentStats  1  }

    axIpv4InIpv6SessionExpired	OBJECT-TYPE	
	SYNTAX			CounterBasedGauge64
	MAX-ACCESS		read-only
	STATUS			current
	DESCRIPTION		
		"The count of l3 ipv4 in ipv6 session expired."
	DEFVAL			{ 0 }
	::=  {  axIpv4InIpv6FragmentStats  2  }

    axIpv4InIpv6IcmpReceived	OBJECT-TYPE	
	SYNTAX			CounterBasedGauge64
	MAX-ACCESS		read-only
	STATUS			current
	DESCRIPTION		
		"The count of l3 ipv4 in ipv6 ICMP Received."
	DEFVAL			{ 0 }
	::=  {  axIpv4InIpv6FragmentStats  3  }
    
    axIpv4InIpv6Icmpv6Received	OBJECT-TYPE	
	SYNTAX			CounterBasedGauge64
	MAX-ACCESS		read-only
	STATUS			current
	DESCRIPTION		
		"The count of l3 ipv4 in ipv6 ICMPv6 Received."
	DEFVAL			{ 0 }
	::=  {  axIpv4InIpv6FragmentStats  4  }

    axIpv4InIpv6UdpReceived	OBJECT-TYPE	
	SYNTAX			CounterBasedGauge64
	MAX-ACCESS		read-only
	STATUS			current
	DESCRIPTION		
		"The count of l3 ipv4 in ipv6 UDP Received."
	DEFVAL			{ 0 }
	::=  {  axIpv4InIpv6FragmentStats  5  }

    axIpv4InIpv6TcpReceived	OBJECT-TYPE	
	SYNTAX			CounterBasedGauge64
	MAX-ACCESS		read-only
	STATUS			current
	DESCRIPTION		
		"The count of l3 ipv4 in ipv6 Tcp Received."
	DEFVAL			{ 0 }
	::=  {  axIpv4InIpv6FragmentStats  6  }

    axIpv4InIpv6IpInIpReceived	OBJECT-TYPE	
	SYNTAX			CounterBasedGauge64
	MAX-ACCESS		read-only
	STATUS			current
	DESCRIPTION		
		"The count of l3 ipv4 in ipv6 Ip-In-Ip Received."
	DEFVAL			{ 0 }
	::=  {  axIpv4InIpv6FragmentStats  7  }

    axIpv4InIpv6Ipv6InIpReceived	OBJECT-TYPE	
	SYNTAX			CounterBasedGauge64
	MAX-ACCESS		read-only
	STATUS			current
	DESCRIPTION		
		"The count of l3 ipv4 in ipv6 Ipv6-In-Ip Received."
	DEFVAL			{ 0 }
	::=  {  axIpv4InIpv6FragmentStats  8  }

    axIpv4InIpv6OtherReceived	OBJECT-TYPE	
	SYNTAX			CounterBasedGauge64
	MAX-ACCESS		read-only
	STATUS			current
	DESCRIPTION		
		"The count of l3 ipv4 in ipv6 other Received."
	DEFVAL			{ 0 }
	::=  {  axIpv4InIpv6FragmentStats  9  }

    axIpv4InIpv6IcmpDropped	OBJECT-TYPE	
	SYNTAX			CounterBasedGauge64
	MAX-ACCESS		read-only
	STATUS			current
	DESCRIPTION		
		"The count of l3 ipv4 in ipv6 ICMP dropped."
	DEFVAL			{ 0 }
	::=  {  axIpv4InIpv6FragmentStats  10  }

    axIpv4InIpv6Icmpv6Dropped	OBJECT-TYPE	
	SYNTAX			CounterBasedGauge64
	MAX-ACCESS		read-only
	STATUS			current
	DESCRIPTION		
		"The count of l3 ipv4 in ipv6 ICMPv6 dropped."
	DEFVAL			{ 0 }
	::=  {  axIpv4InIpv6FragmentStats  11  }

    axIpv4InIpv6UdpDropped	OBJECT-TYPE	
	SYNTAX			CounterBasedGauge64
	MAX-ACCESS		read-only
	STATUS			current
	DESCRIPTION		
		"The count of l3 ipv4 in ipv6 UDP dropped."
	DEFVAL			{ 0 }
	::=  {  axIpv4InIpv6FragmentStats  12  }

    axIpv4InIpv6TcpDropped	OBJECT-TYPE	
	SYNTAX			CounterBasedGauge64
	MAX-ACCESS		read-only
	STATUS			current
	DESCRIPTION		
		"The count of l3 ipv4 in ipv6 TCP dropped."
	DEFVAL			{ 0 }
	::=  {  axIpv4InIpv6FragmentStats  13  }

    axIpv4InIpv6IpInIpDropped	OBJECT-TYPE	
	SYNTAX			CounterBasedGauge64
	MAX-ACCESS		read-only
	STATUS			current
	DESCRIPTION		
		"The count of l3 ipv4 in ipv6 Ip-In-Ip dropped."
	DEFVAL			{ 0 }
	::=  {  axIpv4InIpv6FragmentStats  14  }

    axIpv4InIpv6Ipv6InIpDropped	OBJECT-TYPE	
	SYNTAX			CounterBasedGauge64
	MAX-ACCESS		read-only
	STATUS			current
	DESCRIPTION		
		"The count of l3 ipv4 in ipv6 Ipv6-In-Ip dropped."
	DEFVAL			{ 0 }
	::=  {  axIpv4InIpv6FragmentStats  15  }

    axIpv4InIpv6OtherDropped	OBJECT-TYPE	
	SYNTAX			CounterBasedGauge64
	MAX-ACCESS		read-only
	STATUS			current
	DESCRIPTION		
		"The count of l3 ipv4 in ipv6 Other dropped."
	DEFVAL			{ 0 }
	::=  {  axIpv4InIpv6FragmentStats  16  }

    axIpv4InIpv6OverlappingFragmentDropped	OBJECT-TYPE	
	SYNTAX			CounterBasedGauge64
	MAX-ACCESS		read-only
	STATUS			current
	DESCRIPTION		
		"The count of l3 ipv4 in ipv6 overlapping fragment dropped."
	DEFVAL			{ 0 }
	::=  {  axIpv4InIpv6FragmentStats  17  }

    axIpv4InIpv6BadIpLength	OBJECT-TYPE	
	SYNTAX			CounterBasedGauge64
	MAX-ACCESS		read-only
	STATUS			current
	DESCRIPTION		
		"The count of l3 ipv4 in ipv6 bad ip length."
	DEFVAL			{ 0 }
	::=  {  axIpv4InIpv6FragmentStats  18  }

    axIpv4InIpv6FragmentTooSmallDrop	OBJECT-TYPE	
	SYNTAX			CounterBasedGauge64
	MAX-ACCESS		read-only
	STATUS			current
	DESCRIPTION		
		"The count of l3 ipv4 in ipv6 fragment too small drop."
	DEFVAL			{ 0 }
	::=  {  axIpv4InIpv6FragmentStats  19  }

    axIpv4InIpv6FirstTcpFragmentTooSmallDrop	OBJECT-TYPE	
	SYNTAX			CounterBasedGauge64
	MAX-ACCESS		read-only
	STATUS			current
	DESCRIPTION		
		"The count of l3 ipv4 in ipv6 first TCP fragment too small drop."
	DEFVAL			{ 0 }
	::=  {  axIpv4InIpv6FragmentStats  20  }

    axIpv4InIpv6FirstL4FragmentTooSmallDrop	OBJECT-TYPE	
	SYNTAX			CounterBasedGauge64
	MAX-ACCESS		read-only
	STATUS			current
	DESCRIPTION		
		"The count of l3 ipv4 in ipv6 first L4 fragment too small drop."
	DEFVAL			{ 0 }
	::=  {  axIpv4InIpv6FragmentStats  21  }

    axIpv4InIpv6TotalSessionsExceedDrop	OBJECT-TYPE	
	SYNTAX			CounterBasedGauge64
	MAX-ACCESS		read-only
	STATUS			current
	DESCRIPTION		
		"The count of l3 ipv4 in ipv6 total sessions exceed drop."
	DEFVAL			{ 0 }
	::=  {  axIpv4InIpv6FragmentStats  22  }

    axIpv4InIpv6OutOfSessionMemory OBJECT-TYPE	
	SYNTAX			CounterBasedGauge64
	MAX-ACCESS		read-only
	STATUS			current
	DESCRIPTION		
		"The count of l3 ipv4 in ipv6 out of session memory."
	DEFVAL			{ 0 }
	::=  {  axIpv4InIpv6FragmentStats  23  }

    axIpv4InIpv6FragmentationFastAgingSet OBJECT-TYPE	
	SYNTAX			CounterBasedGauge64
	MAX-ACCESS		read-only
	STATUS			current
	DESCRIPTION		
		"The count of l3 ipv4 in ipv6 fragmentation fast aging set."
	DEFVAL			{ 0 }
	::=  {  axIpv4InIpv6FragmentStats  24  }

    axIpv4InIpv6FragmentationFastAgingUnset OBJECT-TYPE	
	SYNTAX			CounterBasedGauge64
	MAX-ACCESS		read-only
	STATUS			current
	DESCRIPTION		
		"The count of l3 ipv4 in ipv6 fragmentation fast aging unset."
	DEFVAL			{ 0 }
	::=  {  axIpv4InIpv6FragmentStats  25  }

    axIpv4InIpv6FragmentQueueSuccess OBJECT-TYPE	
	SYNTAX			CounterBasedGauge64
	MAX-ACCESS		read-only
	STATUS			current
	DESCRIPTION		
		"The count of l3 ipv4 in ipv6 fragment queue success."
	DEFVAL			{ 0 }
	::=  {  axIpv4InIpv6FragmentStats  26  }

    axIpv4InIpv6PayloadLengthUnaligned OBJECT-TYPE	
	SYNTAX			CounterBasedGauge64
	MAX-ACCESS		read-only
	STATUS			current
	DESCRIPTION		
		"The count of l3 ipv4 in ipv6 payload length unaligned."
	DEFVAL			{ 0 }
	::=  {  axIpv4InIpv6FragmentStats  27  }

    axIpv4InIpv6PayloadLengthOutOfBounds OBJECT-TYPE	
	SYNTAX			CounterBasedGauge64
	MAX-ACCESS		read-only
	STATUS			current
	DESCRIPTION		
		"The count of l3 ipv4 in ipv6 payload length out of bounds."
	DEFVAL			{ 0 }
	::=  {  axIpv4InIpv6FragmentStats  28  }

    axIpv4InIpv6DuplicateFirstFragment OBJECT-TYPE	
	SYNTAX			CounterBasedGauge64
	MAX-ACCESS		read-only
	STATUS			current
	DESCRIPTION		
		"The count of l3 ipv4 in ipv6 duplicate first fragment."
	DEFVAL			{ 0 }
	::=  {  axIpv4InIpv6FragmentStats  29  }

    axIpv4InIpv6DuplicateLastFragment OBJECT-TYPE	
	SYNTAX			CounterBasedGauge64
	MAX-ACCESS		read-only
	STATUS			current
	DESCRIPTION		
		"The count of l3 ipv4 in ipv6 duplicate last fragment."
	DEFVAL			{ 0 }
	::=  {  axIpv4InIpv6FragmentStats  30  }

    axIpv4InIpv6TotalQueuedFragmentsExceed OBJECT-TYPE	
	SYNTAX			CounterBasedGauge64
	MAX-ACCESS		read-only
	STATUS			current
	DESCRIPTION		
		"The count of l3 ipv4 in ipv6 total queued fragments exceed."
	DEFVAL			{ 0 }
	::=  {  axIpv4InIpv6FragmentStats  31  }

    axIpv4InIpv6FragmentQueueFailure OBJECT-TYPE	
	SYNTAX			CounterBasedGauge64
	MAX-ACCESS		read-only
	STATUS			current
	DESCRIPTION		
		"The count of l3 ipv4 in ipv6 fragment queue failure."
	DEFVAL			{ 0 }
	::=  {  axIpv4InIpv6FragmentStats  32  }

    axIpv4InIpv6FragmentReassemblySuccess OBJECT-TYPE	
	SYNTAX			CounterBasedGauge64
	MAX-ACCESS		read-only
	STATUS			current
	DESCRIPTION		
		"The count of l3 ipv4 in ipv6 fragment reassembly success."
	DEFVAL			{ 0 }
	::=  {  axIpv4InIpv6FragmentStats  33  }

    axIpv4InIpv6FragmentMaxDataLengthExceed OBJECT-TYPE	
	SYNTAX			CounterBasedGauge64
	MAX-ACCESS		read-only
	STATUS			current
	DESCRIPTION		
		"The count of l3 ipv4 in ipv6 fragment max data length exceed."
	DEFVAL			{ 0 }
	::=  {  axIpv4InIpv6FragmentStats  34  }

    axIpv4InIpv6FragmentReassemblyFailure OBJECT-TYPE	
	SYNTAX			CounterBasedGauge64
	MAX-ACCESS		read-only
	STATUS			current
	DESCRIPTION		
		"The count of l3 ipv4 in ipv6 fragment reassembly failure."
	DEFVAL			{ 0 }
	::=  {  axIpv4InIpv6FragmentStats  35  }

    axIpv4InIpv6MtuExceedPolicyDrop OBJECT-TYPE	
	SYNTAX			CounterBasedGauge64
	MAX-ACCESS		read-only
	STATUS			current
	DESCRIPTION		
		"The count of l3 ipv4 in ipv6 MTU exceed policy drop."
	DEFVAL			{ 0 }
	::=  {  axIpv4InIpv6FragmentStats  36  }

    axIpv4InIpv6FragmentProcessingDrop OBJECT-TYPE	
	SYNTAX			CounterBasedGauge64
	MAX-ACCESS		read-only
	STATUS			current
	DESCRIPTION		
		"The count of l3 ipv4 in ipv6 fragment processing drop."
	DEFVAL			{ 0 }
	::=  {  axIpv4InIpv6FragmentStats  37  }

    axIpv4InIpv6TooManyPacketsPerReassemblyDrop OBJECT-TYPE	
	SYNTAX			CounterBasedGauge64
	MAX-ACCESS		read-only
	STATUS			current
	DESCRIPTION		
		"The count of l3 ipv4 in ipv6 fragment too many packets per reassembly drop."
	DEFVAL			{ 0 }
	::=  {  axIpv4InIpv6FragmentStats  38  }

    axIpv4InIpv6SessionMaxPacketsExceed OBJECT-TYPE	
	SYNTAX			CounterBasedGauge64
	MAX-ACCESS		read-only
	STATUS			current
	DESCRIPTION		
		"The count of l3 ipv4 in ipv6 fragment Session max packets exceed."
	DEFVAL			{ 0 }
	::=  {  axIpv4InIpv6FragmentStats  39  }


--==================================================================
-- axIpv6InIpv4FragmentStats
--==================================================================

    axIpv6InIpv4FragmentStats        OBJECT IDENTIFIER ::= { axFragmentStats 4 }

    axIpv6InIpv4SessionInsert	OBJECT-TYPE	
	SYNTAX			CounterBasedGauge64
	MAX-ACCESS		read-only
	STATUS			current
	DESCRIPTION		
		"The count of l3 ipv6 in ipv4 session inserts."
	DEFVAL			{ 0 }
	::=  {  axIpv6InIpv4FragmentStats  1  }

    axIpv6InIpv4SessionExpired	OBJECT-TYPE	
	SYNTAX			CounterBasedGauge64
	MAX-ACCESS		read-only
	STATUS			current
	DESCRIPTION		
		"The count of l3 ipv6 in ipv4 session expired."
	DEFVAL			{ 0 }
	::=  {  axIpv6InIpv4FragmentStats  2  }

    axIpv6InIpv4IcmpReceived	OBJECT-TYPE	
	SYNTAX			CounterBasedGauge64
	MAX-ACCESS		read-only
	STATUS			current
	DESCRIPTION		
		"The count of l3 ipv6 in ipv4 ICMP Received."
	DEFVAL			{ 0 }
	::=  {  axIpv6InIpv4FragmentStats  3  }
    
    axIpv6InIpv4Icmpv6Received	OBJECT-TYPE	
	SYNTAX			CounterBasedGauge64
	MAX-ACCESS		read-only
	STATUS			current
	DESCRIPTION		
		"The count of l3 ipv6 in ipv4 ICMPv6 Received."
	DEFVAL			{ 0 }
	::=  {  axIpv6InIpv4FragmentStats  4  }

    axIpv6InIpv4UdpReceived	OBJECT-TYPE	
	SYNTAX			CounterBasedGauge64
	MAX-ACCESS		read-only
	STATUS			current
	DESCRIPTION		
		"The count of l3 ipv6 in ipv4 UDP Received."
	DEFVAL			{ 0 }
	::=  {  axIpv6InIpv4FragmentStats  5  }

    axIpv6InIpv4TcpReceived	OBJECT-TYPE	
	SYNTAX			CounterBasedGauge64
	MAX-ACCESS		read-only
	STATUS			current
	DESCRIPTION		
		"The count of l3 ipv6 in ipv4 Tcp Received."
	DEFVAL			{ 0 }
	::=  {  axIpv6InIpv4FragmentStats  6  }

    axIpv6InIpv4IpInIpReceived	OBJECT-TYPE	
	SYNTAX			CounterBasedGauge64
	MAX-ACCESS		read-only
	STATUS			current
	DESCRIPTION		
		"The count of l3 ipv6 in ipv4 Ip-In-Ip Received."
	DEFVAL			{ 0 }
	::=  {  axIpv6InIpv4FragmentStats  7  }

    axIpv6InIpv4Ipv6InIpReceived	OBJECT-TYPE	
	SYNTAX			CounterBasedGauge64
	MAX-ACCESS		read-only
	STATUS			current
	DESCRIPTION		
		"The count of l3 ipv6 in ipv4 Ipv6-In-Ip Received."
	DEFVAL			{ 0 }
	::=  {  axIpv6InIpv4FragmentStats  8  }

    axIpv6InIpv4OtherReceived	OBJECT-TYPE	
	SYNTAX			CounterBasedGauge64
	MAX-ACCESS		read-only
	STATUS			current
	DESCRIPTION		
		"The count of l3 ipv6 in ipv4 other Received."
	DEFVAL			{ 0 }
	::=  {  axIpv6InIpv4FragmentStats  9  }

    axIpv6InIpv4IcmpDropped	OBJECT-TYPE	
	SYNTAX			CounterBasedGauge64
	MAX-ACCESS		read-only
	STATUS			current
	DESCRIPTION		
		"The count of l3 ipv6 in ipv4 ICMP dropped."
	DEFVAL			{ 0 }
	::=  {  axIpv6InIpv4FragmentStats  10  }

    axIpv6InIpv4Icmpv6Dropped	OBJECT-TYPE	
	SYNTAX			CounterBasedGauge64
	MAX-ACCESS		read-only
	STATUS			current
	DESCRIPTION		
		"The count of l3 ipv6 in ipv4 ICMPv6 dropped."
	DEFVAL			{ 0 }
	::=  {  axIpv6InIpv4FragmentStats  11  }

    axIpv6InIpv4UdpDropped	OBJECT-TYPE	
	SYNTAX			CounterBasedGauge64
	MAX-ACCESS		read-only
	STATUS			current
	DESCRIPTION		
		"The count of l3 ipv6 in ipv4 UDP dropped."
	DEFVAL			{ 0 }
	::=  {  axIpv6InIpv4FragmentStats  12  }

    axIpv6InIpv4TcpDropped	OBJECT-TYPE	
	SYNTAX			CounterBasedGauge64
	MAX-ACCESS		read-only
	STATUS			current
	DESCRIPTION		
		"The count of l3 ipv6 in ipv4 TCP dropped."
	DEFVAL			{ 0 }
	::=  {  axIpv6InIpv4FragmentStats  13  }

    axIpv6InIpv4IpInIpDropped	OBJECT-TYPE	
	SYNTAX			CounterBasedGauge64
	MAX-ACCESS		read-only
	STATUS			current
	DESCRIPTION		
		"The count of l3 ipv6 in ipv4 Ip-In-Ip dropped."
	DEFVAL			{ 0 }
	::=  {  axIpv6InIpv4FragmentStats  14  }

    axIpv6InIpv4Ipv6InIpDropped	OBJECT-TYPE	
	SYNTAX			CounterBasedGauge64
	MAX-ACCESS		read-only
	STATUS			current
	DESCRIPTION		
		"The count of l3 ipv6 in ipv4 Ipv6-In-Ip dropped."
	DEFVAL			{ 0 }
	::=  {  axIpv6InIpv4FragmentStats  15  }

    axIpv6InIpv4OtherDropped	OBJECT-TYPE	
	SYNTAX			CounterBasedGauge64
	MAX-ACCESS		read-only
	STATUS			current
	DESCRIPTION		
		"The count of l3 ipv6 in ipv4 Other dropped."
	DEFVAL			{ 0 }
	::=  {  axIpv6InIpv4FragmentStats  16  }

    axIpv6InIpv4OverlappingFragmentDropped	OBJECT-TYPE	
	SYNTAX			CounterBasedGauge64
	MAX-ACCESS		read-only
	STATUS			current
	DESCRIPTION		
		"The count of l3 ipv6 in ipv4 overlapping fragment dropped."
	DEFVAL			{ 0 }
	::=  {  axIpv6InIpv4FragmentStats  17  }

    axIpv6InIpv4BadIpLength	OBJECT-TYPE	
	SYNTAX			CounterBasedGauge64
	MAX-ACCESS		read-only
	STATUS			current
	DESCRIPTION		
		"The count of l3 ipv6 in ipv4 bad ip length."
	DEFVAL			{ 0 }
	::=  {  axIpv6InIpv4FragmentStats  18  }

    axIpv6InIpv4FragmentTooSmallDrop	OBJECT-TYPE	
	SYNTAX			CounterBasedGauge64
	MAX-ACCESS		read-only
	STATUS			current
	DESCRIPTION		
		"The count of l3 ipv6 in ipv4 fragment too small drop."
	DEFVAL			{ 0 }
	::=  {  axIpv6InIpv4FragmentStats  19  }

    axIpv6InIpv4FirstTcpFragmentTooSmallDrop	OBJECT-TYPE	
	SYNTAX			CounterBasedGauge64
	MAX-ACCESS		read-only
	STATUS			current
	DESCRIPTION		
		"The count of l3 ipv6 in ipv4 first TCP fragment too small drop."
	DEFVAL			{ 0 }
	::=  {  axIpv6InIpv4FragmentStats  20  }

    axIpv6InIpv4FirstL4FragmentTooSmallDrop	OBJECT-TYPE	
	SYNTAX			CounterBasedGauge64
	MAX-ACCESS		read-only
	STATUS			current
	DESCRIPTION		
		"The count of l3 ipv6 in ipv4 first L4 fragment too small drop."
	DEFVAL			{ 0 }
	::=  {  axIpv6InIpv4FragmentStats  21  }

    axIpv6InIpv4TotalSessionsExceedDrop	OBJECT-TYPE	
	SYNTAX			CounterBasedGauge64
	MAX-ACCESS		read-only
	STATUS			current
	DESCRIPTION		
		"The count of l3 ipv6 in ipv4 total sessions exceed drop."
	DEFVAL			{ 0 }
	::=  {  axIpv6InIpv4FragmentStats  22  }

    axIpv6InIpv4OutOfSessionMemory OBJECT-TYPE	
	SYNTAX			CounterBasedGauge64
	MAX-ACCESS		read-only
	STATUS			current
	DESCRIPTION		
		"The count of l3 ipv6 in ipv4 out of session memory."
	DEFVAL			{ 0 }
	::=  {  axIpv6InIpv4FragmentStats  23  }

    axIpv6InIpv4FragmentationFastAgingSet OBJECT-TYPE	
	SYNTAX			CounterBasedGauge64
	MAX-ACCESS		read-only
	STATUS			current
	DESCRIPTION		
		"The count of l3 ipv6 in ipv4 fragmentation fast aging set."
	DEFVAL			{ 0 }
	::=  {  axIpv6InIpv4FragmentStats  24  }

    axIpv6InIpv4FragmentationFastAgingUnset OBJECT-TYPE	
	SYNTAX			CounterBasedGauge64
	MAX-ACCESS		read-only
	STATUS			current
	DESCRIPTION		
		"The count of l3 ipv6 in ipv4 fragmentation fast aging unset."
	DEFVAL			{ 0 }
	::=  {  axIpv6InIpv4FragmentStats  25  }

    axIpv6InIpv4FragmentQueueSuccess OBJECT-TYPE	
	SYNTAX			CounterBasedGauge64
	MAX-ACCESS		read-only
	STATUS			current
	DESCRIPTION		
		"The count of l3 ipv6 in ipv4 fragment queue success."
	DEFVAL			{ 0 }
	::=  {  axIpv6InIpv4FragmentStats  26  }

    axIpv6InIpv4PayloadLengthUnaligned OBJECT-TYPE	
	SYNTAX			CounterBasedGauge64
	MAX-ACCESS		read-only
	STATUS			current
	DESCRIPTION		
		"The count of l3 ipv6 in ipv4 payload length unaligned."
	DEFVAL			{ 0 }
	::=  {  axIpv6InIpv4FragmentStats  27  }

    axIpv6InIpv4PayloadLengthOutOfBounds OBJECT-TYPE	
	SYNTAX			CounterBasedGauge64
	MAX-ACCESS		read-only
	STATUS			current
	DESCRIPTION		
		"The count of l3 ipv6 in ipv4 payload length out of bounds."
	DEFVAL			{ 0 }
	::=  {  axIpv6InIpv4FragmentStats  28  }

    axIpv6InIpv4DuplicateFirstFragment OBJECT-TYPE	
	SYNTAX			CounterBasedGauge64
	MAX-ACCESS		read-only
	STATUS			current
	DESCRIPTION		
		"The count of l3 ipv6 in ipv4 duplicate first fragment."
	DEFVAL			{ 0 }
	::=  {  axIpv6InIpv4FragmentStats  29  }

    axIpv6InIpv4DuplicateLastFragment OBJECT-TYPE	
	SYNTAX			CounterBasedGauge64
	MAX-ACCESS		read-only
	STATUS			current
	DESCRIPTION		
		"The count of l3 ipv6 in ipv4 duplicate last fragment."
	DEFVAL			{ 0 }
	::=  {  axIpv6InIpv4FragmentStats  30  }

    axIpv6InIpv4TotalQueuedFragmentsExceed OBJECT-TYPE	
	SYNTAX			CounterBasedGauge64
	MAX-ACCESS		read-only
	STATUS			current
	DESCRIPTION		
		"The count of l3 ipv6 in ipv4 total queued fragments exceed."
	DEFVAL			{ 0 }
	::=  {  axIpv6InIpv4FragmentStats  31  }

    axIpv6InIpv4FragmentQueueFailure OBJECT-TYPE	
	SYNTAX			CounterBasedGauge64
	MAX-ACCESS		read-only
	STATUS			current
	DESCRIPTION		
		"The count of l3 ipv6 in ipv4 fragment queue failure."
	DEFVAL			{ 0 }
	::=  {  axIpv6InIpv4FragmentStats  32  }

    axIpv6InIpv4FragmentReassemblySuccess OBJECT-TYPE	
	SYNTAX			CounterBasedGauge64
	MAX-ACCESS		read-only
	STATUS			current
	DESCRIPTION		
		"The count of l3 ipv6 in ipv4 fragment reassembly success."
	DEFVAL			{ 0 }
	::=  {  axIpv6InIpv4FragmentStats  33  }

    axIpv6InIpv4FragmentMaxDataLengthExceed OBJECT-TYPE	
	SYNTAX			CounterBasedGauge64
	MAX-ACCESS		read-only
	STATUS			current
	DESCRIPTION		
		"The count of l3 ipv6 in ipv4 fragment max data length exceed."
	DEFVAL			{ 0 }
	::=  {  axIpv6InIpv4FragmentStats  34  }

    axIpv6InIpv4FragmentReassemblyFailure OBJECT-TYPE	
	SYNTAX			CounterBasedGauge64
	MAX-ACCESS		read-only
	STATUS			current
	DESCRIPTION		
		"The count of l3 ipv6 in ipv4 fragment reassembly failure."
	DEFVAL			{ 0 }
	::=  {  axIpv6InIpv4FragmentStats  35  }

    axIpv6InIpv4MtuExceedPolicyDrop OBJECT-TYPE	
	SYNTAX			CounterBasedGauge64
	MAX-ACCESS		read-only
	STATUS			current
	DESCRIPTION		
		"The count of l3 ipv6 in ipv4 MTU exceed policy drop."
	DEFVAL			{ 0 }
	::=  {  axIpv6InIpv4FragmentStats  36  }

    axIpv6InIpv4FragmentProcessingDrop OBJECT-TYPE	
	SYNTAX			CounterBasedGauge64
	MAX-ACCESS		read-only
	STATUS			current
	DESCRIPTION		
		"The count of l3 ipv6 in ipv4 fragment processing drop."
	DEFVAL			{ 0 }
	::=  {  axIpv6InIpv4FragmentStats  37  }

    axIpv6InIpv4TooManyPacketsPerReassemblyDrop OBJECT-TYPE	
	SYNTAX			CounterBasedGauge64
	MAX-ACCESS		read-only
	STATUS			current
	DESCRIPTION		
		"The count of l3 ipv6 in ipv4 fragment too many packets per reassembly drop."
	DEFVAL			{ 0 }
	::=  {  axIpv6InIpv4FragmentStats  38  }

    axIpv6InIpv4SessionMaxPacketsExceed OBJECT-TYPE	
	SYNTAX			CounterBasedGauge64
	MAX-ACCESS		read-only
	STATUS			current
	DESCRIPTION		
		"The count of l3 ipv6 in ipv4 fragment Session max packets exceed."
	DEFVAL			{ 0 }
	::=  {  axIpv6InIpv4FragmentStats  39  }

--=================================================================================

    axFixedNatPortMappingPortTable OBJECT-TYPE
	SYNTAX SEQUENCE OF AxFixedNatPortMappingPortEntry
	MAX-ACCESS not-accessible
	STATUS current
	DESCRIPTION
		"A table has information of the servers."
	::= { axFixedNatMapping 1 } 

    axFixedNatPortMappingPortEntry OBJECT-TYPE
	SYNTAX  AxFixedNatPortMappingPortEntry
	MAX-ACCESS not-accessible
	STATUS current
	DESCRIPTION
		"Columns in the axFixedNatPortMappingPortTable Table"
	INDEX {
		axFixedNatPortMappingPortNatIpAddress, axFixedNatPortMappingPortInsideUser
	}
	::= { axFixedNatPortMappingPortTable 1 } 

    AxFixedNatPortMappingPortEntry ::= 
	SEQUENCE {
        	axFixedNatPortMappingPortNatIpAddress	             DisplayString,
        	axFixedNatPortMappingPortInsideUser                  DisplayString,
		    axFixedNatPortMappingPortInsideUserIpType            INTEGER,
        	axFixedNatPortMappingPortTcpBeginPort                INTEGER,
        	axFixedNatPortMappingPortTcpEndPort                  INTEGER,
        	axFixedNatPortMappingPortUdpBeginPort                INTEGER,
        	axFixedNatPortMappingPortUdpEndPort                  INTEGER,
        	axFixedNatPortMappingPortIcmpBeginPort               INTEGER,
        	axFixedNatPortMappingPortIcmpEndPort                 INTEGER
	}

    axFixedNatPortMappingPortNatIpAddress OBJECT-TYPE 
	SYNTAX DisplayString
	MAX-ACCESS read-only
	STATUS current
	DESCRIPTION
		"The nat ip address of the fixed nat."
	::= { axFixedNatPortMappingPortEntry 1 } 

    axFixedNatPortMappingPortInsideUser OBJECT-TYPE 
	SYNTAX DisplayString
	MAX-ACCESS read-only
	STATUS current
	DESCRIPTION
		"The inside user address of the fixed nat."
	::= { axFixedNatPortMappingPortEntry 2 } 

    axFixedNatPortMappingPortInsideUserIpType OBJECT-TYPE 
	SYNTAX INTEGER {
		ipv4(0),
		ipv6(1),
        dynamic(2)
    }
	MAX-ACCESS read-only
	STATUS current
	DESCRIPTION
		"The inside user address type of the fixed nat."
	::= { axFixedNatPortMappingPortEntry 3 } 

    axFixedNatPortMappingPortTcpBeginPort OBJECT-TYPE 
	SYNTAX INTEGER
	MAX-ACCESS read-only
	STATUS current
	DESCRIPTION
		"The TCP begin port of the fixed nat."
	::= { axFixedNatPortMappingPortEntry 4 } 

    axFixedNatPortMappingPortTcpEndPort OBJECT-TYPE 
	SYNTAX INTEGER
	MAX-ACCESS read-only
	STATUS current
	DESCRIPTION
		"The TCP end port of the fixed nat."
	::= { axFixedNatPortMappingPortEntry 5 } 

    axFixedNatPortMappingPortUdpBeginPort OBJECT-TYPE 
	SYNTAX INTEGER
	MAX-ACCESS read-only
	STATUS current
	DESCRIPTION
		"The UDP end port of the fixed nat."
	::= { axFixedNatPortMappingPortEntry 6 } 

    axFixedNatPortMappingPortUdpEndPort OBJECT-TYPE 
	SYNTAX INTEGER
	MAX-ACCESS read-only
	STATUS current
	DESCRIPTION
		"The UDP end port of the fixed nat."
	::= { axFixedNatPortMappingPortEntry 7 } 

    axFixedNatPortMappingPortIcmpBeginPort OBJECT-TYPE 
	SYNTAX INTEGER
	MAX-ACCESS read-only
	STATUS current
	DESCRIPTION
		"The ICMP end port of the fixed nat."
	::= { axFixedNatPortMappingPortEntry 8 } 

    axFixedNatPortMappingPortIcmpEndPort OBJECT-TYPE 
	SYNTAX INTEGER
	MAX-ACCESS read-only
	STATUS current
	DESCRIPTION
		"The ICMP end port of the fixed nat."
	::= { axFixedNatPortMappingPortEntry 9 } 

--====================axFixedNatFullConeSess=======================================

    axFixedNatFullConeSessDsliteTable OBJECT-TYPE
	SYNTAX SEQUENCE OF AxFixedNatFullConeSessDsliteEntry
	MAX-ACCESS not-accessible
	STATUS current
	DESCRIPTION
		"A table has information of fixed nat full-cone-session ds-lite."
	::= { axFixedNatFullConeSess 1 } 

    axFixedNatFullConeSessDsliteEntry OBJECT-TYPE
	SYNTAX  AxFixedNatFullConeSessDsliteEntry
	MAX-ACCESS not-accessible
	STATUS current
	DESCRIPTION
		"Columns in the axFixedNatFullConeSessDsliteTable Table"
	INDEX {
		axFixedNatFullConeSessDsliteNatIpAddress, axFixedNatFullConeSessDsliteInsideUser,
		axFixedNatFullConeSessDsliteProtType
	}
	::= { axFixedNatFullConeSessDsliteTable 1 } 

    AxFixedNatFullConeSessDsliteEntry ::= 
	SEQUENCE {
        	axFixedNatFullConeSessDsliteNatIpAddress	        DisplayString,
        	axFixedNatFullConeSessDsliteInsideUser              DisplayString,
            axFixedNatFullConeSessDsliteProtType                INTEGER,
		    axFixedNatFullConeSessDsliteEIM                     INTEGER,
        	axFixedNatFullConeSessDsliteEIF                     INTEGER,
        	axFixedNatFullConeSessDsliteCPU                     INTEGER,
        	axFixedNatFullConeSessDsliteAge                     INTEGER,
        	axFixedNatFullConeSessDslitePcpFlags                INTEGER
	}

    axFixedNatFullConeSessDsliteNatIpAddress OBJECT-TYPE 
	SYNTAX DisplayString
	MAX-ACCESS read-only
	STATUS current
	DESCRIPTION
		"The nat ip address and port of the fixed nat."
	::= { axFixedNatFullConeSessDsliteEntry 1 } 

    axFixedNatFullConeSessDsliteInsideUser OBJECT-TYPE 
	SYNTAX DisplayString
	MAX-ACCESS read-only
	STATUS current
	DESCRIPTION
		"The inside user address and port of the fixed nat."
	::= { axFixedNatFullConeSessDsliteEntry 2 } 

    axFixedNatFullConeSessDsliteProtType  OBJECT-TYPE 
      SYNTAX                  INTEGER {
        unknown(0),
        tcp(1),
        udp(2),
        alg(3)
      }
      MAX-ACCESS        read-only
      STATUS                  current
      DESCRIPTION       
            "The protocol type of fixed nat."
      ::=  {  axFixedNatFullConeSessDsliteEntry  3  }

    axFixedNatFullConeSessDsliteEIM  OBJECT-TYPE 
      SYNTAX            INTEGER
      MAX-ACCESS        read-only
      STATUS            current
      DESCRIPTION       
            "The EIM value of the full cone session fixed nat."
      ::=  {  axFixedNatFullConeSessDsliteEntry  4  }

    axFixedNatFullConeSessDsliteEIF  OBJECT-TYPE 
      SYNTAX            INTEGER
      MAX-ACCESS        read-only
      STATUS            current
      DESCRIPTION       
            "The EIF value of the full cone session fixed nat."
      ::=  {  axFixedNatFullConeSessDsliteEntry  5  }

    axFixedNatFullConeSessDsliteCPU  OBJECT-TYPE 
      SYNTAX            INTEGER
      MAX-ACCESS        read-only
      STATUS            current
      DESCRIPTION       
            "The CPU of the full cone session fixed nat."
      ::=  {  axFixedNatFullConeSessDsliteEntry  6  }

    axFixedNatFullConeSessDsliteAge  OBJECT-TYPE 
      SYNTAX            INTEGER
      MAX-ACCESS        read-only
      STATUS            current
      DESCRIPTION       
            "The ages of the full cone session fixed nat."
      ::=  {  axFixedNatFullConeSessDsliteEntry  7  }

    axFixedNatFullConeSessDslitePcpFlags OBJECT-TYPE
      SYNTAX    INTEGER {
        other(0),
        pcp(1)
      }
      MAX-ACCESS        read-only
      STATUS             current
      DESCRIPTION       
            "The flag of pcp."
      ::=  {  axFixedNatFullConeSessDsliteEntry  8  }

--============axFixedNatFullConeSessNat44Table===================

    axFixedNatFullConeSessNat44Table OBJECT-TYPE
	SYNTAX SEQUENCE OF AxFixedNatFullConeSessNat44Entry
	MAX-ACCESS not-accessible
	STATUS current
	DESCRIPTION
		"A table has information of fixed nat full-cone-session NAT44."
	::= { axFixedNatFullConeSess 2 } 

    axFixedNatFullConeSessNat44Entry OBJECT-TYPE
	SYNTAX  AxFixedNatFullConeSessNat44Entry
	MAX-ACCESS not-accessible
	STATUS current
	DESCRIPTION
		"Columns in the axFixedNatFullConeSessNat44Table Table"
	INDEX {
		axFixedNatFullConeSessNat44NatIpAddress, axFixedNatFullConeSessNat44InsideUser,
		axFixedNatFullConeSessNat44ProtType
	}
	::= { axFixedNatFullConeSessNat44Table 1 } 

    AxFixedNatFullConeSessNat44Entry ::= 
	SEQUENCE {
        	axFixedNatFullConeSessNat44NatIpAddress	        DisplayString,
        	axFixedNatFullConeSessNat44InsideUser              DisplayString,
            axFixedNatFullConeSessNat44ProtType                INTEGER,
		    axFixedNatFullConeSessNat44EIM                     INTEGER,
        	axFixedNatFullConeSessNat44EIF                     INTEGER,
        	axFixedNatFullConeSessNat44CPU                     INTEGER,
        	axFixedNatFullConeSessNat44Age                     INTEGER,
        	axFixedNatFullConeSessNat44PcpFlags                INTEGER
	}

    axFixedNatFullConeSessNat44NatIpAddress OBJECT-TYPE 
	SYNTAX DisplayString
	MAX-ACCESS read-only
	STATUS current
	DESCRIPTION
		"The nat ip address and port of the fixed nat."
	::= { axFixedNatFullConeSessNat44Entry 1 } 

    axFixedNatFullConeSessNat44InsideUser OBJECT-TYPE 
	SYNTAX DisplayString
	MAX-ACCESS read-only
	STATUS current
	DESCRIPTION
		"The inside user address and port of the fixed nat."
	::= { axFixedNatFullConeSessNat44Entry 2 } 

    axFixedNatFullConeSessNat44ProtType  OBJECT-TYPE 
      SYNTAX                  INTEGER {
        unknown(0),
        tcp(1),
        udp(2),
        alg(3)
      }
      MAX-ACCESS        read-only
      STATUS                  current
      DESCRIPTION       
            "The protocol type of fixed nat."
      ::=  {  axFixedNatFullConeSessNat44Entry  3  }

    axFixedNatFullConeSessNat44EIM  OBJECT-TYPE 
      SYNTAX            INTEGER
      MAX-ACCESS        read-only
      STATUS            current
      DESCRIPTION       
            "The EIM value of the full cone session fixed nat."
      ::=  {  axFixedNatFullConeSessNat44Entry  4  }

    axFixedNatFullConeSessNat44EIF  OBJECT-TYPE 
      SYNTAX            INTEGER
      MAX-ACCESS        read-only
      STATUS            current
      DESCRIPTION       
            "The EIF value of the full cone session fixed nat."
      ::=  {  axFixedNatFullConeSessNat44Entry  5  }

    axFixedNatFullConeSessNat44CPU  OBJECT-TYPE 
      SYNTAX            INTEGER
      MAX-ACCESS        read-only
      STATUS            current
      DESCRIPTION       
            "The CPU of the full cone session fixed nat."
      ::=  {  axFixedNatFullConeSessNat44Entry  6  }

    axFixedNatFullConeSessNat44Age  OBJECT-TYPE 
      SYNTAX            INTEGER
      MAX-ACCESS        read-only
      STATUS            current
      DESCRIPTION       
            "The ages of the full cone session fixed nat."
      ::=  {  axFixedNatFullConeSessNat44Entry  7  }

    axFixedNatFullConeSessNat44PcpFlags OBJECT-TYPE
      SYNTAX    INTEGER {
        other(0),
        pcp(1)
      }
      MAX-ACCESS        read-only
      STATUS             current
      DESCRIPTION       
            "The flag of pcp."
      ::=  {  axFixedNatFullConeSessNat44Entry  8  }

--============axFixedNatFullConeSessNat64Table===================

    axFixedNatFullConeSessNat64Table OBJECT-TYPE
	SYNTAX SEQUENCE OF AxFixedNatFullConeSessNat64Entry
	MAX-ACCESS not-accessible
	STATUS current
	DESCRIPTION
		"A table has information of fixed nat full-cone-session NAT64."
	::= { axFixedNatFullConeSess 3 } 

    axFixedNatFullConeSessNat64Entry OBJECT-TYPE
	SYNTAX  AxFixedNatFullConeSessNat64Entry
	MAX-ACCESS not-accessible
	STATUS current
	DESCRIPTION
		"Columns in the axFixedNatFullConeSessNat64Table Table"
	INDEX {
		axFixedNatFullConeSessNat64NatIpAddress, axFixedNatFullConeSessNat64InsideUser,
		axFixedNatFullConeSessNat64ProtType
	}
	::= { axFixedNatFullConeSessNat64Table 1 } 

    AxFixedNatFullConeSessNat64Entry ::= 
	SEQUENCE {
        	axFixedNatFullConeSessNat64NatIpAddress	           DisplayString,
        	axFixedNatFullConeSessNat64InsideUser              DisplayString,
            axFixedNatFullConeSessNat64ProtType                INTEGER,
		    axFixedNatFullConeSessNat64EIM                     INTEGER,
        	axFixedNatFullConeSessNat64EIF                     INTEGER,
        	axFixedNatFullConeSessNat64CPU                     INTEGER,
        	axFixedNatFullConeSessNat64Age                     INTEGER,
        	axFixedNatFullConeSessNat64PcpFlags                INTEGER
	}

    axFixedNatFullConeSessNat64NatIpAddress OBJECT-TYPE 
	SYNTAX DisplayString
	MAX-ACCESS read-only
	STATUS current
	DESCRIPTION
		"The nat ip address and port of the fixed nat."
	::= { axFixedNatFullConeSessNat64Entry 1 } 

    axFixedNatFullConeSessNat64InsideUser OBJECT-TYPE 
	SYNTAX DisplayString
	MAX-ACCESS read-only
	STATUS current
	DESCRIPTION
		"The inside user address and port of the fixed nat."
	::= { axFixedNatFullConeSessNat64Entry 2 } 

    axFixedNatFullConeSessNat64ProtType  OBJECT-TYPE 
      SYNTAX                  INTEGER {
        unknown(0),
        tcp(1),
        udp(2),
        alg(3)
      }
      MAX-ACCESS        read-only
      STATUS                  current
      DESCRIPTION       
            "The protocol type of fixed nat."
      ::=  {  axFixedNatFullConeSessNat64Entry  3  }

    axFixedNatFullConeSessNat64EIM  OBJECT-TYPE 
      SYNTAX            INTEGER
      MAX-ACCESS        read-only
      STATUS            current
      DESCRIPTION       
            "The EIM value of the full cone session fixed nat."
      ::=  {  axFixedNatFullConeSessNat64Entry  4  }

    axFixedNatFullConeSessNat64EIF  OBJECT-TYPE 
      SYNTAX            INTEGER
      MAX-ACCESS        read-only
      STATUS            current
      DESCRIPTION       
            "The EIF value of the full cone session fixed nat."
      ::=  {  axFixedNatFullConeSessNat64Entry  5  }

    axFixedNatFullConeSessNat64CPU  OBJECT-TYPE 
      SYNTAX            INTEGER
      MAX-ACCESS        read-only
      STATUS            current
      DESCRIPTION       
            "The CPU of the full cone session fixed nat."
      ::=  {  axFixedNatFullConeSessNat64Entry  6  }

    axFixedNatFullConeSessNat64Age  OBJECT-TYPE 
      SYNTAX            INTEGER
      MAX-ACCESS        read-only
      STATUS            current
      DESCRIPTION       
            "The ages of the full cone session fixed nat."
      ::=  {  axFixedNatFullConeSessNat64Entry  7  }

    axFixedNatFullConeSessNat64PcpFlags OBJECT-TYPE
      SYNTAX    INTEGER {
        other(0),
        pcp(1)
      }
      MAX-ACCESS        read-only
      STATUS             current
      DESCRIPTION       
            "The flag of pcp."
      ::=  {  axFixedNatFullConeSessNat64Entry  8  }


END

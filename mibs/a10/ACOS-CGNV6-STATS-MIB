ACOS-CGNV6-STATS-MIB DEFINITIONS ::= BEGIN
	IMPORTS
		DisplayString, PhysAddress
		FROM SNMPv2-TC
	InetAddressType
		FROM INET-ADDRESS-MIB
	acosRootStats
		FROM A10-AX-MIB
	MODULE-IDENTITY, OBJECT-TYPE, Counter32, Integer32, Counter64, OBJECT-IDENTITY, NOTIFICATION-TYPE
		FROM SNMPv2-SMI;
		acosCgnv6 MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "Cgnv6 OID for ACOS"
				::=  {  acosRootStats 115  }

acosCgnv6Global                     OBJECT IDENTIFIER ::= { acosCgnv6 1 }
acosCgnv6GlobalS                    OBJECT IDENTIFIER ::= { acosCgnv6Global 1 }

		tcpTotalPortsAllocated OBJECT-TYPE
		SYNTAX  CounterBasedGauge64 
		MAX-ACCESS read-only 
		STATUS current
		DESCRIPTION  "Total TCP ports allocated" 
		::={ acosCgnv6GlobalS 1 } 

		udpTotalPortsAllocated OBJECT-TYPE
		SYNTAX  CounterBasedGauge64 
		MAX-ACCESS read-only 
		STATUS current
		DESCRIPTION  "Total UDP ports allocated" 
		::={ acosCgnv6GlobalS 2 } 

		icmpTotalPortsAllocated OBJECT-TYPE
		SYNTAX  CounterBasedGauge64 
		MAX-ACCESS read-only 
		STATUS current
		DESCRIPTION  "Total ICMP ports allocated" 
		::={ acosCgnv6GlobalS 3 } 

acosCgnv6Server                     OBJECT IDENTIFIER ::= { acosCgnv6 2 }
acosCgnv6ServerS                    OBJECT IDENTIFIER ::= { acosCgnv6Server 1 }

cgnv6ServerSTable OBJECT-TYPE
		SYNTAX SEQUENCE OF Cgnv6ServerSEntry
		MAX-ACCESS not-accessible
		STATUS current
		::={ acosCgnv6ServerS 1 } 


	cgnv6ServerSEntry OBJECT-TYPE
		SYNTAX Cgnv6ServerSEntry
		MAX-ACCESS not-accessible
		STATUS current
		INDEX {
			cgnv6Name
		}
		::={ cgnv6ServerSTable 1 } 


	Cgnv6ServerSEntry ::=
		SEQUENCE {
			cgnv6Name DisplayString, 
			cgnv6ServerCurrConn CounterBasedGauge64,
			totalConn CounterBasedGauge64,
			fwdPkt CounterBasedGauge64,
			revPkt CounterBasedGauge64,
			peakConn CounterBasedGauge64
		}

			cgnv6Name OBJECT-TYPE
			SYNTAX  DisplayString 
			MAX-ACCESS read-only 
			STATUS current
			DESCRIPTION  "Server Name" 
			::={ cgnv6ServerSEntry 1 } 

			cgnv6ServerCurrConn OBJECT-TYPE
			SYNTAX  CounterBasedGauge64 
			MAX-ACCESS read-only 
			STATUS current
			DESCRIPTION  "Current connections" 
			::={ cgnv6ServerSEntry 2 } 

			totalConn OBJECT-TYPE
			SYNTAX  CounterBasedGauge64 
			MAX-ACCESS read-only 
			STATUS current
			DESCRIPTION  "Total connections" 
			::={ cgnv6ServerSEntry 3 } 

			fwdPkt OBJECT-TYPE
			SYNTAX  CounterBasedGauge64 
			MAX-ACCESS read-only 
			STATUS current
			DESCRIPTION  "Forward packets" 
			::={ cgnv6ServerSEntry 4 } 

			revPkt OBJECT-TYPE
			SYNTAX  CounterBasedGauge64 
			MAX-ACCESS read-only 
			STATUS current
			DESCRIPTION  "Reverse Packets" 
			::={ cgnv6ServerSEntry 5 } 

			peakConn OBJECT-TYPE
			SYNTAX  CounterBasedGauge64 
			MAX-ACCESS read-only 
			STATUS current
			DESCRIPTION  "Peak connections" 
			::={ cgnv6ServerSEntry 6 } 

acosCgnv6ServiceGroup               OBJECT IDENTIFIER ::= { acosCgnv6 3 }
acosCgnv6ServiceGroupS              OBJECT IDENTIFIER ::= { acosCgnv6ServiceGroup 1 }

cgnv6ServiceGroupSTable OBJECT-TYPE
		SYNTAX SEQUENCE OF Cgnv6ServiceGroupSEntry
		MAX-ACCESS not-accessible
		STATUS current
		::={ acosCgnv6ServiceGroupS 1 } 


	cgnv6ServiceGroupSEntry OBJECT-TYPE
		SYNTAX Cgnv6ServiceGroupSEntry
		MAX-ACCESS not-accessible
		STATUS current
		INDEX {
			cgnv6ServiceGroupName
		}
		::={ cgnv6ServiceGroupSTable 1 } 


	Cgnv6ServiceGroupSEntry ::=
		SEQUENCE {
			cgnv6ServiceGroupName DisplayString, 
			cgnv6ServerSelectionFailDrop CounterBasedGauge64,
			cgnv6ServerSelectionFailReset CounterBasedGauge64,
			cgnv6ServicePeakConn CounterBasedGauge64
		}

			cgnv6ServiceGroupName OBJECT-TYPE
			SYNTAX  DisplayString 
			MAX-ACCESS read-only 
			STATUS current
			DESCRIPTION  "CGNV6 Service Name" 
			::={ cgnv6ServiceGroupSEntry 1 } 

			cgnv6ServerSelectionFailDrop OBJECT-TYPE
			SYNTAX  CounterBasedGauge64 
			MAX-ACCESS read-only 
			STATUS current
			DESCRIPTION  "Service selection fail drop" 
			::={ cgnv6ServiceGroupSEntry 2 } 

			cgnv6ServerSelectionFailReset OBJECT-TYPE
			SYNTAX  CounterBasedGauge64 
			MAX-ACCESS read-only 
			STATUS current
			DESCRIPTION  "Service selection fail reset" 
			::={ cgnv6ServiceGroupSEntry 3 } 

			cgnv6ServicePeakConn OBJECT-TYPE
			SYNTAX  CounterBasedGauge64 
			MAX-ACCESS read-only 
			STATUS current
			DESCRIPTION  "Service peak connection" 
			::={ cgnv6ServiceGroupSEntry 4 } 

acosCgnv6DdosProtection             OBJECT IDENTIFIER ::= { acosCgnv6 5 }
acosCgnv6DdosProtectionS            OBJECT IDENTIFIER ::= { acosCgnv6DdosProtection 1 }

		l3EntryAdded OBJECT-TYPE
		SYNTAX  CounterBasedGauge64 
		MAX-ACCESS read-only 
		STATUS current
		DESCRIPTION  "L3 Entry Added" 
		::={ acosCgnv6DdosProtectionS 1 } 

		l3EntryDeleted OBJECT-TYPE
		SYNTAX  CounterBasedGauge64 
		MAX-ACCESS read-only 
		STATUS current
		DESCRIPTION  "L3 Entry Deleted" 
		::={ acosCgnv6DdosProtectionS 2 } 

		l3EntryAddedToBgp OBJECT-TYPE
		SYNTAX  CounterBasedGauge64 
		MAX-ACCESS read-only 
		STATUS current
		DESCRIPTION  "L3 Entry added to BGP" 
		::={ acosCgnv6DdosProtectionS 3 } 

		l3EntryRemovedFromBgp OBJECT-TYPE
		SYNTAX  CounterBasedGauge64 
		MAX-ACCESS read-only 
		STATUS current
		DESCRIPTION  "Entry removed from BGP" 
		::={ acosCgnv6DdosProtectionS 4 } 

		l3EntryAddedToHw OBJECT-TYPE
		SYNTAX  CounterBasedGauge64 
		MAX-ACCESS read-only 
		STATUS current
		DESCRIPTION  "L3 Entry added to HW" 
		::={ acosCgnv6DdosProtectionS 5 } 

		l3EntryRemovedFromHw OBJECT-TYPE
		SYNTAX  CounterBasedGauge64 
		MAX-ACCESS read-only 
		STATUS current
		DESCRIPTION  "L3 Entry removed from HW" 
		::={ acosCgnv6DdosProtectionS 6 } 

		l3EntryTooMany OBJECT-TYPE
		SYNTAX  CounterBasedGauge64 
		MAX-ACCESS read-only 
		STATUS current
		DESCRIPTION  "L3 Too many entries" 
		::={ acosCgnv6DdosProtectionS 7 } 

		l3EntryMatchDrop OBJECT-TYPE
		SYNTAX  CounterBasedGauge64 
		MAX-ACCESS read-only 
		STATUS current
		DESCRIPTION  "L3 Entry match drop" 
		::={ acosCgnv6DdosProtectionS 8 } 

		l3EntryMatchDropHw OBJECT-TYPE
		SYNTAX  CounterBasedGauge64 
		MAX-ACCESS read-only 
		STATUS current
		DESCRIPTION  "L3 HW entry match drop" 
		::={ acosCgnv6DdosProtectionS 9 } 

		l3EntryDropMaxHwExceeded OBJECT-TYPE
		SYNTAX  CounterBasedGauge64 
		MAX-ACCESS read-only 
		STATUS current
		DESCRIPTION  "L3 Entry Drop due to HW Limit Exceeded" 
		::={ acosCgnv6DdosProtectionS 10 } 

		l4EntryAdded OBJECT-TYPE
		SYNTAX  CounterBasedGauge64 
		MAX-ACCESS read-only 
		STATUS current
		DESCRIPTION  "L4 Entry added" 
		::={ acosCgnv6DdosProtectionS 11 } 

		l4EntryDeleted OBJECT-TYPE
		SYNTAX  CounterBasedGauge64 
		MAX-ACCESS read-only 
		STATUS current
		DESCRIPTION  "L4 Entry deleted" 
		::={ acosCgnv6DdosProtectionS 12 } 

		l4EntryAddedToHw OBJECT-TYPE
		SYNTAX  CounterBasedGauge64 
		MAX-ACCESS read-only 
		STATUS current
		DESCRIPTION  "L4 Entry added to HW" 
		::={ acosCgnv6DdosProtectionS 13 } 

		l4EntryRemovedFromHw OBJECT-TYPE
		SYNTAX  CounterBasedGauge64 
		MAX-ACCESS read-only 
		STATUS current
		DESCRIPTION  "L4 Entry removed from HW" 
		::={ acosCgnv6DdosProtectionS 14 } 

		l4HwOutOfEntries OBJECT-TYPE
		SYNTAX  CounterBasedGauge64 
		MAX-ACCESS read-only 
		STATUS current
		DESCRIPTION  "HW out of L4 entries" 
		::={ acosCgnv6DdosProtectionS 15 } 

		l4EntryMatchDrop OBJECT-TYPE
		SYNTAX  CounterBasedGauge64 
		MAX-ACCESS read-only 
		STATUS current
		DESCRIPTION  "L4 Entry match drop" 
		::={ acosCgnv6DdosProtectionS 16 } 

		l4EntryMatchDropHw OBJECT-TYPE
		SYNTAX  CounterBasedGauge64 
		MAX-ACCESS read-only 
		STATUS current
		DESCRIPTION  "L4 HW Entry match drop" 
		::={ acosCgnv6DdosProtectionS 17 } 

		l4EntryDropMaxHwExceeded OBJECT-TYPE
		SYNTAX  CounterBasedGauge64 
		MAX-ACCESS read-only 
		STATUS current
		DESCRIPTION  "L4 Entry Drop due to HW Limit Exceeded" 
		::={ acosCgnv6DdosProtectionS 18 } 

		l4EntryListAlloc OBJECT-TYPE
		SYNTAX  CounterBasedGauge64 
		MAX-ACCESS read-only 
		STATUS current
		DESCRIPTION  "L4 Entry list alloc" 
		::={ acosCgnv6DdosProtectionS 19 } 

		l4EntryListFree OBJECT-TYPE
		SYNTAX  CounterBasedGauge64 
		MAX-ACCESS read-only 
		STATUS current
		DESCRIPTION  "L4 Entry list free" 
		::={ acosCgnv6DdosProtectionS 20 } 

		l4EntryListAllocFailure OBJECT-TYPE
		SYNTAX  CounterBasedGauge64 
		MAX-ACCESS read-only 
		STATUS current
		DESCRIPTION  "L4 Entry list alloc failures" 
		::={ acosCgnv6DdosProtectionS 21 } 

		ipNodeAlloc OBJECT-TYPE
		SYNTAX  CounterBasedGauge64 
		MAX-ACCESS read-only 
		STATUS current
		DESCRIPTION  "Node alloc" 
		::={ acosCgnv6DdosProtectionS 22 } 

		ipNodeFree OBJECT-TYPE
		SYNTAX  CounterBasedGauge64 
		MAX-ACCESS read-only 
		STATUS current
		DESCRIPTION  "Node free" 
		::={ acosCgnv6DdosProtectionS 23 } 

		ipNodeAllocFailure OBJECT-TYPE
		SYNTAX  CounterBasedGauge64 
		MAX-ACCESS read-only 
		STATUS current
		DESCRIPTION  "Node alloc failures" 
		::={ acosCgnv6DdosProtectionS 24 } 

		ipPortBlockAlloc OBJECT-TYPE
		SYNTAX  CounterBasedGauge64 
		MAX-ACCESS read-only 
		STATUS current
		DESCRIPTION  "Port block alloc" 
		::={ acosCgnv6DdosProtectionS 25 } 

		ipPortBlockFree OBJECT-TYPE
		SYNTAX  CounterBasedGauge64 
		MAX-ACCESS read-only 
		STATUS current
		DESCRIPTION  "Port block free" 
		::={ acosCgnv6DdosProtectionS 26 } 

		ipPortBlockAllocFailure OBJECT-TYPE
		SYNTAX  CounterBasedGauge64 
		MAX-ACCESS read-only 
		STATUS current
		DESCRIPTION  "Port block alloc failure" 
		::={ acosCgnv6DdosProtectionS 27 } 

		ipOtherBlockAlloc OBJECT-TYPE
		SYNTAX  CounterBasedGauge64 
		MAX-ACCESS read-only 
		STATUS current
		DESCRIPTION  "Other block alloc" 
		::={ acosCgnv6DdosProtectionS 28 } 

		ipOtherBlockFree OBJECT-TYPE
		SYNTAX  CounterBasedGauge64 
		MAX-ACCESS read-only 
		STATUS current
		DESCRIPTION  "Other block free" 
		::={ acosCgnv6DdosProtectionS 29 } 

		ipOtherBlockAllocFailure OBJECT-TYPE
		SYNTAX  CounterBasedGauge64 
		MAX-ACCESS read-only 
		STATUS current
		DESCRIPTION  "Other block alloc failure" 
		::={ acosCgnv6DdosProtectionS 30 } 

		entryAddedShadow OBJECT-TYPE
		SYNTAX  CounterBasedGauge64 
		MAX-ACCESS read-only 
		STATUS current
		DESCRIPTION  "Entry added shadow" 
		::={ acosCgnv6DdosProtectionS 31 } 

		entryInvalidated OBJECT-TYPE
		SYNTAX  CounterBasedGauge64 
		MAX-ACCESS read-only 
		STATUS current
		DESCRIPTION  "Entry invalidated" 
		::={ acosCgnv6DdosProtectionS 32 } 

		l3EntryAddToBgpFailure OBJECT-TYPE
		SYNTAX  CounterBasedGauge64 
		MAX-ACCESS read-only 
		STATUS current
		DESCRIPTION  "L3 Entry BGP add failures" 
		::={ acosCgnv6DdosProtectionS 33 } 

		l3EntryRemoveFromBgpFailure OBJECT-TYPE
		SYNTAX  CounterBasedGauge64 
		MAX-ACCESS read-only 
		STATUS current
		DESCRIPTION  "L3 entry BGP remove failures" 
		::={ acosCgnv6DdosProtectionS 34 } 

		l3EntryAddToHwFailure OBJECT-TYPE
		SYNTAX  CounterBasedGauge64 
		MAX-ACCESS read-only 
		STATUS current
		DESCRIPTION  "L3 entry HW add failure" 
		::={ acosCgnv6DdosProtectionS 35 } 

		synCookieSynAckSent OBJECT-TYPE
		SYNTAX  CounterBasedGauge64 
		MAX-ACCESS read-only 
		STATUS current
		DESCRIPTION  "SYN cookie SYN ACK sent" 
		::={ acosCgnv6DdosProtectionS 36 } 

		synCookieVerificationPassed OBJECT-TYPE
		SYNTAX  CounterBasedGauge64 
		MAX-ACCESS read-only 
		STATUS current
		DESCRIPTION  "SYN cookie verification passed" 
		::={ acosCgnv6DdosProtectionS 37 } 

		synCookieVerificationFailed OBJECT-TYPE
		SYNTAX  CounterBasedGauge64 
		MAX-ACCESS read-only 
		STATUS current
		DESCRIPTION  "SYN cookie verification failed" 
		::={ acosCgnv6DdosProtectionS 38 } 

		synCookieConnSetupFailed OBJECT-TYPE
		SYNTAX  CounterBasedGauge64 
		MAX-ACCESS read-only 
		STATUS current
		DESCRIPTION  "SYN cookie connection setup failed" 
		::={ acosCgnv6DdosProtectionS 39 } 

acosCgnv6Lsn                        OBJECT IDENTIFIER ::= { acosCgnv6 7 }
acosCgnv6LsnPerformance             OBJECT IDENTIFIER ::= { acosCgnv6Lsn 2 }
acosCgnv6LsnPerformanceS            OBJECT IDENTIFIER ::= { acosCgnv6LsnPerformance 1 }

		dataSessionsCurrentEpoch OBJECT-TYPE
		SYNTAX  CounterBasedGauge64 
		MAX-ACCESS read-only 
		STATUS current
		DESCRIPTION  "some help string" 
		::={ acosCgnv6LsnPerformanceS 1 } 

		fullconeCreatedCurrentEpoch OBJECT-TYPE
		SYNTAX  CounterBasedGauge64 
		MAX-ACCESS read-only 
		STATUS current
		DESCRIPTION  "some help string" 
		::={ acosCgnv6LsnPerformanceS 2 } 

		userQuoteCreatedCurrentEpoch OBJECT-TYPE
		SYNTAX  CounterBasedGauge64 
		MAX-ACCESS read-only 
		STATUS current
		DESCRIPTION  "some help string" 
		::={ acosCgnv6LsnPerformanceS 3 } 

		dataSessionsPreviousEpochFirst OBJECT-TYPE
		SYNTAX  CounterBasedGauge64 
		MAX-ACCESS read-only 
		STATUS current
		DESCRIPTION  "some help string" 
		::={ acosCgnv6LsnPerformanceS 4 } 

		fullconeCreatedPreviousEpochFirst OBJECT-TYPE
		SYNTAX  CounterBasedGauge64 
		MAX-ACCESS read-only 
		STATUS current
		DESCRIPTION  "some help string" 
		::={ acosCgnv6LsnPerformanceS 5 } 

		userQuoteCreatedPreviousEpochFirst OBJECT-TYPE
		SYNTAX  CounterBasedGauge64 
		MAX-ACCESS read-only 
		STATUS current
		DESCRIPTION  "some help string" 
		::={ acosCgnv6LsnPerformanceS 6 } 

		dataSessionsPreviousEpochLast OBJECT-TYPE
		SYNTAX  CounterBasedGauge64 
		MAX-ACCESS read-only 
		STATUS current
		DESCRIPTION  "some help string" 
		::={ acosCgnv6LsnPerformanceS 7 } 

		fullconeCreatedPreviousEpochLast OBJECT-TYPE
		SYNTAX  CounterBasedGauge64 
		MAX-ACCESS read-only 
		STATUS current
		DESCRIPTION  "some help string" 
		::={ acosCgnv6LsnPerformanceS 8 } 

		userQuoteCreatedPreviousEpochLast OBJECT-TYPE
		SYNTAX  CounterBasedGauge64 
		MAX-ACCESS read-only 
		STATUS current
		DESCRIPTION  "some help string" 
		::={ acosCgnv6LsnPerformanceS 9 } 

acosCgnv6LsnGlobal                  OBJECT IDENTIFIER ::= { acosCgnv6Lsn 4 }
acosCgnv6LsnGlobalS                 OBJECT IDENTIFIER ::= { acosCgnv6LsnGlobal 1 }

		cgnv6lsnGlobalTotalTcpAllocated OBJECT-TYPE
		SYNTAX  CounterBasedGauge64 
		MAX-ACCESS read-only 
		STATUS current
		DESCRIPTION  "Total TCP Ports Allocated" 
		::={ acosCgnv6LsnGlobalS 1 } 

		cgnv6lsnGlobalTotalTcpFreed OBJECT-TYPE
		SYNTAX  CounterBasedGauge64 
		MAX-ACCESS read-only 
		STATUS current
		DESCRIPTION  "Total TCP Ports Freed" 
		::={ acosCgnv6LsnGlobalS 2 } 

		cgnv6lsnGlobalTotalUdpAllocated OBJECT-TYPE
		SYNTAX  CounterBasedGauge64 
		MAX-ACCESS read-only 
		STATUS current
		DESCRIPTION  "Total UDP Ports Allocated" 
		::={ acosCgnv6LsnGlobalS 3 } 

		cgnv6lsnGlobalTotalUdpFreed OBJECT-TYPE
		SYNTAX  CounterBasedGauge64 
		MAX-ACCESS read-only 
		STATUS current
		DESCRIPTION  "Total UDP Ports Freed" 
		::={ acosCgnv6LsnGlobalS 4 } 

		cgnv6lsnGlobalTotalIcmpAllocated OBJECT-TYPE
		SYNTAX  CounterBasedGauge64 
		MAX-ACCESS read-only 
		STATUS current
		DESCRIPTION  "Total ICMP Ports Allocated" 
		::={ acosCgnv6LsnGlobalS 5 } 

		cgnv6lsnGlobalTotalIcmpFreed OBJECT-TYPE
		SYNTAX  CounterBasedGauge64 
		MAX-ACCESS read-only 
		STATUS current
		DESCRIPTION  "Total ICMP Ports Freed" 
		::={ acosCgnv6LsnGlobalS 6 } 

		cgnv6lsnGlobalDataSessionCreated OBJECT-TYPE
		SYNTAX  CounterBasedGauge64 
		MAX-ACCESS read-only 
		STATUS current
		DESCRIPTION  "Data Session Created" 
		::={ acosCgnv6LsnGlobalS 7 } 

		cgnv6lsnGlobalDataSessionFreed OBJECT-TYPE
		SYNTAX  CounterBasedGauge64 
		MAX-ACCESS read-only 
		STATUS current
		DESCRIPTION  "Data Session Freed" 
		::={ acosCgnv6LsnGlobalS 8 } 

		cgnv6lsnGlobalTotalUserQuotaCreated OBJECT-TYPE
		SYNTAX  CounterBasedGauge64 
		MAX-ACCESS read-only 
		STATUS current
		DESCRIPTION  "User-Quota Created" 
		::={ acosCgnv6LsnGlobalS 9 } 

		cgnv6lsnGlobalUserQuotaPutInDelQ OBJECT-TYPE
		SYNTAX  CounterBasedGauge64 
		MAX-ACCESS read-only 
		STATUS current
		DESCRIPTION  "User-Quota Freed" 
		::={ acosCgnv6LsnGlobalS 10 } 

		cgnv6lsnGlobalUserQuotaFailure OBJECT-TYPE
		SYNTAX  CounterBasedGauge64 
		MAX-ACCESS read-only 
		STATUS current
		DESCRIPTION  "User-Quota Creation Failed" 
		::={ acosCgnv6LsnGlobalS 11 } 

		cgnv6lsnGlobalNatPortUnavailableTcp OBJECT-TYPE
		SYNTAX  CounterBasedGauge64 
		MAX-ACCESS read-only 
		STATUS current
		DESCRIPTION  "TCP NAT Port Unavailable" 
		::={ acosCgnv6LsnGlobalS 12 } 

		cgnv6lsnGlobalNatPortUnavailableUdp OBJECT-TYPE
		SYNTAX  CounterBasedGauge64 
		MAX-ACCESS read-only 
		STATUS current
		DESCRIPTION  "UDP NAT Port Unavailable" 
		::={ acosCgnv6LsnGlobalS 13 } 

		cgnv6lsnGlobalNatPortUnavailableIcmp OBJECT-TYPE
		SYNTAX  CounterBasedGauge64 
		MAX-ACCESS read-only 
		STATUS current
		DESCRIPTION  "ICMP NAT Port Unavailable" 
		::={ acosCgnv6LsnGlobalS 14 } 

		cgnv6lsnGlobalNewUserResourceUnavailable OBJECT-TYPE
		SYNTAX  CounterBasedGauge64 
		MAX-ACCESS read-only 
		STATUS current
		DESCRIPTION  "New User NAT Resource Unavailable" 
		::={ acosCgnv6LsnGlobalS 15 } 

		cgnv6lsnGlobalTcpUserQuotaExceeded OBJECT-TYPE
		SYNTAX  CounterBasedGauge64 
		MAX-ACCESS read-only 
		STATUS current
		DESCRIPTION  "TCP User-Quota Exceeded" 
		::={ acosCgnv6LsnGlobalS 16 } 

		cgnv6lsnGlobalUdpUserQuotaExceeded OBJECT-TYPE
		SYNTAX  CounterBasedGauge64 
		MAX-ACCESS read-only 
		STATUS current
		DESCRIPTION  "UDP User-Quota Exceeded" 
		::={ acosCgnv6LsnGlobalS 17 } 

		cgnv6lsnGlobalIcmpUserQuotaExceeded OBJECT-TYPE
		SYNTAX  CounterBasedGauge64 
		MAX-ACCESS read-only 
		STATUS current
		DESCRIPTION  "ICMP User-Quota Exceeded" 
		::={ acosCgnv6LsnGlobalS 18 } 

		cgnv6lsnGlobalExtendedQuotaMatched OBJECT-TYPE
		SYNTAX  CounterBasedGauge64 
		MAX-ACCESS read-only 
		STATUS current
		DESCRIPTION  "Extended User-Quota Matched" 
		::={ acosCgnv6LsnGlobalS 19 } 

		cgnv6lsnGlobalExtendedQuotaExceeded OBJECT-TYPE
		SYNTAX  CounterBasedGauge64 
		MAX-ACCESS read-only 
		STATUS current
		DESCRIPTION  "Extended User-Quota Exceeded" 
		::={ acosCgnv6LsnGlobalS 20 } 

		cgnv6lsnGlobalDataSesnUserQuotaExceeded OBJECT-TYPE
		SYNTAX  CounterBasedGauge64 
		MAX-ACCESS read-only 
		STATUS current
		DESCRIPTION  "Data Session User-Quota Exceeded" 
		::={ acosCgnv6LsnGlobalS 21 } 

		cgnv6lsnGlobalDataSesnRateUserQuotaExceeded OBJECT-TYPE
		SYNTAX  CounterBasedGauge64 
		MAX-ACCESS read-only 
		STATUS current
		DESCRIPTION  "Conn Rate User-Quota Exceeded" 
		::={ acosCgnv6LsnGlobalS 22 } 

		cgnv6lsnGlobalTcpFullconeCreated OBJECT-TYPE
		SYNTAX  CounterBasedGauge64 
		MAX-ACCESS read-only 
		STATUS current
		DESCRIPTION  "TCP Full-cone Session Created" 
		::={ acosCgnv6LsnGlobalS 23 } 

		cgnv6lsnGlobalTcpFullconeFreed OBJECT-TYPE
		SYNTAX  CounterBasedGauge64 
		MAX-ACCESS read-only 
		STATUS current
		DESCRIPTION  "TCP Full-cone Session Freed" 
		::={ acosCgnv6LsnGlobalS 24 } 

		cgnv6lsnGlobalUdpFullconeCreated OBJECT-TYPE
		SYNTAX  CounterBasedGauge64 
		MAX-ACCESS read-only 
		STATUS current
		DESCRIPTION  "UDP Full-cone Session Created" 
		::={ acosCgnv6LsnGlobalS 25 } 

		cgnv6lsnGlobalUdpFullconeFreed OBJECT-TYPE
		SYNTAX  CounterBasedGauge64 
		MAX-ACCESS read-only 
		STATUS current
		DESCRIPTION  "UDP Full-cone Session Freed" 
		::={ acosCgnv6LsnGlobalS 26 } 

		cgnv6lsnGlobalFullconeFailure OBJECT-TYPE
		SYNTAX  CounterBasedGauge64 
		MAX-ACCESS read-only 
		STATUS current
		DESCRIPTION  "Full-cone Session Creation Failed" 
		::={ acosCgnv6LsnGlobalS 27 } 

		cgnv6lsnGlobalHairpin OBJECT-TYPE
		SYNTAX  CounterBasedGauge64 
		MAX-ACCESS read-only 
		STATUS current
		DESCRIPTION  "Hairpin Session Created" 
		::={ acosCgnv6LsnGlobalS 28 } 

		cgnv6lsnGlobalFullconeSelfHairpinningDrop OBJECT-TYPE
		SYNTAX  CounterBasedGauge64 
		MAX-ACCESS read-only 
		STATUS current
		DESCRIPTION  "Self-Hairpinning Drop" 
		::={ acosCgnv6LsnGlobalS 29 } 

		cgnv6lsnGlobalEndpointIndepMapMatch OBJECT-TYPE
		SYNTAX  CounterBasedGauge64 
		MAX-ACCESS read-only 
		STATUS current
		DESCRIPTION  "Endpoint-Independent Mapping Matched" 
		::={ acosCgnv6LsnGlobalS 30 } 

		cgnv6lsnGlobalEndpointIndepFilterMatch OBJECT-TYPE
		SYNTAX  CounterBasedGauge64 
		MAX-ACCESS read-only 
		STATUS current
		DESCRIPTION  "Endpoint-Independent Filtering Matched" 
		::={ acosCgnv6LsnGlobalS 31 } 

		cgnv6lsnGlobalInboundFiltered OBJECT-TYPE
		SYNTAX  CounterBasedGauge64 
		MAX-ACCESS read-only 
		STATUS current
		DESCRIPTION  "Endpoint-Dependent Filtering Drop" 
		::={ acosCgnv6LsnGlobalS 32 } 

		cgnv6lsnGlobalEifLimitExceeded OBJECT-TYPE
		SYNTAX  CounterBasedGauge64 
		MAX-ACCESS read-only 
		STATUS current
		DESCRIPTION  "Endpoint-Independent Filtering Inbound Limit Exceeded" 
		::={ acosCgnv6LsnGlobalS 33 } 

		cgnv6lsnGlobalTotalTcpOverloaded OBJECT-TYPE
		SYNTAX  CounterBasedGauge64 
		MAX-ACCESS read-only 
		STATUS current
		DESCRIPTION  "TCP Port Overloaded" 
		::={ acosCgnv6LsnGlobalS 35 } 

		cgnv6LsnGlobalTotalUdpOverloaded OBJECT-TYPE
		SYNTAX  CounterBasedGauge64 
		MAX-ACCESS read-only 
		STATUS current
		DESCRIPTION  "UDP Port Overloaded" 
		::={ acosCgnv6LsnGlobalS 36 } 

		cgnv6lsnGlobalPortOverloadingSmpInsertedTcp OBJECT-TYPE
		SYNTAX  CounterBasedGauge64 
		MAX-ACCESS read-only 
		STATUS current
		DESCRIPTION  "TCP Port Overloading Session Created" 
		::={ acosCgnv6LsnGlobalS 37 } 

		cgnv6lsnGlobalPortOverloadingSmpInsertedUdp OBJECT-TYPE
		SYNTAX  CounterBasedGauge64 
		MAX-ACCESS read-only 
		STATUS current
		DESCRIPTION  "UDP Port Overloading Session Created" 
		::={ acosCgnv6LsnGlobalS 38 } 

		cgnv6lsnGlobalPortOverloadingSmpFreeTcp OBJECT-TYPE
		SYNTAX  CounterBasedGauge64 
		MAX-ACCESS read-only 
		STATUS current
		DESCRIPTION  "TCP Port Overloading Session Freed" 
		::={ acosCgnv6LsnGlobalS 39 } 

		cgnv6lsnGlobalPortOverloadingSmpFreeUdp OBJECT-TYPE
		SYNTAX  CounterBasedGauge64 
		MAX-ACCESS read-only 
		STATUS current
		DESCRIPTION  "UDP Port Overloading Session Freed" 
		::={ acosCgnv6LsnGlobalS 40 } 

		cgnv6lsnGlobalNatPoolUnsable OBJECT-TYPE
		SYNTAX  CounterBasedGauge64 
		MAX-ACCESS read-only 
		STATUS current
		DESCRIPTION  "NAT Pool Unusable" 
		::={ acosCgnv6LsnGlobalS 41 } 

		cgnv6lsnGlobalHaNatPoolUnusable OBJECT-TYPE
		SYNTAX  CounterBasedGauge64 
		MAX-ACCESS read-only 
		STATUS current
		DESCRIPTION  "HA NAT Pool Unusable" 
		::={ acosCgnv6LsnGlobalS 42 } 

		haNatPoolBatchTypeMismatch OBJECT-TYPE
		SYNTAX  CounterBasedGauge64 
		MAX-ACCESS read-only 
		STATUS current
		DESCRIPTION  "HA NAT Pool Batch Type Mismatch" 
		::={ acosCgnv6LsnGlobalS 43 } 

		noRadiusProfileMatch OBJECT-TYPE
		SYNTAX  CounterBasedGauge64 
		MAX-ACCESS read-only 
		STATUS current
		DESCRIPTION  "No RADIUS Profile Match" 
		::={ acosCgnv6LsnGlobalS 44 } 

		natIpMaxTcpPortsAllocated OBJECT-TYPE
		SYNTAX  CounterBasedGauge64 
		MAX-ACCESS read-only 
		STATUS current
		DESCRIPTION  "NAT IP TCP Max Ports Allocated" 
		::={ acosCgnv6LsnGlobalS 45 } 

		natIpMaxUdpPortsAllocated OBJECT-TYPE
		SYNTAX  CounterBasedGauge64 
		MAX-ACCESS read-only 
		STATUS current
		DESCRIPTION  "NAT IP UDP Max Ports Allocated" 
		::={ acosCgnv6LsnGlobalS 46 } 

		noClassListMatch OBJECT-TYPE
		SYNTAX  CounterBasedGauge64 
		MAX-ACCESS read-only 
		STATUS current
		DESCRIPTION  "No Class-List Match" 
		::={ acosCgnv6LsnGlobalS 47 } 

		lidDrop OBJECT-TYPE
		SYNTAX  CounterBasedGauge64 
		MAX-ACCESS read-only 
		STATUS current
		DESCRIPTION  "LSN LID Drop" 
		::={ acosCgnv6LsnGlobalS 48 } 

		lidPassThrough OBJECT-TYPE
		SYNTAX  CounterBasedGauge64 
		MAX-ACCESS read-only 
		STATUS current
		DESCRIPTION  "LSN LID Pass-through" 
		::={ acosCgnv6LsnGlobalS 49 } 

		fullconeInDelQ OBJECT-TYPE
		SYNTAX  CounterBasedGauge64 
		MAX-ACCESS read-only 
		STATUS current
		DESCRIPTION  "Full-cone session found in delete queue" 
		::={ acosCgnv6LsnGlobalS 50 } 

		fullconeRetryLookup OBJECT-TYPE
		SYNTAX  CounterBasedGauge64 
		MAX-ACCESS read-only 
		STATUS current
		DESCRIPTION  "Full-cone session retry look-up" 
		::={ acosCgnv6LsnGlobalS 51 } 

		fullconeNotFound OBJECT-TYPE
		SYNTAX  CounterBasedGauge64 
		MAX-ACCESS read-only 
		STATUS current
		DESCRIPTION  "Full-cone session not found" 
		::={ acosCgnv6LsnGlobalS 52 } 

		natPortDoubleFree OBJECT-TYPE
		SYNTAX  CounterBasedGauge64 
		MAX-ACCESS read-only 
		STATUS current
		DESCRIPTION  "NAT Port Double Free" 
		::={ acosCgnv6LsnGlobalS 53 } 

		natPortChunkFreedFromCpu OBJECT-TYPE
		SYNTAX  CounterBasedGauge64 
		MAX-ACCESS read-only 
		STATUS current
		DESCRIPTION  "NAT Port Chunks Freed From CPU" 
		::={ acosCgnv6LsnGlobalS 54 } 

		natPortFreedFromDiffCpu OBJECT-TYPE
		SYNTAX  CounterBasedGauge64 
		MAX-ACCESS read-only 
		STATUS current
		DESCRIPTION  "NAT Port Freed On Different CPU" 
		::={ acosCgnv6LsnGlobalS 55 } 

		natPoolDeleted OBJECT-TYPE
		SYNTAX  CounterBasedGauge64 
		MAX-ACCESS read-only 
		STATUS current
		DESCRIPTION  "NAT Pool Deleted" 
		::={ acosCgnv6LsnGlobalS 56 } 

		natEspIpConflicts OBJECT-TYPE
		SYNTAX  CounterBasedGauge64 
		MAX-ACCESS read-only 
		STATUS current
		DESCRIPTION  "LSN NAT ESP IP Conflicts" 
		::={ acosCgnv6LsnGlobalS 57 } 

		natEspNoControlSesn OBJECT-TYPE
		SYNTAX  CounterBasedGauge64 
		MAX-ACCESS read-only 
		STATUS current
		DESCRIPTION  "LSN NAT ESP No Control Session" 
		::={ acosCgnv6LsnGlobalS 58 } 

		espUserQuotaExceeded OBJECT-TYPE
		SYNTAX  CounterBasedGauge64 
		MAX-ACCESS read-only 
		STATUS current
		DESCRIPTION  "ESP User-Quota exceeded" 
		::={ acosCgnv6LsnGlobalS 59 } 

		udpAlgUserQuotaExceeded OBJECT-TYPE
		SYNTAX  CounterBasedGauge64 
		MAX-ACCESS read-only 
		STATUS current
		DESCRIPTION  "UDP ALG User-Quota exceeded" 
		::={ acosCgnv6LsnGlobalS 60 } 

		greUserQuotaExceeded OBJECT-TYPE
		SYNTAX  CounterBasedGauge64 
		MAX-ACCESS read-only 
		STATUS current
		DESCRIPTION  "GRE User-Quota exceeded" 
		::={ acosCgnv6LsnGlobalS 61 } 

		haClasslistMismatch OBJECT-TYPE
		SYNTAX  CounterBasedGauge64 
		MAX-ACCESS read-only 
		STATUS current
		DESCRIPTION  "HA Class-list Mismatch" 
		::={ acosCgnv6LsnGlobalS 62 } 

		haUserQuotaMismatch OBJECT-TYPE
		SYNTAX  CounterBasedGauge64 
		MAX-ACCESS read-only 
		STATUS current
		DESCRIPTION  "HA User-Quota Mismatch" 
		::={ acosCgnv6LsnGlobalS 63 } 

		haFullconeMismatch OBJECT-TYPE
		SYNTAX  CounterBasedGauge64 
		MAX-ACCESS read-only 
		STATUS current
		DESCRIPTION  "HA Full-cone Mismatch" 
		::={ acosCgnv6LsnGlobalS 64 } 

		haPortMismatch OBJECT-TYPE
		SYNTAX  CounterBasedGauge64 
		MAX-ACCESS read-only 
		STATUS current
		DESCRIPTION  "HA Port Mismatch" 
		::={ acosCgnv6LsnGlobalS 65 } 

		haDnatMismatch OBJECT-TYPE
		SYNTAX  CounterBasedGauge64 
		MAX-ACCESS read-only 
		STATUS current
		DESCRIPTION  "HA Destination NAT Config Mismatch" 
		::={ acosCgnv6LsnGlobalS 66 } 

		haNatPortUnavailable OBJECT-TYPE
		SYNTAX  CounterBasedGauge64 
		MAX-ACCESS read-only 
		STATUS current
		DESCRIPTION  "HA NAT Port Unavailable" 
		::={ acosCgnv6LsnGlobalS 67 } 

		haUnknownNatIp OBJECT-TYPE
		SYNTAX  CounterBasedGauge64 
		MAX-ACCESS read-only 
		STATUS current
		DESCRIPTION  "HA Unknown NAT IP" 
		::={ acosCgnv6LsnGlobalS 68 } 

		haFullconeFailure OBJECT-TYPE
		SYNTAX  CounterBasedGauge64 
		MAX-ACCESS read-only 
		STATUS current
		DESCRIPTION  "HA Full-cone Session Failure" 
		::={ acosCgnv6LsnGlobalS 69 } 

		haFullconeCreateRaceFailure OBJECT-TYPE
		SYNTAX  CounterBasedGauge64 
		MAX-ACCESS read-only 
		STATUS current
		DESCRIPTION  "HA Full-cone Create Race Failure" 
		::={ acosCgnv6LsnGlobalS 70 } 

		haEndpointIndepMapMatch OBJECT-TYPE
		SYNTAX  CounterBasedGauge64 
		MAX-ACCESS read-only 
		STATUS current
		DESCRIPTION  "HA Endpoint-independent Matching" 
		::={ acosCgnv6LsnGlobalS 71 } 

		standbyClassListDrop OBJECT-TYPE
		SYNTAX  CounterBasedGauge64 
		MAX-ACCESS read-only 
		STATUS current
		DESCRIPTION  "HA Standby Class-List drop" 
		::={ acosCgnv6LsnGlobalS 72 } 

		badTupleNatIp OBJECT-TYPE
		SYNTAX  CounterBasedGauge64 
		MAX-ACCESS read-only 
		STATUS current
		DESCRIPTION  "Bad NAT IP from tuple" 
		::={ acosCgnv6LsnGlobalS 73 } 

		badSmpTupleNatIp OBJECT-TYPE
		SYNTAX  CounterBasedGauge64 
		MAX-ACCESS read-only 
		STATUS current
		DESCRIPTION  "Bad NAT IP from SMP tuple" 
		::={ acosCgnv6LsnGlobalS 74 } 

		fullconeInboundNatPoolMismatch OBJECT-TYPE
		SYNTAX  CounterBasedGauge64 
		MAX-ACCESS read-only 
		STATUS current
		DESCRIPTION  "Full-cone Session NAT Pool Mismatch" 
		::={ acosCgnv6LsnGlobalS 75 } 

		fullconeOverflowEim OBJECT-TYPE
		SYNTAX  CounterBasedGauge64 
		MAX-ACCESS read-only 
		STATUS current
		DESCRIPTION  "Full-cone Session EIM Overflow" 
		::={ acosCgnv6LsnGlobalS 76 } 

		fullconeOverflowEif OBJECT-TYPE
		SYNTAX  CounterBasedGauge64 
		MAX-ACCESS read-only 
		STATUS current
		DESCRIPTION  "Full-cone Session EIF Overflow" 
		::={ acosCgnv6LsnGlobalS 77 } 

		crossCpuHelperCreated OBJECT-TYPE
		SYNTAX  CounterBasedGauge64 
		MAX-ACCESS read-only 
		STATUS current
		DESCRIPTION  "Cross CPU Session Helper Created" 
		::={ acosCgnv6LsnGlobalS 78 } 

		crossCpuSent OBJECT-TYPE
		SYNTAX  CounterBasedGauge64 
		MAX-ACCESS read-only 
		STATUS current
		DESCRIPTION  "Cross CPU Helper Packets Sent" 
		::={ acosCgnv6LsnGlobalS 79 } 

		crossCpuRcv OBJECT-TYPE
		SYNTAX  CounterBasedGauge64 
		MAX-ACCESS read-only 
		STATUS current
		DESCRIPTION  "Cross CPU Helper Packets Received" 
		::={ acosCgnv6LsnGlobalS 80 } 

		crossCpuBadL3 OBJECT-TYPE
		SYNTAX  CounterBasedGauge64 
		MAX-ACCESS read-only 
		STATUS current
		DESCRIPTION  "Cross CPU Unsupported L3" 
		::={ acosCgnv6LsnGlobalS 81 } 

		crossCpuBadL4 OBJECT-TYPE
		SYNTAX  CounterBasedGauge64 
		MAX-ACCESS read-only 
		STATUS current
		DESCRIPTION  "Cross CPU Unsupported L4" 
		::={ acosCgnv6LsnGlobalS 82 } 

		crossCpuNoSession OBJECT-TYPE
		SYNTAX  CounterBasedGauge64 
		MAX-ACCESS read-only 
		STATUS current
		DESCRIPTION  "Cross CPU No Session Found" 
		::={ acosCgnv6LsnGlobalS 83 } 

		crossCpuHelperFree OBJECT-TYPE
		SYNTAX  CounterBasedGauge64 
		MAX-ACCESS read-only 
		STATUS current
		DESCRIPTION  "Cross CPU Helper Free" 
		::={ acosCgnv6LsnGlobalS 84 } 

		crossCpuHelperFreeRetryLookup OBJECT-TYPE
		SYNTAX  CounterBasedGauge64 
		MAX-ACCESS read-only 
		STATUS current
		DESCRIPTION  "Cross CPU Helper Free Retry Lookup" 
		::={ acosCgnv6LsnGlobalS 85 } 

		crossCpuHelperFreeNotFound OBJECT-TYPE
		SYNTAX  CounterBasedGauge64 
		MAX-ACCESS read-only 
		STATUS current
		DESCRIPTION  "Cross CPU Helper Free Not Found" 
		::={ acosCgnv6LsnGlobalS 86 } 

		crossCpuHelperDeleted OBJECT-TYPE
		SYNTAX  CounterBasedGauge64 
		MAX-ACCESS read-only 
		STATUS current
		DESCRIPTION  "Cross CPU Helper Deleted" 
		::={ acosCgnv6LsnGlobalS 87 } 

		crossCpuHelperCpuMismatch OBJECT-TYPE
		SYNTAX  CounterBasedGauge64 
		MAX-ACCESS read-only 
		STATUS current
		DESCRIPTION  "Cross CPU Helper CPU Mismatch" 
		::={ acosCgnv6LsnGlobalS 88 } 

		crossCpuHelperNatPoolStandby OBJECT-TYPE
		SYNTAX  CounterBasedGauge64 
		MAX-ACCESS read-only 
		STATUS current
		DESCRIPTION  "Cross CPU Helper NAT Pool Standby" 
		::={ acosCgnv6LsnGlobalS 89 } 

		crossCpuHelperDoubleAdd OBJECT-TYPE
		SYNTAX  CounterBasedGauge64 
		MAX-ACCESS read-only 
		STATUS current
		DESCRIPTION  "Cross CPU Helper Double Add Attempt" 
		::={ acosCgnv6LsnGlobalS 90 } 

		mtuExceeded OBJECT-TYPE
		SYNTAX  CounterBasedGauge64 
		MAX-ACCESS read-only 
		STATUS current
		DESCRIPTION  "Packet Exceeded MTU" 
		::={ acosCgnv6LsnGlobalS 91 } 

		frag OBJECT-TYPE
		SYNTAX  CounterBasedGauge64 
		MAX-ACCESS read-only 
		STATUS current
		DESCRIPTION  "Fragmented Packets" 
		::={ acosCgnv6LsnGlobalS 92 } 

		dsliteTunnelFrag OBJECT-TYPE
		SYNTAX  CounterBasedGauge64 
		MAX-ACCESS read-only 
		STATUS current
		DESCRIPTION  "IPv4 Fragment DS-Lite Packet" 
		::={ acosCgnv6LsnGlobalS 93 } 

		sixrdTunnelFrag OBJECT-TYPE
		SYNTAX  CounterBasedGauge64 
		MAX-ACCESS read-only 
		STATUS current
		DESCRIPTION  "IPv6 Fragment IPv6-in-IPv4 Packet" 
		::={ acosCgnv6LsnGlobalS 94 } 

		fragIcmp OBJECT-TYPE
		SYNTAX  CounterBasedGauge64 
		MAX-ACCESS read-only 
		STATUS current
		DESCRIPTION  "ICMP Packet Too Big Sent" 
		::={ acosCgnv6LsnGlobalS 95 } 

		fragTunnelIcmp OBJECT-TYPE
		SYNTAX  CounterBasedGauge64 
		MAX-ACCESS read-only 
		STATUS current
		DESCRIPTION  "DS-Lite ICMP Packet Too Big Sent" 
		::={ acosCgnv6LsnGlobalS 96 } 

		quotaExtMemAllocated OBJECT-TYPE
		SYNTAX  CounterBasedGauge64 
		MAX-ACCESS read-only 
		STATUS current
		DESCRIPTION  "Quota Extension Memory Allocated" 
		::={ acosCgnv6LsnGlobalS 97 } 

		quotaExtMemAllocFailure OBJECT-TYPE
		SYNTAX  CounterBasedGauge64 
		MAX-ACCESS read-only 
		STATUS current
		DESCRIPTION  "Quota Extension Out of Memory" 
		::={ acosCgnv6LsnGlobalS 98 } 

		quotaExtMemFreed OBJECT-TYPE
		SYNTAX  CounterBasedGauge64 
		MAX-ACCESS read-only 
		STATUS current
		DESCRIPTION  "Quota Extension Memory Freed" 
		::={ acosCgnv6LsnGlobalS 99 } 

		quotaExtPutInDelQ OBJECT-TYPE
		SYNTAX  CounterBasedGauge64 
		MAX-ACCESS read-only 
		STATUS current
		DESCRIPTION  "Quota Extension Put in Delete Queue" 
		::={ acosCgnv6LsnGlobalS 100 } 

		portBatchNumMismatch OBJECT-TYPE
		SYNTAX  CounterBasedGauge64 
		MAX-ACCESS read-only 
		STATUS current
		DESCRIPTION  "Specific Port Batch Num Ports Mismatch" 
		::={ acosCgnv6LsnGlobalS 101 } 

		portBatchIntervalMismatch OBJECT-TYPE
		SYNTAX  CounterBasedGauge64 
		MAX-ACCESS read-only 
		STATUS current
		DESCRIPTION  "Specific Port Batch Port Interval Mismatch" 
		::={ acosCgnv6LsnGlobalS 102 } 

		portPairAllocBadMath OBJECT-TYPE
		SYNTAX  CounterBasedGauge64 
		MAX-ACCESS read-only 
		STATUS current
		DESCRIPTION  "Port Pair Alloc Bad Math" 
		::={ acosCgnv6LsnGlobalS 103 } 

		freePortFromQuotaNoContainer OBJECT-TYPE
		SYNTAX  CounterBasedGauge64 
		MAX-ACCESS read-only 
		STATUS current
		DESCRIPTION  "Free Port from Quota No Container" 
		::={ acosCgnv6LsnGlobalS 104 } 

		freePortFromQuotaNoPortInfo OBJECT-TYPE
		SYNTAX  CounterBasedGauge64 
		MAX-ACCESS read-only 
		STATUS current
		DESCRIPTION  "Free Port From Quota No Port Info" 
		::={ acosCgnv6LsnGlobalS 105 } 

		staticNatCrossCpuHelperCreated OBJECT-TYPE
		SYNTAX  CounterBasedGauge64 
		MAX-ACCESS read-only 
		STATUS current
		DESCRIPTION  "Cross CPU Helper Created for Static NAT" 
		::={ acosCgnv6LsnGlobalS 106 } 

		staticNatCrossCpuHelperDeleted OBJECT-TYPE
		SYNTAX  CounterBasedGauge64 
		MAX-ACCESS read-only 
		STATUS current
		DESCRIPTION  "Cross CPU Helper Deleted for Static NAT" 
		::={ acosCgnv6LsnGlobalS 107 } 

		staticNatCrossCpuHelperStandby OBJECT-TYPE
		SYNTAX  CounterBasedGauge64 
		MAX-ACCESS read-only 
		STATUS current
		DESCRIPTION  "Cross CPU Helper Static NAT Standby" 
		::={ acosCgnv6LsnGlobalS 108 } 

		staticNatCrossCpuHelperCpuMismatch OBJECT-TYPE
		SYNTAX  CounterBasedGauge64 
		MAX-ACCESS read-only 
		STATUS current
		DESCRIPTION  "Static NAT Cross CPU Helper CPU Mismatch" 
		::={ acosCgnv6LsnGlobalS 109 } 

		staticNatCrossCpuSent OBJECT-TYPE
		SYNTAX  CounterBasedGauge64 
		MAX-ACCESS read-only 
		STATUS current
		DESCRIPTION  "Static NAT Cross CPU Helper Sent" 
		::={ acosCgnv6LsnGlobalS 110 } 

		staticNatCrossCpuRcv OBJECT-TYPE
		SYNTAX  CounterBasedGauge64 
		MAX-ACCESS read-only 
		STATUS current
		DESCRIPTION  "Static NAT Cross CPU Helper Packets Received" 
		::={ acosCgnv6LsnGlobalS 111 } 

		staticNatCrossCpuBadL3 OBJECT-TYPE
		SYNTAX  CounterBasedGauge64 
		MAX-ACCESS read-only 
		STATUS current
		DESCRIPTION  "Static NAT Cross CPU Unsupported L3" 
		::={ acosCgnv6LsnGlobalS 112 } 

		staticNatCrossCpuBadL4 OBJECT-TYPE
		SYNTAX  CounterBasedGauge64 
		MAX-ACCESS read-only 
		STATUS current
		DESCRIPTION  "Static NAT Cross CPU Unsupported L4" 
		::={ acosCgnv6LsnGlobalS 113 } 

		staticNatCrossCpuNoSession OBJECT-TYPE
		SYNTAX  CounterBasedGauge64 
		MAX-ACCESS read-only 
		STATUS current
		DESCRIPTION  "Static NAT Cross CPU No Session Found" 
		::={ acosCgnv6LsnGlobalS 114 } 

		staticNatCrossCpuHelperFree OBJECT-TYPE
		SYNTAX  CounterBasedGauge64 
		MAX-ACCESS read-only 
		STATUS current
		DESCRIPTION  "Static NAT Cross CPU Helper Free" 
		::={ acosCgnv6LsnGlobalS 115 } 

		staticNatCrossCpuHelperFreeRetryLookup OBJECT-TYPE
		SYNTAX  CounterBasedGauge64 
		MAX-ACCESS read-only 
		STATUS current
		DESCRIPTION  "Static NAT Cross CPU Helper Free Retry Lookup" 
		::={ acosCgnv6LsnGlobalS 116 } 

		staticNatCrossCpuHelperFreeNotFound OBJECT-TYPE
		SYNTAX  CounterBasedGauge64 
		MAX-ACCESS read-only 
		STATUS current
		DESCRIPTION  "Static NAT Cross CPU Helper Free Not Found" 
		::={ acosCgnv6LsnGlobalS 117 } 

		staticNatHaMapMismatch OBJECT-TYPE
		SYNTAX  CounterBasedGauge64 
		MAX-ACCESS read-only 
		STATUS current
		DESCRIPTION  "Static NAT Mapping Mismatch on HA Standby" 
		::={ acosCgnv6LsnGlobalS 118 } 

		ipSlbCrossCpuSent OBJECT-TYPE
		SYNTAX  CounterBasedGauge64 
		MAX-ACCESS read-only 
		STATUS current
		DESCRIPTION  "IP SLB Cross CPU Packets Sent" 
		::={ acosCgnv6LsnGlobalS 119 } 

		fullconeForceDeleted OBJECT-TYPE
		SYNTAX  CounterBasedGauge64 
		MAX-ACCESS read-only 
		STATUS current
		DESCRIPTION  "Full-cone Session Force Deleted" 
		::={ acosCgnv6LsnGlobalS 120 } 

		userQuotaMemAllocated OBJECT-TYPE
		SYNTAX  CounterBasedGauge64 
		MAX-ACCESS read-only 
		STATUS current
		DESCRIPTION  "User-Quota Memory Allocated" 
		::={ acosCgnv6LsnGlobalS 121 } 

		userQuotaMemFreed OBJECT-TYPE
		SYNTAX  CounterBasedGauge64 
		MAX-ACCESS read-only 
		STATUS current
		DESCRIPTION  "User-Quota Memory Freed" 
		::={ acosCgnv6LsnGlobalS 122 } 

		userQuotaCreatedShadow OBJECT-TYPE
		SYNTAX  CounterBasedGauge64 
		MAX-ACCESS read-only 
		STATUS current
		DESCRIPTION  "Total User-Quota Created" 
		::={ acosCgnv6LsnGlobalS 123 } 

		quotaMarkedDeleted OBJECT-TYPE
		SYNTAX  CounterBasedGauge64 
		MAX-ACCESS read-only 
		STATUS current
		DESCRIPTION  "User-Quota Marked Deleted" 
		::={ acosCgnv6LsnGlobalS 124 } 

		quotaDeleteNotInBucket OBJECT-TYPE
		SYNTAX  CounterBasedGauge64 
		MAX-ACCESS read-only 
		STATUS current
		DESCRIPTION  "User-Quota Delete Not In Bucket" 
		::={ acosCgnv6LsnGlobalS 125 } 

		userQuotaPutInDelQShadow OBJECT-TYPE
		SYNTAX  CounterBasedGauge64 
		MAX-ACCESS read-only 
		STATUS current
		DESCRIPTION  "Total User-Quota Put In Del Q" 
		::={ acosCgnv6LsnGlobalS 126 } 

		tcpOutOfStateRstSent OBJECT-TYPE
		SYNTAX  CounterBasedGauge64 
		MAX-ACCESS read-only 
		STATUS current
		DESCRIPTION  "Total Out of State TCP RST sent" 
		::={ acosCgnv6LsnGlobalS 127 } 

		tcpOutOfStateRstDropped OBJECT-TYPE
		SYNTAX  CounterBasedGauge64 
		MAX-ACCESS read-only 
		STATUS current
		DESCRIPTION  "Total Out of State TCP RST dropped" 
		::={ acosCgnv6LsnGlobalS 128 } 

		icmpOutOfStateUqeAdminFilteredSent OBJECT-TYPE
		SYNTAX  CounterBasedGauge64 
		MAX-ACCESS read-only 
		STATUS current
		DESCRIPTION  "Total User Quota Exceeded ICMP admin filtered sent" 
		::={ acosCgnv6LsnGlobalS 129 } 

		icmpOutOfStateUqeHostUnreachableSent OBJECT-TYPE
		SYNTAX  CounterBasedGauge64 
		MAX-ACCESS read-only 
		STATUS current
		DESCRIPTION  "Total User Quota Exceeded ICMP host unreachable sent" 
		::={ acosCgnv6LsnGlobalS 130 } 

		icmpOutOfStateUqeDropped OBJECT-TYPE
		SYNTAX  CounterBasedGauge64 
		MAX-ACCESS read-only 
		STATUS current
		DESCRIPTION  "Total User Queue Exceeded ICMP notification dropped" 
		::={ acosCgnv6LsnGlobalS 131 } 

		userQuotaNotFound OBJECT-TYPE
		SYNTAX  CounterBasedGauge64 
		MAX-ACCESS read-only 
		STATUS current
		DESCRIPTION  "User-Quota Not Found" 
		::={ acosCgnv6LsnGlobalS 132 } 

		tcpFullconeCreatedShadow OBJECT-TYPE
		SYNTAX  CounterBasedGauge64 
		MAX-ACCESS read-only 
		STATUS current
		DESCRIPTION  "Total TCP Full-cone sessions created" 
		::={ acosCgnv6LsnGlobalS 133 } 

		tcpFullconeFreedShadow OBJECT-TYPE
		SYNTAX  CounterBasedGauge64 
		MAX-ACCESS read-only 
		STATUS current
		DESCRIPTION  "Total TCP Full-cone sessions freed" 
		::={ acosCgnv6LsnGlobalS 134 } 

		udpFullconeCreatedShadow OBJECT-TYPE
		SYNTAX  CounterBasedGauge64 
		MAX-ACCESS read-only 
		STATUS current
		DESCRIPTION  "Total UDP Full-cone sessions created" 
		::={ acosCgnv6LsnGlobalS 135 } 

		udpFullconeFreedShadow OBJECT-TYPE
		SYNTAX  CounterBasedGauge64 
		MAX-ACCESS read-only 
		STATUS current
		DESCRIPTION  "Total UDP Full-cone sessions freed" 
		::={ acosCgnv6LsnGlobalS 136 } 

		udpAlgFullconeCreated OBJECT-TYPE
		SYNTAX  CounterBasedGauge64 
		MAX-ACCESS read-only 
		STATUS current
		DESCRIPTION  "Total UDP ALG Full-cone sessions created" 
		::={ acosCgnv6LsnGlobalS 137 } 

		udpAlgFullconeFreed OBJECT-TYPE
		SYNTAX  CounterBasedGauge64 
		MAX-ACCESS read-only 
		STATUS current
		DESCRIPTION  "Total UDP ALG Full-cone sessions freed" 
		::={ acosCgnv6LsnGlobalS 138 } 

		fullconeCreated OBJECT-TYPE
		SYNTAX  CounterBasedGauge64 
		MAX-ACCESS read-only 
		STATUS current
		DESCRIPTION  "Total Full-cone sessions created" 
		::={ acosCgnv6LsnGlobalS 139 } 

		fullconeFreed OBJECT-TYPE
		SYNTAX  CounterBasedGauge64 
		MAX-ACCESS read-only 
		STATUS current
		DESCRIPTION  "Total Full-cone sessions freed" 
		::={ acosCgnv6LsnGlobalS 140 } 

		dataSessionCreatedShadow OBJECT-TYPE
		SYNTAX  CounterBasedGauge64 
		MAX-ACCESS read-only 
		STATUS current
		DESCRIPTION  "Total Data Sessions Created" 
		::={ acosCgnv6LsnGlobalS 141 } 

		dataSessionFreedShadow OBJECT-TYPE
		SYNTAX  CounterBasedGauge64 
		MAX-ACCESS read-only 
		STATUS current
		DESCRIPTION  "Total Data Sessions Freed" 
		::={ acosCgnv6LsnGlobalS 142 } 

		dataSessionUserQuotaMismatch OBJECT-TYPE
		SYNTAX  CounterBasedGauge64 
		MAX-ACCESS read-only 
		STATUS current
		DESCRIPTION  "Data Session Counter Per User Mismatch" 
		::={ acosCgnv6LsnGlobalS 143 } 

		extendedQuotaMismatched OBJECT-TYPE
		SYNTAX  CounterBasedGauge64 
		MAX-ACCESS read-only 
		STATUS current
		DESCRIPTION  "Extended User-Quota Mismatched" 
		::={ acosCgnv6LsnGlobalS 144 } 

		natPortUnavailableOther OBJECT-TYPE
		SYNTAX  CounterBasedGauge64 
		MAX-ACCESS read-only 
		STATUS current
		DESCRIPTION  "Other NAT Port Unavailable" 
		::={ acosCgnv6LsnGlobalS 145 } 

		natPortUnavailable OBJECT-TYPE
		SYNTAX  CounterBasedGauge64 
		MAX-ACCESS read-only 
		STATUS current
		DESCRIPTION  "Total NAT Port Unavailable" 
		::={ acosCgnv6LsnGlobalS 146 } 

		newUserResourceUnavailableTcp OBJECT-TYPE
		SYNTAX  CounterBasedGauge64 
		MAX-ACCESS read-only 
		STATUS current
		DESCRIPTION  "TCP New User NAT Resource Unavailable" 
		::={ acosCgnv6LsnGlobalS 147 } 

		newUserResourceUnavailableUdp OBJECT-TYPE
		SYNTAX  CounterBasedGauge64 
		MAX-ACCESS read-only 
		STATUS current
		DESCRIPTION  "UDP New User NAT Resource Unavailable" 
		::={ acosCgnv6LsnGlobalS 148 } 

		newUserResourceUnavailableIcmp OBJECT-TYPE
		SYNTAX  CounterBasedGauge64 
		MAX-ACCESS read-only 
		STATUS current
		DESCRIPTION  "ICMP New User NAT Resource Unavailable" 
		::={ acosCgnv6LsnGlobalS 149 } 

		newUserResourceUnavailableOther OBJECT-TYPE
		SYNTAX  CounterBasedGauge64 
		MAX-ACCESS read-only 
		STATUS current
		DESCRIPTION  "Other New User NAT Resource Unavailable" 
		::={ acosCgnv6LsnGlobalS 150 } 

		totalTcpAllocatedShadow OBJECT-TYPE
		SYNTAX  CounterBasedGauge64 
		MAX-ACCESS read-only 
		STATUS current
		DESCRIPTION  "Total TCP Ports Allocated" 
		::={ acosCgnv6LsnGlobalS 151 } 

		totalTcpFreedShadow OBJECT-TYPE
		SYNTAX  CounterBasedGauge64 
		MAX-ACCESS read-only 
		STATUS current
		DESCRIPTION  "Total TCP Ports Freed" 
		::={ acosCgnv6LsnGlobalS 152 } 

		totalUdpAllocatedShadow OBJECT-TYPE
		SYNTAX  CounterBasedGauge64 
		MAX-ACCESS read-only 
		STATUS current
		DESCRIPTION  "Total UDP Ports Allocated" 
		::={ acosCgnv6LsnGlobalS 153 } 

		totalUdpFreedShadow OBJECT-TYPE
		SYNTAX  CounterBasedGauge64 
		MAX-ACCESS read-only 
		STATUS current
		DESCRIPTION  "Total UDP Ports Freed" 
		::={ acosCgnv6LsnGlobalS 154 } 

		totalIcmpAllocatedShadow OBJECT-TYPE
		SYNTAX  CounterBasedGauge64 
		MAX-ACCESS read-only 
		STATUS current
		DESCRIPTION  "Total ICMP Ports Allocated" 
		::={ acosCgnv6LsnGlobalS 155 } 

		totalIcmpFreedShadow OBJECT-TYPE
		SYNTAX  CounterBasedGauge64 
		MAX-ACCESS read-only 
		STATUS current
		DESCRIPTION  "Total ICMP Ports Freed" 
		::={ acosCgnv6LsnGlobalS 156 } 

		udpAlgNoQuota OBJECT-TYPE
		SYNTAX  CounterBasedGauge64 
		MAX-ACCESS read-only 
		STATUS current
		DESCRIPTION  "UDP ALG User-Quota Not Found" 
		::={ acosCgnv6LsnGlobalS 157 } 

		udpAlgEimMismatch OBJECT-TYPE
		SYNTAX  CounterBasedGauge64 
		MAX-ACCESS read-only 
		STATUS current
		DESCRIPTION  "UDP ALG Endpoint-Independent Mapping Mismatch" 
		::={ acosCgnv6LsnGlobalS 158 } 

		udpAlgNoNatIp OBJECT-TYPE
		SYNTAX  CounterBasedGauge64 
		MAX-ACCESS read-only 
		STATUS current
		DESCRIPTION  "UDP ALG User-Quota Unknown NAT IP" 
		::={ acosCgnv6LsnGlobalS 159 } 

		udpAlgAllocFailure OBJECT-TYPE
		SYNTAX  CounterBasedGauge64 
		MAX-ACCESS read-only 
		STATUS current
		DESCRIPTION  "UDP ALG Port Allocation Failure" 
		::={ acosCgnv6LsnGlobalS 160 } 

		sipAlgNoQuota OBJECT-TYPE
		SYNTAX  CounterBasedGauge64 
		MAX-ACCESS read-only 
		STATUS current
		DESCRIPTION  "SIP ALG User-Quota Not Found" 
		::={ acosCgnv6LsnGlobalS 161 } 

		sipAlgQuotaIncFailure OBJECT-TYPE
		SYNTAX  CounterBasedGauge64 
		MAX-ACCESS read-only 
		STATUS current
		DESCRIPTION  "SIP ALG User-Quota Exceeded" 
		::={ acosCgnv6LsnGlobalS 162 } 

		sipAlgNoNatIp OBJECT-TYPE
		SYNTAX  CounterBasedGauge64 
		MAX-ACCESS read-only 
		STATUS current
		DESCRIPTION  "SIP ALG Unknown NAT IP" 
		::={ acosCgnv6LsnGlobalS 163 } 

		sipAlgReuseContactFullcone OBJECT-TYPE
		SYNTAX  CounterBasedGauge64 
		MAX-ACCESS read-only 
		STATUS current
		DESCRIPTION  "SIP ALG Reuse Contact Full-cone Session" 
		::={ acosCgnv6LsnGlobalS 164 } 

		sipAlgContactFullconeMismatch OBJECT-TYPE
		SYNTAX  CounterBasedGauge64 
		MAX-ACCESS read-only 
		STATUS current
		DESCRIPTION  "SIP ALG Contact Full-cone Session Mismatch" 
		::={ acosCgnv6LsnGlobalS 165 } 

		sipAlgAllocContactPortFailure OBJECT-TYPE
		SYNTAX  CounterBasedGauge64 
		MAX-ACCESS read-only 
		STATUS current
		DESCRIPTION  "SIP ALG Alloc Contact NAT Port Failure" 
		::={ acosCgnv6LsnGlobalS 166 } 

		sipAlgCreateContactFullconeFailure OBJECT-TYPE
		SYNTAX  CounterBasedGauge64 
		MAX-ACCESS read-only 
		STATUS current
		DESCRIPTION  "SIP ALG Create Contact Full-cone Session Failure" 
		::={ acosCgnv6LsnGlobalS 167 } 

		sipAlgReleaseContactPortFailure OBJECT-TYPE
		SYNTAX  CounterBasedGauge64 
		MAX-ACCESS read-only 
		STATUS current
		DESCRIPTION  "SIP ALG Release Contact NAT Port Failure" 
		::={ acosCgnv6LsnGlobalS 168 } 

		sipAlgSingleRtpFullcone OBJECT-TYPE
		SYNTAX  CounterBasedGauge64 
		MAX-ACCESS read-only 
		STATUS current
		DESCRIPTION  "SIP ALG Single RTP Full-cone Found" 
		::={ acosCgnv6LsnGlobalS 169 } 

		sipAlgSingleRtcpFullcone OBJECT-TYPE
		SYNTAX  CounterBasedGauge64 
		MAX-ACCESS read-only 
		STATUS current
		DESCRIPTION  "SIP ALG Single RTCP Full-cone Found" 
		::={ acosCgnv6LsnGlobalS 170 } 

		sipAlgRtcpFullconeMismatch OBJECT-TYPE
		SYNTAX  CounterBasedGauge64 
		MAX-ACCESS read-only 
		STATUS current
		DESCRIPTION  "SIP ALG RTCP Full-cone NAT Port Mismatch" 
		::={ acosCgnv6LsnGlobalS 171 } 

		sipAlgReuseRtpRtcpFullcone OBJECT-TYPE
		SYNTAX  CounterBasedGauge64 
		MAX-ACCESS read-only 
		STATUS current
		DESCRIPTION  "SIP ALG Reuse RTP/RTCP Full-cone Session" 
		::={ acosCgnv6LsnGlobalS 172 } 

		sipAlgAllocRtpRtcpPortFailure OBJECT-TYPE
		SYNTAX  CounterBasedGauge64 
		MAX-ACCESS read-only 
		STATUS current
		DESCRIPTION  "SIP ALG Alloc RTP/RTCP NAT Ports Failure" 
		::={ acosCgnv6LsnGlobalS 173 } 

		sipAlgAllocSinglePortFailure OBJECT-TYPE
		SYNTAX  CounterBasedGauge64 
		MAX-ACCESS read-only 
		STATUS current
		DESCRIPTION  "SIP ALG Alloc Single RTP or RTCP NAT Port Failure" 
		::={ acosCgnv6LsnGlobalS 174 } 

		sipAlgCreateSingleFullconeFailure OBJECT-TYPE
		SYNTAX  CounterBasedGauge64 
		MAX-ACCESS read-only 
		STATUS current
		DESCRIPTION  "SIP ALG Create Single RTP or RTCP Full-cone Session Failure" 
		::={ acosCgnv6LsnGlobalS 175 } 

		sipAlgCreateRtpFullconeFailure OBJECT-TYPE
		SYNTAX  CounterBasedGauge64 
		MAX-ACCESS read-only 
		STATUS current
		DESCRIPTION  "SIP ALG Create RTP Full-cone Session Failure" 
		::={ acosCgnv6LsnGlobalS 176 } 

		sipAlgCreateRtcpFullconeFailure OBJECT-TYPE
		SYNTAX  CounterBasedGauge64 
		MAX-ACCESS read-only 
		STATUS current
		DESCRIPTION  "SIP ALG Create RTCP Full-cone Session Failure" 
		::={ acosCgnv6LsnGlobalS 177 } 

		sipAlgPortPairAllocFromConsecutive OBJECT-TYPE
		SYNTAX  CounterBasedGauge64 
		MAX-ACCESS read-only 
		STATUS current
		DESCRIPTION  "SIP ALG Port Pair Allocated From Consecutive" 
		::={ acosCgnv6LsnGlobalS 178 } 

		sipAlgPortPairAllocFromPartition OBJECT-TYPE
		SYNTAX  CounterBasedGauge64 
		MAX-ACCESS read-only 
		STATUS current
		DESCRIPTION  "SIP ALG Port Pair Allocated From Partition" 
		::={ acosCgnv6LsnGlobalS 179 } 

		sipAlgPortPairAllocFromPoolPortBatch OBJECT-TYPE
		SYNTAX  CounterBasedGauge64 
		MAX-ACCESS read-only 
		STATUS current
		DESCRIPTION  "SIP ALG Port Pair Allocated From Pool Port Batch" 
		::={ acosCgnv6LsnGlobalS 180 } 

		sipAlgPortPairAllocFromQuotaConsecutive OBJECT-TYPE
		SYNTAX  CounterBasedGauge64 
		MAX-ACCESS read-only 
		STATUS current
		DESCRIPTION  "SIP ALG Port Pair Allocated From Quota Consecutive" 
		::={ acosCgnv6LsnGlobalS 181 } 

		sipAlgPortPairAllocFromQuotaPartition OBJECT-TYPE
		SYNTAX  CounterBasedGauge64 
		MAX-ACCESS read-only 
		STATUS current
		DESCRIPTION  "SIP ALG Port Pair Allocated From Quota Partition" 
		::={ acosCgnv6LsnGlobalS 182 } 

		sipAlgPortPairAllocFromQuotaPartitionError OBJECT-TYPE
		SYNTAX  CounterBasedGauge64 
		MAX-ACCESS read-only 
		STATUS current
		DESCRIPTION  "SIP ALG Port Pair Allocated From Quota Partition Error" 
		::={ acosCgnv6LsnGlobalS 183 } 

		sipAlgPortPairAllocFromQuotaPoolPortBatch OBJECT-TYPE
		SYNTAX  CounterBasedGauge64 
		MAX-ACCESS read-only 
		STATUS current
		DESCRIPTION  "SIP ALG Port Pair Allocated From Quota Pool Port Batch" 
		::={ acosCgnv6LsnGlobalS 184 } 

		sipAlgPortPairAllocFromQuotaPoolPortBatchWithFrag OBJECT-TYPE
		SYNTAX  CounterBasedGauge64 
		MAX-ACCESS read-only 
		STATUS current
		DESCRIPTION  "SIP ALG Port Pair Allocated From Quota Port Batch Version 2 with Frag Free Ports" 
		::={ acosCgnv6LsnGlobalS 185 } 

		h323AlgNoQuota OBJECT-TYPE
		SYNTAX  CounterBasedGauge64 
		MAX-ACCESS read-only 
		STATUS current
		DESCRIPTION  "H323 ALG User-Quota Not Found" 
		::={ acosCgnv6LsnGlobalS 186 } 

		h323AlgQuotaIncFailure OBJECT-TYPE
		SYNTAX  CounterBasedGauge64 
		MAX-ACCESS read-only 
		STATUS current
		DESCRIPTION  "H323 ALG User-Quota Exceeded" 
		::={ acosCgnv6LsnGlobalS 187 } 

		h323AlgNoNatIp OBJECT-TYPE
		SYNTAX  CounterBasedGauge64 
		MAX-ACCESS read-only 
		STATUS current
		DESCRIPTION  "H323 ALG Unknown NAT IP" 
		::={ acosCgnv6LsnGlobalS 188 } 

		h323AlgReuseFullcone OBJECT-TYPE
		SYNTAX  CounterBasedGauge64 
		MAX-ACCESS read-only 
		STATUS current
		DESCRIPTION  "H323 ALG Reuse Full-cone Session" 
		::={ acosCgnv6LsnGlobalS 189 } 

		h323AlgFullconeMismatch OBJECT-TYPE
		SYNTAX  CounterBasedGauge64 
		MAX-ACCESS read-only 
		STATUS current
		DESCRIPTION  "H323 ALG Full-cone Session Mismatch" 
		::={ acosCgnv6LsnGlobalS 190 } 

		h323AlgAllocPortFailure OBJECT-TYPE
		SYNTAX  CounterBasedGauge64 
		MAX-ACCESS read-only 
		STATUS current
		DESCRIPTION  "H323 ALG Alloc NAT Port Failure" 
		::={ acosCgnv6LsnGlobalS 191 } 

		h323AlgCreateFullconeFailure OBJECT-TYPE
		SYNTAX  CounterBasedGauge64 
		MAX-ACCESS read-only 
		STATUS current
		DESCRIPTION  "H323 ALG Create Full-cone Session Failure" 
		::={ acosCgnv6LsnGlobalS 192 } 

		h323AlgReleasePortFailure OBJECT-TYPE
		SYNTAX  CounterBasedGauge64 
		MAX-ACCESS read-only 
		STATUS current
		DESCRIPTION  "H323 ALG Release NAT Port Failure" 
		::={ acosCgnv6LsnGlobalS 193 } 

		h323AlgSingleRtpFullcone OBJECT-TYPE
		SYNTAX  CounterBasedGauge64 
		MAX-ACCESS read-only 
		STATUS current
		DESCRIPTION  "H323 ALG Single RTP Full-cone Found" 
		::={ acosCgnv6LsnGlobalS 194 } 

		h323AlgSingleRtcpFullcone OBJECT-TYPE
		SYNTAX  CounterBasedGauge64 
		MAX-ACCESS read-only 
		STATUS current
		DESCRIPTION  "H323 ALG Single RTCP Full-cone Found" 
		::={ acosCgnv6LsnGlobalS 195 } 

		h323AlgRtcpFullconeMismatch OBJECT-TYPE
		SYNTAX  CounterBasedGauge64 
		MAX-ACCESS read-only 
		STATUS current
		DESCRIPTION  "H323 ALG RTCP Full-cone NAT Port Mismatch" 
		::={ acosCgnv6LsnGlobalS 196 } 

		h323AlgReuseRtpRtcpFullcone OBJECT-TYPE
		SYNTAX  CounterBasedGauge64 
		MAX-ACCESS read-only 
		STATUS current
		DESCRIPTION  "H323 ALG Reuse RTP/RTCP Full-cone Session" 
		::={ acosCgnv6LsnGlobalS 197 } 

		h323AlgAllocRtpRtcpPortFailure OBJECT-TYPE
		SYNTAX  CounterBasedGauge64 
		MAX-ACCESS read-only 
		STATUS current
		DESCRIPTION  "H323 ALG Alloc RTP/RTCP NAT Ports Failure" 
		::={ acosCgnv6LsnGlobalS 198 } 

		h323AlgAllocSinglePortFailure OBJECT-TYPE
		SYNTAX  CounterBasedGauge64 
		MAX-ACCESS read-only 
		STATUS current
		DESCRIPTION  "H323 ALG Alloc Single RTP or RTCP NAT Port Failure" 
		::={ acosCgnv6LsnGlobalS 199 } 

		h323AlgCreateSingleFullconeFailure OBJECT-TYPE
		SYNTAX  CounterBasedGauge64 
		MAX-ACCESS read-only 
		STATUS current
		DESCRIPTION  "H323 ALG Create Single RTP or RTCP Full-cone Session Failure" 
		::={ acosCgnv6LsnGlobalS 200 } 

		h323AlgCreateRtpFullconeFailure OBJECT-TYPE
		SYNTAX  CounterBasedGauge64 
		MAX-ACCESS read-only 
		STATUS current
		DESCRIPTION  "H323 ALG Create RTP Full-cone Session Failure" 
		::={ acosCgnv6LsnGlobalS 201 } 

		h323AlgCreateRtcpFullconeFailure OBJECT-TYPE
		SYNTAX  CounterBasedGauge64 
		MAX-ACCESS read-only 
		STATUS current
		DESCRIPTION  "H323 ALG Create RTCP Full-cone Session Failure" 
		::={ acosCgnv6LsnGlobalS 202 } 

		h323AlgPortPairAllocFromConsecutive OBJECT-TYPE
		SYNTAX  CounterBasedGauge64 
		MAX-ACCESS read-only 
		STATUS current
		DESCRIPTION  "H323 ALG Port Pair Allocated From Consecutive" 
		::={ acosCgnv6LsnGlobalS 203 } 

		h323AlgPortPairAllocFromPartition OBJECT-TYPE
		SYNTAX  CounterBasedGauge64 
		MAX-ACCESS read-only 
		STATUS current
		DESCRIPTION  "H323 ALG Port Pair Allocated From Partition" 
		::={ acosCgnv6LsnGlobalS 204 } 

		h323AlgPortPairAllocFromPoolPortBatch OBJECT-TYPE
		SYNTAX  CounterBasedGauge64 
		MAX-ACCESS read-only 
		STATUS current
		DESCRIPTION  "H323 ALG Port Pair Allocated From Pool Port Batch" 
		::={ acosCgnv6LsnGlobalS 205 } 

		h323AlgPortPairAllocFromQuotaConsecutive OBJECT-TYPE
		SYNTAX  CounterBasedGauge64 
		MAX-ACCESS read-only 
		STATUS current
		DESCRIPTION  "H323 ALG Port Pair Allocated From Quota Consecutive" 
		::={ acosCgnv6LsnGlobalS 206 } 

		h323AlgPortPairAllocFromQuotaPartition OBJECT-TYPE
		SYNTAX  CounterBasedGauge64 
		MAX-ACCESS read-only 
		STATUS current
		DESCRIPTION  "H323 ALG Port Pair Allocated From Quota Partition" 
		::={ acosCgnv6LsnGlobalS 207 } 

		h323AlgPortPairAllocFromQuotaPartitionError OBJECT-TYPE
		SYNTAX  CounterBasedGauge64 
		MAX-ACCESS read-only 
		STATUS current
		DESCRIPTION  "H323 ALG Port Pair Allocated From Quota Partition Error" 
		::={ acosCgnv6LsnGlobalS 208 } 

		h323AlgPortPairAllocFromQuotaPoolPortBatch OBJECT-TYPE
		SYNTAX  CounterBasedGauge64 
		MAX-ACCESS read-only 
		STATUS current
		DESCRIPTION  "H323 ALG Port Pair Allocated From Quota Pool Port Batch" 
		::={ acosCgnv6LsnGlobalS 209 } 

		portBatchQuotaExtensionAllocFailure OBJECT-TYPE
		SYNTAX  CounterBasedGauge64 
		MAX-ACCESS read-only 
		STATUS current
		DESCRIPTION  "Port Batch Extension Alloc Failure (No memory)" 
		::={ acosCgnv6LsnGlobalS 210 } 

		portBatchFreeQuotaNotFound OBJECT-TYPE
		SYNTAX  CounterBasedGauge64 
		MAX-ACCESS read-only 
		STATUS current
		DESCRIPTION  "Port Batch Quota Not Found on Free" 
		::={ acosCgnv6LsnGlobalS 211 } 

		portBatchFreePortNotFound OBJECT-TYPE
		SYNTAX  CounterBasedGauge64 
		MAX-ACCESS read-only 
		STATUS current
		DESCRIPTION  "Port Batch Port Not Found on Free" 
		::={ acosCgnv6LsnGlobalS 212 } 

		portBatchFreeWrongPartition OBJECT-TYPE
		SYNTAX  CounterBasedGauge64 
		MAX-ACCESS read-only 
		STATUS current
		DESCRIPTION  "Port Batch Free Wrong Partition" 
		::={ acosCgnv6LsnGlobalS 213 } 

		radiusQueryQuotaExtAllocFailure OBJECT-TYPE
		SYNTAX  CounterBasedGauge64 
		MAX-ACCESS read-only 
		STATUS current
		DESCRIPTION  "RADIUS Query Container Alloc (No Memoty)" 
		::={ acosCgnv6LsnGlobalS 214 } 

		radiusQueryQuotaExtAllocRaceFree OBJECT-TYPE
		SYNTAX  CounterBasedGauge64 
		MAX-ACCESS read-only 
		STATUS current
		DESCRIPTION  "RADIUS Query Container Alloc Race Free" 
		::={ acosCgnv6LsnGlobalS 215 } 

		quotaExtensionAdded OBJECT-TYPE
		SYNTAX  CounterBasedGauge64 
		MAX-ACCESS read-only 
		STATUS current
		DESCRIPTION  "Quota Extension Added to Quota" 
		::={ acosCgnv6LsnGlobalS 216 } 

		quotaExtensionRemoved OBJECT-TYPE
		SYNTAX  CounterBasedGauge64 
		MAX-ACCESS read-only 
		STATUS current
		DESCRIPTION  "Quota Extension Removed from Quota" 
		::={ acosCgnv6LsnGlobalS 217 } 

		quotaExtensionRemoveNotFound OBJECT-TYPE
		SYNTAX  CounterBasedGauge64 
		MAX-ACCESS read-only 
		STATUS current
		DESCRIPTION  "Quota Extension Not Found on Remove" 
		::={ acosCgnv6LsnGlobalS 218 } 

		haSyncPortBatchSent OBJECT-TYPE
		SYNTAX  CounterBasedGauge64 
		MAX-ACCESS read-only 
		STATUS current
		DESCRIPTION  "HA Port Batch Extension Sync Sent" 
		::={ acosCgnv6LsnGlobalS 219 } 

		haSyncPortBatchRcv OBJECT-TYPE
		SYNTAX  CounterBasedGauge64 
		MAX-ACCESS read-only 
		STATUS current
		DESCRIPTION  "HA Port Batch Extension Sync Received" 
		::={ acosCgnv6LsnGlobalS 220 } 

		haSendPortBatchNotFound OBJECT-TYPE
		SYNTAX  CounterBasedGauge64 
		MAX-ACCESS read-only 
		STATUS current
		DESCRIPTION  "HA Port Batch Not Found on Sync Send" 
		::={ acosCgnv6LsnGlobalS 221 } 

		haRcvPortNotInPortBatch OBJECT-TYPE
		SYNTAX  CounterBasedGauge64 
		MAX-ACCESS read-only 
		STATUS current
		DESCRIPTION  "HA Port Not in Port Batch on Sync Rcv" 
		::={ acosCgnv6LsnGlobalS 222 } 

		badPortToFree OBJECT-TYPE
		SYNTAX  CounterBasedGauge64 
		MAX-ACCESS read-only 
		STATUS current
		DESCRIPTION  "Freeing Bad Port" 
		::={ acosCgnv6LsnGlobalS 223 } 

		consecutivePortFree OBJECT-TYPE
		SYNTAX  CounterBasedGauge64 
		MAX-ACCESS read-only 
		STATUS current
		DESCRIPTION  "Port Freed from Consecutive Pool" 
		::={ acosCgnv6LsnGlobalS 224 } 

		partitionPortFree OBJECT-TYPE
		SYNTAX  CounterBasedGauge64 
		MAX-ACCESS read-only 
		STATUS current
		DESCRIPTION  "Port Freed from Partition" 
		::={ acosCgnv6LsnGlobalS 225 } 

		poolPortBatchPortFree OBJECT-TYPE
		SYNTAX  CounterBasedGauge64 
		MAX-ACCESS read-only 
		STATUS current
		DESCRIPTION  "Port Freed from Pool Port Batch" 
		::={ acosCgnv6LsnGlobalS 226 } 

		portAllocatedFromQuotaConsecutive OBJECT-TYPE
		SYNTAX  CounterBasedGauge64 
		MAX-ACCESS read-only 
		STATUS current
		DESCRIPTION  "Port Allocated from Quota Consecutive" 
		::={ acosCgnv6LsnGlobalS 227 } 

		portAllocatedFromQuotaPartition OBJECT-TYPE
		SYNTAX  CounterBasedGauge64 
		MAX-ACCESS read-only 
		STATUS current
		DESCRIPTION  "Port Allocated from Quota Partition" 
		::={ acosCgnv6LsnGlobalS 228 } 

		portAllocatedFromQuotaPoolPortBatch OBJECT-TYPE
		SYNTAX  CounterBasedGauge64 
		MAX-ACCESS read-only 
		STATUS current
		DESCRIPTION  "Port Allocated from Quota Pool Port Batch" 
		::={ acosCgnv6LsnGlobalS 229 } 

		portFreedFromQuotaConsecutive OBJECT-TYPE
		SYNTAX  CounterBasedGauge64 
		MAX-ACCESS read-only 
		STATUS current
		DESCRIPTION  "Port Freed from Quota Consecutive" 
		::={ acosCgnv6LsnGlobalS 230 } 

		portFreedFromQuotaPartition OBJECT-TYPE
		SYNTAX  CounterBasedGauge64 
		MAX-ACCESS read-only 
		STATUS current
		DESCRIPTION  "Port Freed from Quota Partition" 
		::={ acosCgnv6LsnGlobalS 231 } 

		portFreedFromQuotaPoolPortBatch OBJECT-TYPE
		SYNTAX  CounterBasedGauge64 
		MAX-ACCESS read-only 
		STATUS current
		DESCRIPTION  "Port Freed from Quota Pool Port Batch" 
		::={ acosCgnv6LsnGlobalS 232 } 

		portBatchAllocatedToQuota OBJECT-TYPE
		SYNTAX  CounterBasedGauge64 
		MAX-ACCESS read-only 
		STATUS current
		DESCRIPTION  "Port Batch Allocated to Quota" 
		::={ acosCgnv6LsnGlobalS 233 } 

		portBatchFreedFromQuota OBJECT-TYPE
		SYNTAX  CounterBasedGauge64 
		MAX-ACCESS read-only 
		STATUS current
		DESCRIPTION  "Port Batch Freed From Quota" 
		::={ acosCgnv6LsnGlobalS 234 } 

		specificPortAllocatedFromQuotaConsecutive OBJECT-TYPE
		SYNTAX  CounterBasedGauge64 
		MAX-ACCESS read-only 
		STATUS current
		DESCRIPTION  "Specific Port Allocated from Quota Consecutive" 
		::={ acosCgnv6LsnGlobalS 235 } 

		specificPortAllocatedFromQuotaPartition OBJECT-TYPE
		SYNTAX  CounterBasedGauge64 
		MAX-ACCESS read-only 
		STATUS current
		DESCRIPTION  "Specific Port Allocated from Quota Partition" 
		::={ acosCgnv6LsnGlobalS 236 } 

		specificPortAllocatedFromQuotaPoolPortBatch OBJECT-TYPE
		SYNTAX  CounterBasedGauge64 
		MAX-ACCESS read-only 
		STATUS current
		DESCRIPTION  "Specific Port Allocated from Quota Pool Port Batch" 
		::={ acosCgnv6LsnGlobalS 237 } 

		portBatchContainerAllocFailure OBJECT-TYPE
		SYNTAX  CounterBasedGauge64 
		MAX-ACCESS read-only 
		STATUS current
		DESCRIPTION  "Port Batch Container Alloc Out of Memory" 
		::={ acosCgnv6LsnGlobalS 238 } 

		portBatchContainerAllocRaceFree OBJECT-TYPE
		SYNTAX  CounterBasedGauge64 
		MAX-ACCESS read-only 
		STATUS current
		DESCRIPTION  "Port Batch Container Race Free" 
		::={ acosCgnv6LsnGlobalS 239 } 

		portOverloadingDestinationConflict OBJECT-TYPE
		SYNTAX  CounterBasedGauge64 
		MAX-ACCESS read-only 
		STATUS current
		DESCRIPTION  "Port Overloading Destination Conflict" 
		::={ acosCgnv6LsnGlobalS 240 } 

		portOverloadingOutOfMemory OBJECT-TYPE
		SYNTAX  CounterBasedGauge64 
		MAX-ACCESS read-only 
		STATUS current
		DESCRIPTION  "Port Overloading Out of Memory" 
		::={ acosCgnv6LsnGlobalS 241 } 

		portOverloadingAssignUser OBJECT-TYPE
		SYNTAX  CounterBasedGauge64 
		MAX-ACCESS read-only 
		STATUS current
		DESCRIPTION  "Port Overloading Port Assign User" 
		::={ acosCgnv6LsnGlobalS 242 } 

		portOverloadingAssignUserPortBatch OBJECT-TYPE
		SYNTAX  CounterBasedGauge64 
		MAX-ACCESS read-only 
		STATUS current
		DESCRIPTION  "Port Overloading Port Assign User Port Batch" 
		::={ acosCgnv6LsnGlobalS 243 } 

		portOverloadingInc OBJECT-TYPE
		SYNTAX  CounterBasedGauge64 
		MAX-ACCESS read-only 
		STATUS current
		DESCRIPTION  "Port Overloading Port Increment" 
		::={ acosCgnv6LsnGlobalS 244 } 

		portOverloadingDecOnConflict OBJECT-TYPE
		SYNTAX  CounterBasedGauge64 
		MAX-ACCESS read-only 
		STATUS current
		DESCRIPTION  "Port Overloading Port Decrement on Conflict" 
		::={ acosCgnv6LsnGlobalS 245 } 

		portOverloadingDecOnFree OBJECT-TYPE
		SYNTAX  CounterBasedGauge64 
		MAX-ACCESS read-only 
		STATUS current
		DESCRIPTION  "Port Overloading Port Decrement on Free" 
		::={ acosCgnv6LsnGlobalS 246 } 

		portOverloadingFreePortOnConflict OBJECT-TYPE
		SYNTAX  CounterBasedGauge64 
		MAX-ACCESS read-only 
		STATUS current
		DESCRIPTION  "Port Overloading Free Port on Conflict" 
		::={ acosCgnv6LsnGlobalS 247 } 

		portOverloadingFreePortBatchOnConflict OBJECT-TYPE
		SYNTAX  CounterBasedGauge64 
		MAX-ACCESS read-only 
		STATUS current
		DESCRIPTION  "Port Overloading Free Port Batch on Conflict" 
		::={ acosCgnv6LsnGlobalS 248 } 

		portOverloadingIncOverflow OBJECT-TYPE
		SYNTAX  CounterBasedGauge64 
		MAX-ACCESS read-only 
		STATUS current
		DESCRIPTION  "Port Overloading Inc Overflow" 
		::={ acosCgnv6LsnGlobalS 249 } 

		portOverloadingAttemptConsecutivePorts OBJECT-TYPE
		SYNTAX  CounterBasedGauge64 
		MAX-ACCESS read-only 
		STATUS current
		DESCRIPTION  "Port Overloading on Consecutive Ports" 
		::={ acosCgnv6LsnGlobalS 250 } 

		portOverloadingAttemptSamePartition OBJECT-TYPE
		SYNTAX  CounterBasedGauge64 
		MAX-ACCESS read-only 
		STATUS current
		DESCRIPTION  "Port Overloading on Same Partition" 
		::={ acosCgnv6LsnGlobalS 251 } 

		portOverloadingAttemptDiffPartition OBJECT-TYPE
		SYNTAX  CounterBasedGauge64 
		MAX-ACCESS read-only 
		STATUS current
		DESCRIPTION  "Port Overloading on Different Partition" 
		::={ acosCgnv6LsnGlobalS 252 } 

		portOverloadingAttemptFailed OBJECT-TYPE
		SYNTAX  CounterBasedGauge64 
		MAX-ACCESS read-only 
		STATUS current
		DESCRIPTION  "Port Overloading Attempt Failed" 
		::={ acosCgnv6LsnGlobalS 253 } 

		portOverloadingConnFreeRetryLookup OBJECT-TYPE
		SYNTAX  CounterBasedGauge64 
		MAX-ACCESS read-only 
		STATUS current
		DESCRIPTION  "Port Overloading Conn Free Retry Lookup" 
		::={ acosCgnv6LsnGlobalS 254 } 

		portOverloadingConnFreeNotFound OBJECT-TYPE
		SYNTAX  CounterBasedGauge64 
		MAX-ACCESS read-only 
		STATUS current
		DESCRIPTION  "Port Overloading Conn Free Not Found" 
		::={ acosCgnv6LsnGlobalS 255 } 

		portOverloadingSmpMemAllocated OBJECT-TYPE
		SYNTAX  CounterBasedGauge64 
		MAX-ACCESS read-only 
		STATUS current
		DESCRIPTION  "Port Overloading SMP Session Allocated" 
		::={ acosCgnv6LsnGlobalS 256 } 

		portOverloadingSmpMemFreed OBJECT-TYPE
		SYNTAX  CounterBasedGauge64 
		MAX-ACCESS read-only 
		STATUS current
		DESCRIPTION  "Port Overloading SMP Session Freed" 
		::={ acosCgnv6LsnGlobalS 257 } 

		portOverloadingSmpInserted OBJECT-TYPE
		SYNTAX  CounterBasedGauge64 
		MAX-ACCESS read-only 
		STATUS current
		DESCRIPTION  "Port Overloading SMP Inserted" 
		::={ acosCgnv6LsnGlobalS 258 } 

		portOverloadingSmpInsertedTcpShadow OBJECT-TYPE
		SYNTAX  CounterBasedGauge64 
		MAX-ACCESS read-only 
		STATUS current
		DESCRIPTION  "Total Port Overloading SMP TCP Inserted" 
		::={ acosCgnv6LsnGlobalS 259 } 

		portOverloadingSmpInsertedUdpShadow OBJECT-TYPE
		SYNTAX  CounterBasedGauge64 
		MAX-ACCESS read-only 
		STATUS current
		DESCRIPTION  "Total Port Overloading SMP UDP Inserted" 
		::={ acosCgnv6LsnGlobalS 260 } 

		portOverloadingSmpFreeTcpShadow OBJECT-TYPE
		SYNTAX  CounterBasedGauge64 
		MAX-ACCESS read-only 
		STATUS current
		DESCRIPTION  "Total Port Overloading SMP TCP Freed" 
		::={ acosCgnv6LsnGlobalS 261 } 

		portOverloadingSmpFreeUdpShadow OBJECT-TYPE
		SYNTAX  CounterBasedGauge64 
		MAX-ACCESS read-only 
		STATUS current
		DESCRIPTION  "Total Port Overloading SMP UDP Freed" 
		::={ acosCgnv6LsnGlobalS 262 } 

		portOverloadingSmpPutInDelQFromConn OBJECT-TYPE
		SYNTAX  CounterBasedGauge64 
		MAX-ACCESS read-only 
		STATUS current
		DESCRIPTION  "Port Overloading SMP Free From Conn" 
		::={ acosCgnv6LsnGlobalS 263 } 

		portOverloadingSmpFreeDecFailure OBJECT-TYPE
		SYNTAX  CounterBasedGauge64 
		MAX-ACCESS read-only 
		STATUS current
		DESCRIPTION  "Port Overloading SMP Free Dec Failure" 
		::={ acosCgnv6LsnGlobalS 264 } 

		portOverloadingSmpFreeNoQuota OBJECT-TYPE
		SYNTAX  CounterBasedGauge64 
		MAX-ACCESS read-only 
		STATUS current
		DESCRIPTION  "Port Overloading SMP Free No Quota" 
		::={ acosCgnv6LsnGlobalS 265 } 

		portOverloadingSmpFreePort OBJECT-TYPE
		SYNTAX  CounterBasedGauge64 
		MAX-ACCESS read-only 
		STATUS current
		DESCRIPTION  "Port Overloading SMP Free Port" 
		::={ acosCgnv6LsnGlobalS 266 } 

		portOverloadingSmpFreePortFromQuota OBJECT-TYPE
		SYNTAX  CounterBasedGauge64 
		MAX-ACCESS read-only 
		STATUS current
		DESCRIPTION  "Port Overloading SMP Free Port From Quota" 
		::={ acosCgnv6LsnGlobalS 267 } 

		portOverloadingForNoPorts OBJECT-TYPE
		SYNTAX  CounterBasedGauge64 
		MAX-ACCESS read-only 
		STATUS current
		DESCRIPTION  "Port Overloading for No Ports" 
		::={ acosCgnv6LsnGlobalS 268 } 

		portOverloadingForNoPortsSuccess OBJECT-TYPE
		SYNTAX  CounterBasedGauge64 
		MAX-ACCESS read-only 
		STATUS current
		DESCRIPTION  "Port Overloading for No Ports Success" 
		::={ acosCgnv6LsnGlobalS 269 } 

		portOverloadingForQuotaExceeded OBJECT-TYPE
		SYNTAX  CounterBasedGauge64 
		MAX-ACCESS read-only 
		STATUS current
		DESCRIPTION  "Port Overloading for Quota Exceeded" 
		::={ acosCgnv6LsnGlobalS 270 } 

		portOverloadingForQuotaExceededSuccess OBJECT-TYPE
		SYNTAX  CounterBasedGauge64 
		MAX-ACCESS read-only 
		STATUS current
		DESCRIPTION  "Port Overloading for Quota Exceeded Success" 
		::={ acosCgnv6LsnGlobalS 271 } 

		portOverloadingForQuotaExceededRace OBJECT-TYPE
		SYNTAX  CounterBasedGauge64 
		MAX-ACCESS read-only 
		STATUS current
		DESCRIPTION  "Port Overloading for Quota Exceeded Race" 
		::={ acosCgnv6LsnGlobalS 272 } 

		portOverloadingForQuotaExceededRaceSuccess OBJECT-TYPE
		SYNTAX  CounterBasedGauge64 
		MAX-ACCESS read-only 
		STATUS current
		DESCRIPTION  "Port Overloading for Quota Exceeded Race Success" 
		::={ acosCgnv6LsnGlobalS 273 } 

		portOverloadingForNewUser OBJECT-TYPE
		SYNTAX  CounterBasedGauge64 
		MAX-ACCESS read-only 
		STATUS current
		DESCRIPTION  "Port Overloading for New User" 
		::={ acosCgnv6LsnGlobalS 274 } 

		portOverloadingForNewUserSuccess OBJECT-TYPE
		SYNTAX  CounterBasedGauge64 
		MAX-ACCESS read-only 
		STATUS current
		DESCRIPTION  "Port Overloading for New User Success" 
		::={ acosCgnv6LsnGlobalS 275 } 

		haPortOverloadingAttemptFailed OBJECT-TYPE
		SYNTAX  CounterBasedGauge64 
		MAX-ACCESS read-only 
		STATUS current
		DESCRIPTION  "HA Port Overloading Attempt Failed" 
		::={ acosCgnv6LsnGlobalS 276 } 

		haPortOverloadingForNoPorts OBJECT-TYPE
		SYNTAX  CounterBasedGauge64 
		MAX-ACCESS read-only 
		STATUS current
		DESCRIPTION  "HA Port Overloading for No Ports" 
		::={ acosCgnv6LsnGlobalS 277 } 

		haPortOverloadingForNoPortsSuccess OBJECT-TYPE
		SYNTAX  CounterBasedGauge64 
		MAX-ACCESS read-only 
		STATUS current
		DESCRIPTION  "HA Port Overloading for No Ports Success" 
		::={ acosCgnv6LsnGlobalS 278 } 

		haPortOverloadingForQuotaExceeded OBJECT-TYPE
		SYNTAX  CounterBasedGauge64 
		MAX-ACCESS read-only 
		STATUS current
		DESCRIPTION  "HA Port Overloading for Quota Exceeded" 
		::={ acosCgnv6LsnGlobalS 279 } 

		haPortOverloadingForQuotaExceededSuccess OBJECT-TYPE
		SYNTAX  CounterBasedGauge64 
		MAX-ACCESS read-only 
		STATUS current
		DESCRIPTION  "HA Port Overloading for Quota Exceeded Success" 
		::={ acosCgnv6LsnGlobalS 280 } 

		haPortOverloadingForQuotaExceededRace OBJECT-TYPE
		SYNTAX  CounterBasedGauge64 
		MAX-ACCESS read-only 
		STATUS current
		DESCRIPTION  "HA Port Overloading for Quota Exceeded Race" 
		::={ acosCgnv6LsnGlobalS 281 } 

		haPortOverloadingForQuotaExceededRaceSuccess OBJECT-TYPE
		SYNTAX  CounterBasedGauge64 
		MAX-ACCESS read-only 
		STATUS current
		DESCRIPTION  "HA Port Overloading for Quota Exceeded Race Success" 
		::={ acosCgnv6LsnGlobalS 282 } 

		haPortOverloadingForNewUser OBJECT-TYPE
		SYNTAX  CounterBasedGauge64 
		MAX-ACCESS read-only 
		STATUS current
		DESCRIPTION  "HA Port Overloading for New User" 
		::={ acosCgnv6LsnGlobalS 283 } 

		haPortOverloadingForNewUserSuccess OBJECT-TYPE
		SYNTAX  CounterBasedGauge64 
		MAX-ACCESS read-only 
		STATUS current
		DESCRIPTION  "HA Port Overloading for New User Success" 
		::={ acosCgnv6LsnGlobalS 284 } 

		natPoolForceDelete OBJECT-TYPE
		SYNTAX  CounterBasedGauge64 
		MAX-ACCESS read-only 
		STATUS current
		DESCRIPTION  "NAT Pool Force Delete" 
		::={ acosCgnv6LsnGlobalS 285 } 

		quotaExtTooMany OBJECT-TYPE
		SYNTAX  CounterBasedGauge64 
		MAX-ACCESS read-only 
		STATUS current
		DESCRIPTION  "Quota Ext Too Many" 
		::={ acosCgnv6LsnGlobalS 286 } 

		natPoolNotFoundOnFree OBJECT-TYPE
		SYNTAX  CounterBasedGauge64 
		MAX-ACCESS read-only 
		STATUS current
		DESCRIPTION  "NAT Pool Not Found on Free" 
		::={ acosCgnv6LsnGlobalS 287 } 

		fullconeExtMemFreed OBJECT-TYPE
		SYNTAX  CounterBasedGauge64 
		MAX-ACCESS read-only 
		STATUS current
		DESCRIPTION  "LSN Fullcone Extension Memory Freed" 
		::={ acosCgnv6LsnGlobalS 288 } 

		fullconeExtMemAllocated OBJECT-TYPE
		SYNTAX  CounterBasedGauge64 
		MAX-ACCESS read-only 
		STATUS current
		DESCRIPTION  "LSN Fullcone Extension Memory Allocated" 
		::={ acosCgnv6LsnGlobalS 289 } 

		fullconeExtMemAllocFailure OBJECT-TYPE
		SYNTAX  CounterBasedGauge64 
		MAX-ACCESS read-only 
		STATUS current
		DESCRIPTION  "LSN Fullcone Extension Memory Allocate Failure" 
		::={ acosCgnv6LsnGlobalS 290 } 

		fullconeExtMemAllocInitFaulure OBJECT-TYPE
		SYNTAX  CounterBasedGauge64 
		MAX-ACCESS read-only 
		STATUS current
		DESCRIPTION  "LSN Fullcone Extension Initialization Failure" 
		::={ acosCgnv6LsnGlobalS 291 } 

		fullconeExtAdded OBJECT-TYPE
		SYNTAX  CounterBasedGauge64 
		MAX-ACCESS read-only 
		STATUS current
		DESCRIPTION  "LSN Fullcone Extension Added" 
		::={ acosCgnv6LsnGlobalS 292 } 

		fullconeExtTooMany OBJECT-TYPE
		SYNTAX  CounterBasedGauge64 
		MAX-ACCESS read-only 
		STATUS current
		DESCRIPTION  "LSN Fullcone Extension Too Many" 
		::={ acosCgnv6LsnGlobalS 293 } 

		natPoolAttemptAddingMultipleFreeBatches OBJECT-TYPE
		SYNTAX  CounterBasedGauge64 
		MAX-ACCESS read-only 
		STATUS current
		DESCRIPTION  "Attempt Adding Multiple Free Batches to Quota" 
		::={ acosCgnv6LsnGlobalS 294 } 

		natPoolAddFreeBatchFailed OBJECT-TYPE
		SYNTAX  CounterBasedGauge64 
		MAX-ACCESS read-only 
		STATUS current
		DESCRIPTION  "Add Batch to Quota Failed" 
		::={ acosCgnv6LsnGlobalS 295 } 

		mgcpAlgNoQuota OBJECT-TYPE
		SYNTAX  CounterBasedGauge64 
		MAX-ACCESS read-only 
		STATUS current
		DESCRIPTION  "MGCP ALG User-Quota Not Found" 
		::={ acosCgnv6LsnGlobalS 296 } 

		mgcpAlgQuotaIncFailure OBJECT-TYPE
		SYNTAX  CounterBasedGauge64 
		MAX-ACCESS read-only 
		STATUS current
		DESCRIPTION  "MGCP ALG User-Quota Exceeded" 
		::={ acosCgnv6LsnGlobalS 297 } 

		mgcpAlgNoNatIp OBJECT-TYPE
		SYNTAX  CounterBasedGauge64 
		MAX-ACCESS read-only 
		STATUS current
		DESCRIPTION  "MGCP ALG Unknown NAT IP" 
		::={ acosCgnv6LsnGlobalS 298 } 

		mgcpAlgReuseFullcone OBJECT-TYPE
		SYNTAX  CounterBasedGauge64 
		MAX-ACCESS read-only 
		STATUS current
		DESCRIPTION  "MGCP ALG Reuse Full-cone Session" 
		::={ acosCgnv6LsnGlobalS 299 } 

		mgcpAlgFullconeMismatch OBJECT-TYPE
		SYNTAX  CounterBasedGauge64 
		MAX-ACCESS read-only 
		STATUS current
		DESCRIPTION  "MGCP ALG Full-cone Session Mismatch" 
		::={ acosCgnv6LsnGlobalS 300 } 

		mgcpAlgAllocPortFailure OBJECT-TYPE
		SYNTAX  CounterBasedGauge64 
		MAX-ACCESS read-only 
		STATUS current
		DESCRIPTION  "MGCP ALG Alloc NAT Port Failure" 
		::={ acosCgnv6LsnGlobalS 301 } 

		mgcpAlgCreateFullconeFailure OBJECT-TYPE
		SYNTAX  CounterBasedGauge64 
		MAX-ACCESS read-only 
		STATUS current
		DESCRIPTION  "MGCP ALG Create Full-cone Session Failure" 
		::={ acosCgnv6LsnGlobalS 302 } 

		mgcpAlgReleasePortFailure OBJECT-TYPE
		SYNTAX  CounterBasedGauge64 
		MAX-ACCESS read-only 
		STATUS current
		DESCRIPTION  "MGCP ALG Release NAT Port Failure" 
		::={ acosCgnv6LsnGlobalS 303 } 

		mgcpAlgSingleRtpFullcone OBJECT-TYPE
		SYNTAX  CounterBasedGauge64 
		MAX-ACCESS read-only 
		STATUS current
		DESCRIPTION  "MGCP ALG Single RTP Full-cone Found" 
		::={ acosCgnv6LsnGlobalS 304 } 

		mgcpAlgSingleRtcpFullcone OBJECT-TYPE
		SYNTAX  CounterBasedGauge64 
		MAX-ACCESS read-only 
		STATUS current
		DESCRIPTION  "MGCP ALG Single RTCP Full-cone Found" 
		::={ acosCgnv6LsnGlobalS 305 } 

		mgcpAlgRtcpFullconeMismatch OBJECT-TYPE
		SYNTAX  CounterBasedGauge64 
		MAX-ACCESS read-only 
		STATUS current
		DESCRIPTION  "MGCP ALG RTCP Full-cone NAT Port Mismatch" 
		::={ acosCgnv6LsnGlobalS 306 } 

		mgcpAlgReuseRtpRtcpFullcone OBJECT-TYPE
		SYNTAX  CounterBasedGauge64 
		MAX-ACCESS read-only 
		STATUS current
		DESCRIPTION  "MGCP ALG Reuse RTP/RTCP Full-cone Session" 
		::={ acosCgnv6LsnGlobalS 307 } 

		mgcpAlgAllocRtpRtcpPortFailure OBJECT-TYPE
		SYNTAX  CounterBasedGauge64 
		MAX-ACCESS read-only 
		STATUS current
		DESCRIPTION  "MGCP ALG Alloc RTP/RTCP NAT Ports Failure" 
		::={ acosCgnv6LsnGlobalS 308 } 

		mgcpAlgAllocSinglePortFailure OBJECT-TYPE
		SYNTAX  CounterBasedGauge64 
		MAX-ACCESS read-only 
		STATUS current
		DESCRIPTION  "MGCP ALG Alloc Single RTP or RTCP NAT Port Failure" 
		::={ acosCgnv6LsnGlobalS 309 } 

		mgcpAlgCreateSingleFullconeFailure OBJECT-TYPE
		SYNTAX  CounterBasedGauge64 
		MAX-ACCESS read-only 
		STATUS current
		DESCRIPTION  "MGCP ALG Create Single RTP or RTCP Full-cone Session Failure" 
		::={ acosCgnv6LsnGlobalS 310 } 

		mgcpAlgCreateRtpFullconeFailure OBJECT-TYPE
		SYNTAX  CounterBasedGauge64 
		MAX-ACCESS read-only 
		STATUS current
		DESCRIPTION  "MGCP ALG Create RTP Full-cone Session Failure" 
		::={ acosCgnv6LsnGlobalS 311 } 

		mgcpAlgCreateRtcpFullconeFailure OBJECT-TYPE
		SYNTAX  CounterBasedGauge64 
		MAX-ACCESS read-only 
		STATUS current
		DESCRIPTION  "MGCP ALG Create RTCP Full-cone Session Failure" 
		::={ acosCgnv6LsnGlobalS 312 } 

		mgcpAlgPortPairAllocFromConsecutive OBJECT-TYPE
		SYNTAX  CounterBasedGauge64 
		MAX-ACCESS read-only 
		STATUS current
		DESCRIPTION  "MGCP ALG Port Pair Allocated From Consecutive" 
		::={ acosCgnv6LsnGlobalS 313 } 

		mgcpAlgPortPairAllocFromPartition OBJECT-TYPE
		SYNTAX  CounterBasedGauge64 
		MAX-ACCESS read-only 
		STATUS current
		DESCRIPTION  "MGCP ALG Port Pair Allocated From Partition" 
		::={ acosCgnv6LsnGlobalS 314 } 

		mgcpAlgPortPairAllocFromPoolPortBatch OBJECT-TYPE
		SYNTAX  CounterBasedGauge64 
		MAX-ACCESS read-only 
		STATUS current
		DESCRIPTION  "MGCP ALG Port Pair Allocated From Pool Port Batch" 
		::={ acosCgnv6LsnGlobalS 315 } 

		mgcpAlgPortPairAllocFromQuotaConsecutive OBJECT-TYPE
		SYNTAX  CounterBasedGauge64 
		MAX-ACCESS read-only 
		STATUS current
		DESCRIPTION  "MGCP ALG Port Pair Allocated From Quota Consecutive" 
		::={ acosCgnv6LsnGlobalS 316 } 

		mgcpAlgPortPairAllocFromQuotaPartition OBJECT-TYPE
		SYNTAX  CounterBasedGauge64 
		MAX-ACCESS read-only 
		STATUS current
		DESCRIPTION  "MGCP ALG Port Pair Allocated From Quota Partition" 
		::={ acosCgnv6LsnGlobalS 317 } 

		mgcpAlgPortPairAllocFromQuotaPartitionError OBJECT-TYPE
		SYNTAX  CounterBasedGauge64 
		MAX-ACCESS read-only 
		STATUS current
		DESCRIPTION  "MGCP ALG Port Pair Allocated From Quota Partition Error" 
		::={ acosCgnv6LsnGlobalS 318 } 

		mgcpAlgPortPairAllocFromQuotaPoolPortBatch OBJECT-TYPE
		SYNTAX  CounterBasedGauge64 
		MAX-ACCESS read-only 
		STATUS current
		DESCRIPTION  "MGCP ALG Port Pair Allocated From Quota Pool Port Batch" 
		::={ acosCgnv6LsnGlobalS 319 } 

		userQuotaUnusableDrop OBJECT-TYPE
		SYNTAX  CounterBasedGauge64 
		MAX-ACCESS read-only 
		STATUS current
		DESCRIPTION  "User-Quota Unusable Drop" 
		::={ acosCgnv6LsnGlobalS 320 } 

		userQuotaUnusable OBJECT-TYPE
		SYNTAX  CounterBasedGauge64 
		MAX-ACCESS read-only 
		STATUS current
		DESCRIPTION  "User-Quota Marked Unusable" 
		::={ acosCgnv6LsnGlobalS 321 } 

		natPoolSamePortBatchUdpFailed OBJECT-TYPE
		SYNTAX  CounterBasedGauge64 
		MAX-ACCESS read-only 
		STATUS current
		DESCRIPTION  "Simultaneous Batch Allocation UDP Port Allocation Failed" 
		::={ acosCgnv6LsnGlobalS 322 } 

		crossCpuHelperCreatedEim OBJECT-TYPE
		SYNTAX  CounterBasedGauge64 
		MAX-ACCESS read-only 
		STATUS current
		DESCRIPTION  "EIM Cross CPU Session Helper Created" 
		::={ acosCgnv6LsnGlobalS 323 } 

		crossCpuHelperCreatedEif OBJECT-TYPE
		SYNTAX  CounterBasedGauge64 
		MAX-ACCESS read-only 
		STATUS current
		DESCRIPTION  "EIF Cross CPU Session Helper Created" 
		::={ acosCgnv6LsnGlobalS 324 } 

		crossCpuHelperCreatedUdp OBJECT-TYPE
		SYNTAX  CounterBasedGauge64 
		MAX-ACCESS read-only 
		STATUS current
		DESCRIPTION  "UDP Cross CPU Session Helper Created" 
		::={ acosCgnv6LsnGlobalS 325 } 

		crossCpuHelperCreatedTcp OBJECT-TYPE
		SYNTAX  CounterBasedGauge64 
		MAX-ACCESS read-only 
		STATUS current
		DESCRIPTION  "TCP Cross CPU Session Helper Created" 
		::={ acosCgnv6LsnGlobalS 326 } 

		crossCpuHelperCreatedIcmp OBJECT-TYPE
		SYNTAX  CounterBasedGauge64 
		MAX-ACCESS read-only 
		STATUS current
		DESCRIPTION  "ICMP Cross CPU Session Helper Created" 
		::={ acosCgnv6LsnGlobalS 327 } 

		crossCpuHelperCreatedIp OBJECT-TYPE
		SYNTAX  CounterBasedGauge64 
		MAX-ACCESS read-only 
		STATUS current
		DESCRIPTION  "IP Cross CPU Session Helper Created" 
		::={ acosCgnv6LsnGlobalS 328 } 

		crossCpuHelperFreeNotFoundIp OBJECT-TYPE
		SYNTAX  CounterBasedGauge64 
		MAX-ACCESS read-only 
		STATUS current
		DESCRIPTION  "IP Cross CPU Helper Free Not Found" 
		::={ acosCgnv6LsnGlobalS 329 } 

		crossCpuHelperFreeNotFoundIcmp OBJECT-TYPE
		SYNTAX  CounterBasedGauge64 
		MAX-ACCESS read-only 
		STATUS current
		DESCRIPTION  "ICMP Cross CPU Helper Free Not Found" 
		::={ acosCgnv6LsnGlobalS 330 } 

		crossCpuHelperFreeNotFoundTcp OBJECT-TYPE
		SYNTAX  CounterBasedGauge64 
		MAX-ACCESS read-only 
		STATUS current
		DESCRIPTION  "TCP Cross CPU Helper Free Not Found" 
		::={ acosCgnv6LsnGlobalS 331 } 

		crossCpuHelperFreeNotFoundUdp OBJECT-TYPE
		SYNTAX  CounterBasedGauge64 
		MAX-ACCESS read-only 
		STATUS current
		DESCRIPTION  "UDP Cross CPU Helper Free Not Found" 
		::={ acosCgnv6LsnGlobalS 332 } 

		adcPortAllocationFailed OBJECT-TYPE
		SYNTAX  CounterBasedGauge64 
		MAX-ACCESS read-only 
		STATUS current
		DESCRIPTION  "ADC Port Allocation Failed" 
		::={ acosCgnv6LsnGlobalS 333 } 

		adcPortAllocationIneligible OBJECT-TYPE
		SYNTAX  CounterBasedGauge64 
		MAX-ACCESS read-only 
		STATUS current
		DESCRIPTION  "ADC Port Allocation Not Allowed" 
		::={ acosCgnv6LsnGlobalS 334 } 

		aclHttpDomainNodeExceeded OBJECT-TYPE
		SYNTAX  CounterBasedGauge64 
		MAX-ACCESS read-only 
		STATUS current
		DESCRIPTION  "ACL HTTP Domain Node Exceeded" 
		::={ acosCgnv6LsnGlobalS 335 } 

		fwdIngressPacketsTcp OBJECT-TYPE
		SYNTAX  CounterBasedGauge64 
		MAX-ACCESS read-only 
		STATUS current
		DESCRIPTION  "Forward Ingress Packets TCP" 
		::={ acosCgnv6LsnGlobalS 336 } 

		fwdEgressPacketsTcp OBJECT-TYPE
		SYNTAX  CounterBasedGauge64 
		MAX-ACCESS read-only 
		STATUS current
		DESCRIPTION  "Forward Egress Packets TCP" 
		::={ acosCgnv6LsnGlobalS 337 } 

		revIngressPacketsTcp OBJECT-TYPE
		SYNTAX  CounterBasedGauge64 
		MAX-ACCESS read-only 
		STATUS current
		DESCRIPTION  "Reverse Ingress Packets TCP" 
		::={ acosCgnv6LsnGlobalS 338 } 

		revEgressPacketsTcp OBJECT-TYPE
		SYNTAX  CounterBasedGauge64 
		MAX-ACCESS read-only 
		STATUS current
		DESCRIPTION  "Reverse Egress Packets TCP" 
		::={ acosCgnv6LsnGlobalS 339 } 

		fwdIngressBytesTcp OBJECT-TYPE
		SYNTAX  CounterBasedGauge64 
		MAX-ACCESS read-only 
		STATUS current
		DESCRIPTION  "Forward Ingress Bytes TCP" 
		::={ acosCgnv6LsnGlobalS 340 } 

		fwdEgressBytesTcp OBJECT-TYPE
		SYNTAX  CounterBasedGauge64 
		MAX-ACCESS read-only 
		STATUS current
		DESCRIPTION  "Forward Egress Bytes TCP" 
		::={ acosCgnv6LsnGlobalS 341 } 

		revIngressBytesTcp OBJECT-TYPE
		SYNTAX  CounterBasedGauge64 
		MAX-ACCESS read-only 
		STATUS current
		DESCRIPTION  "Reverse Ingress Bytes TCP" 
		::={ acosCgnv6LsnGlobalS 342 } 

		revEgressBytesTcp OBJECT-TYPE
		SYNTAX  CounterBasedGauge64 
		MAX-ACCESS read-only 
		STATUS current
		DESCRIPTION  "Reverse Egress Bytes TCP" 
		::={ acosCgnv6LsnGlobalS 343 } 

		fwdIngressPacketsUdp OBJECT-TYPE
		SYNTAX  CounterBasedGauge64 
		MAX-ACCESS read-only 
		STATUS current
		DESCRIPTION  "Forward Ingress Packets UDP" 
		::={ acosCgnv6LsnGlobalS 344 } 

		fwdEgressPacketsUdp OBJECT-TYPE
		SYNTAX  CounterBasedGauge64 
		MAX-ACCESS read-only 
		STATUS current
		DESCRIPTION  "Forward Egress Packets UDP" 
		::={ acosCgnv6LsnGlobalS 345 } 

		revIngressPacketsUdp OBJECT-TYPE
		SYNTAX  CounterBasedGauge64 
		MAX-ACCESS read-only 
		STATUS current
		DESCRIPTION  "Reverse Ingress Packets UDP" 
		::={ acosCgnv6LsnGlobalS 346 } 

		revEgressPacketsUdp OBJECT-TYPE
		SYNTAX  CounterBasedGauge64 
		MAX-ACCESS read-only 
		STATUS current
		DESCRIPTION  "Reverse Egress Packets UDP" 
		::={ acosCgnv6LsnGlobalS 347 } 

		fwdIngressBytesUdp OBJECT-TYPE
		SYNTAX  CounterBasedGauge64 
		MAX-ACCESS read-only 
		STATUS current
		DESCRIPTION  "Forward Ingress Bytes UDP" 
		::={ acosCgnv6LsnGlobalS 348 } 

		fwdEgressBytesUdp OBJECT-TYPE
		SYNTAX  CounterBasedGauge64 
		MAX-ACCESS read-only 
		STATUS current
		DESCRIPTION  "Forward Egress Bytes UDP" 
		::={ acosCgnv6LsnGlobalS 349 } 

		revIngressBytesUdp OBJECT-TYPE
		SYNTAX  CounterBasedGauge64 
		MAX-ACCESS read-only 
		STATUS current
		DESCRIPTION  "Reverse Ingress Bytes UDP" 
		::={ acosCgnv6LsnGlobalS 350 } 

		revEgressBytesUdp OBJECT-TYPE
		SYNTAX  CounterBasedGauge64 
		MAX-ACCESS read-only 
		STATUS current
		DESCRIPTION  "Reverse Egress Bytes UDP" 
		::={ acosCgnv6LsnGlobalS 351 } 

		fwdIngressPacketsIcmp OBJECT-TYPE
		SYNTAX  CounterBasedGauge64 
		MAX-ACCESS read-only 
		STATUS current
		DESCRIPTION  "Forward Ingress Packets ICMP" 
		::={ acosCgnv6LsnGlobalS 352 } 

		fwdEgressPacketsIcmp OBJECT-TYPE
		SYNTAX  CounterBasedGauge64 
		MAX-ACCESS read-only 
		STATUS current
		DESCRIPTION  "Forward Egress Packets ICMP" 
		::={ acosCgnv6LsnGlobalS 353 } 

		revIngressPacketsIcmp OBJECT-TYPE
		SYNTAX  CounterBasedGauge64 
		MAX-ACCESS read-only 
		STATUS current
		DESCRIPTION  "Reverse Ingress Packets ICMP" 
		::={ acosCgnv6LsnGlobalS 354 } 

		revEgressPacketsIcmp OBJECT-TYPE
		SYNTAX  CounterBasedGauge64 
		MAX-ACCESS read-only 
		STATUS current
		DESCRIPTION  "Reverse Egress Packets ICMP" 
		::={ acosCgnv6LsnGlobalS 355 } 

		fwdIngressBytesIcmp OBJECT-TYPE
		SYNTAX  CounterBasedGauge64 
		MAX-ACCESS read-only 
		STATUS current
		DESCRIPTION  "Forward Ingress Bytes ICMP" 
		::={ acosCgnv6LsnGlobalS 356 } 

		fwdEgressBytesIcmp OBJECT-TYPE
		SYNTAX  CounterBasedGauge64 
		MAX-ACCESS read-only 
		STATUS current
		DESCRIPTION  "Forward Egress Bytes ICMP" 
		::={ acosCgnv6LsnGlobalS 357 } 

		revIngressBytesIcmp OBJECT-TYPE
		SYNTAX  CounterBasedGauge64 
		MAX-ACCESS read-only 
		STATUS current
		DESCRIPTION  "Reverse Ingress Bytes ICMP" 
		::={ acosCgnv6LsnGlobalS 358 } 

		revEgressBytesIcmp OBJECT-TYPE
		SYNTAX  CounterBasedGauge64 
		MAX-ACCESS read-only 
		STATUS current
		DESCRIPTION  "Reverse Egress Bytes ICMP" 
		::={ acosCgnv6LsnGlobalS 359 } 

		fwdIngressPacketsOthers OBJECT-TYPE
		SYNTAX  CounterBasedGauge64 
		MAX-ACCESS read-only 
		STATUS current
		DESCRIPTION  "Forward Ingress Packets OTHERS" 
		::={ acosCgnv6LsnGlobalS 360 } 

		fwdEgressPacketsOthers OBJECT-TYPE
		SYNTAX  CounterBasedGauge64 
		MAX-ACCESS read-only 
		STATUS current
		DESCRIPTION  "Forward Egress Packets OTHERS" 
		::={ acosCgnv6LsnGlobalS 361 } 

		revIngressPacketsOthers OBJECT-TYPE
		SYNTAX  CounterBasedGauge64 
		MAX-ACCESS read-only 
		STATUS current
		DESCRIPTION  "Reverse Ingress Packets OTHERS" 
		::={ acosCgnv6LsnGlobalS 362 } 

		revEgressPacketsOthers OBJECT-TYPE
		SYNTAX  CounterBasedGauge64 
		MAX-ACCESS read-only 
		STATUS current
		DESCRIPTION  "Reverse Egress Packets OTHERS" 
		::={ acosCgnv6LsnGlobalS 363 } 

		fwdIngressBytesOthers OBJECT-TYPE
		SYNTAX  CounterBasedGauge64 
		MAX-ACCESS read-only 
		STATUS current
		DESCRIPTION  "Forward Ingress Bytes OTHERS" 
		::={ acosCgnv6LsnGlobalS 364 } 

		fwdEgressBytesOthers OBJECT-TYPE
		SYNTAX  CounterBasedGauge64 
		MAX-ACCESS read-only 
		STATUS current
		DESCRIPTION  "Forward Egress Bytes OTHERS" 
		::={ acosCgnv6LsnGlobalS 365 } 

		revIngressBytesOthers OBJECT-TYPE
		SYNTAX  CounterBasedGauge64 
		MAX-ACCESS read-only 
		STATUS current
		DESCRIPTION  "Reverse Ingress Bytes OTHERS" 
		::={ acosCgnv6LsnGlobalS 366 } 

		revEgressBytesOthers OBJECT-TYPE
		SYNTAX  CounterBasedGauge64 
		MAX-ACCESS read-only 
		STATUS current
		DESCRIPTION  "Reverse Egress Bytes OTHERS" 
		::={ acosCgnv6LsnGlobalS 367 } 

		fwdIngressPktSizeRange1 OBJECT-TYPE
		SYNTAX  CounterBasedGauge64 
		MAX-ACCESS read-only 
		STATUS current
		DESCRIPTION  "Forward Ingress Packet size between 0 and 200" 
		::={ acosCgnv6LsnGlobalS 368 } 

		fwdIngressPktSizeRange2 OBJECT-TYPE
		SYNTAX  CounterBasedGauge64 
		MAX-ACCESS read-only 
		STATUS current
		DESCRIPTION  "Forward Ingress Packet size between 201 and 800" 
		::={ acosCgnv6LsnGlobalS 369 } 

		fwdIngressPktSizeRange3 OBJECT-TYPE
		SYNTAX  CounterBasedGauge64 
		MAX-ACCESS read-only 
		STATUS current
		DESCRIPTION  "Forward Ingress Packet size between 801 and 1550" 
		::={ acosCgnv6LsnGlobalS 370 } 

		fwdIngressPktSizeRange4 OBJECT-TYPE
		SYNTAX  CounterBasedGauge64 
		MAX-ACCESS read-only 
		STATUS current
		DESCRIPTION  "Forward Ingress Packet size between 1551 and 9000" 
		::={ acosCgnv6LsnGlobalS 371 } 

		fwdEgressPktSizeRange1 OBJECT-TYPE
		SYNTAX  CounterBasedGauge64 
		MAX-ACCESS read-only 
		STATUS current
		DESCRIPTION  "Forward Egress Packet size between 0 and 200" 
		::={ acosCgnv6LsnGlobalS 372 } 

		fwdEgressPktSizeRange2 OBJECT-TYPE
		SYNTAX  CounterBasedGauge64 
		MAX-ACCESS read-only 
		STATUS current
		DESCRIPTION  "Forward Egress Packet size between 201 and 800" 
		::={ acosCgnv6LsnGlobalS 373 } 

		fwdEgressPktSizeRange3 OBJECT-TYPE
		SYNTAX  CounterBasedGauge64 
		MAX-ACCESS read-only 
		STATUS current
		DESCRIPTION  "Forward Egress Packet size between 801 and 1550" 
		::={ acosCgnv6LsnGlobalS 374 } 

		fwdEgressPktSizeRange4 OBJECT-TYPE
		SYNTAX  CounterBasedGauge64 
		MAX-ACCESS read-only 
		STATUS current
		DESCRIPTION  "Forward Egress Packet size between 1551 and 9000" 
		::={ acosCgnv6LsnGlobalS 375 } 

		revIngressPktSizeRange1 OBJECT-TYPE
		SYNTAX  CounterBasedGauge64 
		MAX-ACCESS read-only 
		STATUS current
		DESCRIPTION  "Reverse Ingress Packet size between 0 and 200" 
		::={ acosCgnv6LsnGlobalS 376 } 

		revIngressPktSizeRange2 OBJECT-TYPE
		SYNTAX  CounterBasedGauge64 
		MAX-ACCESS read-only 
		STATUS current
		DESCRIPTION  "Reverse Ingress Packet size between 201 and 800" 
		::={ acosCgnv6LsnGlobalS 377 } 

		revIngressPktSizeRange3 OBJECT-TYPE
		SYNTAX  CounterBasedGauge64 
		MAX-ACCESS read-only 
		STATUS current
		DESCRIPTION  "Reverse Ingress Packet size between 801 and 1550" 
		::={ acosCgnv6LsnGlobalS 378 } 

		revIngressPktSizeRange4 OBJECT-TYPE
		SYNTAX  CounterBasedGauge64 
		MAX-ACCESS read-only 
		STATUS current
		DESCRIPTION  "Reverse Ingress Packet size between 1551 and 9000" 
		::={ acosCgnv6LsnGlobalS 379 } 

		revEgressPktSizeRange1 OBJECT-TYPE
		SYNTAX  CounterBasedGauge64 
		MAX-ACCESS read-only 
		STATUS current
		DESCRIPTION  "Reverse Egress Packet size between 0 and 200" 
		::={ acosCgnv6LsnGlobalS 380 } 

		revEgressPktSizeRange2 OBJECT-TYPE
		SYNTAX  CounterBasedGauge64 
		MAX-ACCESS read-only 
		STATUS current
		DESCRIPTION  "Reverse Egress Packet size between 201 and 800" 
		::={ acosCgnv6LsnGlobalS 381 } 

		revEgressPktSizeRange3 OBJECT-TYPE
		SYNTAX  CounterBasedGauge64 
		MAX-ACCESS read-only 
		STATUS current
		DESCRIPTION  "Reverse Egress Packet size between 801 and 1550" 
		::={ acosCgnv6LsnGlobalS 382 } 

		revEgressPktSizeRange4 OBJECT-TYPE
		SYNTAX  CounterBasedGauge64 
		MAX-ACCESS read-only 
		STATUS current
		DESCRIPTION  "Reverse Egress Packet size between 1551 and 9000" 
		::={ acosCgnv6LsnGlobalS 383 } 

acosCgnv6LsnAlg                     OBJECT IDENTIFIER ::= { acosCgnv6Lsn 5 }
acosCgnv6LsnAlgEsp                  OBJECT IDENTIFIER ::= { acosCgnv6LsnAlg 1 }
acosCgnv6LsnAlgEspS                 OBJECT IDENTIFIER ::= { acosCgnv6LsnAlgEsp 1 }

		cgnv6LsnAlgEspSessionCreated OBJECT-TYPE
		SYNTAX  CounterBasedGauge64 
		MAX-ACCESS read-only 
		STATUS current
		DESCRIPTION  "ESP Sessions Created" 
		::={ acosCgnv6LsnAlgEspS 1 } 

		placeholderDebug OBJECT-TYPE
		SYNTAX  CounterBasedGauge64 
		MAX-ACCESS read-only 
		STATUS current
		DESCRIPTION  "Placeholder Debug" 
		::={ acosCgnv6LsnAlgEspS 2 } 

		natIpConflict OBJECT-TYPE
		SYNTAX  CounterBasedGauge64 
		MAX-ACCESS read-only 
		STATUS current
		DESCRIPTION  "NAT IP Conflict" 
		::={ acosCgnv6LsnAlgEspS 3 } 

acosCgnv6LsnAlgFtp                  OBJECT IDENTIFIER ::= { acosCgnv6LsnAlg 2 }
acosCgnv6LsnAlgFtpS                 OBJECT IDENTIFIER ::= { acosCgnv6LsnAlgFtp 1 }

		portRequests OBJECT-TYPE
		SYNTAX  CounterBasedGauge64 
		MAX-ACCESS read-only 
		STATUS current
		DESCRIPTION  "PORT Requests From Client" 
		::={ acosCgnv6LsnAlgFtpS 1 } 

		eprtRequests OBJECT-TYPE
		SYNTAX  CounterBasedGauge64 
		MAX-ACCESS read-only 
		STATUS current
		DESCRIPTION  "EPRT Requests From Client" 
		::={ acosCgnv6LsnAlgFtpS 2 } 

		lprtRequests OBJECT-TYPE
		SYNTAX  CounterBasedGauge64 
		MAX-ACCESS read-only 
		STATUS current
		DESCRIPTION  "LPRT Requests From Client" 
		::={ acosCgnv6LsnAlgFtpS 3 } 

		pasvReplies OBJECT-TYPE
		SYNTAX  CounterBasedGauge64 
		MAX-ACCESS read-only 
		STATUS current
		DESCRIPTION  "PASV Replies From Server" 
		::={ acosCgnv6LsnAlgFtpS 4 } 

		epsvReplies OBJECT-TYPE
		SYNTAX  CounterBasedGauge64 
		MAX-ACCESS read-only 
		STATUS current
		DESCRIPTION  "EPSV Replies From Server" 
		::={ acosCgnv6LsnAlgFtpS 5 } 

		lpsvReplies OBJECT-TYPE
		SYNTAX  CounterBasedGauge64 
		MAX-ACCESS read-only 
		STATUS current
		DESCRIPTION  "LPSV Replies From Server" 
		::={ acosCgnv6LsnAlgFtpS 6 } 

		portRetransmits OBJECT-TYPE
		SYNTAX  CounterBasedGauge64 
		MAX-ACCESS read-only 
		STATUS current
		DESCRIPTION  "Port Mode Request Retransmits" 
		::={ acosCgnv6LsnAlgFtpS 7 } 

		pasvRetransmits OBJECT-TYPE
		SYNTAX  CounterBasedGauge64 
		MAX-ACCESS read-only 
		STATUS current
		DESCRIPTION  "Passive Mode Reply Retransmits" 
		::={ acosCgnv6LsnAlgFtpS 8 } 

		portHelperCreated OBJECT-TYPE
		SYNTAX  CounterBasedGauge64 
		MAX-ACCESS read-only 
		STATUS current
		DESCRIPTION  "Port Mode Helper Created" 
		::={ acosCgnv6LsnAlgFtpS 9 } 

		pasvHelperCreated OBJECT-TYPE
		SYNTAX  CounterBasedGauge64 
		MAX-ACCESS read-only 
		STATUS current
		DESCRIPTION  "Passive Mode Helper Created" 
		::={ acosCgnv6LsnAlgFtpS 10 } 

		portHelperFreed OBJECT-TYPE
		SYNTAX  CounterBasedGauge64 
		MAX-ACCESS read-only 
		STATUS current
		DESCRIPTION  "Port Mode Helper Freed" 
		::={ acosCgnv6LsnAlgFtpS 11 } 

		pasvHelperFreed OBJECT-TYPE
		SYNTAX  CounterBasedGauge64 
		MAX-ACCESS read-only 
		STATUS current
		DESCRIPTION  "Passive Mode Helper Freed" 
		::={ acosCgnv6LsnAlgFtpS 12 } 

		portHelperUnused OBJECT-TYPE
		SYNTAX  CounterBasedGauge64 
		MAX-ACCESS read-only 
		STATUS current
		DESCRIPTION  "Port Mode Helper Unused" 
		::={ acosCgnv6LsnAlgFtpS 13 } 

		pasvHelperUnused OBJECT-TYPE
		SYNTAX  CounterBasedGauge64 
		MAX-ACCESS read-only 
		STATUS current
		DESCRIPTION  "Passive Mode Helper Unused" 
		::={ acosCgnv6LsnAlgFtpS 14 } 

		portHelperCreationFailure OBJECT-TYPE
		SYNTAX  CounterBasedGauge64 
		MAX-ACCESS read-only 
		STATUS current
		DESCRIPTION  "Port Helper Creation Failure" 
		::={ acosCgnv6LsnAlgFtpS 15 } 

		pasvHelperCreationFailure OBJECT-TYPE
		SYNTAX  CounterBasedGauge64 
		MAX-ACCESS read-only 
		STATUS current
		DESCRIPTION  "Passive Helper Creation Failure" 
		::={ acosCgnv6LsnAlgFtpS 16 } 

		getConnExtFailure OBJECT-TYPE
		SYNTAX  CounterBasedGauge64 
		MAX-ACCESS read-only 
		STATUS current
		DESCRIPTION  "Get Conn Extension Failure" 
		::={ acosCgnv6LsnAlgFtpS 17 } 

		smpAppTypeMismatch OBJECT-TYPE
		SYNTAX  CounterBasedGauge64 
		MAX-ACCESS read-only 
		STATUS current
		DESCRIPTION  "SMP ALG App Type Mismatch" 
		::={ acosCgnv6LsnAlgFtpS 18 } 

acosCgnv6LsnAlgPptp                 OBJECT IDENTIFIER ::= { acosCgnv6LsnAlg 3 }
acosCgnv6LsnAlgPptpS                OBJECT IDENTIFIER ::= { acosCgnv6LsnAlgPptp 1 }

		cgnv6LsnAlgPptpCallsEstablished OBJECT-TYPE
		SYNTAX  CounterBasedGauge64 
		MAX-ACCESS read-only 
		STATUS current
		DESCRIPTION  "Calls Established" 
		::={ acosCgnv6LsnAlgPptpS 1 } 

		cgnv6LsnAlgPptpMismatchedPnsCallId OBJECT-TYPE
		SYNTAX  CounterBasedGauge64 
		MAX-ACCESS read-only 
		STATUS current
		DESCRIPTION  "Mismatched PNS Call ID" 
		::={ acosCgnv6LsnAlgPptpS 2 } 

		cgnv6LsnAlgPtptGreSessionsCreated OBJECT-TYPE
		SYNTAX  CounterBasedGauge64 
		MAX-ACCESS read-only 
		STATUS current
		DESCRIPTION  "GRE Sessions Created" 
		::={ acosCgnv6LsnAlgPptpS 3 } 

		cgnv6LsnAlgPtptGreSessionsFreed OBJECT-TYPE
		SYNTAX  CounterBasedGauge64 
		MAX-ACCESS read-only 
		STATUS current
		DESCRIPTION  "GRE Sessions Freed" 
		::={ acosCgnv6LsnAlgPptpS 4 } 

		cgnv6LsnAlgPtptNoGreSessionMatch OBJECT-TYPE
		SYNTAX  CounterBasedGauge64 
		MAX-ACCESS read-only 
		STATUS current
		DESCRIPTION  "No Matching GRE Session" 
		::={ acosCgnv6LsnAlgPptpS 5 } 

		smpSessionsCreated OBJECT-TYPE
		SYNTAX  CounterBasedGauge64 
		MAX-ACCESS read-only 
		STATUS current
		DESCRIPTION  "SMP Sessions Created" 
		::={ acosCgnv6LsnAlgPptpS 6 } 

		smpSessionsFreed OBJECT-TYPE
		SYNTAX  CounterBasedGauge64 
		MAX-ACCESS read-only 
		STATUS current
		DESCRIPTION  "SMP Sessions Freed" 
		::={ acosCgnv6LsnAlgPptpS 7 } 

		smpSessionCreationFailure OBJECT-TYPE
		SYNTAX  CounterBasedGauge64 
		MAX-ACCESS read-only 
		STATUS current
		DESCRIPTION  "SMP Session Creation Failures" 
		::={ acosCgnv6LsnAlgPptpS 8 } 

		extensionCreationFailure OBJECT-TYPE
		SYNTAX  CounterBasedGauge64 
		MAX-ACCESS read-only 
		STATUS current
		DESCRIPTION  "Extension Creation Failures" 
		::={ acosCgnv6LsnAlgPptpS 9 } 

		haSent OBJECT-TYPE
		SYNTAX  CounterBasedGauge64 
		MAX-ACCESS read-only 
		STATUS current
		DESCRIPTION  "HA Info Sent" 
		::={ acosCgnv6LsnAlgPptpS 10 } 

		haRcv OBJECT-TYPE
		SYNTAX  CounterBasedGauge64 
		MAX-ACCESS read-only 
		STATUS current
		DESCRIPTION  "HA Info Received" 
		::={ acosCgnv6LsnAlgPptpS 11 } 

		haNoMem OBJECT-TYPE
		SYNTAX  CounterBasedGauge64 
		MAX-ACCESS read-only 
		STATUS current
		DESCRIPTION  "HA Memory Allocation Failure" 
		::={ acosCgnv6LsnAlgPptpS 12 } 

		haConflict OBJECT-TYPE
		SYNTAX  CounterBasedGauge64 
		MAX-ACCESS read-only 
		STATUS current
		DESCRIPTION  "HA Call ID Conflicts" 
		::={ acosCgnv6LsnAlgPptpS 13 } 

		haOverwrite OBJECT-TYPE
		SYNTAX  CounterBasedGauge64 
		MAX-ACCESS read-only 
		STATUS current
		DESCRIPTION  "HA Call ID Overwrites" 
		::={ acosCgnv6LsnAlgPptpS 14 } 

		haCallSent OBJECT-TYPE
		SYNTAX  CounterBasedGauge64 
		MAX-ACCESS read-only 
		STATUS current
		DESCRIPTION  "HA Call Sent" 
		::={ acosCgnv6LsnAlgPptpS 15 } 

		haCallRcv OBJECT-TYPE
		SYNTAX  CounterBasedGauge64 
		MAX-ACCESS read-only 
		STATUS current
		DESCRIPTION  "HA Call Received" 
		::={ acosCgnv6LsnAlgPptpS 16 } 

		haSmpConflict OBJECT-TYPE
		SYNTAX  CounterBasedGauge64 
		MAX-ACCESS read-only 
		STATUS current
		DESCRIPTION  "HA SMP Conflicts" 
		::={ acosCgnv6LsnAlgPptpS 17 } 

		haSmpInDelQ OBJECT-TYPE
		SYNTAX  CounterBasedGauge64 
		MAX-ACCESS read-only 
		STATUS current
		DESCRIPTION  "HA SMP Deleted" 
		::={ acosCgnv6LsnAlgPptpS 18 } 

		smpAppTypeMismatch OBJECT-TYPE
		SYNTAX  CounterBasedGauge64 
		MAX-ACCESS read-only 
		STATUS current
		DESCRIPTION  "SMP ALG App Type Mismatch" 
		::={ acosCgnv6LsnAlgPptpS 19 } 

		quotaInc OBJECT-TYPE
		SYNTAX  CounterBasedGauge64 
		MAX-ACCESS read-only 
		STATUS current
		DESCRIPTION  "Quota Incremented" 
		::={ acosCgnv6LsnAlgPptpS 20 } 

		quotaDec OBJECT-TYPE
		SYNTAX  CounterBasedGauge64 
		MAX-ACCESS read-only 
		STATUS current
		DESCRIPTION  "Quota Decremented" 
		::={ acosCgnv6LsnAlgPptpS 21 } 

		quotaIncNotFound OBJECT-TYPE
		SYNTAX  CounterBasedGauge64 
		MAX-ACCESS read-only 
		STATUS current
		DESCRIPTION  "Quota Not Found on Increment" 
		::={ acosCgnv6LsnAlgPptpS 22 } 

		quotaDecNotFound OBJECT-TYPE
		SYNTAX  CounterBasedGauge64 
		MAX-ACCESS read-only 
		STATUS current
		DESCRIPTION  "Quota Not Found on Decrement" 
		::={ acosCgnv6LsnAlgPptpS 23 } 

		callReqPnsCallIdMismatch OBJECT-TYPE
		SYNTAX  CounterBasedGauge64 
		MAX-ACCESS read-only 
		STATUS current
		DESCRIPTION  "Call ID Mismatch on Call Request" 
		::={ acosCgnv6LsnAlgPptpS 24 } 

		callReplyPnsCallIdMismatch OBJECT-TYPE
		SYNTAX  CounterBasedGauge64 
		MAX-ACCESS read-only 
		STATUS current
		DESCRIPTION  "Call ID Mismatch on Call Reply" 
		::={ acosCgnv6LsnAlgPptpS 25 } 

		callReqRetransmit OBJECT-TYPE
		SYNTAX  CounterBasedGauge64 
		MAX-ACCESS read-only 
		STATUS current
		DESCRIPTION  "Call Request Retransmit" 
		::={ acosCgnv6LsnAlgPptpS 26 } 

		callReqNew OBJECT-TYPE
		SYNTAX  CounterBasedGauge64 
		MAX-ACCESS read-only 
		STATUS current
		DESCRIPTION  "Call Request New" 
		::={ acosCgnv6LsnAlgPptpS 27 } 

		callReqExtAllocFailure OBJECT-TYPE
		SYNTAX  CounterBasedGauge64 
		MAX-ACCESS read-only 
		STATUS current
		DESCRIPTION  "Call Request Ext Alloc Failure" 
		::={ acosCgnv6LsnAlgPptpS 28 } 

		callReplyCallIdUnknown OBJECT-TYPE
		SYNTAX  CounterBasedGauge64 
		MAX-ACCESS read-only 
		STATUS current
		DESCRIPTION  "Call Reply Unknown Client Call ID" 
		::={ acosCgnv6LsnAlgPptpS 29 } 

		callReplyRetransmit OBJECT-TYPE
		SYNTAX  CounterBasedGauge64 
		MAX-ACCESS read-only 
		STATUS current
		DESCRIPTION  "Call Reply Retransmit" 
		::={ acosCgnv6LsnAlgPptpS 30 } 

		callReplyRetransmitWrongControl OBJECT-TYPE
		SYNTAX  CounterBasedGauge64 
		MAX-ACCESS read-only 
		STATUS current
		DESCRIPTION  "Call Reply Retransmit Wrong Control" 
		::={ acosCgnv6LsnAlgPptpS 31 } 

		callReplyRetransmitAcquired OBJECT-TYPE
		SYNTAX  CounterBasedGauge64 
		MAX-ACCESS read-only 
		STATUS current
		DESCRIPTION  "Call Reply Retransmit Acquired" 
		::={ acosCgnv6LsnAlgPptpS 32 } 

		callReplyExtAllocFailure OBJECT-TYPE
		SYNTAX  CounterBasedGauge64 
		MAX-ACCESS read-only 
		STATUS current
		DESCRIPTION  "Call Request Ext Alloc Failure" 
		::={ acosCgnv6LsnAlgPptpS 33 } 

		smpClientCallIdMismatch OBJECT-TYPE
		SYNTAX  CounterBasedGauge64 
		MAX-ACCESS read-only 
		STATUS current
		DESCRIPTION  "SMP Client Call ID Mismatch" 
		::={ acosCgnv6LsnAlgPptpS 34 } 

		smpAllocFailure OBJECT-TYPE
		SYNTAX  CounterBasedGauge64 
		MAX-ACCESS read-only 
		STATUS current
		DESCRIPTION  "SMP Session Alloc Failure" 
		::={ acosCgnv6LsnAlgPptpS 35 } 

		greConnCreationFailure OBJECT-TYPE
		SYNTAX  CounterBasedGauge64 
		MAX-ACCESS read-only 
		STATUS current
		DESCRIPTION  "GRE Conn Alloc Failure" 
		::={ acosCgnv6LsnAlgPptpS 36 } 

		greConnExtCreationFailure OBJECT-TYPE
		SYNTAX  CounterBasedGauge64 
		MAX-ACCESS read-only 
		STATUS current
		DESCRIPTION  "GRE Conn Ext Alloc Failure" 
		::={ acosCgnv6LsnAlgPptpS 37 } 

		greNoFwdRoute OBJECT-TYPE
		SYNTAX  CounterBasedGauge64 
		MAX-ACCESS read-only 
		STATUS current
		DESCRIPTION  "GRE No Fwd Route" 
		::={ acosCgnv6LsnAlgPptpS 38 } 

		greNoRevRoute OBJECT-TYPE
		SYNTAX  CounterBasedGauge64 
		MAX-ACCESS read-only 
		STATUS current
		DESCRIPTION  "GRE No Rev Route" 
		::={ acosCgnv6LsnAlgPptpS 39 } 

		greNoControlConn OBJECT-TYPE
		SYNTAX  CounterBasedGauge64 
		MAX-ACCESS read-only 
		STATUS current
		DESCRIPTION  "GRE No Control Conn" 
		::={ acosCgnv6LsnAlgPptpS 40 } 

		greConnAlreadyExists OBJECT-TYPE
		SYNTAX  CounterBasedGauge64 
		MAX-ACCESS read-only 
		STATUS current
		DESCRIPTION  "GRE Conn Already Exists" 
		::={ acosCgnv6LsnAlgPptpS 41 } 

		greFreeNoExt OBJECT-TYPE
		SYNTAX  CounterBasedGauge64 
		MAX-ACCESS read-only 
		STATUS current
		DESCRIPTION  "GRE Free No Ext" 
		::={ acosCgnv6LsnAlgPptpS 42 } 

		greFreeNoSmp OBJECT-TYPE
		SYNTAX  CounterBasedGauge64 
		MAX-ACCESS read-only 
		STATUS current
		DESCRIPTION  "GRE Free No SMP" 
		::={ acosCgnv6LsnAlgPptpS 43 } 

		greFreeSmpAppTypeMismatch OBJECT-TYPE
		SYNTAX  CounterBasedGauge64 
		MAX-ACCESS read-only 
		STATUS current
		DESCRIPTION  "GRE Free SMP App Type Mismatch" 
		::={ acosCgnv6LsnAlgPptpS 44 } 

		controlFreed OBJECT-TYPE
		SYNTAX  CounterBasedGauge64 
		MAX-ACCESS read-only 
		STATUS current
		DESCRIPTION  "Control Session Freed" 
		::={ acosCgnv6LsnAlgPptpS 45 } 

		controlFreeNoExt OBJECT-TYPE
		SYNTAX  CounterBasedGauge64 
		MAX-ACCESS read-only 
		STATUS current
		DESCRIPTION  "Control Free No Ext" 
		::={ acosCgnv6LsnAlgPptpS 46 } 

		controlFreeNoSmp OBJECT-TYPE
		SYNTAX  CounterBasedGauge64 
		MAX-ACCESS read-only 
		STATUS current
		DESCRIPTION  "Control Free No SMP" 
		::={ acosCgnv6LsnAlgPptpS 47 } 

		controlFreeSmpAppTypeMismatch OBJECT-TYPE
		SYNTAX  CounterBasedGauge64 
		MAX-ACCESS read-only 
		STATUS current
		DESCRIPTION  "Control Free SMP App Type Mismatch" 
		::={ acosCgnv6LsnAlgPptpS 48 } 

acosCgnv6LsnAlgRtsp                 OBJECT IDENTIFIER ::= { acosCgnv6LsnAlg 4 }
acosCgnv6LsnAlgRtspS                OBJECT IDENTIFIER ::= { acosCgnv6LsnAlgRtsp 1 }

		cgnv6LsnAlgRtspStreamsCreated OBJECT-TYPE
		SYNTAX  CounterBasedGauge64 
		MAX-ACCESS read-only 
		STATUS current
		DESCRIPTION  "Streams Created" 
		::={ acosCgnv6LsnAlgRtspS 1 } 

		cgnv6LsnAlgRtspStreamsFreed OBJECT-TYPE
		SYNTAX  CounterBasedGauge64 
		MAX-ACCESS read-only 
		STATUS current
		DESCRIPTION  "Streams Freed" 
		::={ acosCgnv6LsnAlgRtspS 2 } 

		cgnv6LsnAlgRtspStreamsCreationFailure OBJECT-TYPE
		SYNTAX  CounterBasedGauge64 
		MAX-ACCESS read-only 
		STATUS current
		DESCRIPTION  "Stream Creation Failures" 
		::={ acosCgnv6LsnAlgRtspS 3 } 

		cgnv6LsnAlgRtspPortsAllocated OBJECT-TYPE
		SYNTAX  CounterBasedGauge64 
		MAX-ACCESS read-only 
		STATUS current
		DESCRIPTION  "Stream Client Ports Allocated" 
		::={ acosCgnv6LsnAlgRtspS 4 } 

		cgnv6LsnAlgRtspPortsFreed OBJECT-TYPE
		SYNTAX  CounterBasedGauge64 
		MAX-ACCESS read-only 
		STATUS current
		DESCRIPTION  "Stream Client Ports Freed" 
		::={ acosCgnv6LsnAlgRtspS 5 } 

		cgnv6LsnAlgRtspPortAllocationFailure OBJECT-TYPE
		SYNTAX  CounterBasedGauge64 
		MAX-ACCESS read-only 
		STATUS current
		DESCRIPTION  "Stream Client Port Allocation Failures" 
		::={ acosCgnv6LsnAlgRtspS 6 } 

		cgnv6LsnAlgRtspUnknownClientPortFromServer OBJECT-TYPE
		SYNTAX  CounterBasedGauge64 
		MAX-ACCESS read-only 
		STATUS current
		DESCRIPTION  "Server Replies With Unknown Client Ports" 
		::={ acosCgnv6LsnAlgRtspS 7 } 

		cgnv6LsnAlgRtspDataSessionCreated OBJECT-TYPE
		SYNTAX  CounterBasedGauge64 
		MAX-ACCESS read-only 
		STATUS current
		DESCRIPTION  "Data Session Created" 
		::={ acosCgnv6LsnAlgRtspS 8 } 

		cgnv6LsnAlgRtspDataSessionFreed OBJECT-TYPE
		SYNTAX  CounterBasedGauge64 
		MAX-ACCESS read-only 
		STATUS current
		DESCRIPTION  "Data Session Freed" 
		::={ acosCgnv6LsnAlgRtspS 9 } 

		cgnv6LsnAlgRtspNoSessionMem OBJECT-TYPE
		SYNTAX  CounterBasedGauge64 
		MAX-ACCESS read-only 
		STATUS current
		DESCRIPTION  "Data Session Creation Failures" 
		::={ acosCgnv6LsnAlgRtspS 10 } 

		haSent OBJECT-TYPE
		SYNTAX  CounterBasedGauge64 
		MAX-ACCESS read-only 
		STATUS current
		DESCRIPTION  "HA Sent" 
		::={ acosCgnv6LsnAlgRtspS 11 } 

		haRcv OBJECT-TYPE
		SYNTAX  CounterBasedGauge64 
		MAX-ACCESS read-only 
		STATUS current
		DESCRIPTION  "HA RCV" 
		::={ acosCgnv6LsnAlgRtspS 12 } 

		smpInserted OBJECT-TYPE
		SYNTAX  CounterBasedGauge64 
		MAX-ACCESS read-only 
		STATUS current
		DESCRIPTION  "SMP Session Inserted" 
		::={ acosCgnv6LsnAlgRtspS 13 } 

		smpRemoved OBJECT-TYPE
		SYNTAX  CounterBasedGauge64 
		MAX-ACCESS read-only 
		STATUS current
		DESCRIPTION  "SMP Session Removed" 
		::={ acosCgnv6LsnAlgRtspS 14 } 

		smpReused OBJECT-TYPE
		SYNTAX  CounterBasedGauge64 
		MAX-ACCESS read-only 
		STATUS current
		DESCRIPTION  "SMP Session Reused" 
		::={ acosCgnv6LsnAlgRtspS 15 } 

		natPoolStandby OBJECT-TYPE
		SYNTAX  CounterBasedGauge64 
		MAX-ACCESS read-only 
		STATUS current
		DESCRIPTION  "New Session NAT Pool Standby" 
		::={ acosCgnv6LsnAlgRtspS 16 } 

		smpDeleted OBJECT-TYPE
		SYNTAX  CounterBasedGauge64 
		MAX-ACCESS read-only 
		STATUS current
		DESCRIPTION  "New Session SMP Already Deleted" 
		::={ acosCgnv6LsnAlgRtspS 17 } 

		controlClosed OBJECT-TYPE
		SYNTAX  CounterBasedGauge64 
		MAX-ACCESS read-only 
		STATUS current
		DESCRIPTION  "New Session Closed" 
		::={ acosCgnv6LsnAlgRtspS 18 } 

		dataSessionExists OBJECT-TYPE
		SYNTAX  CounterBasedGauge64 
		MAX-ACCESS read-only 
		STATUS current
		DESCRIPTION  "New Session Already Exists" 
		::={ acosCgnv6LsnAlgRtspS 19 } 

		dataSessionCreationFailure OBJECT-TYPE
		SYNTAX  CounterBasedGauge64 
		MAX-ACCESS read-only 
		STATUS current
		DESCRIPTION  "New Data Session Creation Failure" 
		::={ acosCgnv6LsnAlgRtspS 20 } 

		rtpReversed OBJECT-TYPE
		SYNTAX  CounterBasedGauge64 
		MAX-ACCESS read-only 
		STATUS current
		DESCRIPTION  "RTP Reverse Creation" 
		::={ acosCgnv6LsnAlgRtspS 21 } 

		rtcpReversed OBJECT-TYPE
		SYNTAX  CounterBasedGauge64 
		MAX-ACCESS read-only 
		STATUS current
		DESCRIPTION  "RTCP Reverse Creation" 
		::={ acosCgnv6LsnAlgRtspS 22 } 

		crossCpuSent OBJECT-TYPE
		SYNTAX  CounterBasedGauge64 
		MAX-ACCESS read-only 
		STATUS current
		DESCRIPTION  "Cross CPU Sent" 
		::={ acosCgnv6LsnAlgRtspS 23 } 

		crossCpuRcv OBJECT-TYPE
		SYNTAX  CounterBasedGauge64 
		MAX-ACCESS read-only 
		STATUS current
		DESCRIPTION  "Cross CPU Received" 
		::={ acosCgnv6LsnAlgRtspS 24 } 

		crossCpuNoSession OBJECT-TYPE
		SYNTAX  CounterBasedGauge64 
		MAX-ACCESS read-only 
		STATUS current
		DESCRIPTION  "Cross CPU No Session Found" 
		::={ acosCgnv6LsnAlgRtspS 25 } 

		crossCpuCreated OBJECT-TYPE
		SYNTAX  CounterBasedGauge64 
		MAX-ACCESS read-only 
		STATUS current
		DESCRIPTION  "Cross CPU Creation" 
		::={ acosCgnv6LsnAlgRtspS 26 } 

		crossCpuRcvFailure OBJECT-TYPE
		SYNTAX  CounterBasedGauge64 
		MAX-ACCESS read-only 
		STATUS current
		DESCRIPTION  "Cross CPU Receive Failure" 
		::={ acosCgnv6LsnAlgRtspS 27 } 

		dataFreeSmpRetryLookup OBJECT-TYPE
		SYNTAX  CounterBasedGauge64 
		MAX-ACCESS read-only 
		STATUS current
		DESCRIPTION  "Data Session Free SMP Retry Lookup" 
		::={ acosCgnv6LsnAlgRtspS 28 } 

		dataFreeSmpNotFound OBJECT-TYPE
		SYNTAX  CounterBasedGauge64 
		MAX-ACCESS read-only 
		STATUS current
		DESCRIPTION  "Data Session Free SMP Not Found" 
		::={ acosCgnv6LsnAlgRtspS 29 } 

		haStreamsSent OBJECT-TYPE
		SYNTAX  CounterBasedGauge64 
		MAX-ACCESS read-only 
		STATUS current
		DESCRIPTION  "HA Streams Sent" 
		::={ acosCgnv6LsnAlgRtspS 30 } 

		haStreamsRcv OBJECT-TYPE
		SYNTAX  CounterBasedGauge64 
		MAX-ACCESS read-only 
		STATUS current
		DESCRIPTION  "HA Streams Received" 
		::={ acosCgnv6LsnAlgRtspS 31 } 

		haStreamIncompatible OBJECT-TYPE
		SYNTAX  CounterBasedGauge64 
		MAX-ACCESS read-only 
		STATUS current
		DESCRIPTION  "HA Incompatible Streams Received" 
		::={ acosCgnv6LsnAlgRtspS 32 } 

		haStreamExists OBJECT-TYPE
		SYNTAX  CounterBasedGauge64 
		MAX-ACCESS read-only 
		STATUS current
		DESCRIPTION  "HA Stream Already Exists" 
		::={ acosCgnv6LsnAlgRtspS 33 } 

		haPortAllocationFailure OBJECT-TYPE
		SYNTAX  CounterBasedGauge64 
		MAX-ACCESS read-only 
		STATUS current
		DESCRIPTION  "HA Stream Port Allocation Failure" 
		::={ acosCgnv6LsnAlgRtspS 34 } 

		haDataSessionSent OBJECT-TYPE
		SYNTAX  CounterBasedGauge64 
		MAX-ACCESS read-only 
		STATUS current
		DESCRIPTION  "HA Data Session Sent" 
		::={ acosCgnv6LsnAlgRtspS 35 } 

		haDataSessionRcv OBJECT-TYPE
		SYNTAX  CounterBasedGauge64 
		MAX-ACCESS read-only 
		STATUS current
		DESCRIPTION  "HA Data Session Received" 
		::={ acosCgnv6LsnAlgRtspS 36 } 

		haDataNoSmp OBJECT-TYPE
		SYNTAX  CounterBasedGauge64 
		MAX-ACCESS read-only 
		STATUS current
		DESCRIPTION  "HA Data Session SMP Not Found" 
		::={ acosCgnv6LsnAlgRtspS 37 } 

		haControlClosed OBJECT-TYPE
		SYNTAX  CounterBasedGauge64 
		MAX-ACCESS read-only 
		STATUS current
		DESCRIPTION  "HA New Data Control Session Closed" 
		::={ acosCgnv6LsnAlgRtspS 38 } 

		haDataExists OBJECT-TYPE
		SYNTAX  CounterBasedGauge64 
		MAX-ACCESS read-only 
		STATUS current
		DESCRIPTION  "HA New Data Session Already Exists" 
		::={ acosCgnv6LsnAlgRtspS 39 } 

		haExtensionFailure OBJECT-TYPE
		SYNTAX  CounterBasedGauge64 
		MAX-ACCESS read-only 
		STATUS current
		DESCRIPTION  "HA Conn Extension Failure" 
		::={ acosCgnv6LsnAlgRtspS 40 } 

		haStreamSmpReused OBJECT-TYPE
		SYNTAX  CounterBasedGauge64 
		MAX-ACCESS read-only 
		STATUS current
		DESCRIPTION  "HA SMP Session Reused" 
		::={ acosCgnv6LsnAlgRtspS 41 } 

		haStreamSmpAcquireFailure OBJECT-TYPE
		SYNTAX  CounterBasedGauge64 
		MAX-ACCESS read-only 
		STATUS current
		DESCRIPTION  "HA SMP Session Acquire Failure" 
		::={ acosCgnv6LsnAlgRtspS 42 } 

		smpAppTypeMismatch OBJECT-TYPE
		SYNTAX  CounterBasedGauge64 
		MAX-ACCESS read-only 
		STATUS current
		DESCRIPTION  "SMP ALG App Type Mismatch" 
		::={ acosCgnv6LsnAlgRtspS 43 } 

acosCgnv6LsnAlgSip                  OBJECT IDENTIFIER ::= { acosCgnv6LsnAlg 6 }
acosCgnv6LsnAlgSipS                 OBJECT IDENTIFIER ::= { acosCgnv6LsnAlgSip 1 }

		lsnAlgSipMethodRegister OBJECT-TYPE
		SYNTAX  CounterBasedGauge64 
		MAX-ACCESS read-only 
		STATUS current
		DESCRIPTION  "SIP Method REGISTER" 
		::={ acosCgnv6LsnAlgSipS 1 } 

		lsnAlgSipMethodInvite OBJECT-TYPE
		SYNTAX  CounterBasedGauge64 
		MAX-ACCESS read-only 
		STATUS current
		DESCRIPTION  "SIP Method INVITE" 
		::={ acosCgnv6LsnAlgSipS 2 } 

		lsnAlgSipMethodAck OBJECT-TYPE
		SYNTAX  CounterBasedGauge64 
		MAX-ACCESS read-only 
		STATUS current
		DESCRIPTION  "SIP Method ACK" 
		::={ acosCgnv6LsnAlgSipS 3 } 

		lsnAlgSipMethodCancel OBJECT-TYPE
		SYNTAX  CounterBasedGauge64 
		MAX-ACCESS read-only 
		STATUS current
		DESCRIPTION  "SIP Method CANCEL" 
		::={ acosCgnv6LsnAlgSipS 4 } 

		lsnAlgSipMethodBye OBJECT-TYPE
		SYNTAX  CounterBasedGauge64 
		MAX-ACCESS read-only 
		STATUS current
		DESCRIPTION  "SIP Method BYE" 
		::={ acosCgnv6LsnAlgSipS 5 } 

		lsnAlgSipMethodOption OBJECT-TYPE
		SYNTAX  CounterBasedGauge64 
		MAX-ACCESS read-only 
		STATUS current
		DESCRIPTION  "SIP Method OPTIONS" 
		::={ acosCgnv6LsnAlgSipS 6 } 

		lsnAlgSipMethodPrack OBJECT-TYPE
		SYNTAX  CounterBasedGauge64 
		MAX-ACCESS read-only 
		STATUS current
		DESCRIPTION  "SIP Method PRACK" 
		::={ acosCgnv6LsnAlgSipS 7 } 

		lsnAlgSipMethodSubscribe OBJECT-TYPE
		SYNTAX  CounterBasedGauge64 
		MAX-ACCESS read-only 
		STATUS current
		DESCRIPTION  "SIP Method SUBSCRIBE" 
		::={ acosCgnv6LsnAlgSipS 8 } 

		lsnAlgSipMethodNotify OBJECT-TYPE
		SYNTAX  CounterBasedGauge64 
		MAX-ACCESS read-only 
		STATUS current
		DESCRIPTION  "SIP Method NOTIFY" 
		::={ acosCgnv6LsnAlgSipS 9 } 

		lsnAlgSipMethodPublish OBJECT-TYPE
		SYNTAX  CounterBasedGauge64 
		MAX-ACCESS read-only 
		STATUS current
		DESCRIPTION  "SIP Method PUBLISH" 
		::={ acosCgnv6LsnAlgSipS 10 } 

		lsnAlgSipMethodInfo OBJECT-TYPE
		SYNTAX  CounterBasedGauge64 
		MAX-ACCESS read-only 
		STATUS current
		DESCRIPTION  "SIP Method INFO" 
		::={ acosCgnv6LsnAlgSipS 11 } 

		lsnAlgSipMethodRefer OBJECT-TYPE
		SYNTAX  CounterBasedGauge64 
		MAX-ACCESS read-only 
		STATUS current
		DESCRIPTION  "SIP Method REFER" 
		::={ acosCgnv6LsnAlgSipS 12 } 

		lsnAlgSipMethodMessage OBJECT-TYPE
		SYNTAX  CounterBasedGauge64 
		MAX-ACCESS read-only 
		STATUS current
		DESCRIPTION  "SIP Method MESSAGE" 
		::={ acosCgnv6LsnAlgSipS 13 } 

		lsnAlgSipMethodUpdate OBJECT-TYPE
		SYNTAX  CounterBasedGauge64 
		MAX-ACCESS read-only 
		STATUS current
		DESCRIPTION  "SIP Method UPDATE" 
		::={ acosCgnv6LsnAlgSipS 14 } 

		lsnAlgSipMethodUnkown OBJECT-TYPE
		SYNTAX  CounterBasedGauge64 
		MAX-ACCESS read-only 
		STATUS current
		DESCRIPTION  "SIP Method UNKNOWN" 
		::={ acosCgnv6LsnAlgSipS 15 } 

		parseError OBJECT-TYPE
		SYNTAX  CounterBasedGauge64 
		MAX-ACCESS read-only 
		STATUS current
		DESCRIPTION  "SIP Message Parse Error" 
		::={ acosCgnv6LsnAlgSipS 16 } 

		reqUriOpFailrue OBJECT-TYPE
		SYNTAX  CounterBasedGauge64 
		MAX-ACCESS read-only 
		STATUS current
		DESCRIPTION  "SIP Operate Request Uri Failure" 
		::={ acosCgnv6LsnAlgSipS 17 } 

		viaHdrOpFailrue OBJECT-TYPE
		SYNTAX  CounterBasedGauge64 
		MAX-ACCESS read-only 
		STATUS current
		DESCRIPTION  "SIP Operate Via Header Failure" 
		::={ acosCgnv6LsnAlgSipS 18 } 

		contactHdrOpFailrue OBJECT-TYPE
		SYNTAX  CounterBasedGauge64 
		MAX-ACCESS read-only 
		STATUS current
		DESCRIPTION  "SIP Operate Contact Header Failure" 
		::={ acosCgnv6LsnAlgSipS 19 } 

		fromHdrOpFailrue OBJECT-TYPE
		SYNTAX  CounterBasedGauge64 
		MAX-ACCESS read-only 
		STATUS current
		DESCRIPTION  "SIP Operate From Header Failure" 
		::={ acosCgnv6LsnAlgSipS 20 } 

		toHdrOpFailrue OBJECT-TYPE
		SYNTAX  CounterBasedGauge64 
		MAX-ACCESS read-only 
		STATUS current
		DESCRIPTION  "SIP Operate To Header Failure" 
		::={ acosCgnv6LsnAlgSipS 21 } 

		routeHdrOpFailrue OBJECT-TYPE
		SYNTAX  CounterBasedGauge64 
		MAX-ACCESS read-only 
		STATUS current
		DESCRIPTION  "SIP Operate Route Header Failure" 
		::={ acosCgnv6LsnAlgSipS 22 } 

		recordRouteHdrOpFailrue OBJECT-TYPE
		SYNTAX  CounterBasedGauge64 
		MAX-ACCESS read-only 
		STATUS current
		DESCRIPTION  "SIP Operate Record-Route Header Failure" 
		::={ acosCgnv6LsnAlgSipS 23 } 

		contentLengthHdrOpFailrue OBJECT-TYPE
		SYNTAX  CounterBasedGauge64 
		MAX-ACCESS read-only 
		STATUS current
		DESCRIPTION  "SIP Operate Content-Length Failure" 
		::={ acosCgnv6LsnAlgSipS 24 } 

		thirdPartyRegistration OBJECT-TYPE
		SYNTAX  CounterBasedGauge64 
		MAX-ACCESS read-only 
		STATUS current
		DESCRIPTION  "SIP Third-Party Registration" 
		::={ acosCgnv6LsnAlgSipS 25 } 

		connExtCreationFailure OBJECT-TYPE
		SYNTAX  CounterBasedGauge64 
		MAX-ACCESS read-only 
		STATUS current
		DESCRIPTION  "SIP Create Connection Extension Failure" 
		::={ acosCgnv6LsnAlgSipS 26 } 

		allocContactPortFailure OBJECT-TYPE
		SYNTAX  CounterBasedGauge64 
		MAX-ACCESS read-only 
		STATUS current
		DESCRIPTION  "SIP Alloc Contact Port Failure" 
		::={ acosCgnv6LsnAlgSipS 27 } 

		outsideContactPortMismatch OBJECT-TYPE
		SYNTAX  CounterBasedGauge64 
		MAX-ACCESS read-only 
		STATUS current
		DESCRIPTION  "SIP Outside Contact Port Mismatch NAT Port" 
		::={ acosCgnv6LsnAlgSipS 28 } 

		insideContactPortMismatch OBJECT-TYPE
		SYNTAX  CounterBasedGauge64 
		MAX-ACCESS read-only 
		STATUS current
		DESCRIPTION  "SIP Inside Contact Port Mismatch" 
		::={ acosCgnv6LsnAlgSipS 29 } 

		thirdPartySdp OBJECT-TYPE
		SYNTAX  CounterBasedGauge64 
		MAX-ACCESS read-only 
		STATUS current
		DESCRIPTION  "SIP Third-Party SDP" 
		::={ acosCgnv6LsnAlgSipS 30 } 

		sdpProcessCandidateFailure OBJECT-TYPE
		SYNTAX  CounterBasedGauge64 
		MAX-ACCESS read-only 
		STATUS current
		DESCRIPTION  "SIP Operate SDP Media Candidate Attribute Failure" 
		::={ acosCgnv6LsnAlgSipS 31 } 

		sdpOpFailure OBJECT-TYPE
		SYNTAX  CounterBasedGauge64 
		MAX-ACCESS read-only 
		STATUS current
		DESCRIPTION  "SIP Operate SDP Failure" 
		::={ acosCgnv6LsnAlgSipS 32 } 

		sdpAllocPortMapSuccess OBJECT-TYPE
		SYNTAX  CounterBasedGauge64 
		MAX-ACCESS read-only 
		STATUS current
		DESCRIPTION  "SIP Alloc SDP Port Map Success" 
		::={ acosCgnv6LsnAlgSipS 33 } 

		sdpAllocPortMapFailure OBJECT-TYPE
		SYNTAX  CounterBasedGauge64 
		MAX-ACCESS read-only 
		STATUS current
		DESCRIPTION  "SIP Alloc SDP Port Map Failure" 
		::={ acosCgnv6LsnAlgSipS 34 } 

		modifyFailure OBJECT-TYPE
		SYNTAX  CounterBasedGauge64 
		MAX-ACCESS read-only 
		STATUS current
		DESCRIPTION  "SIP Message Modify Failure" 
		::={ acosCgnv6LsnAlgSipS 35 } 

		rewriteFailure OBJECT-TYPE
		SYNTAX  CounterBasedGauge64 
		MAX-ACCESS read-only 
		STATUS current
		DESCRIPTION  "SIP Message Rewrite Failure" 
		::={ acosCgnv6LsnAlgSipS 36 } 

		tcpOutOfOrderDrop OBJECT-TYPE
		SYNTAX  CounterBasedGauge64 
		MAX-ACCESS read-only 
		STATUS current
		DESCRIPTION  "TCP Out-of-Order Drop" 
		::={ acosCgnv6LsnAlgSipS 37 } 

		smpConnAllocFailure OBJECT-TYPE
		SYNTAX  CounterBasedGauge64 
		MAX-ACCESS read-only 
		STATUS current
		DESCRIPTION  "SMP Helper Conn Alloc Failure" 
		::={ acosCgnv6LsnAlgSipS 38 } 

		helperFound OBJECT-TYPE
		SYNTAX  CounterBasedGauge64 
		MAX-ACCESS read-only 
		STATUS current
		DESCRIPTION  "SMP Helper Conn Found" 
		::={ acosCgnv6LsnAlgSipS 39 } 

		helperCreated OBJECT-TYPE
		SYNTAX  CounterBasedGauge64 
		MAX-ACCESS read-only 
		STATUS current
		DESCRIPTION  "SMP Helper Conn Created" 
		::={ acosCgnv6LsnAlgSipS 40 } 

		helperDeleted OBJECT-TYPE
		SYNTAX  CounterBasedGauge64 
		MAX-ACCESS read-only 
		STATUS current
		DESCRIPTION  "SMP Helper Conn Already Deleted" 
		::={ acosCgnv6LsnAlgSipS 41 } 

		helperFreed OBJECT-TYPE
		SYNTAX  CounterBasedGauge64 
		MAX-ACCESS read-only 
		STATUS current
		DESCRIPTION  "SMP Helper Conn Freed" 
		::={ acosCgnv6LsnAlgSipS 42 } 

		helperFailure OBJECT-TYPE
		SYNTAX  CounterBasedGauge64 
		MAX-ACCESS read-only 
		STATUS current
		DESCRIPTION  "SMP Helper Failure" 
		::={ acosCgnv6LsnAlgSipS 43 } 

acosCgnv6LsnAlgMgcp                 OBJECT IDENTIFIER ::= { acosCgnv6LsnAlg 7 }
acosCgnv6LsnAlgMgcpS                OBJECT IDENTIFIER ::= { acosCgnv6LsnAlgMgcp 1 }

		auep OBJECT-TYPE
		SYNTAX  CounterBasedGauge64 
		MAX-ACCESS read-only 
		STATUS current
		DESCRIPTION  "MGCP AUEP" 
		::={ acosCgnv6LsnAlgMgcpS 1 } 

		aucx OBJECT-TYPE
		SYNTAX  CounterBasedGauge64 
		MAX-ACCESS read-only 
		STATUS current
		DESCRIPTION  "MGCP AUCX" 
		::={ acosCgnv6LsnAlgMgcpS 2 } 

		crcx OBJECT-TYPE
		SYNTAX  CounterBasedGauge64 
		MAX-ACCESS read-only 
		STATUS current
		DESCRIPTION  "MGCP CRCX" 
		::={ acosCgnv6LsnAlgMgcpS 3 } 

		dlcx OBJECT-TYPE
		SYNTAX  CounterBasedGauge64 
		MAX-ACCESS read-only 
		STATUS current
		DESCRIPTION  "MGCP DLCX" 
		::={ acosCgnv6LsnAlgMgcpS 4 } 

		epcf OBJECT-TYPE
		SYNTAX  CounterBasedGauge64 
		MAX-ACCESS read-only 
		STATUS current
		DESCRIPTION  "MGCP EPCF" 
		::={ acosCgnv6LsnAlgMgcpS 5 } 

		mdcx OBJECT-TYPE
		SYNTAX  CounterBasedGauge64 
		MAX-ACCESS read-only 
		STATUS current
		DESCRIPTION  "MGCP MDCX" 
		::={ acosCgnv6LsnAlgMgcpS 6 } 

		ntfy OBJECT-TYPE
		SYNTAX  CounterBasedGauge64 
		MAX-ACCESS read-only 
		STATUS current
		DESCRIPTION  "MGCP NTFY" 
		::={ acosCgnv6LsnAlgMgcpS 7 } 

		rqnt OBJECT-TYPE
		SYNTAX  CounterBasedGauge64 
		MAX-ACCESS read-only 
		STATUS current
		DESCRIPTION  "MGCP RQNT" 
		::={ acosCgnv6LsnAlgMgcpS 8 } 

		rsip OBJECT-TYPE
		SYNTAX  CounterBasedGauge64 
		MAX-ACCESS read-only 
		STATUS current
		DESCRIPTION  "MGCP RSIP" 
		::={ acosCgnv6LsnAlgMgcpS 9 } 

		parseError OBJECT-TYPE
		SYNTAX  CounterBasedGauge64 
		MAX-ACCESS read-only 
		STATUS current
		DESCRIPTION  "MGCP Message Parse Error" 
		::={ acosCgnv6LsnAlgMgcpS 10 } 

		connExtCreationFailure OBJECT-TYPE
		SYNTAX  CounterBasedGauge64 
		MAX-ACCESS read-only 
		STATUS current
		DESCRIPTION  "MGCP Create Connection Extension Failure" 
		::={ acosCgnv6LsnAlgMgcpS 11 } 

		thirdPartySdp OBJECT-TYPE
		SYNTAX  CounterBasedGauge64 
		MAX-ACCESS read-only 
		STATUS current
		DESCRIPTION  "MGCP Third-Party SDP" 
		::={ acosCgnv6LsnAlgMgcpS 12 } 

		sdpProcessCandidateFailure OBJECT-TYPE
		SYNTAX  CounterBasedGauge64 
		MAX-ACCESS read-only 
		STATUS current
		DESCRIPTION  "MGCP Operate SDP Media Candidate Attribute Failure" 
		::={ acosCgnv6LsnAlgMgcpS 13 } 

		sdpOpFailure OBJECT-TYPE
		SYNTAX  CounterBasedGauge64 
		MAX-ACCESS read-only 
		STATUS current
		DESCRIPTION  "MGCP Operate SDP Failure" 
		::={ acosCgnv6LsnAlgMgcpS 14 } 

		sdpAllocPortMapSuccess OBJECT-TYPE
		SYNTAX  CounterBasedGauge64 
		MAX-ACCESS read-only 
		STATUS current
		DESCRIPTION  "MGCP Alloc SDP Port Map Success" 
		::={ acosCgnv6LsnAlgMgcpS 15 } 

		sdpAllocPortMapFailure OBJECT-TYPE
		SYNTAX  CounterBasedGauge64 
		MAX-ACCESS read-only 
		STATUS current
		DESCRIPTION  "MGCP Alloc SDP Port Map Failure" 
		::={ acosCgnv6LsnAlgMgcpS 16 } 

		modifyFailure OBJECT-TYPE
		SYNTAX  CounterBasedGauge64 
		MAX-ACCESS read-only 
		STATUS current
		DESCRIPTION  "MGCP Message Modify Failure" 
		::={ acosCgnv6LsnAlgMgcpS 17 } 

		rewriteFailure OBJECT-TYPE
		SYNTAX  CounterBasedGauge64 
		MAX-ACCESS read-only 
		STATUS current
		DESCRIPTION  "MGCP Message Rewrite Failure" 
		::={ acosCgnv6LsnAlgMgcpS 18 } 

		tcpOutOfOrderDrop OBJECT-TYPE
		SYNTAX  CounterBasedGauge64 
		MAX-ACCESS read-only 
		STATUS current
		DESCRIPTION  "TCP Out-of-Order Drop" 
		::={ acosCgnv6LsnAlgMgcpS 19 } 

acosCgnv6LsnAlgH323                 OBJECT IDENTIFIER ::= { acosCgnv6LsnAlg 8 }
acosCgnv6LsnAlgH323S                OBJECT IDENTIFIER ::= { acosCgnv6LsnAlgH323 1 }

		h225rasMessage OBJECT-TYPE
		SYNTAX  CounterBasedGauge64 
		MAX-ACCESS read-only 
		STATUS current
		DESCRIPTION  "H323 H225 RAS Message" 
		::={ acosCgnv6LsnAlgH323S 1 } 

		h225csMessage OBJECT-TYPE
		SYNTAX  CounterBasedGauge64 
		MAX-ACCESS read-only 
		STATUS current
		DESCRIPTION  "H323 H225 Call Signaling Message" 
		::={ acosCgnv6LsnAlgH323S 2 } 

		h245ctlMessage OBJECT-TYPE
		SYNTAX  CounterBasedGauge64 
		MAX-ACCESS read-only 
		STATUS current
		DESCRIPTION  "H323 H245 Media Control Message" 
		::={ acosCgnv6LsnAlgH323S 3 } 

		h245Tunneled OBJECT-TYPE
		SYNTAX  CounterBasedGauge64 
		MAX-ACCESS read-only 
		STATUS current
		DESCRIPTION  "H323 H245 Tunnelled Message" 
		::={ acosCgnv6LsnAlgH323S 4 } 

		fastStart OBJECT-TYPE
		SYNTAX  CounterBasedGauge64 
		MAX-ACCESS read-only 
		STATUS current
		DESCRIPTION  "H323 FastStart" 
		::={ acosCgnv6LsnAlgH323S 5 } 

		parseError OBJECT-TYPE
		SYNTAX  CounterBasedGauge64 
		MAX-ACCESS read-only 
		STATUS current
		DESCRIPTION  "Message Parse Error" 
		::={ acosCgnv6LsnAlgH323S 6 } 

		messageCrossMultiPackets OBJECT-TYPE
		SYNTAX  CounterBasedGauge64 
		MAX-ACCESS read-only 
		STATUS current
		DESCRIPTION  "H323 Message Cross Multiple Packets" 
		::={ acosCgnv6LsnAlgH323S 7 } 

		connExtCreationFailure OBJECT-TYPE
		SYNTAX  CounterBasedGauge64 
		MAX-ACCESS read-only 
		STATUS current
		DESCRIPTION  "H323 Packet Rewrite Failure" 
		::={ acosCgnv6LsnAlgH323S 8 } 

		rewriteFailure OBJECT-TYPE
		SYNTAX  CounterBasedGauge64 
		MAX-ACCESS read-only 
		STATUS current
		DESCRIPTION  "H323 Message Rewrite Failure" 
		::={ acosCgnv6LsnAlgH323S 9 } 

		tcpOutOfOrderDrop OBJECT-TYPE
		SYNTAX  CounterBasedGauge64 
		MAX-ACCESS read-only 
		STATUS current
		DESCRIPTION  "TCP Out-of-Order Drop" 
		::={ acosCgnv6LsnAlgH323S 10 } 

		h245DynamicAddrExceed OBJECT-TYPE
		SYNTAX  CounterBasedGauge64 
		MAX-ACCESS read-only 
		STATUS current
		DESCRIPTION  "H323 H245 Dynamic Address Exceed" 
		::={ acosCgnv6LsnAlgH323S 11 } 

acosCgnv6LsnAlgTftp                 OBJECT IDENTIFIER ::= { acosCgnv6LsnAlg 9 }
acosCgnv6LsnAlgTftpS                OBJECT IDENTIFIER ::= { acosCgnv6LsnAlgTftp 1 }

		cgnv6LsnAlgTftpSessionCreated OBJECT-TYPE
		SYNTAX  CounterBasedGauge64 
		MAX-ACCESS read-only 
		STATUS current
		DESCRIPTION  "TFTP Client Sessions Created" 
		::={ acosCgnv6LsnAlgTftpS 1 } 

		helperCreated OBJECT-TYPE
		SYNTAX  CounterBasedGauge64 
		MAX-ACCESS read-only 
		STATUS current
		DESCRIPTION  "TFTP Helper Sessions created" 
		::={ acosCgnv6LsnAlgTftpS 2 } 

		helperFreed OBJECT-TYPE
		SYNTAX  CounterBasedGauge64 
		MAX-ACCESS read-only 
		STATUS current
		DESCRIPTION  "TFTP Helper Sessions freed" 
		::={ acosCgnv6LsnAlgTftpS 3 } 

		helperFreedUsed OBJECT-TYPE
		SYNTAX  CounterBasedGauge64 
		MAX-ACCESS read-only 
		STATUS current
		DESCRIPTION  "TFTP Helper Sessions freed used" 
		::={ acosCgnv6LsnAlgTftpS 4 } 

		helperFreedUnused OBJECT-TYPE
		SYNTAX  CounterBasedGauge64 
		MAX-ACCESS read-only 
		STATUS current
		DESCRIPTION  "TFTP Helper Sessions freed unused" 
		::={ acosCgnv6LsnAlgTftpS 5 } 

		helperAlreadyUsed OBJECT-TYPE
		SYNTAX  CounterBasedGauge64 
		MAX-ACCESS read-only 
		STATUS current
		DESCRIPTION  "TFTP Helper Session already used" 
		::={ acosCgnv6LsnAlgTftpS 6 } 

		helperInRml OBJECT-TYPE
		SYNTAX  CounterBasedGauge64 
		MAX-ACCESS read-only 
		STATUS current
		DESCRIPTION  "TFTP Helper Session in Remove List" 
		::={ acosCgnv6LsnAlgTftpS 7 } 

acosCgnv6LsnRadius                  OBJECT IDENTIFIER ::= { acosCgnv6Lsn 11 }
acosCgnv6LsnRadiusServer            OBJECT IDENTIFIER ::= { acosCgnv6LsnRadius 1 }
acosCgnv6LsnRadiusServerS           OBJECT IDENTIFIER ::= { acosCgnv6LsnRadiusServer 1 }

		msisdnReceived OBJECT-TYPE
		SYNTAX  CounterBasedGauge64 
		MAX-ACCESS read-only 
		STATUS current
		DESCRIPTION  "MSISDN Received" 
		::={ acosCgnv6LsnRadiusServerS 1 } 

		imeiReceived OBJECT-TYPE
		SYNTAX  CounterBasedGauge64 
		MAX-ACCESS read-only 
		STATUS current
		DESCRIPTION  "IMEI Received" 
		::={ acosCgnv6LsnRadiusServerS 2 } 

		imsiReceived OBJECT-TYPE
		SYNTAX  CounterBasedGauge64 
		MAX-ACCESS read-only 
		STATUS current
		DESCRIPTION  "IMSI Received" 
		::={ acosCgnv6LsnRadiusServerS 3 } 

		customReceived OBJECT-TYPE
		SYNTAX  CounterBasedGauge64 
		MAX-ACCESS read-only 
		STATUS current
		DESCRIPTION  "Custom attribute Received" 
		::={ acosCgnv6LsnRadiusServerS 4 } 

		radiusRequestReceived OBJECT-TYPE
		SYNTAX  CounterBasedGauge64 
		MAX-ACCESS read-only 
		STATUS current
		DESCRIPTION  "RADIUS Request Received" 
		::={ acosCgnv6LsnRadiusServerS 5 } 

		radiusRequestDropped OBJECT-TYPE
		SYNTAX  CounterBasedGauge64 
		MAX-ACCESS read-only 
		STATUS current
		DESCRIPTION  "RADIUS Request Dropped (Malformed Packet)" 
		::={ acosCgnv6LsnRadiusServerS 6 } 

		requestBadSecretDropped OBJECT-TYPE
		SYNTAX  CounterBasedGauge64 
		MAX-ACCESS read-only 
		STATUS current
		DESCRIPTION  "RADIUS Request Bad Secret Dropped" 
		::={ acosCgnv6LsnRadiusServerS 7 } 

		requestNoKeyVapDropped OBJECT-TYPE
		SYNTAX  CounterBasedGauge64 
		MAX-ACCESS read-only 
		STATUS current
		DESCRIPTION  "RADIUS Request No Key Attribute Dropped" 
		::={ acosCgnv6LsnRadiusServerS 8 } 

		requestMalformedDropped OBJECT-TYPE
		SYNTAX  CounterBasedGauge64 
		MAX-ACCESS read-only 
		STATUS current
		DESCRIPTION  "RADIUS Request Malformed Dropped" 
		::={ acosCgnv6LsnRadiusServerS 9 } 

		requestIgnored OBJECT-TYPE
		SYNTAX  CounterBasedGauge64 
		MAX-ACCESS read-only 
		STATUS current
		DESCRIPTION  "RADIUS Request Ignored" 
		::={ acosCgnv6LsnRadiusServerS 10 } 

		radiusTableFull OBJECT-TYPE
		SYNTAX  CounterBasedGauge64 
		MAX-ACCESS read-only 
		STATUS current
		DESCRIPTION  "RADIUS Request Dropped (Table Full)" 
		::={ acosCgnv6LsnRadiusServerS 11 } 

		secretNotConfiguredDropped OBJECT-TYPE
		SYNTAX  CounterBasedGauge64 
		MAX-ACCESS read-only 
		STATUS current
		DESCRIPTION  "RADIUS Secret Not Configured Dropped" 
		::={ acosCgnv6LsnRadiusServerS 12 } 

		haStandbyDropped OBJECT-TYPE
		SYNTAX  CounterBasedGauge64 
		MAX-ACCESS read-only 
		STATUS current
		DESCRIPTION  "HA Standby Dropped" 
		::={ acosCgnv6LsnRadiusServerS 13 } 

		ipv6PrefixLengthMismatch OBJECT-TYPE
		SYNTAX  CounterBasedGauge64 
		MAX-ACCESS read-only 
		STATUS current
		DESCRIPTION  "Framed IPV6 Prefix Length Mismatch" 
		::={ acosCgnv6LsnRadiusServerS 14 } 

		invalidKey OBJECT-TYPE
		SYNTAX  CounterBasedGauge64 
		MAX-ACCESS read-only 
		STATUS current
		DESCRIPTION  "Radius Request has Invalid Key Field" 
		::={ acosCgnv6LsnRadiusServerS 15 } 

		smpCreated OBJECT-TYPE
		SYNTAX  CounterBasedGauge64 
		MAX-ACCESS read-only 
		STATUS current
		DESCRIPTION  "RADIUS SMP Created" 
		::={ acosCgnv6LsnRadiusServerS 16 } 

		smpDeleted OBJECT-TYPE
		SYNTAX  CounterBasedGauge64 
		MAX-ACCESS read-only 
		STATUS current
		DESCRIPTION  "RADIUS SMP Deleted" 
		::={ acosCgnv6LsnRadiusServerS 17 } 

		smpMemAllocated OBJECT-TYPE
		SYNTAX  CounterBasedGauge64 
		MAX-ACCESS read-only 
		STATUS current
		DESCRIPTION  "RADIUS SMP Memory Allocated" 
		::={ acosCgnv6LsnRadiusServerS 23 } 

		smpMemAllocFailed OBJECT-TYPE
		SYNTAX  CounterBasedGauge64 
		MAX-ACCESS read-only 
		STATUS current
		DESCRIPTION  "RADIUS SMP Memory Allocation Failed" 
		::={ acosCgnv6LsnRadiusServerS 24 } 

		smpMemFreed OBJECT-TYPE
		SYNTAX  CounterBasedGauge64 
		MAX-ACCESS read-only 
		STATUS current
		DESCRIPTION  "RADIUS SMP Memory Freed" 
		::={ acosCgnv6LsnRadiusServerS 25 } 

		smpInRml OBJECT-TYPE
		SYNTAX  CounterBasedGauge64 
		MAX-ACCESS read-only 
		STATUS current
		DESCRIPTION  "RADIUS SMP in RML" 
		::={ acosCgnv6LsnRadiusServerS 26 } 

		memAllocated OBJECT-TYPE
		SYNTAX  CounterBasedGauge64 
		MAX-ACCESS read-only 
		STATUS current
		DESCRIPTION  "RADIUS Memory Allocated" 
		::={ acosCgnv6LsnRadiusServerS 27 } 

		memAllocFailed OBJECT-TYPE
		SYNTAX  CounterBasedGauge64 
		MAX-ACCESS read-only 
		STATUS current
		DESCRIPTION  "RADIUS Memory Allocation Failed" 
		::={ acosCgnv6LsnRadiusServerS 28 } 

		memFreed OBJECT-TYPE
		SYNTAX  CounterBasedGauge64 
		MAX-ACCESS read-only 
		STATUS current
		DESCRIPTION  "RADIUS Memory Freed" 
		::={ acosCgnv6LsnRadiusServerS 29 } 

		haSyncCreateSent OBJECT-TYPE
		SYNTAX  CounterBasedGauge64 
		MAX-ACCESS read-only 
		STATUS current
		DESCRIPTION  "HA Record Sync Create Sent" 
		::={ acosCgnv6LsnRadiusServerS 30 } 

		haSyncDeleteSent OBJECT-TYPE
		SYNTAX  CounterBasedGauge64 
		MAX-ACCESS read-only 
		STATUS current
		DESCRIPTION  "HA Record Sync Delete Sent" 
		::={ acosCgnv6LsnRadiusServerS 31 } 

		haSyncCreateRecv OBJECT-TYPE
		SYNTAX  CounterBasedGauge64 
		MAX-ACCESS read-only 
		STATUS current
		DESCRIPTION  "HA Record Sync Create Received" 
		::={ acosCgnv6LsnRadiusServerS 32 } 

		haSyncDeleteRecv OBJECT-TYPE
		SYNTAX  CounterBasedGauge64 
		MAX-ACCESS read-only 
		STATUS current
		DESCRIPTION  "HA Record Sync Delete Received" 
		::={ acosCgnv6LsnRadiusServerS 33 } 

		acctOnFiltersFull OBJECT-TYPE
		SYNTAX  CounterBasedGauge64 
		MAX-ACCESS read-only 
		STATUS current
		DESCRIPTION  "RADIUS Acct On Request Ignored(Filters Full)" 
		::={ acosCgnv6LsnRadiusServerS 34 } 

		acctOnDupRequest OBJECT-TYPE
		SYNTAX  CounterBasedGauge64 
		MAX-ACCESS read-only 
		STATUS current
		DESCRIPTION  "Duplicate RADIUS Acct On Request" 
		::={ acosCgnv6LsnRadiusServerS 35 } 

		ipMismatchDelete OBJECT-TYPE
		SYNTAX  CounterBasedGauge64 
		MAX-ACCESS read-only 
		STATUS current
		DESCRIPTION  "Radius Entry IP Mismatch Delete" 
		::={ acosCgnv6LsnRadiusServerS 36 } 

		ipAddRaceDrop OBJECT-TYPE
		SYNTAX  CounterBasedGauge64 
		MAX-ACCESS read-only 
		STATUS current
		DESCRIPTION  "Radius Entry IP Add Race Drop" 
		::={ acosCgnv6LsnRadiusServerS 37 } 

		haSyncNoKeyVapDropped OBJECT-TYPE
		SYNTAX  CounterBasedGauge64 
		MAX-ACCESS read-only 
		STATUS current
		DESCRIPTION  "HA Record Sync No key dropped" 
		::={ acosCgnv6LsnRadiusServerS 38 } 

		interCardMsgFailDrop OBJECT-TYPE
		SYNTAX  CounterBasedGauge64 
		MAX-ACCESS read-only 
		STATUS current
		DESCRIPTION  "Inter-Card Message Fail Drop" 
		::={ acosCgnv6LsnRadiusServerS 39 } 

		radiusPacketsRedirected OBJECT-TYPE
		SYNTAX  CounterBasedGauge64 
		MAX-ACCESS read-only 
		STATUS current
		DESCRIPTION  "RADIUS packets redirected (SO)" 
		::={ acosCgnv6LsnRadiusServerS 40 } 

		radiusPacketsRedirectFailDropped OBJECT-TYPE
		SYNTAX  CounterBasedGauge64 
		MAX-ACCESS read-only 
		STATUS current
		DESCRIPTION  "RADIUS packets dropped due to redirect failure (SO)" 
		::={ acosCgnv6LsnRadiusServerS 41 } 

		radiusPacketsProcessLocal OBJECT-TYPE
		SYNTAX  CounterBasedGauge64 
		MAX-ACCESS read-only 
		STATUS current
		DESCRIPTION  "RADIUS packets processed locally without redirection (SO)" 
		::={ acosCgnv6LsnRadiusServerS 42 } 

		radiusPacketsDroppedNotLo OBJECT-TYPE
		SYNTAX  CounterBasedGauge64 
		MAX-ACCESS read-only 
		STATUS current
		DESCRIPTION  "RADIUS packets dropped dest not loopback (SO)" 
		::={ acosCgnv6LsnRadiusServerS 43 } 

		radiusInterCardDupRedir OBJECT-TYPE
		SYNTAX  CounterBasedGauge64 
		MAX-ACCESS read-only 
		STATUS current
		DESCRIPTION  "RADIUS packet dropped as redirected by other blade (SO)" 
		::={ acosCgnv6LsnRadiusServerS 44 } 

acosCgnv6LsnPerInstance             OBJECT IDENTIFIER ::= { acosCgnv6Lsn 21 }
acosCgnv6LsnPerInstanceS            OBJECT IDENTIFIER ::= { acosCgnv6LsnPerInstance 1 }
acosCgnv6Nat                        OBJECT IDENTIFIER ::= { acosCgnv6 8 }
acosCgnv6NatPool                    OBJECT IDENTIFIER ::= { acosCgnv6Nat 1 }
acosCgnv6NatPoolS                   OBJECT IDENTIFIER ::= { acosCgnv6NatPool 1 }

cgnv6NatPoolSTable OBJECT-TYPE
		SYNTAX SEQUENCE OF Cgnv6NatPoolSEntry
		MAX-ACCESS not-accessible
		STATUS current
		::={ acosCgnv6NatPoolS 1 } 


	cgnv6NatPoolSEntry OBJECT-TYPE
		SYNTAX Cgnv6NatPoolSEntry
		MAX-ACCESS not-accessible
		STATUS current
		INDEX {
			cgnv6NatPoolPoolName
		}
		::={ cgnv6NatPoolSTable 1 } 


	Cgnv6NatPoolSEntry ::=
		SEQUENCE {
			cgnv6NatPoolPoolName DisplayString, 
			users CounterBasedGauge64,
			icmp CounterBasedGauge64,
			icmpFreed CounterBasedGauge64,
			icmpTotal CounterBasedGauge64,
			icmpRsvd CounterBasedGauge64,
			icmpPeak CounterBasedGauge64,
			icmpHitFull CounterBasedGauge64,
			udp CounterBasedGauge64,
			udpFreed CounterBasedGauge64,
			udpTotal CounterBasedGauge64,
			udpRsvd CounterBasedGauge64,
			udpPeak CounterBasedGauge64,
			udpHitFull CounterBasedGauge64,
			udpPortOverloaded CounterBasedGauge64,
			udpPortOverloadCreate CounterBasedGauge64,
			udpPortOverloadFree CounterBasedGauge64,
			tcp CounterBasedGauge64,
			tcpFreed CounterBasedGauge64,
			tcpTotal CounterBasedGauge64,
			tcpRsvd CounterBasedGauge64,
			tcpPeak CounterBasedGauge64,
			tcpHitFull CounterBasedGauge64,
			tcpPortOverloaded CounterBasedGauge64,
			tcpPortOverloadCreate CounterBasedGauge64,
			tcpPortOverloadFree CounterBasedGauge64,
			ipUsed CounterBasedGauge64,
			ipFree CounterBasedGauge64,
			ipTotal CounterBasedGauge64
		}

			cgnv6NatPoolPoolName OBJECT-TYPE
			SYNTAX  DisplayString 
			MAX-ACCESS read-only 
			STATUS current
			DESCRIPTION  "Specify pool name" 
			::={ cgnv6NatPoolSEntry 1 } 

			users OBJECT-TYPE
			SYNTAX  CounterBasedGauge64 
			MAX-ACCESS read-only 
			STATUS current
			DESCRIPTION  "Users" 
			::={ cgnv6NatPoolSEntry 2 } 

			icmp OBJECT-TYPE
			SYNTAX  CounterBasedGauge64 
			MAX-ACCESS read-only 
			STATUS current
			DESCRIPTION  "ICMP" 
			::={ cgnv6NatPoolSEntry 3 } 

			icmpFreed OBJECT-TYPE
			SYNTAX  CounterBasedGauge64 
			MAX-ACCESS read-only 
			STATUS current
			DESCRIPTION  "ICMP Freed" 
			::={ cgnv6NatPoolSEntry 4 } 

			icmpTotal OBJECT-TYPE
			SYNTAX  CounterBasedGauge64 
			MAX-ACCESS read-only 
			STATUS current
			DESCRIPTION  "ICMP Total" 
			::={ cgnv6NatPoolSEntry 5 } 

			icmpRsvd OBJECT-TYPE
			SYNTAX  CounterBasedGauge64 
			MAX-ACCESS read-only 
			STATUS current
			DESCRIPTION  "ICMP Reserved" 
			::={ cgnv6NatPoolSEntry 6 } 

			icmpPeak OBJECT-TYPE
			SYNTAX  CounterBasedGauge64 
			MAX-ACCESS read-only 
			STATUS current
			DESCRIPTION  "ICMP Peak" 
			::={ cgnv6NatPoolSEntry 7 } 

			icmpHitFull OBJECT-TYPE
			SYNTAX  CounterBasedGauge64 
			MAX-ACCESS read-only 
			STATUS current
			DESCRIPTION  "ICMP Hit Full" 
			::={ cgnv6NatPoolSEntry 8 } 

			udp OBJECT-TYPE
			SYNTAX  CounterBasedGauge64 
			MAX-ACCESS read-only 
			STATUS current
			DESCRIPTION  "UDP" 
			::={ cgnv6NatPoolSEntry 9 } 

			udpFreed OBJECT-TYPE
			SYNTAX  CounterBasedGauge64 
			MAX-ACCESS read-only 
			STATUS current
			DESCRIPTION  "UDP Freed" 
			::={ cgnv6NatPoolSEntry 10 } 

			udpTotal OBJECT-TYPE
			SYNTAX  CounterBasedGauge64 
			MAX-ACCESS read-only 
			STATUS current
			DESCRIPTION  "UDP Total" 
			::={ cgnv6NatPoolSEntry 11 } 

			udpRsvd OBJECT-TYPE
			SYNTAX  CounterBasedGauge64 
			MAX-ACCESS read-only 
			STATUS current
			DESCRIPTION  "UDP Reserved" 
			::={ cgnv6NatPoolSEntry 12 } 

			udpPeak OBJECT-TYPE
			SYNTAX  CounterBasedGauge64 
			MAX-ACCESS read-only 
			STATUS current
			DESCRIPTION  "UDP Peak" 
			::={ cgnv6NatPoolSEntry 13 } 

			udpHitFull OBJECT-TYPE
			SYNTAX  CounterBasedGauge64 
			MAX-ACCESS read-only 
			STATUS current
			DESCRIPTION  "UDP Hit Full" 
			::={ cgnv6NatPoolSEntry 14 } 

			udpPortOverloaded OBJECT-TYPE
			SYNTAX  CounterBasedGauge64 
			MAX-ACCESS read-only 
			STATUS current
			DESCRIPTION  "UDP Port Overloaded" 
			::={ cgnv6NatPoolSEntry 15 } 

			udpPortOverloadCreate OBJECT-TYPE
			SYNTAX  CounterBasedGauge64 
			MAX-ACCESS read-only 
			STATUS current
			DESCRIPTION  "UDP Port Overloading Session Created" 
			::={ cgnv6NatPoolSEntry 16 } 

			udpPortOverloadFree OBJECT-TYPE
			SYNTAX  CounterBasedGauge64 
			MAX-ACCESS read-only 
			STATUS current
			DESCRIPTION  "UDP Port Overloading Session Freed" 
			::={ cgnv6NatPoolSEntry 17 } 

			tcp OBJECT-TYPE
			SYNTAX  CounterBasedGauge64 
			MAX-ACCESS read-only 
			STATUS current
			DESCRIPTION  "TCP" 
			::={ cgnv6NatPoolSEntry 18 } 

			tcpFreed OBJECT-TYPE
			SYNTAX  CounterBasedGauge64 
			MAX-ACCESS read-only 
			STATUS current
			DESCRIPTION  "TCP Freed" 
			::={ cgnv6NatPoolSEntry 19 } 

			tcpTotal OBJECT-TYPE
			SYNTAX  CounterBasedGauge64 
			MAX-ACCESS read-only 
			STATUS current
			DESCRIPTION  "TCP total" 
			::={ cgnv6NatPoolSEntry 20 } 

			tcpRsvd OBJECT-TYPE
			SYNTAX  CounterBasedGauge64 
			MAX-ACCESS read-only 
			STATUS current
			DESCRIPTION  "TCP Reserved" 
			::={ cgnv6NatPoolSEntry 21 } 

			tcpPeak OBJECT-TYPE
			SYNTAX  CounterBasedGauge64 
			MAX-ACCESS read-only 
			STATUS current
			DESCRIPTION  "TCP Peak" 
			::={ cgnv6NatPoolSEntry 22 } 

			tcpHitFull OBJECT-TYPE
			SYNTAX  CounterBasedGauge64 
			MAX-ACCESS read-only 
			STATUS current
			DESCRIPTION  "TCP Hit Full" 
			::={ cgnv6NatPoolSEntry 23 } 

			tcpPortOverloaded OBJECT-TYPE
			SYNTAX  CounterBasedGauge64 
			MAX-ACCESS read-only 
			STATUS current
			DESCRIPTION  "TCP Port Overloaded" 
			::={ cgnv6NatPoolSEntry 24 } 

			tcpPortOverloadCreate OBJECT-TYPE
			SYNTAX  CounterBasedGauge64 
			MAX-ACCESS read-only 
			STATUS current
			DESCRIPTION  "TCP Port Overloading Session Created" 
			::={ cgnv6NatPoolSEntry 25 } 

			tcpPortOverloadFree OBJECT-TYPE
			SYNTAX  CounterBasedGauge64 
			MAX-ACCESS read-only 
			STATUS current
			DESCRIPTION  "TCP Port Overloading Session Freed" 
			::={ cgnv6NatPoolSEntry 26 } 

			ipUsed OBJECT-TYPE
			SYNTAX  CounterBasedGauge64 
			MAX-ACCESS read-only 
			STATUS current
			DESCRIPTION  "IP Used" 
			::={ cgnv6NatPoolSEntry 27 } 

			ipFree OBJECT-TYPE
			SYNTAX  CounterBasedGauge64 
			MAX-ACCESS read-only 
			STATUS current
			DESCRIPTION  "IP Free" 
			::={ cgnv6NatPoolSEntry 28 } 

			ipTotal OBJECT-TYPE
			SYNTAX  CounterBasedGauge64 
			MAX-ACCESS read-only 
			STATUS current
			DESCRIPTION  "IP Total" 
			::={ cgnv6NatPoolSEntry 29 } 

acosCgnv6Dns64VServer               OBJECT IDENTIFIER ::= { acosCgnv6 11 }
acosCgnv6Dns64VServerPort           OBJECT IDENTIFIER ::= { acosCgnv6Dns64VServer 2 }
acosCgnv6Dns64VServerPortS          OBJECT IDENTIFIER ::= { acosCgnv6Dns64VServerPort 1 }

cgnv6Dns64VServerPortSTable OBJECT-TYPE
		SYNTAX SEQUENCE OF Cgnv6Dns64VServerPortSEntry
		MAX-ACCESS not-accessible
		STATUS current
		::={ acosCgnv6Dns64VServerPortS 1 } 


	cgnv6Dns64VServerPortSEntry OBJECT-TYPE
		SYNTAX Cgnv6Dns64VServerPortSEntry
		MAX-ACCESS not-accessible
		STATUS current
		INDEX {
			cgnv6Dns64VirtualserverName,
			cgnv6Dns64VServerPortNumber,
			cgnv6Dns64VServerProtocol
		}
		::={ cgnv6Dns64VServerPortSTable 1 } 


	Cgnv6Dns64VServerPortSEntry ::=
		SEQUENCE {
			cgnv6Dns64VirtualserverName DisplayString, 
			cgnv6Dns64VServerPortNumber INTEGER, 
			cgnv6Dns64VServerProtocol DisplayString, 
			cgnv6Dns64VServerPortCurrConn CounterBasedGauge64,
			cgnv6Dns64VServerPortTotalL4Conn CounterBasedGauge64,
			cgnv6Dns64VServerPortTotalL7Conn CounterBasedGauge64,
			toatalTcpConn CounterBasedGauge64,
			cgnv6Dns64VServerPortTotalConn CounterBasedGauge64,
			cgnv6VServerPortTotalFwdBytes CounterBasedGauge64,
			cgnv6Dns64VServerPortTotalFwdPkts CounterBasedGauge64,
			cgnv6Dns64VServerPortTotalRevBytes CounterBasedGauge64,
			cgnv6Dns64VServerPortTotalRevPkts CounterBasedGauge64,
			totalDnsPkts CounterBasedGauge64,
			totalMfDnsPkts CounterBasedGauge64,
			esTotalFailureActions CounterBasedGauge64,
			compressionBytesBefore CounterBasedGauge64,
			compressionBytesAfter CounterBasedGauge64,
			compressionHit CounterBasedGauge64,
			compressionMiss CounterBasedGauge64,
			compressionMissNoClient CounterBasedGauge64,
			compressionMissTemplateExclusion CounterBasedGauge64,
			cgnv6Dns64VirtualServerPortCurrentReq CounterBasedGauge64,
			cgnv6Dns64VirtualServerPortTotalReq CounterBasedGauge64,
			totalReqSucc CounterBasedGauge64,
			cgnv6Dns64VirtualServerPortPeakConn CounterBasedGauge64,
			currConnRate CounterBasedGauge64,
			lastRspTime CounterBasedGauge64,
			cgnv6Dns64VirtualServerPortFastestRspTime CounterBasedGauge64,
			cgnv6Dns64VirtualServerPortSlowestRspTime CounterBasedGauge64
		}

			cgnv6Dns64VirtualserverName OBJECT-TYPE
			SYNTAX  DisplayString 
			MAX-ACCESS read-only 
			STATUS current
			DESCRIPTION  "CGNV6 Virtual Server Name" 
			::={ cgnv6Dns64VServerPortSEntry 1 } 

			cgnv6Dns64VServerPortNumber OBJECT-TYPE
			SYNTAX  INTEGER 
			MAX-ACCESS read-only 
			STATUS current
			DESCRIPTION  "Port" 
			::={ cgnv6Dns64VServerPortSEntry 2 } 

			cgnv6Dns64VServerProtocol OBJECT-TYPE
			SYNTAX  DisplayString 
			MAX-ACCESS read-only 
			STATUS current
			DESCRIPTION  "protocol" 
			::={ cgnv6Dns64VServerPortSEntry 3 } 

			cgnv6Dns64VServerPortCurrConn OBJECT-TYPE
			SYNTAX  CounterBasedGauge64 
			MAX-ACCESS read-only 
			STATUS current
			DESCRIPTION  "Current connection" 
			::={ cgnv6Dns64VServerPortSEntry 4 } 

			cgnv6Dns64VServerPortTotalL4Conn OBJECT-TYPE
			SYNTAX  CounterBasedGauge64 
			MAX-ACCESS read-only 
			STATUS current
			DESCRIPTION  "Total L4 connections" 
			::={ cgnv6Dns64VServerPortSEntry 5 } 

			cgnv6Dns64VServerPortTotalL7Conn OBJECT-TYPE
			SYNTAX  CounterBasedGauge64 
			MAX-ACCESS read-only 
			STATUS current
			DESCRIPTION  "Total L7 connections" 
			::={ cgnv6Dns64VServerPortSEntry 6 } 

			toatalTcpConn OBJECT-TYPE
			SYNTAX  CounterBasedGauge64 
			MAX-ACCESS read-only 
			STATUS current
			DESCRIPTION  "Total TCP connections" 
			::={ cgnv6Dns64VServerPortSEntry 7 } 

			cgnv6Dns64VServerPortTotalConn OBJECT-TYPE
			SYNTAX  CounterBasedGauge64 
			MAX-ACCESS read-only 
			STATUS current
			DESCRIPTION  "Total connections" 
			::={ cgnv6Dns64VServerPortSEntry 8 } 

			cgnv6VServerPortTotalFwdBytes OBJECT-TYPE
			SYNTAX  CounterBasedGauge64 
			MAX-ACCESS read-only 
			STATUS current
			DESCRIPTION  "Total forward bytes" 
			::={ cgnv6Dns64VServerPortSEntry 9 } 

			cgnv6Dns64VServerPortTotalFwdPkts OBJECT-TYPE
			SYNTAX  CounterBasedGauge64 
			MAX-ACCESS read-only 
			STATUS current
			DESCRIPTION  "Total forward packets" 
			::={ cgnv6Dns64VServerPortSEntry 10 } 

			cgnv6Dns64VServerPortTotalRevBytes OBJECT-TYPE
			SYNTAX  CounterBasedGauge64 
			MAX-ACCESS read-only 
			STATUS current
			DESCRIPTION  "Total reverse bytes" 
			::={ cgnv6Dns64VServerPortSEntry 11 } 

			cgnv6Dns64VServerPortTotalRevPkts OBJECT-TYPE
			SYNTAX  CounterBasedGauge64 
			MAX-ACCESS read-only 
			STATUS current
			DESCRIPTION  "Total reverse packets" 
			::={ cgnv6Dns64VServerPortSEntry 12 } 

			totalDnsPkts OBJECT-TYPE
			SYNTAX  CounterBasedGauge64 
			MAX-ACCESS read-only 
			STATUS current
			DESCRIPTION  "Total DNS packets" 
			::={ cgnv6Dns64VServerPortSEntry 13 } 

			totalMfDnsPkts OBJECT-TYPE
			SYNTAX  CounterBasedGauge64 
			MAX-ACCESS read-only 
			STATUS current
			DESCRIPTION  "Total MF DNS packets" 
			::={ cgnv6Dns64VServerPortSEntry 14 } 

			esTotalFailureActions OBJECT-TYPE
			SYNTAX  CounterBasedGauge64 
			MAX-ACCESS read-only 
			STATUS current
			DESCRIPTION  "Total failure actions" 
			::={ cgnv6Dns64VServerPortSEntry 15 } 

			compressionBytesBefore OBJECT-TYPE
			SYNTAX  CounterBasedGauge64 
			MAX-ACCESS read-only 
			STATUS current
			DESCRIPTION  "Data into compression engine" 
			::={ cgnv6Dns64VServerPortSEntry 16 } 

			compressionBytesAfter OBJECT-TYPE
			SYNTAX  CounterBasedGauge64 
			MAX-ACCESS read-only 
			STATUS current
			DESCRIPTION  "Data out of compression engine" 
			::={ cgnv6Dns64VServerPortSEntry 17 } 

			compressionHit OBJECT-TYPE
			SYNTAX  CounterBasedGauge64 
			MAX-ACCESS read-only 
			STATUS current
			DESCRIPTION  "Number of requests compressed" 
			::={ cgnv6Dns64VServerPortSEntry 18 } 

			compressionMiss OBJECT-TYPE
			SYNTAX  CounterBasedGauge64 
			MAX-ACCESS read-only 
			STATUS current
			DESCRIPTION  "Number of requests NOT compressed" 
			::={ cgnv6Dns64VServerPortSEntry 19 } 

			compressionMissNoClient OBJECT-TYPE
			SYNTAX  CounterBasedGauge64 
			MAX-ACCESS read-only 
			STATUS current
			DESCRIPTION  "Compression miss no client" 
			::={ cgnv6Dns64VServerPortSEntry 20 } 

			compressionMissTemplateExclusion OBJECT-TYPE
			SYNTAX  CounterBasedGauge64 
			MAX-ACCESS read-only 
			STATUS current
			DESCRIPTION  "Compression miss template exclusion" 
			::={ cgnv6Dns64VServerPortSEntry 21 } 

			cgnv6Dns64VirtualServerPortCurrentReq OBJECT-TYPE
			SYNTAX  CounterBasedGauge64 
			MAX-ACCESS read-only 
			STATUS current
			DESCRIPTION  "Current requests" 
			::={ cgnv6Dns64VServerPortSEntry 22 } 

			cgnv6Dns64VirtualServerPortTotalReq OBJECT-TYPE
			SYNTAX  CounterBasedGauge64 
			MAX-ACCESS read-only 
			STATUS current
			DESCRIPTION  "Total requests" 
			::={ cgnv6Dns64VServerPortSEntry 23 } 

			totalReqSucc OBJECT-TYPE
			SYNTAX  CounterBasedGauge64 
			MAX-ACCESS read-only 
			STATUS current
			DESCRIPTION  "Total successful requests" 
			::={ cgnv6Dns64VServerPortSEntry 24 } 

			cgnv6Dns64VirtualServerPortPeakConn OBJECT-TYPE
			SYNTAX  CounterBasedGauge64 
			MAX-ACCESS read-only 
			STATUS current
			DESCRIPTION  "Peak connections" 
			::={ cgnv6Dns64VServerPortSEntry 25 } 

			currConnRate OBJECT-TYPE
			SYNTAX  CounterBasedGauge64 
			MAX-ACCESS read-only 
			STATUS current
			DESCRIPTION  "Current connection rate" 
			::={ cgnv6Dns64VServerPortSEntry 26 } 

			lastRspTime OBJECT-TYPE
			SYNTAX  CounterBasedGauge64 
			MAX-ACCESS read-only 
			STATUS current
			DESCRIPTION  "Last response time" 
			::={ cgnv6Dns64VServerPortSEntry 27 } 

			cgnv6Dns64VirtualServerPortFastestRspTime OBJECT-TYPE
			SYNTAX  CounterBasedGauge64 
			MAX-ACCESS read-only 
			STATUS current
			DESCRIPTION  "Fastest response time" 
			::={ cgnv6Dns64VServerPortSEntry 28 } 

			cgnv6Dns64VirtualServerPortSlowestRspTime OBJECT-TYPE
			SYNTAX  CounterBasedGauge64 
			MAX-ACCESS read-only 
			STATUS current
			DESCRIPTION  "Slowest response time" 
			::={ cgnv6Dns64VServerPortSEntry 29 } 

acosCgnv6OneToOne                   OBJECT IDENTIFIER ::= { acosCgnv6 14 }
acosCgnv6OneToOneGlobal             OBJECT IDENTIFIER ::= { acosCgnv6OneToOne 1 }
acosCgnv6OneToOneGlobalS            OBJECT IDENTIFIER ::= { acosCgnv6OneToOneGlobal 1 }

		totalMapAllocated OBJECT-TYPE
		SYNTAX  CounterBasedGauge64 
		MAX-ACCESS read-only 
		STATUS current
		DESCRIPTION  "Total One-to-One Address Mapping Allocated" 
		::={ acosCgnv6OneToOneGlobalS 1 } 

		totalMapFreed OBJECT-TYPE
		SYNTAX  CounterBasedGauge64 
		MAX-ACCESS read-only 
		STATUS current
		DESCRIPTION  "Total One-to-One Address Mapping Freed" 
		::={ acosCgnv6OneToOneGlobalS 2 } 

		mapAllocFailure OBJECT-TYPE
		SYNTAX  CounterBasedGauge64 
		MAX-ACCESS read-only 
		STATUS current
		DESCRIPTION  "One-to-One Address Mapping Allocation Failure" 
		::={ acosCgnv6OneToOneGlobalS 3 } 

		mapDblFree OBJECT-TYPE
		SYNTAX  CounterBasedGauge64 
		MAX-ACCESS read-only 
		STATUS current
		DESCRIPTION  "Address Mapping Double Free" 
		::={ acosCgnv6OneToOneGlobalS 4 } 

		allocMapRace OBJECT-TYPE
		SYNTAX  CounterBasedGauge64 
		MAX-ACCESS read-only 
		STATUS current
		DESCRIPTION  "Mapping Exists When Allocating Address Mapping" 
		::={ acosCgnv6OneToOneGlobalS 5 } 

		mapNotFound OBJECT-TYPE
		SYNTAX  CounterBasedGauge64 
		MAX-ACCESS read-only 
		STATUS current
		DESCRIPTION  "Mapping to be Released Not Found" 
		::={ acosCgnv6OneToOneGlobalS 6 } 

		haMapMismatch OBJECT-TYPE
		SYNTAX  CounterBasedGauge64 
		MAX-ACCESS read-only 
		STATUS current
		DESCRIPTION  "HA Standby Mapping Mismatch" 
		::={ acosCgnv6OneToOneGlobalS 7 } 

		haSelectAddrFailure OBJECT-TYPE
		SYNTAX  CounterBasedGauge64 
		MAX-ACCESS read-only 
		STATUS current
		DESCRIPTION  "HA Standby Allocate Address Failure" 
		::={ acosCgnv6OneToOneGlobalS 8 } 

		haAllocMapConflicts OBJECT-TYPE
		SYNTAX  CounterBasedGauge64 
		MAX-ACCESS read-only 
		STATUS current
		DESCRIPTION  "HA Standby Allocate Mapping Conflicts" 
		::={ acosCgnv6OneToOneGlobalS 9 } 

acosCgnv6OneToOnePool               OBJECT IDENTIFIER ::= { acosCgnv6OneToOne 2 }
acosCgnv6OneToOnePoolS              OBJECT IDENTIFIER ::= { acosCgnv6OneToOnePool 1 }

cgnv6OneToOnePoolSTable OBJECT-TYPE
		SYNTAX SEQUENCE OF Cgnv6OneToOnePoolSEntry
		MAX-ACCESS not-accessible
		STATUS current
		::={ acosCgnv6OneToOnePoolS 1 } 


	cgnv6OneToOnePoolSEntry OBJECT-TYPE
		SYNTAX Cgnv6OneToOnePoolSEntry
		MAX-ACCESS not-accessible
		STATUS current
		INDEX {
			cgnv6OneToOnePoolName
		}
		::={ cgnv6OneToOnePoolSTable 1 } 


	Cgnv6OneToOnePoolSEntry ::=
		SEQUENCE {
			cgnv6OneToOnePoolName DisplayString, 
			totalAddress CounterBasedGauge64,
			usedAddress CounterBasedGauge64,
			freeAddress CounterBasedGauge64
		}

			cgnv6OneToOnePoolName OBJECT-TYPE
			SYNTAX  DisplayString 
			MAX-ACCESS read-only 
			STATUS current
			DESCRIPTION  "Specify pool name or pool group" 
			::={ cgnv6OneToOnePoolSEntry 1 } 

			totalAddress OBJECT-TYPE
			SYNTAX  CounterBasedGauge64 
			MAX-ACCESS read-only 
			STATUS current
			DESCRIPTION  "Total Address" 
			::={ cgnv6OneToOnePoolSEntry 2 } 

			usedAddress OBJECT-TYPE
			SYNTAX  CounterBasedGauge64 
			MAX-ACCESS read-only 
			STATUS current
			DESCRIPTION  "Used Address" 
			::={ cgnv6OneToOnePoolSEntry 3 } 

			freeAddress OBJECT-TYPE
			SYNTAX  CounterBasedGauge64 
			MAX-ACCESS read-only 
			STATUS current
			DESCRIPTION  "Free Address" 
			::={ cgnv6OneToOnePoolSEntry 4 } 

acosCgnv6LsnRuleList                OBJECT IDENTIFIER ::= { acosCgnv6 15 }
acosCgnv6LsnRuleListDomainIp        OBJECT IDENTIFIER ::= { acosCgnv6LsnRuleList 6 }
acosCgnv6LsnRuleListDomainIpS       OBJECT IDENTIFIER ::= { acosCgnv6LsnRuleListDomainIp 1 }
acosCgnv6LsnRuleListDefault         OBJECT IDENTIFIER ::= { acosCgnv6LsnRuleList 2 }
acosCgnv6LsnRuleListDefaultS        OBJECT IDENTIFIER ::= { acosCgnv6LsnRuleListDefault 1 }
acosCgnv6LsnRuleListDomainName      OBJECT IDENTIFIER ::= { acosCgnv6LsnRuleList 3 }
acosCgnv6LsnRuleListDomainNameS     OBJECT IDENTIFIER ::= { acosCgnv6LsnRuleListDomainName 1 }
acosCgnv6LsnRuleListDomainListName  OBJECT IDENTIFIER ::= { acosCgnv6LsnRuleList 4 }
acosCgnv6LsnRuleListDomainListNameS OBJECT IDENTIFIER ::= { acosCgnv6LsnRuleListDomainListName 1 }
acosCgnv6LsnRuleListIp              OBJECT IDENTIFIER ::= { acosCgnv6LsnRuleList 5 }
acosCgnv6LsnRuleListIpS             OBJECT IDENTIFIER ::= { acosCgnv6LsnRuleListIp 1 }
acosCgnv6Nat64                      OBJECT IDENTIFIER ::= { acosCgnv6 18 }
acosCgnv6Nat64Global                OBJECT IDENTIFIER ::= { acosCgnv6Nat64 1 }
acosCgnv6Nat64GlobalS               OBJECT IDENTIFIER ::= { acosCgnv6Nat64Global 1 }

		totalTcpAllocated OBJECT-TYPE
		SYNTAX  CounterBasedGauge64 
		MAX-ACCESS read-only 
		STATUS current
		DESCRIPTION  "Total TCP Ports Allocated" 
		::={ acosCgnv6Nat64GlobalS 1 } 

		totalTcpFreed OBJECT-TYPE
		SYNTAX  CounterBasedGauge64 
		MAX-ACCESS read-only 
		STATUS current
		DESCRIPTION  "Total TCP Ports Freed" 
		::={ acosCgnv6Nat64GlobalS 2 } 

		totalUdpAllocated OBJECT-TYPE
		SYNTAX  CounterBasedGauge64 
		MAX-ACCESS read-only 
		STATUS current
		DESCRIPTION  "Total UDP Ports Allocated" 
		::={ acosCgnv6Nat64GlobalS 3 } 

		totalUdpFreed OBJECT-TYPE
		SYNTAX  CounterBasedGauge64 
		MAX-ACCESS read-only 
		STATUS current
		DESCRIPTION  "Total UDP Ports Freed" 
		::={ acosCgnv6Nat64GlobalS 4 } 

		totalIcmpAllocated OBJECT-TYPE
		SYNTAX  CounterBasedGauge64 
		MAX-ACCESS read-only 
		STATUS current
		DESCRIPTION  "Total ICMP Ports Allocated" 
		::={ acosCgnv6Nat64GlobalS 5 } 

		totalIcmpFreed OBJECT-TYPE
		SYNTAX  CounterBasedGauge64 
		MAX-ACCESS read-only 
		STATUS current
		DESCRIPTION  "Total ICMP Ports Freed" 
		::={ acosCgnv6Nat64GlobalS 6 } 

		dataSessionCreated OBJECT-TYPE
		SYNTAX  CounterBasedGauge64 
		MAX-ACCESS read-only 
		STATUS current
		DESCRIPTION  "Data Session Created" 
		::={ acosCgnv6Nat64GlobalS 7 } 

		dataSessionFreed OBJECT-TYPE
		SYNTAX  CounterBasedGauge64 
		MAX-ACCESS read-only 
		STATUS current
		DESCRIPTION  "Data Session Freed" 
		::={ acosCgnv6Nat64GlobalS 8 } 

		userQuotaCreated OBJECT-TYPE
		SYNTAX  CounterBasedGauge64 
		MAX-ACCESS read-only 
		STATUS current
		DESCRIPTION  "User-Quota Created" 
		::={ acosCgnv6Nat64GlobalS 9 } 

		userQuotaPutInDelQ OBJECT-TYPE
		SYNTAX  CounterBasedGauge64 
		MAX-ACCESS read-only 
		STATUS current
		DESCRIPTION  "User-Quota Freed" 
		::={ acosCgnv6Nat64GlobalS 10 } 

		userQuotaFailure OBJECT-TYPE
		SYNTAX  CounterBasedGauge64 
		MAX-ACCESS read-only 
		STATUS current
		DESCRIPTION  "User-Quota Creation Failed" 
		::={ acosCgnv6Nat64GlobalS 11 } 

		natPortUnavailableTcp OBJECT-TYPE
		SYNTAX  CounterBasedGauge64 
		MAX-ACCESS read-only 
		STATUS current
		DESCRIPTION  "TCP NAT Port Unavailable" 
		::={ acosCgnv6Nat64GlobalS 12 } 

		natPortUnavailableUdp OBJECT-TYPE
		SYNTAX  CounterBasedGauge64 
		MAX-ACCESS read-only 
		STATUS current
		DESCRIPTION  "UDP NAT Port Unavailable" 
		::={ acosCgnv6Nat64GlobalS 13 } 

		natPortUnavailableIcmp OBJECT-TYPE
		SYNTAX  CounterBasedGauge64 
		MAX-ACCESS read-only 
		STATUS current
		DESCRIPTION  "ICMP NAT Port Unavailable" 
		::={ acosCgnv6Nat64GlobalS 14 } 

		newUserResourceUnavailable OBJECT-TYPE
		SYNTAX  CounterBasedGauge64 
		MAX-ACCESS read-only 
		STATUS current
		DESCRIPTION  "New User NAT Resource Unavailable" 
		::={ acosCgnv6Nat64GlobalS 15 } 

		tcpUserQuotaExceeded OBJECT-TYPE
		SYNTAX  CounterBasedGauge64 
		MAX-ACCESS read-only 
		STATUS current
		DESCRIPTION  "TCP User-Quota Exceeded" 
		::={ acosCgnv6Nat64GlobalS 16 } 

		udpUserQuotaExceeded OBJECT-TYPE
		SYNTAX  CounterBasedGauge64 
		MAX-ACCESS read-only 
		STATUS current
		DESCRIPTION  "UDP User-Quota Exceeded" 
		::={ acosCgnv6Nat64GlobalS 17 } 

		icmpUserQuotaExceeded OBJECT-TYPE
		SYNTAX  CounterBasedGauge64 
		MAX-ACCESS read-only 
		STATUS current
		DESCRIPTION  "ICMP User-Quota Exceeded" 
		::={ acosCgnv6Nat64GlobalS 18 } 

		extendedQuotaMatched OBJECT-TYPE
		SYNTAX  CounterBasedGauge64 
		MAX-ACCESS read-only 
		STATUS current
		DESCRIPTION  "Extended User-Quota Matched" 
		::={ acosCgnv6Nat64GlobalS 19 } 

		extendedQuotaExceeded OBJECT-TYPE
		SYNTAX  CounterBasedGauge64 
		MAX-ACCESS read-only 
		STATUS current
		DESCRIPTION  "Extended User-Quota Exceeded" 
		::={ acosCgnv6Nat64GlobalS 20 } 

		dataSesnUserQuotaExceeded OBJECT-TYPE
		SYNTAX  CounterBasedGauge64 
		MAX-ACCESS read-only 
		STATUS current
		DESCRIPTION  "Data Session User-Quota Exceeded" 
		::={ acosCgnv6Nat64GlobalS 21 } 

		dataSesnRateUserQuotaExceeded OBJECT-TYPE
		SYNTAX  CounterBasedGauge64 
		MAX-ACCESS read-only 
		STATUS current
		DESCRIPTION  "Conn Rate User-Quota Exceeded" 
		::={ acosCgnv6Nat64GlobalS 22 } 

		tcpFullconeCreated OBJECT-TYPE
		SYNTAX  CounterBasedGauge64 
		MAX-ACCESS read-only 
		STATUS current
		DESCRIPTION  "TCP Full-cone Session Created" 
		::={ acosCgnv6Nat64GlobalS 23 } 

		tcpFullconeFreed OBJECT-TYPE
		SYNTAX  CounterBasedGauge64 
		MAX-ACCESS read-only 
		STATUS current
		DESCRIPTION  "TCP Full-cone Session Freed" 
		::={ acosCgnv6Nat64GlobalS 24 } 

		udpFullconeCreated OBJECT-TYPE
		SYNTAX  CounterBasedGauge64 
		MAX-ACCESS read-only 
		STATUS current
		DESCRIPTION  "UDP Full-cone Session Created" 
		::={ acosCgnv6Nat64GlobalS 25 } 

		udpFullconeFreed OBJECT-TYPE
		SYNTAX  CounterBasedGauge64 
		MAX-ACCESS read-only 
		STATUS current
		DESCRIPTION  "UDP Full-cone Session Freed" 
		::={ acosCgnv6Nat64GlobalS 26 } 

		fullconeFailure OBJECT-TYPE
		SYNTAX  CounterBasedGauge64 
		MAX-ACCESS read-only 
		STATUS current
		DESCRIPTION  "Full-cone Session Creation Failed" 
		::={ acosCgnv6Nat64GlobalS 27 } 

		hairpin OBJECT-TYPE
		SYNTAX  CounterBasedGauge64 
		MAX-ACCESS read-only 
		STATUS current
		DESCRIPTION  "Hairpin Session Created" 
		::={ acosCgnv6Nat64GlobalS 28 } 

		fullconeSelfHairpinningDrop OBJECT-TYPE
		SYNTAX  CounterBasedGauge64 
		MAX-ACCESS read-only 
		STATUS current
		DESCRIPTION  "Self-Hairpinning Drop" 
		::={ acosCgnv6Nat64GlobalS 29 } 

		endpointIndepMapMatch OBJECT-TYPE
		SYNTAX  CounterBasedGauge64 
		MAX-ACCESS read-only 
		STATUS current
		DESCRIPTION  "Endpoint-Independent Mapping Matched" 
		::={ acosCgnv6Nat64GlobalS 30 } 

		endpointIndepFilterMatch OBJECT-TYPE
		SYNTAX  CounterBasedGauge64 
		MAX-ACCESS read-only 
		STATUS current
		DESCRIPTION  "Endpoint-Independent Filtering Matched" 
		::={ acosCgnv6Nat64GlobalS 31 } 

		inboundFiltered OBJECT-TYPE
		SYNTAX  CounterBasedGauge64 
		MAX-ACCESS read-only 
		STATUS current
		DESCRIPTION  "Endpoint-Dependent Filtering Drop" 
		::={ acosCgnv6Nat64GlobalS 32 } 

		eifLimitExceeded OBJECT-TYPE
		SYNTAX  CounterBasedGauge64 
		MAX-ACCESS read-only 
		STATUS current
		DESCRIPTION  "Endpoint-Independent Filtering Inbound Limit Exceeded" 
		::={ acosCgnv6Nat64GlobalS 33 } 

		totalTcpOverloaded OBJECT-TYPE
		SYNTAX  CounterBasedGauge64 
		MAX-ACCESS read-only 
		STATUS current
		DESCRIPTION  "TCP Port Overloaded" 
		::={ acosCgnv6Nat64GlobalS 35 } 

		totalUdpOverloaded OBJECT-TYPE
		SYNTAX  CounterBasedGauge64 
		MAX-ACCESS read-only 
		STATUS current
		DESCRIPTION  "UDP Port Overloaded" 
		::={ acosCgnv6Nat64GlobalS 36 } 

		portOverloadingSmpInsertedTcp OBJECT-TYPE
		SYNTAX  CounterBasedGauge64 
		MAX-ACCESS read-only 
		STATUS current
		DESCRIPTION  "TCP Port Overloading Session Created" 
		::={ acosCgnv6Nat64GlobalS 37 } 

		portOverloadingSmpInsertedUdp OBJECT-TYPE
		SYNTAX  CounterBasedGauge64 
		MAX-ACCESS read-only 
		STATUS current
		DESCRIPTION  "UDP Port Overloading Session Created" 
		::={ acosCgnv6Nat64GlobalS 38 } 

		portOverloadingSmpFreeTcp OBJECT-TYPE
		SYNTAX  CounterBasedGauge64 
		MAX-ACCESS read-only 
		STATUS current
		DESCRIPTION  "TCP Port Overloading Session Freed" 
		::={ acosCgnv6Nat64GlobalS 39 } 

		portOverloadingSmpFreeUdp OBJECT-TYPE
		SYNTAX  CounterBasedGauge64 
		MAX-ACCESS read-only 
		STATUS current
		DESCRIPTION  "UDP Port Overloading Session Freed" 
		::={ acosCgnv6Nat64GlobalS 40 } 

		natPoolUnusable OBJECT-TYPE
		SYNTAX  CounterBasedGauge64 
		MAX-ACCESS read-only 
		STATUS current
		DESCRIPTION  "NAT Pool Unusable" 
		::={ acosCgnv6Nat64GlobalS 41 } 

		haNatPoolUnusable OBJECT-TYPE
		SYNTAX  CounterBasedGauge64 
		MAX-ACCESS read-only 
		STATUS current
		DESCRIPTION  "HA NAT Pool Unusable" 
		::={ acosCgnv6Nat64GlobalS 42 } 

		haNatPoolBatchTypeMismatch OBJECT-TYPE
		SYNTAX  CounterBasedGauge64 
		MAX-ACCESS read-only 
		STATUS current
		DESCRIPTION  "HA NAT Pool Batch Type Mismatch" 
		::={ acosCgnv6Nat64GlobalS 43 } 

		noRadiusProfileMatch OBJECT-TYPE
		SYNTAX  CounterBasedGauge64 
		MAX-ACCESS read-only 
		STATUS current
		DESCRIPTION  "No RADIUS Profile Match" 
		::={ acosCgnv6Nat64GlobalS 44 } 

		l3 OBJECT-TYPE
		SYNTAX  CounterBasedGauge64 
		MAX-ACCESS read-only 
		STATUS current
		DESCRIPTION  "Layer 3 Forwarded Packets" 
		::={ acosCgnv6Nat64GlobalS 45 } 

		sourceMatchesPrefix OBJECT-TYPE
		SYNTAX  CounterBasedGauge64 
		MAX-ACCESS read-only 
		STATUS current
		DESCRIPTION  "Source Address Prefix Match Drop" 
		::={ acosCgnv6Nat64GlobalS 46 } 

		lidDrop OBJECT-TYPE
		SYNTAX  CounterBasedGauge64 
		MAX-ACCESS read-only 
		STATUS current
		DESCRIPTION  "LSN LID Drop" 
		::={ acosCgnv6Nat64GlobalS 47 } 

		lidPassThrough OBJECT-TYPE
		SYNTAX  CounterBasedGauge64 
		MAX-ACCESS read-only 
		STATUS current
		DESCRIPTION  "LSN LID Pass-through" 
		::={ acosCgnv6Nat64GlobalS 48 } 

		noClassListMatch OBJECT-TYPE
		SYNTAX  CounterBasedGauge64 
		MAX-ACCESS read-only 
		STATUS current
		DESCRIPTION  "No Class-List Match" 
		::={ acosCgnv6Nat64GlobalS 49 } 

		userQuotaMemAllocated OBJECT-TYPE
		SYNTAX  CounterBasedGauge64 
		MAX-ACCESS read-only 
		STATUS current
		DESCRIPTION  "User-Quota Memory Allocated" 
		::={ acosCgnv6Nat64GlobalS 50 } 

		userQuotaMemFreed OBJECT-TYPE
		SYNTAX  CounterBasedGauge64 
		MAX-ACCESS read-only 
		STATUS current
		DESCRIPTION  "User-Quota Memory Freed" 
		::={ acosCgnv6Nat64GlobalS 51 } 

		userQuotaCreatedShadow OBJECT-TYPE
		SYNTAX  CounterBasedGauge64 
		MAX-ACCESS read-only 
		STATUS current
		DESCRIPTION  "Total User-Quota Created" 
		::={ acosCgnv6Nat64GlobalS 52 } 

		quotaMarkedDeleted OBJECT-TYPE
		SYNTAX  CounterBasedGauge64 
		MAX-ACCESS read-only 
		STATUS current
		DESCRIPTION  "User-Quota Marked Deleted" 
		::={ acosCgnv6Nat64GlobalS 53 } 

		quotaDeleteNotInBucket OBJECT-TYPE
		SYNTAX  CounterBasedGauge64 
		MAX-ACCESS read-only 
		STATUS current
		DESCRIPTION  "User-Quota Delete Not In Bucket" 
		::={ acosCgnv6Nat64GlobalS 54 } 

		userQuotaPutInDelQShadow OBJECT-TYPE
		SYNTAX  CounterBasedGauge64 
		MAX-ACCESS read-only 
		STATUS current
		DESCRIPTION  "Total User-Quota Put In Del Q" 
		::={ acosCgnv6Nat64GlobalS 55 } 

		prefixQuotaCreated OBJECT-TYPE
		SYNTAX  CounterBasedGauge64 
		MAX-ACCESS read-only 
		STATUS current
		DESCRIPTION  "Total Prefix Quota Created" 
		::={ acosCgnv6Nat64GlobalS 56 } 

		prefixQuotaPutInDelQ OBJECT-TYPE
		SYNTAX  CounterBasedGauge64 
		MAX-ACCESS read-only 
		STATUS current
		DESCRIPTION  "Total Prefix Quota Freed" 
		::={ acosCgnv6Nat64GlobalS 57 } 

		prefixQuotaFailure OBJECT-TYPE
		SYNTAX  CounterBasedGauge64 
		MAX-ACCESS read-only 
		STATUS current
		DESCRIPTION  "Total Prefix Quota Failure" 
		::={ acosCgnv6Nat64GlobalS 58 } 

		totalUserQuotaCreated OBJECT-TYPE
		SYNTAX  CounterBasedGauge64 
		MAX-ACCESS read-only 
		STATUS current
		DESCRIPTION  "Total Quota Structure Created" 
		::={ acosCgnv6Nat64GlobalS 59 } 

		totalUserQuotaPutInDelQ OBJECT-TYPE
		SYNTAX  CounterBasedGauge64 
		MAX-ACCESS read-only 
		STATUS current
		DESCRIPTION  "Total Quota Structure Freed" 
		::={ acosCgnv6Nat64GlobalS 60 } 

		totalUserQuotaFailure OBJECT-TYPE
		SYNTAX  CounterBasedGauge64 
		MAX-ACCESS read-only 
		STATUS current
		DESCRIPTION  "Total Quota Structure Failure" 
		::={ acosCgnv6Nat64GlobalS 61 } 

		tcpOutOfStateRstSent OBJECT-TYPE
		SYNTAX  CounterBasedGauge64 
		MAX-ACCESS read-only 
		STATUS current
		DESCRIPTION  "Total Out of State TCP RST sent" 
		::={ acosCgnv6Nat64GlobalS 62 } 

		tcpOutOfStateRstDropped OBJECT-TYPE
		SYNTAX  CounterBasedGauge64 
		MAX-ACCESS read-only 
		STATUS current
		DESCRIPTION  "Total Out of State TCP RST dropped" 
		::={ acosCgnv6Nat64GlobalS 63 } 

		icmpOutOfStateUqeAdminFilteredSent OBJECT-TYPE
		SYNTAX  CounterBasedGauge64 
		MAX-ACCESS read-only 
		STATUS current
		DESCRIPTION  "Total User Quota Exceeded ICMP admin filtered sent" 
		::={ acosCgnv6Nat64GlobalS 64 } 

		icmpOutOfStateUqeHostUnreachableSent OBJECT-TYPE
		SYNTAX  CounterBasedGauge64 
		MAX-ACCESS read-only 
		STATUS current
		DESCRIPTION  "Total User Quota Exceeded ICMP host unreachable sent" 
		::={ acosCgnv6Nat64GlobalS 65 } 

		icmpOutOfStateUqeDropped OBJECT-TYPE
		SYNTAX  CounterBasedGauge64 
		MAX-ACCESS read-only 
		STATUS current
		DESCRIPTION  "Total User Queue Exceeded ICMP notification dropped" 
		::={ acosCgnv6Nat64GlobalS 66 } 

		userQuotaNotFound OBJECT-TYPE
		SYNTAX  CounterBasedGauge64 
		MAX-ACCESS read-only 
		STATUS current
		DESCRIPTION  "User-Quota Not Found" 
		::={ acosCgnv6Nat64GlobalS 67 } 

		tcpFullconeCreatedShadow OBJECT-TYPE
		SYNTAX  CounterBasedGauge64 
		MAX-ACCESS read-only 
		STATUS current
		DESCRIPTION  "Total TCP Full-cone sessions created" 
		::={ acosCgnv6Nat64GlobalS 68 } 

		tcpFullconeFreedShadow OBJECT-TYPE
		SYNTAX  CounterBasedGauge64 
		MAX-ACCESS read-only 
		STATUS current
		DESCRIPTION  "Total TCP Full-cone sessions freed" 
		::={ acosCgnv6Nat64GlobalS 69 } 

		udpFullconeCreatedShadow OBJECT-TYPE
		SYNTAX  CounterBasedGauge64 
		MAX-ACCESS read-only 
		STATUS current
		DESCRIPTION  "Total UDP Full-cone sessions created" 
		::={ acosCgnv6Nat64GlobalS 70 } 

		udpFullconeFreedShadow OBJECT-TYPE
		SYNTAX  CounterBasedGauge64 
		MAX-ACCESS read-only 
		STATUS current
		DESCRIPTION  "Total UDP Full-cone sessions freed" 
		::={ acosCgnv6Nat64GlobalS 71 } 

		udpAlgFullconeCreated OBJECT-TYPE
		SYNTAX  CounterBasedGauge64 
		MAX-ACCESS read-only 
		STATUS current
		DESCRIPTION  "Total UDP ALG Full-cone sessions created" 
		::={ acosCgnv6Nat64GlobalS 72 } 

		udpAlgFullconeFreed OBJECT-TYPE
		SYNTAX  CounterBasedGauge64 
		MAX-ACCESS read-only 
		STATUS current
		DESCRIPTION  "Total UDP ALG Full-cone sessions freed" 
		::={ acosCgnv6Nat64GlobalS 73 } 

		fullconeCreated OBJECT-TYPE
		SYNTAX  CounterBasedGauge64 
		MAX-ACCESS read-only 
		STATUS current
		DESCRIPTION  "Total Full-cone sessions created" 
		::={ acosCgnv6Nat64GlobalS 74 } 

		fullconeFreed OBJECT-TYPE
		SYNTAX  CounterBasedGauge64 
		MAX-ACCESS read-only 
		STATUS current
		DESCRIPTION  "Total Full-cone sessions freed" 
		::={ acosCgnv6Nat64GlobalS 75 } 

		dataSessionCreatedShadow OBJECT-TYPE
		SYNTAX  CounterBasedGauge64 
		MAX-ACCESS read-only 
		STATUS current
		DESCRIPTION  "Total Data Sessions Created" 
		::={ acosCgnv6Nat64GlobalS 76 } 

		dataSessionFreedShadow OBJECT-TYPE
		SYNTAX  CounterBasedGauge64 
		MAX-ACCESS read-only 
		STATUS current
		DESCRIPTION  "Total Data Sessions Freed" 
		::={ acosCgnv6Nat64GlobalS 77 } 

		dataSessionUserQuotaMismatch OBJECT-TYPE
		SYNTAX  CounterBasedGauge64 
		MAX-ACCESS read-only 
		STATUS current
		DESCRIPTION  "Data Session Counter Per User Mismatch" 
		::={ acosCgnv6Nat64GlobalS 78 } 

		extendedQuotaMismatched OBJECT-TYPE
		SYNTAX  CounterBasedGauge64 
		MAX-ACCESS read-only 
		STATUS current
		DESCRIPTION  "Extended User-Quota Mismatched" 
		::={ acosCgnv6Nat64GlobalS 79 } 

		natPortUnavailableOther OBJECT-TYPE
		SYNTAX  CounterBasedGauge64 
		MAX-ACCESS read-only 
		STATUS current
		DESCRIPTION  "Other NAT Port Unavailable" 
		::={ acosCgnv6Nat64GlobalS 80 } 

		natPortUnavailable OBJECT-TYPE
		SYNTAX  CounterBasedGauge64 
		MAX-ACCESS read-only 
		STATUS current
		DESCRIPTION  "Total NAT Port Unavailable" 
		::={ acosCgnv6Nat64GlobalS 81 } 

		newUserResourceUnavailableTcp OBJECT-TYPE
		SYNTAX  CounterBasedGauge64 
		MAX-ACCESS read-only 
		STATUS current
		DESCRIPTION  "TCP New User NAT Resource Unavailable" 
		::={ acosCgnv6Nat64GlobalS 82 } 

		newUserResourceUnavailableUdp OBJECT-TYPE
		SYNTAX  CounterBasedGauge64 
		MAX-ACCESS read-only 
		STATUS current
		DESCRIPTION  "UDP New User NAT Resource Unavailable" 
		::={ acosCgnv6Nat64GlobalS 83 } 

		newUserResourceUnavailableIcmp OBJECT-TYPE
		SYNTAX  CounterBasedGauge64 
		MAX-ACCESS read-only 
		STATUS current
		DESCRIPTION  "ICMP New User NAT Resource Unavailable" 
		::={ acosCgnv6Nat64GlobalS 84 } 

		newUserResourceUnavailableOther OBJECT-TYPE
		SYNTAX  CounterBasedGauge64 
		MAX-ACCESS read-only 
		STATUS current
		DESCRIPTION  "Other New User NAT Resource Unavailable" 
		::={ acosCgnv6Nat64GlobalS 85 } 

		totalTcpAllocatedShadow OBJECT-TYPE
		SYNTAX  CounterBasedGauge64 
		MAX-ACCESS read-only 
		STATUS current
		DESCRIPTION  "Total TCP Ports Allocated" 
		::={ acosCgnv6Nat64GlobalS 86 } 

		totalTcpFreedShadow OBJECT-TYPE
		SYNTAX  CounterBasedGauge64 
		MAX-ACCESS read-only 
		STATUS current
		DESCRIPTION  "Total TCP Ports Freed" 
		::={ acosCgnv6Nat64GlobalS 87 } 

		totalUdpAllocatedShadow OBJECT-TYPE
		SYNTAX  CounterBasedGauge64 
		MAX-ACCESS read-only 
		STATUS current
		DESCRIPTION  "Total UDP Ports Allocated" 
		::={ acosCgnv6Nat64GlobalS 88 } 

		totalUdpFreedShadow OBJECT-TYPE
		SYNTAX  CounterBasedGauge64 
		MAX-ACCESS read-only 
		STATUS current
		DESCRIPTION  "Total UDP Ports Freed" 
		::={ acosCgnv6Nat64GlobalS 89 } 

		totalIcmpAllocatedShadow OBJECT-TYPE
		SYNTAX  CounterBasedGauge64 
		MAX-ACCESS read-only 
		STATUS current
		DESCRIPTION  "Total ICMP Ports Allocated" 
		::={ acosCgnv6Nat64GlobalS 90 } 

		totalIcmpFreedShadow OBJECT-TYPE
		SYNTAX  CounterBasedGauge64 
		MAX-ACCESS read-only 
		STATUS current
		DESCRIPTION  "Total ICMP Ports Freed" 
		::={ acosCgnv6Nat64GlobalS 91 } 

		udpAlgNoQuota OBJECT-TYPE
		SYNTAX  CounterBasedGauge64 
		MAX-ACCESS read-only 
		STATUS current
		DESCRIPTION  "UDP ALG User-Quota Not Found" 
		::={ acosCgnv6Nat64GlobalS 92 } 

		udpAlgEimMismatch OBJECT-TYPE
		SYNTAX  CounterBasedGauge64 
		MAX-ACCESS read-only 
		STATUS current
		DESCRIPTION  "UDP ALG Endpoint-Independent Mapping Mismatch" 
		::={ acosCgnv6Nat64GlobalS 93 } 

		udpAlgNoNatIp OBJECT-TYPE
		SYNTAX  CounterBasedGauge64 
		MAX-ACCESS read-only 
		STATUS current
		DESCRIPTION  "UDP ALG User-Quota Unknown NAT IP" 
		::={ acosCgnv6Nat64GlobalS 94 } 

		udpAlgAllocFailure OBJECT-TYPE
		SYNTAX  CounterBasedGauge64 
		MAX-ACCESS read-only 
		STATUS current
		DESCRIPTION  "UDP ALG Port Allocation Failure" 
		::={ acosCgnv6Nat64GlobalS 95 } 

		sipAlgNoQuota OBJECT-TYPE
		SYNTAX  CounterBasedGauge64 
		MAX-ACCESS read-only 
		STATUS current
		DESCRIPTION  "SIP ALG User-Quota Not Found" 
		::={ acosCgnv6Nat64GlobalS 96 } 

		sipAlgQuotaIncFailure OBJECT-TYPE
		SYNTAX  CounterBasedGauge64 
		MAX-ACCESS read-only 
		STATUS current
		DESCRIPTION  "SIP ALG User-Quota Exceeded" 
		::={ acosCgnv6Nat64GlobalS 97 } 

		sipAlgNoNatIp OBJECT-TYPE
		SYNTAX  CounterBasedGauge64 
		MAX-ACCESS read-only 
		STATUS current
		DESCRIPTION  "SIP ALG Unknown NAT IP" 
		::={ acosCgnv6Nat64GlobalS 98 } 

		sipAlgReuseContactFullcone OBJECT-TYPE
		SYNTAX  CounterBasedGauge64 
		MAX-ACCESS read-only 
		STATUS current
		DESCRIPTION  "SIP ALG Reuse Contact Full-cone Session" 
		::={ acosCgnv6Nat64GlobalS 99 } 

		sipAlgContactFullconeMismatch OBJECT-TYPE
		SYNTAX  CounterBasedGauge64 
		MAX-ACCESS read-only 
		STATUS current
		DESCRIPTION  "SIP ALG Contact Full-cone Session Mismatch" 
		::={ acosCgnv6Nat64GlobalS 100 } 

		sipAlgAllocContactPortFailure OBJECT-TYPE
		SYNTAX  CounterBasedGauge64 
		MAX-ACCESS read-only 
		STATUS current
		DESCRIPTION  "SIP ALG Alloc Contact NAT Port Failure" 
		::={ acosCgnv6Nat64GlobalS 101 } 

		sipAlgCreateContactFullconeFailure OBJECT-TYPE
		SYNTAX  CounterBasedGauge64 
		MAX-ACCESS read-only 
		STATUS current
		DESCRIPTION  "SIP ALG Create Contact Full-cone Session Failure" 
		::={ acosCgnv6Nat64GlobalS 102 } 

		sipAlgReleaseContactPortFailure OBJECT-TYPE
		SYNTAX  CounterBasedGauge64 
		MAX-ACCESS read-only 
		STATUS current
		DESCRIPTION  "SIP ALG Release Contact NAT Port Failure" 
		::={ acosCgnv6Nat64GlobalS 103 } 

		sipAlgSingleRtpFullcone OBJECT-TYPE
		SYNTAX  CounterBasedGauge64 
		MAX-ACCESS read-only 
		STATUS current
		DESCRIPTION  "SIP ALG Single RTP Full-cone Found" 
		::={ acosCgnv6Nat64GlobalS 104 } 

		sipAlgSingleRtcpFullcone OBJECT-TYPE
		SYNTAX  CounterBasedGauge64 
		MAX-ACCESS read-only 
		STATUS current
		DESCRIPTION  "SIP ALG Single RTCP Full-cone Found" 
		::={ acosCgnv6Nat64GlobalS 105 } 

		sipAlgRtcpFullconeMismatch OBJECT-TYPE
		SYNTAX  CounterBasedGauge64 
		MAX-ACCESS read-only 
		STATUS current
		DESCRIPTION  "SIP ALG RTCP Full-cone NAT Port Mismatch" 
		::={ acosCgnv6Nat64GlobalS 106 } 

		sipAlgReuseRtpRtcpFullcone OBJECT-TYPE
		SYNTAX  CounterBasedGauge64 
		MAX-ACCESS read-only 
		STATUS current
		DESCRIPTION  "SIP ALG Reuse RTP/RTCP Full-cone Session" 
		::={ acosCgnv6Nat64GlobalS 107 } 

		sipAlgAllocRtpRtcpPortFailure OBJECT-TYPE
		SYNTAX  CounterBasedGauge64 
		MAX-ACCESS read-only 
		STATUS current
		DESCRIPTION  "SIP ALG Alloc RTP/RTCP NAT Ports Failure" 
		::={ acosCgnv6Nat64GlobalS 108 } 

		sipAlgAllocSinglePortFailure OBJECT-TYPE
		SYNTAX  CounterBasedGauge64 
		MAX-ACCESS read-only 
		STATUS current
		DESCRIPTION  "SIP ALG Alloc Single RTP or RTCP NAT Port Failure" 
		::={ acosCgnv6Nat64GlobalS 109 } 

		sipAlgCreateSingleFullconeFailure OBJECT-TYPE
		SYNTAX  CounterBasedGauge64 
		MAX-ACCESS read-only 
		STATUS current
		DESCRIPTION  "SIP ALG Create Single RTP or RTCP Full-cone Session Failure" 
		::={ acosCgnv6Nat64GlobalS 110 } 

		sipAlgCreateRtpFullconeFailure OBJECT-TYPE
		SYNTAX  CounterBasedGauge64 
		MAX-ACCESS read-only 
		STATUS current
		DESCRIPTION  "SIP ALG Create RTP Full-cone Session Failure" 
		::={ acosCgnv6Nat64GlobalS 111 } 

		sipAlgCreateRtcpFullconeFailure OBJECT-TYPE
		SYNTAX  CounterBasedGauge64 
		MAX-ACCESS read-only 
		STATUS current
		DESCRIPTION  "SIP ALG Create RTCP Full-cone Session Failure" 
		::={ acosCgnv6Nat64GlobalS 112 } 

		sipAlgPortPairAllocFromConsecutive OBJECT-TYPE
		SYNTAX  CounterBasedGauge64 
		MAX-ACCESS read-only 
		STATUS current
		DESCRIPTION  "SIP ALG Port Pair Allocated From Consecutive" 
		::={ acosCgnv6Nat64GlobalS 113 } 

		sipAlgPortPairAllocFromPartition OBJECT-TYPE
		SYNTAX  CounterBasedGauge64 
		MAX-ACCESS read-only 
		STATUS current
		DESCRIPTION  "SIP ALG Port Pair Allocated From Partition" 
		::={ acosCgnv6Nat64GlobalS 114 } 

		sipAlgPortPairAllocFromPoolPortBatch OBJECT-TYPE
		SYNTAX  CounterBasedGauge64 
		MAX-ACCESS read-only 
		STATUS current
		DESCRIPTION  "SIP ALG Port Pair Allocated From Pool Port Batch" 
		::={ acosCgnv6Nat64GlobalS 115 } 

		sipAlgPortPairAllocFromQuotaConsecutive OBJECT-TYPE
		SYNTAX  CounterBasedGauge64 
		MAX-ACCESS read-only 
		STATUS current
		DESCRIPTION  "SIP ALG Port Pair Allocated From Quota Consecutive" 
		::={ acosCgnv6Nat64GlobalS 116 } 

		sipAlgPortPairAllocFromQuotaPartition OBJECT-TYPE
		SYNTAX  CounterBasedGauge64 
		MAX-ACCESS read-only 
		STATUS current
		DESCRIPTION  "SIP ALG Port Pair Allocated From Quota Partition" 
		::={ acosCgnv6Nat64GlobalS 117 } 

		sipAlgPortPairAllocFromQuotaPartitionError OBJECT-TYPE
		SYNTAX  CounterBasedGauge64 
		MAX-ACCESS read-only 
		STATUS current
		DESCRIPTION  "SIP ALG Port Pair Allocated From Quota Partition Error" 
		::={ acosCgnv6Nat64GlobalS 118 } 

		sipAlgPortPairAllocFromQuotaPoolPortBatch OBJECT-TYPE
		SYNTAX  CounterBasedGauge64 
		MAX-ACCESS read-only 
		STATUS current
		DESCRIPTION  "SIP ALG Port Pair Allocated From Quota Pool Port Batch" 
		::={ acosCgnv6Nat64GlobalS 119 } 

		sipAlgPortPairAllocFromQuotaPoolPortBatchWithFrag OBJECT-TYPE
		SYNTAX  CounterBasedGauge64 
		MAX-ACCESS read-only 
		STATUS current
		DESCRIPTION  "SIP ALG Port Pair Allocated From Quota Port Batch Version 2 with Frag Free Ports" 
		::={ acosCgnv6Nat64GlobalS 120 } 

		h323AlgNoQuota OBJECT-TYPE
		SYNTAX  CounterBasedGauge64 
		MAX-ACCESS read-only 
		STATUS current
		DESCRIPTION  "H323 ALG User-Quota Not Found" 
		::={ acosCgnv6Nat64GlobalS 121 } 

		h323AlgQuotaIncFailure OBJECT-TYPE
		SYNTAX  CounterBasedGauge64 
		MAX-ACCESS read-only 
		STATUS current
		DESCRIPTION  "H323 ALG User-Quota Exceeded" 
		::={ acosCgnv6Nat64GlobalS 122 } 

		h323AlgNoNatIp OBJECT-TYPE
		SYNTAX  CounterBasedGauge64 
		MAX-ACCESS read-only 
		STATUS current
		DESCRIPTION  "H323 ALG Unknown NAT IP" 
		::={ acosCgnv6Nat64GlobalS 123 } 

		h323AlgReuseFullcone OBJECT-TYPE
		SYNTAX  CounterBasedGauge64 
		MAX-ACCESS read-only 
		STATUS current
		DESCRIPTION  "H323 ALG Reuse Full-cone Session" 
		::={ acosCgnv6Nat64GlobalS 124 } 

		h323AlgFullconeMismatch OBJECT-TYPE
		SYNTAX  CounterBasedGauge64 
		MAX-ACCESS read-only 
		STATUS current
		DESCRIPTION  "H323 ALG Full-cone Session Mismatch" 
		::={ acosCgnv6Nat64GlobalS 125 } 

		h323AlgAllocPortFailure OBJECT-TYPE
		SYNTAX  CounterBasedGauge64 
		MAX-ACCESS read-only 
		STATUS current
		DESCRIPTION  "H323 ALG Alloc NAT Port Failure" 
		::={ acosCgnv6Nat64GlobalS 126 } 

		h323AlgCreateFullconeFailure OBJECT-TYPE
		SYNTAX  CounterBasedGauge64 
		MAX-ACCESS read-only 
		STATUS current
		DESCRIPTION  "H323 ALG Create Full-cone Session Failure" 
		::={ acosCgnv6Nat64GlobalS 127 } 

		h323AlgReleasePortFailure OBJECT-TYPE
		SYNTAX  CounterBasedGauge64 
		MAX-ACCESS read-only 
		STATUS current
		DESCRIPTION  "H323 ALG Release NAT Port Failure" 
		::={ acosCgnv6Nat64GlobalS 128 } 

		h323AlgSingleRtpFullcone OBJECT-TYPE
		SYNTAX  CounterBasedGauge64 
		MAX-ACCESS read-only 
		STATUS current
		DESCRIPTION  "H323 ALG Single RTP Full-cone Found" 
		::={ acosCgnv6Nat64GlobalS 129 } 

		h323AlgSingleRtcpFullcone OBJECT-TYPE
		SYNTAX  CounterBasedGauge64 
		MAX-ACCESS read-only 
		STATUS current
		DESCRIPTION  "H323 ALG Single RTCP Full-cone Found" 
		::={ acosCgnv6Nat64GlobalS 130 } 

		h323AlgRtcpFullconeMismatch OBJECT-TYPE
		SYNTAX  CounterBasedGauge64 
		MAX-ACCESS read-only 
		STATUS current
		DESCRIPTION  "H323 ALG RTCP Full-cone NAT Port Mismatch" 
		::={ acosCgnv6Nat64GlobalS 131 } 

		h323AlgReuseRtpRtcpFullcone OBJECT-TYPE
		SYNTAX  CounterBasedGauge64 
		MAX-ACCESS read-only 
		STATUS current
		DESCRIPTION  "H323 ALG Reuse RTP/RTCP Full-cone Session" 
		::={ acosCgnv6Nat64GlobalS 132 } 

		h323AlgAllocRtpRtcpPortFailure OBJECT-TYPE
		SYNTAX  CounterBasedGauge64 
		MAX-ACCESS read-only 
		STATUS current
		DESCRIPTION  "H323 ALG Alloc RTP/RTCP NAT Ports Failure" 
		::={ acosCgnv6Nat64GlobalS 133 } 

		h323AlgAllocSinglePortFailure OBJECT-TYPE
		SYNTAX  CounterBasedGauge64 
		MAX-ACCESS read-only 
		STATUS current
		DESCRIPTION  "H323 ALG Alloc Single RTP or RTCP NAT Port Failure" 
		::={ acosCgnv6Nat64GlobalS 134 } 

		h323AlgCreateSingleFullconeFailure OBJECT-TYPE
		SYNTAX  CounterBasedGauge64 
		MAX-ACCESS read-only 
		STATUS current
		DESCRIPTION  "H323 ALG Create Single RTP or RTCP Full-cone Session Failure" 
		::={ acosCgnv6Nat64GlobalS 135 } 

		h323AlgCreateRtpFullconeFailure OBJECT-TYPE
		SYNTAX  CounterBasedGauge64 
		MAX-ACCESS read-only 
		STATUS current
		DESCRIPTION  "H323 ALG Create RTP Full-cone Session Failure" 
		::={ acosCgnv6Nat64GlobalS 136 } 

		h323AlgCreateRtcpFullconeFailure OBJECT-TYPE
		SYNTAX  CounterBasedGauge64 
		MAX-ACCESS read-only 
		STATUS current
		DESCRIPTION  "H323 ALG Create RTCP Full-cone Session Failure" 
		::={ acosCgnv6Nat64GlobalS 137 } 

		h323AlgPortPairAllocFromConsecutive OBJECT-TYPE
		SYNTAX  CounterBasedGauge64 
		MAX-ACCESS read-only 
		STATUS current
		DESCRIPTION  "H323 ALG Port Pair Allocated From Consecutive" 
		::={ acosCgnv6Nat64GlobalS 138 } 

		h323AlgPortPairAllocFromPartition OBJECT-TYPE
		SYNTAX  CounterBasedGauge64 
		MAX-ACCESS read-only 
		STATUS current
		DESCRIPTION  "H323 ALG Port Pair Allocated From Partition" 
		::={ acosCgnv6Nat64GlobalS 139 } 

		h323AlgPortPairAllocFromPoolPortBatch OBJECT-TYPE
		SYNTAX  CounterBasedGauge64 
		MAX-ACCESS read-only 
		STATUS current
		DESCRIPTION  "H323 ALG Port Pair Allocated From Pool Port Batch" 
		::={ acosCgnv6Nat64GlobalS 140 } 

		h323AlgPortPairAllocFromQuotaConsecutive OBJECT-TYPE
		SYNTAX  CounterBasedGauge64 
		MAX-ACCESS read-only 
		STATUS current
		DESCRIPTION  "H323 ALG Port Pair Allocated From Quota Consecutive" 
		::={ acosCgnv6Nat64GlobalS 141 } 

		h323AlgPortPairAllocFromQuotaPartition OBJECT-TYPE
		SYNTAX  CounterBasedGauge64 
		MAX-ACCESS read-only 
		STATUS current
		DESCRIPTION  "H323 ALG Port Pair Allocated From Quota Partition" 
		::={ acosCgnv6Nat64GlobalS 142 } 

		h323AlgPortPairAllocFromQuotaPartitionError OBJECT-TYPE
		SYNTAX  CounterBasedGauge64 
		MAX-ACCESS read-only 
		STATUS current
		DESCRIPTION  "H323 ALG Port Pair Allocated From Quota Partition Error" 
		::={ acosCgnv6Nat64GlobalS 143 } 

		h323AlgPortPairAllocFromQuotaPoolPortBatch OBJECT-TYPE
		SYNTAX  CounterBasedGauge64 
		MAX-ACCESS read-only 
		STATUS current
		DESCRIPTION  "H323 ALG Port Pair Allocated From Quota Pool Port Batch" 
		::={ acosCgnv6Nat64GlobalS 144 } 

		portBatchQuotaExtensionAllocFailure OBJECT-TYPE
		SYNTAX  CounterBasedGauge64 
		MAX-ACCESS read-only 
		STATUS current
		DESCRIPTION  "Port Batch Extension Alloc Failure (No memory)" 
		::={ acosCgnv6Nat64GlobalS 145 } 

		portBatchFreeQuotaNotFound OBJECT-TYPE
		SYNTAX  CounterBasedGauge64 
		MAX-ACCESS read-only 
		STATUS current
		DESCRIPTION  "Port Batch Quota Not Found on Free" 
		::={ acosCgnv6Nat64GlobalS 146 } 

		portBatchFreePortNotFound OBJECT-TYPE
		SYNTAX  CounterBasedGauge64 
		MAX-ACCESS read-only 
		STATUS current
		DESCRIPTION  "Port Batch Port Not Found on Free" 
		::={ acosCgnv6Nat64GlobalS 147 } 

		portBatchFreeWrongPartition OBJECT-TYPE
		SYNTAX  CounterBasedGauge64 
		MAX-ACCESS read-only 
		STATUS current
		DESCRIPTION  "Port Batch Free Wrong Partition" 
		::={ acosCgnv6Nat64GlobalS 148 } 

		radiusQueryQuotaExtAllocFailure OBJECT-TYPE
		SYNTAX  CounterBasedGauge64 
		MAX-ACCESS read-only 
		STATUS current
		DESCRIPTION  "RADIUS Query Container Alloc (No Memoty)" 
		::={ acosCgnv6Nat64GlobalS 149 } 

		radiusQueryQuotaExtAllocRaceFree OBJECT-TYPE
		SYNTAX  CounterBasedGauge64 
		MAX-ACCESS read-only 
		STATUS current
		DESCRIPTION  "RADIUS Query Container Alloc Race Free" 
		::={ acosCgnv6Nat64GlobalS 150 } 

		quotaExtensionAdded OBJECT-TYPE
		SYNTAX  CounterBasedGauge64 
		MAX-ACCESS read-only 
		STATUS current
		DESCRIPTION  "Quota Extension Added to Quota" 
		::={ acosCgnv6Nat64GlobalS 151 } 

		quotaExtensionRemoved OBJECT-TYPE
		SYNTAX  CounterBasedGauge64 
		MAX-ACCESS read-only 
		STATUS current
		DESCRIPTION  "Quota Extension Removed from Quota" 
		::={ acosCgnv6Nat64GlobalS 152 } 

		quotaExtensionRemoveNotFound OBJECT-TYPE
		SYNTAX  CounterBasedGauge64 
		MAX-ACCESS read-only 
		STATUS current
		DESCRIPTION  "Quota Extension Not Found on Remove" 
		::={ acosCgnv6Nat64GlobalS 153 } 

		haSyncPortBatchSent OBJECT-TYPE
		SYNTAX  CounterBasedGauge64 
		MAX-ACCESS read-only 
		STATUS current
		DESCRIPTION  "HA Port Batch Extension Sync Sent" 
		::={ acosCgnv6Nat64GlobalS 154 } 

		haSyncPortBatchRcv OBJECT-TYPE
		SYNTAX  CounterBasedGauge64 
		MAX-ACCESS read-only 
		STATUS current
		DESCRIPTION  "HA Port Batch Extension Sync Received" 
		::={ acosCgnv6Nat64GlobalS 155 } 

		haSendPortBatchNotFound OBJECT-TYPE
		SYNTAX  CounterBasedGauge64 
		MAX-ACCESS read-only 
		STATUS current
		DESCRIPTION  "HA Port Batch Not Found on Sync Send" 
		::={ acosCgnv6Nat64GlobalS 156 } 

		haRcvPortNotInPortBatch OBJECT-TYPE
		SYNTAX  CounterBasedGauge64 
		MAX-ACCESS read-only 
		STATUS current
		DESCRIPTION  "HA Port Not in Port Batch on Sync Rcv" 
		::={ acosCgnv6Nat64GlobalS 157 } 

		badPortToFree OBJECT-TYPE
		SYNTAX  CounterBasedGauge64 
		MAX-ACCESS read-only 
		STATUS current
		DESCRIPTION  "Freeing Bad Port" 
		::={ acosCgnv6Nat64GlobalS 158 } 

		consecutivePortFree OBJECT-TYPE
		SYNTAX  CounterBasedGauge64 
		MAX-ACCESS read-only 
		STATUS current
		DESCRIPTION  "Port Freed from Consecutive Pool" 
		::={ acosCgnv6Nat64GlobalS 159 } 

		partitionPortFree OBJECT-TYPE
		SYNTAX  CounterBasedGauge64 
		MAX-ACCESS read-only 
		STATUS current
		DESCRIPTION  "Port Freed from Partition" 
		::={ acosCgnv6Nat64GlobalS 160 } 

		poolPortBatchPortFree OBJECT-TYPE
		SYNTAX  CounterBasedGauge64 
		MAX-ACCESS read-only 
		STATUS current
		DESCRIPTION  "Port Freed from Pool Port Batch" 
		::={ acosCgnv6Nat64GlobalS 161 } 

		portAllocatedFromQuotaConsecutive OBJECT-TYPE
		SYNTAX  CounterBasedGauge64 
		MAX-ACCESS read-only 
		STATUS current
		DESCRIPTION  "Port Allocated from Quota Consecutive" 
		::={ acosCgnv6Nat64GlobalS 162 } 

		portAllocatedFromQuotaPartition OBJECT-TYPE
		SYNTAX  CounterBasedGauge64 
		MAX-ACCESS read-only 
		STATUS current
		DESCRIPTION  "Port Allocated from Quota Partition" 
		::={ acosCgnv6Nat64GlobalS 163 } 

		portAllocatedFromQuotaPoolPortBatch OBJECT-TYPE
		SYNTAX  CounterBasedGauge64 
		MAX-ACCESS read-only 
		STATUS current
		DESCRIPTION  "Port Allocated from Quota Pool Port Batch" 
		::={ acosCgnv6Nat64GlobalS 164 } 

		portFreedFromQuotaConsecutive OBJECT-TYPE
		SYNTAX  CounterBasedGauge64 
		MAX-ACCESS read-only 
		STATUS current
		DESCRIPTION  "Port Freed from Quota Consecutive" 
		::={ acosCgnv6Nat64GlobalS 165 } 

		portFreedFromQuotaPartition OBJECT-TYPE
		SYNTAX  CounterBasedGauge64 
		MAX-ACCESS read-only 
		STATUS current
		DESCRIPTION  "Port Freed from Quota Partition" 
		::={ acosCgnv6Nat64GlobalS 166 } 

		portFreedFromQuotaPoolPortBatch OBJECT-TYPE
		SYNTAX  CounterBasedGauge64 
		MAX-ACCESS read-only 
		STATUS current
		DESCRIPTION  "Port Freed from Quota Pool Port Batch" 
		::={ acosCgnv6Nat64GlobalS 167 } 

		portBatchAllocatedToQuota OBJECT-TYPE
		SYNTAX  CounterBasedGauge64 
		MAX-ACCESS read-only 
		STATUS current
		DESCRIPTION  "Port Batch Allocated to Quota" 
		::={ acosCgnv6Nat64GlobalS 168 } 

		portBatchFreedFromQuota OBJECT-TYPE
		SYNTAX  CounterBasedGauge64 
		MAX-ACCESS read-only 
		STATUS current
		DESCRIPTION  "Port Batch Freed From Quota" 
		::={ acosCgnv6Nat64GlobalS 169 } 

		specificPortAllocatedFromQuotaConsecutive OBJECT-TYPE
		SYNTAX  CounterBasedGauge64 
		MAX-ACCESS read-only 
		STATUS current
		DESCRIPTION  "Specific Port Allocated from Quota Consecutive" 
		::={ acosCgnv6Nat64GlobalS 170 } 

		specificPortAllocatedFromQuotaPartition OBJECT-TYPE
		SYNTAX  CounterBasedGauge64 
		MAX-ACCESS read-only 
		STATUS current
		DESCRIPTION  "Specific Port Allocated from Quota Partition" 
		::={ acosCgnv6Nat64GlobalS 171 } 

		specificPortAllocatedFromQuotaPoolPortBatch OBJECT-TYPE
		SYNTAX  CounterBasedGauge64 
		MAX-ACCESS read-only 
		STATUS current
		DESCRIPTION  "Specific Port Allocated from Quota Pool Port Batch" 
		::={ acosCgnv6Nat64GlobalS 172 } 

		portBatchContainerAllocFailure OBJECT-TYPE
		SYNTAX  CounterBasedGauge64 
		MAX-ACCESS read-only 
		STATUS current
		DESCRIPTION  "Port Batch Container Alloc Out of Memory" 
		::={ acosCgnv6Nat64GlobalS 173 } 

		portBatchContainerAllocRaceFree OBJECT-TYPE
		SYNTAX  CounterBasedGauge64 
		MAX-ACCESS read-only 
		STATUS current
		DESCRIPTION  "Port Batch Container Race Free" 
		::={ acosCgnv6Nat64GlobalS 174 } 

		portOverloadingDestinationConflict OBJECT-TYPE
		SYNTAX  CounterBasedGauge64 
		MAX-ACCESS read-only 
		STATUS current
		DESCRIPTION  "Port Overloading Destination Conflict" 
		::={ acosCgnv6Nat64GlobalS 175 } 

		portOverloadingOutOfMemory OBJECT-TYPE
		SYNTAX  CounterBasedGauge64 
		MAX-ACCESS read-only 
		STATUS current
		DESCRIPTION  "Port Overloading Out of Memory" 
		::={ acosCgnv6Nat64GlobalS 176 } 

		portOverloadingAssignUser OBJECT-TYPE
		SYNTAX  CounterBasedGauge64 
		MAX-ACCESS read-only 
		STATUS current
		DESCRIPTION  "Port Overloading Port Assign User" 
		::={ acosCgnv6Nat64GlobalS 177 } 

		portOverloadingAssignUserPortBatch OBJECT-TYPE
		SYNTAX  CounterBasedGauge64 
		MAX-ACCESS read-only 
		STATUS current
		DESCRIPTION  "Port Overloading Port Assign User Port Batch" 
		::={ acosCgnv6Nat64GlobalS 178 } 

		portOverloadingInc OBJECT-TYPE
		SYNTAX  CounterBasedGauge64 
		MAX-ACCESS read-only 
		STATUS current
		DESCRIPTION  "Port Overloading Port Increment" 
		::={ acosCgnv6Nat64GlobalS 179 } 

		portOverloadingDecOnConflict OBJECT-TYPE
		SYNTAX  CounterBasedGauge64 
		MAX-ACCESS read-only 
		STATUS current
		DESCRIPTION  "Port Overloading Port Decrement on Conflict" 
		::={ acosCgnv6Nat64GlobalS 180 } 

		portOverloadingDecOnFree OBJECT-TYPE
		SYNTAX  CounterBasedGauge64 
		MAX-ACCESS read-only 
		STATUS current
		DESCRIPTION  "Port Overloading Port Decrement on Free" 
		::={ acosCgnv6Nat64GlobalS 181 } 

		portOverloadingFreePortOnConflict OBJECT-TYPE
		SYNTAX  CounterBasedGauge64 
		MAX-ACCESS read-only 
		STATUS current
		DESCRIPTION  "Port Overloading Free Port on Conflict" 
		::={ acosCgnv6Nat64GlobalS 182 } 

		portOverloadingFreePortBatchOnConflict OBJECT-TYPE
		SYNTAX  CounterBasedGauge64 
		MAX-ACCESS read-only 
		STATUS current
		DESCRIPTION  "Port Overloading Free Port Batch on Conflict" 
		::={ acosCgnv6Nat64GlobalS 183 } 

		portOverloadingIncOverflow OBJECT-TYPE
		SYNTAX  CounterBasedGauge64 
		MAX-ACCESS read-only 
		STATUS current
		DESCRIPTION  "Port Overloading Inc Overflow" 
		::={ acosCgnv6Nat64GlobalS 184 } 

		portOverloadingAttemptConsecutivePorts OBJECT-TYPE
		SYNTAX  CounterBasedGauge64 
		MAX-ACCESS read-only 
		STATUS current
		DESCRIPTION  "Port Overloading on Consecutive Ports" 
		::={ acosCgnv6Nat64GlobalS 185 } 

		portOverloadingAttemptSamePartition OBJECT-TYPE
		SYNTAX  CounterBasedGauge64 
		MAX-ACCESS read-only 
		STATUS current
		DESCRIPTION  "Port Overloading on Same Partition" 
		::={ acosCgnv6Nat64GlobalS 186 } 

		portOverloadingAttemptDiffPartition OBJECT-TYPE
		SYNTAX  CounterBasedGauge64 
		MAX-ACCESS read-only 
		STATUS current
		DESCRIPTION  "Port Overloading on Different Partition" 
		::={ acosCgnv6Nat64GlobalS 187 } 

		portOverloadingAttemptFailed OBJECT-TYPE
		SYNTAX  CounterBasedGauge64 
		MAX-ACCESS read-only 
		STATUS current
		DESCRIPTION  "Port Overloading Attempt Failed" 
		::={ acosCgnv6Nat64GlobalS 188 } 

		portOverloadingConnFreeRetryLookup OBJECT-TYPE
		SYNTAX  CounterBasedGauge64 
		MAX-ACCESS read-only 
		STATUS current
		DESCRIPTION  "Port Overloading Conn Free Retry Lookup" 
		::={ acosCgnv6Nat64GlobalS 189 } 

		portOverloadingConnFreeNotFound OBJECT-TYPE
		SYNTAX  CounterBasedGauge64 
		MAX-ACCESS read-only 
		STATUS current
		DESCRIPTION  "Port Overloading Conn Free Not Found" 
		::={ acosCgnv6Nat64GlobalS 190 } 

		portOverloadingSmpMemAllocated OBJECT-TYPE
		SYNTAX  CounterBasedGauge64 
		MAX-ACCESS read-only 
		STATUS current
		DESCRIPTION  "Port Overloading SMP Session Allocated" 
		::={ acosCgnv6Nat64GlobalS 191 } 

		portOverloadingSmpMemFreed OBJECT-TYPE
		SYNTAX  CounterBasedGauge64 
		MAX-ACCESS read-only 
		STATUS current
		DESCRIPTION  "Port Overloading SMP Session Freed" 
		::={ acosCgnv6Nat64GlobalS 192 } 

		portOverloadingSmpInserted OBJECT-TYPE
		SYNTAX  CounterBasedGauge64 
		MAX-ACCESS read-only 
		STATUS current
		DESCRIPTION  "Port Overloading SMP Inserted" 
		::={ acosCgnv6Nat64GlobalS 193 } 

		portOverloadingSmpInsertedTcpShadow OBJECT-TYPE
		SYNTAX  CounterBasedGauge64 
		MAX-ACCESS read-only 
		STATUS current
		DESCRIPTION  "Total Port Overloading SMP TCP Inserted" 
		::={ acosCgnv6Nat64GlobalS 194 } 

		portOverloadingSmpInsertedUdpShadow OBJECT-TYPE
		SYNTAX  CounterBasedGauge64 
		MAX-ACCESS read-only 
		STATUS current
		DESCRIPTION  "Total Port Overloading SMP UDP Inserted" 
		::={ acosCgnv6Nat64GlobalS 195 } 

		portOverloadingSmpFreeTcpShadow OBJECT-TYPE
		SYNTAX  CounterBasedGauge64 
		MAX-ACCESS read-only 
		STATUS current
		DESCRIPTION  "Total Port Overloading SMP TCP Freed" 
		::={ acosCgnv6Nat64GlobalS 196 } 

		portOverloadingSmpFreeUdpShadow OBJECT-TYPE
		SYNTAX  CounterBasedGauge64 
		MAX-ACCESS read-only 
		STATUS current
		DESCRIPTION  "Total Port Overloading SMP UDP Freed" 
		::={ acosCgnv6Nat64GlobalS 197 } 

		portOverloadingSmpPutInDelQFromConn OBJECT-TYPE
		SYNTAX  CounterBasedGauge64 
		MAX-ACCESS read-only 
		STATUS current
		DESCRIPTION  "Port Overloading SMP Free From Conn" 
		::={ acosCgnv6Nat64GlobalS 198 } 

		portOverloadingSmpFreeDecFailure OBJECT-TYPE
		SYNTAX  CounterBasedGauge64 
		MAX-ACCESS read-only 
		STATUS current
		DESCRIPTION  "Port Overloading SMP Free Dec Failure" 
		::={ acosCgnv6Nat64GlobalS 199 } 

		portOverloadingSmpFreeNoQuota OBJECT-TYPE
		SYNTAX  CounterBasedGauge64 
		MAX-ACCESS read-only 
		STATUS current
		DESCRIPTION  "Port Overloading SMP Free No Quota" 
		::={ acosCgnv6Nat64GlobalS 200 } 

		portOverloadingSmpFreePort OBJECT-TYPE
		SYNTAX  CounterBasedGauge64 
		MAX-ACCESS read-only 
		STATUS current
		DESCRIPTION  "Port Overloading SMP Free Port" 
		::={ acosCgnv6Nat64GlobalS 201 } 

		portOverloadingSmpFreePortFromQuota OBJECT-TYPE
		SYNTAX  CounterBasedGauge64 
		MAX-ACCESS read-only 
		STATUS current
		DESCRIPTION  "Port Overloading SMP Free Port From Quota" 
		::={ acosCgnv6Nat64GlobalS 202 } 

		portOverloadingForNoPorts OBJECT-TYPE
		SYNTAX  CounterBasedGauge64 
		MAX-ACCESS read-only 
		STATUS current
		DESCRIPTION  "Port Overloading for No Ports" 
		::={ acosCgnv6Nat64GlobalS 203 } 

		portOverloadingForNoPortsSuccess OBJECT-TYPE
		SYNTAX  CounterBasedGauge64 
		MAX-ACCESS read-only 
		STATUS current
		DESCRIPTION  "Port Overloading for No Ports Success" 
		::={ acosCgnv6Nat64GlobalS 204 } 

		portOverloadingForQuotaExceeded OBJECT-TYPE
		SYNTAX  CounterBasedGauge64 
		MAX-ACCESS read-only 
		STATUS current
		DESCRIPTION  "Port Overloading for Quota Exceeded" 
		::={ acosCgnv6Nat64GlobalS 205 } 

		portOverloadingForQuotaExceededSuccess OBJECT-TYPE
		SYNTAX  CounterBasedGauge64 
		MAX-ACCESS read-only 
		STATUS current
		DESCRIPTION  "Port Overloading for Quota Exceeded Success" 
		::={ acosCgnv6Nat64GlobalS 206 } 

		portOverloadingForQuotaExceededRace OBJECT-TYPE
		SYNTAX  CounterBasedGauge64 
		MAX-ACCESS read-only 
		STATUS current
		DESCRIPTION  "Port Overloading for Quota Exceeded Race" 
		::={ acosCgnv6Nat64GlobalS 207 } 

		portOverloadingForQuotaExceededRaceSuccess OBJECT-TYPE
		SYNTAX  CounterBasedGauge64 
		MAX-ACCESS read-only 
		STATUS current
		DESCRIPTION  "Port Overloading for Quota Exceeded Race Success" 
		::={ acosCgnv6Nat64GlobalS 208 } 

		portOverloadingForNewUser OBJECT-TYPE
		SYNTAX  CounterBasedGauge64 
		MAX-ACCESS read-only 
		STATUS current
		DESCRIPTION  "Port Overloading for New User" 
		::={ acosCgnv6Nat64GlobalS 209 } 

		portOverloadingForNewUserSuccess OBJECT-TYPE
		SYNTAX  CounterBasedGauge64 
		MAX-ACCESS read-only 
		STATUS current
		DESCRIPTION  "Port Overloading for New User Success" 
		::={ acosCgnv6Nat64GlobalS 210 } 

		haPortOverloadingAttemptFailed OBJECT-TYPE
		SYNTAX  CounterBasedGauge64 
		MAX-ACCESS read-only 
		STATUS current
		DESCRIPTION  "HA Port Overloading Attempt Failed" 
		::={ acosCgnv6Nat64GlobalS 211 } 

		haPortOverloadingForNoPorts OBJECT-TYPE
		SYNTAX  CounterBasedGauge64 
		MAX-ACCESS read-only 
		STATUS current
		DESCRIPTION  "HA Port Overloading for No Ports" 
		::={ acosCgnv6Nat64GlobalS 212 } 

		haPortOverloadingForNoPortsSuccess OBJECT-TYPE
		SYNTAX  CounterBasedGauge64 
		MAX-ACCESS read-only 
		STATUS current
		DESCRIPTION  "HA Port Overloading for No Ports Success" 
		::={ acosCgnv6Nat64GlobalS 213 } 

		haPortOverloadingForQuotaExceeded OBJECT-TYPE
		SYNTAX  CounterBasedGauge64 
		MAX-ACCESS read-only 
		STATUS current
		DESCRIPTION  "HA Port Overloading for Quota Exceeded" 
		::={ acosCgnv6Nat64GlobalS 214 } 

		haPortOverloadingForQuotaExceededSuccess OBJECT-TYPE
		SYNTAX  CounterBasedGauge64 
		MAX-ACCESS read-only 
		STATUS current
		DESCRIPTION  "HA Port Overloading for Quota Exceeded Success" 
		::={ acosCgnv6Nat64GlobalS 215 } 

		haPortOverloadingForQuotaExceededRace OBJECT-TYPE
		SYNTAX  CounterBasedGauge64 
		MAX-ACCESS read-only 
		STATUS current
		DESCRIPTION  "HA Port Overloading for Quota Exceeded Race" 
		::={ acosCgnv6Nat64GlobalS 216 } 

		haPortOverloadingForQuotaExceededRaceSuccess OBJECT-TYPE
		SYNTAX  CounterBasedGauge64 
		MAX-ACCESS read-only 
		STATUS current
		DESCRIPTION  "HA Port Overloading for Quota Exceeded Race Success" 
		::={ acosCgnv6Nat64GlobalS 217 } 

		haPortOverloadingForNewUser OBJECT-TYPE
		SYNTAX  CounterBasedGauge64 
		MAX-ACCESS read-only 
		STATUS current
		DESCRIPTION  "HA Port Overloading for New User" 
		::={ acosCgnv6Nat64GlobalS 218 } 

		haPortOverloadingForNewUserSuccess OBJECT-TYPE
		SYNTAX  CounterBasedGauge64 
		MAX-ACCESS read-only 
		STATUS current
		DESCRIPTION  "HA Port Overloading for New User Success" 
		::={ acosCgnv6Nat64GlobalS 219 } 

		natPoolForceDelete OBJECT-TYPE
		SYNTAX  CounterBasedGauge64 
		MAX-ACCESS read-only 
		STATUS current
		DESCRIPTION  "NAT Pool Force Delete" 
		::={ acosCgnv6Nat64GlobalS 220 } 

		quotaExtTooMany OBJECT-TYPE
		SYNTAX  CounterBasedGauge64 
		MAX-ACCESS read-only 
		STATUS current
		DESCRIPTION  "Quota Ext Too Many" 
		::={ acosCgnv6Nat64GlobalS 221 } 

		natPoolNotFoundOnFree OBJECT-TYPE
		SYNTAX  CounterBasedGauge64 
		MAX-ACCESS read-only 
		STATUS current
		DESCRIPTION  "NAT Pool Not Found on Free" 
		::={ acosCgnv6Nat64GlobalS 222 } 

		standbyClassListDrop OBJECT-TYPE
		SYNTAX  CounterBasedGauge64 
		MAX-ACCESS read-only 
		STATUS current
		DESCRIPTION  "Standby Class-List Drop" 
		::={ acosCgnv6Nat64GlobalS 223 } 

		dstPrefixMismatch OBJECT-TYPE
		SYNTAX  CounterBasedGauge64 
		MAX-ACCESS read-only 
		STATUS current
		DESCRIPTION  "Destination Prefix Mismatch Drop" 
		::={ acosCgnv6Nat64GlobalS 224 } 

		fullconeInboundNatPoolMismatch OBJECT-TYPE
		SYNTAX  CounterBasedGauge64 
		MAX-ACCESS read-only 
		STATUS current
		DESCRIPTION  "Full-cone Session NAT Pool Mismatch" 
		::={ acosCgnv6Nat64GlobalS 225 } 

		sixRdNoMatchDomainDrop OBJECT-TYPE
		SYNTAX  CounterBasedGauge64 
		MAX-ACCESS read-only 
		STATUS current
		DESCRIPTION  "Sixrd Packets Domain Not Found" 
		::={ acosCgnv6Nat64GlobalS 226 } 

		haPrefixNotFound OBJECT-TYPE
		SYNTAX  CounterBasedGauge64 
		MAX-ACCESS read-only 
		STATUS current
		DESCRIPTION  "HA No Matching Prefix Found" 
		::={ acosCgnv6Nat64GlobalS 227 } 

		natPoolAttemptAddingMultipleFreeBatches OBJECT-TYPE
		SYNTAX  CounterBasedGauge64 
		MAX-ACCESS read-only 
		STATUS current
		DESCRIPTION  "Attempt Adding Multiple Free Batches to Quota" 
		::={ acosCgnv6Nat64GlobalS 228 } 

		natPoolAddFreeBatchFailed OBJECT-TYPE
		SYNTAX  CounterBasedGauge64 
		MAX-ACCESS read-only 
		STATUS current
		DESCRIPTION  "Add Batch to Quota Failed" 
		::={ acosCgnv6Nat64GlobalS 229 } 

		mgcpAlgNoQuota OBJECT-TYPE
		SYNTAX  CounterBasedGauge64 
		MAX-ACCESS read-only 
		STATUS current
		DESCRIPTION  "MGCP ALG User-Quota Not Found" 
		::={ acosCgnv6Nat64GlobalS 230 } 

		mgcpAlgQuotaIncFailure OBJECT-TYPE
		SYNTAX  CounterBasedGauge64 
		MAX-ACCESS read-only 
		STATUS current
		DESCRIPTION  "MGCP ALG User-Quota Exceeded" 
		::={ acosCgnv6Nat64GlobalS 231 } 

		mgcpAlgNoNatIp OBJECT-TYPE
		SYNTAX  CounterBasedGauge64 
		MAX-ACCESS read-only 
		STATUS current
		DESCRIPTION  "MGCP ALG Unknown NAT IP" 
		::={ acosCgnv6Nat64GlobalS 232 } 

		mgcpAlgReuseFullcone OBJECT-TYPE
		SYNTAX  CounterBasedGauge64 
		MAX-ACCESS read-only 
		STATUS current
		DESCRIPTION  "MGCP ALG Reuse Full-cone Session" 
		::={ acosCgnv6Nat64GlobalS 233 } 

		mgcpAlgFullconeMismatch OBJECT-TYPE
		SYNTAX  CounterBasedGauge64 
		MAX-ACCESS read-only 
		STATUS current
		DESCRIPTION  "MGCP ALG Full-cone Session Mismatch" 
		::={ acosCgnv6Nat64GlobalS 234 } 

		mgcpAlgAllocPortFailure OBJECT-TYPE
		SYNTAX  CounterBasedGauge64 
		MAX-ACCESS read-only 
		STATUS current
		DESCRIPTION  "MGCP ALG Alloc NAT Port Failure" 
		::={ acosCgnv6Nat64GlobalS 235 } 

		mgcpAlgCreateFullconeFailure OBJECT-TYPE
		SYNTAX  CounterBasedGauge64 
		MAX-ACCESS read-only 
		STATUS current
		DESCRIPTION  "MGCP ALG Create Full-cone Session Failure" 
		::={ acosCgnv6Nat64GlobalS 236 } 

		mgcpAlgReleasePortFailure OBJECT-TYPE
		SYNTAX  CounterBasedGauge64 
		MAX-ACCESS read-only 
		STATUS current
		DESCRIPTION  "MGCP ALG Release NAT Port Failure" 
		::={ acosCgnv6Nat64GlobalS 237 } 

		mgcpAlgSingleRtpFullcone OBJECT-TYPE
		SYNTAX  CounterBasedGauge64 
		MAX-ACCESS read-only 
		STATUS current
		DESCRIPTION  "MGCP ALG Single RTP Full-cone Found" 
		::={ acosCgnv6Nat64GlobalS 238 } 

		mgcpAlgSingleRtcpFullcone OBJECT-TYPE
		SYNTAX  CounterBasedGauge64 
		MAX-ACCESS read-only 
		STATUS current
		DESCRIPTION  "MGCP ALG Single RTCP Full-cone Found" 
		::={ acosCgnv6Nat64GlobalS 239 } 

		mgcpAlgRtcpFullconeMismatch OBJECT-TYPE
		SYNTAX  CounterBasedGauge64 
		MAX-ACCESS read-only 
		STATUS current
		DESCRIPTION  "MGCP ALG RTCP Full-cone NAT Port Mismatch" 
		::={ acosCgnv6Nat64GlobalS 240 } 

		mgcpAlgReuseRtpRtcpFullcone OBJECT-TYPE
		SYNTAX  CounterBasedGauge64 
		MAX-ACCESS read-only 
		STATUS current
		DESCRIPTION  "MGCP ALG Reuse RTP/RTCP Full-cone Session" 
		::={ acosCgnv6Nat64GlobalS 241 } 

		mgcpAlgAllocRtpRtcpPortFailure OBJECT-TYPE
		SYNTAX  CounterBasedGauge64 
		MAX-ACCESS read-only 
		STATUS current
		DESCRIPTION  "MGCP ALG Alloc RTP/RTCP NAT Ports Failure" 
		::={ acosCgnv6Nat64GlobalS 242 } 

		mgcpAlgAllocSinglePortFailure OBJECT-TYPE
		SYNTAX  CounterBasedGauge64 
		MAX-ACCESS read-only 
		STATUS current
		DESCRIPTION  "MGCP ALG Alloc Single RTP or RTCP NAT Port Failure" 
		::={ acosCgnv6Nat64GlobalS 243 } 

		mgcpAlgCreateSingleFullconeFailure OBJECT-TYPE
		SYNTAX  CounterBasedGauge64 
		MAX-ACCESS read-only 
		STATUS current
		DESCRIPTION  "MGCP ALG Create Single RTP or RTCP Full-cone Session Failure" 
		::={ acosCgnv6Nat64GlobalS 244 } 

		mgcpAlgCreateRtpFullconeFailure OBJECT-TYPE
		SYNTAX  CounterBasedGauge64 
		MAX-ACCESS read-only 
		STATUS current
		DESCRIPTION  "MGCP ALG Create RTP Full-cone Session Failure" 
		::={ acosCgnv6Nat64GlobalS 245 } 

		mgcpAlgCreateRtcpFullconeFailure OBJECT-TYPE
		SYNTAX  CounterBasedGauge64 
		MAX-ACCESS read-only 
		STATUS current
		DESCRIPTION  "MGCP ALG Create RTCP Full-cone Session Failure" 
		::={ acosCgnv6Nat64GlobalS 246 } 

		mgcpAlgPortPairAllocFromConsecutive OBJECT-TYPE
		SYNTAX  CounterBasedGauge64 
		MAX-ACCESS read-only 
		STATUS current
		DESCRIPTION  "MGCP ALG Port Pair Allocated From Consecutive" 
		::={ acosCgnv6Nat64GlobalS 247 } 

		mgcpAlgPortPairAllocFromPartition OBJECT-TYPE
		SYNTAX  CounterBasedGauge64 
		MAX-ACCESS read-only 
		STATUS current
		DESCRIPTION  "MGCP ALG Port Pair Allocated From Partition" 
		::={ acosCgnv6Nat64GlobalS 248 } 

		mgcpAlgPortPairAllocFromPoolPortBatch OBJECT-TYPE
		SYNTAX  CounterBasedGauge64 
		MAX-ACCESS read-only 
		STATUS current
		DESCRIPTION  "MGCP ALG Port Pair Allocated From Pool Port Batch" 
		::={ acosCgnv6Nat64GlobalS 249 } 

		mgcpAlgPortPairAllocFromQuotaConsecutive OBJECT-TYPE
		SYNTAX  CounterBasedGauge64 
		MAX-ACCESS read-only 
		STATUS current
		DESCRIPTION  "MGCP ALG Port Pair Allocated From Quota Consecutive" 
		::={ acosCgnv6Nat64GlobalS 250 } 

		mgcpAlgPortPairAllocFromQuotaPartition OBJECT-TYPE
		SYNTAX  CounterBasedGauge64 
		MAX-ACCESS read-only 
		STATUS current
		DESCRIPTION  "MGCP ALG Port Pair Allocated From Quota Partition" 
		::={ acosCgnv6Nat64GlobalS 251 } 

		mgcpAlgPortPairAllocFromQuotaPartitionError OBJECT-TYPE
		SYNTAX  CounterBasedGauge64 
		MAX-ACCESS read-only 
		STATUS current
		DESCRIPTION  "MGCP ALG Port Pair Allocated From Quota Partition Error" 
		::={ acosCgnv6Nat64GlobalS 252 } 

		mgcpAlgPortPairAllocFromQuotaPoolPortBatch OBJECT-TYPE
		SYNTAX  CounterBasedGauge64 
		MAX-ACCESS read-only 
		STATUS current
		DESCRIPTION  "MGCP ALG Port Pair Allocated From Quota Pool Port Batch" 
		::={ acosCgnv6Nat64GlobalS 253 } 

		userQuotaUnusableDrop OBJECT-TYPE
		SYNTAX  CounterBasedGauge64 
		MAX-ACCESS read-only 
		STATUS current
		DESCRIPTION  "User-Quota Unusable Drop" 
		::={ acosCgnv6Nat64GlobalS 254 } 

		userQuotaUnusable OBJECT-TYPE
		SYNTAX  CounterBasedGauge64 
		MAX-ACCESS read-only 
		STATUS current
		DESCRIPTION  "User-Quota Marked Unusable" 
		::={ acosCgnv6Nat64GlobalS 255 } 

		natPoolSamePortBatchUdpFailed OBJECT-TYPE
		SYNTAX  CounterBasedGauge64 
		MAX-ACCESS read-only 
		STATUS current
		DESCRIPTION  "Simultaneous Batch Allocation UDP Port Allocation Failed" 
		::={ acosCgnv6Nat64GlobalS 256 } 

		adcPortAllocationFailed OBJECT-TYPE
		SYNTAX  CounterBasedGauge64 
		MAX-ACCESS read-only 
		STATUS current
		DESCRIPTION  "ADC Port Allocation Failed" 
		::={ acosCgnv6Nat64GlobalS 257 } 

		adcPortAllocationIneligible OBJECT-TYPE
		SYNTAX  CounterBasedGauge64 
		MAX-ACCESS read-only 
		STATUS current
		DESCRIPTION  "ADC Port Allocation Not Allowed" 
		::={ acosCgnv6Nat64GlobalS 258 } 

		fwdIngressPacketsTcp OBJECT-TYPE
		SYNTAX  CounterBasedGauge64 
		MAX-ACCESS read-only 
		STATUS current
		DESCRIPTION  "Forward Ingress Packets TCP" 
		::={ acosCgnv6Nat64GlobalS 259 } 

		fwdEgressPacketsTcp OBJECT-TYPE
		SYNTAX  CounterBasedGauge64 
		MAX-ACCESS read-only 
		STATUS current
		DESCRIPTION  "Forward Egress Packets TCP" 
		::={ acosCgnv6Nat64GlobalS 260 } 

		revIngressPacketsTcp OBJECT-TYPE
		SYNTAX  CounterBasedGauge64 
		MAX-ACCESS read-only 
		STATUS current
		DESCRIPTION  "Reverse Ingress Packets TCP" 
		::={ acosCgnv6Nat64GlobalS 261 } 

		revEgressPacketsTcp OBJECT-TYPE
		SYNTAX  CounterBasedGauge64 
		MAX-ACCESS read-only 
		STATUS current
		DESCRIPTION  "Reverse Egress Packets TCP" 
		::={ acosCgnv6Nat64GlobalS 262 } 

		fwdIngressBytesTcp OBJECT-TYPE
		SYNTAX  CounterBasedGauge64 
		MAX-ACCESS read-only 
		STATUS current
		DESCRIPTION  "Forward Ingress Bytes TCP" 
		::={ acosCgnv6Nat64GlobalS 263 } 

		fwdEgressBytesTcp OBJECT-TYPE
		SYNTAX  CounterBasedGauge64 
		MAX-ACCESS read-only 
		STATUS current
		DESCRIPTION  "Forward Egress Bytes TCP" 
		::={ acosCgnv6Nat64GlobalS 264 } 

		revIngressBytesTcp OBJECT-TYPE
		SYNTAX  CounterBasedGauge64 
		MAX-ACCESS read-only 
		STATUS current
		DESCRIPTION  "Reverse Ingress Bytes TCP" 
		::={ acosCgnv6Nat64GlobalS 265 } 

		revEgressBytesTcp OBJECT-TYPE
		SYNTAX  CounterBasedGauge64 
		MAX-ACCESS read-only 
		STATUS current
		DESCRIPTION  "Reverse Egress Bytes TCP" 
		::={ acosCgnv6Nat64GlobalS 266 } 

		fwdIngressPacketsUdp OBJECT-TYPE
		SYNTAX  CounterBasedGauge64 
		MAX-ACCESS read-only 
		STATUS current
		DESCRIPTION  "Forward Ingress Packets UDP" 
		::={ acosCgnv6Nat64GlobalS 267 } 

		fwdEgressPacketsUdp OBJECT-TYPE
		SYNTAX  CounterBasedGauge64 
		MAX-ACCESS read-only 
		STATUS current
		DESCRIPTION  "Forward Egress Packets UDP" 
		::={ acosCgnv6Nat64GlobalS 268 } 

		revIngressPacketsUdp OBJECT-TYPE
		SYNTAX  CounterBasedGauge64 
		MAX-ACCESS read-only 
		STATUS current
		DESCRIPTION  "Reverse Ingress Packets UDP" 
		::={ acosCgnv6Nat64GlobalS 269 } 

		revEgressPacketsUdp OBJECT-TYPE
		SYNTAX  CounterBasedGauge64 
		MAX-ACCESS read-only 
		STATUS current
		DESCRIPTION  "Reverse Egress Packets UDP" 
		::={ acosCgnv6Nat64GlobalS 270 } 

		fwdIngressBytesUdp OBJECT-TYPE
		SYNTAX  CounterBasedGauge64 
		MAX-ACCESS read-only 
		STATUS current
		DESCRIPTION  "Forward Ingress Bytes UDP" 
		::={ acosCgnv6Nat64GlobalS 271 } 

		fwdEgressBytesUdp OBJECT-TYPE
		SYNTAX  CounterBasedGauge64 
		MAX-ACCESS read-only 
		STATUS current
		DESCRIPTION  "Forward Egress Bytes UDP" 
		::={ acosCgnv6Nat64GlobalS 272 } 

		revIngressBytesUdp OBJECT-TYPE
		SYNTAX  CounterBasedGauge64 
		MAX-ACCESS read-only 
		STATUS current
		DESCRIPTION  "Reverse Ingress Bytes UDP" 
		::={ acosCgnv6Nat64GlobalS 273 } 

		revEgressBytesUdp OBJECT-TYPE
		SYNTAX  CounterBasedGauge64 
		MAX-ACCESS read-only 
		STATUS current
		DESCRIPTION  "Reverse Egress Bytes UDP" 
		::={ acosCgnv6Nat64GlobalS 274 } 

		fwdIngressPacketsIcmp OBJECT-TYPE
		SYNTAX  CounterBasedGauge64 
		MAX-ACCESS read-only 
		STATUS current
		DESCRIPTION  "Forward Ingress Packets ICMP" 
		::={ acosCgnv6Nat64GlobalS 275 } 

		fwdEgressPacketsIcmp OBJECT-TYPE
		SYNTAX  CounterBasedGauge64 
		MAX-ACCESS read-only 
		STATUS current
		DESCRIPTION  "Forward Egress Packets ICMP" 
		::={ acosCgnv6Nat64GlobalS 276 } 

		revIngressPacketsIcmp OBJECT-TYPE
		SYNTAX  CounterBasedGauge64 
		MAX-ACCESS read-only 
		STATUS current
		DESCRIPTION  "Reverse Ingress Packets ICMP" 
		::={ acosCgnv6Nat64GlobalS 277 } 

		revEgressPacketsIcmp OBJECT-TYPE
		SYNTAX  CounterBasedGauge64 
		MAX-ACCESS read-only 
		STATUS current
		DESCRIPTION  "Reverse Egress Packets ICMP" 
		::={ acosCgnv6Nat64GlobalS 278 } 

		fwdIngressBytesIcmp OBJECT-TYPE
		SYNTAX  CounterBasedGauge64 
		MAX-ACCESS read-only 
		STATUS current
		DESCRIPTION  "Forward Ingress Bytes ICMP" 
		::={ acosCgnv6Nat64GlobalS 279 } 

		fwdEgressBytesIcmp OBJECT-TYPE
		SYNTAX  CounterBasedGauge64 
		MAX-ACCESS read-only 
		STATUS current
		DESCRIPTION  "Forward Egress Bytes ICMP" 
		::={ acosCgnv6Nat64GlobalS 280 } 

		revIngressBytesIcmp OBJECT-TYPE
		SYNTAX  CounterBasedGauge64 
		MAX-ACCESS read-only 
		STATUS current
		DESCRIPTION  "Reverse Ingress Bytes ICMP" 
		::={ acosCgnv6Nat64GlobalS 281 } 

		revEgressBytesIcmp OBJECT-TYPE
		SYNTAX  CounterBasedGauge64 
		MAX-ACCESS read-only 
		STATUS current
		DESCRIPTION  "Reverse Egress Bytes ICMP" 
		::={ acosCgnv6Nat64GlobalS 282 } 

		fwdIngressPacketsOthers OBJECT-TYPE
		SYNTAX  CounterBasedGauge64 
		MAX-ACCESS read-only 
		STATUS current
		DESCRIPTION  "Forward Ingress Packets OTHERS" 
		::={ acosCgnv6Nat64GlobalS 283 } 

		fwdEgressPacketsOthers OBJECT-TYPE
		SYNTAX  CounterBasedGauge64 
		MAX-ACCESS read-only 
		STATUS current
		DESCRIPTION  "Forward Egress Packets OTHERS" 
		::={ acosCgnv6Nat64GlobalS 284 } 

		revIngressPacketsOthers OBJECT-TYPE
		SYNTAX  CounterBasedGauge64 
		MAX-ACCESS read-only 
		STATUS current
		DESCRIPTION  "Reverse Ingress Packets OTHERS" 
		::={ acosCgnv6Nat64GlobalS 285 } 

		revEgressPacketsOthers OBJECT-TYPE
		SYNTAX  CounterBasedGauge64 
		MAX-ACCESS read-only 
		STATUS current
		DESCRIPTION  "Reverse Egress Packets OTHERS" 
		::={ acosCgnv6Nat64GlobalS 286 } 

		fwdIngressBytesOthers OBJECT-TYPE
		SYNTAX  CounterBasedGauge64 
		MAX-ACCESS read-only 
		STATUS current
		DESCRIPTION  "Forward Ingress Bytes OTHERS" 
		::={ acosCgnv6Nat64GlobalS 287 } 

		fwdEgressBytesOthers OBJECT-TYPE
		SYNTAX  CounterBasedGauge64 
		MAX-ACCESS read-only 
		STATUS current
		DESCRIPTION  "Forward Egress Bytes OTHERS" 
		::={ acosCgnv6Nat64GlobalS 288 } 

		revIngressBytesOthers OBJECT-TYPE
		SYNTAX  CounterBasedGauge64 
		MAX-ACCESS read-only 
		STATUS current
		DESCRIPTION  "Reverse Ingress Bytes OTHERS" 
		::={ acosCgnv6Nat64GlobalS 289 } 

		revEgressBytesOthers OBJECT-TYPE
		SYNTAX  CounterBasedGauge64 
		MAX-ACCESS read-only 
		STATUS current
		DESCRIPTION  "Reverse Egress Bytes OTHERS" 
		::={ acosCgnv6Nat64GlobalS 290 } 

		fwdIngressPktSizeRange1 OBJECT-TYPE
		SYNTAX  CounterBasedGauge64 
		MAX-ACCESS read-only 
		STATUS current
		DESCRIPTION  "Forward Ingress Packet size between 0 and 200" 
		::={ acosCgnv6Nat64GlobalS 291 } 

		fwdIngressPktSizeRange2 OBJECT-TYPE
		SYNTAX  CounterBasedGauge64 
		MAX-ACCESS read-only 
		STATUS current
		DESCRIPTION  "Forward Ingress Packet size between 201 and 800" 
		::={ acosCgnv6Nat64GlobalS 292 } 

		fwdIngressPktSizeRange3 OBJECT-TYPE
		SYNTAX  CounterBasedGauge64 
		MAX-ACCESS read-only 
		STATUS current
		DESCRIPTION  "Forward Ingress Packet size between 801 and 1550" 
		::={ acosCgnv6Nat64GlobalS 293 } 

		fwdIngressPktSizeRange4 OBJECT-TYPE
		SYNTAX  CounterBasedGauge64 
		MAX-ACCESS read-only 
		STATUS current
		DESCRIPTION  "Forward Ingress Packet size between 1551 and 9000" 
		::={ acosCgnv6Nat64GlobalS 294 } 

		fwdEgressPktSizeRange1 OBJECT-TYPE
		SYNTAX  CounterBasedGauge64 
		MAX-ACCESS read-only 
		STATUS current
		DESCRIPTION  "Forward Egress Packet size between 0 and 200" 
		::={ acosCgnv6Nat64GlobalS 295 } 

		fwdEgressPktSizeRange2 OBJECT-TYPE
		SYNTAX  CounterBasedGauge64 
		MAX-ACCESS read-only 
		STATUS current
		DESCRIPTION  "Forward Egress Packet size between 201 and 800" 
		::={ acosCgnv6Nat64GlobalS 296 } 

		fwdEgressPktSizeRange3 OBJECT-TYPE
		SYNTAX  CounterBasedGauge64 
		MAX-ACCESS read-only 
		STATUS current
		DESCRIPTION  "Forward Egress Packet size between 801 and 1550" 
		::={ acosCgnv6Nat64GlobalS 297 } 

		fwdEgressPktSizeRange4 OBJECT-TYPE
		SYNTAX  CounterBasedGauge64 
		MAX-ACCESS read-only 
		STATUS current
		DESCRIPTION  "Forward Egress Packet size between 1551 and 9000" 
		::={ acosCgnv6Nat64GlobalS 298 } 

		revIngressPktSizeRange1 OBJECT-TYPE
		SYNTAX  CounterBasedGauge64 
		MAX-ACCESS read-only 
		STATUS current
		DESCRIPTION  "Reverse Ingress Packet size between 0 and 200" 
		::={ acosCgnv6Nat64GlobalS 299 } 

		revIngressPktSizeRange2 OBJECT-TYPE
		SYNTAX  CounterBasedGauge64 
		MAX-ACCESS read-only 
		STATUS current
		DESCRIPTION  "Reverse Ingress Packet size between 201 and 800" 
		::={ acosCgnv6Nat64GlobalS 300 } 

		revIngressPktSizeRange3 OBJECT-TYPE
		SYNTAX  CounterBasedGauge64 
		MAX-ACCESS read-only 
		STATUS current
		DESCRIPTION  "Reverse Ingress Packet size between 801 and 1550" 
		::={ acosCgnv6Nat64GlobalS 301 } 

		revIngressPktSizeRange4 OBJECT-TYPE
		SYNTAX  CounterBasedGauge64 
		MAX-ACCESS read-only 
		STATUS current
		DESCRIPTION  "Reverse Ingress Packet size between 1551 and 9000" 
		::={ acosCgnv6Nat64GlobalS 302 } 

		revEgressPktSizeRange1 OBJECT-TYPE
		SYNTAX  CounterBasedGauge64 
		MAX-ACCESS read-only 
		STATUS current
		DESCRIPTION  "Reverse Egress Packet size between 0 and 200" 
		::={ acosCgnv6Nat64GlobalS 303 } 

		revEgressPktSizeRange2 OBJECT-TYPE
		SYNTAX  CounterBasedGauge64 
		MAX-ACCESS read-only 
		STATUS current
		DESCRIPTION  "Reverse Egress Packet size between 201 and 800" 
		::={ acosCgnv6Nat64GlobalS 304 } 

		revEgressPktSizeRange3 OBJECT-TYPE
		SYNTAX  CounterBasedGauge64 
		MAX-ACCESS read-only 
		STATUS current
		DESCRIPTION  "Reverse Egress Packet size between 801 and 1550" 
		::={ acosCgnv6Nat64GlobalS 305 } 

		revEgressPktSizeRange4 OBJECT-TYPE
		SYNTAX  CounterBasedGauge64 
		MAX-ACCESS read-only 
		STATUS current
		DESCRIPTION  "Reverse Egress Packet size between 1551 and 9000" 
		::={ acosCgnv6Nat64GlobalS 306 } 

		prefixQuotaMismatch OBJECT-TYPE
		SYNTAX  CounterBasedGauge64 
		MAX-ACCESS read-only 
		STATUS current
		DESCRIPTION  "Prefix Quota NAT IP Mismatch" 
		::={ acosCgnv6Nat64GlobalS 307 } 

acosCgnv6Nat64Alg                   OBJECT IDENTIFIER ::= { acosCgnv6Nat64 2 }
acosCgnv6Nat64AlgEsp                OBJECT IDENTIFIER ::= { acosCgnv6Nat64Alg 1 }
acosCgnv6Nat64AlgEspS               OBJECT IDENTIFIER ::= { acosCgnv6Nat64AlgEsp 1 }

		sessionCreated OBJECT-TYPE
		SYNTAX  CounterBasedGauge64 
		MAX-ACCESS read-only 
		STATUS current
		DESCRIPTION  "ESP Sessions Created" 
		::={ acosCgnv6Nat64AlgEspS 1 } 

		natIpConflict OBJECT-TYPE
		SYNTAX  CounterBasedGauge64 
		MAX-ACCESS read-only 
		STATUS current
		DESCRIPTION  "NAT IP Conflict" 
		::={ acosCgnv6Nat64AlgEspS 2 } 

acosCgnv6DsLite                     OBJECT IDENTIFIER ::= { acosCgnv6 19 }
acosCgnv6DsLiteGlobal               OBJECT IDENTIFIER ::= { acosCgnv6DsLite 1 }
acosCgnv6DsLiteGlobalS              OBJECT IDENTIFIER ::= { acosCgnv6DsLiteGlobal 1 }

		cgnv6DsliteGlobalTotalTcpAllocated OBJECT-TYPE
		SYNTAX  CounterBasedGauge64 
		MAX-ACCESS read-only 
		STATUS current
		DESCRIPTION  "Total TCP Ports Allocated" 
		::={ acosCgnv6DsLiteGlobalS 1 } 

		cgnv6DsliteGlobalTotalTcpFreed OBJECT-TYPE
		SYNTAX  CounterBasedGauge64 
		MAX-ACCESS read-only 
		STATUS current
		DESCRIPTION  "Total TCP Ports Freed" 
		::={ acosCgnv6DsLiteGlobalS 2 } 

		cgnv6DsliteGlobalTotalUdpAllocated OBJECT-TYPE
		SYNTAX  CounterBasedGauge64 
		MAX-ACCESS read-only 
		STATUS current
		DESCRIPTION  "Total UDP Ports Allocated" 
		::={ acosCgnv6DsLiteGlobalS 3 } 

		cgnv6DsliteGlobalTotalUdpFreed OBJECT-TYPE
		SYNTAX  CounterBasedGauge64 
		MAX-ACCESS read-only 
		STATUS current
		DESCRIPTION  "Total UDP Ports Freed" 
		::={ acosCgnv6DsLiteGlobalS 4 } 

		cgnv6DsliteGlobalTotalIcmpAllocated OBJECT-TYPE
		SYNTAX  CounterBasedGauge64 
		MAX-ACCESS read-only 
		STATUS current
		DESCRIPTION  "Total ICMP Ports Allocated" 
		::={ acosCgnv6DsLiteGlobalS 5 } 

		cgnv6DsliteGlobalTotalIcmpFreed OBJECT-TYPE
		SYNTAX  CounterBasedGauge64 
		MAX-ACCESS read-only 
		STATUS current
		DESCRIPTION  "Total ICMP Ports Freed" 
		::={ acosCgnv6DsLiteGlobalS 6 } 

		cgnv6DsliteGlobalDataSessionCreated OBJECT-TYPE
		SYNTAX  CounterBasedGauge64 
		MAX-ACCESS read-only 
		STATUS current
		DESCRIPTION  "Data Session Created" 
		::={ acosCgnv6DsLiteGlobalS 7 } 

		cgnv6DsliteGlobalDataSessionFreed OBJECT-TYPE
		SYNTAX  CounterBasedGauge64 
		MAX-ACCESS read-only 
		STATUS current
		DESCRIPTION  "Data Session Freed" 
		::={ acosCgnv6DsLiteGlobalS 8 } 

		cgnv6DsliteGlobalUserQuotaCreated OBJECT-TYPE
		SYNTAX  CounterBasedGauge64 
		MAX-ACCESS read-only 
		STATUS current
		DESCRIPTION  "User-Quota Created" 
		::={ acosCgnv6DsLiteGlobalS 9 } 

		cgnv6DsliteGlobalTotalUserQuotaPuInDelQ OBJECT-TYPE
		SYNTAX  CounterBasedGauge64 
		MAX-ACCESS read-only 
		STATUS current
		DESCRIPTION  "User-Quota Freed" 
		::={ acosCgnv6DsLiteGlobalS 10 } 

		cgnv6DsliteGlobalUserQuotaFailure OBJECT-TYPE
		SYNTAX  CounterBasedGauge64 
		MAX-ACCESS read-only 
		STATUS current
		DESCRIPTION  "User-Quota Creation Failed" 
		::={ acosCgnv6DsLiteGlobalS 11 } 

		cgnv6DsliteGlobalNatPortUnavailableTcp OBJECT-TYPE
		SYNTAX  CounterBasedGauge64 
		MAX-ACCESS read-only 
		STATUS current
		DESCRIPTION  "TCP NAT Port Unavailable" 
		::={ acosCgnv6DsLiteGlobalS 12 } 

		cgnv6DsliteGlobalNatPortUnavailableUdp OBJECT-TYPE
		SYNTAX  CounterBasedGauge64 
		MAX-ACCESS read-only 
		STATUS current
		DESCRIPTION  "UDP NAT Port Unavailable" 
		::={ acosCgnv6DsLiteGlobalS 13 } 

		cgnv6DsliteGlobalNatPortUnavailableIcmp OBJECT-TYPE
		SYNTAX  CounterBasedGauge64 
		MAX-ACCESS read-only 
		STATUS current
		DESCRIPTION  "ICMP NAT Port Unavailable" 
		::={ acosCgnv6DsLiteGlobalS 14 } 

		cgnv6DsliteGlobalNewUserResourceUnavailable OBJECT-TYPE
		SYNTAX  CounterBasedGauge64 
		MAX-ACCESS read-only 
		STATUS current
		DESCRIPTION  "New User NAT Resource Unavailable" 
		::={ acosCgnv6DsLiteGlobalS 15 } 

		cgnv6DsliteGlobalTcpUserQuotaExceeded OBJECT-TYPE
		SYNTAX  CounterBasedGauge64 
		MAX-ACCESS read-only 
		STATUS current
		DESCRIPTION  "TCP User-Quota Exceeded" 
		::={ acosCgnv6DsLiteGlobalS 16 } 

		cgnv6DsliteGlobalUdpUserQuotaExceeded OBJECT-TYPE
		SYNTAX  CounterBasedGauge64 
		MAX-ACCESS read-only 
		STATUS current
		DESCRIPTION  "UDP User-Quota Exceeded" 
		::={ acosCgnv6DsLiteGlobalS 17 } 

		cgnv6DsliteGlobalIcmpUserQuotaExceeded OBJECT-TYPE
		SYNTAX  CounterBasedGauge64 
		MAX-ACCESS read-only 
		STATUS current
		DESCRIPTION  "ICMP User-Quota Exceeded" 
		::={ acosCgnv6DsLiteGlobalS 18 } 

		cgnv6DsliteGlobalExtendedQuotaMatched OBJECT-TYPE
		SYNTAX  CounterBasedGauge64 
		MAX-ACCESS read-only 
		STATUS current
		DESCRIPTION  "Extended User-Quota Matched" 
		::={ acosCgnv6DsLiteGlobalS 19 } 

		cgnv6DsliteGlobalExtendedQuotaExceeded OBJECT-TYPE
		SYNTAX  CounterBasedGauge64 
		MAX-ACCESS read-only 
		STATUS current
		DESCRIPTION  "Extended User-Quota Exceeded" 
		::={ acosCgnv6DsLiteGlobalS 20 } 

		cgnv6DsliteGlobalDataSesnUserQuotaExceeded OBJECT-TYPE
		SYNTAX  CounterBasedGauge64 
		MAX-ACCESS read-only 
		STATUS current
		DESCRIPTION  "Data Session User-Quota Exceeded" 
		::={ acosCgnv6DsLiteGlobalS 21 } 

		cgnv6DsliteGlobalDataSesnRateUserQuotaExceeded OBJECT-TYPE
		SYNTAX  CounterBasedGauge64 
		MAX-ACCESS read-only 
		STATUS current
		DESCRIPTION  "Conn Rate User-Quota Exceeded" 
		::={ acosCgnv6DsLiteGlobalS 22 } 

		cgnv6DsliteGlobalTcpFullconeCreated OBJECT-TYPE
		SYNTAX  CounterBasedGauge64 
		MAX-ACCESS read-only 
		STATUS current
		DESCRIPTION  "TCP Full-cone Session Created" 
		::={ acosCgnv6DsLiteGlobalS 23 } 

		cgnv6DsliteGlobalTcpFullconeFreed OBJECT-TYPE
		SYNTAX  CounterBasedGauge64 
		MAX-ACCESS read-only 
		STATUS current
		DESCRIPTION  "TCP Full-cone Session Freed" 
		::={ acosCgnv6DsLiteGlobalS 24 } 

		cgnv6DsliteGlobalUdpFullconeCreated OBJECT-TYPE
		SYNTAX  CounterBasedGauge64 
		MAX-ACCESS read-only 
		STATUS current
		DESCRIPTION  "UDP Full-cone Session Created" 
		::={ acosCgnv6DsLiteGlobalS 25 } 

		cgnv6DsliteGlobalUdpFullconeFreed OBJECT-TYPE
		SYNTAX  CounterBasedGauge64 
		MAX-ACCESS read-only 
		STATUS current
		DESCRIPTION  "UDP Full-cone Session Freed" 
		::={ acosCgnv6DsLiteGlobalS 26 } 

		cgnv6DsliteGlobalFullconeFailure OBJECT-TYPE
		SYNTAX  CounterBasedGauge64 
		MAX-ACCESS read-only 
		STATUS current
		DESCRIPTION  "Full-cone Session Creation Failed" 
		::={ acosCgnv6DsLiteGlobalS 27 } 

		cgnv6DsliteGlobalHairpin OBJECT-TYPE
		SYNTAX  CounterBasedGauge64 
		MAX-ACCESS read-only 
		STATUS current
		DESCRIPTION  "Hairpin Session Created" 
		::={ acosCgnv6DsLiteGlobalS 28 } 

		cgnv6DsliteGlobalFullconeSelfHairpinningDrop OBJECT-TYPE
		SYNTAX  CounterBasedGauge64 
		MAX-ACCESS read-only 
		STATUS current
		DESCRIPTION  "Self-Hairpinning Drop" 
		::={ acosCgnv6DsLiteGlobalS 29 } 

		cgnv6DsliteGlobalEndpointIndepMapMatch OBJECT-TYPE
		SYNTAX  CounterBasedGauge64 
		MAX-ACCESS read-only 
		STATUS current
		DESCRIPTION  "Endpoint-Independent Mapping Matched" 
		::={ acosCgnv6DsLiteGlobalS 30 } 

		cgnv6DsliteGlobalEndpointIndepFilterMatch OBJECT-TYPE
		SYNTAX  CounterBasedGauge64 
		MAX-ACCESS read-only 
		STATUS current
		DESCRIPTION  "Endpoint-Independent Filtering Matched" 
		::={ acosCgnv6DsLiteGlobalS 31 } 

		cgnv6DsliteGlobalInboundFiltered OBJECT-TYPE
		SYNTAX  CounterBasedGauge64 
		MAX-ACCESS read-only 
		STATUS current
		DESCRIPTION  "Endpoint-Dependent Filtering Drop" 
		::={ acosCgnv6DsLiteGlobalS 32 } 

		cgnv6DsliteGlobalEifLimitExceeded OBJECT-TYPE
		SYNTAX  CounterBasedGauge64 
		MAX-ACCESS read-only 
		STATUS current
		DESCRIPTION  "Endpoint-Independent Filtering Inbound Limit Exceeded" 
		::={ acosCgnv6DsLiteGlobalS 33 } 

		cgnv6DsliteGlobalTotalTcpOverloaded OBJECT-TYPE
		SYNTAX  CounterBasedGauge64 
		MAX-ACCESS read-only 
		STATUS current
		DESCRIPTION  "TCP Port Overloaded" 
		::={ acosCgnv6DsLiteGlobalS 35 } 

		cgnv6DsliteGlobalTotalUdpOverloaded OBJECT-TYPE
		SYNTAX  CounterBasedGauge64 
		MAX-ACCESS read-only 
		STATUS current
		DESCRIPTION  "UDP Port Overloaded" 
		::={ acosCgnv6DsLiteGlobalS 36 } 

		cgnv6DsliteGlobalPortOverloadingSmpInsertedTcp OBJECT-TYPE
		SYNTAX  CounterBasedGauge64 
		MAX-ACCESS read-only 
		STATUS current
		DESCRIPTION  "TCP Port Overloading Session Created" 
		::={ acosCgnv6DsLiteGlobalS 37 } 

		cgnv6DsliteGlobalPortOverloadingSmpInsertedUdp OBJECT-TYPE
		SYNTAX  CounterBasedGauge64 
		MAX-ACCESS read-only 
		STATUS current
		DESCRIPTION  "UDP Port Overloading Session Created" 
		::={ acosCgnv6DsLiteGlobalS 38 } 

		cgnv6DsliteGlobalPortOverloadingSmpFreeTcp OBJECT-TYPE
		SYNTAX  CounterBasedGauge64 
		MAX-ACCESS read-only 
		STATUS current
		DESCRIPTION  "TCP Port Overloading Session Freed" 
		::={ acosCgnv6DsLiteGlobalS 39 } 

		cgnv6DsliteGlobalPortOverloadingSmpFreeUdp OBJECT-TYPE
		SYNTAX  CounterBasedGauge64 
		MAX-ACCESS read-only 
		STATUS current
		DESCRIPTION  "UDP Port Overloading Session Freed" 
		::={ acosCgnv6DsLiteGlobalS 40 } 

		cgnv6DsliteGlobalNatPoolUnusable OBJECT-TYPE
		SYNTAX  CounterBasedGauge64 
		MAX-ACCESS read-only 
		STATUS current
		DESCRIPTION  "NAT Pool Unusable" 
		::={ acosCgnv6DsLiteGlobalS 41 } 

		cgnv6DsliteGlobalHaNatPoolUnusable OBJECT-TYPE
		SYNTAX  CounterBasedGauge64 
		MAX-ACCESS read-only 
		STATUS current
		DESCRIPTION  "HA NAT Pool Unusable" 
		::={ acosCgnv6DsLiteGlobalS 42 } 

		haNatPoolBatchTypeMismatch OBJECT-TYPE
		SYNTAX  CounterBasedGauge64 
		MAX-ACCESS read-only 
		STATUS current
		DESCRIPTION  "HA NAT Pool Batch Type Mismatch" 
		::={ acosCgnv6DsLiteGlobalS 43 } 

		noRadiusProfileMatch OBJECT-TYPE
		SYNTAX  CounterBasedGauge64 
		MAX-ACCESS read-only 
		STATUS current
		DESCRIPTION  "No RADIUS Profile Match" 
		::={ acosCgnv6DsLiteGlobalS 44 } 

		truncatedPacket OBJECT-TYPE
		SYNTAX  CounterBasedGauge64 
		MAX-ACCESS read-only 
		STATUS current
		DESCRIPTION  "Truncated Packet" 
		::={ acosCgnv6DsLiteGlobalS 45 } 

		lidDrop OBJECT-TYPE
		SYNTAX  CounterBasedGauge64 
		MAX-ACCESS read-only 
		STATUS current
		DESCRIPTION  "LSN LID Drop" 
		::={ acosCgnv6DsLiteGlobalS 46 } 

		lidPassThrough OBJECT-TYPE
		SYNTAX  CounterBasedGauge64 
		MAX-ACCESS read-only 
		STATUS current
		DESCRIPTION  "LSN LID Pass-through" 
		::={ acosCgnv6DsLiteGlobalS 47 } 

		noClassListMatch OBJECT-TYPE
		SYNTAX  CounterBasedGauge64 
		MAX-ACCESS read-only 
		STATUS current
		DESCRIPTION  "No Class-List Match" 
		::={ acosCgnv6DsLiteGlobalS 48 } 

		classListPermitDrop OBJECT-TYPE
		SYNTAX  CounterBasedGauge64 
		MAX-ACCESS read-only 
		STATUS current
		DESCRIPTION  "Permit Class-List Drop" 
		::={ acosCgnv6DsLiteGlobalS 49 } 

		userQuotaMemAllocated OBJECT-TYPE
		SYNTAX  CounterBasedGauge64 
		MAX-ACCESS read-only 
		STATUS current
		DESCRIPTION  "User-Quota Memory Allocated" 
		::={ acosCgnv6DsLiteGlobalS 50 } 

		userQuotaMemFreed OBJECT-TYPE
		SYNTAX  CounterBasedGauge64 
		MAX-ACCESS read-only 
		STATUS current
		DESCRIPTION  "User-Quota Memory Freed" 
		::={ acosCgnv6DsLiteGlobalS 51 } 

		userQuotaCreatedShadow OBJECT-TYPE
		SYNTAX  CounterBasedGauge64 
		MAX-ACCESS read-only 
		STATUS current
		DESCRIPTION  "Total User-Quota Created" 
		::={ acosCgnv6DsLiteGlobalS 52 } 

		quotaMarkedDeleted OBJECT-TYPE
		SYNTAX  CounterBasedGauge64 
		MAX-ACCESS read-only 
		STATUS current
		DESCRIPTION  "User-Quota Marked Deleted" 
		::={ acosCgnv6DsLiteGlobalS 53 } 

		quotaDeleteNotInBucket OBJECT-TYPE
		SYNTAX  CounterBasedGauge64 
		MAX-ACCESS read-only 
		STATUS current
		DESCRIPTION  "User-Quota Delete Not In Bucket" 
		::={ acosCgnv6DsLiteGlobalS 54 } 

		userQuotaPutInDelQShadow OBJECT-TYPE
		SYNTAX  CounterBasedGauge64 
		MAX-ACCESS read-only 
		STATUS current
		DESCRIPTION  "Total User-Quota Put In Del Q" 
		::={ acosCgnv6DsLiteGlobalS 55 } 

		prefixQuotaCreated OBJECT-TYPE
		SYNTAX  CounterBasedGauge64 
		MAX-ACCESS read-only 
		STATUS current
		DESCRIPTION  "Total Prefix Quota Created" 
		::={ acosCgnv6DsLiteGlobalS 56 } 

		prefixQuotaPutInDelQ OBJECT-TYPE
		SYNTAX  CounterBasedGauge64 
		MAX-ACCESS read-only 
		STATUS current
		DESCRIPTION  "Total Prefix Quota Freed" 
		::={ acosCgnv6DsLiteGlobalS 57 } 

		prefixQuotaFailure OBJECT-TYPE
		SYNTAX  CounterBasedGauge64 
		MAX-ACCESS read-only 
		STATUS current
		DESCRIPTION  "Total Prefix Quota Failure" 
		::={ acosCgnv6DsLiteGlobalS 58 } 

		totalUserQuotaCreated OBJECT-TYPE
		SYNTAX  CounterBasedGauge64 
		MAX-ACCESS read-only 
		STATUS current
		DESCRIPTION  "Total Quota Structure Created" 
		::={ acosCgnv6DsLiteGlobalS 59 } 

		totalUserQuotaPutInDelQ OBJECT-TYPE
		SYNTAX  CounterBasedGauge64 
		MAX-ACCESS read-only 
		STATUS current
		DESCRIPTION  "Total Quota Structure Freed" 
		::={ acosCgnv6DsLiteGlobalS 60 } 

		totalUserQuotaFailure OBJECT-TYPE
		SYNTAX  CounterBasedGauge64 
		MAX-ACCESS read-only 
		STATUS current
		DESCRIPTION  "Total Quota Structure Failure" 
		::={ acosCgnv6DsLiteGlobalS 61 } 

		tcpOutOfStateRstSent OBJECT-TYPE
		SYNTAX  CounterBasedGauge64 
		MAX-ACCESS read-only 
		STATUS current
		DESCRIPTION  "Total Out of State TCP RST sent" 
		::={ acosCgnv6DsLiteGlobalS 62 } 

		tcpOutOfStateRstDropped OBJECT-TYPE
		SYNTAX  CounterBasedGauge64 
		MAX-ACCESS read-only 
		STATUS current
		DESCRIPTION  "Total Out of State TCP RST dropped" 
		::={ acosCgnv6DsLiteGlobalS 63 } 

		icmpOutOfStateUqeAdminFilteredSent OBJECT-TYPE
		SYNTAX  CounterBasedGauge64 
		MAX-ACCESS read-only 
		STATUS current
		DESCRIPTION  "Total User Quota Exceeded ICMP admin filtered sent" 
		::={ acosCgnv6DsLiteGlobalS 64 } 

		icmpOutOfStateUqeHostUnreachableSent OBJECT-TYPE
		SYNTAX  CounterBasedGauge64 
		MAX-ACCESS read-only 
		STATUS current
		DESCRIPTION  "Total User Quota Exceeded ICMP host unreachable sent" 
		::={ acosCgnv6DsLiteGlobalS 65 } 

		icmpOutOfStateUqeDropped OBJECT-TYPE
		SYNTAX  CounterBasedGauge64 
		MAX-ACCESS read-only 
		STATUS current
		DESCRIPTION  "Total User Queue Exceeded ICMP notification dropped" 
		::={ acosCgnv6DsLiteGlobalS 66 } 

		userQuotaNotFound OBJECT-TYPE
		SYNTAX  CounterBasedGauge64 
		MAX-ACCESS read-only 
		STATUS current
		DESCRIPTION  "User-Quota Not Found" 
		::={ acosCgnv6DsLiteGlobalS 67 } 

		tcpFullconeCreatedShadow OBJECT-TYPE
		SYNTAX  CounterBasedGauge64 
		MAX-ACCESS read-only 
		STATUS current
		DESCRIPTION  "Total TCP Full-cone sessions created" 
		::={ acosCgnv6DsLiteGlobalS 68 } 

		tcpFullconeFreedShadow OBJECT-TYPE
		SYNTAX  CounterBasedGauge64 
		MAX-ACCESS read-only 
		STATUS current
		DESCRIPTION  "Total TCP Full-cone sessions freed" 
		::={ acosCgnv6DsLiteGlobalS 69 } 

		udpFullconeCreatedShadow OBJECT-TYPE
		SYNTAX  CounterBasedGauge64 
		MAX-ACCESS read-only 
		STATUS current
		DESCRIPTION  "Total UDP Full-cone sessions created" 
		::={ acosCgnv6DsLiteGlobalS 70 } 

		udpFullconeFreedShadow OBJECT-TYPE
		SYNTAX  CounterBasedGauge64 
		MAX-ACCESS read-only 
		STATUS current
		DESCRIPTION  "Total UDP Full-cone sessions freed" 
		::={ acosCgnv6DsLiteGlobalS 71 } 

		udpAlgFullconeCreated OBJECT-TYPE
		SYNTAX  CounterBasedGauge64 
		MAX-ACCESS read-only 
		STATUS current
		DESCRIPTION  "Total UDP ALG Full-cone sessions created" 
		::={ acosCgnv6DsLiteGlobalS 72 } 

		udpAlgFullconeFreed OBJECT-TYPE
		SYNTAX  CounterBasedGauge64 
		MAX-ACCESS read-only 
		STATUS current
		DESCRIPTION  "Total UDP ALG Full-cone sessions freed" 
		::={ acosCgnv6DsLiteGlobalS 73 } 

		fullconeCreated OBJECT-TYPE
		SYNTAX  CounterBasedGauge64 
		MAX-ACCESS read-only 
		STATUS current
		DESCRIPTION  "Total Full-cone sessions created" 
		::={ acosCgnv6DsLiteGlobalS 74 } 

		fullconeFreed OBJECT-TYPE
		SYNTAX  CounterBasedGauge64 
		MAX-ACCESS read-only 
		STATUS current
		DESCRIPTION  "Total Full-cone sessions freed" 
		::={ acosCgnv6DsLiteGlobalS 75 } 

		dataSessionCreatedShadow OBJECT-TYPE
		SYNTAX  CounterBasedGauge64 
		MAX-ACCESS read-only 
		STATUS current
		DESCRIPTION  "Total Data Sessions Created" 
		::={ acosCgnv6DsLiteGlobalS 76 } 

		dataSessionFreedShadow OBJECT-TYPE
		SYNTAX  CounterBasedGauge64 
		MAX-ACCESS read-only 
		STATUS current
		DESCRIPTION  "Total Data Sessions Freed" 
		::={ acosCgnv6DsLiteGlobalS 77 } 

		dataSessionUserQuotaMismatch OBJECT-TYPE
		SYNTAX  CounterBasedGauge64 
		MAX-ACCESS read-only 
		STATUS current
		DESCRIPTION  "Data Session Counter Per User Mismatch" 
		::={ acosCgnv6DsLiteGlobalS 78 } 

		extendedQuotaMismatched OBJECT-TYPE
		SYNTAX  CounterBasedGauge64 
		MAX-ACCESS read-only 
		STATUS current
		DESCRIPTION  "Extended User-Quota Mismatched" 
		::={ acosCgnv6DsLiteGlobalS 79 } 

		natPortUnavailableOther OBJECT-TYPE
		SYNTAX  CounterBasedGauge64 
		MAX-ACCESS read-only 
		STATUS current
		DESCRIPTION  "Other NAT Port Unavailable" 
		::={ acosCgnv6DsLiteGlobalS 80 } 

		natPortUnavailable OBJECT-TYPE
		SYNTAX  CounterBasedGauge64 
		MAX-ACCESS read-only 
		STATUS current
		DESCRIPTION  "Total NAT Port Unavailable" 
		::={ acosCgnv6DsLiteGlobalS 81 } 

		newUserResourceUnavailableTcp OBJECT-TYPE
		SYNTAX  CounterBasedGauge64 
		MAX-ACCESS read-only 
		STATUS current
		DESCRIPTION  "TCP New User NAT Resource Unavailable" 
		::={ acosCgnv6DsLiteGlobalS 82 } 

		newUserResourceUnavailableUdp OBJECT-TYPE
		SYNTAX  CounterBasedGauge64 
		MAX-ACCESS read-only 
		STATUS current
		DESCRIPTION  "UDP New User NAT Resource Unavailable" 
		::={ acosCgnv6DsLiteGlobalS 83 } 

		newUserResourceUnavailableIcmp OBJECT-TYPE
		SYNTAX  CounterBasedGauge64 
		MAX-ACCESS read-only 
		STATUS current
		DESCRIPTION  "ICMP New User NAT Resource Unavailable" 
		::={ acosCgnv6DsLiteGlobalS 84 } 

		newUserResourceUnavailableOther OBJECT-TYPE
		SYNTAX  CounterBasedGauge64 
		MAX-ACCESS read-only 
		STATUS current
		DESCRIPTION  "Other New User NAT Resource Unavailable" 
		::={ acosCgnv6DsLiteGlobalS 85 } 

		totalTcpAllocatedShadow OBJECT-TYPE
		SYNTAX  CounterBasedGauge64 
		MAX-ACCESS read-only 
		STATUS current
		DESCRIPTION  "Total TCP Ports Allocated" 
		::={ acosCgnv6DsLiteGlobalS 86 } 

		totalTcpFreedShadow OBJECT-TYPE
		SYNTAX  CounterBasedGauge64 
		MAX-ACCESS read-only 
		STATUS current
		DESCRIPTION  "Total TCP Ports Freed" 
		::={ acosCgnv6DsLiteGlobalS 87 } 

		totalUdpAllocatedShadow OBJECT-TYPE
		SYNTAX  CounterBasedGauge64 
		MAX-ACCESS read-only 
		STATUS current
		DESCRIPTION  "Total UDP Ports Allocated" 
		::={ acosCgnv6DsLiteGlobalS 88 } 

		totalUdpFreedShadow OBJECT-TYPE
		SYNTAX  CounterBasedGauge64 
		MAX-ACCESS read-only 
		STATUS current
		DESCRIPTION  "Total UDP Ports Freed" 
		::={ acosCgnv6DsLiteGlobalS 89 } 

		totalIcmpAllocatedShadow OBJECT-TYPE
		SYNTAX  CounterBasedGauge64 
		MAX-ACCESS read-only 
		STATUS current
		DESCRIPTION  "Total ICMP Ports Allocated" 
		::={ acosCgnv6DsLiteGlobalS 90 } 

		totalIcmpFreedShadow OBJECT-TYPE
		SYNTAX  CounterBasedGauge64 
		MAX-ACCESS read-only 
		STATUS current
		DESCRIPTION  "Total ICMP Ports Freed" 
		::={ acosCgnv6DsLiteGlobalS 91 } 

		udpAlgNoQuota OBJECT-TYPE
		SYNTAX  CounterBasedGauge64 
		MAX-ACCESS read-only 
		STATUS current
		DESCRIPTION  "UDP ALG User-Quota Not Found" 
		::={ acosCgnv6DsLiteGlobalS 92 } 

		udpAlgEimMismatch OBJECT-TYPE
		SYNTAX  CounterBasedGauge64 
		MAX-ACCESS read-only 
		STATUS current
		DESCRIPTION  "UDP ALG Endpoint-Independent Mapping Mismatch" 
		::={ acosCgnv6DsLiteGlobalS 93 } 

		udpAlgNoNatIp OBJECT-TYPE
		SYNTAX  CounterBasedGauge64 
		MAX-ACCESS read-only 
		STATUS current
		DESCRIPTION  "UDP ALG User-Quota Unknown NAT IP" 
		::={ acosCgnv6DsLiteGlobalS 94 } 

		udpAlgAllocFailure OBJECT-TYPE
		SYNTAX  CounterBasedGauge64 
		MAX-ACCESS read-only 
		STATUS current
		DESCRIPTION  "UDP ALG Port Allocation Failure" 
		::={ acosCgnv6DsLiteGlobalS 95 } 

		sipAlgNoQuota OBJECT-TYPE
		SYNTAX  CounterBasedGauge64 
		MAX-ACCESS read-only 
		STATUS current
		DESCRIPTION  "SIP ALG User-Quota Not Found" 
		::={ acosCgnv6DsLiteGlobalS 96 } 

		sipAlgQuotaIncFailure OBJECT-TYPE
		SYNTAX  CounterBasedGauge64 
		MAX-ACCESS read-only 
		STATUS current
		DESCRIPTION  "SIP ALG User-Quota Exceeded" 
		::={ acosCgnv6DsLiteGlobalS 97 } 

		sipAlgNoNatIp OBJECT-TYPE
		SYNTAX  CounterBasedGauge64 
		MAX-ACCESS read-only 
		STATUS current
		DESCRIPTION  "SIP ALG Unknown NAT IP" 
		::={ acosCgnv6DsLiteGlobalS 98 } 

		sipAlgReuseContactFullcone OBJECT-TYPE
		SYNTAX  CounterBasedGauge64 
		MAX-ACCESS read-only 
		STATUS current
		DESCRIPTION  "SIP ALG Reuse Contact Full-cone Session" 
		::={ acosCgnv6DsLiteGlobalS 99 } 

		sipAlgContactFullconeMismatch OBJECT-TYPE
		SYNTAX  CounterBasedGauge64 
		MAX-ACCESS read-only 
		STATUS current
		DESCRIPTION  "SIP ALG Contact Full-cone Session Mismatch" 
		::={ acosCgnv6DsLiteGlobalS 100 } 

		sipAlgAllocContactPortFailure OBJECT-TYPE
		SYNTAX  CounterBasedGauge64 
		MAX-ACCESS read-only 
		STATUS current
		DESCRIPTION  "SIP ALG Alloc Contact NAT Port Failure" 
		::={ acosCgnv6DsLiteGlobalS 101 } 

		sipAlgCreateContactFullconeFailure OBJECT-TYPE
		SYNTAX  CounterBasedGauge64 
		MAX-ACCESS read-only 
		STATUS current
		DESCRIPTION  "SIP ALG Create Contact Full-cone Session Failure" 
		::={ acosCgnv6DsLiteGlobalS 102 } 

		sipAlgReleaseContactPortFailure OBJECT-TYPE
		SYNTAX  CounterBasedGauge64 
		MAX-ACCESS read-only 
		STATUS current
		DESCRIPTION  "SIP ALG Release Contact NAT Port Failure" 
		::={ acosCgnv6DsLiteGlobalS 103 } 

		sipAlgSingleRtpFullcone OBJECT-TYPE
		SYNTAX  CounterBasedGauge64 
		MAX-ACCESS read-only 
		STATUS current
		DESCRIPTION  "SIP ALG Single RTP Full-cone Found" 
		::={ acosCgnv6DsLiteGlobalS 104 } 

		sipAlgSingleRtcpFullcone OBJECT-TYPE
		SYNTAX  CounterBasedGauge64 
		MAX-ACCESS read-only 
		STATUS current
		DESCRIPTION  "SIP ALG Single RTCP Full-cone Found" 
		::={ acosCgnv6DsLiteGlobalS 105 } 

		sipAlgRtcpFullconeMismatch OBJECT-TYPE
		SYNTAX  CounterBasedGauge64 
		MAX-ACCESS read-only 
		STATUS current
		DESCRIPTION  "SIP ALG RTCP Full-cone NAT Port Mismatch" 
		::={ acosCgnv6DsLiteGlobalS 106 } 

		sipAlgReuseRtpRtcpFullcone OBJECT-TYPE
		SYNTAX  CounterBasedGauge64 
		MAX-ACCESS read-only 
		STATUS current
		DESCRIPTION  "SIP ALG Reuse RTP/RTCP Full-cone Session" 
		::={ acosCgnv6DsLiteGlobalS 107 } 

		sipAlgAllocRtpRtcpPortFailure OBJECT-TYPE
		SYNTAX  CounterBasedGauge64 
		MAX-ACCESS read-only 
		STATUS current
		DESCRIPTION  "SIP ALG Alloc RTP/RTCP NAT Ports Failure" 
		::={ acosCgnv6DsLiteGlobalS 108 } 

		sipAlgAllocSinglePortFailure OBJECT-TYPE
		SYNTAX  CounterBasedGauge64 
		MAX-ACCESS read-only 
		STATUS current
		DESCRIPTION  "SIP ALG Alloc Single RTP or RTCP NAT Port Failure" 
		::={ acosCgnv6DsLiteGlobalS 109 } 

		sipAlgCreateSingleFullconeFailure OBJECT-TYPE
		SYNTAX  CounterBasedGauge64 
		MAX-ACCESS read-only 
		STATUS current
		DESCRIPTION  "SIP ALG Create Single RTP or RTCP Full-cone Session Failure" 
		::={ acosCgnv6DsLiteGlobalS 110 } 

		sipAlgCreateRtpFullconeFailure OBJECT-TYPE
		SYNTAX  CounterBasedGauge64 
		MAX-ACCESS read-only 
		STATUS current
		DESCRIPTION  "SIP ALG Create RTP Full-cone Session Failure" 
		::={ acosCgnv6DsLiteGlobalS 111 } 

		sipAlgCreateRtcpFullconeFailure OBJECT-TYPE
		SYNTAX  CounterBasedGauge64 
		MAX-ACCESS read-only 
		STATUS current
		DESCRIPTION  "SIP ALG Create RTCP Full-cone Session Failure" 
		::={ acosCgnv6DsLiteGlobalS 112 } 

		sipAlgPortPairAllocFromConsecutive OBJECT-TYPE
		SYNTAX  CounterBasedGauge64 
		MAX-ACCESS read-only 
		STATUS current
		DESCRIPTION  "SIP ALG Port Pair Allocated From Consecutive" 
		::={ acosCgnv6DsLiteGlobalS 113 } 

		sipAlgPortPairAllocFromPartition OBJECT-TYPE
		SYNTAX  CounterBasedGauge64 
		MAX-ACCESS read-only 
		STATUS current
		DESCRIPTION  "SIP ALG Port Pair Allocated From Partition" 
		::={ acosCgnv6DsLiteGlobalS 114 } 

		sipAlgPortPairAllocFromPoolPortBatch OBJECT-TYPE
		SYNTAX  CounterBasedGauge64 
		MAX-ACCESS read-only 
		STATUS current
		DESCRIPTION  "SIP ALG Port Pair Allocated From Pool Port Batch" 
		::={ acosCgnv6DsLiteGlobalS 115 } 

		sipAlgPortPairAllocFromQuotaConsecutive OBJECT-TYPE
		SYNTAX  CounterBasedGauge64 
		MAX-ACCESS read-only 
		STATUS current
		DESCRIPTION  "SIP ALG Port Pair Allocated From Quota Consecutive" 
		::={ acosCgnv6DsLiteGlobalS 116 } 

		sipAlgPortPairAllocFromQuotaPartition OBJECT-TYPE
		SYNTAX  CounterBasedGauge64 
		MAX-ACCESS read-only 
		STATUS current
		DESCRIPTION  "SIP ALG Port Pair Allocated From Quota Partition" 
		::={ acosCgnv6DsLiteGlobalS 117 } 

		sipAlgPortPairAllocFromQuotaPartitionError OBJECT-TYPE
		SYNTAX  CounterBasedGauge64 
		MAX-ACCESS read-only 
		STATUS current
		DESCRIPTION  "SIP ALG Port Pair Allocated From Quota Partition Error" 
		::={ acosCgnv6DsLiteGlobalS 118 } 

		sipAlgPortPairAllocFromQuotaPoolPortBatch OBJECT-TYPE
		SYNTAX  CounterBasedGauge64 
		MAX-ACCESS read-only 
		STATUS current
		DESCRIPTION  "SIP ALG Port Pair Allocated From Quota Pool Port Batch" 
		::={ acosCgnv6DsLiteGlobalS 119 } 

		sipAlgPortPairAllocFromQuotaPoolPortBatchWithFrag OBJECT-TYPE
		SYNTAX  CounterBasedGauge64 
		MAX-ACCESS read-only 
		STATUS current
		DESCRIPTION  "SIP ALG Port Pair Allocated From Quota Port Batch Version 2 with Frag Free Ports" 
		::={ acosCgnv6DsLiteGlobalS 120 } 

		h323AlgNoQuota OBJECT-TYPE
		SYNTAX  CounterBasedGauge64 
		MAX-ACCESS read-only 
		STATUS current
		DESCRIPTION  "H323 ALG User-Quota Not Found" 
		::={ acosCgnv6DsLiteGlobalS 121 } 

		h323AlgQuotaIncFailure OBJECT-TYPE
		SYNTAX  CounterBasedGauge64 
		MAX-ACCESS read-only 
		STATUS current
		DESCRIPTION  "H323 ALG User-Quota Exceeded" 
		::={ acosCgnv6DsLiteGlobalS 122 } 

		h323AlgNoNatIp OBJECT-TYPE
		SYNTAX  CounterBasedGauge64 
		MAX-ACCESS read-only 
		STATUS current
		DESCRIPTION  "H323 ALG Unknown NAT IP" 
		::={ acosCgnv6DsLiteGlobalS 123 } 

		h323AlgReuseFullcone OBJECT-TYPE
		SYNTAX  CounterBasedGauge64 
		MAX-ACCESS read-only 
		STATUS current
		DESCRIPTION  "H323 ALG Reuse Full-cone Session" 
		::={ acosCgnv6DsLiteGlobalS 124 } 

		h323AlgFullconeMismatch OBJECT-TYPE
		SYNTAX  CounterBasedGauge64 
		MAX-ACCESS read-only 
		STATUS current
		DESCRIPTION  "H323 ALG Full-cone Session Mismatch" 
		::={ acosCgnv6DsLiteGlobalS 125 } 

		h323AlgAllocPortFailure OBJECT-TYPE
		SYNTAX  CounterBasedGauge64 
		MAX-ACCESS read-only 
		STATUS current
		DESCRIPTION  "H323 ALG Alloc NAT Port Failure" 
		::={ acosCgnv6DsLiteGlobalS 126 } 

		h323AlgCreateFullconeFailure OBJECT-TYPE
		SYNTAX  CounterBasedGauge64 
		MAX-ACCESS read-only 
		STATUS current
		DESCRIPTION  "H323 ALG Create Full-cone Session Failure" 
		::={ acosCgnv6DsLiteGlobalS 127 } 

		h323AlgReleasePortFailure OBJECT-TYPE
		SYNTAX  CounterBasedGauge64 
		MAX-ACCESS read-only 
		STATUS current
		DESCRIPTION  "H323 ALG Release NAT Port Failure" 
		::={ acosCgnv6DsLiteGlobalS 128 } 

		h323AlgSingleRtpFullcone OBJECT-TYPE
		SYNTAX  CounterBasedGauge64 
		MAX-ACCESS read-only 
		STATUS current
		DESCRIPTION  "H323 ALG Single RTP Full-cone Found" 
		::={ acosCgnv6DsLiteGlobalS 129 } 

		h323AlgSingleRtcpFullcone OBJECT-TYPE
		SYNTAX  CounterBasedGauge64 
		MAX-ACCESS read-only 
		STATUS current
		DESCRIPTION  "H323 ALG Single RTCP Full-cone Found" 
		::={ acosCgnv6DsLiteGlobalS 130 } 

		h323AlgRtcpFullconeMismatch OBJECT-TYPE
		SYNTAX  CounterBasedGauge64 
		MAX-ACCESS read-only 
		STATUS current
		DESCRIPTION  "H323 ALG RTCP Full-cone NAT Port Mismatch" 
		::={ acosCgnv6DsLiteGlobalS 131 } 

		h323AlgReuseRtpRtcpFullcone OBJECT-TYPE
		SYNTAX  CounterBasedGauge64 
		MAX-ACCESS read-only 
		STATUS current
		DESCRIPTION  "H323 ALG Reuse RTP/RTCP Full-cone Session" 
		::={ acosCgnv6DsLiteGlobalS 132 } 

		h323AlgAllocRtpRtcpPortFailure OBJECT-TYPE
		SYNTAX  CounterBasedGauge64 
		MAX-ACCESS read-only 
		STATUS current
		DESCRIPTION  "H323 ALG Alloc RTP/RTCP NAT Ports Failure" 
		::={ acosCgnv6DsLiteGlobalS 133 } 

		h323AlgAllocSinglePortFailure OBJECT-TYPE
		SYNTAX  CounterBasedGauge64 
		MAX-ACCESS read-only 
		STATUS current
		DESCRIPTION  "H323 ALG Alloc Single RTP or RTCP NAT Port Failure" 
		::={ acosCgnv6DsLiteGlobalS 134 } 

		h323AlgCreateSingleFullconeFailure OBJECT-TYPE
		SYNTAX  CounterBasedGauge64 
		MAX-ACCESS read-only 
		STATUS current
		DESCRIPTION  "H323 ALG Create Single RTP or RTCP Full-cone Session Failure" 
		::={ acosCgnv6DsLiteGlobalS 135 } 

		h323AlgCreateRtpFullconeFailure OBJECT-TYPE
		SYNTAX  CounterBasedGauge64 
		MAX-ACCESS read-only 
		STATUS current
		DESCRIPTION  "H323 ALG Create RTP Full-cone Session Failure" 
		::={ acosCgnv6DsLiteGlobalS 136 } 

		h323AlgCreateRtcpFullconeFailure OBJECT-TYPE
		SYNTAX  CounterBasedGauge64 
		MAX-ACCESS read-only 
		STATUS current
		DESCRIPTION  "H323 ALG Create RTCP Full-cone Session Failure" 
		::={ acosCgnv6DsLiteGlobalS 137 } 

		h323AlgPortPairAllocFromConsecutive OBJECT-TYPE
		SYNTAX  CounterBasedGauge64 
		MAX-ACCESS read-only 
		STATUS current
		DESCRIPTION  "H323 ALG Port Pair Allocated From Consecutive" 
		::={ acosCgnv6DsLiteGlobalS 138 } 

		h323AlgPortPairAllocFromPartition OBJECT-TYPE
		SYNTAX  CounterBasedGauge64 
		MAX-ACCESS read-only 
		STATUS current
		DESCRIPTION  "H323 ALG Port Pair Allocated From Partition" 
		::={ acosCgnv6DsLiteGlobalS 139 } 

		h323AlgPortPairAllocFromPoolPortBatch OBJECT-TYPE
		SYNTAX  CounterBasedGauge64 
		MAX-ACCESS read-only 
		STATUS current
		DESCRIPTION  "H323 ALG Port Pair Allocated From Pool Port Batch" 
		::={ acosCgnv6DsLiteGlobalS 140 } 

		h323AlgPortPairAllocFromQuotaConsecutive OBJECT-TYPE
		SYNTAX  CounterBasedGauge64 
		MAX-ACCESS read-only 
		STATUS current
		DESCRIPTION  "H323 ALG Port Pair Allocated From Quota Consecutive" 
		::={ acosCgnv6DsLiteGlobalS 141 } 

		h323AlgPortPairAllocFromQuotaPartition OBJECT-TYPE
		SYNTAX  CounterBasedGauge64 
		MAX-ACCESS read-only 
		STATUS current
		DESCRIPTION  "H323 ALG Port Pair Allocated From Quota Partition" 
		::={ acosCgnv6DsLiteGlobalS 142 } 

		h323AlgPortPairAllocFromQuotaPartitionError OBJECT-TYPE
		SYNTAX  CounterBasedGauge64 
		MAX-ACCESS read-only 
		STATUS current
		DESCRIPTION  "H323 ALG Port Pair Allocated From Quota Partition Error" 
		::={ acosCgnv6DsLiteGlobalS 143 } 

		h323AlgPortPairAllocFromQuotaPoolPortBatch OBJECT-TYPE
		SYNTAX  CounterBasedGauge64 
		MAX-ACCESS read-only 
		STATUS current
		DESCRIPTION  "H323 ALG Port Pair Allocated From Quota Pool Port Batch" 
		::={ acosCgnv6DsLiteGlobalS 144 } 

		portBatchQuotaExtensionAllocFailure OBJECT-TYPE
		SYNTAX  CounterBasedGauge64 
		MAX-ACCESS read-only 
		STATUS current
		DESCRIPTION  "Port Batch Extension Alloc Failure (No memory)" 
		::={ acosCgnv6DsLiteGlobalS 145 } 

		portBatchFreeQuotaNotFound OBJECT-TYPE
		SYNTAX  CounterBasedGauge64 
		MAX-ACCESS read-only 
		STATUS current
		DESCRIPTION  "Port Batch Quota Not Found on Free" 
		::={ acosCgnv6DsLiteGlobalS 146 } 

		portBatchFreePortNotFound OBJECT-TYPE
		SYNTAX  CounterBasedGauge64 
		MAX-ACCESS read-only 
		STATUS current
		DESCRIPTION  "Port Batch Port Not Found on Free" 
		::={ acosCgnv6DsLiteGlobalS 147 } 

		portBatchFreeWrongPartition OBJECT-TYPE
		SYNTAX  CounterBasedGauge64 
		MAX-ACCESS read-only 
		STATUS current
		DESCRIPTION  "Port Batch Free Wrong Partition" 
		::={ acosCgnv6DsLiteGlobalS 148 } 

		radiusQueryQuotaExtAllocFailure OBJECT-TYPE
		SYNTAX  CounterBasedGauge64 
		MAX-ACCESS read-only 
		STATUS current
		DESCRIPTION  "RADIUS Query Container Alloc (No Memoty)" 
		::={ acosCgnv6DsLiteGlobalS 149 } 

		radiusQueryQuotaExtAllocRaceFree OBJECT-TYPE
		SYNTAX  CounterBasedGauge64 
		MAX-ACCESS read-only 
		STATUS current
		DESCRIPTION  "RADIUS Query Container Alloc Race Free" 
		::={ acosCgnv6DsLiteGlobalS 150 } 

		quotaExtensionAdded OBJECT-TYPE
		SYNTAX  CounterBasedGauge64 
		MAX-ACCESS read-only 
		STATUS current
		DESCRIPTION  "Quota Extension Added to Quota" 
		::={ acosCgnv6DsLiteGlobalS 151 } 

		quotaExtensionRemoved OBJECT-TYPE
		SYNTAX  CounterBasedGauge64 
		MAX-ACCESS read-only 
		STATUS current
		DESCRIPTION  "Quota Extension Removed from Quota" 
		::={ acosCgnv6DsLiteGlobalS 152 } 

		quotaExtensionRemoveNotFound OBJECT-TYPE
		SYNTAX  CounterBasedGauge64 
		MAX-ACCESS read-only 
		STATUS current
		DESCRIPTION  "Quota Extension Not Found on Remove" 
		::={ acosCgnv6DsLiteGlobalS 153 } 

		haSyncPortBatchSent OBJECT-TYPE
		SYNTAX  CounterBasedGauge64 
		MAX-ACCESS read-only 
		STATUS current
		DESCRIPTION  "HA Port Batch Extension Sync Sent" 
		::={ acosCgnv6DsLiteGlobalS 154 } 

		haSyncPortBatchRcv OBJECT-TYPE
		SYNTAX  CounterBasedGauge64 
		MAX-ACCESS read-only 
		STATUS current
		DESCRIPTION  "HA Port Batch Extension Sync Received" 
		::={ acosCgnv6DsLiteGlobalS 155 } 

		haSendPortBatchNotFound OBJECT-TYPE
		SYNTAX  CounterBasedGauge64 
		MAX-ACCESS read-only 
		STATUS current
		DESCRIPTION  "HA Port Batch Not Found on Sync Send" 
		::={ acosCgnv6DsLiteGlobalS 156 } 

		haRcvPortNotInPortBatch OBJECT-TYPE
		SYNTAX  CounterBasedGauge64 
		MAX-ACCESS read-only 
		STATUS current
		DESCRIPTION  "HA Port Not in Port Batch on Sync Rcv" 
		::={ acosCgnv6DsLiteGlobalS 157 } 

		badPortToFree OBJECT-TYPE
		SYNTAX  CounterBasedGauge64 
		MAX-ACCESS read-only 
		STATUS current
		DESCRIPTION  "Freeing Bad Port" 
		::={ acosCgnv6DsLiteGlobalS 158 } 

		consecutivePortFree OBJECT-TYPE
		SYNTAX  CounterBasedGauge64 
		MAX-ACCESS read-only 
		STATUS current
		DESCRIPTION  "Port Freed from Consecutive Pool" 
		::={ acosCgnv6DsLiteGlobalS 159 } 

		partitionPortFree OBJECT-TYPE
		SYNTAX  CounterBasedGauge64 
		MAX-ACCESS read-only 
		STATUS current
		DESCRIPTION  "Port Freed from Partition" 
		::={ acosCgnv6DsLiteGlobalS 160 } 

		poolPortBatchPortFree OBJECT-TYPE
		SYNTAX  CounterBasedGauge64 
		MAX-ACCESS read-only 
		STATUS current
		DESCRIPTION  "Port Freed from Pool Port Batch" 
		::={ acosCgnv6DsLiteGlobalS 161 } 

		portAllocatedFromQuotaConsecutive OBJECT-TYPE
		SYNTAX  CounterBasedGauge64 
		MAX-ACCESS read-only 
		STATUS current
		DESCRIPTION  "Port Allocated from Quota Consecutive" 
		::={ acosCgnv6DsLiteGlobalS 162 } 

		portAllocatedFromQuotaPartition OBJECT-TYPE
		SYNTAX  CounterBasedGauge64 
		MAX-ACCESS read-only 
		STATUS current
		DESCRIPTION  "Port Allocated from Quota Partition" 
		::={ acosCgnv6DsLiteGlobalS 163 } 

		portAllocatedFromQuotaPoolPortBatch OBJECT-TYPE
		SYNTAX  CounterBasedGauge64 
		MAX-ACCESS read-only 
		STATUS current
		DESCRIPTION  "Port Allocated from Quota Pool Port Batch" 
		::={ acosCgnv6DsLiteGlobalS 164 } 

		portFreedFromQuotaConsecutive OBJECT-TYPE
		SYNTAX  CounterBasedGauge64 
		MAX-ACCESS read-only 
		STATUS current
		DESCRIPTION  "Port Freed from Quota Consecutive" 
		::={ acosCgnv6DsLiteGlobalS 165 } 

		portFreedFromQuotaPartition OBJECT-TYPE
		SYNTAX  CounterBasedGauge64 
		MAX-ACCESS read-only 
		STATUS current
		DESCRIPTION  "Port Freed from Quota Partition" 
		::={ acosCgnv6DsLiteGlobalS 166 } 

		portFreedFromQuotaPoolPortBatch OBJECT-TYPE
		SYNTAX  CounterBasedGauge64 
		MAX-ACCESS read-only 
		STATUS current
		DESCRIPTION  "Port Freed from Quota Pool Port Batch" 
		::={ acosCgnv6DsLiteGlobalS 167 } 

		portBatchAllocatedToQuota OBJECT-TYPE
		SYNTAX  CounterBasedGauge64 
		MAX-ACCESS read-only 
		STATUS current
		DESCRIPTION  "Port Batch Allocated to Quota" 
		::={ acosCgnv6DsLiteGlobalS 168 } 

		portBatchFreedFromQuota OBJECT-TYPE
		SYNTAX  CounterBasedGauge64 
		MAX-ACCESS read-only 
		STATUS current
		DESCRIPTION  "Port Batch Freed From Quota" 
		::={ acosCgnv6DsLiteGlobalS 169 } 

		specificPortAllocatedFromQuotaConsecutive OBJECT-TYPE
		SYNTAX  CounterBasedGauge64 
		MAX-ACCESS read-only 
		STATUS current
		DESCRIPTION  "Specific Port Allocated from Quota Consecutive" 
		::={ acosCgnv6DsLiteGlobalS 170 } 

		specificPortAllocatedFromQuotaPartition OBJECT-TYPE
		SYNTAX  CounterBasedGauge64 
		MAX-ACCESS read-only 
		STATUS current
		DESCRIPTION  "Specific Port Allocated from Quota Partition" 
		::={ acosCgnv6DsLiteGlobalS 171 } 

		specificPortAllocatedFromQuotaPoolPortBatch OBJECT-TYPE
		SYNTAX  CounterBasedGauge64 
		MAX-ACCESS read-only 
		STATUS current
		DESCRIPTION  "Specific Port Allocated from Quota Pool Port Batch" 
		::={ acosCgnv6DsLiteGlobalS 172 } 

		portBatchContainerAllocFailure OBJECT-TYPE
		SYNTAX  CounterBasedGauge64 
		MAX-ACCESS read-only 
		STATUS current
		DESCRIPTION  "Port Batch Container Alloc Out of Memory" 
		::={ acosCgnv6DsLiteGlobalS 173 } 

		portBatchContainerAllocRaceFree OBJECT-TYPE
		SYNTAX  CounterBasedGauge64 
		MAX-ACCESS read-only 
		STATUS current
		DESCRIPTION  "Port Batch Container Race Free" 
		::={ acosCgnv6DsLiteGlobalS 174 } 

		portOverloadingDestinationConflict OBJECT-TYPE
		SYNTAX  CounterBasedGauge64 
		MAX-ACCESS read-only 
		STATUS current
		DESCRIPTION  "Port Overloading Destination Conflict" 
		::={ acosCgnv6DsLiteGlobalS 175 } 

		portOverloadingOutOfMemory OBJECT-TYPE
		SYNTAX  CounterBasedGauge64 
		MAX-ACCESS read-only 
		STATUS current
		DESCRIPTION  "Port Overloading Out of Memory" 
		::={ acosCgnv6DsLiteGlobalS 176 } 

		portOverloadingAssignUser OBJECT-TYPE
		SYNTAX  CounterBasedGauge64 
		MAX-ACCESS read-only 
		STATUS current
		DESCRIPTION  "Port Overloading Port Assign User" 
		::={ acosCgnv6DsLiteGlobalS 177 } 

		portOverloadingAssignUserPortBatch OBJECT-TYPE
		SYNTAX  CounterBasedGauge64 
		MAX-ACCESS read-only 
		STATUS current
		DESCRIPTION  "Port Overloading Port Assign User Port Batch" 
		::={ acosCgnv6DsLiteGlobalS 178 } 

		portOverloadingInc OBJECT-TYPE
		SYNTAX  CounterBasedGauge64 
		MAX-ACCESS read-only 
		STATUS current
		DESCRIPTION  "Port Overloading Port Increment" 
		::={ acosCgnv6DsLiteGlobalS 179 } 

		portOverloadingDecOnConflict OBJECT-TYPE
		SYNTAX  CounterBasedGauge64 
		MAX-ACCESS read-only 
		STATUS current
		DESCRIPTION  "Port Overloading Port Decrement on Conflict" 
		::={ acosCgnv6DsLiteGlobalS 180 } 

		portOverloadingDecOnFree OBJECT-TYPE
		SYNTAX  CounterBasedGauge64 
		MAX-ACCESS read-only 
		STATUS current
		DESCRIPTION  "Port Overloading Port Decrement on Free" 
		::={ acosCgnv6DsLiteGlobalS 181 } 

		portOverloadingFreePortOnConflict OBJECT-TYPE
		SYNTAX  CounterBasedGauge64 
		MAX-ACCESS read-only 
		STATUS current
		DESCRIPTION  "Port Overloading Free Port on Conflict" 
		::={ acosCgnv6DsLiteGlobalS 182 } 

		portOverloadingFreePortBatchOnConflict OBJECT-TYPE
		SYNTAX  CounterBasedGauge64 
		MAX-ACCESS read-only 
		STATUS current
		DESCRIPTION  "Port Overloading Free Port Batch on Conflict" 
		::={ acosCgnv6DsLiteGlobalS 183 } 

		portOverloadingIncOverflow OBJECT-TYPE
		SYNTAX  CounterBasedGauge64 
		MAX-ACCESS read-only 
		STATUS current
		DESCRIPTION  "Port Overloading Inc Overflow" 
		::={ acosCgnv6DsLiteGlobalS 184 } 

		portOverloadingAttemptConsecutivePorts OBJECT-TYPE
		SYNTAX  CounterBasedGauge64 
		MAX-ACCESS read-only 
		STATUS current
		DESCRIPTION  "Port Overloading on Consecutive Ports" 
		::={ acosCgnv6DsLiteGlobalS 185 } 

		portOverloadingAttemptSamePartition OBJECT-TYPE
		SYNTAX  CounterBasedGauge64 
		MAX-ACCESS read-only 
		STATUS current
		DESCRIPTION  "Port Overloading on Same Partition" 
		::={ acosCgnv6DsLiteGlobalS 186 } 

		portOverloadingAttemptDiffPartition OBJECT-TYPE
		SYNTAX  CounterBasedGauge64 
		MAX-ACCESS read-only 
		STATUS current
		DESCRIPTION  "Port Overloading on Different Partition" 
		::={ acosCgnv6DsLiteGlobalS 187 } 

		portOverloadingAttemptFailed OBJECT-TYPE
		SYNTAX  CounterBasedGauge64 
		MAX-ACCESS read-only 
		STATUS current
		DESCRIPTION  "Port Overloading Attempt Failed" 
		::={ acosCgnv6DsLiteGlobalS 188 } 

		portOverloadingConnFreeRetryLookup OBJECT-TYPE
		SYNTAX  CounterBasedGauge64 
		MAX-ACCESS read-only 
		STATUS current
		DESCRIPTION  "Port Overloading Conn Free Retry Lookup" 
		::={ acosCgnv6DsLiteGlobalS 189 } 

		portOverloadingConnFreeNotFound OBJECT-TYPE
		SYNTAX  CounterBasedGauge64 
		MAX-ACCESS read-only 
		STATUS current
		DESCRIPTION  "Port Overloading Conn Free Not Found" 
		::={ acosCgnv6DsLiteGlobalS 190 } 

		portOverloadingSmpMemAllocated OBJECT-TYPE
		SYNTAX  CounterBasedGauge64 
		MAX-ACCESS read-only 
		STATUS current
		DESCRIPTION  "Port Overloading SMP Session Allocated" 
		::={ acosCgnv6DsLiteGlobalS 191 } 

		portOverloadingSmpMemFreed OBJECT-TYPE
		SYNTAX  CounterBasedGauge64 
		MAX-ACCESS read-only 
		STATUS current
		DESCRIPTION  "Port Overloading SMP Session Freed" 
		::={ acosCgnv6DsLiteGlobalS 192 } 

		portOverloadingSmpInserted OBJECT-TYPE
		SYNTAX  CounterBasedGauge64 
		MAX-ACCESS read-only 
		STATUS current
		DESCRIPTION  "Port Overloading SMP Inserted" 
		::={ acosCgnv6DsLiteGlobalS 193 } 

		portOverloadingSmpInsertedTcpShadow OBJECT-TYPE
		SYNTAX  CounterBasedGauge64 
		MAX-ACCESS read-only 
		STATUS current
		DESCRIPTION  "Total Port Overloading SMP TCP Inserted" 
		::={ acosCgnv6DsLiteGlobalS 194 } 

		portOverloadingSmpInsertedUdpShadow OBJECT-TYPE
		SYNTAX  CounterBasedGauge64 
		MAX-ACCESS read-only 
		STATUS current
		DESCRIPTION  "Total Port Overloading SMP UDP Inserted" 
		::={ acosCgnv6DsLiteGlobalS 195 } 

		portOverloadingSmpFreeTcpShadow OBJECT-TYPE
		SYNTAX  CounterBasedGauge64 
		MAX-ACCESS read-only 
		STATUS current
		DESCRIPTION  "Total Port Overloading SMP TCP Freed" 
		::={ acosCgnv6DsLiteGlobalS 196 } 

		portOverloadingSmpFreeUdpShadow OBJECT-TYPE
		SYNTAX  CounterBasedGauge64 
		MAX-ACCESS read-only 
		STATUS current
		DESCRIPTION  "Total Port Overloading SMP UDP Freed" 
		::={ acosCgnv6DsLiteGlobalS 197 } 

		portOverloadingSmpPutInDelQFromConn OBJECT-TYPE
		SYNTAX  CounterBasedGauge64 
		MAX-ACCESS read-only 
		STATUS current
		DESCRIPTION  "Port Overloading SMP Free From Conn" 
		::={ acosCgnv6DsLiteGlobalS 198 } 

		portOverloadingSmpFreeDecFailure OBJECT-TYPE
		SYNTAX  CounterBasedGauge64 
		MAX-ACCESS read-only 
		STATUS current
		DESCRIPTION  "Port Overloading SMP Free Dec Failure" 
		::={ acosCgnv6DsLiteGlobalS 199 } 

		portOverloadingSmpFreeNoQuota OBJECT-TYPE
		SYNTAX  CounterBasedGauge64 
		MAX-ACCESS read-only 
		STATUS current
		DESCRIPTION  "Port Overloading SMP Free No Quota" 
		::={ acosCgnv6DsLiteGlobalS 200 } 

		portOverloadingSmpFreePort OBJECT-TYPE
		SYNTAX  CounterBasedGauge64 
		MAX-ACCESS read-only 
		STATUS current
		DESCRIPTION  "Port Overloading SMP Free Port" 
		::={ acosCgnv6DsLiteGlobalS 201 } 

		portOverloadingSmpFreePortFromQuota OBJECT-TYPE
		SYNTAX  CounterBasedGauge64 
		MAX-ACCESS read-only 
		STATUS current
		DESCRIPTION  "Port Overloading SMP Free Port From Quota" 
		::={ acosCgnv6DsLiteGlobalS 202 } 

		portOverloadingForNoPorts OBJECT-TYPE
		SYNTAX  CounterBasedGauge64 
		MAX-ACCESS read-only 
		STATUS current
		DESCRIPTION  "Port Overloading for No Ports" 
		::={ acosCgnv6DsLiteGlobalS 203 } 

		portOverloadingForNoPortsSuccess OBJECT-TYPE
		SYNTAX  CounterBasedGauge64 
		MAX-ACCESS read-only 
		STATUS current
		DESCRIPTION  "Port Overloading for No Ports Success" 
		::={ acosCgnv6DsLiteGlobalS 204 } 

		portOverloadingForQuotaExceeded OBJECT-TYPE
		SYNTAX  CounterBasedGauge64 
		MAX-ACCESS read-only 
		STATUS current
		DESCRIPTION  "Port Overloading for Quota Exceeded" 
		::={ acosCgnv6DsLiteGlobalS 205 } 

		portOverloadingForQuotaExceededSuccess OBJECT-TYPE
		SYNTAX  CounterBasedGauge64 
		MAX-ACCESS read-only 
		STATUS current
		DESCRIPTION  "Port Overloading for Quota Exceeded Success" 
		::={ acosCgnv6DsLiteGlobalS 206 } 

		portOverloadingForQuotaExceededRace OBJECT-TYPE
		SYNTAX  CounterBasedGauge64 
		MAX-ACCESS read-only 
		STATUS current
		DESCRIPTION  "Port Overloading for Quota Exceeded Race" 
		::={ acosCgnv6DsLiteGlobalS 207 } 

		portOverloadingForQuotaExceededRaceSuccess OBJECT-TYPE
		SYNTAX  CounterBasedGauge64 
		MAX-ACCESS read-only 
		STATUS current
		DESCRIPTION  "Port Overloading for Quota Exceeded Race Success" 
		::={ acosCgnv6DsLiteGlobalS 208 } 

		portOverloadingForNewUser OBJECT-TYPE
		SYNTAX  CounterBasedGauge64 
		MAX-ACCESS read-only 
		STATUS current
		DESCRIPTION  "Port Overloading for New User" 
		::={ acosCgnv6DsLiteGlobalS 209 } 

		portOverloadingForNewUserSuccess OBJECT-TYPE
		SYNTAX  CounterBasedGauge64 
		MAX-ACCESS read-only 
		STATUS current
		DESCRIPTION  "Port Overloading for New User Success" 
		::={ acosCgnv6DsLiteGlobalS 210 } 

		haPortOverloadingAttemptFailed OBJECT-TYPE
		SYNTAX  CounterBasedGauge64 
		MAX-ACCESS read-only 
		STATUS current
		DESCRIPTION  "HA Port Overloading Attempt Failed" 
		::={ acosCgnv6DsLiteGlobalS 211 } 

		haPortOverloadingForNoPorts OBJECT-TYPE
		SYNTAX  CounterBasedGauge64 
		MAX-ACCESS read-only 
		STATUS current
		DESCRIPTION  "HA Port Overloading for No Ports" 
		::={ acosCgnv6DsLiteGlobalS 212 } 

		haPortOverloadingForNoPortsSuccess OBJECT-TYPE
		SYNTAX  CounterBasedGauge64 
		MAX-ACCESS read-only 
		STATUS current
		DESCRIPTION  "HA Port Overloading for No Ports Success" 
		::={ acosCgnv6DsLiteGlobalS 213 } 

		haPortOverloadingForQuotaExceeded OBJECT-TYPE
		SYNTAX  CounterBasedGauge64 
		MAX-ACCESS read-only 
		STATUS current
		DESCRIPTION  "HA Port Overloading for Quota Exceeded" 
		::={ acosCgnv6DsLiteGlobalS 214 } 

		haPortOverloadingForQuotaExceededSuccess OBJECT-TYPE
		SYNTAX  CounterBasedGauge64 
		MAX-ACCESS read-only 
		STATUS current
		DESCRIPTION  "HA Port Overloading for Quota Exceeded Success" 
		::={ acosCgnv6DsLiteGlobalS 215 } 

		haPortOverloadingForQuotaExceededRace OBJECT-TYPE
		SYNTAX  CounterBasedGauge64 
		MAX-ACCESS read-only 
		STATUS current
		DESCRIPTION  "HA Port Overloading for Quota Exceeded Race" 
		::={ acosCgnv6DsLiteGlobalS 216 } 

		haPortOverloadingForQuotaExceededRaceSuccess OBJECT-TYPE
		SYNTAX  CounterBasedGauge64 
		MAX-ACCESS read-only 
		STATUS current
		DESCRIPTION  "HA Port Overloading for Quota Exceeded Race Success" 
		::={ acosCgnv6DsLiteGlobalS 217 } 

		haPortOverloadingForNewUser OBJECT-TYPE
		SYNTAX  CounterBasedGauge64 
		MAX-ACCESS read-only 
		STATUS current
		DESCRIPTION  "HA Port Overloading for New User" 
		::={ acosCgnv6DsLiteGlobalS 218 } 

		haPortOverloadingForNewUserSuccess OBJECT-TYPE
		SYNTAX  CounterBasedGauge64 
		MAX-ACCESS read-only 
		STATUS current
		DESCRIPTION  "HA Port Overloading for New User Success" 
		::={ acosCgnv6DsLiteGlobalS 219 } 

		natPoolForceDelete OBJECT-TYPE
		SYNTAX  CounterBasedGauge64 
		MAX-ACCESS read-only 
		STATUS current
		DESCRIPTION  "NAT Pool Force Delete" 
		::={ acosCgnv6DsLiteGlobalS 220 } 

		quotaExtTooMany OBJECT-TYPE
		SYNTAX  CounterBasedGauge64 
		MAX-ACCESS read-only 
		STATUS current
		DESCRIPTION  "Quota Ext Too Many" 
		::={ acosCgnv6DsLiteGlobalS 221 } 

		natPoolNotFoundOnFree OBJECT-TYPE
		SYNTAX  CounterBasedGauge64 
		MAX-ACCESS read-only 
		STATUS current
		DESCRIPTION  "NAT Pool Not Found on Free" 
		::={ acosCgnv6DsLiteGlobalS 222 } 

		standbyClassListDrop OBJECT-TYPE
		SYNTAX  CounterBasedGauge64 
		MAX-ACCESS read-only 
		STATUS current
		DESCRIPTION  "Standby Class-List Drop" 
		::={ acosCgnv6DsLiteGlobalS 223 } 

		fullconeInboundNatPoolMismatch OBJECT-TYPE
		SYNTAX  CounterBasedGauge64 
		MAX-ACCESS read-only 
		STATUS current
		DESCRIPTION  "Full-cone Session NAT Pool Mismatch" 
		::={ acosCgnv6DsLiteGlobalS 224 } 

		badIpTotLen OBJECT-TYPE
		SYNTAX  CounterBasedGauge64 
		MAX-ACCESS read-only 
		STATUS current
		DESCRIPTION  "Bad IPv4 Total Length" 
		::={ acosCgnv6DsLiteGlobalS 225 } 

		ipChecksumVerified OBJECT-TYPE
		SYNTAX  CounterBasedGauge64 
		MAX-ACCESS read-only 
		STATUS current
		DESCRIPTION  "IP Checksum Verified" 
		::={ acosCgnv6DsLiteGlobalS 226 } 

		ipChecksumFixed OBJECT-TYPE
		SYNTAX  CounterBasedGauge64 
		MAX-ACCESS read-only 
		STATUS current
		DESCRIPTION  "IP Checksum Fixed" 
		::={ acosCgnv6DsLiteGlobalS 227 } 

		ipChecksumBadDrop OBJECT-TYPE
		SYNTAX  CounterBasedGauge64 
		MAX-ACCESS read-only 
		STATUS current
		DESCRIPTION  "IP Checksum Bad Drop" 
		::={ acosCgnv6DsLiteGlobalS 228 } 

		ipFragChecksumFixed OBJECT-TYPE
		SYNTAX  CounterBasedGauge64 
		MAX-ACCESS read-only 
		STATUS current
		DESCRIPTION  "IP Frag Checksum Fixed" 
		::={ acosCgnv6DsLiteGlobalS 229 } 

		l4ChecksumVerified OBJECT-TYPE
		SYNTAX  CounterBasedGauge64 
		MAX-ACCESS read-only 
		STATUS current
		DESCRIPTION  "L4 Checksum Verified" 
		::={ acosCgnv6DsLiteGlobalS 230 } 

		l4ChecksumFixed OBJECT-TYPE
		SYNTAX  CounterBasedGauge64 
		MAX-ACCESS read-only 
		STATUS current
		DESCRIPTION  "L4 Checksum Fixed" 
		::={ acosCgnv6DsLiteGlobalS 231 } 

		l4ChecksumBadDrop OBJECT-TYPE
		SYNTAX  CounterBasedGauge64 
		MAX-ACCESS read-only 
		STATUS current
		DESCRIPTION  "L4 Checksum Bad Drop" 
		::={ acosCgnv6DsLiteGlobalS 232 } 

		jumboListBadL4Len OBJECT-TYPE
		SYNTAX  CounterBasedGauge64 
		MAX-ACCESS read-only 
		STATUS current
		DESCRIPTION  "Jumbo List Bad L4 Len" 
		::={ acosCgnv6DsLiteGlobalS 233 } 

		fragListBadL4Len OBJECT-TYPE
		SYNTAX  CounterBasedGauge64 
		MAX-ACCESS read-only 
		STATUS current
		DESCRIPTION  "Frag List Bad L4 Len" 
		::={ acosCgnv6DsLiteGlobalS 234 } 

		natPoolAttemptAddingMultipleFreeBatches OBJECT-TYPE
		SYNTAX  CounterBasedGauge64 
		MAX-ACCESS read-only 
		STATUS current
		DESCRIPTION  "Attempt Adding Multiple Free Batches to Quota" 
		::={ acosCgnv6DsLiteGlobalS 235 } 

		natPoolAddFreeBatchFailed OBJECT-TYPE
		SYNTAX  CounterBasedGauge64 
		MAX-ACCESS read-only 
		STATUS current
		DESCRIPTION  "Add Batch to Quota Failed" 
		::={ acosCgnv6DsLiteGlobalS 236 } 

		mgcpAlgNoQuota OBJECT-TYPE
		SYNTAX  CounterBasedGauge64 
		MAX-ACCESS read-only 
		STATUS current
		DESCRIPTION  "MGCP ALG User-Quota Not Found" 
		::={ acosCgnv6DsLiteGlobalS 237 } 

		mgcpAlgQuotaIncFailure OBJECT-TYPE
		SYNTAX  CounterBasedGauge64 
		MAX-ACCESS read-only 
		STATUS current
		DESCRIPTION  "MGCP ALG User-Quota Exceeded" 
		::={ acosCgnv6DsLiteGlobalS 238 } 

		mgcpAlgNoNatIp OBJECT-TYPE
		SYNTAX  CounterBasedGauge64 
		MAX-ACCESS read-only 
		STATUS current
		DESCRIPTION  "MGCP ALG Unknown NAT IP" 
		::={ acosCgnv6DsLiteGlobalS 239 } 

		mgcpAlgReuseFullcone OBJECT-TYPE
		SYNTAX  CounterBasedGauge64 
		MAX-ACCESS read-only 
		STATUS current
		DESCRIPTION  "MGCP ALG Reuse Full-cone Session" 
		::={ acosCgnv6DsLiteGlobalS 240 } 

		mgcpAlgFullconeMismatch OBJECT-TYPE
		SYNTAX  CounterBasedGauge64 
		MAX-ACCESS read-only 
		STATUS current
		DESCRIPTION  "MGCP ALG Full-cone Session Mismatch" 
		::={ acosCgnv6DsLiteGlobalS 241 } 

		mgcpAlgAllocPortFailure OBJECT-TYPE
		SYNTAX  CounterBasedGauge64 
		MAX-ACCESS read-only 
		STATUS current
		DESCRIPTION  "MGCP ALG Alloc NAT Port Failure" 
		::={ acosCgnv6DsLiteGlobalS 242 } 

		mgcpAlgCreateFullconeFailure OBJECT-TYPE
		SYNTAX  CounterBasedGauge64 
		MAX-ACCESS read-only 
		STATUS current
		DESCRIPTION  "MGCP ALG Create Full-cone Session Failure" 
		::={ acosCgnv6DsLiteGlobalS 243 } 

		mgcpAlgReleasePortFailure OBJECT-TYPE
		SYNTAX  CounterBasedGauge64 
		MAX-ACCESS read-only 
		STATUS current
		DESCRIPTION  "MGCP ALG Release NAT Port Failure" 
		::={ acosCgnv6DsLiteGlobalS 244 } 

		mgcpAlgSingleRtpFullcone OBJECT-TYPE
		SYNTAX  CounterBasedGauge64 
		MAX-ACCESS read-only 
		STATUS current
		DESCRIPTION  "MGCP ALG Single RTP Full-cone Found" 
		::={ acosCgnv6DsLiteGlobalS 245 } 

		mgcpAlgSingleRtcpFullcone OBJECT-TYPE
		SYNTAX  CounterBasedGauge64 
		MAX-ACCESS read-only 
		STATUS current
		DESCRIPTION  "MGCP ALG Single RTCP Full-cone Found" 
		::={ acosCgnv6DsLiteGlobalS 246 } 

		mgcpAlgRtcpFullconeMismatch OBJECT-TYPE
		SYNTAX  CounterBasedGauge64 
		MAX-ACCESS read-only 
		STATUS current
		DESCRIPTION  "MGCP ALG RTCP Full-cone NAT Port Mismatch" 
		::={ acosCgnv6DsLiteGlobalS 247 } 

		mgcpAlgReuseRtpRtcpFullcone OBJECT-TYPE
		SYNTAX  CounterBasedGauge64 
		MAX-ACCESS read-only 
		STATUS current
		DESCRIPTION  "MGCP ALG Reuse RTP/RTCP Full-cone Session" 
		::={ acosCgnv6DsLiteGlobalS 248 } 

		mgcpAlgAllocRtpRtcpPortFailure OBJECT-TYPE
		SYNTAX  CounterBasedGauge64 
		MAX-ACCESS read-only 
		STATUS current
		DESCRIPTION  "MGCP ALG Alloc RTP/RTCP NAT Ports Failure" 
		::={ acosCgnv6DsLiteGlobalS 249 } 

		mgcpAlgAllocSinglePortFailure OBJECT-TYPE
		SYNTAX  CounterBasedGauge64 
		MAX-ACCESS read-only 
		STATUS current
		DESCRIPTION  "MGCP ALG Alloc Single RTP or RTCP NAT Port Failure" 
		::={ acosCgnv6DsLiteGlobalS 250 } 

		mgcpAlgCreateSingleFullconeFailure OBJECT-TYPE
		SYNTAX  CounterBasedGauge64 
		MAX-ACCESS read-only 
		STATUS current
		DESCRIPTION  "MGCP ALG Create Single RTP or RTCP Full-cone Session Failure" 
		::={ acosCgnv6DsLiteGlobalS 251 } 

		mgcpAlgCreateRtpFullconeFailure OBJECT-TYPE
		SYNTAX  CounterBasedGauge64 
		MAX-ACCESS read-only 
		STATUS current
		DESCRIPTION  "MGCP ALG Create RTP Full-cone Session Failure" 
		::={ acosCgnv6DsLiteGlobalS 252 } 

		mgcpAlgCreateRtcpFullconeFailure OBJECT-TYPE
		SYNTAX  CounterBasedGauge64 
		MAX-ACCESS read-only 
		STATUS current
		DESCRIPTION  "MGCP ALG Create RTCP Full-cone Session Failure" 
		::={ acosCgnv6DsLiteGlobalS 253 } 

		mgcpAlgPortPairAllocFromConsecutive OBJECT-TYPE
		SYNTAX  CounterBasedGauge64 
		MAX-ACCESS read-only 
		STATUS current
		DESCRIPTION  "MGCP ALG Port Pair Allocated From Consecutive" 
		::={ acosCgnv6DsLiteGlobalS 254 } 

		mgcpAlgPortPairAllocFromPartition OBJECT-TYPE
		SYNTAX  CounterBasedGauge64 
		MAX-ACCESS read-only 
		STATUS current
		DESCRIPTION  "MGCP ALG Port Pair Allocated From Partition" 
		::={ acosCgnv6DsLiteGlobalS 255 } 

		mgcpAlgPortPairAllocFromPoolPortBatch OBJECT-TYPE
		SYNTAX  CounterBasedGauge64 
		MAX-ACCESS read-only 
		STATUS current
		DESCRIPTION  "MGCP ALG Port Pair Allocated From Pool Port Batch" 
		::={ acosCgnv6DsLiteGlobalS 256 } 

		mgcpAlgPortPairAllocFromQuotaConsecutive OBJECT-TYPE
		SYNTAX  CounterBasedGauge64 
		MAX-ACCESS read-only 
		STATUS current
		DESCRIPTION  "MGCP ALG Port Pair Allocated From Quota Consecutive" 
		::={ acosCgnv6DsLiteGlobalS 257 } 

		mgcpAlgPortPairAllocFromQuotaPartition OBJECT-TYPE
		SYNTAX  CounterBasedGauge64 
		MAX-ACCESS read-only 
		STATUS current
		DESCRIPTION  "MGCP ALG Port Pair Allocated From Quota Partition" 
		::={ acosCgnv6DsLiteGlobalS 258 } 

		mgcpAlgPortPairAllocFromQuotaPartitionError OBJECT-TYPE
		SYNTAX  CounterBasedGauge64 
		MAX-ACCESS read-only 
		STATUS current
		DESCRIPTION  "MGCP ALG Port Pair Allocated From Quota Partition Error" 
		::={ acosCgnv6DsLiteGlobalS 259 } 

		mgcpAlgPortPairAllocFromQuotaPoolPortBatch OBJECT-TYPE
		SYNTAX  CounterBasedGauge64 
		MAX-ACCESS read-only 
		STATUS current
		DESCRIPTION  "MGCP ALG Port Pair Allocated From Quota Pool Port Batch" 
		::={ acosCgnv6DsLiteGlobalS 260 } 

		userQuotaUnusableDrop OBJECT-TYPE
		SYNTAX  CounterBasedGauge64 
		MAX-ACCESS read-only 
		STATUS current
		DESCRIPTION  "User-Quota Unusable Drop" 
		::={ acosCgnv6DsLiteGlobalS 261 } 

		userQuotaUnusable OBJECT-TYPE
		SYNTAX  CounterBasedGauge64 
		MAX-ACCESS read-only 
		STATUS current
		DESCRIPTION  "User-Quota Marked Unusable" 
		::={ acosCgnv6DsLiteGlobalS 262 } 

		natPoolSamePortBatchUdpFailed OBJECT-TYPE
		SYNTAX  CounterBasedGauge64 
		MAX-ACCESS read-only 
		STATUS current
		DESCRIPTION  "Simultaneous Batch Allocation UDP Port Allocation Failed" 
		::={ acosCgnv6DsLiteGlobalS 263 } 

		fwdIngressPacketsTcp OBJECT-TYPE
		SYNTAX  CounterBasedGauge64 
		MAX-ACCESS read-only 
		STATUS current
		DESCRIPTION  "Forward Ingress Packets TCP" 
		::={ acosCgnv6DsLiteGlobalS 264 } 

		fwdEgressPacketsTcp OBJECT-TYPE
		SYNTAX  CounterBasedGauge64 
		MAX-ACCESS read-only 
		STATUS current
		DESCRIPTION  "Forward Egress Packets TCP" 
		::={ acosCgnv6DsLiteGlobalS 265 } 

		revIngressPacketsTcp OBJECT-TYPE
		SYNTAX  CounterBasedGauge64 
		MAX-ACCESS read-only 
		STATUS current
		DESCRIPTION  "Reverse Ingress Packets TCP" 
		::={ acosCgnv6DsLiteGlobalS 266 } 

		revEgressPacketsTcp OBJECT-TYPE
		SYNTAX  CounterBasedGauge64 
		MAX-ACCESS read-only 
		STATUS current
		DESCRIPTION  "Reverse Egress Packets TCP" 
		::={ acosCgnv6DsLiteGlobalS 267 } 

		fwdIngressBytesTcp OBJECT-TYPE
		SYNTAX  CounterBasedGauge64 
		MAX-ACCESS read-only 
		STATUS current
		DESCRIPTION  "Forward Ingress Bytes TCP" 
		::={ acosCgnv6DsLiteGlobalS 268 } 

		fwdEgressBytesTcp OBJECT-TYPE
		SYNTAX  CounterBasedGauge64 
		MAX-ACCESS read-only 
		STATUS current
		DESCRIPTION  "Forward Egress Bytes TCP" 
		::={ acosCgnv6DsLiteGlobalS 269 } 

		revIngressBytesTcp OBJECT-TYPE
		SYNTAX  CounterBasedGauge64 
		MAX-ACCESS read-only 
		STATUS current
		DESCRIPTION  "Reverse Ingress Bytes TCP" 
		::={ acosCgnv6DsLiteGlobalS 270 } 

		revEgressBytesTcp OBJECT-TYPE
		SYNTAX  CounterBasedGauge64 
		MAX-ACCESS read-only 
		STATUS current
		DESCRIPTION  "Reverse Egress Bytes TCP" 
		::={ acosCgnv6DsLiteGlobalS 271 } 

		fwdIngressPacketsUdp OBJECT-TYPE
		SYNTAX  CounterBasedGauge64 
		MAX-ACCESS read-only 
		STATUS current
		DESCRIPTION  "Forward Ingress Packets UDP" 
		::={ acosCgnv6DsLiteGlobalS 272 } 

		fwdEgressPacketsUdp OBJECT-TYPE
		SYNTAX  CounterBasedGauge64 
		MAX-ACCESS read-only 
		STATUS current
		DESCRIPTION  "Forward Egress Packets UDP" 
		::={ acosCgnv6DsLiteGlobalS 273 } 

		revIngressPacketsUdp OBJECT-TYPE
		SYNTAX  CounterBasedGauge64 
		MAX-ACCESS read-only 
		STATUS current
		DESCRIPTION  "Reverse Ingress Packets UDP" 
		::={ acosCgnv6DsLiteGlobalS 274 } 

		revEgressPacketsUdp OBJECT-TYPE
		SYNTAX  CounterBasedGauge64 
		MAX-ACCESS read-only 
		STATUS current
		DESCRIPTION  "Reverse Egress Packets UDP" 
		::={ acosCgnv6DsLiteGlobalS 275 } 

		fwdIngressBytesUdp OBJECT-TYPE
		SYNTAX  CounterBasedGauge64 
		MAX-ACCESS read-only 
		STATUS current
		DESCRIPTION  "Forward Ingress Bytes UDP" 
		::={ acosCgnv6DsLiteGlobalS 276 } 

		fwdEgressBytesUdp OBJECT-TYPE
		SYNTAX  CounterBasedGauge64 
		MAX-ACCESS read-only 
		STATUS current
		DESCRIPTION  "Forward Egress Bytes UDP" 
		::={ acosCgnv6DsLiteGlobalS 277 } 

		revIngressBytesUdp OBJECT-TYPE
		SYNTAX  CounterBasedGauge64 
		MAX-ACCESS read-only 
		STATUS current
		DESCRIPTION  "Reverse Ingress Bytes UDP" 
		::={ acosCgnv6DsLiteGlobalS 278 } 

		revEgressBytesUdp OBJECT-TYPE
		SYNTAX  CounterBasedGauge64 
		MAX-ACCESS read-only 
		STATUS current
		DESCRIPTION  "Reverse Egress Bytes UDP" 
		::={ acosCgnv6DsLiteGlobalS 279 } 

		fwdIngressPacketsIcmp OBJECT-TYPE
		SYNTAX  CounterBasedGauge64 
		MAX-ACCESS read-only 
		STATUS current
		DESCRIPTION  "Forward Ingress Packets ICMP" 
		::={ acosCgnv6DsLiteGlobalS 280 } 

		fwdEgressPacketsIcmp OBJECT-TYPE
		SYNTAX  CounterBasedGauge64 
		MAX-ACCESS read-only 
		STATUS current
		DESCRIPTION  "Forward Egress Packets ICMP" 
		::={ acosCgnv6DsLiteGlobalS 281 } 

		revIngressPacketsIcmp OBJECT-TYPE
		SYNTAX  CounterBasedGauge64 
		MAX-ACCESS read-only 
		STATUS current
		DESCRIPTION  "Reverse Ingress Packets ICMP" 
		::={ acosCgnv6DsLiteGlobalS 282 } 

		revEgressPacketsIcmp OBJECT-TYPE
		SYNTAX  CounterBasedGauge64 
		MAX-ACCESS read-only 
		STATUS current
		DESCRIPTION  "Reverse Egress Packets ICMP" 
		::={ acosCgnv6DsLiteGlobalS 283 } 

		fwdIngressBytesIcmp OBJECT-TYPE
		SYNTAX  CounterBasedGauge64 
		MAX-ACCESS read-only 
		STATUS current
		DESCRIPTION  "Forward Ingress Bytes ICMP" 
		::={ acosCgnv6DsLiteGlobalS 284 } 

		fwdEgressBytesIcmp OBJECT-TYPE
		SYNTAX  CounterBasedGauge64 
		MAX-ACCESS read-only 
		STATUS current
		DESCRIPTION  "Forward Egress Bytes ICMP" 
		::={ acosCgnv6DsLiteGlobalS 285 } 

		revIngressBytesIcmp OBJECT-TYPE
		SYNTAX  CounterBasedGauge64 
		MAX-ACCESS read-only 
		STATUS current
		DESCRIPTION  "Reverse Ingress Bytes ICMP" 
		::={ acosCgnv6DsLiteGlobalS 286 } 

		revEgressBytesIcmp OBJECT-TYPE
		SYNTAX  CounterBasedGauge64 
		MAX-ACCESS read-only 
		STATUS current
		DESCRIPTION  "Reverse Egress Bytes ICMP" 
		::={ acosCgnv6DsLiteGlobalS 287 } 

		fwdIngressPacketsOthers OBJECT-TYPE
		SYNTAX  CounterBasedGauge64 
		MAX-ACCESS read-only 
		STATUS current
		DESCRIPTION  "Forward Ingress Packets OTHERS" 
		::={ acosCgnv6DsLiteGlobalS 288 } 

		fwdEgressPacketsOthers OBJECT-TYPE
		SYNTAX  CounterBasedGauge64 
		MAX-ACCESS read-only 
		STATUS current
		DESCRIPTION  "Forward Egress Packets OTHERS" 
		::={ acosCgnv6DsLiteGlobalS 289 } 

		revIngressPacketsOthers OBJECT-TYPE
		SYNTAX  CounterBasedGauge64 
		MAX-ACCESS read-only 
		STATUS current
		DESCRIPTION  "Reverse Ingress Packets OTHERS" 
		::={ acosCgnv6DsLiteGlobalS 290 } 

		revEgressPacketsOthers OBJECT-TYPE
		SYNTAX  CounterBasedGauge64 
		MAX-ACCESS read-only 
		STATUS current
		DESCRIPTION  "Reverse Egress Packets OTHERS" 
		::={ acosCgnv6DsLiteGlobalS 291 } 

		fwdIngressBytesOthers OBJECT-TYPE
		SYNTAX  CounterBasedGauge64 
		MAX-ACCESS read-only 
		STATUS current
		DESCRIPTION  "Forward Ingress Bytes OTHERS" 
		::={ acosCgnv6DsLiteGlobalS 292 } 

		fwdEgressBytesOthers OBJECT-TYPE
		SYNTAX  CounterBasedGauge64 
		MAX-ACCESS read-only 
		STATUS current
		DESCRIPTION  "Forward Egress Bytes OTHERS" 
		::={ acosCgnv6DsLiteGlobalS 293 } 

		revIngressBytesOthers OBJECT-TYPE
		SYNTAX  CounterBasedGauge64 
		MAX-ACCESS read-only 
		STATUS current
		DESCRIPTION  "Reverse Ingress Bytes OTHERS" 
		::={ acosCgnv6DsLiteGlobalS 294 } 

		revEgressBytesOthers OBJECT-TYPE
		SYNTAX  CounterBasedGauge64 
		MAX-ACCESS read-only 
		STATUS current
		DESCRIPTION  "Reverse Egress Bytes OTHERS" 
		::={ acosCgnv6DsLiteGlobalS 295 } 

		fwdIngressPktSizeRange1 OBJECT-TYPE
		SYNTAX  CounterBasedGauge64 
		MAX-ACCESS read-only 
		STATUS current
		DESCRIPTION  "Forward Ingress Packet size between 0 and 200" 
		::={ acosCgnv6DsLiteGlobalS 296 } 

		fwdIngressPktSizeRange2 OBJECT-TYPE
		SYNTAX  CounterBasedGauge64 
		MAX-ACCESS read-only 
		STATUS current
		DESCRIPTION  "Forward Ingress Packet size between 201 and 800" 
		::={ acosCgnv6DsLiteGlobalS 297 } 

		fwdIngressPktSizeRange3 OBJECT-TYPE
		SYNTAX  CounterBasedGauge64 
		MAX-ACCESS read-only 
		STATUS current
		DESCRIPTION  "Forward Ingress Packet size between 801 and 1550" 
		::={ acosCgnv6DsLiteGlobalS 298 } 

		fwdIngressPktSizeRange4 OBJECT-TYPE
		SYNTAX  CounterBasedGauge64 
		MAX-ACCESS read-only 
		STATUS current
		DESCRIPTION  "Forward Ingress Packet size between 1551 and 9000" 
		::={ acosCgnv6DsLiteGlobalS 299 } 

		fwdEgressPktSizeRange1 OBJECT-TYPE
		SYNTAX  CounterBasedGauge64 
		MAX-ACCESS read-only 
		STATUS current
		DESCRIPTION  "Forward Egress Packet size between 0 and 200" 
		::={ acosCgnv6DsLiteGlobalS 300 } 

		fwdEgressPktSizeRange2 OBJECT-TYPE
		SYNTAX  CounterBasedGauge64 
		MAX-ACCESS read-only 
		STATUS current
		DESCRIPTION  "Forward Egress Packet size between 201 and 800" 
		::={ acosCgnv6DsLiteGlobalS 301 } 

		fwdEgressPktSizeRange3 OBJECT-TYPE
		SYNTAX  CounterBasedGauge64 
		MAX-ACCESS read-only 
		STATUS current
		DESCRIPTION  "Forward Egress Packet size between 801 and 1550" 
		::={ acosCgnv6DsLiteGlobalS 302 } 

		fwdEgressPktSizeRange4 OBJECT-TYPE
		SYNTAX  CounterBasedGauge64 
		MAX-ACCESS read-only 
		STATUS current
		DESCRIPTION  "Forward Egress Packet size between 1551 and 9000" 
		::={ acosCgnv6DsLiteGlobalS 303 } 

		revIngressPktSizeRange1 OBJECT-TYPE
		SYNTAX  CounterBasedGauge64 
		MAX-ACCESS read-only 
		STATUS current
		DESCRIPTION  "Reverse Ingress Packet size between 0 and 200" 
		::={ acosCgnv6DsLiteGlobalS 304 } 

		revIngressPktSizeRange2 OBJECT-TYPE
		SYNTAX  CounterBasedGauge64 
		MAX-ACCESS read-only 
		STATUS current
		DESCRIPTION  "Reverse Ingress Packet size between 201 and 800" 
		::={ acosCgnv6DsLiteGlobalS 305 } 

		revIngressPktSizeRange3 OBJECT-TYPE
		SYNTAX  CounterBasedGauge64 
		MAX-ACCESS read-only 
		STATUS current
		DESCRIPTION  "Reverse Ingress Packet size between 801 and 1550" 
		::={ acosCgnv6DsLiteGlobalS 306 } 

		revIngressPktSizeRange4 OBJECT-TYPE
		SYNTAX  CounterBasedGauge64 
		MAX-ACCESS read-only 
		STATUS current
		DESCRIPTION  "Reverse Ingress Packet size between 1551 and 9000" 
		::={ acosCgnv6DsLiteGlobalS 307 } 

		revEgressPktSizeRange1 OBJECT-TYPE
		SYNTAX  CounterBasedGauge64 
		MAX-ACCESS read-only 
		STATUS current
		DESCRIPTION  "Reverse Egress Packet size between 0 and 200" 
		::={ acosCgnv6DsLiteGlobalS 308 } 

		revEgressPktSizeRange2 OBJECT-TYPE
		SYNTAX  CounterBasedGauge64 
		MAX-ACCESS read-only 
		STATUS current
		DESCRIPTION  "Reverse Egress Packet size between 201 and 800" 
		::={ acosCgnv6DsLiteGlobalS 309 } 

		revEgressPktSizeRange3 OBJECT-TYPE
		SYNTAX  CounterBasedGauge64 
		MAX-ACCESS read-only 
		STATUS current
		DESCRIPTION  "Reverse Egress Packet size between 801 and 1550" 
		::={ acosCgnv6DsLiteGlobalS 310 } 

		revEgressPktSizeRange4 OBJECT-TYPE
		SYNTAX  CounterBasedGauge64 
		MAX-ACCESS read-only 
		STATUS current
		DESCRIPTION  "Reverse Egress Packet size between 1551 and 9000" 
		::={ acosCgnv6DsLiteGlobalS 311 } 

		prefixQuotaMismatch OBJECT-TYPE
		SYNTAX  CounterBasedGauge64 
		MAX-ACCESS read-only 
		STATUS current
		DESCRIPTION  "Prefix Quota NAT IP Mismatch" 
		::={ acosCgnv6DsLiteGlobalS 312 } 

acosCgnv6Sixrd                      OBJECT IDENTIFIER ::= { acosCgnv6 20 }
acosCgnv6SixrdDomain                OBJECT IDENTIFIER ::= { acosCgnv6Sixrd 1 }
acosCgnv6SixrdDomainS               OBJECT IDENTIFIER ::= { acosCgnv6SixrdDomain 1 }

cgnv6SixrdDomainSTable OBJECT-TYPE
		SYNTAX SEQUENCE OF Cgnv6SixrdDomainSEntry
		MAX-ACCESS not-accessible
		STATUS current
		::={ acosCgnv6SixrdDomainS 1 } 


	cgnv6SixrdDomainSEntry OBJECT-TYPE
		SYNTAX Cgnv6SixrdDomainSEntry
		MAX-ACCESS not-accessible
		STATUS current
		INDEX {
			cgnv6SixrdDomainName
		}
		::={ cgnv6SixrdDomainSTable 1 } 


	Cgnv6SixrdDomainSEntry ::=
		SEQUENCE {
			cgnv6SixrdDomainName DisplayString, 
			outboundTcpPacketsReceived CounterBasedGauge64,
			outboundUdpPacketsReceived CounterBasedGauge64,
			outboundIcmpPacketsReceived CounterBasedGauge64,
			outboundOtherPacketsReceived CounterBasedGauge64,
			outboundPacketsDrop CounterBasedGauge64,
			outboundIpv6DestUnreachable CounterBasedGauge64,
			outboundFragmentIpv6 CounterBasedGauge64,
			inboundTcpPacketsReceived CounterBasedGauge64,
			inboundUdpPacketsReceived CounterBasedGauge64,
			inboundIcmpPacketsReceived CounterBasedGauge64,
			inboundOtherPacketsReceived CounterBasedGauge64,
			inboundPacketsDrop CounterBasedGauge64,
			inboundIpv4DestUnreachable CounterBasedGauge64,
			inboundFragmentIpv4 CounterBasedGauge64,
			inboundTunnelFragmentIpv6 CounterBasedGauge64,
			vportMatched CounterBasedGauge64,
			unknownDelegatedPrefix CounterBasedGauge64,
			cgnv6SixrdDomainPacketTooBig CounterBasedGauge64,
			notLocalIp CounterBasedGauge64,
			cgnv6SixrdDomainFragmentError CounterBasedGauge64,
			cgnv6SixrdDomainOtherError CounterBasedGauge64
		}

			cgnv6SixrdDomainName OBJECT-TYPE
			SYNTAX  DisplayString 
			MAX-ACCESS read-only 
			STATUS current
			DESCRIPTION  "6rd Domain name" 
			::={ cgnv6SixrdDomainSEntry 1 } 

			outboundTcpPacketsReceived OBJECT-TYPE
			SYNTAX  CounterBasedGauge64 
			MAX-ACCESS read-only 
			STATUS current
			DESCRIPTION  "Outbound TCP packets received" 
			::={ cgnv6SixrdDomainSEntry 2 } 

			outboundUdpPacketsReceived OBJECT-TYPE
			SYNTAX  CounterBasedGauge64 
			MAX-ACCESS read-only 
			STATUS current
			DESCRIPTION  "Outbound UDP packets received" 
			::={ cgnv6SixrdDomainSEntry 3 } 

			outboundIcmpPacketsReceived OBJECT-TYPE
			SYNTAX  CounterBasedGauge64 
			MAX-ACCESS read-only 
			STATUS current
			DESCRIPTION  "Outbound ICMP packets received" 
			::={ cgnv6SixrdDomainSEntry 4 } 

			outboundOtherPacketsReceived OBJECT-TYPE
			SYNTAX  CounterBasedGauge64 
			MAX-ACCESS read-only 
			STATUS current
			DESCRIPTION  "Outbound other packets received" 
			::={ cgnv6SixrdDomainSEntry 5 } 

			outboundPacketsDrop OBJECT-TYPE
			SYNTAX  CounterBasedGauge64 
			MAX-ACCESS read-only 
			STATUS current
			DESCRIPTION  "Outbound packets dropped" 
			::={ cgnv6SixrdDomainSEntry 6 } 

			outboundIpv6DestUnreachable OBJECT-TYPE
			SYNTAX  CounterBasedGauge64 
			MAX-ACCESS read-only 
			STATUS current
			DESCRIPTION  "Outbound IPv6 destination unreachable" 
			::={ cgnv6SixrdDomainSEntry 7 } 

			outboundFragmentIpv6 OBJECT-TYPE
			SYNTAX  CounterBasedGauge64 
			MAX-ACCESS read-only 
			STATUS current
			DESCRIPTION  "Outbound Fragmented IPv6" 
			::={ cgnv6SixrdDomainSEntry 8 } 

			inboundTcpPacketsReceived OBJECT-TYPE
			SYNTAX  CounterBasedGauge64 
			MAX-ACCESS read-only 
			STATUS current
			DESCRIPTION  "Inbound TCP packets received" 
			::={ cgnv6SixrdDomainSEntry 9 } 

			inboundUdpPacketsReceived OBJECT-TYPE
			SYNTAX  CounterBasedGauge64 
			MAX-ACCESS read-only 
			STATUS current
			DESCRIPTION  "Inbound UDP packets received" 
			::={ cgnv6SixrdDomainSEntry 10 } 

			inboundIcmpPacketsReceived OBJECT-TYPE
			SYNTAX  CounterBasedGauge64 
			MAX-ACCESS read-only 
			STATUS current
			DESCRIPTION  "Inbound ICMP packets received" 
			::={ cgnv6SixrdDomainSEntry 11 } 

			inboundOtherPacketsReceived OBJECT-TYPE
			SYNTAX  CounterBasedGauge64 
			MAX-ACCESS read-only 
			STATUS current
			DESCRIPTION  "Inbound other packets received" 
			::={ cgnv6SixrdDomainSEntry 12 } 

			inboundPacketsDrop OBJECT-TYPE
			SYNTAX  CounterBasedGauge64 
			MAX-ACCESS read-only 
			STATUS current
			DESCRIPTION  "Inbound packets dropped" 
			::={ cgnv6SixrdDomainSEntry 13 } 

			inboundIpv4DestUnreachable OBJECT-TYPE
			SYNTAX  CounterBasedGauge64 
			MAX-ACCESS read-only 
			STATUS current
			DESCRIPTION  "Inbound IPv4 destination unreachable" 
			::={ cgnv6SixrdDomainSEntry 14 } 

			inboundFragmentIpv4 OBJECT-TYPE
			SYNTAX  CounterBasedGauge64 
			MAX-ACCESS read-only 
			STATUS current
			DESCRIPTION  "Inbound Fragmented IPv4" 
			::={ cgnv6SixrdDomainSEntry 15 } 

			inboundTunnelFragmentIpv6 OBJECT-TYPE
			SYNTAX  CounterBasedGauge64 
			MAX-ACCESS read-only 
			STATUS current
			DESCRIPTION  "Inbound Fragmented IPv6 in tunnel" 
			::={ cgnv6SixrdDomainSEntry 16 } 

			vportMatched OBJECT-TYPE
			SYNTAX  CounterBasedGauge64 
			MAX-ACCESS read-only 
			STATUS current
			DESCRIPTION  "Traffic match SLB virtual port" 
			::={ cgnv6SixrdDomainSEntry 17 } 

			unknownDelegatedPrefix OBJECT-TYPE
			SYNTAX  CounterBasedGauge64 
			MAX-ACCESS read-only 
			STATUS current
			DESCRIPTION  "Unknown 6rd delegated prefix" 
			::={ cgnv6SixrdDomainSEntry 18 } 

			cgnv6SixrdDomainPacketTooBig OBJECT-TYPE
			SYNTAX  CounterBasedGauge64 
			MAX-ACCESS read-only 
			STATUS current
			DESCRIPTION  "Packet too big" 
			::={ cgnv6SixrdDomainSEntry 19 } 

			notLocalIp OBJECT-TYPE
			SYNTAX  CounterBasedGauge64 
			MAX-ACCESS read-only 
			STATUS current
			DESCRIPTION  "Not local IP" 
			::={ cgnv6SixrdDomainSEntry 20 } 

			cgnv6SixrdDomainFragmentError OBJECT-TYPE
			SYNTAX  CounterBasedGauge64 
			MAX-ACCESS read-only 
			STATUS current
			DESCRIPTION  "Fragment processing errors" 
			::={ cgnv6SixrdDomainSEntry 21 } 

			cgnv6SixrdDomainOtherError OBJECT-TYPE
			SYNTAX  CounterBasedGauge64 
			MAX-ACCESS read-only 
			STATUS current
			DESCRIPTION  "Other errors" 
			::={ cgnv6SixrdDomainSEntry 22 } 

acosCgnv6Lw4o6                      OBJECT IDENTIFIER ::= { acosCgnv6 21 }
acosCgnv6Lw4o6Global                OBJECT IDENTIFIER ::= { acosCgnv6Lw4o6 1 }
acosCgnv6Lw4o6GlobalS               OBJECT IDENTIFIER ::= { acosCgnv6Lw4o6Global 1 }

		entryCount OBJECT-TYPE
		SYNTAX  CounterBasedGauge64 
		MAX-ACCESS read-only 
		STATUS current
		DESCRIPTION  "Total Entries Configured" 
		::={ acosCgnv6Lw4o6GlobalS 1 } 

		selfHairpinningDrop OBJECT-TYPE
		SYNTAX  CounterBasedGauge64 
		MAX-ACCESS read-only 
		STATUS current
		DESCRIPTION  "Self-Hairpinning Drops" 
		::={ acosCgnv6Lw4o6GlobalS 2 } 

		allHairpinningDrop OBJECT-TYPE
		SYNTAX  CounterBasedGauge64 
		MAX-ACCESS read-only 
		STATUS current
		DESCRIPTION  "All Hairpinning Drops" 
		::={ acosCgnv6Lw4o6GlobalS 3 } 

		noMatchIcmpv6Sent OBJECT-TYPE
		SYNTAX  CounterBasedGauge64 
		MAX-ACCESS read-only 
		STATUS current
		DESCRIPTION  "No-Forward-Match ICMPv6 Sent" 
		::={ acosCgnv6Lw4o6GlobalS 4 } 

		noMatchIcmpSent OBJECT-TYPE
		SYNTAX  CounterBasedGauge64 
		MAX-ACCESS read-only 
		STATUS current
		DESCRIPTION  "No-Reverse-Match ICMP Sent" 
		::={ acosCgnv6Lw4o6GlobalS 5 } 

		icmpInboundDrop OBJECT-TYPE
		SYNTAX  CounterBasedGauge64 
		MAX-ACCESS read-only 
		STATUS current
		DESCRIPTION  "Inbound ICMP Drops" 
		::={ acosCgnv6Lw4o6GlobalS 6 } 

		fwdLookupFailed OBJECT-TYPE
		SYNTAX  CounterBasedGauge64 
		MAX-ACCESS read-only 
		STATUS current
		DESCRIPTION  "Forward Route Lookup Failed" 
		::={ acosCgnv6Lw4o6GlobalS 7 } 

		revLookupFailed OBJECT-TYPE
		SYNTAX  CounterBasedGauge64 
		MAX-ACCESS read-only 
		STATUS current
		DESCRIPTION  "Reverse Route Lookup Failed" 
		::={ acosCgnv6Lw4o6GlobalS 8 } 

		interfaceNotConfigured OBJECT-TYPE
		SYNTAX  CounterBasedGauge64 
		MAX-ACCESS read-only 
		STATUS current
		DESCRIPTION  "LW-4over6 Interfaces not Configured Drops" 
		::={ acosCgnv6Lw4o6GlobalS 9 } 

		noBindingTableMatchesFwd OBJECT-TYPE
		SYNTAX  CounterBasedGauge64 
		MAX-ACCESS read-only 
		STATUS current
		DESCRIPTION  "No Forward Binding Table Entry Match Drops" 
		::={ acosCgnv6Lw4o6GlobalS 10 } 

		noBindingTableMatchesRev OBJECT-TYPE
		SYNTAX  CounterBasedGauge64 
		MAX-ACCESS read-only 
		STATUS current
		DESCRIPTION  "No Reverse Binding Table Entry Match Drops" 
		::={ acosCgnv6Lw4o6GlobalS 11 } 

		sessionCount OBJECT-TYPE
		SYNTAX  CounterBasedGauge64 
		MAX-ACCESS read-only 
		STATUS current
		DESCRIPTION  "LW-4over6 Session Count" 
		::={ acosCgnv6Lw4o6GlobalS 12 } 

		systemAddressDrop OBJECT-TYPE
		SYNTAX  CounterBasedGauge64 
		MAX-ACCESS read-only 
		STATUS current
		DESCRIPTION  "LW-4over6 System Address Drops" 
		::={ acosCgnv6Lw4o6GlobalS 13 } 

acosCgnv6StatefulFirewall           OBJECT IDENTIFIER ::= { acosCgnv6 22 }
acosCgnv6StatefulFirewallGlobal     OBJECT IDENTIFIER ::= { acosCgnv6StatefulFirewall 1 }
acosCgnv6StatefulFirewallGlobalS    OBJECT IDENTIFIER ::= { acosCgnv6StatefulFirewallGlobal 1 }

		tcpPacketProcess OBJECT-TYPE
		SYNTAX  CounterBasedGauge64 
		MAX-ACCESS read-only 
		STATUS current
		DESCRIPTION  "TCP Packet Process" 
		::={ acosCgnv6StatefulFirewallGlobalS 1 } 

		udpPacketProcess OBJECT-TYPE
		SYNTAX  CounterBasedGauge64 
		MAX-ACCESS read-only 
		STATUS current
		DESCRIPTION  "UDP Packet Process" 
		::={ acosCgnv6StatefulFirewallGlobalS 2 } 

		otherPacketProcess OBJECT-TYPE
		SYNTAX  CounterBasedGauge64 
		MAX-ACCESS read-only 
		STATUS current
		DESCRIPTION  "Other Packet Process" 
		::={ acosCgnv6StatefulFirewallGlobalS 3 } 

		packetInboundDeny OBJECT-TYPE
		SYNTAX  CounterBasedGauge64 
		MAX-ACCESS read-only 
		STATUS current
		DESCRIPTION  "Inbound Packet Denied" 
		::={ acosCgnv6StatefulFirewallGlobalS 4 } 

		packetProcessFailure OBJECT-TYPE
		SYNTAX  CounterBasedGauge64 
		MAX-ACCESS read-only 
		STATUS current
		DESCRIPTION  "Packet Error Drop" 
		::={ acosCgnv6StatefulFirewallGlobalS 5 } 

		outboundSessionCreated OBJECT-TYPE
		SYNTAX  CounterBasedGauge64 
		MAX-ACCESS read-only 
		STATUS current
		DESCRIPTION  "Outbound Session Created" 
		::={ acosCgnv6StatefulFirewallGlobalS 6 } 

		outboundSessionFreed OBJECT-TYPE
		SYNTAX  CounterBasedGauge64 
		MAX-ACCESS read-only 
		STATUS current
		DESCRIPTION  "Outbound Session Freed" 
		::={ acosCgnv6StatefulFirewallGlobalS 7 } 

		inboundSessionCreated OBJECT-TYPE
		SYNTAX  CounterBasedGauge64 
		MAX-ACCESS read-only 
		STATUS current
		DESCRIPTION  "Inbound Session Created" 
		::={ acosCgnv6StatefulFirewallGlobalS 8 } 

		inboundSessionFreed OBJECT-TYPE
		SYNTAX  CounterBasedGauge64 
		MAX-ACCESS read-only 
		STATUS current
		DESCRIPTION  "Inbound Session Freed" 
		::={ acosCgnv6StatefulFirewallGlobalS 9 } 

		cgnv6StateFullFirewallGlobalTcpSessionCreated OBJECT-TYPE
		SYNTAX  CounterBasedGauge64 
		MAX-ACCESS read-only 
		STATUS current
		DESCRIPTION  "TCP Session Created" 
		::={ acosCgnv6StatefulFirewallGlobalS 10 } 

		tcpSessionFreed OBJECT-TYPE
		SYNTAX  CounterBasedGauge64 
		MAX-ACCESS read-only 
		STATUS current
		DESCRIPTION  "TCP Session Freed" 
		::={ acosCgnv6StatefulFirewallGlobalS 11 } 

		cgnv6StateFullFirewallGlobalUdpSessionCreated OBJECT-TYPE
		SYNTAX  CounterBasedGauge64 
		MAX-ACCESS read-only 
		STATUS current
		DESCRIPTION  "UDP Session Created" 
		::={ acosCgnv6StatefulFirewallGlobalS 12 } 

		udpSessionFreed OBJECT-TYPE
		SYNTAX  CounterBasedGauge64 
		MAX-ACCESS read-only 
		STATUS current
		DESCRIPTION  "UDP Session Freed" 
		::={ acosCgnv6StatefulFirewallGlobalS 13 } 

		otherSessionCreated OBJECT-TYPE
		SYNTAX  CounterBasedGauge64 
		MAX-ACCESS read-only 
		STATUS current
		DESCRIPTION  "Other Session Created" 
		::={ acosCgnv6StatefulFirewallGlobalS 14 } 

		otherSessionFreed OBJECT-TYPE
		SYNTAX  CounterBasedGauge64 
		MAX-ACCESS read-only 
		STATUS current
		DESCRIPTION  "Other Session Freed" 
		::={ acosCgnv6StatefulFirewallGlobalS 15 } 

		sessionCreationFailure OBJECT-TYPE
		SYNTAX  CounterBasedGauge64 
		MAX-ACCESS read-only 
		STATUS current
		DESCRIPTION  "Session Creation Failure" 
		::={ acosCgnv6StatefulFirewallGlobalS 16 } 

		cgnv6StateFullFirewallGlobalNoFwdRoute OBJECT-TYPE
		SYNTAX  CounterBasedGauge64 
		MAX-ACCESS read-only 
		STATUS current
		DESCRIPTION  "No Forward Route" 
		::={ acosCgnv6StatefulFirewallGlobalS 17 } 

		cgnv6StateFullFirewallGlobalNoRevRoute OBJECT-TYPE
		SYNTAX  CounterBasedGauge64 
		MAX-ACCESS read-only 
		STATUS current
		DESCRIPTION  "No Reverse Route" 
		::={ acosCgnv6StatefulFirewallGlobalS 18 } 

		packetStandbyDrop OBJECT-TYPE
		SYNTAX  CounterBasedGauge64 
		MAX-ACCESS read-only 
		STATUS current
		DESCRIPTION  "Standby Drop" 
		::={ acosCgnv6StatefulFirewallGlobalS 19 } 

		cgnv6StateFullFirewallGlobalTcpFullconeCreated OBJECT-TYPE
		SYNTAX  CounterBasedGauge64 
		MAX-ACCESS read-only 
		STATUS current
		DESCRIPTION  "TCP Full-cone Created" 
		::={ acosCgnv6StatefulFirewallGlobalS 20 } 

		cgnv6StateFullFirewallGlobalTcpFullconeFreed OBJECT-TYPE
		SYNTAX  CounterBasedGauge64 
		MAX-ACCESS read-only 
		STATUS current
		DESCRIPTION  "TCP Full-cone Freed" 
		::={ acosCgnv6StatefulFirewallGlobalS 21 } 

		cgnv6StateFullFirewallGlobalUdpFullconeCreated OBJECT-TYPE
		SYNTAX  CounterBasedGauge64 
		MAX-ACCESS read-only 
		STATUS current
		DESCRIPTION  "UDP Full-cone Created" 
		::={ acosCgnv6StatefulFirewallGlobalS 22 } 

		cgnv6StateFullFirewallGlobalUdpFullconeFreed OBJECT-TYPE
		SYNTAX  CounterBasedGauge64 
		MAX-ACCESS read-only 
		STATUS current
		DESCRIPTION  "UDP Full-cone Freed" 
		::={ acosCgnv6StatefulFirewallGlobalS 23 } 

		fullconeCreationFailure OBJECT-TYPE
		SYNTAX  CounterBasedGauge64 
		MAX-ACCESS read-only 
		STATUS current
		DESCRIPTION  "Full-Cone Creation Failure" 
		::={ acosCgnv6StatefulFirewallGlobalS 24 } 

		eifProcess OBJECT-TYPE
		SYNTAX  CounterBasedGauge64 
		MAX-ACCESS read-only 
		STATUS current
		DESCRIPTION  "Endpnt-Independent Filter Matched" 
		::={ acosCgnv6StatefulFirewallGlobalS 25 } 

		oneArmDrop OBJECT-TYPE
		SYNTAX  CounterBasedGauge64 
		MAX-ACCESS read-only 
		STATUS current
		DESCRIPTION  "One-Arm Drop" 
		::={ acosCgnv6StatefulFirewallGlobalS 26 } 

		cgnv6StatefullFirewallGlobalNoClassListMatch OBJECT-TYPE
		SYNTAX  CounterBasedGauge64 
		MAX-ACCESS read-only 
		STATUS current
		DESCRIPTION  "No Class-List Match Drop" 
		::={ acosCgnv6StatefulFirewallGlobalS 27 } 

		outboundSessionCreatedShadow OBJECT-TYPE
		SYNTAX  CounterBasedGauge64 
		MAX-ACCESS read-only 
		STATUS current
		DESCRIPTION  "Outbound Session Created Shadow" 
		::={ acosCgnv6StatefulFirewallGlobalS 28 } 

		outboundSessionFreedShadow OBJECT-TYPE
		SYNTAX  CounterBasedGauge64 
		MAX-ACCESS read-only 
		STATUS current
		DESCRIPTION  "Outbound Session Freed Shadow" 
		::={ acosCgnv6StatefulFirewallGlobalS 29 } 

		inboundSessionCreatedShadow OBJECT-TYPE
		SYNTAX  CounterBasedGauge64 
		MAX-ACCESS read-only 
		STATUS current
		DESCRIPTION  "Inbound Session Created Shadow" 
		::={ acosCgnv6StatefulFirewallGlobalS 30 } 

		inboundSessionFreedShadow OBJECT-TYPE
		SYNTAX  CounterBasedGauge64 
		MAX-ACCESS read-only 
		STATUS current
		DESCRIPTION  "Inbound Session Freed Shadow" 
		::={ acosCgnv6StatefulFirewallGlobalS 31 } 

		tcpSessionCreatedShadow OBJECT-TYPE
		SYNTAX  CounterBasedGauge64 
		MAX-ACCESS read-only 
		STATUS current
		DESCRIPTION  "TCP Session Created Shadow" 
		::={ acosCgnv6StatefulFirewallGlobalS 32 } 

		tcpSessionFreedShadow OBJECT-TYPE
		SYNTAX  CounterBasedGauge64 
		MAX-ACCESS read-only 
		STATUS current
		DESCRIPTION  "TCP Session Freed Shadow" 
		::={ acosCgnv6StatefulFirewallGlobalS 33 } 

		udpSessionCreatedShadow OBJECT-TYPE
		SYNTAX  CounterBasedGauge64 
		MAX-ACCESS read-only 
		STATUS current
		DESCRIPTION  "UDP Session Created Shadow" 
		::={ acosCgnv6StatefulFirewallGlobalS 34 } 

		udpSessionFreedShadow OBJECT-TYPE
		SYNTAX  CounterBasedGauge64 
		MAX-ACCESS read-only 
		STATUS current
		DESCRIPTION  "UDP Session Freed Shadow" 
		::={ acosCgnv6StatefulFirewallGlobalS 35 } 

		otherSessionCreatedShadow OBJECT-TYPE
		SYNTAX  CounterBasedGauge64 
		MAX-ACCESS read-only 
		STATUS current
		DESCRIPTION  "Other Session Created Shadow" 
		::={ acosCgnv6StatefulFirewallGlobalS 36 } 

		otherSessionFreedShadow OBJECT-TYPE
		SYNTAX  CounterBasedGauge64 
		MAX-ACCESS read-only 
		STATUS current
		DESCRIPTION  "Other Session Freed Shadow" 
		::={ acosCgnv6StatefulFirewallGlobalS 37 } 

		sessionCreationFailureShadow OBJECT-TYPE
		SYNTAX  CounterBasedGauge64 
		MAX-ACCESS read-only 
		STATUS current
		DESCRIPTION  "Session Creation Failure Shadow" 
		::={ acosCgnv6StatefulFirewallGlobalS 38 } 

		badSessionFreed OBJECT-TYPE
		SYNTAX  CounterBasedGauge64 
		MAX-ACCESS read-only 
		STATUS current
		DESCRIPTION  "Bad Session Proto on Free" 
		::={ acosCgnv6StatefulFirewallGlobalS 39 } 

		ctlMemAlloc OBJECT-TYPE
		SYNTAX  CounterBasedGauge64 
		MAX-ACCESS read-only 
		STATUS current
		DESCRIPTION  "Memory Alloc" 
		::={ acosCgnv6StatefulFirewallGlobalS 40 } 

		ctlMemFree OBJECT-TYPE
		SYNTAX  CounterBasedGauge64 
		MAX-ACCESS read-only 
		STATUS current
		DESCRIPTION  "Memory Free" 
		::={ acosCgnv6StatefulFirewallGlobalS 41 } 

		tcpFullconeCreatedShadow OBJECT-TYPE
		SYNTAX  CounterBasedGauge64 
		MAX-ACCESS read-only 
		STATUS current
		DESCRIPTION  "TCP Full-cone Created Shadow" 
		::={ acosCgnv6StatefulFirewallGlobalS 42 } 

		tcpFullconeFreedShadow OBJECT-TYPE
		SYNTAX  CounterBasedGauge64 
		MAX-ACCESS read-only 
		STATUS current
		DESCRIPTION  "TCP Full-cone Freed Shadow" 
		::={ acosCgnv6StatefulFirewallGlobalS 43 } 

		udpFullconeCreatedShadow OBJECT-TYPE
		SYNTAX  CounterBasedGauge64 
		MAX-ACCESS read-only 
		STATUS current
		DESCRIPTION  "UDP Full-cone Created Shadow" 
		::={ acosCgnv6StatefulFirewallGlobalS 44 } 

		udpFullconeFreedShadow OBJECT-TYPE
		SYNTAX  CounterBasedGauge64 
		MAX-ACCESS read-only 
		STATUS current
		DESCRIPTION  "UDP Full-cone Freed Shadow" 
		::={ acosCgnv6StatefulFirewallGlobalS 45 } 

		fullconeInDelQ OBJECT-TYPE
		SYNTAX  CounterBasedGauge64 
		MAX-ACCESS read-only 
		STATUS current
		DESCRIPTION  "Full-cone Found in Delete Queue" 
		::={ acosCgnv6StatefulFirewallGlobalS 46 } 

		fullconeOverflowEim OBJECT-TYPE
		SYNTAX  CounterBasedGauge64 
		MAX-ACCESS read-only 
		STATUS current
		DESCRIPTION  "EIM Overflow" 
		::={ acosCgnv6StatefulFirewallGlobalS 47 } 

		fullconeOverflowEif OBJECT-TYPE
		SYNTAX  CounterBasedGauge64 
		MAX-ACCESS read-only 
		STATUS current
		DESCRIPTION  "EIF Overflow" 
		::={ acosCgnv6StatefulFirewallGlobalS 48 } 

		fullconeFreeFound OBJECT-TYPE
		SYNTAX  CounterBasedGauge64 
		MAX-ACCESS read-only 
		STATUS current
		DESCRIPTION  "Full-cone Free Found From Conn" 
		::={ acosCgnv6StatefulFirewallGlobalS 49 } 

		fullconeFreeRetryLookup OBJECT-TYPE
		SYNTAX  CounterBasedGauge64 
		MAX-ACCESS read-only 
		STATUS current
		DESCRIPTION  "Full-cone Retry Look-up" 
		::={ acosCgnv6StatefulFirewallGlobalS 50 } 

		fullconeFreeNotFound OBJECT-TYPE
		SYNTAX  CounterBasedGauge64 
		MAX-ACCESS read-only 
		STATUS current
		DESCRIPTION  "Full-cone Free Not Found" 
		::={ acosCgnv6StatefulFirewallGlobalS 51 } 

		eifLimitExceeded OBJECT-TYPE
		SYNTAX  CounterBasedGauge64 
		MAX-ACCESS read-only 
		STATUS current
		DESCRIPTION  "EIF Limit Exceeded" 
		::={ acosCgnv6StatefulFirewallGlobalS 52 } 

		eifDisableDrop OBJECT-TYPE
		SYNTAX  CounterBasedGauge64 
		MAX-ACCESS read-only 
		STATUS current
		DESCRIPTION  "EIF Disable Drop" 
		::={ acosCgnv6StatefulFirewallGlobalS 53 } 

		eifProcessFailure OBJECT-TYPE
		SYNTAX  CounterBasedGauge64 
		MAX-ACCESS read-only 
		STATUS current
		DESCRIPTION  "EIF Process Failure" 
		::={ acosCgnv6StatefulFirewallGlobalS 54 } 

		eifFiltered OBJECT-TYPE
		SYNTAX  CounterBasedGauge64 
		MAX-ACCESS read-only 
		STATUS current
		DESCRIPTION  "EIF Filtered" 
		::={ acosCgnv6StatefulFirewallGlobalS 55 } 

		haStandbySessionCreated OBJECT-TYPE
		SYNTAX  CounterBasedGauge64 
		MAX-ACCESS read-only 
		STATUS current
		DESCRIPTION  "HA Standby Session Created" 
		::={ acosCgnv6StatefulFirewallGlobalS 56 } 

		haStandbySessionEim OBJECT-TYPE
		SYNTAX  CounterBasedGauge64 
		MAX-ACCESS read-only 
		STATUS current
		DESCRIPTION  "HA Standby Session EIM" 
		::={ acosCgnv6StatefulFirewallGlobalS 57 } 

		haStandbySessionEif OBJECT-TYPE
		SYNTAX  CounterBasedGauge64 
		MAX-ACCESS read-only 
		STATUS current
		DESCRIPTION  "HA Standby Session EIF" 
		::={ acosCgnv6StatefulFirewallGlobalS 58 } 

acosCgnv6StatefulFirewallAlg        OBJECT IDENTIFIER ::= { acosCgnv6StatefulFirewall 2 }
acosCgnv6StatefulFirewallAlgFtp     OBJECT IDENTIFIER ::= { acosCgnv6StatefulFirewallAlg 1 }
acosCgnv6StatefulFirewallAlgFtpS    OBJECT IDENTIFIER ::= { acosCgnv6StatefulFirewallAlgFtp 1 }

		clientPortRequest OBJECT-TYPE
		SYNTAX  CounterBasedGauge64 
		MAX-ACCESS read-only 
		STATUS current
		DESCRIPTION  "PORT Requests From Client" 
		::={ acosCgnv6StatefulFirewallAlgFtpS 1 } 

		clientEprtRequest OBJECT-TYPE
		SYNTAX  CounterBasedGauge64 
		MAX-ACCESS read-only 
		STATUS current
		DESCRIPTION  "EPRT Requests From Client" 
		::={ acosCgnv6StatefulFirewallAlgFtpS 2 } 

		serverPasvReply OBJECT-TYPE
		SYNTAX  CounterBasedGauge64 
		MAX-ACCESS read-only 
		STATUS current
		DESCRIPTION  "PASV Replies From Server" 
		::={ acosCgnv6StatefulFirewallAlgFtpS 3 } 

		serverEpsvReply OBJECT-TYPE
		SYNTAX  CounterBasedGauge64 
		MAX-ACCESS read-only 
		STATUS current
		DESCRIPTION  "EPSV Replies From Server" 
		::={ acosCgnv6StatefulFirewallAlgFtpS 4 } 

		portRetransmits OBJECT-TYPE
		SYNTAX  CounterBasedGauge64 
		MAX-ACCESS read-only 
		STATUS current
		DESCRIPTION  "PORT Retransmits" 
		::={ acosCgnv6StatefulFirewallAlgFtpS 5 } 

		pasvRetransmits OBJECT-TYPE
		SYNTAX  CounterBasedGauge64 
		MAX-ACCESS read-only 
		STATUS current
		DESCRIPTION  "PASV Retransmits" 
		::={ acosCgnv6StatefulFirewallAlgFtpS 6 } 

		smpAppTypeMismatch OBJECT-TYPE
		SYNTAX  CounterBasedGauge64 
		MAX-ACCESS read-only 
		STATUS current
		DESCRIPTION  "SMP App Type Mismatch" 
		::={ acosCgnv6StatefulFirewallAlgFtpS 7 } 

		retransmitSanityCheckFailure OBJECT-TYPE
		SYNTAX  CounterBasedGauge64 
		MAX-ACCESS read-only 
		STATUS current
		DESCRIPTION  "Retransmit Sanity Check Failure" 
		::={ acosCgnv6StatefulFirewallAlgFtpS 8 } 

		smpConnAllocFailure OBJECT-TYPE
		SYNTAX  CounterBasedGauge64 
		MAX-ACCESS read-only 
		STATUS current
		DESCRIPTION  "SMP Helper Conn Alloc Failure" 
		::={ acosCgnv6StatefulFirewallAlgFtpS 9 } 

		portHelperCreated OBJECT-TYPE
		SYNTAX  CounterBasedGauge64 
		MAX-ACCESS read-only 
		STATUS current
		DESCRIPTION  "PORT Helper Created" 
		::={ acosCgnv6StatefulFirewallAlgFtpS 10 } 

		pasvHelperCreated OBJECT-TYPE
		SYNTAX  CounterBasedGauge64 
		MAX-ACCESS read-only 
		STATUS current
		DESCRIPTION  "PASV Helper Created" 
		::={ acosCgnv6StatefulFirewallAlgFtpS 11 } 

		portHelperAcquireInDelQ OBJECT-TYPE
		SYNTAX  CounterBasedGauge64 
		MAX-ACCESS read-only 
		STATUS current
		DESCRIPTION  "PORT Helper Acquire In Del Queue" 
		::={ acosCgnv6StatefulFirewallAlgFtpS 12 } 

		portHelperAcquireAlreadyUsed OBJECT-TYPE
		SYNTAX  CounterBasedGauge64 
		MAX-ACCESS read-only 
		STATUS current
		DESCRIPTION  "PORT Helper Acquire Already Used" 
		::={ acosCgnv6StatefulFirewallAlgFtpS 13 } 

		pasvHelperAcquireInDelQ OBJECT-TYPE
		SYNTAX  CounterBasedGauge64 
		MAX-ACCESS read-only 
		STATUS current
		DESCRIPTION  "PASV Helper Acquire In Del Queue" 
		::={ acosCgnv6StatefulFirewallAlgFtpS 14 } 

		pasvHelperAcquireAlreadyUsed OBJECT-TYPE
		SYNTAX  CounterBasedGauge64 
		MAX-ACCESS read-only 
		STATUS current
		DESCRIPTION  "PASV Helper Acquire Already Used" 
		::={ acosCgnv6StatefulFirewallAlgFtpS 15 } 

		portHelperFreedUsed OBJECT-TYPE
		SYNTAX  CounterBasedGauge64 
		MAX-ACCESS read-only 
		STATUS current
		DESCRIPTION  "PORT Helper Freed Used" 
		::={ acosCgnv6StatefulFirewallAlgFtpS 16 } 

		portHelperFreedUnused OBJECT-TYPE
		SYNTAX  CounterBasedGauge64 
		MAX-ACCESS read-only 
		STATUS current
		DESCRIPTION  "PORT Helper Freed Unused" 
		::={ acosCgnv6StatefulFirewallAlgFtpS 17 } 

		pasvHelperFreedUsed OBJECT-TYPE
		SYNTAX  CounterBasedGauge64 
		MAX-ACCESS read-only 
		STATUS current
		DESCRIPTION  "PASV Helper Freed Used" 
		::={ acosCgnv6StatefulFirewallAlgFtpS 18 } 

		pasvHelperFreedUnused OBJECT-TYPE
		SYNTAX  CounterBasedGauge64 
		MAX-ACCESS read-only 
		STATUS current
		DESCRIPTION  "PASV Helper Freed Unused" 
		::={ acosCgnv6StatefulFirewallAlgFtpS 19 } 

acosCgnv6StatefulFirewallAlgPptp    OBJECT IDENTIFIER ::= { acosCgnv6StatefulFirewallAlg 2 }
acosCgnv6StatefulFirewallAlgPptpS   OBJECT IDENTIFIER ::= { acosCgnv6StatefulFirewallAlgPptp 1 }

		callsEstablished OBJECT-TYPE
		SYNTAX  CounterBasedGauge64 
		MAX-ACCESS read-only 
		STATUS current
		DESCRIPTION  "Calls Established" 
		::={ acosCgnv6StatefulFirewallAlgPptpS 1 } 

		callReqPnsCallIdMismatch OBJECT-TYPE
		SYNTAX  CounterBasedGauge64 
		MAX-ACCESS read-only 
		STATUS current
		DESCRIPTION  "Call ID Mismatch on Call Request" 
		::={ acosCgnv6StatefulFirewallAlgPptpS 2 } 

		callReplyPnsCallIdMismatch OBJECT-TYPE
		SYNTAX  CounterBasedGauge64 
		MAX-ACCESS read-only 
		STATUS current
		DESCRIPTION  "Call ID Mismatch on Call Reply" 
		::={ acosCgnv6StatefulFirewallAlgPptpS 3 } 

		greSessionCreated OBJECT-TYPE
		SYNTAX  CounterBasedGauge64 
		MAX-ACCESS read-only 
		STATUS current
		DESCRIPTION  "GRE Session Created" 
		::={ acosCgnv6StatefulFirewallAlgPptpS 4 } 

		greSessionFreed OBJECT-TYPE
		SYNTAX  CounterBasedGauge64 
		MAX-ACCESS read-only 
		STATUS current
		DESCRIPTION  "GRE Session Freed" 
		::={ acosCgnv6StatefulFirewallAlgPptpS 5 } 

		callReqRetransmit OBJECT-TYPE
		SYNTAX  CounterBasedGauge64 
		MAX-ACCESS read-only 
		STATUS current
		DESCRIPTION  "Call Request Retransmit" 
		::={ acosCgnv6StatefulFirewallAlgPptpS 6 } 

		callReqNew OBJECT-TYPE
		SYNTAX  CounterBasedGauge64 
		MAX-ACCESS read-only 
		STATUS current
		DESCRIPTION  "Call Request New" 
		::={ acosCgnv6StatefulFirewallAlgPptpS 7 } 

		callReqExtAllocFailure OBJECT-TYPE
		SYNTAX  CounterBasedGauge64 
		MAX-ACCESS read-only 
		STATUS current
		DESCRIPTION  "Call Request Ext Alloc Failure" 
		::={ acosCgnv6StatefulFirewallAlgPptpS 8 } 

		callReplyCallIdUnknown OBJECT-TYPE
		SYNTAX  CounterBasedGauge64 
		MAX-ACCESS read-only 
		STATUS current
		DESCRIPTION  "Call Reply Unknown Client Call ID" 
		::={ acosCgnv6StatefulFirewallAlgPptpS 9 } 

		callReplyRetransmit OBJECT-TYPE
		SYNTAX  CounterBasedGauge64 
		MAX-ACCESS read-only 
		STATUS current
		DESCRIPTION  "Call Reply Retransmit" 
		::={ acosCgnv6StatefulFirewallAlgPptpS 10 } 

		callReplyExtExtAllocFailure OBJECT-TYPE
		SYNTAX  CounterBasedGauge64 
		MAX-ACCESS read-only 
		STATUS current
		DESCRIPTION  "Call Request Ext Alloc Failure" 
		::={ acosCgnv6StatefulFirewallAlgPptpS 11 } 

		smpAppTypeMismatch OBJECT-TYPE
		SYNTAX  CounterBasedGauge64 
		MAX-ACCESS read-only 
		STATUS current
		DESCRIPTION  "SMP App Type Mismatch" 
		::={ acosCgnv6StatefulFirewallAlgPptpS 12 } 

		smpClientCallIdMismatch OBJECT-TYPE
		SYNTAX  CounterBasedGauge64 
		MAX-ACCESS read-only 
		STATUS current
		DESCRIPTION  "SMP Client Call ID Mismatch" 
		::={ acosCgnv6StatefulFirewallAlgPptpS 13 } 

		smpSessionsCreated OBJECT-TYPE
		SYNTAX  CounterBasedGauge64 
		MAX-ACCESS read-only 
		STATUS current
		DESCRIPTION  "SMP Session Created" 
		::={ acosCgnv6StatefulFirewallAlgPptpS 14 } 

		smpSessionsFreed OBJECT-TYPE
		SYNTAX  CounterBasedGauge64 
		MAX-ACCESS read-only 
		STATUS current
		DESCRIPTION  "SMP Session Freed" 
		::={ acosCgnv6StatefulFirewallAlgPptpS 15 } 

		smpAllocFailure OBJECT-TYPE
		SYNTAX  CounterBasedGauge64 
		MAX-ACCESS read-only 
		STATUS current
		DESCRIPTION  "SMP Session Alloc Failure" 
		::={ acosCgnv6StatefulFirewallAlgPptpS 16 } 

		greConnCreationFailure OBJECT-TYPE
		SYNTAX  CounterBasedGauge64 
		MAX-ACCESS read-only 
		STATUS current
		DESCRIPTION  "GRE Conn Alloc Failure" 
		::={ acosCgnv6StatefulFirewallAlgPptpS 17 } 

		greConnExtCreationFailure OBJECT-TYPE
		SYNTAX  CounterBasedGauge64 
		MAX-ACCESS read-only 
		STATUS current
		DESCRIPTION  "GRE Conn Ext Alloc Failure" 
		::={ acosCgnv6StatefulFirewallAlgPptpS 18 } 

		greNoFwdRoute OBJECT-TYPE
		SYNTAX  CounterBasedGauge64 
		MAX-ACCESS read-only 
		STATUS current
		DESCRIPTION  "GRE No Fwd Route" 
		::={ acosCgnv6StatefulFirewallAlgPptpS 19 } 

		greNoRevRoute OBJECT-TYPE
		SYNTAX  CounterBasedGauge64 
		MAX-ACCESS read-only 
		STATUS current
		DESCRIPTION  "GRE No Rev Route" 
		::={ acosCgnv6StatefulFirewallAlgPptpS 20 } 

		greNoControlConn OBJECT-TYPE
		SYNTAX  CounterBasedGauge64 
		MAX-ACCESS read-only 
		STATUS current
		DESCRIPTION  "GRE No Control Conn" 
		::={ acosCgnv6StatefulFirewallAlgPptpS 21 } 

		greConnAlreadyExists OBJECT-TYPE
		SYNTAX  CounterBasedGauge64 
		MAX-ACCESS read-only 
		STATUS current
		DESCRIPTION  "GRE Conn Already Exists" 
		::={ acosCgnv6StatefulFirewallAlgPptpS 22 } 

		greFreeNoExt OBJECT-TYPE
		SYNTAX  CounterBasedGauge64 
		MAX-ACCESS read-only 
		STATUS current
		DESCRIPTION  "GRE Free No Ext" 
		::={ acosCgnv6StatefulFirewallAlgPptpS 23 } 

		greFreeNoSmp OBJECT-TYPE
		SYNTAX  CounterBasedGauge64 
		MAX-ACCESS read-only 
		STATUS current
		DESCRIPTION  "GRE Free No SMP" 
		::={ acosCgnv6StatefulFirewallAlgPptpS 24 } 

		greFreeSmpAppTypeMismatch OBJECT-TYPE
		SYNTAX  CounterBasedGauge64 
		MAX-ACCESS read-only 
		STATUS current
		DESCRIPTION  "GRE Free SMP App Type Mismatch" 
		::={ acosCgnv6StatefulFirewallAlgPptpS 25 } 

		controlFreed OBJECT-TYPE
		SYNTAX  CounterBasedGauge64 
		MAX-ACCESS read-only 
		STATUS current
		DESCRIPTION  "Control Session Freed" 
		::={ acosCgnv6StatefulFirewallAlgPptpS 26 } 

		controlFreeNoExt OBJECT-TYPE
		SYNTAX  CounterBasedGauge64 
		MAX-ACCESS read-only 
		STATUS current
		DESCRIPTION  "Control Free No Ext" 
		::={ acosCgnv6StatefulFirewallAlgPptpS 27 } 

		controlFreeNoSmp OBJECT-TYPE
		SYNTAX  CounterBasedGauge64 
		MAX-ACCESS read-only 
		STATUS current
		DESCRIPTION  "Control Free No SMP" 
		::={ acosCgnv6StatefulFirewallAlgPptpS 28 } 

		controlFreeSmpAppTypeMismatch OBJECT-TYPE
		SYNTAX  CounterBasedGauge64 
		MAX-ACCESS read-only 
		STATUS current
		DESCRIPTION  "Control Free SMP App Type Mismatch" 
		::={ acosCgnv6StatefulFirewallAlgPptpS 29 } 

acosCgnv6StatefulFirewallAlgRtsp    OBJECT IDENTIFIER ::= { acosCgnv6StatefulFirewallAlg 4 }
acosCgnv6StatefulFirewallAlgRtspS   OBJECT IDENTIFIER ::= { acosCgnv6StatefulFirewallAlgRtsp 1 }

		transportInserted OBJECT-TYPE
		SYNTAX  CounterBasedGauge64 
		MAX-ACCESS read-only 
		STATUS current
		DESCRIPTION  "Transport Created" 
		::={ acosCgnv6StatefulFirewallAlgRtspS 1 } 

		transportFreed OBJECT-TYPE
		SYNTAX  CounterBasedGauge64 
		MAX-ACCESS read-only 
		STATUS current
		DESCRIPTION  "Transport Freed" 
		::={ acosCgnv6StatefulFirewallAlgRtspS 2 } 

		transportAllocFailure OBJECT-TYPE
		SYNTAX  CounterBasedGauge64 
		MAX-ACCESS read-only 
		STATUS current
		DESCRIPTION  "Transport Alloc Failure" 
		::={ acosCgnv6StatefulFirewallAlgRtspS 3 } 

		cgnv6StatefullFireWallAlgRtspDataSessionCreated OBJECT-TYPE
		SYNTAX  CounterBasedGauge64 
		MAX-ACCESS read-only 
		STATUS current
		DESCRIPTION  "Data Session Created" 
		::={ acosCgnv6StatefulFirewallAlgRtspS 4 } 

		cgnv6StatefullFireWallAlgRtspDataSessionFreed OBJECT-TYPE
		SYNTAX  CounterBasedGauge64 
		MAX-ACCESS read-only 
		STATUS current
		DESCRIPTION  "Data Session Freed" 
		::={ acosCgnv6StatefulFirewallAlgRtspS 5 } 

		extCreationFailure OBJECT-TYPE
		SYNTAX  CounterBasedGauge64 
		MAX-ACCESS read-only 
		STATUS current
		DESCRIPTION  "Extension Creation Failure" 
		::={ acosCgnv6StatefulFirewallAlgRtspS 6 } 

		transportAddToExt OBJECT-TYPE
		SYNTAX  CounterBasedGauge64 
		MAX-ACCESS read-only 
		STATUS current
		DESCRIPTION  "Transport Added to Extension" 
		::={ acosCgnv6StatefulFirewallAlgRtspS 7 } 

		transportRemovedFromExt OBJECT-TYPE
		SYNTAX  CounterBasedGauge64 
		MAX-ACCESS read-only 
		STATUS current
		DESCRIPTION  "Transport Removed from Extension" 
		::={ acosCgnv6StatefulFirewallAlgRtspS 8 } 

		transportTooMany OBJECT-TYPE
		SYNTAX  CounterBasedGauge64 
		MAX-ACCESS read-only 
		STATUS current
		DESCRIPTION  "Too Many Transports for Control Conn" 
		::={ acosCgnv6StatefulFirewallAlgRtspS 9 } 

		transportAlreadyInExt OBJECT-TYPE
		SYNTAX  CounterBasedGauge64 
		MAX-ACCESS read-only 
		STATUS current
		DESCRIPTION  "Transport Already in Extension" 
		::={ acosCgnv6StatefulFirewallAlgRtspS 10 } 

		transportExists OBJECT-TYPE
		SYNTAX  CounterBasedGauge64 
		MAX-ACCESS read-only 
		STATUS current
		DESCRIPTION  "Transport Already Exists" 
		::={ acosCgnv6StatefulFirewallAlgRtspS 11 } 

		transportLinkExtFailureControl OBJECT-TYPE
		SYNTAX  CounterBasedGauge64 
		MAX-ACCESS read-only 
		STATUS current
		DESCRIPTION  "Transport Link to Extension Failure Control" 
		::={ acosCgnv6StatefulFirewallAlgRtspS 12 } 

		transportLinkExtData OBJECT-TYPE
		SYNTAX  CounterBasedGauge64 
		MAX-ACCESS read-only 
		STATUS current
		DESCRIPTION  "Transport Link to Extension Data" 
		::={ acosCgnv6StatefulFirewallAlgRtspS 13 } 

		transportLinkExtFailureData OBJECT-TYPE
		SYNTAX  CounterBasedGauge64 
		MAX-ACCESS read-only 
		STATUS current
		DESCRIPTION  "Transport Link to Extension Failure Data" 
		::={ acosCgnv6StatefulFirewallAlgRtspS 14 } 

		transportInsertedShadow OBJECT-TYPE
		SYNTAX  CounterBasedGauge64 
		MAX-ACCESS read-only 
		STATUS current
		DESCRIPTION  "Transport Inserted Shadow" 
		::={ acosCgnv6StatefulFirewallAlgRtspS 15 } 

		transportCreationRace OBJECT-TYPE
		SYNTAX  CounterBasedGauge64 
		MAX-ACCESS read-only 
		STATUS current
		DESCRIPTION  "Transport Create Race" 
		::={ acosCgnv6StatefulFirewallAlgRtspS 16 } 

		transportAllocFailureShadow OBJECT-TYPE
		SYNTAX  CounterBasedGauge64 
		MAX-ACCESS read-only 
		STATUS current
		DESCRIPTION  "Transport Alloc Failure Shadow" 
		::={ acosCgnv6StatefulFirewallAlgRtspS 17 } 

		transportPutInDelQ OBJECT-TYPE
		SYNTAX  CounterBasedGauge64 
		MAX-ACCESS read-only 
		STATUS current
		DESCRIPTION  "Transport Put in Delete Queue" 
		::={ acosCgnv6StatefulFirewallAlgRtspS 18 } 

		transportFreedShadow OBJECT-TYPE
		SYNTAX  CounterBasedGauge64 
		MAX-ACCESS read-only 
		STATUS current
		DESCRIPTION  "Transport Freed Shadow" 
		::={ acosCgnv6StatefulFirewallAlgRtspS 19 } 

		transportAcquiredFromControl OBJECT-TYPE
		SYNTAX  CounterBasedGauge64 
		MAX-ACCESS read-only 
		STATUS current
		DESCRIPTION  "Transport Acquired Control" 
		::={ acosCgnv6StatefulFirewallAlgRtspS 20 } 

		transportFoundFromPrevControl OBJECT-TYPE
		SYNTAX  CounterBasedGauge64 
		MAX-ACCESS read-only 
		STATUS current
		DESCRIPTION  "Transport Found From Prev Control" 
		::={ acosCgnv6StatefulFirewallAlgRtspS 21 } 

		transportAcquireFailureFromControl OBJECT-TYPE
		SYNTAX  CounterBasedGauge64 
		MAX-ACCESS read-only 
		STATUS current
		DESCRIPTION  "Transport Acquire Failure Control" 
		::={ acosCgnv6StatefulFirewallAlgRtspS 22 } 

		transportReleasedFromControl OBJECT-TYPE
		SYNTAX  CounterBasedGauge64 
		MAX-ACCESS read-only 
		STATUS current
		DESCRIPTION  "Transport Released Control" 
		::={ acosCgnv6StatefulFirewallAlgRtspS 23 } 

		transportDoubleReleaseFromControl OBJECT-TYPE
		SYNTAX  CounterBasedGauge64 
		MAX-ACCESS read-only 
		STATUS current
		DESCRIPTION  "Transport Double Release Control" 
		::={ acosCgnv6StatefulFirewallAlgRtspS 24 } 

		transportAcquiredFromData OBJECT-TYPE
		SYNTAX  CounterBasedGauge64 
		MAX-ACCESS read-only 
		STATUS current
		DESCRIPTION  "Transport Acquired Data" 
		::={ acosCgnv6StatefulFirewallAlgRtspS 25 } 

		transportAcquireFailureFromData OBJECT-TYPE
		SYNTAX  CounterBasedGauge64 
		MAX-ACCESS read-only 
		STATUS current
		DESCRIPTION  "Transport Acquire Failure Data" 
		::={ acosCgnv6StatefulFirewallAlgRtspS 26 } 

		transportReleasedFromData OBJECT-TYPE
		SYNTAX  CounterBasedGauge64 
		MAX-ACCESS read-only 
		STATUS current
		DESCRIPTION  "Transport Released Data" 
		::={ acosCgnv6StatefulFirewallAlgRtspS 27 } 

		transportDoubleReleaseFromData OBJECT-TYPE
		SYNTAX  CounterBasedGauge64 
		MAX-ACCESS read-only 
		STATUS current
		DESCRIPTION  "Transport Double Release Data" 
		::={ acosCgnv6StatefulFirewallAlgRtspS 28 } 

		transportRetryLookupOnDataFree OBJECT-TYPE
		SYNTAX  CounterBasedGauge64 
		MAX-ACCESS read-only 
		STATUS current
		DESCRIPTION  "Transport Retry Lookup Data" 
		::={ acosCgnv6StatefulFirewallAlgRtspS 29 } 

		transportNotFoundOnDataFree OBJECT-TYPE
		SYNTAX  CounterBasedGauge64 
		MAX-ACCESS read-only 
		STATUS current
		DESCRIPTION  "Transport Not Found Data" 
		::={ acosCgnv6StatefulFirewallAlgRtspS 30 } 

		dataSessionCreatedShadow OBJECT-TYPE
		SYNTAX  CounterBasedGauge64 
		MAX-ACCESS read-only 
		STATUS current
		DESCRIPTION  "Data Session Created Shadow" 
		::={ acosCgnv6StatefulFirewallAlgRtspS 31 } 

		dataSessionFreedShadow OBJECT-TYPE
		SYNTAX  CounterBasedGauge64 
		MAX-ACCESS read-only 
		STATUS current
		DESCRIPTION  "Data Session Freed Shadow" 
		::={ acosCgnv6StatefulFirewallAlgRtspS 32 } 

		haControlExtCreationFailure OBJECT-TYPE
		SYNTAX  CounterBasedGauge64 
		MAX-ACCESS read-only 
		STATUS current
		DESCRIPTION  "HA Control Extension Creation Failure" 
		::={ acosCgnv6StatefulFirewallAlgRtspS 33 } 

		haControlSessionCreated OBJECT-TYPE
		SYNTAX  CounterBasedGauge64 
		MAX-ACCESS read-only 
		STATUS current
		DESCRIPTION  "HA Control Session Created" 
		::={ acosCgnv6StatefulFirewallAlgRtspS 34 } 

		haDataSessionCreated OBJECT-TYPE
		SYNTAX  CounterBasedGauge64 
		MAX-ACCESS read-only 
		STATUS current
		DESCRIPTION  "HA Data Session Created" 
		::={ acosCgnv6StatefulFirewallAlgRtspS 35 } 

acosCgnv6StatefulFirewallAlgSip     OBJECT IDENTIFIER ::= { acosCgnv6StatefulFirewallAlg 5 }
acosCgnv6StatefulFirewallAlgSipS    OBJECT IDENTIFIER ::= { acosCgnv6StatefulFirewallAlgSip 1 }

		statRequest OBJECT-TYPE
		SYNTAX  CounterBasedGauge64 
		MAX-ACCESS read-only 
		STATUS current
		DESCRIPTION  "Request Received" 
		::={ acosCgnv6StatefulFirewallAlgSipS 1 } 

		statResponse OBJECT-TYPE
		SYNTAX  CounterBasedGauge64 
		MAX-ACCESS read-only 
		STATUS current
		DESCRIPTION  "Response Received" 
		::={ acosCgnv6StatefulFirewallAlgSipS 2 } 

		methodRegister OBJECT-TYPE
		SYNTAX  CounterBasedGauge64 
		MAX-ACCESS read-only 
		STATUS current
		DESCRIPTION  "Method REGISTER" 
		::={ acosCgnv6StatefulFirewallAlgSipS 3 } 

		methodInvite OBJECT-TYPE
		SYNTAX  CounterBasedGauge64 
		MAX-ACCESS read-only 
		STATUS current
		DESCRIPTION  "Method INVITE" 
		::={ acosCgnv6StatefulFirewallAlgSipS 4 } 

		methodAck OBJECT-TYPE
		SYNTAX  CounterBasedGauge64 
		MAX-ACCESS read-only 
		STATUS current
		DESCRIPTION  "Method ACK" 
		::={ acosCgnv6StatefulFirewallAlgSipS 5 } 

		methodCancel OBJECT-TYPE
		SYNTAX  CounterBasedGauge64 
		MAX-ACCESS read-only 
		STATUS current
		DESCRIPTION  "Method CANCEL" 
		::={ acosCgnv6StatefulFirewallAlgSipS 6 } 

		methodBye OBJECT-TYPE
		SYNTAX  CounterBasedGauge64 
		MAX-ACCESS read-only 
		STATUS current
		DESCRIPTION  "Method BYE" 
		::={ acosCgnv6StatefulFirewallAlgSipS 7 } 

		methodPortConfig OBJECT-TYPE
		SYNTAX  CounterBasedGauge64 
		MAX-ACCESS read-only 
		STATUS current
		DESCRIPTION  "Method OPTIONS" 
		::={ acosCgnv6StatefulFirewallAlgSipS 8 } 

		methodPrack OBJECT-TYPE
		SYNTAX  CounterBasedGauge64 
		MAX-ACCESS read-only 
		STATUS current
		DESCRIPTION  "Method PRACK" 
		::={ acosCgnv6StatefulFirewallAlgSipS 9 } 

		methodSubscribe OBJECT-TYPE
		SYNTAX  CounterBasedGauge64 
		MAX-ACCESS read-only 
		STATUS current
		DESCRIPTION  "Method SUBSCRIBE" 
		::={ acosCgnv6StatefulFirewallAlgSipS 10 } 

		methodNotify OBJECT-TYPE
		SYNTAX  CounterBasedGauge64 
		MAX-ACCESS read-only 
		STATUS current
		DESCRIPTION  "Method NOTIFY" 
		::={ acosCgnv6StatefulFirewallAlgSipS 11 } 

		methodPublish OBJECT-TYPE
		SYNTAX  CounterBasedGauge64 
		MAX-ACCESS read-only 
		STATUS current
		DESCRIPTION  "Method PUBLISH" 
		::={ acosCgnv6StatefulFirewallAlgSipS 12 } 

		methodInfo OBJECT-TYPE
		SYNTAX  CounterBasedGauge64 
		MAX-ACCESS read-only 
		STATUS current
		DESCRIPTION  "Method INFO" 
		::={ acosCgnv6StatefulFirewallAlgSipS 13 } 

		methodRefer OBJECT-TYPE
		SYNTAX  CounterBasedGauge64 
		MAX-ACCESS read-only 
		STATUS current
		DESCRIPTION  "Method REFER" 
		::={ acosCgnv6StatefulFirewallAlgSipS 14 } 

		methodMessage OBJECT-TYPE
		SYNTAX  CounterBasedGauge64 
		MAX-ACCESS read-only 
		STATUS current
		DESCRIPTION  "Method MESSAGE" 
		::={ acosCgnv6StatefulFirewallAlgSipS 15 } 

		methodUpdate OBJECT-TYPE
		SYNTAX  CounterBasedGauge64 
		MAX-ACCESS read-only 
		STATUS current
		DESCRIPTION  "Method UPDATE" 
		::={ acosCgnv6StatefulFirewallAlgSipS 16 } 

		methodUnknown OBJECT-TYPE
		SYNTAX  CounterBasedGauge64 
		MAX-ACCESS read-only 
		STATUS current
		DESCRIPTION  "Method Unknown" 
		::={ acosCgnv6StatefulFirewallAlgSipS 17 } 

		parseError OBJECT-TYPE
		SYNTAX  CounterBasedGauge64 
		MAX-ACCESS read-only 
		STATUS current
		DESCRIPTION  "Message Parse Error" 
		::={ acosCgnv6StatefulFirewallAlgSipS 18 } 

		keepAlive OBJECT-TYPE
		SYNTAX  CounterBasedGauge64 
		MAX-ACCESS read-only 
		STATUS current
		DESCRIPTION  "Keep Alive" 
		::={ acosCgnv6StatefulFirewallAlgSipS 19 } 

		contactError OBJECT-TYPE
		SYNTAX  CounterBasedGauge64 
		MAX-ACCESS read-only 
		STATUS current
		DESCRIPTION  "Contact Process Error" 
		::={ acosCgnv6StatefulFirewallAlgSipS 20 } 

		sdpError OBJECT-TYPE
		SYNTAX  CounterBasedGauge64 
		MAX-ACCESS read-only 
		STATUS current
		DESCRIPTION  "SDP Process Error" 
		::={ acosCgnv6StatefulFirewallAlgSipS 21 } 

		rtpPortNoOp OBJECT-TYPE
		SYNTAX  CounterBasedGauge64 
		MAX-ACCESS read-only 
		STATUS current
		DESCRIPTION  "RTP Port No Op" 
		::={ acosCgnv6StatefulFirewallAlgSipS 22 } 

		rtpRtcpPortSuccess OBJECT-TYPE
		SYNTAX  CounterBasedGauge64 
		MAX-ACCESS read-only 
		STATUS current
		DESCRIPTION  "RTP RTCP Port Success" 
		::={ acosCgnv6StatefulFirewallAlgSipS 23 } 

		rtpPortFailure OBJECT-TYPE
		SYNTAX  CounterBasedGauge64 
		MAX-ACCESS read-only 
		STATUS current
		DESCRIPTION  "RTP Port Failure" 
		::={ acosCgnv6StatefulFirewallAlgSipS 24 } 

		rtcpPortFailure OBJECT-TYPE
		SYNTAX  CounterBasedGauge64 
		MAX-ACCESS read-only 
		STATUS current
		DESCRIPTION  "RTCP Port Failure" 
		::={ acosCgnv6StatefulFirewallAlgSipS 25 } 

		contactPortNoOp OBJECT-TYPE
		SYNTAX  CounterBasedGauge64 
		MAX-ACCESS read-only 
		STATUS current
		DESCRIPTION  "Contact Port No Op" 
		::={ acosCgnv6StatefulFirewallAlgSipS 26 } 

		contactPortSuccess OBJECT-TYPE
		SYNTAX  CounterBasedGauge64 
		MAX-ACCESS read-only 
		STATUS current
		DESCRIPTION  "Contact Port Success" 
		::={ acosCgnv6StatefulFirewallAlgSipS 27 } 

		contactPortFailure OBJECT-TYPE
		SYNTAX  CounterBasedGauge64 
		MAX-ACCESS read-only 
		STATUS current
		DESCRIPTION  "Contact Port Failure" 
		::={ acosCgnv6StatefulFirewallAlgSipS 28 } 

		contactNew OBJECT-TYPE
		SYNTAX  CounterBasedGauge64 
		MAX-ACCESS read-only 
		STATUS current
		DESCRIPTION  "Contact Alloc" 
		::={ acosCgnv6StatefulFirewallAlgSipS 29 } 

		contactAllocFailure OBJECT-TYPE
		SYNTAX  CounterBasedGauge64 
		MAX-ACCESS read-only 
		STATUS current
		DESCRIPTION  "Contact Alloc Failure" 
		::={ acosCgnv6StatefulFirewallAlgSipS 30 } 

		contactEim OBJECT-TYPE
		SYNTAX  CounterBasedGauge64 
		MAX-ACCESS read-only 
		STATUS current
		DESCRIPTION  "Contact EIM" 
		::={ acosCgnv6StatefulFirewallAlgSipS 31 } 

		contactEimSet OBJECT-TYPE
		SYNTAX  CounterBasedGauge64 
		MAX-ACCESS read-only 
		STATUS current
		DESCRIPTION  "Contact EIM Set" 
		::={ acosCgnv6StatefulFirewallAlgSipS 32 } 

		rtpNew OBJECT-TYPE
		SYNTAX  CounterBasedGauge64 
		MAX-ACCESS read-only 
		STATUS current
		DESCRIPTION  "RTP Alloc" 
		::={ acosCgnv6StatefulFirewallAlgSipS 33 } 

		rtpAllocFailure OBJECT-TYPE
		SYNTAX  CounterBasedGauge64 
		MAX-ACCESS read-only 
		STATUS current
		DESCRIPTION  "RTP Alloc Failure" 
		::={ acosCgnv6StatefulFirewallAlgSipS 34 } 

		rtpEim OBJECT-TYPE
		SYNTAX  CounterBasedGauge64 
		MAX-ACCESS read-only 
		STATUS current
		DESCRIPTION  "RTP EIM" 
		::={ acosCgnv6StatefulFirewallAlgSipS 35 } 

acosCgnv6StatefulFirewallAlgTftp    OBJECT IDENTIFIER ::= { acosCgnv6StatefulFirewallAlg 6 }
acosCgnv6StatefulFirewallAlgTftpS   OBJECT IDENTIFIER ::= { acosCgnv6StatefulFirewallAlgTftp 1 }

		cgnv6StateFullFirewallAlgTftpSessionCreated OBJECT-TYPE
		SYNTAX  CounterBasedGauge64 
		MAX-ACCESS read-only 
		STATUS current
		DESCRIPTION  "TFTP Client Sessions created" 
		::={ acosCgnv6StatefulFirewallAlgTftpS 1 } 

		helperCreated OBJECT-TYPE
		SYNTAX  CounterBasedGauge64 
		MAX-ACCESS read-only 
		STATUS current
		DESCRIPTION  "TFTP Helper Sessions created" 
		::={ acosCgnv6StatefulFirewallAlgTftpS 2 } 

		helperFreed OBJECT-TYPE
		SYNTAX  CounterBasedGauge64 
		MAX-ACCESS read-only 
		STATUS current
		DESCRIPTION  "TFTP Helper Sessions freed" 
		::={ acosCgnv6StatefulFirewallAlgTftpS 3 } 

		helperFreedUsed OBJECT-TYPE
		SYNTAX  CounterBasedGauge64 
		MAX-ACCESS read-only 
		STATUS current
		DESCRIPTION  "TFTP Helper Sessions freed used" 
		::={ acosCgnv6StatefulFirewallAlgTftpS 4 } 

		helperFreedUnused OBJECT-TYPE
		SYNTAX  CounterBasedGauge64 
		MAX-ACCESS read-only 
		STATUS current
		DESCRIPTION  "TFTP Helper Sessions freed unused" 
		::={ acosCgnv6StatefulFirewallAlgTftpS 5 } 

		helperAlreadyUsed OBJECT-TYPE
		SYNTAX  CounterBasedGauge64 
		MAX-ACCESS read-only 
		STATUS current
		DESCRIPTION  "TFTP Helper Session already used" 
		::={ acosCgnv6StatefulFirewallAlgTftpS 6 } 

		helperInRml OBJECT-TYPE
		SYNTAX  CounterBasedGauge64 
		MAX-ACCESS read-only 
		STATUS current
		DESCRIPTION  "TFTP Helper Session in Remove List" 
		::={ acosCgnv6StatefulFirewallAlgTftpS 7 } 

acosCgnv6Nat46Stateless             OBJECT IDENTIFIER ::= { acosCgnv6 23 }
acosCgnv6Nat46StatelessGlobal       OBJECT IDENTIFIER ::= { acosCgnv6Nat46Stateless 1 }
acosCgnv6Nat46StatelessGlobalS      OBJECT IDENTIFIER ::= { acosCgnv6Nat46StatelessGlobal 1 }

		outboundIpv4Received OBJECT-TYPE
		SYNTAX  CounterBasedGauge64 
		MAX-ACCESS read-only 
		STATUS current
		DESCRIPTION  "Outbound IPv4 packets received" 
		::={ acosCgnv6Nat46StatelessGlobalS 1 } 

		outboundIpv4Drop OBJECT-TYPE
		SYNTAX  CounterBasedGauge64 
		MAX-ACCESS read-only 
		STATUS current
		DESCRIPTION  "Outbound IPv4 packets dropped" 
		::={ acosCgnv6Nat46StatelessGlobalS 2 } 

		outboundIpv4FragmentReceived OBJECT-TYPE
		SYNTAX  CounterBasedGauge64 
		MAX-ACCESS read-only 
		STATUS current
		DESCRIPTION  "Outbound IPv4 fragment packets received" 
		::={ acosCgnv6Nat46StatelessGlobalS 3 } 

		outboundIpv6Unreachable OBJECT-TYPE
		SYNTAX  CounterBasedGauge64 
		MAX-ACCESS read-only 
		STATUS current
		DESCRIPTION  "Outbound IPv6 destination unreachable" 
		::={ acosCgnv6Nat46StatelessGlobalS 4 } 

		outboundIpv6Fragmented OBJECT-TYPE
		SYNTAX  CounterBasedGauge64 
		MAX-ACCESS read-only 
		STATUS current
		DESCRIPTION  "Outbound IPv6 packets fragmented" 
		::={ acosCgnv6Nat46StatelessGlobalS 5 } 

		inboundIpv6Received OBJECT-TYPE
		SYNTAX  CounterBasedGauge64 
		MAX-ACCESS read-only 
		STATUS current
		DESCRIPTION  "Inbound IPv6 packets received" 
		::={ acosCgnv6Nat46StatelessGlobalS 6 } 

		inboundIpv6Drop OBJECT-TYPE
		SYNTAX  CounterBasedGauge64 
		MAX-ACCESS read-only 
		STATUS current
		DESCRIPTION  "Inbound IPv6 packets dropped" 
		::={ acosCgnv6Nat46StatelessGlobalS 7 } 

		inboundIpv6FragmentReceived OBJECT-TYPE
		SYNTAX  CounterBasedGauge64 
		MAX-ACCESS read-only 
		STATUS current
		DESCRIPTION  "Inbound IPv6 fragment packets received" 
		::={ acosCgnv6Nat46StatelessGlobalS 8 } 

		inboundIpv4Unreachable OBJECT-TYPE
		SYNTAX  CounterBasedGauge64 
		MAX-ACCESS read-only 
		STATUS current
		DESCRIPTION  "Inbound IPv4 destination unreachable" 
		::={ acosCgnv6Nat46StatelessGlobalS 9 } 

		inboundIpv4Fragmented OBJECT-TYPE
		SYNTAX  CounterBasedGauge64 
		MAX-ACCESS read-only 
		STATUS current
		DESCRIPTION  "Inbound IPv4 packets fragmented" 
		::={ acosCgnv6Nat46StatelessGlobalS 10 } 

		packetTooBig OBJECT-TYPE
		SYNTAX  CounterBasedGauge64 
		MAX-ACCESS read-only 
		STATUS current
		DESCRIPTION  "Packet too big" 
		::={ acosCgnv6Nat46StatelessGlobalS 11 } 

		fragmentError OBJECT-TYPE
		SYNTAX  CounterBasedGauge64 
		MAX-ACCESS read-only 
		STATUS current
		DESCRIPTION  "Fragment processing errors" 
		::={ acosCgnv6Nat46StatelessGlobalS 12 } 

		icmpv6ToIcmp OBJECT-TYPE
		SYNTAX  CounterBasedGauge64 
		MAX-ACCESS read-only 
		STATUS current
		DESCRIPTION  "ICMPv6 to ICMP" 
		::={ acosCgnv6Nat46StatelessGlobalS 13 } 

		icmpv6ToIcmpError OBJECT-TYPE
		SYNTAX  CounterBasedGauge64 
		MAX-ACCESS read-only 
		STATUS current
		DESCRIPTION  "ICMPv6 to ICMP errors" 
		::={ acosCgnv6Nat46StatelessGlobalS 14 } 

		icmpToIcmpv6 OBJECT-TYPE
		SYNTAX  CounterBasedGauge64 
		MAX-ACCESS read-only 
		STATUS current
		DESCRIPTION  "ICMP to ICMPv6" 
		::={ acosCgnv6Nat46StatelessGlobalS 15 } 

		icmpToIcmpv6Error OBJECT-TYPE
		SYNTAX  CounterBasedGauge64 
		MAX-ACCESS read-only 
		STATUS current
		DESCRIPTION  "ICMP to ICMPv6 errors" 
		::={ acosCgnv6Nat46StatelessGlobalS 16 } 

		haStandby OBJECT-TYPE
		SYNTAX  CounterBasedGauge64 
		MAX-ACCESS read-only 
		STATUS current
		DESCRIPTION  "HA is standby" 
		::={ acosCgnv6Nat46StatelessGlobalS 17 } 

		nat46StatelessOtherError OBJECT-TYPE
		SYNTAX  CounterBasedGauge64 
		MAX-ACCESS read-only 
		STATUS current
		DESCRIPTION  "Other errors" 
		::={ acosCgnv6Nat46StatelessGlobalS 18 } 

		connCount OBJECT-TYPE
		SYNTAX  CounterBasedGauge64 
		MAX-ACCESS read-only 
		STATUS current
		DESCRIPTION  "conn count" 
		::={ acosCgnv6Nat46StatelessGlobalS 19 } 

acosCgnv6FixedNat                   OBJECT IDENTIFIER ::= { acosCgnv6 24 }
acosCgnv6FixedNatGlobal             OBJECT IDENTIFIER ::= { acosCgnv6FixedNat 2 }
acosCgnv6FixedNatGlobalS            OBJECT IDENTIFIER ::= { acosCgnv6FixedNatGlobal 1 }

		totalNatInUse OBJECT-TYPE
		SYNTAX  CounterBasedGauge64 
		MAX-ACCESS read-only 
		STATUS current
		DESCRIPTION  "Total NAT Addresses in-use" 
		::={ acosCgnv6FixedNatGlobalS 1 } 

		cgnv6FixednatGlobalTotalTcpAllocated OBJECT-TYPE
		SYNTAX  CounterBasedGauge64 
		MAX-ACCESS read-only 
		STATUS current
		DESCRIPTION  "Total TCP Ports Allocated" 
		::={ acosCgnv6FixedNatGlobalS 2 } 

		cgnv6FixednatGlobalTotalTcpFreed OBJECT-TYPE
		SYNTAX  CounterBasedGauge64 
		MAX-ACCESS read-only 
		STATUS current
		DESCRIPTION  "Total TCP Ports Freed" 
		::={ acosCgnv6FixedNatGlobalS 3 } 

		cgnv6FixednatGlobalTotalUdpAllocated OBJECT-TYPE
		SYNTAX  CounterBasedGauge64 
		MAX-ACCESS read-only 
		STATUS current
		DESCRIPTION  "Total UDP Ports Allocated" 
		::={ acosCgnv6FixedNatGlobalS 4 } 

		cgnv6FixednatGlobalTotalUdpFreed OBJECT-TYPE
		SYNTAX  CounterBasedGauge64 
		MAX-ACCESS read-only 
		STATUS current
		DESCRIPTION  "Total UDP Ports Freed" 
		::={ acosCgnv6FixedNatGlobalS 5 } 

		cgnv6FixednatGlobalTotalIcmpAllocated OBJECT-TYPE
		SYNTAX  CounterBasedGauge64 
		MAX-ACCESS read-only 
		STATUS current
		DESCRIPTION  "Total ICMP Ports Allocated" 
		::={ acosCgnv6FixedNatGlobalS 6 } 

		cgnv6FixednatGlobalTotalTotalIcmpFreed OBJECT-TYPE
		SYNTAX  CounterBasedGauge64 
		MAX-ACCESS read-only 
		STATUS current
		DESCRIPTION  "Total ICMP Ports Freed" 
		::={ acosCgnv6FixedNatGlobalS 7 } 

		nat44DataSessionCreated OBJECT-TYPE
		SYNTAX  CounterBasedGauge64 
		MAX-ACCESS read-only 
		STATUS current
		DESCRIPTION  "NAT44 Data Sessions Created" 
		::={ acosCgnv6FixedNatGlobalS 8 } 

		nat44DataSessionFreed OBJECT-TYPE
		SYNTAX  CounterBasedGauge64 
		MAX-ACCESS read-only 
		STATUS current
		DESCRIPTION  "NAT44 Data Sessions Freed" 
		::={ acosCgnv6FixedNatGlobalS 9 } 

		nat64DataSessionCreated OBJECT-TYPE
		SYNTAX  CounterBasedGauge64 
		MAX-ACCESS read-only 
		STATUS current
		DESCRIPTION  "NAT64 Data Sessions Created" 
		::={ acosCgnv6FixedNatGlobalS 10 } 

		nat64DataSessionFreed OBJECT-TYPE
		SYNTAX  CounterBasedGauge64 
		MAX-ACCESS read-only 
		STATUS current
		DESCRIPTION  "NAT64 Data Sessions Freed" 
		::={ acosCgnv6FixedNatGlobalS 11 } 

		dsliteDataSessionCreated OBJECT-TYPE
		SYNTAX  CounterBasedGauge64 
		MAX-ACCESS read-only 
		STATUS current
		DESCRIPTION  "DS-Lite Data Sessions Created" 
		::={ acosCgnv6FixedNatGlobalS 12 } 

		dsliteDataSessionFreed OBJECT-TYPE
		SYNTAX  CounterBasedGauge64 
		MAX-ACCESS read-only 
		STATUS current
		DESCRIPTION  "DS-Lite Data Sessions Freed" 
		::={ acosCgnv6FixedNatGlobalS 13 } 

		cgnv6FixednatGlobalNatPortUnavailableTcp OBJECT-TYPE
		SYNTAX  CounterBasedGauge64 
		MAX-ACCESS read-only 
		STATUS current
		DESCRIPTION  "TCP NAT Port Unavailable" 
		::={ acosCgnv6FixedNatGlobalS 14 } 

		cgnv6FixednatGlobalNatPortUnavailableUdp OBJECT-TYPE
		SYNTAX  CounterBasedGauge64 
		MAX-ACCESS read-only 
		STATUS current
		DESCRIPTION  "UDP NAT Port Unavailable" 
		::={ acosCgnv6FixedNatGlobalS 15 } 

		cgnv6FixednatGlobalNatPortUnavailableIcmp OBJECT-TYPE
		SYNTAX  CounterBasedGauge64 
		MAX-ACCESS read-only 
		STATUS current
		DESCRIPTION  "ICMP NAT Port Unavailable" 
		::={ acosCgnv6FixedNatGlobalS 16 } 

		sessionUserQuotaExceeded OBJECT-TYPE
		SYNTAX  CounterBasedGauge64 
		MAX-ACCESS read-only 
		STATUS current
		DESCRIPTION  "Sessions User Quota Exceeded" 
		::={ acosCgnv6FixedNatGlobalS 20 } 

		nat44TcpFullconeCreated OBJECT-TYPE
		SYNTAX  CounterBasedGauge64 
		MAX-ACCESS read-only 
		STATUS current
		DESCRIPTION  "NAT44 TCP Full-Cone Created" 
		::={ acosCgnv6FixedNatGlobalS 21 } 

		nat44TcpFullconeFreed OBJECT-TYPE
		SYNTAX  CounterBasedGauge64 
		MAX-ACCESS read-only 
		STATUS current
		DESCRIPTION  "NAT44 TCP Full-Cone Freed" 
		::={ acosCgnv6FixedNatGlobalS 22 } 

		nat44UdpFullconeCreated OBJECT-TYPE
		SYNTAX  CounterBasedGauge64 
		MAX-ACCESS read-only 
		STATUS current
		DESCRIPTION  "NAT44 UDP Full-Cone Created" 
		::={ acosCgnv6FixedNatGlobalS 23 } 

		nat44UdpFullconeFreed OBJECT-TYPE
		SYNTAX  CounterBasedGauge64 
		MAX-ACCESS read-only 
		STATUS current
		DESCRIPTION  "NAT44 UDP Full-Cone Freed" 
		::={ acosCgnv6FixedNatGlobalS 24 } 

		nat44UdpAlgFullconeCreated OBJECT-TYPE
		SYNTAX  CounterBasedGauge64 
		MAX-ACCESS read-only 
		STATUS current
		DESCRIPTION  "NAT44 UDP ALG Full-Cone Created" 
		::={ acosCgnv6FixedNatGlobalS 25 } 

		nat44UdpAlgFullconeFreed OBJECT-TYPE
		SYNTAX  CounterBasedGauge64 
		MAX-ACCESS read-only 
		STATUS current
		DESCRIPTION  "NAT44 UDP ALG Full-Cone Freed" 
		::={ acosCgnv6FixedNatGlobalS 26 } 

		nat64TcpFullconeCreated OBJECT-TYPE
		SYNTAX  CounterBasedGauge64 
		MAX-ACCESS read-only 
		STATUS current
		DESCRIPTION  "NAT64 TCP Full-Cone Created" 
		::={ acosCgnv6FixedNatGlobalS 27 } 

		nat64TcpFullconeFreed OBJECT-TYPE
		SYNTAX  CounterBasedGauge64 
		MAX-ACCESS read-only 
		STATUS current
		DESCRIPTION  "NAT64 TCP Full-Cone Freed" 
		::={ acosCgnv6FixedNatGlobalS 28 } 

		nat64UdpFullconeCreated OBJECT-TYPE
		SYNTAX  CounterBasedGauge64 
		MAX-ACCESS read-only 
		STATUS current
		DESCRIPTION  "NAT64 UDP Full-Cone Created" 
		::={ acosCgnv6FixedNatGlobalS 29 } 

		nat64UdpFullconeFreed OBJECT-TYPE
		SYNTAX  CounterBasedGauge64 
		MAX-ACCESS read-only 
		STATUS current
		DESCRIPTION  "NAT64 UDP Full-Cone Freed" 
		::={ acosCgnv6FixedNatGlobalS 30 } 

		nat64UdpAlgFullconeCreated OBJECT-TYPE
		SYNTAX  CounterBasedGauge64 
		MAX-ACCESS read-only 
		STATUS current
		DESCRIPTION  "NAT64 UDP ALG Full-Cone Created" 
		::={ acosCgnv6FixedNatGlobalS 31 } 

		nat64UdpAlgFullconeFreed OBJECT-TYPE
		SYNTAX  CounterBasedGauge64 
		MAX-ACCESS read-only 
		STATUS current
		DESCRIPTION  "NAT64 UDP ALG Full-Cone Freed" 
		::={ acosCgnv6FixedNatGlobalS 32 } 

		dsliteTcpFullconeCreated OBJECT-TYPE
		SYNTAX  CounterBasedGauge64 
		MAX-ACCESS read-only 
		STATUS current
		DESCRIPTION  "DS-Lite TCP Full-Cone Created" 
		::={ acosCgnv6FixedNatGlobalS 33 } 

		dsliteTcpFullconeFreed OBJECT-TYPE
		SYNTAX  CounterBasedGauge64 
		MAX-ACCESS read-only 
		STATUS current
		DESCRIPTION  "DS-Lite TCP Full-Cone Freed" 
		::={ acosCgnv6FixedNatGlobalS 34 } 

		dsliteUdpFullconeCreated OBJECT-TYPE
		SYNTAX  CounterBasedGauge64 
		MAX-ACCESS read-only 
		STATUS current
		DESCRIPTION  "DS-Lite UDP Full-Cone Created" 
		::={ acosCgnv6FixedNatGlobalS 35 } 

		dsliteUdpFullconeFreed OBJECT-TYPE
		SYNTAX  CounterBasedGauge64 
		MAX-ACCESS read-only 
		STATUS current
		DESCRIPTION  "DS-Lite UDP Full-Cone Freed" 
		::={ acosCgnv6FixedNatGlobalS 36 } 

		dsliteUdpAlgFullconeCreated OBJECT-TYPE
		SYNTAX  CounterBasedGauge64 
		MAX-ACCESS read-only 
		STATUS current
		DESCRIPTION  "DS-Lite UDP ALG Full-Cone Created" 
		::={ acosCgnv6FixedNatGlobalS 37 } 

		dsliteUdpAlgFullconeFreed OBJECT-TYPE
		SYNTAX  CounterBasedGauge64 
		MAX-ACCESS read-only 
		STATUS current
		DESCRIPTION  "DS-Lite UDP ALG Full-Cone Freed" 
		::={ acosCgnv6FixedNatGlobalS 38 } 

		cgnv6FixednatGlobalFullconeFailure OBJECT-TYPE
		SYNTAX  CounterBasedGauge64 
		MAX-ACCESS read-only 
		STATUS current
		DESCRIPTION  "Full-Cone Session Creation Failed" 
		::={ acosCgnv6FixedNatGlobalS 39 } 

		nat44EimMatch OBJECT-TYPE
		SYNTAX  CounterBasedGauge64 
		MAX-ACCESS read-only 
		STATUS current
		DESCRIPTION  "NAT44 Endpoint-Independent-Mapping Matched" 
		::={ acosCgnv6FixedNatGlobalS 40 } 

		nat64EimMatch OBJECT-TYPE
		SYNTAX  CounterBasedGauge64 
		MAX-ACCESS read-only 
		STATUS current
		DESCRIPTION  "NAT64 Endpoint-Independent-Mapping Matched" 
		::={ acosCgnv6FixedNatGlobalS 41 } 

		dsliteEimMatch OBJECT-TYPE
		SYNTAX  CounterBasedGauge64 
		MAX-ACCESS read-only 
		STATUS current
		DESCRIPTION  "DS-Lite Endpoint-Independent-Mapping Matched" 
		::={ acosCgnv6FixedNatGlobalS 42 } 

		nat44EifMatch OBJECT-TYPE
		SYNTAX  CounterBasedGauge64 
		MAX-ACCESS read-only 
		STATUS current
		DESCRIPTION  "NAT44 Endpoint-Independent-Filtering Matched" 
		::={ acosCgnv6FixedNatGlobalS 43 } 

		nat64EifMatch OBJECT-TYPE
		SYNTAX  CounterBasedGauge64 
		MAX-ACCESS read-only 
		STATUS current
		DESCRIPTION  "NAT64 Endpoint-Independent-Filtering Matched" 
		::={ acosCgnv6FixedNatGlobalS 44 } 

		dsliteEifMatch OBJECT-TYPE
		SYNTAX  CounterBasedGauge64 
		MAX-ACCESS read-only 
		STATUS current
		DESCRIPTION  "DS-Lite Endpoint-Independent-Filtering Matched" 
		::={ acosCgnv6FixedNatGlobalS 45 } 

		nat44InboundFiltered OBJECT-TYPE
		SYNTAX  CounterBasedGauge64 
		MAX-ACCESS read-only 
		STATUS current
		DESCRIPTION  "NAT44 Endpoint-Dependent Filtering Drop" 
		::={ acosCgnv6FixedNatGlobalS 46 } 

		nat64InboundFiltered OBJECT-TYPE
		SYNTAX  CounterBasedGauge64 
		MAX-ACCESS read-only 
		STATUS current
		DESCRIPTION  "NAT64 Endpoint-Dependent Filtering Drop" 
		::={ acosCgnv6FixedNatGlobalS 47 } 

		dsliteInboundFiltered OBJECT-TYPE
		SYNTAX  CounterBasedGauge64 
		MAX-ACCESS read-only 
		STATUS current
		DESCRIPTION  "DS-Lite Endpoint-Dependent Filtering Drop" 
		::={ acosCgnv6FixedNatGlobalS 48 } 

		nat44EifLimitExceeded OBJECT-TYPE
		SYNTAX  CounterBasedGauge64 
		MAX-ACCESS read-only 
		STATUS current
		DESCRIPTION  "NAT44 Endpoint-Independent-Filtering Limit Exceeded" 
		::={ acosCgnv6FixedNatGlobalS 49 } 

		nat64EifLimitExceeded OBJECT-TYPE
		SYNTAX  CounterBasedGauge64 
		MAX-ACCESS read-only 
		STATUS current
		DESCRIPTION  "NAT64 Endpoint-Independent-Filtering Limit Exceeded" 
		::={ acosCgnv6FixedNatGlobalS 50 } 

		dsliteEifLimitExceeded OBJECT-TYPE
		SYNTAX  CounterBasedGauge64 
		MAX-ACCESS read-only 
		STATUS current
		DESCRIPTION  "DS-Lite Endpoint-Independent-Filtering Limit Exceeded" 
		::={ acosCgnv6FixedNatGlobalS 51 } 

		nat44Hairpin OBJECT-TYPE
		SYNTAX  CounterBasedGauge64 
		MAX-ACCESS read-only 
		STATUS current
		DESCRIPTION  "NAT44 Hairpin Session Created" 
		::={ acosCgnv6FixedNatGlobalS 52 } 

		nat64Hairpin OBJECT-TYPE
		SYNTAX  CounterBasedGauge64 
		MAX-ACCESS read-only 
		STATUS current
		DESCRIPTION  "NAT64 Hairpin Session Created" 
		::={ acosCgnv6FixedNatGlobalS 53 } 

		dsliteHairpin OBJECT-TYPE
		SYNTAX  CounterBasedGauge64 
		MAX-ACCESS read-only 
		STATUS current
		DESCRIPTION  "DS-Lite Hairpin Session Created" 
		::={ acosCgnv6FixedNatGlobalS 54 } 

		standbyDrop OBJECT-TYPE
		SYNTAX  CounterBasedGauge64 
		MAX-ACCESS read-only 
		STATUS current
		DESCRIPTION  "Fixed NAT LID Standby Drop" 
		::={ acosCgnv6FixedNatGlobalS 55 } 

		fixedNatFullconeSelfHairpinningDrop OBJECT-TYPE
		SYNTAX  CounterBasedGauge64 
		MAX-ACCESS read-only 
		STATUS current
		DESCRIPTION  "Self-Hairpinning Drop" 
		::={ acosCgnv6FixedNatGlobalS 56 } 

		cgnv6FixednatGlobal6rdDrop OBJECT-TYPE
		SYNTAX  CounterBasedGauge64 
		MAX-ACCESS read-only 
		STATUS current
		DESCRIPTION  "Fixed NAT IPv6 in IPv4 Packet Drop" 
		::={ acosCgnv6FixedNatGlobalS 57 } 

		destRlistDrop OBJECT-TYPE
		SYNTAX  CounterBasedGauge64 
		MAX-ACCESS read-only 
		STATUS current
		DESCRIPTION  "Fixed NAT Dest Rule List Drop" 
		::={ acosCgnv6FixedNatGlobalS 58 } 

		destRlistPassThrough OBJECT-TYPE
		SYNTAX  CounterBasedGauge64 
		MAX-ACCESS read-only 
		STATUS current
		DESCRIPTION  "Fixed NAT Dest Rule List Pass-Through" 
		::={ acosCgnv6FixedNatGlobalS 59 } 

		destRlistSnatDrop OBJECT-TYPE
		SYNTAX  CounterBasedGauge64 
		MAX-ACCESS read-only 
		STATUS current
		DESCRIPTION  "Fixed NAT Dest Rules List Source NAT Drop" 
		::={ acosCgnv6FixedNatGlobalS 60 } 

		crossCpuHelperCreated OBJECT-TYPE
		SYNTAX  CounterBasedGauge64 
		MAX-ACCESS read-only 
		STATUS current
		DESCRIPTION  "Cross CPU Helper Session Created" 
		::={ acosCgnv6FixedNatGlobalS 61 } 

		crossCpuHelperFreeRetryLookup OBJECT-TYPE
		SYNTAX  CounterBasedGauge64 
		MAX-ACCESS read-only 
		STATUS current
		DESCRIPTION  "Cross CPU Helper Session Free Retry Lookup" 
		::={ acosCgnv6FixedNatGlobalS 62 } 

		crossCpuHelperFreeNotFound OBJECT-TYPE
		SYNTAX  CounterBasedGauge64 
		MAX-ACCESS read-only 
		STATUS current
		DESCRIPTION  "Cross CPU Helper Session Free not Found" 
		::={ acosCgnv6FixedNatGlobalS 63 } 

		crossCpuHelperFree OBJECT-TYPE
		SYNTAX  CounterBasedGauge64 
		MAX-ACCESS read-only 
		STATUS current
		DESCRIPTION  "Cross CPU Helper Session Freed" 
		::={ acosCgnv6FixedNatGlobalS 64 } 

		crossCpuRcv OBJECT-TYPE
		SYNTAX  CounterBasedGauge64 
		MAX-ACCESS read-only 
		STATUS current
		DESCRIPTION  "Cross CPU Helper Packets Received" 
		::={ acosCgnv6FixedNatGlobalS 65 } 

		crossCpuBadL3 OBJECT-TYPE
		SYNTAX  CounterBasedGauge64 
		MAX-ACCESS read-only 
		STATUS current
		DESCRIPTION  "Cross CPU Unsupported L3" 
		::={ acosCgnv6FixedNatGlobalS 66 } 

		crossCpuBadL4 OBJECT-TYPE
		SYNTAX  CounterBasedGauge64 
		MAX-ACCESS read-only 
		STATUS current
		DESCRIPTION  "Cross CPU Unsupported L4" 
		::={ acosCgnv6FixedNatGlobalS 67 } 

		crossCpuNoSession OBJECT-TYPE
		SYNTAX  CounterBasedGauge64 
		MAX-ACCESS read-only 
		STATUS current
		DESCRIPTION  "Cross CPU no Session Found" 
		::={ acosCgnv6FixedNatGlobalS 68 } 

		crossCpuHelperDeleted OBJECT-TYPE
		SYNTAX  CounterBasedGauge64 
		MAX-ACCESS read-only 
		STATUS current
		DESCRIPTION  "Cross CPU Helper Session Deleted" 
		::={ acosCgnv6FixedNatGlobalS 69 } 

		crossCpuHelperFixedNatLidStandby OBJECT-TYPE
		SYNTAX  CounterBasedGauge64 
		MAX-ACCESS read-only 
		STATUS current
		DESCRIPTION  "Cross CPU Helper Fixed NAT LID Standby" 
		::={ acosCgnv6FixedNatGlobalS 70 } 

		crossCpuHelperCpuMismatch OBJECT-TYPE
		SYNTAX  CounterBasedGauge64 
		MAX-ACCESS read-only 
		STATUS current
		DESCRIPTION  "Cross CPU Helper CPU Mismatch" 
		::={ acosCgnv6FixedNatGlobalS 71 } 

		crossCpuSent OBJECT-TYPE
		SYNTAX  CounterBasedGauge64 
		MAX-ACCESS read-only 
		STATUS current
		DESCRIPTION  "Cross CPU Helper Packets Sent" 
		::={ acosCgnv6FixedNatGlobalS 72 } 

		configNotFound OBJECT-TYPE
		SYNTAX  CounterBasedGauge64 
		MAX-ACCESS read-only 
		STATUS current
		DESCRIPTION  "Fixed NAT Config not Found" 
		::={ acosCgnv6FixedNatGlobalS 73 } 

		fullconeInDelQ OBJECT-TYPE
		SYNTAX  CounterBasedGauge64 
		MAX-ACCESS read-only 
		STATUS current
		DESCRIPTION  "Full-Cone Session in Delete Queue" 
		::={ acosCgnv6FixedNatGlobalS 74 } 

		fullconeOverflow OBJECT-TYPE
		SYNTAX  CounterBasedGauge64 
		MAX-ACCESS read-only 
		STATUS current
		DESCRIPTION  "Full-Cone Session Conn-Count Overflow" 
		::={ acosCgnv6FixedNatGlobalS 75 } 

		fullconeInboundIdxMismatch OBJECT-TYPE
		SYNTAX  CounterBasedGauge64 
		MAX-ACCESS read-only 
		STATUS current
		DESCRIPTION  "Full-Cone Session Fixed NAT LID mismatch" 
		::={ acosCgnv6FixedNatGlobalS 76 } 

		fullconeRetryLookup OBJECT-TYPE
		SYNTAX  CounterBasedGauge64 
		MAX-ACCESS read-only 
		STATUS current
		DESCRIPTION  "Full-cone session retry look-up" 
		::={ acosCgnv6FixedNatGlobalS 77 } 

		fullconeNotFound OBJECT-TYPE
		SYNTAX  CounterBasedGauge64 
		MAX-ACCESS read-only 
		STATUS current
		DESCRIPTION  "Full-cone session not found" 
		::={ acosCgnv6FixedNatGlobalS 78 } 

		fullconeOverflowEim OBJECT-TYPE
		SYNTAX  CounterBasedGauge64 
		MAX-ACCESS read-only 
		STATUS current
		DESCRIPTION  "Full-cone EIM Overflow" 
		::={ acosCgnv6FixedNatGlobalS 79 } 

		fullconeOverflowEif OBJECT-TYPE
		SYNTAX  CounterBasedGauge64 
		MAX-ACCESS read-only 
		STATUS current
		DESCRIPTION  "Full-cone EIF Overflow" 
		::={ acosCgnv6FixedNatGlobalS 80 } 

		haConfigMismatch OBJECT-TYPE
		SYNTAX  CounterBasedGauge64 
		MAX-ACCESS read-only 
		STATUS current
		DESCRIPTION  "HA Fixed NAT Config Mismatch" 
		::={ acosCgnv6FixedNatGlobalS 81 } 

		haUserQuotaExceeded OBJECT-TYPE
		SYNTAX  CounterBasedGauge64 
		MAX-ACCESS read-only 
		STATUS current
		DESCRIPTION  "HA User Quota Exceeded" 
		::={ acosCgnv6FixedNatGlobalS 82 } 

		haFullconeMismatch OBJECT-TYPE
		SYNTAX  CounterBasedGauge64 
		MAX-ACCESS read-only 
		STATUS current
		DESCRIPTION  "HA Full-Cone Mismatch" 
		::={ acosCgnv6FixedNatGlobalS 83 } 

		haDnatMismatch OBJECT-TYPE
		SYNTAX  CounterBasedGauge64 
		MAX-ACCESS read-only 
		STATUS current
		DESCRIPTION  "HA Destination NAT Config Mismatch" 
		::={ acosCgnv6FixedNatGlobalS 84 } 

		haNatPortUnavailable OBJECT-TYPE
		SYNTAX  CounterBasedGauge64 
		MAX-ACCESS read-only 
		STATUS current
		DESCRIPTION  "HA NAT Port Unavailable" 
		::={ acosCgnv6FixedNatGlobalS 85 } 

		haFullconeFailure OBJECT-TYPE
		SYNTAX  CounterBasedGauge64 
		MAX-ACCESS read-only 
		STATUS current
		DESCRIPTION  "HA Full-Cone Failure" 
		::={ acosCgnv6FixedNatGlobalS 86 } 

		haEndpointIndepMapMatch OBJECT-TYPE
		SYNTAX  CounterBasedGauge64 
		MAX-ACCESS read-only 
		STATUS current
		DESCRIPTION  "HA Endpoint-Independent-Mapping Match" 
		::={ acosCgnv6FixedNatGlobalS 87 } 

		udpAlgEimMismatch OBJECT-TYPE
		SYNTAX  CounterBasedGauge64 
		MAX-ACCESS read-only 
		STATUS current
		DESCRIPTION  "UDP ALG Endpoint-Independent Mapping Mismatch" 
		::={ acosCgnv6FixedNatGlobalS 88 } 

		udpAlgNoNatIp OBJECT-TYPE
		SYNTAX  CounterBasedGauge64 
		MAX-ACCESS read-only 
		STATUS current
		DESCRIPTION  "UDP ALG User-Quota Unknown NAT IP" 
		::={ acosCgnv6FixedNatGlobalS 89 } 

		udpAlgAllocFailure OBJECT-TYPE
		SYNTAX  CounterBasedGauge64 
		MAX-ACCESS read-only 
		STATUS current
		DESCRIPTION  "UDP ALG Port Allocation Failure" 
		::={ acosCgnv6FixedNatGlobalS 90 } 

		mtuExceeded OBJECT-TYPE
		SYNTAX  CounterBasedGauge64 
		MAX-ACCESS read-only 
		STATUS current
		DESCRIPTION  "Packet Exceeded MTU" 
		::={ acosCgnv6FixedNatGlobalS 91 } 

		frag OBJECT-TYPE
		SYNTAX  CounterBasedGauge64 
		MAX-ACCESS read-only 
		STATUS current
		DESCRIPTION  "Fragmented Packets" 
		::={ acosCgnv6FixedNatGlobalS 92 } 

		fragIcmp OBJECT-TYPE
		SYNTAX  CounterBasedGauge64 
		MAX-ACCESS read-only 
		STATUS current
		DESCRIPTION  "ICMP Packet Too Big Sent" 
		::={ acosCgnv6FixedNatGlobalS 93 } 

		periodicLogMsgAlloc OBJECT-TYPE
		SYNTAX  CounterBasedGauge64 
		MAX-ACCESS read-only 
		STATUS current
		DESCRIPTION  "Fixed NAT Periodic Log Msg Allocated" 
		::={ acosCgnv6FixedNatGlobalS 94 } 

		periodicLogMsgFree OBJECT-TYPE
		SYNTAX  CounterBasedGauge64 
		MAX-ACCESS read-only 
		STATUS current
		DESCRIPTION  "Fixed NAT Periodic Log Msg Freed" 
		::={ acosCgnv6FixedNatGlobalS 95 } 

		disableLogMsgAlloc OBJECT-TYPE
		SYNTAX  CounterBasedGauge64 
		MAX-ACCESS read-only 
		STATUS current
		DESCRIPTION  "Fixed NAT Disable Log Msg Allocated" 
		::={ acosCgnv6FixedNatGlobalS 96 } 

		disableLogMsgFree OBJECT-TYPE
		SYNTAX  CounterBasedGauge64 
		MAX-ACCESS read-only 
		STATUS current
		DESCRIPTION  "Fixed NAT Disable Log Msg Freed" 
		::={ acosCgnv6FixedNatGlobalS 97 } 

		sipAlgReuseContactFullcone OBJECT-TYPE
		SYNTAX  CounterBasedGauge64 
		MAX-ACCESS read-only 
		STATUS current
		DESCRIPTION  "SIP ALG Reuse Contact Full-cone Session" 
		::={ acosCgnv6FixedNatGlobalS 98 } 

		sipAlgContactFullconeMismatch OBJECT-TYPE
		SYNTAX  CounterBasedGauge64 
		MAX-ACCESS read-only 
		STATUS current
		DESCRIPTION  "SIP ALG Contact Full-cone Session Mismatch" 
		::={ acosCgnv6FixedNatGlobalS 99 } 

		sipAlgCreateContactFullconeFailure OBJECT-TYPE
		SYNTAX  CounterBasedGauge64 
		MAX-ACCESS read-only 
		STATUS current
		DESCRIPTION  "SIP ALG Create Contact Full-cone Session Failure" 
		::={ acosCgnv6FixedNatGlobalS 100 } 

		sipAlgSingleRtpFullcone OBJECT-TYPE
		SYNTAX  CounterBasedGauge64 
		MAX-ACCESS read-only 
		STATUS current
		DESCRIPTION  "SIP ALG Single RTP Full-cone Found" 
		::={ acosCgnv6FixedNatGlobalS 101 } 

		sipAlgRtcpFullconeMismatch OBJECT-TYPE
		SYNTAX  CounterBasedGauge64 
		MAX-ACCESS read-only 
		STATUS current
		DESCRIPTION  "SIP ALG RTCP Full-cone NAT Port Mismatch" 
		::={ acosCgnv6FixedNatGlobalS 102 } 

		sipAlgReuseRtpRtcpFullcone OBJECT-TYPE
		SYNTAX  CounterBasedGauge64 
		MAX-ACCESS read-only 
		STATUS current
		DESCRIPTION  "SIP ALG Reuse RTP/RTCP Full-cone Session" 
		::={ acosCgnv6FixedNatGlobalS 103 } 

		sipAlgSingleRtcpFullcone OBJECT-TYPE
		SYNTAX  CounterBasedGauge64 
		MAX-ACCESS read-only 
		STATUS current
		DESCRIPTION  "SIP ALG Single RTCP Full-cone Found" 
		::={ acosCgnv6FixedNatGlobalS 104 } 

		sipAlgCreateRtpFullconeFailure OBJECT-TYPE
		SYNTAX  CounterBasedGauge64 
		MAX-ACCESS read-only 
		STATUS current
		DESCRIPTION  "SIP ALG Create RTP Full-cone Session Failure" 
		::={ acosCgnv6FixedNatGlobalS 105 } 

		sipAlgCreateRtcpFullconeFailure OBJECT-TYPE
		SYNTAX  CounterBasedGauge64 
		MAX-ACCESS read-only 
		STATUS current
		DESCRIPTION  "SIP ALG Create RTCP Full-cone Session Failure" 
		::={ acosCgnv6FixedNatGlobalS 106 } 

		icmpOutOfStateUqeAdminFilteredSent OBJECT-TYPE
		SYNTAX  CounterBasedGauge64 
		MAX-ACCESS read-only 
		STATUS current
		DESCRIPTION  "Total User Quota Exceeded ICMP admin filtered sent" 
		::={ acosCgnv6FixedNatGlobalS 107 } 

		icmpOutOfStateUqeHostUnreachableSent OBJECT-TYPE
		SYNTAX  CounterBasedGauge64 
		MAX-ACCESS read-only 
		STATUS current
		DESCRIPTION  "Total User Quota Exceeded ICMP host unreachable sent" 
		::={ acosCgnv6FixedNatGlobalS 108 } 

		icmpOutOfStateUqeDropped OBJECT-TYPE
		SYNTAX  CounterBasedGauge64 
		MAX-ACCESS read-only 
		STATUS current
		DESCRIPTION  "Total User Queue Exceeded ICMP notification dropped" 
		::={ acosCgnv6FixedNatGlobalS 109 } 

		natEspIpConflicts OBJECT-TYPE
		SYNTAX  CounterBasedGauge64 
		MAX-ACCESS read-only 
		STATUS current
		DESCRIPTION  "Fixed NAT ESP IP Conflicts" 
		::={ acosCgnv6FixedNatGlobalS 110 } 

		totalTcpAllocatedShadow OBJECT-TYPE
		SYNTAX  CounterBasedGauge64 
		MAX-ACCESS read-only 
		STATUS current
		DESCRIPTION  "Total TCP Ports Allocated" 
		::={ acosCgnv6FixedNatGlobalS 111 } 

		totalTcpFreedShadow OBJECT-TYPE
		SYNTAX  CounterBasedGauge64 
		MAX-ACCESS read-only 
		STATUS current
		DESCRIPTION  "Total TCP Ports Freed" 
		::={ acosCgnv6FixedNatGlobalS 112 } 

		totalUdpAllocatedShadow OBJECT-TYPE
		SYNTAX  CounterBasedGauge64 
		MAX-ACCESS read-only 
		STATUS current
		DESCRIPTION  "Total UDP Ports Allocated" 
		::={ acosCgnv6FixedNatGlobalS 113 } 

		totalUdpFreedShadow OBJECT-TYPE
		SYNTAX  CounterBasedGauge64 
		MAX-ACCESS read-only 
		STATUS current
		DESCRIPTION  "Total UDP Ports Freed" 
		::={ acosCgnv6FixedNatGlobalS 114 } 

		totalIcmpAllocatedShadow OBJECT-TYPE
		SYNTAX  CounterBasedGauge64 
		MAX-ACCESS read-only 
		STATUS current
		DESCRIPTION  "Total ICMP Ports Allocated" 
		::={ acosCgnv6FixedNatGlobalS 115 } 

		totalIcmpFreedShadow OBJECT-TYPE
		SYNTAX  CounterBasedGauge64 
		MAX-ACCESS read-only 
		STATUS current
		DESCRIPTION  "Total ICMP Ports Freed" 
		::={ acosCgnv6FixedNatGlobalS 116 } 

		nat44DataSessionCreatedShadow OBJECT-TYPE
		SYNTAX  CounterBasedGauge64 
		MAX-ACCESS read-only 
		STATUS current
		DESCRIPTION  "NAT44 Data Sessions Created" 
		::={ acosCgnv6FixedNatGlobalS 117 } 

		nat44DataSessionFreedShadow OBJECT-TYPE
		SYNTAX  CounterBasedGauge64 
		MAX-ACCESS read-only 
		STATUS current
		DESCRIPTION  "NAT44 Data Sessions Freed" 
		::={ acosCgnv6FixedNatGlobalS 118 } 

		nat64DataSessionCreatedShadow OBJECT-TYPE
		SYNTAX  CounterBasedGauge64 
		MAX-ACCESS read-only 
		STATUS current
		DESCRIPTION  "NAT64 Data Sessions Created" 
		::={ acosCgnv6FixedNatGlobalS 119 } 

		nat64DataSessionFreedShadow OBJECT-TYPE
		SYNTAX  CounterBasedGauge64 
		MAX-ACCESS read-only 
		STATUS current
		DESCRIPTION  "NAT64 Data Sessions Freed" 
		::={ acosCgnv6FixedNatGlobalS 120 } 

		dsliteDataSessionCreatedShadow OBJECT-TYPE
		SYNTAX  CounterBasedGauge64 
		MAX-ACCESS read-only 
		STATUS current
		DESCRIPTION  "DS-Lite Data Sessions Created" 
		::={ acosCgnv6FixedNatGlobalS 121 } 

		dsliteDataSessionFreedShadow OBJECT-TYPE
		SYNTAX  CounterBasedGauge64 
		MAX-ACCESS read-only 
		STATUS current
		DESCRIPTION  "DS-Lite Data Sessions Freed" 
		::={ acosCgnv6FixedNatGlobalS 122 } 

		nat44TcpFullconeCreatedShadow OBJECT-TYPE
		SYNTAX  CounterBasedGauge64 
		MAX-ACCESS read-only 
		STATUS current
		DESCRIPTION  "NAT44 TCP Full-Cone Created" 
		::={ acosCgnv6FixedNatGlobalS 123 } 

		nat44TcpFullconeFreedShadow OBJECT-TYPE
		SYNTAX  CounterBasedGauge64 
		MAX-ACCESS read-only 
		STATUS current
		DESCRIPTION  "NAT44 TCP Full-Cone Freed" 
		::={ acosCgnv6FixedNatGlobalS 124 } 

		nat44UdpFullconeCreatedShadow OBJECT-TYPE
		SYNTAX  CounterBasedGauge64 
		MAX-ACCESS read-only 
		STATUS current
		DESCRIPTION  "NAT44 UDP Full-Cone Created" 
		::={ acosCgnv6FixedNatGlobalS 125 } 

		nat44UdpFullconeFreedShadow OBJECT-TYPE
		SYNTAX  CounterBasedGauge64 
		MAX-ACCESS read-only 
		STATUS current
		DESCRIPTION  "NAT44 UDP Full-Cone Freed" 
		::={ acosCgnv6FixedNatGlobalS 126 } 

		nat44UdpAlgFullconeCreatedShadow OBJECT-TYPE
		SYNTAX  CounterBasedGauge64 
		MAX-ACCESS read-only 
		STATUS current
		DESCRIPTION  "NAT44 UDP ALG Full-Cone Created" 
		::={ acosCgnv6FixedNatGlobalS 127 } 

		nat44UdpAlgFullconeFreedShadow OBJECT-TYPE
		SYNTAX  CounterBasedGauge64 
		MAX-ACCESS read-only 
		STATUS current
		DESCRIPTION  "NAT44 UDP ALG Full-Cone Freed" 
		::={ acosCgnv6FixedNatGlobalS 128 } 

		nat64TcpFullconeCreatedShadow OBJECT-TYPE
		SYNTAX  CounterBasedGauge64 
		MAX-ACCESS read-only 
		STATUS current
		DESCRIPTION  "NAT64 TCP Full-Cone Created" 
		::={ acosCgnv6FixedNatGlobalS 129 } 

		nat64TcpFullconeFreedShadow OBJECT-TYPE
		SYNTAX  CounterBasedGauge64 
		MAX-ACCESS read-only 
		STATUS current
		DESCRIPTION  "NAT64 TCP Full-Cone Freed" 
		::={ acosCgnv6FixedNatGlobalS 130 } 

		nat64UdpFullconeCreatedShadow OBJECT-TYPE
		SYNTAX  CounterBasedGauge64 
		MAX-ACCESS read-only 
		STATUS current
		DESCRIPTION  "NAT64 UDP Full-Cone Created" 
		::={ acosCgnv6FixedNatGlobalS 131 } 

		nat64UdpFullconeFreedShadow OBJECT-TYPE
		SYNTAX  CounterBasedGauge64 
		MAX-ACCESS read-only 
		STATUS current
		DESCRIPTION  "NAT64 UDP Full-Cone Freed" 
		::={ acosCgnv6FixedNatGlobalS 132 } 

		nat64UdpAlgFullconeCreatedShadow OBJECT-TYPE
		SYNTAX  CounterBasedGauge64 
		MAX-ACCESS read-only 
		STATUS current
		DESCRIPTION  "NAT64 UDP ALG Full-Cone Created" 
		::={ acosCgnv6FixedNatGlobalS 133 } 

		nat64UdpAlgFullconeFreedShadow OBJECT-TYPE
		SYNTAX  CounterBasedGauge64 
		MAX-ACCESS read-only 
		STATUS current
		DESCRIPTION  "NAT64 UDP ALG Full-Cone Freed" 
		::={ acosCgnv6FixedNatGlobalS 134 } 

		dsliteTcpFullconeCreatedShadow OBJECT-TYPE
		SYNTAX  CounterBasedGauge64 
		MAX-ACCESS read-only 
		STATUS current
		DESCRIPTION  "DS-Lite TCP Full-Cone Created" 
		::={ acosCgnv6FixedNatGlobalS 135 } 

		dsliteTcpFullconeFreedShadow OBJECT-TYPE
		SYNTAX  CounterBasedGauge64 
		MAX-ACCESS read-only 
		STATUS current
		DESCRIPTION  "DS-Lite TCP Full-Cone Freed" 
		::={ acosCgnv6FixedNatGlobalS 136 } 

		dsliteUdpFullconeCreatedShadow OBJECT-TYPE
		SYNTAX  CounterBasedGauge64 
		MAX-ACCESS read-only 
		STATUS current
		DESCRIPTION  "DS-Lite UDP Full-Cone Created" 
		::={ acosCgnv6FixedNatGlobalS 137 } 

		dsliteUdpFullconeFreedShadow OBJECT-TYPE
		SYNTAX  CounterBasedGauge64 
		MAX-ACCESS read-only 
		STATUS current
		DESCRIPTION  "DS-Lite UDP Full-Cone Freed" 
		::={ acosCgnv6FixedNatGlobalS 138 } 

		dsliteUdpAlgFullconeCreatedShadow OBJECT-TYPE
		SYNTAX  CounterBasedGauge64 
		MAX-ACCESS read-only 
		STATUS current
		DESCRIPTION  "DS-Lite UDP ALG Full-Cone Created" 
		::={ acosCgnv6FixedNatGlobalS 139 } 

		dsliteUdpAlgFullconeFreedShadow OBJECT-TYPE
		SYNTAX  CounterBasedGauge64 
		MAX-ACCESS read-only 
		STATUS current
		DESCRIPTION  "DS-Lite UDP ALG Full-Cone Freed" 
		::={ acosCgnv6FixedNatGlobalS 140 } 

		h323AlgReuseFullcone OBJECT-TYPE
		SYNTAX  CounterBasedGauge64 
		MAX-ACCESS read-only 
		STATUS current
		DESCRIPTION  "H323 ALG Reuse Full-cone Session" 
		::={ acosCgnv6FixedNatGlobalS 141 } 

		h323AlgFullconeMismatch OBJECT-TYPE
		SYNTAX  CounterBasedGauge64 
		MAX-ACCESS read-only 
		STATUS current
		DESCRIPTION  "H323 ALG Full-cone Session Mismatch" 
		::={ acosCgnv6FixedNatGlobalS 142 } 

		h323AlgCreateFullconeFailure OBJECT-TYPE
		SYNTAX  CounterBasedGauge64 
		MAX-ACCESS read-only 
		STATUS current
		DESCRIPTION  "H323 ALG Create Full-cone Session Failure" 
		::={ acosCgnv6FixedNatGlobalS 143 } 

		h323AlgSingleRtpFullcone OBJECT-TYPE
		SYNTAX  CounterBasedGauge64 
		MAX-ACCESS read-only 
		STATUS current
		DESCRIPTION  "H323 ALG Single RTP Full-cone Found" 
		::={ acosCgnv6FixedNatGlobalS 144 } 

		h323AlgRtcpFullconeMismatch OBJECT-TYPE
		SYNTAX  CounterBasedGauge64 
		MAX-ACCESS read-only 
		STATUS current
		DESCRIPTION  "H323 ALG RTCP Full-cone NAT Port Mismatch" 
		::={ acosCgnv6FixedNatGlobalS 145 } 

		h323AlgReuseRtpRtcpFullcone OBJECT-TYPE
		SYNTAX  CounterBasedGauge64 
		MAX-ACCESS read-only 
		STATUS current
		DESCRIPTION  "H323 ALG Reuse RTP/RTCP Full-cone Session" 
		::={ acosCgnv6FixedNatGlobalS 146 } 

		h323AlgSingleRtcpFullcone OBJECT-TYPE
		SYNTAX  CounterBasedGauge64 
		MAX-ACCESS read-only 
		STATUS current
		DESCRIPTION  "H323 ALG Single RTCP Full-cone Found" 
		::={ acosCgnv6FixedNatGlobalS 147 } 

		h323AlgCreateRtpFullconeFailure OBJECT-TYPE
		SYNTAX  CounterBasedGauge64 
		MAX-ACCESS read-only 
		STATUS current
		DESCRIPTION  "H323 ALG Create RTP Full-cone Session Failure" 
		::={ acosCgnv6FixedNatGlobalS 148 } 

		h323AlgCreateRtcpFullconeFailure OBJECT-TYPE
		SYNTAX  CounterBasedGauge64 
		MAX-ACCESS read-only 
		STATUS current
		DESCRIPTION  "H323 ALG Create RTCP Full-cone Session Failure" 
		::={ acosCgnv6FixedNatGlobalS 149 } 

		mgcpAlgReuseFullcone OBJECT-TYPE
		SYNTAX  CounterBasedGauge64 
		MAX-ACCESS read-only 
		STATUS current
		DESCRIPTION  "MGCP ALG Reuse Full-cone Session" 
		::={ acosCgnv6FixedNatGlobalS 150 } 

		mgcpAlgFullconeMismatch OBJECT-TYPE
		SYNTAX  CounterBasedGauge64 
		MAX-ACCESS read-only 
		STATUS current
		DESCRIPTION  "MGCP ALG Full-cone Session Mismatch" 
		::={ acosCgnv6FixedNatGlobalS 151 } 

		mgcpAlgCreateFullconeFailure OBJECT-TYPE
		SYNTAX  CounterBasedGauge64 
		MAX-ACCESS read-only 
		STATUS current
		DESCRIPTION  "MGCP ALG Create Full-cone Session Failure" 
		::={ acosCgnv6FixedNatGlobalS 152 } 

		mgcpAlgSingleRtpFullcone OBJECT-TYPE
		SYNTAX  CounterBasedGauge64 
		MAX-ACCESS read-only 
		STATUS current
		DESCRIPTION  "MGCP ALG Single RTP Full-cone Found" 
		::={ acosCgnv6FixedNatGlobalS 153 } 

		mgcpAlgRtcpFullconeMismatch OBJECT-TYPE
		SYNTAX  CounterBasedGauge64 
		MAX-ACCESS read-only 
		STATUS current
		DESCRIPTION  "MGCP ALG RTCP Full-cone NAT Port Mismatch" 
		::={ acosCgnv6FixedNatGlobalS 154 } 

		mgcpAlgReuseRtpRtcpFullcone OBJECT-TYPE
		SYNTAX  CounterBasedGauge64 
		MAX-ACCESS read-only 
		STATUS current
		DESCRIPTION  "MGCP ALG Reuse RTP/RTCP Full-cone Session" 
		::={ acosCgnv6FixedNatGlobalS 155 } 

		mgcpAlgSingleRtcpFullcone OBJECT-TYPE
		SYNTAX  CounterBasedGauge64 
		MAX-ACCESS read-only 
		STATUS current
		DESCRIPTION  "MGCP ALG Single RTCP Full-cone Found" 
		::={ acosCgnv6FixedNatGlobalS 156 } 

		mgcpAlgCreateRtpFullconeFailure OBJECT-TYPE
		SYNTAX  CounterBasedGauge64 
		MAX-ACCESS read-only 
		STATUS current
		DESCRIPTION  "MGCP ALG Create RTP Full-cone Session Failure" 
		::={ acosCgnv6FixedNatGlobalS 157 } 

		mgcpAlgCreateRtcpFullconeFailure OBJECT-TYPE
		SYNTAX  CounterBasedGauge64 
		MAX-ACCESS read-only 
		STATUS current
		DESCRIPTION  "MGCP ALG Create RTCP Full-cone Session Failure" 
		::={ acosCgnv6FixedNatGlobalS 158 } 

		userUnusableDrop OBJECT-TYPE
		SYNTAX  CounterBasedGauge64 
		MAX-ACCESS read-only 
		STATUS current
		DESCRIPTION  "Fixed NAT User Unusable Drop" 
		::={ acosCgnv6FixedNatGlobalS 159 } 

		ipv4UserUnusable OBJECT-TYPE
		SYNTAX  CounterBasedGauge64 
		MAX-ACCESS read-only 
		STATUS current
		DESCRIPTION  "Fixed NAT IPv4 User Marked Unusable" 
		::={ acosCgnv6FixedNatGlobalS 160 } 

		ipv6UserUnusable OBJECT-TYPE
		SYNTAX  CounterBasedGauge64 
		MAX-ACCESS read-only 
		STATUS current
		DESCRIPTION  "Fixed NAT IPv6 User Marked Unusable" 
		::={ acosCgnv6FixedNatGlobalS 161 } 

		ipdDisabled OBJECT-TYPE
		SYNTAX  CounterBasedGauge64 
		MAX-ACCESS read-only 
		STATUS current
		DESCRIPTION  "Fixed NAT IPD disabled" 
		::={ acosCgnv6FixedNatGlobalS 162 } 

		dsliteTunnelFrag OBJECT-TYPE
		SYNTAX  CounterBasedGauge64 
		MAX-ACCESS read-only 
		STATUS current
		DESCRIPTION  "IPv4 Fragment DS-Lite Packet" 
		::={ acosCgnv6FixedNatGlobalS 163 } 

		totalTcpOverloadAcquired OBJECT-TYPE
		SYNTAX  CounterBasedGauge64 
		MAX-ACCESS read-only 
		STATUS current
		DESCRIPTION  "Total TCP ports acquired for port overloading" 
		::={ acosCgnv6FixedNatGlobalS 164 } 

		totalUdpOverloadAcquired OBJECT-TYPE
		SYNTAX  CounterBasedGauge64 
		MAX-ACCESS read-only 
		STATUS current
		DESCRIPTION  "Total UDP ports acquired for port overloading" 
		::={ acosCgnv6FixedNatGlobalS 165 } 

		totalTcpOverloadReleased OBJECT-TYPE
		SYNTAX  CounterBasedGauge64 
		MAX-ACCESS read-only 
		STATUS current
		DESCRIPTION  "Total TCP ports released from port overloading" 
		::={ acosCgnv6FixedNatGlobalS 166 } 

		totalUdpOverloadReleased OBJECT-TYPE
		SYNTAX  CounterBasedGauge64 
		MAX-ACCESS read-only 
		STATUS current
		DESCRIPTION  "Total UDP ports released from port overloading" 
		::={ acosCgnv6FixedNatGlobalS 167 } 

		totalTcpAllocOverload OBJECT-TYPE
		SYNTAX  CounterBasedGauge64 
		MAX-ACCESS read-only 
		STATUS current
		DESCRIPTION  "Total TCP ports allocated via overload" 
		::={ acosCgnv6FixedNatGlobalS 168 } 

		totalUdpAllocOverload OBJECT-TYPE
		SYNTAX  CounterBasedGauge64 
		MAX-ACCESS read-only 
		STATUS current
		DESCRIPTION  "Total UDP ports allocated via overload" 
		::={ acosCgnv6FixedNatGlobalS 169 } 

		totalTcpFreeOverload OBJECT-TYPE
		SYNTAX  CounterBasedGauge64 
		MAX-ACCESS read-only 
		STATUS current
		DESCRIPTION  "Total TCP ports freed via overload" 
		::={ acosCgnv6FixedNatGlobalS 170 } 

		totalUdpFreeOverload OBJECT-TYPE
		SYNTAX  CounterBasedGauge64 
		MAX-ACCESS read-only 
		STATUS current
		DESCRIPTION  "Total UDP ports freed via overload" 
		::={ acosCgnv6FixedNatGlobalS 171 } 

		portOverloadSmpDeleteScheduled OBJECT-TYPE
		SYNTAX  CounterBasedGauge64 
		MAX-ACCESS read-only 
		STATUS current
		DESCRIPTION  "Port overload SMP conn delete scheduled" 
		::={ acosCgnv6FixedNatGlobalS 172 } 

		portOverloadSmpMemAllocated OBJECT-TYPE
		SYNTAX  CounterBasedGauge64 
		MAX-ACCESS read-only 
		STATUS current
		DESCRIPTION  "Port overload SMP mem allocated" 
		::={ acosCgnv6FixedNatGlobalS 173 } 

		portOverloadOutOfMemory OBJECT-TYPE
		SYNTAX  CounterBasedGauge64 
		MAX-ACCESS read-only 
		STATUS current
		DESCRIPTION  "Port overload out of memory" 
		::={ acosCgnv6FixedNatGlobalS 174 } 

		portOverloadSmpFree OBJECT-TYPE
		SYNTAX  CounterBasedGauge64 
		MAX-ACCESS read-only 
		STATUS current
		DESCRIPTION  "Port overload SMP conn free" 
		::={ acosCgnv6FixedNatGlobalS 175 } 

		portOverloadSmpFreeNoLid OBJECT-TYPE
		SYNTAX  CounterBasedGauge64 
		MAX-ACCESS read-only 
		STATUS current
		DESCRIPTION  "Port overload SMP conn free no lid" 
		::={ acosCgnv6FixedNatGlobalS 176 } 

		portOverloadFreeSmpNotFound OBJECT-TYPE
		SYNTAX  CounterBasedGauge64 
		MAX-ACCESS read-only 
		STATUS current
		DESCRIPTION  "Port overload free SMP conn not found" 
		::={ acosCgnv6FixedNatGlobalS 177 } 

		portOverloadFailed OBJECT-TYPE
		SYNTAX  CounterBasedGauge64 
		MAX-ACCESS read-only 
		STATUS current
		DESCRIPTION  "Port overload failed" 
		::={ acosCgnv6FixedNatGlobalS 178 } 

		totalTcpOverloadAcquiredShadow OBJECT-TYPE
		SYNTAX  CounterBasedGauge64 
		MAX-ACCESS read-only 
		STATUS current
		DESCRIPTION  "Total TCP ports acquired for port overloading shadow" 
		::={ acosCgnv6FixedNatGlobalS 179 } 

		totalUdpOverloadAcquiredShadow OBJECT-TYPE
		SYNTAX  CounterBasedGauge64 
		MAX-ACCESS read-only 
		STATUS current
		DESCRIPTION  "Total UDP ports acquired for port overloading shadow" 
		::={ acosCgnv6FixedNatGlobalS 180 } 

		totalTcpOverloadReleasedShadow OBJECT-TYPE
		SYNTAX  CounterBasedGauge64 
		MAX-ACCESS read-only 
		STATUS current
		DESCRIPTION  "Total TCP ports released from port overloading shadow" 
		::={ acosCgnv6FixedNatGlobalS 181 } 

		totalUdpOverloadReleasedShadow OBJECT-TYPE
		SYNTAX  CounterBasedGauge64 
		MAX-ACCESS read-only 
		STATUS current
		DESCRIPTION  "Total UDP ports released from port overloading shadow" 
		::={ acosCgnv6FixedNatGlobalS 182 } 

		totalTcpAllocOverloadShadow OBJECT-TYPE
		SYNTAX  CounterBasedGauge64 
		MAX-ACCESS read-only 
		STATUS current
		DESCRIPTION  "Total TCP allocated via overload shadow" 
		::={ acosCgnv6FixedNatGlobalS 183 } 

		totalUdpAllocOverloadShadow OBJECT-TYPE
		SYNTAX  CounterBasedGauge64 
		MAX-ACCESS read-only 
		STATUS current
		DESCRIPTION  "Total UDP allocated via overload shadow" 
		::={ acosCgnv6FixedNatGlobalS 184 } 

		totalTcpFreeOverloadShadow OBJECT-TYPE
		SYNTAX  CounterBasedGauge64 
		MAX-ACCESS read-only 
		STATUS current
		DESCRIPTION  "Total TCP freed via overload shadow" 
		::={ acosCgnv6FixedNatGlobalS 185 } 

		totalUdpFreeOverloadShadow OBJECT-TYPE
		SYNTAX  CounterBasedGauge64 
		MAX-ACCESS read-only 
		STATUS current
		DESCRIPTION  "Total UDP freed via overload shadow" 
		::={ acosCgnv6FixedNatGlobalS 186 } 

		haSessionUserQuotaExceeded OBJECT-TYPE
		SYNTAX  CounterBasedGauge64 
		MAX-ACCESS read-only 
		STATUS current
		DESCRIPTION  "HA Sessions User Quota Exceeded" 
		::={ acosCgnv6FixedNatGlobalS 187 } 

		tcpUserQuotaExceeded OBJECT-TYPE
		SYNTAX  CounterBasedGauge64 
		MAX-ACCESS read-only 
		STATUS current
		DESCRIPTION  "TCP User Quota Exceeded" 
		::={ acosCgnv6FixedNatGlobalS 188 } 

		udpUserQuotaExceeded OBJECT-TYPE
		SYNTAX  CounterBasedGauge64 
		MAX-ACCESS read-only 
		STATUS current
		DESCRIPTION  "UDP User Quota Exceeded" 
		::={ acosCgnv6FixedNatGlobalS 189 } 

		icmpUserQuotaExceeded OBJECT-TYPE
		SYNTAX  CounterBasedGauge64 
		MAX-ACCESS read-only 
		STATUS current
		DESCRIPTION  "ICMP User Quota Exceeded" 
		::={ acosCgnv6FixedNatGlobalS 190 } 

		haTcpUserQuotaExceeded OBJECT-TYPE
		SYNTAX  CounterBasedGauge64 
		MAX-ACCESS read-only 
		STATUS current
		DESCRIPTION  "HA TCP User Quota Exceeded" 
		::={ acosCgnv6FixedNatGlobalS 191 } 

		haUdpUserQuotaExceeded OBJECT-TYPE
		SYNTAX  CounterBasedGauge64 
		MAX-ACCESS read-only 
		STATUS current
		DESCRIPTION  "HA UDP User Quota Exceeded" 
		::={ acosCgnv6FixedNatGlobalS 192 } 

		haIcmpUserQuotaExceeded OBJECT-TYPE
		SYNTAX  CounterBasedGauge64 
		MAX-ACCESS read-only 
		STATUS current
		DESCRIPTION  "HA ICMP User Quota Exceeded" 
		::={ acosCgnv6FixedNatGlobalS 193 } 

		cgnv6FixednatGlobalNatPortUnavailableTcp OBJECT-TYPE
		SYNTAX  CounterBasedGauge64 
		MAX-ACCESS read-only 
		STATUS current
		DESCRIPTION  "HA TCP NAT Port Unavailable" 
		::={ acosCgnv6FixedNatGlobalS 194 } 

		cgnv6FixednatGlobalNatPortUnavailableUdp OBJECT-TYPE
		SYNTAX  CounterBasedGauge64 
		MAX-ACCESS read-only 
		STATUS current
		DESCRIPTION  "HA UDP NAT Port Unavailable" 
		::={ acosCgnv6FixedNatGlobalS 195 } 

		cgnv6FixednatGlobalNatPortUnavailableIcmp OBJECT-TYPE
		SYNTAX  CounterBasedGauge64 
		MAX-ACCESS read-only 
		STATUS current
		DESCRIPTION  "HA ICMP NAT Port Unavailable" 
		::={ acosCgnv6FixedNatGlobalS 196 } 

		fnat44FwdIngressPacketsTcp OBJECT-TYPE
		SYNTAX  CounterBasedGauge64 
		MAX-ACCESS read-only 
		STATUS current
		DESCRIPTION  "Fixed NAT44 Forward Ingress Packets TCP" 
		::={ acosCgnv6FixedNatGlobalS 197 } 

		fnat44FwdEgressPacketsTcp OBJECT-TYPE
		SYNTAX  CounterBasedGauge64 
		MAX-ACCESS read-only 
		STATUS current
		DESCRIPTION  "Fixed NAT44 Forward Egress Packets TCP" 
		::={ acosCgnv6FixedNatGlobalS 198 } 

		fnat44RevIngressPacketsTcp OBJECT-TYPE
		SYNTAX  CounterBasedGauge64 
		MAX-ACCESS read-only 
		STATUS current
		DESCRIPTION  "Fixed NAT44 Reverse Ingress Packets TCP" 
		::={ acosCgnv6FixedNatGlobalS 199 } 

		fnat44RevEgressPacketsTcp OBJECT-TYPE
		SYNTAX  CounterBasedGauge64 
		MAX-ACCESS read-only 
		STATUS current
		DESCRIPTION  "Fixed NAT44 Reverse Egress Packets TCP" 
		::={ acosCgnv6FixedNatGlobalS 200 } 

		fnat44FwdIngressBytesTcp OBJECT-TYPE
		SYNTAX  CounterBasedGauge64 
		MAX-ACCESS read-only 
		STATUS current
		DESCRIPTION  "Fixed NAT44 Forward Ingress Bytes TCP" 
		::={ acosCgnv6FixedNatGlobalS 201 } 

		fnat44FwdEgressBytesTcp OBJECT-TYPE
		SYNTAX  CounterBasedGauge64 
		MAX-ACCESS read-only 
		STATUS current
		DESCRIPTION  "Fixed NAT44 Forward Egress Bytes TCP" 
		::={ acosCgnv6FixedNatGlobalS 202 } 

		fnat44RevIngressBytesTcp OBJECT-TYPE
		SYNTAX  CounterBasedGauge64 
		MAX-ACCESS read-only 
		STATUS current
		DESCRIPTION  "Fixed NAT44 Reverse Ingress Bytes TCP" 
		::={ acosCgnv6FixedNatGlobalS 203 } 

		fnat44RevEgressBytesTcp OBJECT-TYPE
		SYNTAX  CounterBasedGauge64 
		MAX-ACCESS read-only 
		STATUS current
		DESCRIPTION  "Fixed NAT44 Reverse Egress Bytes TCP" 
		::={ acosCgnv6FixedNatGlobalS 204 } 

		fnat44FwdIngressPacketsUdp OBJECT-TYPE
		SYNTAX  CounterBasedGauge64 
		MAX-ACCESS read-only 
		STATUS current
		DESCRIPTION  "Fixed NAT44 Forward Ingress Packets UDP" 
		::={ acosCgnv6FixedNatGlobalS 205 } 

		fnat44FwdEgressPacketsUdp OBJECT-TYPE
		SYNTAX  CounterBasedGauge64 
		MAX-ACCESS read-only 
		STATUS current
		DESCRIPTION  "Fixed NAT44 Forward Egress Packets UDP" 
		::={ acosCgnv6FixedNatGlobalS 206 } 

		fnat44RevIngressPacketsUdp OBJECT-TYPE
		SYNTAX  CounterBasedGauge64 
		MAX-ACCESS read-only 
		STATUS current
		DESCRIPTION  "Fixed NAT44 Reverse Ingress Packets UDP" 
		::={ acosCgnv6FixedNatGlobalS 207 } 

		fnat44RevEgressPacketsUdp OBJECT-TYPE
		SYNTAX  CounterBasedGauge64 
		MAX-ACCESS read-only 
		STATUS current
		DESCRIPTION  "Fixed NAT44 Reverse Egress Packets UDP" 
		::={ acosCgnv6FixedNatGlobalS 208 } 

		fnat44FwdIngressBytesUdp OBJECT-TYPE
		SYNTAX  CounterBasedGauge64 
		MAX-ACCESS read-only 
		STATUS current
		DESCRIPTION  "Fixed NAT44 Forward Ingress Bytes UDP" 
		::={ acosCgnv6FixedNatGlobalS 209 } 

		fnat44FwdEgressBytesUdp OBJECT-TYPE
		SYNTAX  CounterBasedGauge64 
		MAX-ACCESS read-only 
		STATUS current
		DESCRIPTION  "Fixed NAT44 Forward Egress Bytes UDP" 
		::={ acosCgnv6FixedNatGlobalS 210 } 

		fnat44RevIngressBytesUdp OBJECT-TYPE
		SYNTAX  CounterBasedGauge64 
		MAX-ACCESS read-only 
		STATUS current
		DESCRIPTION  "Fixed NAT44 Reverse Ingress Bytes UDP" 
		::={ acosCgnv6FixedNatGlobalS 211 } 

		fnat44RevEgressBytesUdp OBJECT-TYPE
		SYNTAX  CounterBasedGauge64 
		MAX-ACCESS read-only 
		STATUS current
		DESCRIPTION  "Fixed NAT44 Reverse Egress Bytes UDP" 
		::={ acosCgnv6FixedNatGlobalS 212 } 

		fnat44FwdIngressPacketsIcmp OBJECT-TYPE
		SYNTAX  CounterBasedGauge64 
		MAX-ACCESS read-only 
		STATUS current
		DESCRIPTION  "Fixed NAT44 Forward Ingress Packets ICMP" 
		::={ acosCgnv6FixedNatGlobalS 213 } 

		fnat44FwdEgressPacketsIcmp OBJECT-TYPE
		SYNTAX  CounterBasedGauge64 
		MAX-ACCESS read-only 
		STATUS current
		DESCRIPTION  "Fixed NAT44 Forward Egress Packets ICMP" 
		::={ acosCgnv6FixedNatGlobalS 214 } 

		fnat44RevIngressPacketsIcmp OBJECT-TYPE
		SYNTAX  CounterBasedGauge64 
		MAX-ACCESS read-only 
		STATUS current
		DESCRIPTION  "Fixed NAT44 Reverse Ingress Packets ICMP" 
		::={ acosCgnv6FixedNatGlobalS 215 } 

		fnat44RevEgressPacketsIcmp OBJECT-TYPE
		SYNTAX  CounterBasedGauge64 
		MAX-ACCESS read-only 
		STATUS current
		DESCRIPTION  "Fixed NAT44 Reverse Egress Packets ICMP" 
		::={ acosCgnv6FixedNatGlobalS 216 } 

		fnat44FwdIngressBytesIcmp OBJECT-TYPE
		SYNTAX  CounterBasedGauge64 
		MAX-ACCESS read-only 
		STATUS current
		DESCRIPTION  "Fixed NAT44 Forward Ingress Bytes ICMP" 
		::={ acosCgnv6FixedNatGlobalS 217 } 

		fnat44FwdEgressBytesIcmp OBJECT-TYPE
		SYNTAX  CounterBasedGauge64 
		MAX-ACCESS read-only 
		STATUS current
		DESCRIPTION  "Fixed NAT44 Forward Egress Bytes ICMP" 
		::={ acosCgnv6FixedNatGlobalS 218 } 

		fnat44RevIngressBytesIcmp OBJECT-TYPE
		SYNTAX  CounterBasedGauge64 
		MAX-ACCESS read-only 
		STATUS current
		DESCRIPTION  "Fixed NAT44 Reverse Ingress Bytes ICMP" 
		::={ acosCgnv6FixedNatGlobalS 219 } 

		fnat44RevEgressBytesIcmp OBJECT-TYPE
		SYNTAX  CounterBasedGauge64 
		MAX-ACCESS read-only 
		STATUS current
		DESCRIPTION  "Fixed NAT44 Reverse Egress Bytes ICMP" 
		::={ acosCgnv6FixedNatGlobalS 220 } 

		fnat44FwdIngressPacketsOthers OBJECT-TYPE
		SYNTAX  CounterBasedGauge64 
		MAX-ACCESS read-only 
		STATUS current
		DESCRIPTION  "Fixed NAT44 Forward Ingress Packets OTHERS" 
		::={ acosCgnv6FixedNatGlobalS 221 } 

		fnat44FwdEgressPacketsOthers OBJECT-TYPE
		SYNTAX  CounterBasedGauge64 
		MAX-ACCESS read-only 
		STATUS current
		DESCRIPTION  "Fixed NAT44 Forward Egress Packets OTHERS" 
		::={ acosCgnv6FixedNatGlobalS 222 } 

		fnat44RevIngressPacketsOthers OBJECT-TYPE
		SYNTAX  CounterBasedGauge64 
		MAX-ACCESS read-only 
		STATUS current
		DESCRIPTION  "Fixed NAT44 Reverse Ingress Packets OTHERS" 
		::={ acosCgnv6FixedNatGlobalS 223 } 

		fnat44RevEgressPacketsOthers OBJECT-TYPE
		SYNTAX  CounterBasedGauge64 
		MAX-ACCESS read-only 
		STATUS current
		DESCRIPTION  "Fixed NAT44 Reverse Egress Packets OTHERS" 
		::={ acosCgnv6FixedNatGlobalS 224 } 

		fnat44FwdIngressBytesOthers OBJECT-TYPE
		SYNTAX  CounterBasedGauge64 
		MAX-ACCESS read-only 
		STATUS current
		DESCRIPTION  "Fixed NAT44 Forward Ingress Bytes OTHERS" 
		::={ acosCgnv6FixedNatGlobalS 225 } 

		fnat44FwdEgressBytesOthers OBJECT-TYPE
		SYNTAX  CounterBasedGauge64 
		MAX-ACCESS read-only 
		STATUS current
		DESCRIPTION  "Fixed NAT44 Forward Egress Bytes OTHERS" 
		::={ acosCgnv6FixedNatGlobalS 226 } 

		fnat44RevIngressBytesOthers OBJECT-TYPE
		SYNTAX  CounterBasedGauge64 
		MAX-ACCESS read-only 
		STATUS current
		DESCRIPTION  "Fixed NAT44 Reverse Ingress Bytes OTHERS" 
		::={ acosCgnv6FixedNatGlobalS 227 } 

		fnat44RevEgressBytesOthers OBJECT-TYPE
		SYNTAX  CounterBasedGauge64 
		MAX-ACCESS read-only 
		STATUS current
		DESCRIPTION  "Fixed NAT44 Reverse Egress Bytes OTHERS" 
		::={ acosCgnv6FixedNatGlobalS 228 } 

		fnat44FwdIngressPktSizeRange1 OBJECT-TYPE
		SYNTAX  CounterBasedGauge64 
		MAX-ACCESS read-only 
		STATUS current
		DESCRIPTION  "Fixed NAT44 Forward Ingress Packet size between 0 and 200" 
		::={ acosCgnv6FixedNatGlobalS 229 } 

		fnat44FwdIngressPktSizeRange2 OBJECT-TYPE
		SYNTAX  CounterBasedGauge64 
		MAX-ACCESS read-only 
		STATUS current
		DESCRIPTION  "Fixed NAT44 Forward Ingress Packet size between 201 and 800" 
		::={ acosCgnv6FixedNatGlobalS 230 } 

		fnat44FwdIngressPktSizeRange3 OBJECT-TYPE
		SYNTAX  CounterBasedGauge64 
		MAX-ACCESS read-only 
		STATUS current
		DESCRIPTION  "Fixed NAT44 Forward Ingress Packet size between 801 and 1550" 
		::={ acosCgnv6FixedNatGlobalS 231 } 

		fnat44FwdIngressPktSizeRange4 OBJECT-TYPE
		SYNTAX  CounterBasedGauge64 
		MAX-ACCESS read-only 
		STATUS current
		DESCRIPTION  "Fixed NAT44 Forward Ingress Packet size between 1551 and 9000" 
		::={ acosCgnv6FixedNatGlobalS 232 } 

		fnat44FwdEgressPktSizeRange1 OBJECT-TYPE
		SYNTAX  CounterBasedGauge64 
		MAX-ACCESS read-only 
		STATUS current
		DESCRIPTION  "Fixed NAT44 Forward Egress Packet size between 0 and 200" 
		::={ acosCgnv6FixedNatGlobalS 233 } 

		fnat44FwdEgressPktSizeRange2 OBJECT-TYPE
		SYNTAX  CounterBasedGauge64 
		MAX-ACCESS read-only 
		STATUS current
		DESCRIPTION  "Fixed NAT44 Forward Egress Packet size between 201 and 800" 
		::={ acosCgnv6FixedNatGlobalS 234 } 

		fnat44FwdEgressPktSizeRange3 OBJECT-TYPE
		SYNTAX  CounterBasedGauge64 
		MAX-ACCESS read-only 
		STATUS current
		DESCRIPTION  "Fixed NAT44 Forward Egress Packet size between 801 and 1550" 
		::={ acosCgnv6FixedNatGlobalS 235 } 

		fnat44FwdEgressPktSizeRange4 OBJECT-TYPE
		SYNTAX  CounterBasedGauge64 
		MAX-ACCESS read-only 
		STATUS current
		DESCRIPTION  "Fixed NAT44 Forward Egress Packet size between 1551 and 9000" 
		::={ acosCgnv6FixedNatGlobalS 236 } 

		fnat44RevIngressPktSizeRange1 OBJECT-TYPE
		SYNTAX  CounterBasedGauge64 
		MAX-ACCESS read-only 
		STATUS current
		DESCRIPTION  "Fixed NAT44 Reverse Ingress Packet size between 0 and 200" 
		::={ acosCgnv6FixedNatGlobalS 237 } 

		fnat44RevIngressPktSizeRange2 OBJECT-TYPE
		SYNTAX  CounterBasedGauge64 
		MAX-ACCESS read-only 
		STATUS current
		DESCRIPTION  "Fixed NAT44 Reverse Ingress Packet size between 201 and 800" 
		::={ acosCgnv6FixedNatGlobalS 238 } 

		fnat44RevIngressPktSizeRange3 OBJECT-TYPE
		SYNTAX  CounterBasedGauge64 
		MAX-ACCESS read-only 
		STATUS current
		DESCRIPTION  "Fixed NAT44 Reverse Ingress Packet size between 801 and 1550" 
		::={ acosCgnv6FixedNatGlobalS 239 } 

		fnat44RevIngressPktSizeRange4 OBJECT-TYPE
		SYNTAX  CounterBasedGauge64 
		MAX-ACCESS read-only 
		STATUS current
		DESCRIPTION  "Fixed NAT44 Reverse Ingress Packet size between 1551 and 9000" 
		::={ acosCgnv6FixedNatGlobalS 240 } 

		fnat44RevEgressPktSizeRange1 OBJECT-TYPE
		SYNTAX  CounterBasedGauge64 
		MAX-ACCESS read-only 
		STATUS current
		DESCRIPTION  "Fixed NAT44 Reverse Egress Packet size between 0 and 200" 
		::={ acosCgnv6FixedNatGlobalS 241 } 

		fnat44RevEgressPktSizeRange2 OBJECT-TYPE
		SYNTAX  CounterBasedGauge64 
		MAX-ACCESS read-only 
		STATUS current
		DESCRIPTION  "Fixed NAT44 Reverse Egress Packet size between 201 and 800" 
		::={ acosCgnv6FixedNatGlobalS 242 } 

		fnat44RevEgressPktSizeRange3 OBJECT-TYPE
		SYNTAX  CounterBasedGauge64 
		MAX-ACCESS read-only 
		STATUS current
		DESCRIPTION  "Fixed NAT44 Reverse Egress Packet size between 801 and 1550" 
		::={ acosCgnv6FixedNatGlobalS 243 } 

		fnat44RevEgressPktSizeRange4 OBJECT-TYPE
		SYNTAX  CounterBasedGauge64 
		MAX-ACCESS read-only 
		STATUS current
		DESCRIPTION  "Fixed NAT44 Reverse Egress Packet size between 1551 and 9000" 
		::={ acosCgnv6FixedNatGlobalS 244 } 

		fnat64FwdIngressPacketsTcp OBJECT-TYPE
		SYNTAX  CounterBasedGauge64 
		MAX-ACCESS read-only 
		STATUS current
		DESCRIPTION  "Fixed NAT64 Forward Ingress Packets TCP" 
		::={ acosCgnv6FixedNatGlobalS 245 } 

		fnat64FwdEgressPacketsTcp OBJECT-TYPE
		SYNTAX  CounterBasedGauge64 
		MAX-ACCESS read-only 
		STATUS current
		DESCRIPTION  "Fixed NAT64 Forward Egress Packets TCP" 
		::={ acosCgnv6FixedNatGlobalS 246 } 

		fnat64RevIngressPacketsTcp OBJECT-TYPE
		SYNTAX  CounterBasedGauge64 
		MAX-ACCESS read-only 
		STATUS current
		DESCRIPTION  "Fixed NAT64 Reverse Ingress Packets TCP" 
		::={ acosCgnv6FixedNatGlobalS 247 } 

		fnat64RevEgressPacketsTcp OBJECT-TYPE
		SYNTAX  CounterBasedGauge64 
		MAX-ACCESS read-only 
		STATUS current
		DESCRIPTION  "Fixed NAT64 Reverse Egress Packets TCP" 
		::={ acosCgnv6FixedNatGlobalS 248 } 

		fnat64FwdIngressBytesTcp OBJECT-TYPE
		SYNTAX  CounterBasedGauge64 
		MAX-ACCESS read-only 
		STATUS current
		DESCRIPTION  "Fixed NAT64 Forward Ingress Bytes TCP" 
		::={ acosCgnv6FixedNatGlobalS 249 } 

		fnat64FwdEgressBytesTcp OBJECT-TYPE
		SYNTAX  CounterBasedGauge64 
		MAX-ACCESS read-only 
		STATUS current
		DESCRIPTION  "Fixed NAT64 Forward Egress Bytes TCP" 
		::={ acosCgnv6FixedNatGlobalS 250 } 

		fnat64RevIngressBytesTcp OBJECT-TYPE
		SYNTAX  CounterBasedGauge64 
		MAX-ACCESS read-only 
		STATUS current
		DESCRIPTION  "Fixed NAT64 Reverse Ingress Bytes TCP" 
		::={ acosCgnv6FixedNatGlobalS 251 } 

		fnat64RevEgressBytesTcp OBJECT-TYPE
		SYNTAX  CounterBasedGauge64 
		MAX-ACCESS read-only 
		STATUS current
		DESCRIPTION  "Fixed NAT64 Reverse Egress Bytes TCP" 
		::={ acosCgnv6FixedNatGlobalS 252 } 

		fnat64FwdIngressPacketsUdp OBJECT-TYPE
		SYNTAX  CounterBasedGauge64 
		MAX-ACCESS read-only 
		STATUS current
		DESCRIPTION  "Fixed NAT64 Forward Ingress Packets UDP" 
		::={ acosCgnv6FixedNatGlobalS 253 } 

		fnat64FwdEgressPacketsUdp OBJECT-TYPE
		SYNTAX  CounterBasedGauge64 
		MAX-ACCESS read-only 
		STATUS current
		DESCRIPTION  "Fixed NAT64 Forward Egress Packets UDP" 
		::={ acosCgnv6FixedNatGlobalS 254 } 

		fnat64RevIngressPacketsUdp OBJECT-TYPE
		SYNTAX  CounterBasedGauge64 
		MAX-ACCESS read-only 
		STATUS current
		DESCRIPTION  "Fixed NAT64 Reverse Ingress Packets UDP" 
		::={ acosCgnv6FixedNatGlobalS 255 } 

		fnat64RevEgressPacketsUdp OBJECT-TYPE
		SYNTAX  CounterBasedGauge64 
		MAX-ACCESS read-only 
		STATUS current
		DESCRIPTION  "Fixed NAT64 Reverse Egress Packets UDP" 
		::={ acosCgnv6FixedNatGlobalS 256 } 

		fnat64FwdIngressBytesUdp OBJECT-TYPE
		SYNTAX  CounterBasedGauge64 
		MAX-ACCESS read-only 
		STATUS current
		DESCRIPTION  "Fixed NAT64 Forward Ingress Bytes UDP" 
		::={ acosCgnv6FixedNatGlobalS 257 } 

		fnat64FwdEgressBytesUdp OBJECT-TYPE
		SYNTAX  CounterBasedGauge64 
		MAX-ACCESS read-only 
		STATUS current
		DESCRIPTION  "Fixed NAT64 Forward Egress Bytes UDP" 
		::={ acosCgnv6FixedNatGlobalS 258 } 

		fnat64RevIngressBytesUdp OBJECT-TYPE
		SYNTAX  CounterBasedGauge64 
		MAX-ACCESS read-only 
		STATUS current
		DESCRIPTION  "Fixed NAT64 Reverse Ingress Bytes UDP" 
		::={ acosCgnv6FixedNatGlobalS 259 } 

		fnat64RevEgressBytesUdp OBJECT-TYPE
		SYNTAX  CounterBasedGauge64 
		MAX-ACCESS read-only 
		STATUS current
		DESCRIPTION  "Fixed NAT64 Reverse Egress Bytes UDP" 
		::={ acosCgnv6FixedNatGlobalS 260 } 

		fnat64FwdIngressPacketsIcmp OBJECT-TYPE
		SYNTAX  CounterBasedGauge64 
		MAX-ACCESS read-only 
		STATUS current
		DESCRIPTION  "Fixed NAT64 Forward Ingress Packets ICMP" 
		::={ acosCgnv6FixedNatGlobalS 261 } 

		fnat64FwdEgressPacketsIcmp OBJECT-TYPE
		SYNTAX  CounterBasedGauge64 
		MAX-ACCESS read-only 
		STATUS current
		DESCRIPTION  "Fixed NAT64 Forward Egress Packets ICMP" 
		::={ acosCgnv6FixedNatGlobalS 262 } 

		fnat64RevIngressPacketsIcmp OBJECT-TYPE
		SYNTAX  CounterBasedGauge64 
		MAX-ACCESS read-only 
		STATUS current
		DESCRIPTION  "Fixed NAT64 Reverse Ingress Packets ICMP" 
		::={ acosCgnv6FixedNatGlobalS 263 } 

		fnat64RevEgressPacketsIcmp OBJECT-TYPE
		SYNTAX  CounterBasedGauge64 
		MAX-ACCESS read-only 
		STATUS current
		DESCRIPTION  "Fixed NAT64 Reverse Egress Packets ICMP" 
		::={ acosCgnv6FixedNatGlobalS 264 } 

		fnat64FwdIngressBytesIcmp OBJECT-TYPE
		SYNTAX  CounterBasedGauge64 
		MAX-ACCESS read-only 
		STATUS current
		DESCRIPTION  "Fixed NAT64 Forward Ingress Bytes ICMP" 
		::={ acosCgnv6FixedNatGlobalS 265 } 

		fnat64FwdEgressBytesIcmp OBJECT-TYPE
		SYNTAX  CounterBasedGauge64 
		MAX-ACCESS read-only 
		STATUS current
		DESCRIPTION  "Fixed NAT64 Forward Egress Bytes ICMP" 
		::={ acosCgnv6FixedNatGlobalS 266 } 

		fnat64RevIngressBytesIcmp OBJECT-TYPE
		SYNTAX  CounterBasedGauge64 
		MAX-ACCESS read-only 
		STATUS current
		DESCRIPTION  "Fixed NAT64 Reverse Ingress Bytes ICMP" 
		::={ acosCgnv6FixedNatGlobalS 267 } 

		fnat64RevEgressBytesIcmp OBJECT-TYPE
		SYNTAX  CounterBasedGauge64 
		MAX-ACCESS read-only 
		STATUS current
		DESCRIPTION  "Fixed NAT64 Reverse Egress Bytes ICMP" 
		::={ acosCgnv6FixedNatGlobalS 268 } 

		fnat64FwdIngressPacketsOthers OBJECT-TYPE
		SYNTAX  CounterBasedGauge64 
		MAX-ACCESS read-only 
		STATUS current
		DESCRIPTION  "Fixed NAT64 Forward Ingress Packets OTHERS" 
		::={ acosCgnv6FixedNatGlobalS 269 } 

		fnat64FwdEgressPacketsOthers OBJECT-TYPE
		SYNTAX  CounterBasedGauge64 
		MAX-ACCESS read-only 
		STATUS current
		DESCRIPTION  "Fixed NAT64 Forward Egress Packets OTHERS" 
		::={ acosCgnv6FixedNatGlobalS 270 } 

		fnat64RevIngressPacketsOthers OBJECT-TYPE
		SYNTAX  CounterBasedGauge64 
		MAX-ACCESS read-only 
		STATUS current
		DESCRIPTION  "Fixed NAT64 Reverse Ingress Packets OTHERS" 
		::={ acosCgnv6FixedNatGlobalS 271 } 

		fnat64RevEgressPacketsOthers OBJECT-TYPE
		SYNTAX  CounterBasedGauge64 
		MAX-ACCESS read-only 
		STATUS current
		DESCRIPTION  "Fixed NAT64 Reverse Egress Packets OTHERS" 
		::={ acosCgnv6FixedNatGlobalS 272 } 

		fnat64FwdIngressBytesOthers OBJECT-TYPE
		SYNTAX  CounterBasedGauge64 
		MAX-ACCESS read-only 
		STATUS current
		DESCRIPTION  "Fixed NAT64 Forward Ingress Bytes OTHERS" 
		::={ acosCgnv6FixedNatGlobalS 273 } 

		fnat64FwdEgressBytesOthers OBJECT-TYPE
		SYNTAX  CounterBasedGauge64 
		MAX-ACCESS read-only 
		STATUS current
		DESCRIPTION  "Fixed NAT64 Forward Egress Bytes OTHERS" 
		::={ acosCgnv6FixedNatGlobalS 274 } 

		fnat64RevIngressBytesOthers OBJECT-TYPE
		SYNTAX  CounterBasedGauge64 
		MAX-ACCESS read-only 
		STATUS current
		DESCRIPTION  "Fixed NAT64 Reverse Ingress Bytes OTHERS" 
		::={ acosCgnv6FixedNatGlobalS 275 } 

		fnat64RevEgressBytesOthers OBJECT-TYPE
		SYNTAX  CounterBasedGauge64 
		MAX-ACCESS read-only 
		STATUS current
		DESCRIPTION  "Fixed NAT64 Reverse Egress Bytes OTHERS" 
		::={ acosCgnv6FixedNatGlobalS 276 } 

		fnat64FwdIngressPktSizeRange1 OBJECT-TYPE
		SYNTAX  CounterBasedGauge64 
		MAX-ACCESS read-only 
		STATUS current
		DESCRIPTION  "Fixed NAT64 Forward Ingress Packet size between 0 and 200" 
		::={ acosCgnv6FixedNatGlobalS 277 } 

		fnat64FwdIngressPktSizeRange2 OBJECT-TYPE
		SYNTAX  CounterBasedGauge64 
		MAX-ACCESS read-only 
		STATUS current
		DESCRIPTION  "Fixed NAT64 Forward Ingress Packet size between 201 and 800" 
		::={ acosCgnv6FixedNatGlobalS 278 } 

		fnat64FwdIngressPktSizeRange3 OBJECT-TYPE
		SYNTAX  CounterBasedGauge64 
		MAX-ACCESS read-only 
		STATUS current
		DESCRIPTION  "Fixed NAT64 Forward Ingress Packet size between 801 and 1550" 
		::={ acosCgnv6FixedNatGlobalS 279 } 

		fnat64FwdIngressPktSizeRange4 OBJECT-TYPE
		SYNTAX  CounterBasedGauge64 
		MAX-ACCESS read-only 
		STATUS current
		DESCRIPTION  "Fixed NAT64 Forward Ingress Packet size between 1551 and 9000" 
		::={ acosCgnv6FixedNatGlobalS 280 } 

		fnat64FwdEgressPktSizeRange1 OBJECT-TYPE
		SYNTAX  CounterBasedGauge64 
		MAX-ACCESS read-only 
		STATUS current
		DESCRIPTION  "Fixed NAT64 Forward Egress Packet size between 0 and 200" 
		::={ acosCgnv6FixedNatGlobalS 281 } 

		fnat64FwdEgressPktSizeRange2 OBJECT-TYPE
		SYNTAX  CounterBasedGauge64 
		MAX-ACCESS read-only 
		STATUS current
		DESCRIPTION  "Fixed NAT64 Forward Egress Packet size between 201 and 800" 
		::={ acosCgnv6FixedNatGlobalS 282 } 

		fnat64FwdEgressPktSizeRange3 OBJECT-TYPE
		SYNTAX  CounterBasedGauge64 
		MAX-ACCESS read-only 
		STATUS current
		DESCRIPTION  "Fixed NAT64 Forward Egress Packet size between 801 and 1550" 
		::={ acosCgnv6FixedNatGlobalS 283 } 

		fnat64FwdEgressPktSizeRange4 OBJECT-TYPE
		SYNTAX  CounterBasedGauge64 
		MAX-ACCESS read-only 
		STATUS current
		DESCRIPTION  "Fixed NAT64 Forward Egress Packet size between 1551 and 9000" 
		::={ acosCgnv6FixedNatGlobalS 284 } 

		fnat64RevIngressPktSizeRange1 OBJECT-TYPE
		SYNTAX  CounterBasedGauge64 
		MAX-ACCESS read-only 
		STATUS current
		DESCRIPTION  "Fixed NAT64 Reverse Ingress Packet size between 0 and 200" 
		::={ acosCgnv6FixedNatGlobalS 285 } 

		fnat64RevIngressPktSizeRange2 OBJECT-TYPE
		SYNTAX  CounterBasedGauge64 
		MAX-ACCESS read-only 
		STATUS current
		DESCRIPTION  "Fixed NAT64 Reverse Ingress Packet size between 201 and 800" 
		::={ acosCgnv6FixedNatGlobalS 286 } 

		fnat64RevIngressPktSizeRange3 OBJECT-TYPE
		SYNTAX  CounterBasedGauge64 
		MAX-ACCESS read-only 
		STATUS current
		DESCRIPTION  "Fixed NAT64 Reverse Ingress Packet size between 801 and 1550" 
		::={ acosCgnv6FixedNatGlobalS 287 } 

		fnat64RevIngressPktSizeRange4 OBJECT-TYPE
		SYNTAX  CounterBasedGauge64 
		MAX-ACCESS read-only 
		STATUS current
		DESCRIPTION  "Fixed NAT64 Reverse Ingress Packet size between 1551 and 9000" 
		::={ acosCgnv6FixedNatGlobalS 288 } 

		fnat64RevEgressPktSizeRange1 OBJECT-TYPE
		SYNTAX  CounterBasedGauge64 
		MAX-ACCESS read-only 
		STATUS current
		DESCRIPTION  "Fixed NAT64 Reverse Egress Packet size between 0 and 200" 
		::={ acosCgnv6FixedNatGlobalS 289 } 

		fnat64RevEgressPktSizeRange2 OBJECT-TYPE
		SYNTAX  CounterBasedGauge64 
		MAX-ACCESS read-only 
		STATUS current
		DESCRIPTION  "Fixed NAT64 Reverse Egress Packet size between 201 and 800" 
		::={ acosCgnv6FixedNatGlobalS 290 } 

		fnat64RevEgressPktSizeRange3 OBJECT-TYPE
		SYNTAX  CounterBasedGauge64 
		MAX-ACCESS read-only 
		STATUS current
		DESCRIPTION  "Fixed NAT64 Reverse Egress Packet size between 801 and 1550" 
		::={ acosCgnv6FixedNatGlobalS 291 } 

		fnat64RevEgressPktSizeRange4 OBJECT-TYPE
		SYNTAX  CounterBasedGauge64 
		MAX-ACCESS read-only 
		STATUS current
		DESCRIPTION  "Fixed NAT64 Reverse Egress Packet size between 1551 and 9000" 
		::={ acosCgnv6FixedNatGlobalS 292 } 

		fnatdsliteFwdIngressPacketsTcp OBJECT-TYPE
		SYNTAX  CounterBasedGauge64 
		MAX-ACCESS read-only 
		STATUS current
		DESCRIPTION  "Fixed DS-Lite Forward Ingress Packets TCP" 
		::={ acosCgnv6FixedNatGlobalS 293 } 

		fnatdsliteFwdEgressPacketsTcp OBJECT-TYPE
		SYNTAX  CounterBasedGauge64 
		MAX-ACCESS read-only 
		STATUS current
		DESCRIPTION  "Fixed DS-Lite Forward Egress Packets TCP" 
		::={ acosCgnv6FixedNatGlobalS 294 } 

		fnatdsliteRevIngressPacketsTcp OBJECT-TYPE
		SYNTAX  CounterBasedGauge64 
		MAX-ACCESS read-only 
		STATUS current
		DESCRIPTION  "Fixed DS-Lite Reverse Ingress Packets TCP" 
		::={ acosCgnv6FixedNatGlobalS 295 } 

		fnatdsliteRevEgressPacketsTcp OBJECT-TYPE
		SYNTAX  CounterBasedGauge64 
		MAX-ACCESS read-only 
		STATUS current
		DESCRIPTION  "Fixed DS-Lite Reverse Egress Packets TCP" 
		::={ acosCgnv6FixedNatGlobalS 296 } 

		fnatdsliteFwdIngressBytesTcp OBJECT-TYPE
		SYNTAX  CounterBasedGauge64 
		MAX-ACCESS read-only 
		STATUS current
		DESCRIPTION  "Fixed DS-Lite Forward Ingress Bytes TCP" 
		::={ acosCgnv6FixedNatGlobalS 297 } 

		fnatdsliteFwdEgressBytesTcp OBJECT-TYPE
		SYNTAX  CounterBasedGauge64 
		MAX-ACCESS read-only 
		STATUS current
		DESCRIPTION  "Fixed DS-Lite Forward Egress Bytes TCP" 
		::={ acosCgnv6FixedNatGlobalS 298 } 

		fnatdsliteRevIngressBytesTcp OBJECT-TYPE
		SYNTAX  CounterBasedGauge64 
		MAX-ACCESS read-only 
		STATUS current
		DESCRIPTION  "Fixed DS-Lite Reverse Ingress Bytes TCP" 
		::={ acosCgnv6FixedNatGlobalS 299 } 

		fnatdsliteRevEgressBytesTcp OBJECT-TYPE
		SYNTAX  CounterBasedGauge64 
		MAX-ACCESS read-only 
		STATUS current
		DESCRIPTION  "Fixed DS-Lite Reverse Egress Bytes TCP" 
		::={ acosCgnv6FixedNatGlobalS 300 } 

		fnatdsliteFwdIngressPacketsUdp OBJECT-TYPE
		SYNTAX  CounterBasedGauge64 
		MAX-ACCESS read-only 
		STATUS current
		DESCRIPTION  "Fixed DS-Lite Forward Ingress Packets UDP" 
		::={ acosCgnv6FixedNatGlobalS 301 } 

		fnatdsliteFwdEgressPacketsUdp OBJECT-TYPE
		SYNTAX  CounterBasedGauge64 
		MAX-ACCESS read-only 
		STATUS current
		DESCRIPTION  "Fixed DS-Lite Forward Egress Packets UDP" 
		::={ acosCgnv6FixedNatGlobalS 302 } 

		fnatdsliteRevIngressPacketsUdp OBJECT-TYPE
		SYNTAX  CounterBasedGauge64 
		MAX-ACCESS read-only 
		STATUS current
		DESCRIPTION  "Fixed DS-Lite Reverse Ingress Packets UDP" 
		::={ acosCgnv6FixedNatGlobalS 303 } 

		fnatdsliteRevEgressPacketsUdp OBJECT-TYPE
		SYNTAX  CounterBasedGauge64 
		MAX-ACCESS read-only 
		STATUS current
		DESCRIPTION  "Fixed DS-Lite Reverse Egress Packets UDP" 
		::={ acosCgnv6FixedNatGlobalS 304 } 

		fnatdsliteFwdIngressBytesUdp OBJECT-TYPE
		SYNTAX  CounterBasedGauge64 
		MAX-ACCESS read-only 
		STATUS current
		DESCRIPTION  "Fixed DS-Lite Forward Ingress Bytes UDP" 
		::={ acosCgnv6FixedNatGlobalS 305 } 

		fnatdsliteFwdEgressBytesUdp OBJECT-TYPE
		SYNTAX  CounterBasedGauge64 
		MAX-ACCESS read-only 
		STATUS current
		DESCRIPTION  "Fixed DS-Lite Forward Egress Bytes UDP" 
		::={ acosCgnv6FixedNatGlobalS 306 } 

		fnatdsliteRevIngressBytesUdp OBJECT-TYPE
		SYNTAX  CounterBasedGauge64 
		MAX-ACCESS read-only 
		STATUS current
		DESCRIPTION  "Fixed DS-Lite Reverse Ingress Bytes UDP" 
		::={ acosCgnv6FixedNatGlobalS 307 } 

		fnatdsliteRevEgressBytesUdp OBJECT-TYPE
		SYNTAX  CounterBasedGauge64 
		MAX-ACCESS read-only 
		STATUS current
		DESCRIPTION  "Fixed DS-Lite Reverse Egress Bytes UDP" 
		::={ acosCgnv6FixedNatGlobalS 308 } 

		fnatdsliteFwdIngressPacketsIcmp OBJECT-TYPE
		SYNTAX  CounterBasedGauge64 
		MAX-ACCESS read-only 
		STATUS current
		DESCRIPTION  "Fixed DS-Lite Forward Ingress Packets ICMP" 
		::={ acosCgnv6FixedNatGlobalS 309 } 

		fnatdsliteFwdEgressPacketsIcmp OBJECT-TYPE
		SYNTAX  CounterBasedGauge64 
		MAX-ACCESS read-only 
		STATUS current
		DESCRIPTION  "Fixed DS-Lite Forward Egress Packets ICMP" 
		::={ acosCgnv6FixedNatGlobalS 310 } 

		fnatdsliteRevIngressPacketsIcmp OBJECT-TYPE
		SYNTAX  CounterBasedGauge64 
		MAX-ACCESS read-only 
		STATUS current
		DESCRIPTION  "Fixed DS-Lite Reverse Ingress Packets ICMP" 
		::={ acosCgnv6FixedNatGlobalS 311 } 

		fnatdsliteRevEgressPacketsIcmp OBJECT-TYPE
		SYNTAX  CounterBasedGauge64 
		MAX-ACCESS read-only 
		STATUS current
		DESCRIPTION  "Fixed DS-Lite Reverse Egress Packets ICMP" 
		::={ acosCgnv6FixedNatGlobalS 312 } 

		fnatdsliteFwdIngressBytesIcmp OBJECT-TYPE
		SYNTAX  CounterBasedGauge64 
		MAX-ACCESS read-only 
		STATUS current
		DESCRIPTION  "Fixed DS-Lite Forward Ingress Bytes ICMP" 
		::={ acosCgnv6FixedNatGlobalS 313 } 

		fnatdsliteFwdEgressBytesIcmp OBJECT-TYPE
		SYNTAX  CounterBasedGauge64 
		MAX-ACCESS read-only 
		STATUS current
		DESCRIPTION  "Fixed DS-Lite Forward Egress Bytes ICMP" 
		::={ acosCgnv6FixedNatGlobalS 314 } 

		fnatdsliteRevIngressBytesIcmp OBJECT-TYPE
		SYNTAX  CounterBasedGauge64 
		MAX-ACCESS read-only 
		STATUS current
		DESCRIPTION  "Fixed DS-Lite Reverse Ingress Bytes ICMP" 
		::={ acosCgnv6FixedNatGlobalS 315 } 

		fnatdsliteRevEgressBytesIcmp OBJECT-TYPE
		SYNTAX  CounterBasedGauge64 
		MAX-ACCESS read-only 
		STATUS current
		DESCRIPTION  "Fixed DS-Lite Reverse Egress Bytes ICMP" 
		::={ acosCgnv6FixedNatGlobalS 316 } 

		fnatdsliteFwdIngressPacketsOthers OBJECT-TYPE
		SYNTAX  CounterBasedGauge64 
		MAX-ACCESS read-only 
		STATUS current
		DESCRIPTION  "Fixed DS-Lite Forward Ingress Packets OTHERS" 
		::={ acosCgnv6FixedNatGlobalS 317 } 

		fnatdsliteFwdEgressPacketsOthers OBJECT-TYPE
		SYNTAX  CounterBasedGauge64 
		MAX-ACCESS read-only 
		STATUS current
		DESCRIPTION  "Fixed DS-Lite Forward Egress Packets OTHERS" 
		::={ acosCgnv6FixedNatGlobalS 318 } 

		fnatdsliteRevIngressPacketsOthers OBJECT-TYPE
		SYNTAX  CounterBasedGauge64 
		MAX-ACCESS read-only 
		STATUS current
		DESCRIPTION  "Fixed DS-Lite Reverse Ingress Packets OTHERS" 
		::={ acosCgnv6FixedNatGlobalS 319 } 

		fnatdsliteRevEgressPacketsOthers OBJECT-TYPE
		SYNTAX  CounterBasedGauge64 
		MAX-ACCESS read-only 
		STATUS current
		DESCRIPTION  "Fixed DS-Lite Reverse Egress Packets OTHERS" 
		::={ acosCgnv6FixedNatGlobalS 320 } 

		fnatdsliteFwdIngressBytesOthers OBJECT-TYPE
		SYNTAX  CounterBasedGauge64 
		MAX-ACCESS read-only 
		STATUS current
		DESCRIPTION  "Fixed DS-Lite Forward Ingress Bytes OTHERS" 
		::={ acosCgnv6FixedNatGlobalS 321 } 

		fnatdsliteFwdEgressBytesOthers OBJECT-TYPE
		SYNTAX  CounterBasedGauge64 
		MAX-ACCESS read-only 
		STATUS current
		DESCRIPTION  "Fixed DS-Lite Forward Egress Bytes OTHERS" 
		::={ acosCgnv6FixedNatGlobalS 322 } 

		fnatdsliteRevIngressBytesOthers OBJECT-TYPE
		SYNTAX  CounterBasedGauge64 
		MAX-ACCESS read-only 
		STATUS current
		DESCRIPTION  "Fixed DS-Lite Reverse Ingress Bytes OTHERS" 
		::={ acosCgnv6FixedNatGlobalS 323 } 

		fnatdsliteRevEgressBytesOthers OBJECT-TYPE
		SYNTAX  CounterBasedGauge64 
		MAX-ACCESS read-only 
		STATUS current
		DESCRIPTION  "Fixed DS-Lite Reverse Egress Bytes OTHERS" 
		::={ acosCgnv6FixedNatGlobalS 324 } 

		fnatdsliteFwdIngressPktSizeRange1 OBJECT-TYPE
		SYNTAX  CounterBasedGauge64 
		MAX-ACCESS read-only 
		STATUS current
		DESCRIPTION  "Fixed DS-Lite Forward Ingress Packet size between 0 and 200" 
		::={ acosCgnv6FixedNatGlobalS 325 } 

		fnatdsliteFwdIngressPktSizeRange2 OBJECT-TYPE
		SYNTAX  CounterBasedGauge64 
		MAX-ACCESS read-only 
		STATUS current
		DESCRIPTION  "Fixed DS-Lite Forward Ingress Packet size between 201 and 800" 
		::={ acosCgnv6FixedNatGlobalS 326 } 

		fnatdsliteFwdIngressPktSizeRange3 OBJECT-TYPE
		SYNTAX  CounterBasedGauge64 
		MAX-ACCESS read-only 
		STATUS current
		DESCRIPTION  "Fixed DS-Lite Forward Ingress Packet size between 801 and 1550" 
		::={ acosCgnv6FixedNatGlobalS 327 } 

		fnatdsliteFwdIngressPktSizeRange4 OBJECT-TYPE
		SYNTAX  CounterBasedGauge64 
		MAX-ACCESS read-only 
		STATUS current
		DESCRIPTION  "Fixed DS-Lite Forward Ingress Packet size between 1551 and 9000" 
		::={ acosCgnv6FixedNatGlobalS 328 } 

		fnatdsliteFwdEgressPktSizeRange1 OBJECT-TYPE
		SYNTAX  CounterBasedGauge64 
		MAX-ACCESS read-only 
		STATUS current
		DESCRIPTION  "Fixed DS-Lite Forward Egress Packet size between 0 and 200" 
		::={ acosCgnv6FixedNatGlobalS 329 } 

		fnatdsliteFwdEgressPktSizeRange2 OBJECT-TYPE
		SYNTAX  CounterBasedGauge64 
		MAX-ACCESS read-only 
		STATUS current
		DESCRIPTION  "Fixed DS-Lite Forward Egress Packet size between 201 and 800" 
		::={ acosCgnv6FixedNatGlobalS 330 } 

		fnatdsliteFwdEgressPktSizeRange3 OBJECT-TYPE
		SYNTAX  CounterBasedGauge64 
		MAX-ACCESS read-only 
		STATUS current
		DESCRIPTION  "Fixed DS-Lite Forward Egress Packet size between 801 and 1550" 
		::={ acosCgnv6FixedNatGlobalS 331 } 

		fnatdsliteFwdEgressPktSizeRange4 OBJECT-TYPE
		SYNTAX  CounterBasedGauge64 
		MAX-ACCESS read-only 
		STATUS current
		DESCRIPTION  "Fixed DS-Lite Forward Egress Packet size between 1551 and 9000" 
		::={ acosCgnv6FixedNatGlobalS 332 } 

		fnatdsliteRevIngressPktSizeRange1 OBJECT-TYPE
		SYNTAX  CounterBasedGauge64 
		MAX-ACCESS read-only 
		STATUS current
		DESCRIPTION  "Fixed DS-Lite Reverse Ingress Packet size between 0 and 200" 
		::={ acosCgnv6FixedNatGlobalS 333 } 

		fnatdsliteRevIngressPktSizeRange2 OBJECT-TYPE
		SYNTAX  CounterBasedGauge64 
		MAX-ACCESS read-only 
		STATUS current
		DESCRIPTION  "Fixed DS-Lite Reverse Ingress Packet size between 201 and 800" 
		::={ acosCgnv6FixedNatGlobalS 334 } 

		fnatdsliteRevIngressPktSizeRange3 OBJECT-TYPE
		SYNTAX  CounterBasedGauge64 
		MAX-ACCESS read-only 
		STATUS current
		DESCRIPTION  "Fixed DS-Lite Reverse Ingress Packet size between 801 and 1550" 
		::={ acosCgnv6FixedNatGlobalS 335 } 

		fnatdsliteRevIngressPktSizeRange4 OBJECT-TYPE
		SYNTAX  CounterBasedGauge64 
		MAX-ACCESS read-only 
		STATUS current
		DESCRIPTION  "Fixed DS-Lite Reverse Ingress Packet size between 1551 and 9000" 
		::={ acosCgnv6FixedNatGlobalS 336 } 

		fnatdsliteRevEgressPktSizeRange1 OBJECT-TYPE
		SYNTAX  CounterBasedGauge64 
		MAX-ACCESS read-only 
		STATUS current
		DESCRIPTION  "Fixed DS-Lite Reverse Egress Packet size between 0 and 200" 
		::={ acosCgnv6FixedNatGlobalS 337 } 

		fnatdsliteRevEgressPktSizeRange2 OBJECT-TYPE
		SYNTAX  CounterBasedGauge64 
		MAX-ACCESS read-only 
		STATUS current
		DESCRIPTION  "Fixed DS-Lite Reverse Egress Packet size between 201 and 800" 
		::={ acosCgnv6FixedNatGlobalS 338 } 

		fnatdsliteRevEgressPktSizeRange3 OBJECT-TYPE
		SYNTAX  CounterBasedGauge64 
		MAX-ACCESS read-only 
		STATUS current
		DESCRIPTION  "Fixed DS-Lite Reverse Egress Packet size between 801 and 1550" 
		::={ acosCgnv6FixedNatGlobalS 339 } 

		fnatdsliteRevEgressPktSizeRange4 OBJECT-TYPE
		SYNTAX  CounterBasedGauge64 
		MAX-ACCESS read-only 
		STATUS current
		DESCRIPTION  "Fixed DS-Lite Reverse Egress Packet size between 1551 and 9000" 
		::={ acosCgnv6FixedNatGlobalS 340 } 

		cgnv6FixednatGlobalActiveSubscriberAdded OBJECT-TYPE
		SYNTAX  CounterBasedGauge64 
		MAX-ACCESS read-only 
		STATUS current
		DESCRIPTION  "Active Subscriber Added" 
		::={ acosCgnv6FixedNatGlobalS 341 } 

		cgnv6FixednatGlobalActiveSubscriberRemoved OBJECT-TYPE
		SYNTAX  CounterBasedGauge64 
		MAX-ACCESS read-only 
		STATUS current
		DESCRIPTION  "Active Subscriber Removed" 
		::={ acosCgnv6FixedNatGlobalS 342 } 

		configNotFoundInCtx OBJECT-TYPE
		SYNTAX  CounterBasedGauge64 
		MAX-ACCESS read-only 
		STATUS current
		DESCRIPTION  "Fixed NAT Config Pointer Not Found in MY_CTX" 
		::={ acosCgnv6FixedNatGlobalS 343 } 

acosCgnv6FixedNatAlg                OBJECT IDENTIFIER ::= { acosCgnv6FixedNat 4 }
acosCgnv6FixedNatAlgEsp             OBJECT IDENTIFIER ::= { acosCgnv6FixedNatAlg 1 }
acosCgnv6FixedNatAlgEspS            OBJECT IDENTIFIER ::= { acosCgnv6FixedNatAlgEsp 1 }

		cgnv6FixedNatAlgEspSessionCreated OBJECT-TYPE
		SYNTAX  CounterBasedGauge64 
		MAX-ACCESS read-only 
		STATUS current
		DESCRIPTION  "ESP Sessions Created" 
		::={ acosCgnv6FixedNatAlgEspS 1 } 

		placeholderDebug OBJECT-TYPE
		SYNTAX  CounterBasedGauge64 
		MAX-ACCESS read-only 
		STATUS current
		DESCRIPTION  "Placeholder Debug" 
		::={ acosCgnv6FixedNatAlgEspS 2 } 

acosCgnv6FixedNatAlgFtp             OBJECT IDENTIFIER ::= { acosCgnv6FixedNatAlg 2 }
acosCgnv6FixedNatAlgFtpS            OBJECT IDENTIFIER ::= { acosCgnv6FixedNatAlgFtp 1 }

		cgnv6FixedNatAlgFtpPortRequests OBJECT-TYPE
		SYNTAX  CounterBasedGauge64 
		MAX-ACCESS read-only 
		STATUS current
		DESCRIPTION  "PORT Requests From Client" 
		::={ acosCgnv6FixedNatAlgFtpS 1 } 

		cgnv6FixedNatAlgFtpEprtRequests OBJECT-TYPE
		SYNTAX  CounterBasedGauge64 
		MAX-ACCESS read-only 
		STATUS current
		DESCRIPTION  "EPRT Requests From Client" 
		::={ acosCgnv6FixedNatAlgFtpS 2 } 

		cgnv6FixedNatAlgFtpLprtRequests OBJECT-TYPE
		SYNTAX  CounterBasedGauge64 
		MAX-ACCESS read-only 
		STATUS current
		DESCRIPTION  "LPRT Requests From Client" 
		::={ acosCgnv6FixedNatAlgFtpS 3 } 

		cgnv6FixedNatAlgFtpPasvReplies OBJECT-TYPE
		SYNTAX  CounterBasedGauge64 
		MAX-ACCESS read-only 
		STATUS current
		DESCRIPTION  "PASV Replies From Server" 
		::={ acosCgnv6FixedNatAlgFtpS 4 } 

		cgnv6FixedNatAlgFtpEpsvReplies OBJECT-TYPE
		SYNTAX  CounterBasedGauge64 
		MAX-ACCESS read-only 
		STATUS current
		DESCRIPTION  "EPSV Replies From Server" 
		::={ acosCgnv6FixedNatAlgFtpS 5 } 

		cgnv6FixedNatAlgFtpLpsvReplies OBJECT-TYPE
		SYNTAX  CounterBasedGauge64 
		MAX-ACCESS read-only 
		STATUS current
		DESCRIPTION  "LPSV Replies From Server" 
		::={ acosCgnv6FixedNatAlgFtpS 6 } 

		portRetransmits OBJECT-TYPE
		SYNTAX  CounterBasedGauge64 
		MAX-ACCESS read-only 
		STATUS current
		DESCRIPTION  "Port Mode Request Retransmits" 
		::={ acosCgnv6FixedNatAlgFtpS 7 } 

		pasvRetransmits OBJECT-TYPE
		SYNTAX  CounterBasedGauge64 
		MAX-ACCESS read-only 
		STATUS current
		DESCRIPTION  "Passive Mode Reply Retransmits" 
		::={ acosCgnv6FixedNatAlgFtpS 8 } 

		portHelperCreated OBJECT-TYPE
		SYNTAX  CounterBasedGauge64 
		MAX-ACCESS read-only 
		STATUS current
		DESCRIPTION  "Port Mode Helper Created" 
		::={ acosCgnv6FixedNatAlgFtpS 9 } 

		pasvHelperCreated OBJECT-TYPE
		SYNTAX  CounterBasedGauge64 
		MAX-ACCESS read-only 
		STATUS current
		DESCRIPTION  "Passive Mode Helper Created" 
		::={ acosCgnv6FixedNatAlgFtpS 10 } 

		portHelperFreed OBJECT-TYPE
		SYNTAX  CounterBasedGauge64 
		MAX-ACCESS read-only 
		STATUS current
		DESCRIPTION  "Port Mode Helper Freed" 
		::={ acosCgnv6FixedNatAlgFtpS 11 } 

		pasvHelperFreed OBJECT-TYPE
		SYNTAX  CounterBasedGauge64 
		MAX-ACCESS read-only 
		STATUS current
		DESCRIPTION  "Passive Mode Helper Freed" 
		::={ acosCgnv6FixedNatAlgFtpS 12 } 

		portHelperUnused OBJECT-TYPE
		SYNTAX  CounterBasedGauge64 
		MAX-ACCESS read-only 
		STATUS current
		DESCRIPTION  "Port Mode Helper Unused" 
		::={ acosCgnv6FixedNatAlgFtpS 13 } 

		pasvHelperUnused OBJECT-TYPE
		SYNTAX  CounterBasedGauge64 
		MAX-ACCESS read-only 
		STATUS current
		DESCRIPTION  "Passive Mode Helper Unused" 
		::={ acosCgnv6FixedNatAlgFtpS 14 } 

		portHelperCreationFailure OBJECT-TYPE
		SYNTAX  CounterBasedGauge64 
		MAX-ACCESS read-only 
		STATUS current
		DESCRIPTION  "Port Helper Creation Failure" 
		::={ acosCgnv6FixedNatAlgFtpS 15 } 

		pasvHelperCreationFailure OBJECT-TYPE
		SYNTAX  CounterBasedGauge64 
		MAX-ACCESS read-only 
		STATUS current
		DESCRIPTION  "Passive Helper Creation Failure" 
		::={ acosCgnv6FixedNatAlgFtpS 16 } 

		getConnExtFailure OBJECT-TYPE
		SYNTAX  CounterBasedGauge64 
		MAX-ACCESS read-only 
		STATUS current
		DESCRIPTION  "Get Conn Extension Failure" 
		::={ acosCgnv6FixedNatAlgFtpS 17 } 

		smpAppTypeMismatch OBJECT-TYPE
		SYNTAX  CounterBasedGauge64 
		MAX-ACCESS read-only 
		STATUS current
		DESCRIPTION  "SMP ALG App Type Mismatch" 
		::={ acosCgnv6FixedNatAlgFtpS 18 } 

acosCgnv6FixedNatAlgPptp            OBJECT IDENTIFIER ::= { acosCgnv6FixedNatAlg 3 }
acosCgnv6FixedNatAlgPptpS           OBJECT IDENTIFIER ::= { acosCgnv6FixedNatAlgPptp 1 }

		cgnv6FixedNatAlgPptpCallsEstablished OBJECT-TYPE
		SYNTAX  CounterBasedGauge64 
		MAX-ACCESS read-only 
		STATUS current
		DESCRIPTION  "Calls Established" 
		::={ acosCgnv6FixedNatAlgPptpS 1 } 

		cgnv6FixedNatAlgPptpMismatched OBJECT-TYPE
		SYNTAX  CounterBasedGauge64 
		MAX-ACCESS read-only 
		STATUS current
		DESCRIPTION  "Mismatched PNS Call ID" 
		::={ acosCgnv6FixedNatAlgPptpS 2 } 

		greSessionsCreated OBJECT-TYPE
		SYNTAX  CounterBasedGauge64 
		MAX-ACCESS read-only 
		STATUS current
		DESCRIPTION  "GRE Sessions Created" 
		::={ acosCgnv6FixedNatAlgPptpS 3 } 

		greSessionsFreed OBJECT-TYPE
		SYNTAX  CounterBasedGauge64 
		MAX-ACCESS read-only 
		STATUS current
		DESCRIPTION  "GRE Sessions Freed" 
		::={ acosCgnv6FixedNatAlgPptpS 4 } 

		noGreSessionMatch OBJECT-TYPE
		SYNTAX  CounterBasedGauge64 
		MAX-ACCESS read-only 
		STATUS current
		DESCRIPTION  "No Matching GRE Session" 
		::={ acosCgnv6FixedNatAlgPptpS 5 } 

		smpSessionsCreated OBJECT-TYPE
		SYNTAX  CounterBasedGauge64 
		MAX-ACCESS read-only 
		STATUS current
		DESCRIPTION  "SMP Sessions Created" 
		::={ acosCgnv6FixedNatAlgPptpS 6 } 

		smpSessionsFreed OBJECT-TYPE
		SYNTAX  CounterBasedGauge64 
		MAX-ACCESS read-only 
		STATUS current
		DESCRIPTION  "SMP Sessions Freed" 
		::={ acosCgnv6FixedNatAlgPptpS 7 } 

		smpSessionCreationFailure OBJECT-TYPE
		SYNTAX  CounterBasedGauge64 
		MAX-ACCESS read-only 
		STATUS current
		DESCRIPTION  "SMP Session Creation Failures" 
		::={ acosCgnv6FixedNatAlgPptpS 8 } 

		extensionCreationFailure OBJECT-TYPE
		SYNTAX  CounterBasedGauge64 
		MAX-ACCESS read-only 
		STATUS current
		DESCRIPTION  "Extension Creation Failures" 
		::={ acosCgnv6FixedNatAlgPptpS 9 } 

		haSent OBJECT-TYPE
		SYNTAX  CounterBasedGauge64 
		MAX-ACCESS read-only 
		STATUS current
		DESCRIPTION  "HA Info Sent" 
		::={ acosCgnv6FixedNatAlgPptpS 10 } 

		haRcv OBJECT-TYPE
		SYNTAX  CounterBasedGauge64 
		MAX-ACCESS read-only 
		STATUS current
		DESCRIPTION  "HA Info Received" 
		::={ acosCgnv6FixedNatAlgPptpS 11 } 

		haNoMem OBJECT-TYPE
		SYNTAX  CounterBasedGauge64 
		MAX-ACCESS read-only 
		STATUS current
		DESCRIPTION  "HA Memory Allocation Failure" 
		::={ acosCgnv6FixedNatAlgPptpS 12 } 

		haConflict OBJECT-TYPE
		SYNTAX  CounterBasedGauge64 
		MAX-ACCESS read-only 
		STATUS current
		DESCRIPTION  "HA Call ID Conflicts" 
		::={ acosCgnv6FixedNatAlgPptpS 13 } 

		haOverwrite OBJECT-TYPE
		SYNTAX  CounterBasedGauge64 
		MAX-ACCESS read-only 
		STATUS current
		DESCRIPTION  "HA Call ID Overwrites" 
		::={ acosCgnv6FixedNatAlgPptpS 14 } 

		haCallSent OBJECT-TYPE
		SYNTAX  CounterBasedGauge64 
		MAX-ACCESS read-only 
		STATUS current
		DESCRIPTION  "HA Call Sent" 
		::={ acosCgnv6FixedNatAlgPptpS 15 } 

		haCallRcv OBJECT-TYPE
		SYNTAX  CounterBasedGauge64 
		MAX-ACCESS read-only 
		STATUS current
		DESCRIPTION  "HA Call Received" 
		::={ acosCgnv6FixedNatAlgPptpS 16 } 

		haSmpConflict OBJECT-TYPE
		SYNTAX  CounterBasedGauge64 
		MAX-ACCESS read-only 
		STATUS current
		DESCRIPTION  "HA SMP Conflicts" 
		::={ acosCgnv6FixedNatAlgPptpS 17 } 

		haSmpInDelQ OBJECT-TYPE
		SYNTAX  CounterBasedGauge64 
		MAX-ACCESS read-only 
		STATUS current
		DESCRIPTION  "HA SMP Deleted" 
		::={ acosCgnv6FixedNatAlgPptpS 18 } 

		smpAppTypeMismatch OBJECT-TYPE
		SYNTAX  CounterBasedGauge64 
		MAX-ACCESS read-only 
		STATUS current
		DESCRIPTION  "SMP ALG App Type Mismatch" 
		::={ acosCgnv6FixedNatAlgPptpS 19 } 

		callReqPnsCallIdMismatch OBJECT-TYPE
		SYNTAX  CounterBasedGauge64 
		MAX-ACCESS read-only 
		STATUS current
		DESCRIPTION  "Call ID Mismatch on Call Request" 
		::={ acosCgnv6FixedNatAlgPptpS 20 } 

		callReplyPnsCallIdMismatch OBJECT-TYPE
		SYNTAX  CounterBasedGauge64 
		MAX-ACCESS read-only 
		STATUS current
		DESCRIPTION  "Call ID Mismatch on Call Reply" 
		::={ acosCgnv6FixedNatAlgPptpS 21 } 

		callReqRetransmit OBJECT-TYPE
		SYNTAX  CounterBasedGauge64 
		MAX-ACCESS read-only 
		STATUS current
		DESCRIPTION  "Call Request Retransmit" 
		::={ acosCgnv6FixedNatAlgPptpS 22 } 

		callReqNew OBJECT-TYPE
		SYNTAX  CounterBasedGauge64 
		MAX-ACCESS read-only 
		STATUS current
		DESCRIPTION  "Call Request New" 
		::={ acosCgnv6FixedNatAlgPptpS 23 } 

		callReqExtAllocFailure OBJECT-TYPE
		SYNTAX  CounterBasedGauge64 
		MAX-ACCESS read-only 
		STATUS current
		DESCRIPTION  "Call Request Ext Alloc Failure" 
		::={ acosCgnv6FixedNatAlgPptpS 24 } 

		callReplyCallIdUnknown OBJECT-TYPE
		SYNTAX  CounterBasedGauge64 
		MAX-ACCESS read-only 
		STATUS current
		DESCRIPTION  "Call Reply Unknown Client Call ID" 
		::={ acosCgnv6FixedNatAlgPptpS 25 } 

		callReplyRetransmit OBJECT-TYPE
		SYNTAX  CounterBasedGauge64 
		MAX-ACCESS read-only 
		STATUS current
		DESCRIPTION  "Call Reply Retransmit" 
		::={ acosCgnv6FixedNatAlgPptpS 26 } 

		callReplyRetransmitWrongControl OBJECT-TYPE
		SYNTAX  CounterBasedGauge64 
		MAX-ACCESS read-only 
		STATUS current
		DESCRIPTION  "Call Reply Retransmit Wrong Control" 
		::={ acosCgnv6FixedNatAlgPptpS 27 } 

		callReplyRetransmitAcquired OBJECT-TYPE
		SYNTAX  CounterBasedGauge64 
		MAX-ACCESS read-only 
		STATUS current
		DESCRIPTION  "Call Reply Retransmit Acquired" 
		::={ acosCgnv6FixedNatAlgPptpS 28 } 

		callReplyExtAllocFailure OBJECT-TYPE
		SYNTAX  CounterBasedGauge64 
		MAX-ACCESS read-only 
		STATUS current
		DESCRIPTION  "Call Request Ext Alloc Failure" 
		::={ acosCgnv6FixedNatAlgPptpS 29 } 

		smpClientCallIdMismatch OBJECT-TYPE
		SYNTAX  CounterBasedGauge64 
		MAX-ACCESS read-only 
		STATUS current
		DESCRIPTION  "SMP Client Call ID Mismatch" 
		::={ acosCgnv6FixedNatAlgPptpS 30 } 

		smpAllocFailure OBJECT-TYPE
		SYNTAX  CounterBasedGauge64 
		MAX-ACCESS read-only 
		STATUS current
		DESCRIPTION  "SMP Session Alloc Failure" 
		::={ acosCgnv6FixedNatAlgPptpS 31 } 

		greConnCreationFailure OBJECT-TYPE
		SYNTAX  CounterBasedGauge64 
		MAX-ACCESS read-only 
		STATUS current
		DESCRIPTION  "GRE Conn Alloc Failure" 
		::={ acosCgnv6FixedNatAlgPptpS 32 } 

		greConnExtCreationFailure OBJECT-TYPE
		SYNTAX  CounterBasedGauge64 
		MAX-ACCESS read-only 
		STATUS current
		DESCRIPTION  "GRE Conn Ext Alloc Failure" 
		::={ acosCgnv6FixedNatAlgPptpS 33 } 

		greNoFwdRoute OBJECT-TYPE
		SYNTAX  CounterBasedGauge64 
		MAX-ACCESS read-only 
		STATUS current
		DESCRIPTION  "GRE No Fwd Route" 
		::={ acosCgnv6FixedNatAlgPptpS 34 } 

		greNoRevRoute OBJECT-TYPE
		SYNTAX  CounterBasedGauge64 
		MAX-ACCESS read-only 
		STATUS current
		DESCRIPTION  "GRE No Rev Route" 
		::={ acosCgnv6FixedNatAlgPptpS 35 } 

		greNoControlConn OBJECT-TYPE
		SYNTAX  CounterBasedGauge64 
		MAX-ACCESS read-only 
		STATUS current
		DESCRIPTION  "GRE No Control Conn" 
		::={ acosCgnv6FixedNatAlgPptpS 36 } 

		greConnAlreadyExists OBJECT-TYPE
		SYNTAX  CounterBasedGauge64 
		MAX-ACCESS read-only 
		STATUS current
		DESCRIPTION  "GRE Conn Already Exists" 
		::={ acosCgnv6FixedNatAlgPptpS 37 } 

		greFreeNoExt OBJECT-TYPE
		SYNTAX  CounterBasedGauge64 
		MAX-ACCESS read-only 
		STATUS current
		DESCRIPTION  "GRE Free No Ext" 
		::={ acosCgnv6FixedNatAlgPptpS 38 } 

		greFreeNoSmp OBJECT-TYPE
		SYNTAX  CounterBasedGauge64 
		MAX-ACCESS read-only 
		STATUS current
		DESCRIPTION  "GRE Free No SMP" 
		::={ acosCgnv6FixedNatAlgPptpS 39 } 

		greFreeSmpAppTypeMismatch OBJECT-TYPE
		SYNTAX  CounterBasedGauge64 
		MAX-ACCESS read-only 
		STATUS current
		DESCRIPTION  "GRE Free SMP App Type Mismatch" 
		::={ acosCgnv6FixedNatAlgPptpS 40 } 

		controlFreed OBJECT-TYPE
		SYNTAX  CounterBasedGauge64 
		MAX-ACCESS read-only 
		STATUS current
		DESCRIPTION  "Control Session Freed" 
		::={ acosCgnv6FixedNatAlgPptpS 41 } 

		controlFreeNoExt OBJECT-TYPE
		SYNTAX  CounterBasedGauge64 
		MAX-ACCESS read-only 
		STATUS current
		DESCRIPTION  "Control Free No Ext" 
		::={ acosCgnv6FixedNatAlgPptpS 42 } 

		controlFreeNoSmp OBJECT-TYPE
		SYNTAX  CounterBasedGauge64 
		MAX-ACCESS read-only 
		STATUS current
		DESCRIPTION  "Control Free No SMP" 
		::={ acosCgnv6FixedNatAlgPptpS 43 } 

		controlFreeSmpAppTypeMismatch OBJECT-TYPE
		SYNTAX  CounterBasedGauge64 
		MAX-ACCESS read-only 
		STATUS current
		DESCRIPTION  "Control Free SMP App Type Mismatch" 
		::={ acosCgnv6FixedNatAlgPptpS 44 } 

acosCgnv6FixedNatAlgRtsp            OBJECT IDENTIFIER ::= { acosCgnv6FixedNatAlg 4 }
acosCgnv6FixedNatAlgRtspS           OBJECT IDENTIFIER ::= { acosCgnv6FixedNatAlgRtsp 1 }

		streamsCreated OBJECT-TYPE
		SYNTAX  CounterBasedGauge64 
		MAX-ACCESS read-only 
		STATUS current
		DESCRIPTION  "Streams Created" 
		::={ acosCgnv6FixedNatAlgRtspS 1 } 

		streamsFreed OBJECT-TYPE
		SYNTAX  CounterBasedGauge64 
		MAX-ACCESS read-only 
		STATUS current
		DESCRIPTION  "Streams Freed" 
		::={ acosCgnv6FixedNatAlgRtspS 2 } 

		streamCreationFailure OBJECT-TYPE
		SYNTAX  CounterBasedGauge64 
		MAX-ACCESS read-only 
		STATUS current
		DESCRIPTION  "Stream Creation Failures" 
		::={ acosCgnv6FixedNatAlgRtspS 3 } 

		portsAllocated OBJECT-TYPE
		SYNTAX  CounterBasedGauge64 
		MAX-ACCESS read-only 
		STATUS current
		DESCRIPTION  "Stream Client Ports Allocated" 
		::={ acosCgnv6FixedNatAlgRtspS 4 } 

		portsFreed OBJECT-TYPE
		SYNTAX  CounterBasedGauge64 
		MAX-ACCESS read-only 
		STATUS current
		DESCRIPTION  "Stream Client Ports Freed" 
		::={ acosCgnv6FixedNatAlgRtspS 5 } 

		portAllocationFailure OBJECT-TYPE
		SYNTAX  CounterBasedGauge64 
		MAX-ACCESS read-only 
		STATUS current
		DESCRIPTION  "Stream Client Port Allocation Failures" 
		::={ acosCgnv6FixedNatAlgRtspS 6 } 

		unknownClientPortFromServer OBJECT-TYPE
		SYNTAX  CounterBasedGauge64 
		MAX-ACCESS read-only 
		STATUS current
		DESCRIPTION  "Server Replies With Unknown Client Ports" 
		::={ acosCgnv6FixedNatAlgRtspS 7 } 

		cgnv6FixedNatAlgRtspDataSessionCreated OBJECT-TYPE
		SYNTAX  CounterBasedGauge64 
		MAX-ACCESS read-only 
		STATUS current
		DESCRIPTION  "Data Session Created" 
		::={ acosCgnv6FixedNatAlgRtspS 8 } 

		cgnv6FixedNatAlgRtspDataSessionFreed OBJECT-TYPE
		SYNTAX  CounterBasedGauge64 
		MAX-ACCESS read-only 
		STATUS current
		DESCRIPTION  "Data Session Freed" 
		::={ acosCgnv6FixedNatAlgRtspS 9 } 

		noSessionMem OBJECT-TYPE
		SYNTAX  CounterBasedGauge64 
		MAX-ACCESS read-only 
		STATUS current
		DESCRIPTION  "Data Session Creation Failures" 
		::={ acosCgnv6FixedNatAlgRtspS 10 } 

		smpInserted OBJECT-TYPE
		SYNTAX  CounterBasedGauge64 
		MAX-ACCESS read-only 
		STATUS current
		DESCRIPTION  "SMP Session Inserted" 
		::={ acosCgnv6FixedNatAlgRtspS 11 } 

		smpRemoved OBJECT-TYPE
		SYNTAX  CounterBasedGauge64 
		MAX-ACCESS read-only 
		STATUS current
		DESCRIPTION  "SMP Session Removed" 
		::={ acosCgnv6FixedNatAlgRtspS 12 } 

		smpReused OBJECT-TYPE
		SYNTAX  CounterBasedGauge64 
		MAX-ACCESS read-only 
		STATUS current
		DESCRIPTION  "SMP Session Reused" 
		::={ acosCgnv6FixedNatAlgRtspS 13 } 

		fixedNatLidStandby OBJECT-TYPE
		SYNTAX  CounterBasedGauge64 
		MAX-ACCESS read-only 
		STATUS current
		DESCRIPTION  "New Session Fixed NAT LID Standby" 
		::={ acosCgnv6FixedNatAlgRtspS 14 } 

		smpDeleted OBJECT-TYPE
		SYNTAX  CounterBasedGauge64 
		MAX-ACCESS read-only 
		STATUS current
		DESCRIPTION  "New Session SMP Already Deleted" 
		::={ acosCgnv6FixedNatAlgRtspS 15 } 

		controlClosed OBJECT-TYPE
		SYNTAX  CounterBasedGauge64 
		MAX-ACCESS read-only 
		STATUS current
		DESCRIPTION  "New Session Closed" 
		::={ acosCgnv6FixedNatAlgRtspS 16 } 

		dataSessionExists OBJECT-TYPE
		SYNTAX  CounterBasedGauge64 
		MAX-ACCESS read-only 
		STATUS current
		DESCRIPTION  "New Session Already Exists" 
		::={ acosCgnv6FixedNatAlgRtspS 17 } 

		dataSessionCreationFailure OBJECT-TYPE
		SYNTAX  CounterBasedGauge64 
		MAX-ACCESS read-only 
		STATUS current
		DESCRIPTION  "New Data Session Creation Failure" 
		::={ acosCgnv6FixedNatAlgRtspS 18 } 

		rtpReversed OBJECT-TYPE
		SYNTAX  CounterBasedGauge64 
		MAX-ACCESS read-only 
		STATUS current
		DESCRIPTION  "RTP Reverse Creation" 
		::={ acosCgnv6FixedNatAlgRtspS 19 } 

		rtcpReversed OBJECT-TYPE
		SYNTAX  CounterBasedGauge64 
		MAX-ACCESS read-only 
		STATUS current
		DESCRIPTION  "RTCP Reverse Creation" 
		::={ acosCgnv6FixedNatAlgRtspS 20 } 

		crossCpuSent OBJECT-TYPE
		SYNTAX  CounterBasedGauge64 
		MAX-ACCESS read-only 
		STATUS current
		DESCRIPTION  "Cross CPU Sent" 
		::={ acosCgnv6FixedNatAlgRtspS 21 } 

		crossCpuRcv OBJECT-TYPE
		SYNTAX  CounterBasedGauge64 
		MAX-ACCESS read-only 
		STATUS current
		DESCRIPTION  "Cross CPU Received" 
		::={ acosCgnv6FixedNatAlgRtspS 22 } 

		crossCpuNoSession OBJECT-TYPE
		SYNTAX  CounterBasedGauge64 
		MAX-ACCESS read-only 
		STATUS current
		DESCRIPTION  "Cross CPU No Session Found" 
		::={ acosCgnv6FixedNatAlgRtspS 23 } 

		crossCpuCreated OBJECT-TYPE
		SYNTAX  CounterBasedGauge64 
		MAX-ACCESS read-only 
		STATUS current
		DESCRIPTION  "Cross CPU Creation" 
		::={ acosCgnv6FixedNatAlgRtspS 24 } 

		crossCpuRcvFailure OBJECT-TYPE
		SYNTAX  CounterBasedGauge64 
		MAX-ACCESS read-only 
		STATUS current
		DESCRIPTION  "Cross CPU Receive Failure" 
		::={ acosCgnv6FixedNatAlgRtspS 25 } 

		dataFreeSmpRetryLookup OBJECT-TYPE
		SYNTAX  CounterBasedGauge64 
		MAX-ACCESS read-only 
		STATUS current
		DESCRIPTION  "Data Session Free SMP Retry Lookup" 
		::={ acosCgnv6FixedNatAlgRtspS 26 } 

		dataFreeSmpNotFound OBJECT-TYPE
		SYNTAX  CounterBasedGauge64 
		MAX-ACCESS read-only 
		STATUS current
		DESCRIPTION  "Data Session Free SMP Not Found" 
		::={ acosCgnv6FixedNatAlgRtspS 27 } 

		haStreamsSent OBJECT-TYPE
		SYNTAX  CounterBasedGauge64 
		MAX-ACCESS read-only 
		STATUS current
		DESCRIPTION  "HA Streams Sent" 
		::={ acosCgnv6FixedNatAlgRtspS 28 } 

		haStreamsRcv OBJECT-TYPE
		SYNTAX  CounterBasedGauge64 
		MAX-ACCESS read-only 
		STATUS current
		DESCRIPTION  "HA Streams Received" 
		::={ acosCgnv6FixedNatAlgRtspS 29 } 

		haStreamIncompatible OBJECT-TYPE
		SYNTAX  CounterBasedGauge64 
		MAX-ACCESS read-only 
		STATUS current
		DESCRIPTION  "HA Incompatible Streams Received" 
		::={ acosCgnv6FixedNatAlgRtspS 30 } 

		haStreamExists OBJECT-TYPE
		SYNTAX  CounterBasedGauge64 
		MAX-ACCESS read-only 
		STATUS current
		DESCRIPTION  "HA Stream Already Exists" 
		::={ acosCgnv6FixedNatAlgRtspS 31 } 

		haPortAllocationFailure OBJECT-TYPE
		SYNTAX  CounterBasedGauge64 
		MAX-ACCESS read-only 
		STATUS current
		DESCRIPTION  "HA Stream Port Allocation Failure" 
		::={ acosCgnv6FixedNatAlgRtspS 32 } 

		haDataSessionSent OBJECT-TYPE
		SYNTAX  CounterBasedGauge64 
		MAX-ACCESS read-only 
		STATUS current
		DESCRIPTION  "HA Data Session Sent" 
		::={ acosCgnv6FixedNatAlgRtspS 33 } 

		haDataSessionRcv OBJECT-TYPE
		SYNTAX  CounterBasedGauge64 
		MAX-ACCESS read-only 
		STATUS current
		DESCRIPTION  "HA Data Session Received" 
		::={ acosCgnv6FixedNatAlgRtspS 34 } 

		haDataNoSmp OBJECT-TYPE
		SYNTAX  CounterBasedGauge64 
		MAX-ACCESS read-only 
		STATUS current
		DESCRIPTION  "HA Data Session SMP Not Found" 
		::={ acosCgnv6FixedNatAlgRtspS 35 } 

		haControlClosed OBJECT-TYPE
		SYNTAX  CounterBasedGauge64 
		MAX-ACCESS read-only 
		STATUS current
		DESCRIPTION  "HA New Data Control Session Closed" 
		::={ acosCgnv6FixedNatAlgRtspS 36 } 

		haDataExists OBJECT-TYPE
		SYNTAX  CounterBasedGauge64 
		MAX-ACCESS read-only 
		STATUS current
		DESCRIPTION  "HA New Data Session Already Exists" 
		::={ acosCgnv6FixedNatAlgRtspS 37 } 

		haExtensionFailure OBJECT-TYPE
		SYNTAX  CounterBasedGauge64 
		MAX-ACCESS read-only 
		STATUS current
		DESCRIPTION  "HA Conn Extension Failure" 
		::={ acosCgnv6FixedNatAlgRtspS 38 } 

		haStreamSmpReused OBJECT-TYPE
		SYNTAX  CounterBasedGauge64 
		MAX-ACCESS read-only 
		STATUS current
		DESCRIPTION  "HA SMP Session Reused" 
		::={ acosCgnv6FixedNatAlgRtspS 39 } 

		haStreamSmpAcquireFailure OBJECT-TYPE
		SYNTAX  CounterBasedGauge64 
		MAX-ACCESS read-only 
		STATUS current
		DESCRIPTION  "HA SMP Session Acquire Failure" 
		::={ acosCgnv6FixedNatAlgRtspS 40 } 

		smpAppTypeMismatch OBJECT-TYPE
		SYNTAX  CounterBasedGauge64 
		MAX-ACCESS read-only 
		STATUS current
		DESCRIPTION  "SMP ALG App Type Mismatch" 
		::={ acosCgnv6FixedNatAlgRtspS 41 } 

acosCgnv6FixedNatAlgSip             OBJECT IDENTIFIER ::= { acosCgnv6FixedNatAlg 5 }
acosCgnv6FixedNatAlgSipS            OBJECT IDENTIFIER ::= { acosCgnv6FixedNatAlgSip 1 }

		cgnv6FixedNatAlgSipMethodRegister OBJECT-TYPE
		SYNTAX  CounterBasedGauge64 
		MAX-ACCESS read-only 
		STATUS current
		DESCRIPTION  "SIP Method REGISTER" 
		::={ acosCgnv6FixedNatAlgSipS 1 } 

		cgnv6FixedNatAlgSipMethodInvite OBJECT-TYPE
		SYNTAX  CounterBasedGauge64 
		MAX-ACCESS read-only 
		STATUS current
		DESCRIPTION  "SIP Method INVITE" 
		::={ acosCgnv6FixedNatAlgSipS 2 } 

		cgnv6FixedNatAlgSipMethodAck OBJECT-TYPE
		SYNTAX  CounterBasedGauge64 
		MAX-ACCESS read-only 
		STATUS current
		DESCRIPTION  "SIP Method ACK" 
		::={ acosCgnv6FixedNatAlgSipS 3 } 

		cgnv6FixedNatAlgSipMethodCancel OBJECT-TYPE
		SYNTAX  CounterBasedGauge64 
		MAX-ACCESS read-only 
		STATUS current
		DESCRIPTION  "SIP Method CANCEL" 
		::={ acosCgnv6FixedNatAlgSipS 4 } 

		cgnv6FixedNatAlgSipMethodBye OBJECT-TYPE
		SYNTAX  CounterBasedGauge64 
		MAX-ACCESS read-only 
		STATUS current
		DESCRIPTION  "SIP Method BYE" 
		::={ acosCgnv6FixedNatAlgSipS 5 } 

		methodOptions OBJECT-TYPE
		SYNTAX  CounterBasedGauge64 
		MAX-ACCESS read-only 
		STATUS current
		DESCRIPTION  "SIP Method OPTIONS" 
		::={ acosCgnv6FixedNatAlgSipS 6 } 

		cgnv6FixedNatAlgSipMethodPrack OBJECT-TYPE
		SYNTAX  CounterBasedGauge64 
		MAX-ACCESS read-only 
		STATUS current
		DESCRIPTION  "SIP Method PRACK" 
		::={ acosCgnv6FixedNatAlgSipS 7 } 

		cgnv6FixedNatAlgSipMethodSubscribe OBJECT-TYPE
		SYNTAX  CounterBasedGauge64 
		MAX-ACCESS read-only 
		STATUS current
		DESCRIPTION  "SIP Method SUBSCRIBE" 
		::={ acosCgnv6FixedNatAlgSipS 8 } 

		cgnv6FixedNatAlgSipMethodNotify OBJECT-TYPE
		SYNTAX  CounterBasedGauge64 
		MAX-ACCESS read-only 
		STATUS current
		DESCRIPTION  "SIP Method NOTIFY" 
		::={ acosCgnv6FixedNatAlgSipS 9 } 

		cgnv6FixedNatAlgSipMethodPublish OBJECT-TYPE
		SYNTAX  CounterBasedGauge64 
		MAX-ACCESS read-only 
		STATUS current
		DESCRIPTION  "SIP Method PUBLISH" 
		::={ acosCgnv6FixedNatAlgSipS 10 } 

		cgnv6FixedNatAlgSipMethodInfo OBJECT-TYPE
		SYNTAX  CounterBasedGauge64 
		MAX-ACCESS read-only 
		STATUS current
		DESCRIPTION  "SIP Method INFO" 
		::={ acosCgnv6FixedNatAlgSipS 11 } 

		cgnv6FixedNatAlgSipMethodRefer OBJECT-TYPE
		SYNTAX  CounterBasedGauge64 
		MAX-ACCESS read-only 
		STATUS current
		DESCRIPTION  "SIP Method REFER" 
		::={ acosCgnv6FixedNatAlgSipS 12 } 

		cgnv6FixedNatAlgSipMethodMessage OBJECT-TYPE
		SYNTAX  CounterBasedGauge64 
		MAX-ACCESS read-only 
		STATUS current
		DESCRIPTION  "SIP Method MESSAGE" 
		::={ acosCgnv6FixedNatAlgSipS 13 } 

		cgnv6FixedNatAlgSipMethodUpdate OBJECT-TYPE
		SYNTAX  CounterBasedGauge64 
		MAX-ACCESS read-only 
		STATUS current
		DESCRIPTION  "SIP Method UPDATE" 
		::={ acosCgnv6FixedNatAlgSipS 14 } 

		cgnv6FixedNatAlgSipMethodUnknown OBJECT-TYPE
		SYNTAX  CounterBasedGauge64 
		MAX-ACCESS read-only 
		STATUS current
		DESCRIPTION  "SIP Method UNKNOWN" 
		::={ acosCgnv6FixedNatAlgSipS 15 } 

		parseError OBJECT-TYPE
		SYNTAX  CounterBasedGauge64 
		MAX-ACCESS read-only 
		STATUS current
		DESCRIPTION  "SIP Message Parse Error" 
		::={ acosCgnv6FixedNatAlgSipS 16 } 

		reqUriOpFailrue OBJECT-TYPE
		SYNTAX  CounterBasedGauge64 
		MAX-ACCESS read-only 
		STATUS current
		DESCRIPTION  "SIP Operate Request Uri Failure" 
		::={ acosCgnv6FixedNatAlgSipS 17 } 

		viaHdrOpFailrue OBJECT-TYPE
		SYNTAX  CounterBasedGauge64 
		MAX-ACCESS read-only 
		STATUS current
		DESCRIPTION  "SIP Operate Via Header Failure" 
		::={ acosCgnv6FixedNatAlgSipS 18 } 

		contactHdrOpFailrue OBJECT-TYPE
		SYNTAX  CounterBasedGauge64 
		MAX-ACCESS read-only 
		STATUS current
		DESCRIPTION  "SIP Operate Contact Header Failure" 
		::={ acosCgnv6FixedNatAlgSipS 19 } 

		fromHdrOpFailrue OBJECT-TYPE
		SYNTAX  CounterBasedGauge64 
		MAX-ACCESS read-only 
		STATUS current
		DESCRIPTION  "SIP Operate From Header Failure" 
		::={ acosCgnv6FixedNatAlgSipS 20 } 

		toHdrOpFailrue OBJECT-TYPE
		SYNTAX  CounterBasedGauge64 
		MAX-ACCESS read-only 
		STATUS current
		DESCRIPTION  "SIP Operate To Header Failure" 
		::={ acosCgnv6FixedNatAlgSipS 21 } 

		routeHdrOpFailrue OBJECT-TYPE
		SYNTAX  CounterBasedGauge64 
		MAX-ACCESS read-only 
		STATUS current
		DESCRIPTION  "SIP Operate Route Header Failure" 
		::={ acosCgnv6FixedNatAlgSipS 22 } 

		recordRouteHdrOpFailrue OBJECT-TYPE
		SYNTAX  CounterBasedGauge64 
		MAX-ACCESS read-only 
		STATUS current
		DESCRIPTION  "SIP Operate Record-Route Header Failure" 
		::={ acosCgnv6FixedNatAlgSipS 23 } 

		contentLengthHdrOpFailrue OBJECT-TYPE
		SYNTAX  CounterBasedGauge64 
		MAX-ACCESS read-only 
		STATUS current
		DESCRIPTION  "SIP Operate Content-Length Failure" 
		::={ acosCgnv6FixedNatAlgSipS 24 } 

		thirdPartyRegistration OBJECT-TYPE
		SYNTAX  CounterBasedGauge64 
		MAX-ACCESS read-only 
		STATUS current
		DESCRIPTION  "SIP Third-Party Registration" 
		::={ acosCgnv6FixedNatAlgSipS 25 } 

		connExtCreationFailure OBJECT-TYPE
		SYNTAX  CounterBasedGauge64 
		MAX-ACCESS read-only 
		STATUS current
		DESCRIPTION  "SIP Create Connection Extension Failure" 
		::={ acosCgnv6FixedNatAlgSipS 26 } 

		allocContactPortFailure OBJECT-TYPE
		SYNTAX  CounterBasedGauge64 
		MAX-ACCESS read-only 
		STATUS current
		DESCRIPTION  "SIP Alloc Contact Port Failure" 
		::={ acosCgnv6FixedNatAlgSipS 27 } 

		outsideContactPortMismatch OBJECT-TYPE
		SYNTAX  CounterBasedGauge64 
		MAX-ACCESS read-only 
		STATUS current
		DESCRIPTION  "SIP Outside Contact Port Mismatch NAT Port" 
		::={ acosCgnv6FixedNatAlgSipS 28 } 

		insideContactPortMismatch OBJECT-TYPE
		SYNTAX  CounterBasedGauge64 
		MAX-ACCESS read-only 
		STATUS current
		DESCRIPTION  "SIP Inside Contact Port Mismatch" 
		::={ acosCgnv6FixedNatAlgSipS 29 } 

		thirdPartySdp OBJECT-TYPE
		SYNTAX  CounterBasedGauge64 
		MAX-ACCESS read-only 
		STATUS current
		DESCRIPTION  "SIP Third-Party SDP" 
		::={ acosCgnv6FixedNatAlgSipS 30 } 

		sdpProcessCandidateFailure OBJECT-TYPE
		SYNTAX  CounterBasedGauge64 
		MAX-ACCESS read-only 
		STATUS current
		DESCRIPTION  "SIP Operate SDP Media Candidate Attribute Failure" 
		::={ acosCgnv6FixedNatAlgSipS 31 } 

		sdpOpFailure OBJECT-TYPE
		SYNTAX  CounterBasedGauge64 
		MAX-ACCESS read-only 
		STATUS current
		DESCRIPTION  "SIP Operate SDP Failure" 
		::={ acosCgnv6FixedNatAlgSipS 32 } 

		sdpAllocPortMapSuccess OBJECT-TYPE
		SYNTAX  CounterBasedGauge64 
		MAX-ACCESS read-only 
		STATUS current
		DESCRIPTION  "SIP Alloc SDP Port Map Success" 
		::={ acosCgnv6FixedNatAlgSipS 33 } 

		sdpAllocPortMapFailure OBJECT-TYPE
		SYNTAX  CounterBasedGauge64 
		MAX-ACCESS read-only 
		STATUS current
		DESCRIPTION  "SIP Alloc SDP Port Map Failure" 
		::={ acosCgnv6FixedNatAlgSipS 34 } 

		modifyFailure OBJECT-TYPE
		SYNTAX  CounterBasedGauge64 
		MAX-ACCESS read-only 
		STATUS current
		DESCRIPTION  "SIP Message Modify Failure" 
		::={ acosCgnv6FixedNatAlgSipS 35 } 

		rewriteFailure OBJECT-TYPE
		SYNTAX  CounterBasedGauge64 
		MAX-ACCESS read-only 
		STATUS current
		DESCRIPTION  "SIP Message Rewrite Failure" 
		::={ acosCgnv6FixedNatAlgSipS 36 } 

		tcpOutOfOrderDrop OBJECT-TYPE
		SYNTAX  CounterBasedGauge64 
		MAX-ACCESS read-only 
		STATUS current
		DESCRIPTION  "TCP Out-of-Order Drop" 
		::={ acosCgnv6FixedNatAlgSipS 37 } 

		smpConnAllocFailure OBJECT-TYPE
		SYNTAX  CounterBasedGauge64 
		MAX-ACCESS read-only 
		STATUS current
		DESCRIPTION  "SMP Helper Conn Alloc Failure" 
		::={ acosCgnv6FixedNatAlgSipS 38 } 

		helperFound OBJECT-TYPE
		SYNTAX  CounterBasedGauge64 
		MAX-ACCESS read-only 
		STATUS current
		DESCRIPTION  "SMP Helper Conn Found" 
		::={ acosCgnv6FixedNatAlgSipS 39 } 

		helperCreated OBJECT-TYPE
		SYNTAX  CounterBasedGauge64 
		MAX-ACCESS read-only 
		STATUS current
		DESCRIPTION  "SMP Helper Conn Created" 
		::={ acosCgnv6FixedNatAlgSipS 40 } 

		helperDeleted OBJECT-TYPE
		SYNTAX  CounterBasedGauge64 
		MAX-ACCESS read-only 
		STATUS current
		DESCRIPTION  "SMP Helper Conn Already Deleted" 
		::={ acosCgnv6FixedNatAlgSipS 41 } 

		helperFreed OBJECT-TYPE
		SYNTAX  CounterBasedGauge64 
		MAX-ACCESS read-only 
		STATUS current
		DESCRIPTION  "SMP Helper Conn Freed" 
		::={ acosCgnv6FixedNatAlgSipS 42 } 

		helperFailure OBJECT-TYPE
		SYNTAX  CounterBasedGauge64 
		MAX-ACCESS read-only 
		STATUS current
		DESCRIPTION  "SMP Helper Failure" 
		::={ acosCgnv6FixedNatAlgSipS 43 } 

acosCgnv6FixedNatAlgMgcp            OBJECT IDENTIFIER ::= { acosCgnv6FixedNatAlg 6 }
acosCgnv6FixedNatAlgMgcpS           OBJECT IDENTIFIER ::= { acosCgnv6FixedNatAlgMgcp 1 }

		auep OBJECT-TYPE
		SYNTAX  CounterBasedGauge64 
		MAX-ACCESS read-only 
		STATUS current
		DESCRIPTION  "MGCP AUEP" 
		::={ acosCgnv6FixedNatAlgMgcpS 1 } 

		aucx OBJECT-TYPE
		SYNTAX  CounterBasedGauge64 
		MAX-ACCESS read-only 
		STATUS current
		DESCRIPTION  "MGCP AUCX" 
		::={ acosCgnv6FixedNatAlgMgcpS 2 } 

		crcx OBJECT-TYPE
		SYNTAX  CounterBasedGauge64 
		MAX-ACCESS read-only 
		STATUS current
		DESCRIPTION  "MGCP CRCX" 
		::={ acosCgnv6FixedNatAlgMgcpS 3 } 

		dlcx OBJECT-TYPE
		SYNTAX  CounterBasedGauge64 
		MAX-ACCESS read-only 
		STATUS current
		DESCRIPTION  "MGCP DLCX" 
		::={ acosCgnv6FixedNatAlgMgcpS 4 } 

		epcf OBJECT-TYPE
		SYNTAX  CounterBasedGauge64 
		MAX-ACCESS read-only 
		STATUS current
		DESCRIPTION  "MGCP EPCF" 
		::={ acosCgnv6FixedNatAlgMgcpS 5 } 

		mdcx OBJECT-TYPE
		SYNTAX  CounterBasedGauge64 
		MAX-ACCESS read-only 
		STATUS current
		DESCRIPTION  "MGCP MDCX" 
		::={ acosCgnv6FixedNatAlgMgcpS 6 } 

		ntfy OBJECT-TYPE
		SYNTAX  CounterBasedGauge64 
		MAX-ACCESS read-only 
		STATUS current
		DESCRIPTION  "MGCP NTFY" 
		::={ acosCgnv6FixedNatAlgMgcpS 7 } 

		rqnt OBJECT-TYPE
		SYNTAX  CounterBasedGauge64 
		MAX-ACCESS read-only 
		STATUS current
		DESCRIPTION  "MGCP RQNT" 
		::={ acosCgnv6FixedNatAlgMgcpS 8 } 

		rsip OBJECT-TYPE
		SYNTAX  CounterBasedGauge64 
		MAX-ACCESS read-only 
		STATUS current
		DESCRIPTION  "MGCP RSIP" 
		::={ acosCgnv6FixedNatAlgMgcpS 9 } 

		parseError OBJECT-TYPE
		SYNTAX  CounterBasedGauge64 
		MAX-ACCESS read-only 
		STATUS current
		DESCRIPTION  "MGCP Message Parse Error" 
		::={ acosCgnv6FixedNatAlgMgcpS 10 } 

		connExtCreationFailure OBJECT-TYPE
		SYNTAX  CounterBasedGauge64 
		MAX-ACCESS read-only 
		STATUS current
		DESCRIPTION  "MGCP Create Connection Extension Failure" 
		::={ acosCgnv6FixedNatAlgMgcpS 11 } 

		thirdPartySdp OBJECT-TYPE
		SYNTAX  CounterBasedGauge64 
		MAX-ACCESS read-only 
		STATUS current
		DESCRIPTION  "MGCP Third-Party SDP" 
		::={ acosCgnv6FixedNatAlgMgcpS 12 } 

		sdpProcessCandidateFailure OBJECT-TYPE
		SYNTAX  CounterBasedGauge64 
		MAX-ACCESS read-only 
		STATUS current
		DESCRIPTION  "MGCP Operate SDP Media Candidate Attribute Failure" 
		::={ acosCgnv6FixedNatAlgMgcpS 13 } 

		sdpOpFailure OBJECT-TYPE
		SYNTAX  CounterBasedGauge64 
		MAX-ACCESS read-only 
		STATUS current
		DESCRIPTION  "MGCP Operate SDP Failure" 
		::={ acosCgnv6FixedNatAlgMgcpS 14 } 

		sdpAllocPortMapSuccess OBJECT-TYPE
		SYNTAX  CounterBasedGauge64 
		MAX-ACCESS read-only 
		STATUS current
		DESCRIPTION  "MGCP Alloc SDP Port Map Success" 
		::={ acosCgnv6FixedNatAlgMgcpS 15 } 

		sdpAllocPortMapFailure OBJECT-TYPE
		SYNTAX  CounterBasedGauge64 
		MAX-ACCESS read-only 
		STATUS current
		DESCRIPTION  "MGCP Alloc SDP Port Map Failure" 
		::={ acosCgnv6FixedNatAlgMgcpS 16 } 

		modifyFailure OBJECT-TYPE
		SYNTAX  CounterBasedGauge64 
		MAX-ACCESS read-only 
		STATUS current
		DESCRIPTION  "MGCP Message Modify Failure" 
		::={ acosCgnv6FixedNatAlgMgcpS 17 } 

		rewriteFailure OBJECT-TYPE
		SYNTAX  CounterBasedGauge64 
		MAX-ACCESS read-only 
		STATUS current
		DESCRIPTION  "MGCP Message Rewrite Failure" 
		::={ acosCgnv6FixedNatAlgMgcpS 18 } 

		tcpOutOfOrderDrop OBJECT-TYPE
		SYNTAX  CounterBasedGauge64 
		MAX-ACCESS read-only 
		STATUS current
		DESCRIPTION  "TCP Out-of-Order Drop" 
		::={ acosCgnv6FixedNatAlgMgcpS 19 } 

acosCgnv6FixedNatAlgTftp            OBJECT IDENTIFIER ::= { acosCgnv6FixedNatAlg 7 }
acosCgnv6FixedNatAlgTftpS           OBJECT IDENTIFIER ::= { acosCgnv6FixedNatAlgTftp 1 }

		sessionCreated OBJECT-TYPE
		SYNTAX  CounterBasedGauge64 
		MAX-ACCESS read-only 
		STATUS current
		DESCRIPTION  "TFTP Client Sessions Created" 
		::={ acosCgnv6FixedNatAlgTftpS 1 } 

		helperCreated OBJECT-TYPE
		SYNTAX  CounterBasedGauge64 
		MAX-ACCESS read-only 
		STATUS current
		DESCRIPTION  "TFTP Helper Sessions created" 
		::={ acosCgnv6FixedNatAlgTftpS 2 } 

		helperFreed OBJECT-TYPE
		SYNTAX  CounterBasedGauge64 
		MAX-ACCESS read-only 
		STATUS current
		DESCRIPTION  "TFTP Helper Sessions freed" 
		::={ acosCgnv6FixedNatAlgTftpS 3 } 

		helperFreedUsed OBJECT-TYPE
		SYNTAX  CounterBasedGauge64 
		MAX-ACCESS read-only 
		STATUS current
		DESCRIPTION  "TFTP Helper Sessions freed used" 
		::={ acosCgnv6FixedNatAlgTftpS 4 } 

		helperFreedUnused OBJECT-TYPE
		SYNTAX  CounterBasedGauge64 
		MAX-ACCESS read-only 
		STATUS current
		DESCRIPTION  "TFTP Helper Sessions freed unused" 
		::={ acosCgnv6FixedNatAlgTftpS 5 } 

		helperAlreadyUsed OBJECT-TYPE
		SYNTAX  CounterBasedGauge64 
		MAX-ACCESS read-only 
		STATUS current
		DESCRIPTION  "TFTP Helper Session already used" 
		::={ acosCgnv6FixedNatAlgTftpS 6 } 

		helperInRml OBJECT-TYPE
		SYNTAX  CounterBasedGauge64 
		MAX-ACCESS read-only 
		STATUS current
		DESCRIPTION  "TFTP Helper Session in Remove List" 
		::={ acosCgnv6FixedNatAlgTftpS 7 } 

acosCgnv6FixedNatAlgH323            OBJECT IDENTIFIER ::= { acosCgnv6FixedNatAlg 8 }
acosCgnv6FixedNatAlgH323S           OBJECT IDENTIFIER ::= { acosCgnv6FixedNatAlgH323 1 }

		h225rasMessage OBJECT-TYPE
		SYNTAX  CounterBasedGauge64 
		MAX-ACCESS read-only 
		STATUS current
		DESCRIPTION  "H323 H225 RAS Message" 
		::={ acosCgnv6FixedNatAlgH323S 1 } 

		h225csMessage OBJECT-TYPE
		SYNTAX  CounterBasedGauge64 
		MAX-ACCESS read-only 
		STATUS current
		DESCRIPTION  "H323 H225 Call Signaling Message" 
		::={ acosCgnv6FixedNatAlgH323S 2 } 

		h245ctlMessage OBJECT-TYPE
		SYNTAX  CounterBasedGauge64 
		MAX-ACCESS read-only 
		STATUS current
		DESCRIPTION  "H323 H245 Media Control Message" 
		::={ acosCgnv6FixedNatAlgH323S 3 } 

		h245Tunneled OBJECT-TYPE
		SYNTAX  CounterBasedGauge64 
		MAX-ACCESS read-only 
		STATUS current
		DESCRIPTION  "H323 H245 Tunnelled Message" 
		::={ acosCgnv6FixedNatAlgH323S 4 } 

		fastStart OBJECT-TYPE
		SYNTAX  CounterBasedGauge64 
		MAX-ACCESS read-only 
		STATUS current
		DESCRIPTION  "H323 FastStart" 
		::={ acosCgnv6FixedNatAlgH323S 5 } 

		parseError OBJECT-TYPE
		SYNTAX  CounterBasedGauge64 
		MAX-ACCESS read-only 
		STATUS current
		DESCRIPTION  "Message Parse Error" 
		::={ acosCgnv6FixedNatAlgH323S 6 } 

		messageCrossMultiPackets OBJECT-TYPE
		SYNTAX  CounterBasedGauge64 
		MAX-ACCESS read-only 
		STATUS current
		DESCRIPTION  "H323 Message Cross Multiple Packets" 
		::={ acosCgnv6FixedNatAlgH323S 7 } 

		connExtCreationFailure OBJECT-TYPE
		SYNTAX  CounterBasedGauge64 
		MAX-ACCESS read-only 
		STATUS current
		DESCRIPTION  "H323 Packet Rewrite Failure" 
		::={ acosCgnv6FixedNatAlgH323S 8 } 

		rewriteFailure OBJECT-TYPE
		SYNTAX  CounterBasedGauge64 
		MAX-ACCESS read-only 
		STATUS current
		DESCRIPTION  "H323 Message Rewrite Failure" 
		::={ acosCgnv6FixedNatAlgH323S 9 } 

		tcpOutOfOrderDrop OBJECT-TYPE
		SYNTAX  CounterBasedGauge64 
		MAX-ACCESS read-only 
		STATUS current
		DESCRIPTION  "TCP Out-of-Order Drop" 
		::={ acosCgnv6FixedNatAlgH323S 10 } 

		h245DynamicAddrExceed OBJECT-TYPE
		SYNTAX  CounterBasedGauge64 
		MAX-ACCESS read-only 
		STATUS current
		DESCRIPTION  "H323 H245 Dynamic Address Exceed" 
		::={ acosCgnv6FixedNatAlgH323S 11 } 

acosCgnv6FixedNatPerInstance        OBJECT IDENTIFIER ::= { acosCgnv6FixedNat 12 }
acosCgnv6FixedNatPerInstanceS       OBJECT IDENTIFIER ::= { acosCgnv6FixedNatPerInstance 1 }
acosCgnv6Pcp                        OBJECT IDENTIFIER ::= { acosCgnv6 25 }
acosCgnv6PcpS                       OBJECT IDENTIFIER ::= { acosCgnv6Pcp 1 }

		packetsRcv OBJECT-TYPE
		SYNTAX  CounterBasedGauge64 
		MAX-ACCESS read-only 
		STATUS current
		DESCRIPTION  "Packets Received" 
		::={ acosCgnv6PcpS 1 } 

		lsnMapProcessSuccess OBJECT-TYPE
		SYNTAX  CounterBasedGauge64 
		MAX-ACCESS read-only 
		STATUS current
		DESCRIPTION  "PCP MAP Request Processing Success (NAT44)" 
		::={ acosCgnv6PcpS 2 } 

		dsliteMapProcessSuccess OBJECT-TYPE
		SYNTAX  CounterBasedGauge64 
		MAX-ACCESS read-only 
		STATUS current
		DESCRIPTION  "PCP MAP Request Processing Success (DS-Lite)" 
		::={ acosCgnv6PcpS 3 } 

		nat64MapProcessSuccess OBJECT-TYPE
		SYNTAX  CounterBasedGauge64 
		MAX-ACCESS read-only 
		STATUS current
		DESCRIPTION  "PCP MAP Request Processing Success (NAT64)" 
		::={ acosCgnv6PcpS 4 } 

		lsnPeerProcessSuccess OBJECT-TYPE
		SYNTAX  CounterBasedGauge64 
		MAX-ACCESS read-only 
		STATUS current
		DESCRIPTION  "PCP PEER Request Processing Success (NAT44)" 
		::={ acosCgnv6PcpS 5 } 

		dslitePeerProcessSuccess OBJECT-TYPE
		SYNTAX  CounterBasedGauge64 
		MAX-ACCESS read-only 
		STATUS current
		DESCRIPTION  "PCP PEER Request Processing Success (DS-Lite)" 
		::={ acosCgnv6PcpS 6 } 

		nat64PeerProcessSuccess OBJECT-TYPE
		SYNTAX  CounterBasedGauge64 
		MAX-ACCESS read-only 
		STATUS current
		DESCRIPTION  "PCP PEER Request Processing Success (NAT64)" 
		::={ acosCgnv6PcpS 7 } 

		lsnAnnounceProcessSuccess OBJECT-TYPE
		SYNTAX  CounterBasedGauge64 
		MAX-ACCESS read-only 
		STATUS current
		DESCRIPTION  "PCP ANNOUNCE Request Processing Success (NAT44)" 
		::={ acosCgnv6PcpS 8 } 

		dsliteAnnounceProcessSuccess OBJECT-TYPE
		SYNTAX  CounterBasedGauge64 
		MAX-ACCESS read-only 
		STATUS current
		DESCRIPTION  "PCP ANNOUNCE Request Processing Success (DS-Lite)" 
		::={ acosCgnv6PcpS 9 } 

		nat64AnnounceProcessSuccess OBJECT-TYPE
		SYNTAX  CounterBasedGauge64 
		MAX-ACCESS read-only 
		STATUS current
		DESCRIPTION  "PCP ANNOUNCE Request Processing Success (NAT64)" 
		::={ acosCgnv6PcpS 10 } 

		pktNotRequestDrop OBJECT-TYPE
		SYNTAX  CounterBasedGauge64 
		MAX-ACCESS read-only 
		STATUS current
		DESCRIPTION  "Packet Not a PCP Request" 
		::={ acosCgnv6PcpS 11 } 

		pktTooShortDrop OBJECT-TYPE
		SYNTAX  CounterBasedGauge64 
		MAX-ACCESS read-only 
		STATUS current
		DESCRIPTION  "Packet Too Short" 
		::={ acosCgnv6PcpS 12 } 

		norouteDrop OBJECT-TYPE
		SYNTAX  CounterBasedGauge64 
		MAX-ACCESS read-only 
		STATUS current
		DESCRIPTION  "Response No Route" 
		::={ acosCgnv6PcpS 13 } 

		unsupportedVersion OBJECT-TYPE
		SYNTAX  CounterBasedGauge64 
		MAX-ACCESS read-only 
		STATUS current
		DESCRIPTION  "Unsupported PCP version" 
		::={ acosCgnv6PcpS 14 } 

		notAuthorized OBJECT-TYPE
		SYNTAX  CounterBasedGauge64 
		MAX-ACCESS read-only 
		STATUS current
		DESCRIPTION  "PCP Request Not Authorized" 
		::={ acosCgnv6PcpS 15 } 

		malformRequest OBJECT-TYPE
		SYNTAX  CounterBasedGauge64 
		MAX-ACCESS read-only 
		STATUS current
		DESCRIPTION  "PCP Request Malformed" 
		::={ acosCgnv6PcpS 16 } 

		unsuppOpcode OBJECT-TYPE
		SYNTAX  CounterBasedGauge64 
		MAX-ACCESS read-only 
		STATUS current
		DESCRIPTION  "Unsupported PCP Opcode" 
		::={ acosCgnv6PcpS 17 } 

		unsuppOption OBJECT-TYPE
		SYNTAX  CounterBasedGauge64 
		MAX-ACCESS read-only 
		STATUS current
		DESCRIPTION  "Unsupported PCP Option" 
		::={ acosCgnv6PcpS 18 } 

		malformOption OBJECT-TYPE
		SYNTAX  CounterBasedGauge64 
		MAX-ACCESS read-only 
		STATUS current
		DESCRIPTION  "PCP Option Malformed" 
		::={ acosCgnv6PcpS 19 } 

		noResources OBJECT-TYPE
		SYNTAX  CounterBasedGauge64 
		MAX-ACCESS read-only 
		STATUS current
		DESCRIPTION  "No System or NAT Resources" 
		::={ acosCgnv6PcpS 20 } 

		unsuppProtocol OBJECT-TYPE
		SYNTAX  CounterBasedGauge64 
		MAX-ACCESS read-only 
		STATUS current
		DESCRIPTION  "Unsupported Mapping Protocol" 
		::={ acosCgnv6PcpS 21 } 

		userQuotaExceeded OBJECT-TYPE
		SYNTAX  CounterBasedGauge64 
		MAX-ACCESS read-only 
		STATUS current
		DESCRIPTION  "User Quota Exceeded" 
		::={ acosCgnv6PcpS 22 } 

		cannotProvideSuggest OBJECT-TYPE
		SYNTAX  CounterBasedGauge64 
		MAX-ACCESS read-only 
		STATUS current
		DESCRIPTION  "Cannot Provide Suggested Port When PREFER_FAILURE" 
		::={ acosCgnv6PcpS 23 } 

		addressMismatch OBJECT-TYPE
		SYNTAX  CounterBasedGauge64 
		MAX-ACCESS read-only 
		STATUS current
		DESCRIPTION  "PCP Client Address Mismatch" 
		::={ acosCgnv6PcpS 24 } 

		excessiveRemotePeers OBJECT-TYPE
		SYNTAX  CounterBasedGauge64 
		MAX-ACCESS read-only 
		STATUS current
		DESCRIPTION  "Excessive Remote Peers" 
		::={ acosCgnv6PcpS 25 } 

		pktNotFromNatInside OBJECT-TYPE
		SYNTAX  CounterBasedGauge64 
		MAX-ACCESS read-only 
		STATUS current
		DESCRIPTION  "Packet Dropped For Not Coming From NAT Inside" 
		::={ acosCgnv6PcpS 26 } 

		l4ProcessError OBJECT-TYPE
		SYNTAX  CounterBasedGauge64 
		MAX-ACCESS read-only 
		STATUS current
		DESCRIPTION  "L3/L4 Process Error" 
		::={ acosCgnv6PcpS 27 } 

		internalErrorDrop OBJECT-TYPE
		SYNTAX  CounterBasedGauge64 
		MAX-ACCESS read-only 
		STATUS current
		DESCRIPTION  "Internal Error" 
		::={ acosCgnv6PcpS 28 } 

		unsolAnceSentSucc OBJECT-TYPE
		SYNTAX  CounterBasedGauge64 
		MAX-ACCESS read-only 
		STATUS current
		DESCRIPTION  "Unsolicited Announce Sent" 
		::={ acosCgnv6PcpS 29 } 

		unsolAnceSentFail OBJECT-TYPE
		SYNTAX  CounterBasedGauge64 
		MAX-ACCESS read-only 
		STATUS current
		DESCRIPTION  "Unsolicited Announce Send Failure" 
		::={ acosCgnv6PcpS 30 } 

		haSyncEpochSent OBJECT-TYPE
		SYNTAX  CounterBasedGauge64 
		MAX-ACCESS read-only 
		STATUS current
		DESCRIPTION  "HA Sync PCP Epoch Sent" 
		::={ acosCgnv6PcpS 31 } 

		haSyncEpochRcv OBJECT-TYPE
		SYNTAX  CounterBasedGauge64 
		MAX-ACCESS read-only 
		STATUS current
		DESCRIPTION  "HA Sync PCP Epoch Recv" 
		::={ acosCgnv6PcpS 32 } 

		fullconeExtAlloc OBJECT-TYPE
		SYNTAX  CounterBasedGauge64 
		MAX-ACCESS read-only 
		STATUS current
		DESCRIPTION  "PCP Fullcone Extension Alloc" 
		::={ acosCgnv6PcpS 33 } 

		fullconeExtFree OBJECT-TYPE
		SYNTAX  CounterBasedGauge64 
		MAX-ACCESS read-only 
		STATUS current
		DESCRIPTION  "PCP Fullcone Extension Free" 
		::={ acosCgnv6PcpS 34 } 

		fullconeExtAllocFailure OBJECT-TYPE
		SYNTAX  CounterBasedGauge64 
		MAX-ACCESS read-only 
		STATUS current
		DESCRIPTION  "PCP Fullcone Extension Alloc Failure" 
		::={ acosCgnv6PcpS 35 } 

		fullconeExtNotfound OBJECT-TYPE
		SYNTAX  CounterBasedGauge64 
		MAX-ACCESS read-only 
		STATUS current
		DESCRIPTION  "PCP Fullcone Extension Not Found" 
		::={ acosCgnv6PcpS 36 } 

		fullconeExtReuse OBJECT-TYPE
		SYNTAX  CounterBasedGauge64 
		MAX-ACCESS read-only 
		STATUS current
		DESCRIPTION  "PCP Fullcone Extension Reuse" 
		::={ acosCgnv6PcpS 37 } 

		clientNonceMismatch OBJECT-TYPE
		SYNTAX  CounterBasedGauge64 
		MAX-ACCESS read-only 
		STATUS current
		DESCRIPTION  "PCP Client Nonce Mismatch" 
		::={ acosCgnv6PcpS 38 } 

		mapFilterSet OBJECT-TYPE
		SYNTAX  CounterBasedGauge64 
		MAX-ACCESS read-only 
		STATUS current
		DESCRIPTION  "PCP MAP Filter Set" 
		::={ acosCgnv6PcpS 39 } 

		mapFilterDeny OBJECT-TYPE
		SYNTAX  CounterBasedGauge64 
		MAX-ACCESS read-only 
		STATUS current
		DESCRIPTION  "PCP MAP Filter Deny Inbound" 
		::={ acosCgnv6PcpS 40 } 

		interBoardPkts OBJECT-TYPE
		SYNTAX  CounterBasedGauge64 
		MAX-ACCESS read-only 
		STATUS current
		DESCRIPTION  "PCP Inter board packets" 
		::={ acosCgnv6PcpS 41 } 

acosCgnv6Nptv6                      OBJECT IDENTIFIER ::= { acosCgnv6 26 }
acosCgnv6Nptv6Domain                OBJECT IDENTIFIER ::= { acosCgnv6Nptv6 2 }
acosCgnv6Nptv6DomainS               OBJECT IDENTIFIER ::= { acosCgnv6Nptv6Domain 1 }

cgnv6Nptv6DomainSTable OBJECT-TYPE
		SYNTAX SEQUENCE OF Cgnv6Nptv6DomainSEntry
		MAX-ACCESS not-accessible
		STATUS current
		::={ acosCgnv6Nptv6DomainS 1 } 


	cgnv6Nptv6DomainSEntry OBJECT-TYPE
		SYNTAX Cgnv6Nptv6DomainSEntry
		MAX-ACCESS not-accessible
		STATUS current
		INDEX {
			name
		}
		::={ cgnv6Nptv6DomainSTable 1 } 


	Cgnv6Nptv6DomainSEntry ::=
		SEQUENCE {
			name DisplayString, 
			outboundPackets CounterBasedGauge64,
			inboundPackets CounterBasedGauge64,
			hairpinPackets CounterBasedGauge64,
			addressNotValidForTranslation CounterBasedGauge64,
			inboundPacketsNoMap CounterBasedGauge64,
			packetsDestUnreachable CounterBasedGauge64
		}

			name OBJECT-TYPE
			SYNTAX  DisplayString 
			MAX-ACCESS read-only 
			STATUS current
			DESCRIPTION  "Name of NPTv6 domain" 
			::={ cgnv6Nptv6DomainSEntry 1 } 

			outboundPackets OBJECT-TYPE
			SYNTAX  CounterBasedGauge64 
			MAX-ACCESS read-only 
			STATUS current
			DESCRIPTION  "Outbound Packets" 
			::={ cgnv6Nptv6DomainSEntry 2 } 

			inboundPackets OBJECT-TYPE
			SYNTAX  CounterBasedGauge64 
			MAX-ACCESS read-only 
			STATUS current
			DESCRIPTION  "Inbound Packets" 
			::={ cgnv6Nptv6DomainSEntry 3 } 

			hairpinPackets OBJECT-TYPE
			SYNTAX  CounterBasedGauge64 
			MAX-ACCESS read-only 
			STATUS current
			DESCRIPTION  "Hairpin Packets" 
			::={ cgnv6Nptv6DomainSEntry 4 } 

			addressNotValidForTranslation OBJECT-TYPE
			SYNTAX  CounterBasedGauge64 
			MAX-ACCESS read-only 
			STATUS current
			DESCRIPTION  "Address Not Valid For Translation" 
			::={ cgnv6Nptv6DomainSEntry 5 } 

			inboundPacketsNoMap OBJECT-TYPE
			SYNTAX  CounterBasedGauge64 
			MAX-ACCESS read-only 
			STATUS current
			DESCRIPTION  "Inbound Packets No Map" 
			::={ cgnv6Nptv6DomainSEntry 6 } 

			packetsDestUnreachable OBJECT-TYPE
			SYNTAX  CounterBasedGauge64 
			MAX-ACCESS read-only 
			STATUS current
			DESCRIPTION  "Packets Destination Unreachable" 
			::={ cgnv6Nptv6DomainSEntry 7 } 

acosCgnv6Logging                    OBJECT IDENTIFIER ::= { acosCgnv6 27 }
acosCgnv6LoggingS                   OBJECT IDENTIFIER ::= { acosCgnv6Logging 1 }

		tcpSessionCreated OBJECT-TYPE
		SYNTAX  CounterBasedGauge64 
		MAX-ACCESS read-only 
		STATUS current
		DESCRIPTION  "TCP Session Created" 
		::={ acosCgnv6LoggingS 1 } 

		tcpSessionDeleted OBJECT-TYPE
		SYNTAX  CounterBasedGauge64 
		MAX-ACCESS read-only 
		STATUS current
		DESCRIPTION  "TCP Session Deleted" 
		::={ acosCgnv6LoggingS 2 } 

		tcpPortAllocated OBJECT-TYPE
		SYNTAX  CounterBasedGauge64 
		MAX-ACCESS read-only 
		STATUS current
		DESCRIPTION  "TCP Port Allocated" 
		::={ acosCgnv6LoggingS 3 } 

		tcpPortFreed OBJECT-TYPE
		SYNTAX  CounterBasedGauge64 
		MAX-ACCESS read-only 
		STATUS current
		DESCRIPTION  "TCP Port Freed" 
		::={ acosCgnv6LoggingS 4 } 

		tcpPortBatchAllocated OBJECT-TYPE
		SYNTAX  CounterBasedGauge64 
		MAX-ACCESS read-only 
		STATUS current
		DESCRIPTION  "TCP Port Batch Allocated" 
		::={ acosCgnv6LoggingS 5 } 

		tcpPortBatchFreed OBJECT-TYPE
		SYNTAX  CounterBasedGauge64 
		MAX-ACCESS read-only 
		STATUS current
		DESCRIPTION  "TCP Port Batch Freed" 
		::={ acosCgnv6LoggingS 6 } 

		udpSessionCreated OBJECT-TYPE
		SYNTAX  CounterBasedGauge64 
		MAX-ACCESS read-only 
		STATUS current
		DESCRIPTION  "UDP Session Created" 
		::={ acosCgnv6LoggingS 7 } 

		udpSessionDeleted OBJECT-TYPE
		SYNTAX  CounterBasedGauge64 
		MAX-ACCESS read-only 
		STATUS current
		DESCRIPTION  "UDP Session Deleted" 
		::={ acosCgnv6LoggingS 8 } 

		udpPortAllocated OBJECT-TYPE
		SYNTAX  CounterBasedGauge64 
		MAX-ACCESS read-only 
		STATUS current
		DESCRIPTION  "UDP Port Allocated" 
		::={ acosCgnv6LoggingS 9 } 

		udpPortFreed OBJECT-TYPE
		SYNTAX  CounterBasedGauge64 
		MAX-ACCESS read-only 
		STATUS current
		DESCRIPTION  "UDP Port Freed" 
		::={ acosCgnv6LoggingS 10 } 

		udpPortBatchAllocated OBJECT-TYPE
		SYNTAX  CounterBasedGauge64 
		MAX-ACCESS read-only 
		STATUS current
		DESCRIPTION  "UDP Port Batch Allocated" 
		::={ acosCgnv6LoggingS 11 } 

		udpPortBatchFreed OBJECT-TYPE
		SYNTAX  CounterBasedGauge64 
		MAX-ACCESS read-only 
		STATUS current
		DESCRIPTION  "UDP Port Batch Freed" 
		::={ acosCgnv6LoggingS 12 } 

		icmpSessionCreated OBJECT-TYPE
		SYNTAX  CounterBasedGauge64 
		MAX-ACCESS read-only 
		STATUS current
		DESCRIPTION  "ICMP Session Created" 
		::={ acosCgnv6LoggingS 13 } 

		icmpSessionDeleted OBJECT-TYPE
		SYNTAX  CounterBasedGauge64 
		MAX-ACCESS read-only 
		STATUS current
		DESCRIPTION  "ICMP Session Deleted" 
		::={ acosCgnv6LoggingS 14 } 

		icmpResourceAllocated OBJECT-TYPE
		SYNTAX  CounterBasedGauge64 
		MAX-ACCESS read-only 
		STATUS current
		DESCRIPTION  "ICMP Resource Allocated" 
		::={ acosCgnv6LoggingS 15 } 

		icmpResourceFreed OBJECT-TYPE
		SYNTAX  CounterBasedGauge64 
		MAX-ACCESS read-only 
		STATUS current
		DESCRIPTION  "ICMP Resource Freed" 
		::={ acosCgnv6LoggingS 16 } 

		icmpv6SessionCreated OBJECT-TYPE
		SYNTAX  CounterBasedGauge64 
		MAX-ACCESS read-only 
		STATUS current
		DESCRIPTION  "ICMPV6 Session Created" 
		::={ acosCgnv6LoggingS 17 } 

		icmpv6SessionDeleted OBJECT-TYPE
		SYNTAX  CounterBasedGauge64 
		MAX-ACCESS read-only 
		STATUS current
		DESCRIPTION  "ICMPV6 Session Deleted" 
		::={ acosCgnv6LoggingS 18 } 

		icmpv6ResourceAllocated OBJECT-TYPE
		SYNTAX  CounterBasedGauge64 
		MAX-ACCESS read-only 
		STATUS current
		DESCRIPTION  "ICMPV6 Resource Allocated" 
		::={ acosCgnv6LoggingS 19 } 

		icmpv6ResourceFreed OBJECT-TYPE
		SYNTAX  CounterBasedGauge64 
		MAX-ACCESS read-only 
		STATUS current
		DESCRIPTION  "ICMPV6 Resource Freed" 
		::={ acosCgnv6LoggingS 20 } 

		cgnv6LoggingGreSessionCreated OBJECT-TYPE
		SYNTAX  CounterBasedGauge64 
		MAX-ACCESS read-only 
		STATUS current
		DESCRIPTION  "GRE Session Created" 
		::={ acosCgnv6LoggingS 21 } 

		greSessionDeleted OBJECT-TYPE
		SYNTAX  CounterBasedGauge64 
		MAX-ACCESS read-only 
		STATUS current
		DESCRIPTION  "GRE Session Deleted" 
		::={ acosCgnv6LoggingS 22 } 

		greResourceAllocated OBJECT-TYPE
		SYNTAX  CounterBasedGauge64 
		MAX-ACCESS read-only 
		STATUS current
		DESCRIPTION  "GRE Resource Allocated" 
		::={ acosCgnv6LoggingS 23 } 

		greResourceFreed OBJECT-TYPE
		SYNTAX  CounterBasedGauge64 
		MAX-ACCESS read-only 
		STATUS current
		DESCRIPTION  "GRE Resource Freed" 
		::={ acosCgnv6LoggingS 24 } 

		espSessionCreated OBJECT-TYPE
		SYNTAX  CounterBasedGauge64 
		MAX-ACCESS read-only 
		STATUS current
		DESCRIPTION  "ESP Session Created" 
		::={ acosCgnv6LoggingS 25 } 

		espSessionDeleted OBJECT-TYPE
		SYNTAX  CounterBasedGauge64 
		MAX-ACCESS read-only 
		STATUS current
		DESCRIPTION  "ESP Session Deleted" 
		::={ acosCgnv6LoggingS 26 } 

		espResourceAllocated OBJECT-TYPE
		SYNTAX  CounterBasedGauge64 
		MAX-ACCESS read-only 
		STATUS current
		DESCRIPTION  "ESP Resource Allocated" 
		::={ acosCgnv6LoggingS 27 } 

		espResourceFreed OBJECT-TYPE
		SYNTAX  CounterBasedGauge64 
		MAX-ACCESS read-only 
		STATUS current
		DESCRIPTION  "ESP Resource Freed" 
		::={ acosCgnv6LoggingS 28 } 

		fixedNatUserPorts OBJECT-TYPE
		SYNTAX  CounterBasedGauge64 
		MAX-ACCESS read-only 
		STATUS current
		DESCRIPTION  "Fixed NAT Inside User Port Mapping" 
		::={ acosCgnv6LoggingS 29 } 

		fixedNatDisableConfigLogged OBJECT-TYPE
		SYNTAX  CounterBasedGauge64 
		MAX-ACCESS read-only 
		STATUS current
		DESCRIPTION  "Fixed NAT Periodic Configs Logged" 
		::={ acosCgnv6LoggingS 30 } 

		fixedNatDisableConfigLogsSent OBJECT-TYPE
		SYNTAX  CounterBasedGauge64 
		MAX-ACCESS read-only 
		STATUS current
		DESCRIPTION  "Fixed NAT Periodic Config Logs Sent" 
		::={ acosCgnv6LoggingS 31 } 

		fixedNatPeriodicConfigLogsSent OBJECT-TYPE
		SYNTAX  CounterBasedGauge64 
		MAX-ACCESS read-only 
		STATUS current
		DESCRIPTION  "Fixed NAT Disabled Configs Logged" 
		::={ acosCgnv6LoggingS 32 } 

		fixedNatPeriodicConfigLogged OBJECT-TYPE
		SYNTAX  CounterBasedGauge64 
		MAX-ACCESS read-only 
		STATUS current
		DESCRIPTION  "Fixed NAT Disabled Config Logs Sent" 
		::={ acosCgnv6LoggingS 33 } 

		fixedNatInterimUpdated OBJECT-TYPE
		SYNTAX  CounterBasedGauge64 
		MAX-ACCESS read-only 
		STATUS current
		DESCRIPTION  "Fixed NAT Interim Updated" 
		::={ acosCgnv6LoggingS 34 } 

		enhancedUserLog OBJECT-TYPE
		SYNTAX  CounterBasedGauge64 
		MAX-ACCESS read-only 
		STATUS current
		DESCRIPTION  "Enhanced User Log" 
		::={ acosCgnv6LoggingS 35 } 

		logSent OBJECT-TYPE
		SYNTAX  CounterBasedGauge64 
		MAX-ACCESS read-only 
		STATUS current
		DESCRIPTION  "Log Packets Sent" 
		::={ acosCgnv6LoggingS 36 } 

		logDropped OBJECT-TYPE
		SYNTAX  CounterBasedGauge64 
		MAX-ACCESS read-only 
		STATUS current
		DESCRIPTION  "Log Packets Dropped" 
		::={ acosCgnv6LoggingS 37 } 

		connTcpEstablished OBJECT-TYPE
		SYNTAX  CounterBasedGauge64 
		MAX-ACCESS read-only 
		STATUS current
		DESCRIPTION  "TCP Connection Established" 
		::={ acosCgnv6LoggingS 38 } 

		connTcpDropped OBJECT-TYPE
		SYNTAX  CounterBasedGauge64 
		MAX-ACCESS read-only 
		STATUS current
		DESCRIPTION  "TCP Connection Lost" 
		::={ acosCgnv6LoggingS 39 } 

		tcpPortOverloadingAllocated OBJECT-TYPE
		SYNTAX  CounterBasedGauge64 
		MAX-ACCESS read-only 
		STATUS current
		DESCRIPTION  "TCP Port Overloading Allocated" 
		::={ acosCgnv6LoggingS 40 } 

		tcpPortOverloadingFreed OBJECT-TYPE
		SYNTAX  CounterBasedGauge64 
		MAX-ACCESS read-only 
		STATUS current
		DESCRIPTION  "TCP Port Overloading Freed" 
		::={ acosCgnv6LoggingS 41 } 

		udpPortOverloadingAllocated OBJECT-TYPE
		SYNTAX  CounterBasedGauge64 
		MAX-ACCESS read-only 
		STATUS current
		DESCRIPTION  "UDP Port Overloading Allocated" 
		::={ acosCgnv6LoggingS 42 } 

		udpPortOverloadingFreed OBJECT-TYPE
		SYNTAX  CounterBasedGauge64 
		MAX-ACCESS read-only 
		STATUS current
		DESCRIPTION  "UDP Port Overloading Freed" 
		::={ acosCgnv6LoggingS 43 } 

		httpRequestLogged OBJECT-TYPE
		SYNTAX  CounterBasedGauge64 
		MAX-ACCESS read-only 
		STATUS current
		DESCRIPTION  "HTTP Request Logged" 
		::={ acosCgnv6LoggingS 44 } 

		reducedLogsByDestination OBJECT-TYPE
		SYNTAX  CounterBasedGauge64 
		MAX-ACCESS read-only 
		STATUS current
		DESCRIPTION  "Reduced Logs by Destination Protocol and Port" 
		::={ acosCgnv6LoggingS 45 } 

		outOfBuffers OBJECT-TYPE
		SYNTAX  CounterBasedGauge64 
		MAX-ACCESS read-only 
		STATUS current
		DESCRIPTION  "Out of Buffers" 
		::={ acosCgnv6LoggingS 46 } 

		addMsgFailed OBJECT-TYPE
		SYNTAX  CounterBasedGauge64 
		MAX-ACCESS read-only 
		STATUS current
		DESCRIPTION  "Add Message to Buffer Failed" 
		::={ acosCgnv6LoggingS 47 } 

		rtspPortAllocated OBJECT-TYPE
		SYNTAX  CounterBasedGauge64 
		MAX-ACCESS read-only 
		STATUS current
		DESCRIPTION  "RTSP UDP Port Allocated" 
		::={ acosCgnv6LoggingS 48 } 

		rtspPortFreed OBJECT-TYPE
		SYNTAX  CounterBasedGauge64 
		MAX-ACCESS read-only 
		STATUS current
		DESCRIPTION  "RTSP UDP Port Freed" 
		::={ acosCgnv6LoggingS 49 } 

		connTcpCreateFailed OBJECT-TYPE
		SYNTAX  CounterBasedGauge64 
		MAX-ACCESS read-only 
		STATUS current
		DESCRIPTION  "TCP Connection Failed" 
		::={ acosCgnv6LoggingS 50 } 

		ipv4FragApplied OBJECT-TYPE
		SYNTAX  CounterBasedGauge64 
		MAX-ACCESS read-only 
		STATUS current
		DESCRIPTION  "IPv4 Fragmentation Applied" 
		::={ acosCgnv6LoggingS 51 } 

		ipv4FragFailed OBJECT-TYPE
		SYNTAX  CounterBasedGauge64 
		MAX-ACCESS read-only 
		STATUS current
		DESCRIPTION  "IPv4 Fragmentation Failed" 
		::={ acosCgnv6LoggingS 52 } 

		ipv6FragApplied OBJECT-TYPE
		SYNTAX  CounterBasedGauge64 
		MAX-ACCESS read-only 
		STATUS current
		DESCRIPTION  "IPv6 Fragmentation Applied" 
		::={ acosCgnv6LoggingS 53 } 

		ipv6FragFailed OBJECT-TYPE
		SYNTAX  CounterBasedGauge64 
		MAX-ACCESS read-only 
		STATUS current
		DESCRIPTION  "IPv6 Fragmentation Failed" 
		::={ acosCgnv6LoggingS 54 } 

		interimUpdateScheduled OBJECT-TYPE
		SYNTAX  CounterBasedGauge64 
		MAX-ACCESS read-only 
		STATUS current
		DESCRIPTION  "Port Allocation Interim Update Scheduled" 
		::={ acosCgnv6LoggingS 55 } 

		interimUpdateScheduleFailed OBJECT-TYPE
		SYNTAX  CounterBasedGauge64 
		MAX-ACCESS read-only 
		STATUS current
		DESCRIPTION  "Port Allocation Interim Update Failed" 
		::={ acosCgnv6LoggingS 56 } 

		interimUpdateTerminated OBJECT-TYPE
		SYNTAX  CounterBasedGauge64 
		MAX-ACCESS read-only 
		STATUS current
		DESCRIPTION  "Port Allocation Interim Update Terminated" 
		::={ acosCgnv6LoggingS 57 } 

		interimUpdateMemoryFreed OBJECT-TYPE
		SYNTAX  CounterBasedGauge64 
		MAX-ACCESS read-only 
		STATUS current
		DESCRIPTION  "Port Allocation Interim Update Memory Freed" 
		::={ acosCgnv6LoggingS 58 } 

		interimUpdateNoBuffRetried OBJECT-TYPE
		SYNTAX  CounterBasedGauge64 
		MAX-ACCESS read-only 
		STATUS current
		DESCRIPTION  "Port Allocation Interim Update Memory Freed" 
		::={ acosCgnv6LoggingS 59 } 

		tcpPortBatchInterimUpdated OBJECT-TYPE
		SYNTAX  CounterBasedGauge64 
		MAX-ACCESS read-only 
		STATUS current
		DESCRIPTION  "TCP Port Batch Interim Updated" 
		::={ acosCgnv6LoggingS 60 } 

		udpPortBatchInterimUpdated OBJECT-TYPE
		SYNTAX  CounterBasedGauge64 
		MAX-ACCESS read-only 
		STATUS current
		DESCRIPTION  "UDP Port Batch Interim Updated" 
		::={ acosCgnv6LoggingS 61 } 

		portBlockAccountingFreed OBJECT-TYPE
		SYNTAX  CounterBasedGauge64 
		MAX-ACCESS read-only 
		STATUS current
		DESCRIPTION  "Port Allocation Accounting Freed" 
		::={ acosCgnv6LoggingS 62 } 

		portBlockAccountingAllocated OBJECT-TYPE
		SYNTAX  CounterBasedGauge64 
		MAX-ACCESS read-only 
		STATUS current
		DESCRIPTION  "Port Allocation Accounting Allocated" 
		::={ acosCgnv6LoggingS 63 } 

		logMessageTooLong OBJECT-TYPE
		SYNTAX  CounterBasedGauge64 
		MAX-ACCESS read-only 
		STATUS current
		DESCRIPTION  "Log message too long" 
		::={ acosCgnv6LoggingS 64 } 

		httpOutOfOrderDropped OBJECT-TYPE
		SYNTAX  CounterBasedGauge64 
		MAX-ACCESS read-only 
		STATUS current
		DESCRIPTION  "HTTP out-of-order dropped" 
		::={ acosCgnv6LoggingS 65 } 

		httpAllocFailed OBJECT-TYPE
		SYNTAX  CounterBasedGauge64 
		MAX-ACCESS read-only 
		STATUS current
		DESCRIPTION  "HTTP Request Info Allocation Failed" 
		::={ acosCgnv6LoggingS 66 } 

		httpFragMergeFailedDropped OBJECT-TYPE
		SYNTAX  CounterBasedGauge64 
		MAX-ACCESS read-only 
		STATUS current
		DESCRIPTION  "HTTP frag merge failed dropped" 
		::={ acosCgnv6LoggingS 67 } 

		httpMalloc OBJECT-TYPE
		SYNTAX  CounterBasedGauge64 
		MAX-ACCESS read-only 
		STATUS current
		DESCRIPTION  "HTTP mem allocate" 
		::={ acosCgnv6LoggingS 68 } 

		httpMfree OBJECT-TYPE
		SYNTAX  CounterBasedGauge64 
		MAX-ACCESS read-only 
		STATUS current
		DESCRIPTION  "HTTP mem free" 
		::={ acosCgnv6LoggingS 69 } 

		httpSpmAllocType0 OBJECT-TYPE
		SYNTAX  CounterBasedGauge64 
		MAX-ACCESS read-only 
		STATUS current
		DESCRIPTION  "HTTP Conn SPM Type 0 allocate" 
		::={ acosCgnv6LoggingS 70 } 

		httpSpmAllocType1 OBJECT-TYPE
		SYNTAX  CounterBasedGauge64 
		MAX-ACCESS read-only 
		STATUS current
		DESCRIPTION  "HTTP Conn SPM Type 1 allocate" 
		::={ acosCgnv6LoggingS 71 } 

		httpSpmAllocType2 OBJECT-TYPE
		SYNTAX  CounterBasedGauge64 
		MAX-ACCESS read-only 
		STATUS current
		DESCRIPTION  "HTTP Conn SPM Type 2 allocate" 
		::={ acosCgnv6LoggingS 72 } 

		httpSpmAllocType3 OBJECT-TYPE
		SYNTAX  CounterBasedGauge64 
		MAX-ACCESS read-only 
		STATUS current
		DESCRIPTION  "HTTP Conn SPM Type 3 allocate" 
		::={ acosCgnv6LoggingS 73 } 

		httpSpmAllocType4 OBJECT-TYPE
		SYNTAX  CounterBasedGauge64 
		MAX-ACCESS read-only 
		STATUS current
		DESCRIPTION  "HTTP Conn SPM Type 4 allocate" 
		::={ acosCgnv6LoggingS 74 } 

		httpSpmFreeType0 OBJECT-TYPE
		SYNTAX  CounterBasedGauge64 
		MAX-ACCESS read-only 
		STATUS current
		DESCRIPTION  "HTTP Conn SPM Type 0 free" 
		::={ acosCgnv6LoggingS 75 } 

		httpSpmFreeType1 OBJECT-TYPE
		SYNTAX  CounterBasedGauge64 
		MAX-ACCESS read-only 
		STATUS current
		DESCRIPTION  "HTTP Conn SPM Type 1 free" 
		::={ acosCgnv6LoggingS 76 } 

		httpSpmFreeType2 OBJECT-TYPE
		SYNTAX  CounterBasedGauge64 
		MAX-ACCESS read-only 
		STATUS current
		DESCRIPTION  "HTTP Conn SPM Type 2 free" 
		::={ acosCgnv6LoggingS 77 } 

		httpSpmFreeType3 OBJECT-TYPE
		SYNTAX  CounterBasedGauge64 
		MAX-ACCESS read-only 
		STATUS current
		DESCRIPTION  "HTTP Conn SPM Type 3 free" 
		::={ acosCgnv6LoggingS 78 } 

		httpSpmFreeType4 OBJECT-TYPE
		SYNTAX  CounterBasedGauge64 
		MAX-ACCESS read-only 
		STATUS current
		DESCRIPTION  "HTTP Conn SPM Type 4 free" 
		::={ acosCgnv6LoggingS 79 } 

		iddosL3EntryCreate OBJECT-TYPE
		SYNTAX  CounterBasedGauge64 
		MAX-ACCESS read-only 
		STATUS current
		DESCRIPTION  "iDDoS L3 Entry Created" 
		::={ acosCgnv6LoggingS 80 } 

		iddosL3EntryDelete OBJECT-TYPE
		SYNTAX  CounterBasedGauge64 
		MAX-ACCESS read-only 
		STATUS current
		DESCRIPTION  "iDDoS L3 Entry Deleted" 
		::={ acosCgnv6LoggingS 81 } 

		iddosL4EntryCreate OBJECT-TYPE
		SYNTAX  CounterBasedGauge64 
		MAX-ACCESS read-only 
		STATUS current
		DESCRIPTION  "iDDoS L4 Entry Created" 
		::={ acosCgnv6LoggingS 82 } 

		iddosL4EntryDelete OBJECT-TYPE
		SYNTAX  CounterBasedGauge64 
		MAX-ACCESS read-only 
		STATUS current
		DESCRIPTION  "iDDoS L4 Entry Deleted" 
		::={ acosCgnv6LoggingS 83 } 

acosCgnv6L4                         OBJECT IDENTIFIER ::= { acosCgnv6 28 }
acosCgnv6L4S                        OBJECT IDENTIFIER ::= { acosCgnv6L4 1 }

		noFwdRoute OBJECT-TYPE
		SYNTAX  CounterBasedGauge64 
		MAX-ACCESS read-only 
		STATUS current
		DESCRIPTION  "No Forward Route for Session" 
		::={ acosCgnv6L4S 1 } 

		noRevRoute OBJECT-TYPE
		SYNTAX  CounterBasedGauge64 
		MAX-ACCESS read-only 
		STATUS current
		DESCRIPTION  "No Reverse Route for Session" 
		::={ acosCgnv6L4S 2 } 

		outOfSessionMemory OBJECT-TYPE
		SYNTAX  CounterBasedGauge64 
		MAX-ACCESS read-only 
		STATUS current
		DESCRIPTION  "Out of Session Memory" 
		::={ acosCgnv6L4S 3 } 

		tcpRstSent OBJECT-TYPE
		SYNTAX  CounterBasedGauge64 
		MAX-ACCESS read-only 
		STATUS current
		DESCRIPTION  "TCP RST Sent" 
		::={ acosCgnv6L4S 4 } 

		ipipIcmpReplySent OBJECT-TYPE
		SYNTAX  CounterBasedGauge64 
		MAX-ACCESS read-only 
		STATUS current
		DESCRIPTION  "IPIP ICMP Echo Reply Sent" 
		::={ acosCgnv6L4S 5 } 

		icmpFilteredSent OBJECT-TYPE
		SYNTAX  CounterBasedGauge64 
		MAX-ACCESS read-only 
		STATUS current
		DESCRIPTION  "ICMP Administratively Filtered Sent" 
		::={ acosCgnv6L4S 6 } 

		icmpHostUnreachableSent OBJECT-TYPE
		SYNTAX  CounterBasedGauge64 
		MAX-ACCESS read-only 
		STATUS current
		DESCRIPTION  "ICMP Host Unreachable Sent" 
		::={ acosCgnv6L4S 7 } 

		icmpReplyNoSessionDrop OBJECT-TYPE
		SYNTAX  CounterBasedGauge64 
		MAX-ACCESS read-only 
		STATUS current
		DESCRIPTION  "ICMP Reply No Session Drop" 
		::={ acosCgnv6L4S 8 } 

		ipipTruncated OBJECT-TYPE
		SYNTAX  CounterBasedGauge64 
		MAX-ACCESS read-only 
		STATUS current
		DESCRIPTION  "IPIP Truncated Packet" 
		::={ acosCgnv6L4S 9 } 

		ipSrcInvalidUnicast OBJECT-TYPE
		SYNTAX  CounterBasedGauge64 
		MAX-ACCESS read-only 
		STATUS current
		DESCRIPTION  "IPv4 Source Not Valid Unicast" 
		::={ acosCgnv6L4S 10 } 

		ipDstInvalidUnicast OBJECT-TYPE
		SYNTAX  CounterBasedGauge64 
		MAX-ACCESS read-only 
		STATUS current
		DESCRIPTION  "IPv4 Destination Not Valid Unicast" 
		::={ acosCgnv6L4S 11 } 

		ipv6SrcInvalidUnicast OBJECT-TYPE
		SYNTAX  CounterBasedGauge64 
		MAX-ACCESS read-only 
		STATUS current
		DESCRIPTION  "IPv6 Source Not Valid Unicast" 
		::={ acosCgnv6L4S 12 } 

		ipv6DstInvalidUnicast OBJECT-TYPE
		SYNTAX  CounterBasedGauge64 
		MAX-ACCESS read-only 
		STATUS current
		DESCRIPTION  "IPv6 Destination Not Valid Unicast" 
		::={ acosCgnv6L4S 13 } 

		rateDropResetUnkn OBJECT-TYPE
		SYNTAX  CounterBasedGauge64 
		MAX-ACCESS read-only 
		STATUS current
		DESCRIPTION  "Rate Drop reset" 
		::={ acosCgnv6L4S 14 } 

		badL3Protocol OBJECT-TYPE
		SYNTAX  CounterBasedGauge64 
		MAX-ACCESS read-only 
		STATUS current
		DESCRIPTION  "Bad Layer 3 Protocol" 
		::={ acosCgnv6L4S 15 } 

		specialIpv4NoRoute OBJECT-TYPE
		SYNTAX  CounterBasedGauge64 
		MAX-ACCESS read-only 
		STATUS current
		DESCRIPTION  "Stateless IPv4 No Forward Route" 
		::={ acosCgnv6L4S 16 } 

		specialIpv6NoRoute OBJECT-TYPE
		SYNTAX  CounterBasedGauge64 
		MAX-ACCESS read-only 
		STATUS current
		DESCRIPTION  "Stateless IPv6 No Forward Route" 
		::={ acosCgnv6L4S 17 } 

		icmpReplySent OBJECT-TYPE
		SYNTAX  CounterBasedGauge64 
		MAX-ACCESS read-only 
		STATUS current
		DESCRIPTION  "ICMP Echo Reply Sent" 
		::={ acosCgnv6L4S 18 } 

		icmpv6ReplySent OBJECT-TYPE
		SYNTAX  CounterBasedGauge64 
		MAX-ACCESS read-only 
		STATUS current
		DESCRIPTION  "ICMPv6 Echo Reply Sent" 
		::={ acosCgnv6L4S 19 } 

		outOfStateDropped OBJECT-TYPE
		SYNTAX  CounterBasedGauge64 
		MAX-ACCESS read-only 
		STATUS current
		DESCRIPTION  "L4 Out of State packets" 
		::={ acosCgnv6L4S 20 } 

		ttlExceededSent OBJECT-TYPE
		SYNTAX  CounterBasedGauge64 
		MAX-ACCESS read-only 
		STATUS current
		DESCRIPTION  "ICMP TTL Exceeded Sent" 
		::={ acosCgnv6L4S 21 } 

		crossCpuAlgGreNoMatch OBJECT-TYPE
		SYNTAX  CounterBasedGauge64 
		MAX-ACCESS read-only 
		STATUS current
		DESCRIPTION  "ALG GRE Cross CPU No Matching Session" 
		::={ acosCgnv6L4S 22 } 

		crossCpuAlgGrePreprocessErr OBJECT-TYPE
		SYNTAX  CounterBasedGauge64 
		MAX-ACCESS read-only 
		STATUS current
		DESCRIPTION  "ALG GRE Cross CPU Preprocess Error" 
		::={ acosCgnv6L4S 23 } 

		lsnFastSetup OBJECT-TYPE
		SYNTAX  CounterBasedGauge64 
		MAX-ACCESS read-only 
		STATUS current
		DESCRIPTION  "LSN Fast Setup Attempt" 
		::={ acosCgnv6L4S 24 } 

		lsnFastSetupErr OBJECT-TYPE
		SYNTAX  CounterBasedGauge64 
		MAX-ACCESS read-only 
		STATUS current
		DESCRIPTION  "LSN Fast Setup Error" 
		::={ acosCgnv6L4S 25 } 

		nat64FastSetup OBJECT-TYPE
		SYNTAX  CounterBasedGauge64 
		MAX-ACCESS read-only 
		STATUS current
		DESCRIPTION  "NAT64 Fast Setup Attempt" 
		::={ acosCgnv6L4S 26 } 

		nat64FastSetupErr OBJECT-TYPE
		SYNTAX  CounterBasedGauge64 
		MAX-ACCESS read-only 
		STATUS current
		DESCRIPTION  "NAT64 Fast Setup Error" 
		::={ acosCgnv6L4S 27 } 

		dsliteFastSetup OBJECT-TYPE
		SYNTAX  CounterBasedGauge64 
		MAX-ACCESS read-only 
		STATUS current
		DESCRIPTION  "DS-Lite Fast Setup Attempt" 
		::={ acosCgnv6L4S 28 } 

		dsliteFastSetupErr OBJECT-TYPE
		SYNTAX  CounterBasedGauge64 
		MAX-ACCESS read-only 
		STATUS current
		DESCRIPTION  "DS-Lite Fast Setup Error" 
		::={ acosCgnv6L4S 29 } 

		fastSetupDelayedErr OBJECT-TYPE
		SYNTAX  CounterBasedGauge64 
		MAX-ACCESS read-only 
		STATUS current
		DESCRIPTION  "Fast Setup Delayed Error" 
		::={ acosCgnv6L4S 30 } 

		fastSetupMtuTooSmall OBJECT-TYPE
		SYNTAX  CounterBasedGauge64 
		MAX-ACCESS read-only 
		STATUS current
		DESCRIPTION  "Fast Setup MTU Too Small" 
		::={ acosCgnv6L4S 31 } 

		fixedNat44FastSetup OBJECT-TYPE
		SYNTAX  CounterBasedGauge64 
		MAX-ACCESS read-only 
		STATUS current
		DESCRIPTION  "Fixed NAT Fast Setup Attempt" 
		::={ acosCgnv6L4S 32 } 

		fixedNat44FastSetupErr OBJECT-TYPE
		SYNTAX  CounterBasedGauge64 
		MAX-ACCESS read-only 
		STATUS current
		DESCRIPTION  "Fixed NAT Fast Setup Error" 
		::={ acosCgnv6L4S 33 } 

		fixedNat64FastSetup OBJECT-TYPE
		SYNTAX  CounterBasedGauge64 
		MAX-ACCESS read-only 
		STATUS current
		DESCRIPTION  "Fixed NAT Fast Setup Attempt" 
		::={ acosCgnv6L4S 34 } 

		fixedNat64FastSetupErr OBJECT-TYPE
		SYNTAX  CounterBasedGauge64 
		MAX-ACCESS read-only 
		STATUS current
		DESCRIPTION  "Fixed NAT Fast Setup Error" 
		::={ acosCgnv6L4S 35 } 

		fixedNatDsliteFastSetup OBJECT-TYPE
		SYNTAX  CounterBasedGauge64 
		MAX-ACCESS read-only 
		STATUS current
		DESCRIPTION  "Fixed NAT Fast Setup Attempt" 
		::={ acosCgnv6L4S 36 } 

		fixedNatDsliteFastSetupErr OBJECT-TYPE
		SYNTAX  CounterBasedGauge64 
		MAX-ACCESS read-only 
		STATUS current
		DESCRIPTION  "Fixed NAT Fast Setup Error" 
		::={ acosCgnv6L4S 37 } 

		fixedNatFastSetupDelayedErr OBJECT-TYPE
		SYNTAX  CounterBasedGauge64 
		MAX-ACCESS read-only 
		STATUS current
		DESCRIPTION  "Fixed NAT Fast Setup Delayed Error" 
		::={ acosCgnv6L4S 38 } 

		fixedNatFastSetupMtuTooSmall OBJECT-TYPE
		SYNTAX  CounterBasedGauge64 
		MAX-ACCESS read-only 
		STATUS current
		DESCRIPTION  "Fixed NAT Fast Setup MTU Too Small" 
		::={ acosCgnv6L4S 39 } 

		staticNatFastSetup OBJECT-TYPE
		SYNTAX  CounterBasedGauge64 
		MAX-ACCESS read-only 
		STATUS current
		DESCRIPTION  "Static NAT Fast Setup Attempt" 
		::={ acosCgnv6L4S 40 } 

		staticNatFastSetupErr OBJECT-TYPE
		SYNTAX  CounterBasedGauge64 
		MAX-ACCESS read-only 
		STATUS current
		DESCRIPTION  "Static NAT Fast Setup Error" 
		::={ acosCgnv6L4S 41 } 

		dstNatNeededDrop OBJECT-TYPE
		SYNTAX  CounterBasedGauge64 
		MAX-ACCESS read-only 
		STATUS current
		DESCRIPTION  "Destination NAT Needed Drop" 
		::={ acosCgnv6L4S 42 } 

		invalidNat64TranslatedAddr OBJECT-TYPE
		SYNTAX  CounterBasedGauge64 
		MAX-ACCESS read-only 
		STATUS current
		DESCRIPTION  "Invalid NAT64 Translated IPv4 Address" 
		::={ acosCgnv6L4S 43 } 

		tcpRstLoopDrop OBJECT-TYPE
		SYNTAX  CounterBasedGauge64 
		MAX-ACCESS read-only 
		STATUS current
		DESCRIPTION  "RST Loop Drop" 
		::={ acosCgnv6L4S 44 } 

		staticNatAlloc OBJECT-TYPE
		SYNTAX  CounterBasedGauge64 
		MAX-ACCESS read-only 
		STATUS current
		DESCRIPTION  "Static NAT Alloc" 
		::={ acosCgnv6L4S 45 } 

		staticNatFree OBJECT-TYPE
		SYNTAX  CounterBasedGauge64 
		MAX-ACCESS read-only 
		STATUS current
		DESCRIPTION  "Static NAT Free" 
		::={ acosCgnv6L4S 46 } 

		processL4 OBJECT-TYPE
		SYNTAX  CounterBasedGauge64 
		MAX-ACCESS read-only 
		STATUS current
		DESCRIPTION  "Process L4" 
		::={ acosCgnv6L4S 47 } 

		preprocessError OBJECT-TYPE
		SYNTAX  CounterBasedGauge64 
		MAX-ACCESS read-only 
		STATUS current
		DESCRIPTION  "Preprocess Error" 
		::={ acosCgnv6L4S 48 } 

		processSpecial OBJECT-TYPE
		SYNTAX  CounterBasedGauge64 
		MAX-ACCESS read-only 
		STATUS current
		DESCRIPTION  "Process Special" 
		::={ acosCgnv6L4S 49 } 

		processContinue OBJECT-TYPE
		SYNTAX  CounterBasedGauge64 
		MAX-ACCESS read-only 
		STATUS current
		DESCRIPTION  "Process Continue" 
		::={ acosCgnv6L4S 50 } 

		processError OBJECT-TYPE
		SYNTAX  CounterBasedGauge64 
		MAX-ACCESS read-only 
		STATUS current
		DESCRIPTION  "Process Error" 
		::={ acosCgnv6L4S 51 } 

		fwMatchNoRuleDrop OBJECT-TYPE
		SYNTAX  CounterBasedGauge64 
		MAX-ACCESS read-only 
		STATUS current
		DESCRIPTION  "Firewall Matched No CGNv6 Rule Drop" 
		::={ acosCgnv6L4S 52 } 

		ipUnknownProcess OBJECT-TYPE
		SYNTAX  CounterBasedGauge64 
		MAX-ACCESS read-only 
		STATUS current
		DESCRIPTION  "Process IP Unknown" 
		::={ acosCgnv6L4S 53 } 

		srcNatPoolNotFound OBJECT-TYPE
		SYNTAX  CounterBasedGauge64 
		MAX-ACCESS read-only 
		STATUS current
		DESCRIPTION  "Src NAT Pool Not Found" 
		::={ acosCgnv6L4S 54 } 

		dstNatPoolNotFound OBJECT-TYPE
		SYNTAX  CounterBasedGauge64 
		MAX-ACCESS read-only 
		STATUS current
		DESCRIPTION  "Dst NAT Pool Not Found" 
		::={ acosCgnv6L4S 55 } 

		l3IpSrcInvalidUnicast OBJECT-TYPE
		SYNTAX  CounterBasedGauge64 
		MAX-ACCESS read-only 
		STATUS current
		DESCRIPTION  "IPv4 L3 Source Invalid Unicast" 
		::={ acosCgnv6L4S 56 } 

		l3IpDstInvalidUnicast OBJECT-TYPE
		SYNTAX  CounterBasedGauge64 
		MAX-ACCESS read-only 
		STATUS current
		DESCRIPTION  "IPv4 L3 Destination Invalid Unicast" 
		::={ acosCgnv6L4S 57 } 

		l3Ipv6SrcInvalidUnicast OBJECT-TYPE
		SYNTAX  CounterBasedGauge64 
		MAX-ACCESS read-only 
		STATUS current
		DESCRIPTION  "IPv6 L3 Source Invalid Unicast" 
		::={ acosCgnv6L4S 58 } 

		l3Ipv6DstInvalidUnicast OBJECT-TYPE
		SYNTAX  CounterBasedGauge64 
		MAX-ACCESS read-only 
		STATUS current
		DESCRIPTION  "IPv6 L3 Destination Invalid Unicast" 
		::={ acosCgnv6L4S 59 } 

		fwZoneMismatchReroutingDrop OBJECT-TYPE
		SYNTAX  CounterBasedGauge64 
		MAX-ACCESS read-only 
		STATUS current
		DESCRIPTION  "Rerouting Zone Mismatch Drop" 
		::={ acosCgnv6L4S 60 } 

		natRangeListAclDeny OBJECT-TYPE
		SYNTAX  CounterBasedGauge64 
		MAX-ACCESS read-only 
		STATUS current
		DESCRIPTION  "Nat range-list ACL deny" 
		::={ acosCgnv6L4S 61 } 

		natRangeListAclPermit OBJECT-TYPE
		SYNTAX  CounterBasedGauge64 
		MAX-ACCESS read-only 
		STATUS current
		DESCRIPTION  "Nat range-list ACL permit" 
		::={ acosCgnv6L4S 62 } 

		fwNextActionIncorrectDrop OBJECT-TYPE
		SYNTAX  CounterBasedGauge64 
		MAX-ACCESS read-only 
		STATUS current
		DESCRIPTION  "FW Next Action Incorrect Drop" 
		::={ acosCgnv6L4S 63 } 

acosCgnv6Icmp                       OBJECT IDENTIFIER ::= { acosCgnv6 29 }
acosCgnv6IcmpS                      OBJECT IDENTIFIER ::= { acosCgnv6Icmp 1 }

		icmpUnknownType OBJECT-TYPE
		SYNTAX  CounterBasedGauge64 
		MAX-ACCESS read-only 
		STATUS current
		DESCRIPTION  "ICMP Unknown Type" 
		::={ acosCgnv6IcmpS 1 } 

		icmpNoPortInfo OBJECT-TYPE
		SYNTAX  CounterBasedGauge64 
		MAX-ACCESS read-only 
		STATUS current
		DESCRIPTION  "ICMP Port Info Not Included" 
		::={ acosCgnv6IcmpS 2 } 

		icmpNoSessionDrop OBJECT-TYPE
		SYNTAX  CounterBasedGauge64 
		MAX-ACCESS read-only 
		STATUS current
		DESCRIPTION  "ICMP No Matching Session Drop" 
		::={ acosCgnv6IcmpS 3 } 

		icmpv6UnknownType OBJECT-TYPE
		SYNTAX  CounterBasedGauge64 
		MAX-ACCESS read-only 
		STATUS current
		DESCRIPTION  "ICMPv6 Unknown Type" 
		::={ acosCgnv6IcmpS 4 } 

		icmpv6NoPortInfo OBJECT-TYPE
		SYNTAX  CounterBasedGauge64 
		MAX-ACCESS read-only 
		STATUS current
		DESCRIPTION  "ICMPv6 Port Info Not Included" 
		::={ acosCgnv6IcmpS 5 } 

		icmpv6NoSessionDrop OBJECT-TYPE
		SYNTAX  CounterBasedGauge64 
		MAX-ACCESS read-only 
		STATUS current
		DESCRIPTION  "ICMPv6 No Matching Session Drop" 
		::={ acosCgnv6IcmpS 6 } 

		icmpToIcmp OBJECT-TYPE
		SYNTAX  CounterBasedGauge64 
		MAX-ACCESS read-only 
		STATUS current
		DESCRIPTION  "ICMP to ICMP Conversion" 
		::={ acosCgnv6IcmpS 7 } 

		cgnv6IcmpIcmpToIcmpv6 OBJECT-TYPE
		SYNTAX  CounterBasedGauge64 
		MAX-ACCESS read-only 
		STATUS current
		DESCRIPTION  "ICMP to ICMPv6 Conversion" 
		::={ acosCgnv6IcmpS 8 } 

		cgnv6IcmpIcmpv6ToIcmp OBJECT-TYPE
		SYNTAX  CounterBasedGauge64 
		MAX-ACCESS read-only 
		STATUS current
		DESCRIPTION  "ICMPv6 to ICMP Conversion" 
		::={ acosCgnv6IcmpS 9 } 

		icmpv6ToIcmpv6 OBJECT-TYPE
		SYNTAX  CounterBasedGauge64 
		MAX-ACCESS read-only 
		STATUS current
		DESCRIPTION  "ICMPv6 to ICMPv6 Conversion" 
		::={ acosCgnv6IcmpS 10 } 

		icmpBadType OBJECT-TYPE
		SYNTAX  CounterBasedGauge64 
		MAX-ACCESS read-only 
		STATUS current
		DESCRIPTION  "Bad Embedded ICMP Type" 
		::={ acosCgnv6IcmpS 11 } 

		icmpv6BadType OBJECT-TYPE
		SYNTAX  CounterBasedGauge64 
		MAX-ACCESS read-only 
		STATUS current
		DESCRIPTION  "Bad Embedded ICMPv6 Type" 
		::={ acosCgnv6IcmpS 12 } 

		cgnv6Icmp64KnownDrop OBJECT-TYPE
		SYNTAX  CounterBasedGauge64 
		MAX-ACCESS read-only 
		STATUS current
		DESCRIPTION  "NAT64 Forward Known ICMPv6 Drop" 
		::={ acosCgnv6IcmpS 13 } 

		cgnv6Icmp64UnknownDrop OBJECT-TYPE
		SYNTAX  CounterBasedGauge64 
		MAX-ACCESS read-only 
		STATUS current
		DESCRIPTION  "NAT64 Forward Unknown ICMPv6 Drop" 
		::={ acosCgnv6IcmpS 14 } 

		cgnv6Icmp64MidpointHop OBJECT-TYPE
		SYNTAX  CounterBasedGauge64 
		MAX-ACCESS read-only 
		STATUS current
		DESCRIPTION  "NAT64 Forward Unknown Source Drop" 
		::={ acosCgnv6IcmpS 15 } 

		cgnv6Icmp46KnownDrop OBJECT-TYPE
		SYNTAX  CounterBasedGauge64 
		MAX-ACCESS read-only 
		STATUS current
		DESCRIPTION  "NAT64 Reverse Known ICMP Drop" 
		::={ acosCgnv6IcmpS 16 } 

		cgnv6Icmp46UnknownDrop OBJECT-TYPE
		SYNTAX  CounterBasedGauge64 
		MAX-ACCESS read-only 
		STATUS current
		DESCRIPTION  "NAT64 Reverse Known ICMPv6 Drop" 
		::={ acosCgnv6IcmpS 17 } 

		cgnv6Icmp46NoPrefixForIpv4 OBJECT-TYPE
		SYNTAX  CounterBasedGauge64 
		MAX-ACCESS read-only 
		STATUS current
		DESCRIPTION  "NAT64 Reverse No Prefix Match for IPv4" 
		::={ acosCgnv6IcmpS 18 } 

		cgnv6Icmp46BadEncapIpHeaderLen OBJECT-TYPE
		SYNTAX  CounterBasedGauge64 
		MAX-ACCESS read-only 
		STATUS current
		DESCRIPTION  "4to6 Bad Encapsulated IP Header Length" 
		::={ acosCgnv6IcmpS 19 } 

		icmpToIcmpErr OBJECT-TYPE
		SYNTAX  CounterBasedGauge64 
		MAX-ACCESS read-only 
		STATUS current
		DESCRIPTION  "ICMP to ICMP Conversion Error" 
		::={ acosCgnv6IcmpS 20 } 

		icmpToIcmpv6Err OBJECT-TYPE
		SYNTAX  CounterBasedGauge64 
		MAX-ACCESS read-only 
		STATUS current
		DESCRIPTION  "ICMP to ICMPv6 Conversion Error" 
		::={ acosCgnv6IcmpS 21 } 

		icmpv6ToIcmpErr OBJECT-TYPE
		SYNTAX  CounterBasedGauge64 
		MAX-ACCESS read-only 
		STATUS current
		DESCRIPTION  "ICMPv6 to ICMP Conversion Error" 
		::={ acosCgnv6IcmpS 22 } 

		icmpv6ToIcmpv6Err OBJECT-TYPE
		SYNTAX  CounterBasedGauge64 
		MAX-ACCESS read-only 
		STATUS current
		DESCRIPTION  "ICMPv6 to ICMPv6 Conversion Error" 
		::={ acosCgnv6IcmpS 23 } 

		encapCrossCpuNoMatch OBJECT-TYPE
		SYNTAX  CounterBasedGauge64 
		MAX-ACCESS read-only 
		STATUS current
		DESCRIPTION  "ICMP Embedded Cross CPU No Matching Session" 
		::={ acosCgnv6IcmpS 24 } 

		encapCrossCpuPreprocessErr OBJECT-TYPE
		SYNTAX  CounterBasedGauge64 
		MAX-ACCESS read-only 
		STATUS current
		DESCRIPTION  "ICMP Embedded Cross CPU Preprocess Error" 
		::={ acosCgnv6IcmpS 25 } 

		icmpToIcmpUnknownL4 OBJECT-TYPE
		SYNTAX  CounterBasedGauge64 
		MAX-ACCESS read-only 
		STATUS current
		DESCRIPTION  "ICMP Embedded Unknown L4 Protocol" 
		::={ acosCgnv6IcmpS 26 } 

		icmpToIcmpv6UnknownL4 OBJECT-TYPE
		SYNTAX  CounterBasedGauge64 
		MAX-ACCESS read-only 
		STATUS current
		DESCRIPTION  "ICMP to ICMPv6 Embedded Unknown L4 Protocol" 
		::={ acosCgnv6IcmpS 27 } 

		icmpv6ToIcmpUnknownL4 OBJECT-TYPE
		SYNTAX  CounterBasedGauge64 
		MAX-ACCESS read-only 
		STATUS current
		DESCRIPTION  "ICMPv6 to ICMP Embedded Unknown L4 Protocol" 
		::={ acosCgnv6IcmpS 28 } 

		icmpv6ToIcmpv6UnknownL4 OBJECT-TYPE
		SYNTAX  CounterBasedGauge64 
		MAX-ACCESS read-only 
		STATUS current
		DESCRIPTION  "ICMPv6 to ICMPv6 Embedded Unknown L4 Protocol" 
		::={ acosCgnv6IcmpS 29 } 

		staticNat OBJECT-TYPE
		SYNTAX  CounterBasedGauge64 
		MAX-ACCESS read-only 
		STATUS current
		DESCRIPTION  "ICMP Static NAT" 
		::={ acosCgnv6IcmpS 30 } 

		echoToPoolReply OBJECT-TYPE
		SYNTAX  CounterBasedGauge64 
		MAX-ACCESS read-only 
		STATUS current
		DESCRIPTION  "Ping to Pool Reply" 
		::={ acosCgnv6IcmpS 31 } 

		echoToPoolDrop OBJECT-TYPE
		SYNTAX  CounterBasedGauge64 
		MAX-ACCESS read-only 
		STATUS current
		DESCRIPTION  "Ping to Pool Drop" 
		::={ acosCgnv6IcmpS 32 } 

		errorToPoolDrop OBJECT-TYPE
		SYNTAX  CounterBasedGauge64 
		MAX-ACCESS read-only 
		STATUS current
		DESCRIPTION  "Error to Pool Drop" 
		::={ acosCgnv6IcmpS 33 } 

		echoToPoolReplyV6 OBJECT-TYPE
		SYNTAX  CounterBasedGauge64 
		MAX-ACCESS read-only 
		STATUS current
		DESCRIPTION  "Ping6 to Pool Reply" 
		::={ acosCgnv6IcmpS 34 } 

		echoToPoolDropV6 OBJECT-TYPE
		SYNTAX  CounterBasedGauge64 
		MAX-ACCESS read-only 
		STATUS current
		DESCRIPTION  "Ping6 to Pool Drop" 
		::={ acosCgnv6IcmpS 35 } 

		errorToPoolDropV6 OBJECT-TYPE
		SYNTAX  CounterBasedGauge64 
		MAX-ACCESS read-only 
		STATUS current
		DESCRIPTION  "Error to IPv6 Pool Drop" 
		::={ acosCgnv6IcmpS 36 } 

		errorIpMismatch OBJECT-TYPE
		SYNTAX  CounterBasedGauge64 
		MAX-ACCESS read-only 
		STATUS current
		DESCRIPTION  "ICMP IP address mismatch" 
		::={ acosCgnv6IcmpS 37 } 

acosCgnv6HttpAlg                    OBJECT IDENTIFIER ::= { acosCgnv6 30 }
acosCgnv6HttpAlgS                   OBJECT IDENTIFIER ::= { acosCgnv6HttpAlg 1 }

		requestProcessed OBJECT-TYPE
		SYNTAX  CounterBasedGauge64 
		MAX-ACCESS read-only 
		STATUS current
		DESCRIPTION  "HTTP Request Processed" 
		::={ acosCgnv6HttpAlgS 1 } 

		requestInsertMsisdnPerformed OBJECT-TYPE
		SYNTAX  CounterBasedGauge64 
		MAX-ACCESS read-only 
		STATUS current
		DESCRIPTION  "HTTP MSISDN Insertion Performed" 
		::={ acosCgnv6HttpAlgS 2 } 

		requestInsertClientIpPerformed OBJECT-TYPE
		SYNTAX  CounterBasedGauge64 
		MAX-ACCESS read-only 
		STATUS current
		DESCRIPTION  "HTTP Client IP Insertion Performed" 
		::={ acosCgnv6HttpAlgS 3 } 

		requestInsertMsisdnUnavailable OBJECT-TYPE
		SYNTAX  CounterBasedGauge64 
		MAX-ACCESS read-only 
		STATUS current
		DESCRIPTION  "Inserted MSISDN is 0000 (MSISDN Unavailable)" 
		::={ acosCgnv6HttpAlgS 4 } 

		queuedSessionTooMany OBJECT-TYPE
		SYNTAX  CounterBasedGauge64 
		MAX-ACCESS read-only 
		STATUS current
		DESCRIPTION  "Queued Session Exceed Drop" 
		::={ acosCgnv6HttpAlgS 5 } 

		radiusQuerySucceed OBJECT-TYPE
		SYNTAX  CounterBasedGauge64 
		MAX-ACCESS read-only 
		STATUS current
		DESCRIPTION  "MSISDN Query Succeed" 
		::={ acosCgnv6HttpAlgS 6 } 

		radiusQueryFailed OBJECT-TYPE
		SYNTAX  CounterBasedGauge64 
		MAX-ACCESS read-only 
		STATUS current
		DESCRIPTION  "MSISDN Query Failed" 
		::={ acosCgnv6HttpAlgS 7 } 

		radiusRequstSent OBJECT-TYPE
		SYNTAX  CounterBasedGauge64 
		MAX-ACCESS read-only 
		STATUS current
		DESCRIPTION  "Query Request Sent" 
		::={ acosCgnv6HttpAlgS 8 } 

		radiusRequstDropped OBJECT-TYPE
		SYNTAX  CounterBasedGauge64 
		MAX-ACCESS read-only 
		STATUS current
		DESCRIPTION  "Query Request Dropped" 
		::={ acosCgnv6HttpAlgS 9 } 

		radiusResponseReceived OBJECT-TYPE
		SYNTAX  CounterBasedGauge64 
		MAX-ACCESS read-only 
		STATUS current
		DESCRIPTION  "Query Response Received" 
		::={ acosCgnv6HttpAlgS 10 } 

		radiusResponseDropped OBJECT-TYPE
		SYNTAX  CounterBasedGauge64 
		MAX-ACCESS read-only 
		STATUS current
		DESCRIPTION  "Query Response Dropped" 
		::={ acosCgnv6HttpAlgS 11 } 

		outOfMemoryDropped OBJECT-TYPE
		SYNTAX  CounterBasedGauge64 
		MAX-ACCESS read-only 
		STATUS current
		DESCRIPTION  "Out-of-Memory Dropped" 
		::={ acosCgnv6HttpAlgS 12 } 

		queueLenExceedDropped OBJECT-TYPE
		SYNTAX  CounterBasedGauge64 
		MAX-ACCESS read-only 
		STATUS current
		DESCRIPTION  "Queue Length Exceed Dropped" 
		::={ acosCgnv6HttpAlgS 13 } 

		outOfOrderDropped OBJECT-TYPE
		SYNTAX  CounterBasedGauge64 
		MAX-ACCESS read-only 
		STATUS current
		DESCRIPTION  "Packet Out-of-Order Dropped" 
		::={ acosCgnv6HttpAlgS 14 } 

		buffResent OBJECT-TYPE
		SYNTAX  CounterBasedGauge64 
		MAX-ACCESS read-only 
		STATUS current
		DESCRIPTION  "Packet Resent from Queue" 
		::={ acosCgnv6HttpAlgS 15 } 

		buffSpiltFailed OBJECT-TYPE
		SYNTAX  CounterBasedGauge64 
		MAX-ACCESS read-only 
		STATUS current
		DESCRIPTION  "Buff Split Failed" 
		::={ acosCgnv6HttpAlgS 16 } 

		headerInsertionFailed OBJECT-TYPE
		SYNTAX  CounterBasedGauge64 
		MAX-ACCESS read-only 
		STATUS current
		DESCRIPTION  "Buff Insertion Failed" 
		::={ acosCgnv6HttpAlgS 17 } 

		headerRemovalFailed OBJECT-TYPE
		SYNTAX  CounterBasedGauge64 
		MAX-ACCESS read-only 
		STATUS current
		DESCRIPTION  "Buff Removal Failed" 
		::={ acosCgnv6HttpAlgS 18 } 

		noQueue OBJECT-TYPE
		SYNTAX  CounterBasedGauge64 
		MAX-ACCESS read-only 
		STATUS current
		DESCRIPTION  "No Queue" 
		::={ acosCgnv6HttpAlgS 19 } 

acosCgnv6Dns64                      OBJECT IDENTIFIER ::= { acosCgnv6 31 }
acosCgnv6Dns64S                     OBJECT IDENTIFIER ::= { acosCgnv6Dns64 1 }

		query OBJECT-TYPE
		SYNTAX  CounterBasedGauge64 
		MAX-ACCESS read-only 
		STATUS current
		DESCRIPTION  "Query" 
		::={ acosCgnv6Dns64S 1 } 

		queryBadPkt OBJECT-TYPE
		SYNTAX  CounterBasedGauge64 
		MAX-ACCESS read-only 
		STATUS current
		DESCRIPTION  "Query Bad Packet" 
		::={ acosCgnv6Dns64S 2 } 

		queryChg OBJECT-TYPE
		SYNTAX  CounterBasedGauge64 
		MAX-ACCESS read-only 
		STATUS current
		DESCRIPTION  "Query Changed" 
		::={ acosCgnv6Dns64S 3 } 

		queryParallel OBJECT-TYPE
		SYNTAX  CounterBasedGauge64 
		MAX-ACCESS read-only 
		STATUS current
		DESCRIPTION  "Query Parallel" 
		::={ acosCgnv6Dns64S 4 } 

		queryPassive OBJECT-TYPE
		SYNTAX  CounterBasedGauge64 
		MAX-ACCESS read-only 
		STATUS current
		DESCRIPTION  "Query Passive" 
		::={ acosCgnv6Dns64S 5 } 

		resp OBJECT-TYPE
		SYNTAX  CounterBasedGauge64 
		MAX-ACCESS read-only 
		STATUS current
		DESCRIPTION  "Response" 
		::={ acosCgnv6Dns64S 6 } 

		respBadPkt OBJECT-TYPE
		SYNTAX  CounterBasedGauge64 
		MAX-ACCESS read-only 
		STATUS current
		DESCRIPTION  "Response Bad Packet" 
		::={ acosCgnv6Dns64S 7 } 

		respBadQr OBJECT-TYPE
		SYNTAX  CounterBasedGauge64 
		MAX-ACCESS read-only 
		STATUS current
		DESCRIPTION  "Response Bad Query" 
		::={ acosCgnv6Dns64S 8 } 

		respChg OBJECT-TYPE
		SYNTAX  CounterBasedGauge64 
		MAX-ACCESS read-only 
		STATUS current
		DESCRIPTION  "Response Changed" 
		::={ acosCgnv6Dns64S 9 } 

		respErr OBJECT-TYPE
		SYNTAX  CounterBasedGauge64 
		MAX-ACCESS read-only 
		STATUS current
		DESCRIPTION  "Response Error" 
		::={ acosCgnv6Dns64S 10 } 

		respEmpty OBJECT-TYPE
		SYNTAX  CounterBasedGauge64 
		MAX-ACCESS read-only 
		STATUS current
		DESCRIPTION  "Response Empty" 
		::={ acosCgnv6Dns64S 11 } 

		respLocal OBJECT-TYPE
		SYNTAX  CounterBasedGauge64 
		MAX-ACCESS read-only 
		STATUS current
		DESCRIPTION  "Response Local" 
		::={ acosCgnv6Dns64S 12 } 

		adjust OBJECT-TYPE
		SYNTAX  CounterBasedGauge64 
		MAX-ACCESS read-only 
		STATUS current
		DESCRIPTION  "Translated" 
		::={ acosCgnv6Dns64S 13 } 

		cache OBJECT-TYPE
		SYNTAX  CounterBasedGauge64 
		MAX-ACCESS read-only 
		STATUS current
		DESCRIPTION  "Cache" 
		::={ acosCgnv6Dns64S 14 } 

		drop OBJECT-TYPE
		SYNTAX  CounterBasedGauge64 
		MAX-ACCESS read-only 
		STATUS current
		DESCRIPTION  "Dropped" 
		::={ acosCgnv6Dns64S 15 } 

acosCgnv6Map                        OBJECT IDENTIFIER ::= { acosCgnv6 32 }
acosCgnv6MapTranslation             OBJECT IDENTIFIER ::= { acosCgnv6Map 1 }
acosCgnv6MapTranslationDomain       OBJECT IDENTIFIER ::= { acosCgnv6MapTranslation 2 }
acosCgnv6MapTranslationDomainS      OBJECT IDENTIFIER ::= { acosCgnv6MapTranslationDomain 1 }

cgnv6MapTranslationDomainSTable OBJECT-TYPE
		SYNTAX SEQUENCE OF Cgnv6MapTranslationDomainSEntry
		MAX-ACCESS not-accessible
		STATUS current
		::={ acosCgnv6MapTranslationDomainS 1 } 


	cgnv6MapTranslationDomainSEntry OBJECT-TYPE
		SYNTAX Cgnv6MapTranslationDomainSEntry
		MAX-ACCESS not-accessible
		STATUS current
		INDEX {
			name
		}
		::={ cgnv6MapTranslationDomainSTable 1 } 


	Cgnv6MapTranslationDomainSEntry ::=
		SEQUENCE {
			name DisplayString, 
			inboundPacketReceived CounterBasedGauge64,
			inboundFragPacketReceived CounterBasedGauge64,
			inboundAddrPortValidationFailed CounterBasedGauge64,
			inboundRevLookupFailed CounterBasedGauge64,
			inboundDestUnreachable CounterBasedGauge64,
			outboundPacketReceived CounterBasedGauge64,
			outboundFragPacketReceived CounterBasedGauge64,
			outboundAddrValidationFailed CounterBasedGauge64,
			outboundRevLookupFailed CounterBasedGauge64,
			outboundDestUnreachable CounterBasedGauge64,
			packetMtuExceeded CounterBasedGauge64,
			fragIcmpSent CounterBasedGauge64,
			interfaceNotConfigured CounterBasedGauge64,
			bmrPrefixrulesConfigured CounterBasedGauge64,
			helperCount CounterBasedGauge64,
			activeDhcpv6Leases CounterBasedGauge64
		}

			name OBJECT-TYPE
			SYNTAX  DisplayString 
			MAX-ACCESS read-only 
			STATUS current
			DESCRIPTION  "MAP-T domain name" 
			::={ cgnv6MapTranslationDomainSEntry 1 } 

			inboundPacketReceived OBJECT-TYPE
			SYNTAX  CounterBasedGauge64 
			MAX-ACCESS read-only 
			STATUS current
			DESCRIPTION  "Inbound IPv4 Packets Received" 
			::={ cgnv6MapTranslationDomainSEntry 2 } 

			inboundFragPacketReceived OBJECT-TYPE
			SYNTAX  CounterBasedGauge64 
			MAX-ACCESS read-only 
			STATUS current
			DESCRIPTION  "Inbound IPv4 Fragment Packets Received" 
			::={ cgnv6MapTranslationDomainSEntry 3 } 

			inboundAddrPortValidationFailed OBJECT-TYPE
			SYNTAX  CounterBasedGauge64 
			MAX-ACCESS read-only 
			STATUS current
			DESCRIPTION  "Inbound IPv4 Destination Address Port Validation Failed" 
			::={ cgnv6MapTranslationDomainSEntry 4 } 

			inboundRevLookupFailed OBJECT-TYPE
			SYNTAX  CounterBasedGauge64 
			MAX-ACCESS read-only 
			STATUS current
			DESCRIPTION  "Inbound IPv4 Reverse Route Lookup Failed" 
			::={ cgnv6MapTranslationDomainSEntry 5 } 

			inboundDestUnreachable OBJECT-TYPE
			SYNTAX  CounterBasedGauge64 
			MAX-ACCESS read-only 
			STATUS current
			DESCRIPTION  "Inbound IPv6 Destination Address Unreachable" 
			::={ cgnv6MapTranslationDomainSEntry 6 } 

			outboundPacketReceived OBJECT-TYPE
			SYNTAX  CounterBasedGauge64 
			MAX-ACCESS read-only 
			STATUS current
			DESCRIPTION  "Outbound IPv6 Packets Received" 
			::={ cgnv6MapTranslationDomainSEntry 7 } 

			outboundFragPacketReceived OBJECT-TYPE
			SYNTAX  CounterBasedGauge64 
			MAX-ACCESS read-only 
			STATUS current
			DESCRIPTION  "Outbound IPv6 Fragment Packets Received" 
			::={ cgnv6MapTranslationDomainSEntry 8 } 

			outboundAddrValidationFailed OBJECT-TYPE
			SYNTAX  CounterBasedGauge64 
			MAX-ACCESS read-only 
			STATUS current
			DESCRIPTION  "Outbound IPv6 Source Address Validation Failed" 
			::={ cgnv6MapTranslationDomainSEntry 9 } 

			outboundRevLookupFailed OBJECT-TYPE
			SYNTAX  CounterBasedGauge64 
			MAX-ACCESS read-only 
			STATUS current
			DESCRIPTION  "Outbound IPv6 Reverse Route Lookup Failed" 
			::={ cgnv6MapTranslationDomainSEntry 10 } 

			outboundDestUnreachable OBJECT-TYPE
			SYNTAX  CounterBasedGauge64 
			MAX-ACCESS read-only 
			STATUS current
			DESCRIPTION  "Outbound IPv4 Destination Address Unreachable" 
			::={ cgnv6MapTranslationDomainSEntry 11 } 

			packetMtuExceeded OBJECT-TYPE
			SYNTAX  CounterBasedGauge64 
			MAX-ACCESS read-only 
			STATUS current
			DESCRIPTION  "Packet Exceeded MTU" 
			::={ cgnv6MapTranslationDomainSEntry 12 } 

			fragIcmpSent OBJECT-TYPE
			SYNTAX  CounterBasedGauge64 
			MAX-ACCESS read-only 
			STATUS current
			DESCRIPTION  "ICMP Packet Too Big Sent" 
			::={ cgnv6MapTranslationDomainSEntry 13 } 

			interfaceNotConfigured OBJECT-TYPE
			SYNTAX  CounterBasedGauge64 
			MAX-ACCESS read-only 
			STATUS current
			DESCRIPTION  "Interfaces not Configured Dropped" 
			::={ cgnv6MapTranslationDomainSEntry 14 } 

			bmrPrefixrulesConfigured OBJECT-TYPE
			SYNTAX  CounterBasedGauge64 
			MAX-ACCESS read-only 
			STATUS current
			DESCRIPTION  "BMR prefix rules configured" 
			::={ cgnv6MapTranslationDomainSEntry 18 } 

			helperCount OBJECT-TYPE
			SYNTAX  CounterBasedGauge64 
			MAX-ACCESS read-only 
			STATUS current
			DESCRIPTION  "Helper Count" 
			::={ cgnv6MapTranslationDomainSEntry 15 } 

			activeDhcpv6Leases OBJECT-TYPE
			SYNTAX  CounterBasedGauge64 
			MAX-ACCESS read-only 
			STATUS current
			DESCRIPTION  "Active DHCPv6 leases" 
			::={ cgnv6MapTranslationDomainSEntry 16 } 

acosCgnv6MapEncapsulation           OBJECT IDENTIFIER ::= { acosCgnv6Map 2 }
acosCgnv6MapEncapsulationDomain     OBJECT IDENTIFIER ::= { acosCgnv6MapEncapsulation 2 }
acosCgnv6MapEncapsulationDomainS    OBJECT IDENTIFIER ::= { acosCgnv6MapEncapsulationDomain 1 }

cgnv6MapEncapsulationDomainSTable OBJECT-TYPE
		SYNTAX SEQUENCE OF Cgnv6MapEncapsulationDomainSEntry
		MAX-ACCESS not-accessible
		STATUS current
		::={ acosCgnv6MapEncapsulationDomainS 1 } 


	cgnv6MapEncapsulationDomainSEntry OBJECT-TYPE
		SYNTAX Cgnv6MapEncapsulationDomainSEntry
		MAX-ACCESS not-accessible
		STATUS current
		INDEX {
			name
		}
		::={ cgnv6MapEncapsulationDomainSTable 1 } 


	Cgnv6MapEncapsulationDomainSEntry ::=
		SEQUENCE {
			name DisplayString, 
			inboundPacketReceived CounterBasedGauge64,
			inboundFragPacketReceived CounterBasedGauge64,
			inboundAddrPortValidationFailed CounterBasedGauge64,
			inboundRevLookupFailed CounterBasedGauge64,
			inboundDestUnreachable CounterBasedGauge64,
			outboundPacketReceived CounterBasedGauge64,
			outboundFragPacketReceived CounterBasedGauge64,
			outboundAddrValidationFailed CounterBasedGauge64,
			outboundRevLookupFailed CounterBasedGauge64,
			outboundDestUnreachable CounterBasedGauge64,
			packetMtuExceeded CounterBasedGauge64,
			fragIcmpSent CounterBasedGauge64,
			interfaceNotConfigured CounterBasedGauge64,
			bmrPrefixrulesConfigured CounterBasedGauge64,
			helperCount CounterBasedGauge64,
			activeDhcpv6Leases CounterBasedGauge64
		}

			name OBJECT-TYPE
			SYNTAX  DisplayString 
			MAX-ACCESS read-only 
			STATUS current
			DESCRIPTION  "MAP-E domain name" 
			::={ cgnv6MapEncapsulationDomainSEntry 1 } 

			inboundPacketReceived OBJECT-TYPE
			SYNTAX  CounterBasedGauge64 
			MAX-ACCESS read-only 
			STATUS current
			DESCRIPTION  "Inbound IPv4 Packets Received" 
			::={ cgnv6MapEncapsulationDomainSEntry 2 } 

			inboundFragPacketReceived OBJECT-TYPE
			SYNTAX  CounterBasedGauge64 
			MAX-ACCESS read-only 
			STATUS current
			DESCRIPTION  "Inbound IPv4 Fragment Packets Received" 
			::={ cgnv6MapEncapsulationDomainSEntry 3 } 

			inboundAddrPortValidationFailed OBJECT-TYPE
			SYNTAX  CounterBasedGauge64 
			MAX-ACCESS read-only 
			STATUS current
			DESCRIPTION  "Inbound IPv4 Destination Address Port Validation Failed" 
			::={ cgnv6MapEncapsulationDomainSEntry 4 } 

			inboundRevLookupFailed OBJECT-TYPE
			SYNTAX  CounterBasedGauge64 
			MAX-ACCESS read-only 
			STATUS current
			DESCRIPTION  "Inbound IPv4 Reverse Route Lookup Failed" 
			::={ cgnv6MapEncapsulationDomainSEntry 5 } 

			inboundDestUnreachable OBJECT-TYPE
			SYNTAX  CounterBasedGauge64 
			MAX-ACCESS read-only 
			STATUS current
			DESCRIPTION  "Inbound IPv6 Destination Address Unreachable" 
			::={ cgnv6MapEncapsulationDomainSEntry 6 } 

			outboundPacketReceived OBJECT-TYPE
			SYNTAX  CounterBasedGauge64 
			MAX-ACCESS read-only 
			STATUS current
			DESCRIPTION  "Outbound IPv6 Packets Received" 
			::={ cgnv6MapEncapsulationDomainSEntry 7 } 

			outboundFragPacketReceived OBJECT-TYPE
			SYNTAX  CounterBasedGauge64 
			MAX-ACCESS read-only 
			STATUS current
			DESCRIPTION  "Outbound IPv6 Fragment Packets Received" 
			::={ cgnv6MapEncapsulationDomainSEntry 8 } 

			outboundAddrValidationFailed OBJECT-TYPE
			SYNTAX  CounterBasedGauge64 
			MAX-ACCESS read-only 
			STATUS current
			DESCRIPTION  "Outbound IPv6 Source Address Validation Failed" 
			::={ cgnv6MapEncapsulationDomainSEntry 9 } 

			outboundRevLookupFailed OBJECT-TYPE
			SYNTAX  CounterBasedGauge64 
			MAX-ACCESS read-only 
			STATUS current
			DESCRIPTION  "Outbound IPv6 Reverse Route Lookup Failed" 
			::={ cgnv6MapEncapsulationDomainSEntry 10 } 

			outboundDestUnreachable OBJECT-TYPE
			SYNTAX  CounterBasedGauge64 
			MAX-ACCESS read-only 
			STATUS current
			DESCRIPTION  "Outbound IPv4 Destination Address Unreachable" 
			::={ cgnv6MapEncapsulationDomainSEntry 11 } 

			packetMtuExceeded OBJECT-TYPE
			SYNTAX  CounterBasedGauge64 
			MAX-ACCESS read-only 
			STATUS current
			DESCRIPTION  "Packet Exceeded MTU" 
			::={ cgnv6MapEncapsulationDomainSEntry 12 } 

			fragIcmpSent OBJECT-TYPE
			SYNTAX  CounterBasedGauge64 
			MAX-ACCESS read-only 
			STATUS current
			DESCRIPTION  "ICMP Packet Too Big Sent" 
			::={ cgnv6MapEncapsulationDomainSEntry 13 } 

			interfaceNotConfigured OBJECT-TYPE
			SYNTAX  CounterBasedGauge64 
			MAX-ACCESS read-only 
			STATUS current
			DESCRIPTION  "Interfaces not Configured Dropped" 
			::={ cgnv6MapEncapsulationDomainSEntry 14 } 

			bmrPrefixrulesConfigured OBJECT-TYPE
			SYNTAX  CounterBasedGauge64 
			MAX-ACCESS read-only 
			STATUS current
			DESCRIPTION  "BMR prefix rules configured" 
			::={ cgnv6MapEncapsulationDomainSEntry 18 } 

			helperCount OBJECT-TYPE
			SYNTAX  CounterBasedGauge64 
			MAX-ACCESS read-only 
			STATUS current
			DESCRIPTION  "Helper Count" 
			::={ cgnv6MapEncapsulationDomainSEntry 15 } 

			activeDhcpv6Leases OBJECT-TYPE
			SYNTAX  CounterBasedGauge64 
			MAX-ACCESS read-only 
			STATUS current
			DESCRIPTION  "Active DHCPv6 leases" 
			::={ cgnv6MapEncapsulationDomainSEntry 16 } 

acosCgnv6Dhcpv6                     OBJECT IDENTIFIER ::= { acosCgnv6 33 }
acosCgnv6Dhcpv6Global               OBJECT IDENTIFIER ::= { acosCgnv6Dhcpv6 2 }
acosCgnv6Dhcpv6GlobalS              OBJECT IDENTIFIER ::= { acosCgnv6Dhcpv6Global 1 }

		solicitRev OBJECT-TYPE
		SYNTAX  CounterBasedGauge64 
		MAX-ACCESS read-only 
		STATUS current
		DESCRIPTION  "Solicit messages received" 
		::={ acosCgnv6Dhcpv6GlobalS 1 } 

		requestRev OBJECT-TYPE
		SYNTAX  CounterBasedGauge64 
		MAX-ACCESS read-only 
		STATUS current
		DESCRIPTION  "Request messages received" 
		::={ acosCgnv6Dhcpv6GlobalS 2 } 

		renewRev OBJECT-TYPE
		SYNTAX  CounterBasedGauge64 
		MAX-ACCESS read-only 
		STATUS current
		DESCRIPTION  "Renew messages received" 
		::={ acosCgnv6Dhcpv6GlobalS 3 } 

		rebindRev OBJECT-TYPE
		SYNTAX  CounterBasedGauge64 
		MAX-ACCESS read-only 
		STATUS current
		DESCRIPTION  "Rebind messages received" 
		::={ acosCgnv6Dhcpv6GlobalS 4 } 

		releaseRev OBJECT-TYPE
		SYNTAX  CounterBasedGauge64 
		MAX-ACCESS read-only 
		STATUS current
		DESCRIPTION  "Release messages received" 
		::={ acosCgnv6Dhcpv6GlobalS 5 } 

		relayForwRcv OBJECT-TYPE
		SYNTAX  CounterBasedGauge64 
		MAX-ACCESS read-only 
		STATUS current
		DESCRIPTION  "Relay forward message received" 
		::={ acosCgnv6Dhcpv6GlobalS 6 } 

		advertiseSent OBJECT-TYPE
		SYNTAX  CounterBasedGauge64 
		MAX-ACCESS read-only 
		STATUS current
		DESCRIPTION  "Advertise messages sent" 
		::={ acosCgnv6Dhcpv6GlobalS 7 } 

		replySent OBJECT-TYPE
		SYNTAX  CounterBasedGauge64 
		MAX-ACCESS read-only 
		STATUS current
		DESCRIPTION  "Reply messages sent" 
		::={ acosCgnv6Dhcpv6GlobalS 8 } 

		relayReplySent OBJECT-TYPE
		SYNTAX  CounterBasedGauge64 
		MAX-ACCESS read-only 
		STATUS current
		DESCRIPTION  "Relay reply messages sent" 
		::={ acosCgnv6Dhcpv6GlobalS 9 } 

		informationReqRcv OBJECT-TYPE
		SYNTAX  CounterBasedGauge64 
		MAX-ACCESS read-only 
		STATUS current
		DESCRIPTION  "Information request messages received" 
		::={ acosCgnv6Dhcpv6GlobalS 10 } 

		packetsDropped OBJECT-TYPE
		SYNTAX  CounterBasedGauge64 
		MAX-ACCESS read-only 
		STATUS current
		DESCRIPTION  "Packets Dropped" 
		::={ acosCgnv6Dhcpv6GlobalS 11 } 

		pktsDroppedDuringClear OBJECT-TYPE
		SYNTAX  CounterBasedGauge64 
		MAX-ACCESS read-only 
		STATUS current
		DESCRIPTION  "Packets dropped during clear bindings process" 
		::={ acosCgnv6Dhcpv6GlobalS 12 } 

		noPrefixAvailSent OBJECT-TYPE
		SYNTAX  CounterBasedGauge64 
		MAX-ACCESS read-only 
		STATUS current
		DESCRIPTION  "NO_PREFIX_AVAILABLE messages sent" 
		::={ acosCgnv6Dhcpv6GlobalS 13 } 

		noBindingMsgsSent OBJECT-TYPE
		SYNTAX  CounterBasedGauge64 
		MAX-ACCESS read-only 
		STATUS current
		DESCRIPTION  "NO_BINDING messages sent" 
		::={ acosCgnv6Dhcpv6GlobalS 14 } 

		rcvNotSupportedMsg OBJECT-TYPE
		SYNTAX  CounterBasedGauge64 
		MAX-ACCESS read-only 
		STATUS current
		DESCRIPTION  "Packets with not supported messages sent" 
		::={ acosCgnv6Dhcpv6GlobalS 15 } 

		rcvNotSupportedOption OBJECT-TYPE
		SYNTAX  CounterBasedGauge64 
		MAX-ACCESS read-only 
		STATUS current
		DESCRIPTION  "PNot supported options received" 
		::={ acosCgnv6Dhcpv6GlobalS 16 } 

END

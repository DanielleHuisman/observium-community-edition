ACOS-EVENT-NOTIFICATION-STATS-MIB DEFINITIONS ::= BEGIN
	IMPORTS
		DisplayString, PhysAddress
		FROM SNMPv2-TC
	InetAddressType
		FROM INET-ADDRESS-MIB
	acosRootStats
		FROM A10-AX-MIB
	MODULE-IDENTITY, OBJECT-TYPE, Counter32, Integer32, Counter64, OBJECT-IDENTITY, NOTIFICATION-TYPE
		FROM SNMPv2-SMI;
		acosEventNotification MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "EventNotification OID for ACOS"
				::=  {  acosRootStats 51  }

acosEventNotificationKafka          OBJECT IDENTIFIER ::= { acosEventNotification 1 }
acosEventNotificationKafkaServer    OBJECT IDENTIFIER ::= { acosEventNotificationKafka 1 }
acosEventNotificationKafkaServerS   OBJECT IDENTIFIER ::= { acosEventNotificationKafkaServer 1 }

		prAcosHarmonyTopic OBJECT-TYPE
		SYNTAX  CounterBasedGauge64 
		MAX-ACCESS read-only 
		STATUS current
		DESCRIPTION  "L7 PR logs sent" 
		::={ acosEventNotificationKafkaServerS 1 } 

		avroDeviceStatusTopic OBJECT-TYPE
		SYNTAX  CounterBasedGauge64 
		MAX-ACCESS read-only 
		STATUS current
		DESCRIPTION  "Device Status Metrics sent" 
		::={ acosEventNotificationKafkaServerS 2 } 

		avroPartitionMetricsTopic OBJECT-TYPE
		SYNTAX  CounterBasedGauge64 
		MAX-ACCESS read-only 
		STATUS current
		DESCRIPTION  "Partition Metrics sent" 
		::={ acosEventNotificationKafkaServerS 3 } 

		avroGenericSent OBJECT-TYPE
		SYNTAX  CounterBasedGauge64 
		MAX-ACCESS read-only 
		STATUS current
		DESCRIPTION  "Generic Metrics sent" 
		::={ acosEventNotificationKafkaServerS 4 } 

		prAcosHarmonyTopicEnqueueErr OBJECT-TYPE
		SYNTAX  CounterBasedGauge64 
		MAX-ACCESS read-only 
		STATUS current
		DESCRIPTION  "L7 PR dropped,enq error on acos queues" 
		::={ acosEventNotificationKafkaServerS 5 } 

		prAcosHarmonyTopicDequeueErr OBJECT-TYPE
		SYNTAX  CounterBasedGauge64 
		MAX-ACCESS read-only 
		STATUS current
		DESCRIPTION  "L7 PR dropped,enq error analytics queues" 
		::={ acosEventNotificationKafkaServerS 6 } 

		avroGenericFailedEncoding OBJECT-TYPE
		SYNTAX  CounterBasedGauge64 
		MAX-ACCESS read-only 
		STATUS current
		DESCRIPTION  "Generic Metrics dropped,encoding error" 
		::={ acosEventNotificationKafkaServerS 7 } 

		avroGenericFailedSending OBJECT-TYPE
		SYNTAX  CounterBasedGauge64 
		MAX-ACCESS read-only 
		STATUS current
		DESCRIPTION  "Generic Metrics dropped,sending failure" 
		::={ acosEventNotificationKafkaServerS 8 } 

		avroDeviceStatusTopicEnqueueErr OBJECT-TYPE
		SYNTAX  CounterBasedGauge64 
		MAX-ACCESS read-only 
		STATUS current
		DESCRIPTION  "Device Status dropped,enq error on acos queues" 
		::={ acosEventNotificationKafkaServerS 9 } 

		avroDeviceStatusTopicDequeueErr OBJECT-TYPE
		SYNTAX  CounterBasedGauge64 
		MAX-ACCESS read-only 
		STATUS current
		DESCRIPTION  "Device Status dropped,enq error analytics queues" 
		::={ acosEventNotificationKafkaServerS 10 } 

		avroPartitionMetricsTopicEnqueueErr OBJECT-TYPE
		SYNTAX  CounterBasedGauge64 
		MAX-ACCESS read-only 
		STATUS current
		DESCRIPTION  "Part metrics dropped,enq error on acos queues" 
		::={ acosEventNotificationKafkaServerS 11 } 

		avroPartitionMetricsTopicDequeueErr OBJECT-TYPE
		SYNTAX  CounterBasedGauge64 
		MAX-ACCESS read-only 
		STATUS current
		DESCRIPTION  "Part metrics dropped,enq error analytics queues" 
		::={ acosEventNotificationKafkaServerS 12 } 

		kafkaUnknownTopicDequeueErr OBJECT-TYPE
		SYNTAX  CounterBasedGauge64 
		MAX-ACCESS read-only 
		STATUS current
		DESCRIPTION  "Unknown type dropped,enq error analytics queues" 
		::={ acosEventNotificationKafkaServerS 13 } 

		kafkaBrokerDown OBJECT-TYPE
		SYNTAX  CounterBasedGauge64 
		MAX-ACCESS read-only 
		STATUS current
		DESCRIPTION  "Messages dropped,analytics down" 
		::={ acosEventNotificationKafkaServerS 14 } 

		kafkaQueueFullErr OBJECT-TYPE
		SYNTAX  CounterBasedGauge64 
		MAX-ACCESS read-only 
		STATUS current
		DESCRIPTION  "Messages dropped,acos analytics queue full" 
		::={ acosEventNotificationKafkaServerS 15 } 

		prThrottleDrop OBJECT-TYPE
		SYNTAX  CounterBasedGauge64 
		MAX-ACCESS read-only 
		STATUS current
		DESCRIPTION  "L7 PR dropped,log throttling" 
		::={ acosEventNotificationKafkaServerS 16 } 

		prNotAllowedDrop OBJECT-TYPE
		SYNTAX  CounterBasedGauge64 
		MAX-ACCESS read-only 
		STATUS current
		DESCRIPTION  "L7 PR dropped, not allowed to be sent" 
		::={ acosEventNotificationKafkaServerS 17 } 

		prBeTtfbAnomaly OBJECT-TYPE
		SYNTAX  CounterBasedGauge64 
		MAX-ACCESS read-only 
		STATUS current
		DESCRIPTION  "L7 PR back-end ttfb is negative" 
		::={ acosEventNotificationKafkaServerS 18 } 

		prBeTtlbAnomaly OBJECT-TYPE
		SYNTAX  CounterBasedGauge64 
		MAX-ACCESS read-only 
		STATUS current
		DESCRIPTION  "L7 PR back-end ttlb is negative" 
		::={ acosEventNotificationKafkaServerS 19 } 

		prInLatencyThresholdExceed OBJECT-TYPE
		SYNTAX  CounterBasedGauge64 
		MAX-ACCESS read-only 
		STATUS current
		DESCRIPTION  "L7 PR on latency threshold exceeded" 
		::={ acosEventNotificationKafkaServerS 20 } 

		prOutLatencyThresholdExceed OBJECT-TYPE
		SYNTAX  CounterBasedGauge64 
		MAX-ACCESS read-only 
		STATUS current
		DESCRIPTION  "L7 PR out latency threshold exceeded" 
		::={ acosEventNotificationKafkaServerS 21 } 

		prOutLatencyAnomaly OBJECT-TYPE
		SYNTAX  CounterBasedGauge64 
		MAX-ACCESS read-only 
		STATUS current
		DESCRIPTION  "L7 PR out latency negative" 
		::={ acosEventNotificationKafkaServerS 22 } 

		prInLatencyAnomaly OBJECT-TYPE
		SYNTAX  CounterBasedGauge64 
		MAX-ACCESS read-only 
		STATUS current
		DESCRIPTION  "L7 PR on latency negative" 
		::={ acosEventNotificationKafkaServerS 23 } 

		kafkaTopicError OBJECT-TYPE
		SYNTAX  CounterBasedGauge64 
		MAX-ACCESS read-only 
		STATUS current
		DESCRIPTION  "Module not supported by analytics" 
		::={ acosEventNotificationKafkaServerS 24 } 

		pcEncodingFailed OBJECT-TYPE
		SYNTAX  CounterBasedGauge64 
		MAX-ACCESS read-only 
		STATUS current
		DESCRIPTION  "L4 PC logs dropped,encoding error" 
		::={ acosEventNotificationKafkaServerS 25 } 

		pcAcosHarmonyTopic OBJECT-TYPE
		SYNTAX  CounterBasedGauge64 
		MAX-ACCESS read-only 
		STATUS current
		DESCRIPTION  "L4 PC logs sent" 
		::={ acosEventNotificationKafkaServerS 26 } 

		pcAcosHarmonyTopicDequeueErr OBJECT-TYPE
		SYNTAX  CounterBasedGauge64 
		MAX-ACCESS read-only 
		STATUS current
		DESCRIPTION  "L4 PC logs dropped,enq error analytics queues" 
		::={ acosEventNotificationKafkaServerS 27 } 

		cgnPcAcosHarmonyTopic OBJECT-TYPE
		SYNTAX  CounterBasedGauge64 
		MAX-ACCESS read-only 
		STATUS current
		DESCRIPTION  "CGN PC logs sent" 
		::={ acosEventNotificationKafkaServerS 28 } 

		cgnPcAcosHarmonyTopicDequeueErr OBJECT-TYPE
		SYNTAX  CounterBasedGauge64 
		MAX-ACCESS read-only 
		STATUS current
		DESCRIPTION  "CGN PC logs dropped,enq error analytics queues" 
		::={ acosEventNotificationKafkaServerS 29 } 

		cgnPeAcosHarmonyTopic OBJECT-TYPE
		SYNTAX  CounterBasedGauge64 
		MAX-ACCESS read-only 
		STATUS current
		DESCRIPTION  "CGN PE logs sent" 
		::={ acosEventNotificationKafkaServerS 30 } 

		cgnPeAcosHarmonyTopicDequeueErr OBJECT-TYPE
		SYNTAX  CounterBasedGauge64 
		MAX-ACCESS read-only 
		STATUS current
		DESCRIPTION  "CGN PE logs dropped,enq error analytics queues" 
		::={ acosEventNotificationKafkaServerS 31 } 

		fwPcAcosHarmonyTopic OBJECT-TYPE
		SYNTAX  CounterBasedGauge64 
		MAX-ACCESS read-only 
		STATUS current
		DESCRIPTION  "FW PC logs sent" 
		::={ acosEventNotificationKafkaServerS 32 } 

		fwPcAcosHarmonyTopicDequeueErr OBJECT-TYPE
		SYNTAX  CounterBasedGauge64 
		MAX-ACCESS read-only 
		STATUS current
		DESCRIPTION  "FW PC logs dropped,enq error analytics queues" 
		::={ acosEventNotificationKafkaServerS 33 } 

		fwDenyPcAcosHarmonyTopic OBJECT-TYPE
		SYNTAX  CounterBasedGauge64 
		MAX-ACCESS read-only 
		STATUS current
		DESCRIPTION  "FW DENY PC logs sent" 
		::={ acosEventNotificationKafkaServerS 34 } 

		fwDenyPcAcosHarmonyTopicDequeueErr OBJECT-TYPE
		SYNTAX  CounterBasedGauge64 
		MAX-ACCESS read-only 
		STATUS current
		DESCRIPTION  "FW DENY PC logs dropped,enq error analytics queues" 
		::={ acosEventNotificationKafkaServerS 35 } 

		fwRstPcAcosHarmonyTopic OBJECT-TYPE
		SYNTAX  CounterBasedGauge64 
		MAX-ACCESS read-only 
		STATUS current
		DESCRIPTION  "FW RST PC logs sent" 
		::={ acosEventNotificationKafkaServerS 36 } 

		fwRstPcAcosHarmonyTopicDequeueErr OBJECT-TYPE
		SYNTAX  CounterBasedGauge64 
		MAX-ACCESS read-only 
		STATUS current
		DESCRIPTION  "FW RST PC logs dropped,enq error analytics queues" 
		::={ acosEventNotificationKafkaServerS 37 } 

		cgnSummaryErrorAcosHarmonyTopic OBJECT-TYPE
		SYNTAX  CounterBasedGauge64 
		MAX-ACCESS read-only 
		STATUS current
		DESCRIPTION  "CGN PE logs sent" 
		::={ acosEventNotificationKafkaServerS 38 } 

		cgnSummaryErrorAcosHarmonyTopicDequeueErr OBJECT-TYPE
		SYNTAX  CounterBasedGauge64 
		MAX-ACCESS read-only 
		STATUS current
		DESCRIPTION  "CGN PE logs dropped,enq error analytics queues" 
		::={ acosEventNotificationKafkaServerS 39 } 

		ruleSetApplicationMetricsTopic OBJECT-TYPE
		SYNTAX  CounterBasedGauge64 
		MAX-ACCESS read-only 
		STATUS current
		DESCRIPTION  "AppFW metrics sent" 
		::={ acosEventNotificationKafkaServerS 40 } 

		ruleSetApplicationMetricsTopicDequeueErr OBJECT-TYPE
		SYNTAX  CounterBasedGauge64 
		MAX-ACCESS read-only 
		STATUS current
		DESCRIPTION  "AppFW metrics dropped,enq error analytics queues" 
		::={ acosEventNotificationKafkaServerS 41 } 

		slbSslStatsMetricsTopic OBJECT-TYPE
		SYNTAX  CounterBasedGauge64 
		MAX-ACCESS read-only 
		STATUS current
		DESCRIPTION  "SSL metrics sent" 
		::={ acosEventNotificationKafkaServerS 42 } 

		slbSslStatsMetricsTopicDequeueErr OBJECT-TYPE
		SYNTAX  CounterBasedGauge64 
		MAX-ACCESS read-only 
		STATUS current
		DESCRIPTION  "SSL metrics dropped,enq error analytics queues" 
		::={ acosEventNotificationKafkaServerS 43 } 

		slbClientSslCountersMetricsTopic OBJECT-TYPE
		SYNTAX  CounterBasedGauge64 
		MAX-ACCESS read-only 
		STATUS current
		DESCRIPTION  "Client SSL metrics sent" 
		::={ acosEventNotificationKafkaServerS 44 } 

		slbClientSslCountersMetricsTopicDequeueErr OBJECT-TYPE
		SYNTAX  CounterBasedGauge64 
		MAX-ACCESS read-only 
		STATUS current
		DESCRIPTION  "Cilent SSL metrics dropped,enq error analytics qs" 
		::={ acosEventNotificationKafkaServerS 45 } 

		slbServerSslCountersMetricsTopic OBJECT-TYPE
		SYNTAX  CounterBasedGauge64 
		MAX-ACCESS read-only 
		STATUS current
		DESCRIPTION  "Server SSL metrics sent" 
		::={ acosEventNotificationKafkaServerS 46 } 

		slbServerSslCountersMetricsTopicDequeueErr OBJECT-TYPE
		SYNTAX  CounterBasedGauge64 
		MAX-ACCESS read-only 
		STATUS current
		DESCRIPTION  "Server SSL metrics dropped,enq error analytics qs" 
		::={ acosEventNotificationKafkaServerS 47 } 

		pcThrottleDrop OBJECT-TYPE
		SYNTAX  CounterBasedGauge64 
		MAX-ACCESS read-only 
		STATUS current
		DESCRIPTION  "L4 PC logs dropped,throttling" 
		::={ acosEventNotificationKafkaServerS 48 } 

		metricsDroppedPtMissing OBJECT-TYPE
		SYNTAX  CounterBasedGauge64 
		MAX-ACCESS read-only 
		STATUS current
		DESCRIPTION  "Metrics dropped,missing partition tenant mapping" 
		::={ acosEventNotificationKafkaServerS 49 } 

		ssliPcAcosHarmonyTopic OBJECT-TYPE
		SYNTAX  CounterBasedGauge64 
		MAX-ACCESS read-only 
		STATUS current
		DESCRIPTION  "SSLi PC topic counter from acos to harmony" 
		::={ acosEventNotificationKafkaServerS 50 } 

		ssliPcAcosHarmonyTopicDequeueErr OBJECT-TYPE
		SYNTAX  CounterBasedGauge64 
		MAX-ACCESS read-only 
		STATUS current
		DESCRIPTION  "SSLi PC topic to harmony dequeue error" 
		::={ acosEventNotificationKafkaServerS 51 } 

		ssliPeAcosHarmonyTopic OBJECT-TYPE
		SYNTAX  CounterBasedGauge64 
		MAX-ACCESS read-only 
		STATUS current
		DESCRIPTION  "SSLi PE topic counter from acos to harmony" 
		::={ acosEventNotificationKafkaServerS 52 } 

		ssliPeAcosHarmonyTopicDequeueErr OBJECT-TYPE
		SYNTAX  CounterBasedGauge64 
		MAX-ACCESS read-only 
		STATUS current
		DESCRIPTION  "SSLi PE topic to harmony dequeue error" 
		::={ acosEventNotificationKafkaServerS 53 } 

		analyticsBusRestart OBJECT-TYPE
		SYNTAX  CounterBasedGauge64 
		MAX-ACCESS read-only 
		STATUS current
		DESCRIPTION  "Analytics bus restart count" 
		::={ acosEventNotificationKafkaServerS 54 } 

		wafLearnPrTopic OBJECT-TYPE
		SYNTAX  CounterBasedGauge64 
		MAX-ACCESS read-only 
		STATUS current
		DESCRIPTION  "WAF learn topic counter" 
		::={ acosEventNotificationKafkaServerS 55 } 

		wafLearnPrTopicDequeueErr OBJECT-TYPE
		SYNTAX  CounterBasedGauge64 
		MAX-ACCESS read-only 
		STATUS current
		DESCRIPTION  "WAF learn metrics dropped,enq error analytics qs" 
		::={ acosEventNotificationKafkaServerS 56 } 

		wafEventsTopic OBJECT-TYPE
		SYNTAX  CounterBasedGauge64 
		MAX-ACCESS read-only 
		STATUS current
		DESCRIPTION  "WAF events topic counter" 
		::={ acosEventNotificationKafkaServerS 57 } 

		wafEventsTopicDequeueErr OBJECT-TYPE
		SYNTAX  CounterBasedGauge64 
		MAX-ACCESS read-only 
		STATUS current
		DESCRIPTION  "WAF events metrics dropped,enq error analytics qs" 
		::={ acosEventNotificationKafkaServerS 58 } 

		visibilityTopnHarmonyTopic OBJECT-TYPE
		SYNTAX  CounterBasedGauge64 
		MAX-ACCESS read-only 
		STATUS current
		DESCRIPTION  "Visibility TopN sent" 
		::={ acosEventNotificationKafkaServerS 59 } 

		visibilityTopnHarmonyTopicDequeueErr OBJECT-TYPE
		SYNTAX  CounterBasedGauge64 
		MAX-ACCESS read-only 
		STATUS current
		DESCRIPTION  "Visibility TopN metrics dropped,enq error analytics qs" 
		::={ acosEventNotificationKafkaServerS 60 } 

		hcLogsSentToMaster OBJECT-TYPE
		SYNTAX  CounterBasedGauge64 
		MAX-ACCESS read-only 
		STATUS current
		DESCRIPTION  "HC logs sent to master" 
		::={ acosEventNotificationKafkaServerS 61 } 

		hcLogsReceivedFromBlade OBJECT-TYPE
		SYNTAX  CounterBasedGauge64 
		MAX-ACCESS read-only 
		STATUS current
		DESCRIPTION  "HC logs received from blade" 
		::={ acosEventNotificationKafkaServerS 62 } 

		hcOperSentToMaster OBJECT-TYPE
		SYNTAX  CounterBasedGauge64 
		MAX-ACCESS read-only 
		STATUS current
		DESCRIPTION  "HC oper to master" 
		::={ acosEventNotificationKafkaServerS 63 } 

		hcOperReceivedFromBlade OBJECT-TYPE
		SYNTAX  CounterBasedGauge64 
		MAX-ACCESS read-only 
		STATUS current
		DESCRIPTION  "HC oper received from blade" 
		::={ acosEventNotificationKafkaServerS 64 } 

		hcCountersSentToMaster OBJECT-TYPE
		SYNTAX  CounterBasedGauge64 
		MAX-ACCESS read-only 
		STATUS current
		DESCRIPTION  "HC counters sent to master" 
		::={ acosEventNotificationKafkaServerS 65 } 

		hcCountersReceivedFromBlade OBJECT-TYPE
		SYNTAX  CounterBasedGauge64 
		MAX-ACCESS read-only 
		STATUS current
		DESCRIPTION  "HC counters received from blade" 
		::={ acosEventNotificationKafkaServerS 66 } 

		hcCountersDroppedFromBlade OBJECT-TYPE
		SYNTAX  CounterBasedGauge64 
		MAX-ACCESS read-only 
		STATUS current
		DESCRIPTION  "HC counters dropped from blade (uuid or size mismatch)" 
		::={ acosEventNotificationKafkaServerS 67 } 

		peAcosHarmonyTopic OBJECT-TYPE
		SYNTAX  CounterBasedGauge64 
		MAX-ACCESS read-only 
		STATUS current
		DESCRIPTION  "L7 PE logs sent" 
		::={ acosEventNotificationKafkaServerS 68 } 

		peAcosHarmonyTopicEnqueueErr OBJECT-TYPE
		SYNTAX  CounterBasedGauge64 
		MAX-ACCESS read-only 
		STATUS current
		DESCRIPTION  "L7 PE dropped,enq error on acos queues" 
		::={ acosEventNotificationKafkaServerS 69 } 

		peAcosHarmonyTopicDequeueErr OBJECT-TYPE
		SYNTAX  CounterBasedGauge64 
		MAX-ACCESS read-only 
		STATUS current
		DESCRIPTION  "L7 PE dropped,enq error analytics queues" 
		::={ acosEventNotificationKafkaServerS 70 } 

		vpnIpsecSaMetricsTopic OBJECT-TYPE
		SYNTAX  CounterBasedGauge64 
		MAX-ACCESS read-only 
		STATUS current
		DESCRIPTION  "IPSec SA metrics sent" 
		::={ acosEventNotificationKafkaServerS 71 } 

		vpnIpsecSaMetricsTopicDequeueErr OBJECT-TYPE
		SYNTAX  CounterBasedGauge64 
		MAX-ACCESS read-only 
		STATUS current
		DESCRIPTION  "IPSec SA metrics dropped,enq error analytics qs" 
		::={ acosEventNotificationKafkaServerS 72 } 

		vpnIkeGatewayMetricsTopic OBJECT-TYPE
		SYNTAX  CounterBasedGauge64 
		MAX-ACCESS read-only 
		STATUS current
		DESCRIPTION  "IKE gateway metrics sent" 
		::={ acosEventNotificationKafkaServerS 73 } 

		vpnIkeGatewayMetricsTopicDequeueErr OBJECT-TYPE
		SYNTAX  CounterBasedGauge64 
		MAX-ACCESS read-only 
		STATUS current
		DESCRIPTION  "IKE gateway metrics dropped,enq error analytics qs" 
		::={ acosEventNotificationKafkaServerS 74 } 

		vpnStatsMetricsTopic OBJECT-TYPE
		SYNTAX  CounterBasedGauge64 
		MAX-ACCESS read-only 
		STATUS current
		DESCRIPTION  "VPN STATS metrics sent" 
		::={ acosEventNotificationKafkaServerS 75 } 

		vpnStatsMetricsTopicDequeueErr OBJECT-TYPE
		SYNTAX  CounterBasedGauge64 
		MAX-ACCESS read-only 
		STATUS current
		DESCRIPTION  "VPN STATS metrics dropped,enq error analytics qs" 
		::={ acosEventNotificationKafkaServerS 76 } 

		cgnPortUsageHstgrmAcosHarmonyTopic OBJECT-TYPE
		SYNTAX  CounterBasedGauge64 
		MAX-ACCESS read-only 
		STATUS current
		DESCRIPTION  "CGN Port Usage Histogram HC Export" 
		::={ acosEventNotificationKafkaServerS 77 } 

		cgnPortUsageHstgrmAcosHarmonyTopicDequeueErr OBJECT-TYPE
		SYNTAX  CounterBasedGauge64 
		MAX-ACCESS read-only 
		STATUS current
		DESCRIPTION  "CGN Port Usage Histogram HC Export Failed" 
		::={ acosEventNotificationKafkaServerS 78 } 

		avroSystemEnvTopic OBJECT-TYPE
		SYNTAX  CounterBasedGauge64 
		MAX-ACCESS read-only 
		STATUS current
		DESCRIPTION  "System environment sent" 
		::={ acosEventNotificationKafkaServerS 79 } 

		avroSystemEnvDequeueErr OBJECT-TYPE
		SYNTAX  CounterBasedGauge64 
		MAX-ACCESS read-only 
		STATUS current
		DESCRIPTION  "System Environmet dropped,enq error analytics queues" 
		::={ acosEventNotificationKafkaServerS 80 } 

		certPinningListTopic OBJECT-TYPE
		SYNTAX  CounterBasedGauge64 
		MAX-ACCESS read-only 
		STATUS current
		DESCRIPTION  "Cert-pinning candidate list sent" 
		::={ acosEventNotificationKafkaServerS 81 } 

		certPinningListTopicDequeueErr OBJECT-TYPE
		SYNTAX  CounterBasedGauge64 
		MAX-ACCESS read-only 
		STATUS current
		DESCRIPTION  "Cert-pinning candidate list dropped,enq error analytics queues" 
		::={ acosEventNotificationKafkaServerS 82 } 

END

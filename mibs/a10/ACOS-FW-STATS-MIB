ACOS-FW-STATS-MIB DEFINITIONS ::= BEGIN
	IMPORTS
		DisplayString, PhysAddress
		FROM SNMPv2-TC
	InetAddressType
		FROM INET-ADDRESS-MIB
	acosRootStats
		FROM A10-AX-MIB
	MODULE-IDENTITY, OBJECT-TYPE, Counter32, Integer32, Counter64, OBJECT-IDENTITY, NOTIFICATION-TYPE
		FROM SNMPv2-SMI;
		acosFw MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "Fw OID for ACOS"
				::=  {  acosRootStats 139  }

acosFwApp                           OBJECT IDENTIFIER ::= { acosFw 23 }
acosFwAppS                          OBJECT IDENTIFIER ::= { acosFwApp 1 }

		dummy OBJECT-TYPE
		SYNTAX  CounterBasedGauge64 
		MAX-ACCESS read-only 
		STATUS current
		DESCRIPTION  "Entry for a10countergen" 
		::={ acosFwAppS 1 } 

acosFwServer                        OBJECT IDENTIFIER ::= { acosFw 3 }
acosFwServerS                       OBJECT IDENTIFIER ::= { acosFwServer 1 }

fwServerSTable OBJECT-TYPE
		SYNTAX SEQUENCE OF FwServerSEntry
		MAX-ACCESS not-accessible
		STATUS current
		::={ acosFwServerS 1 } 


	fwServerSEntry OBJECT-TYPE
		SYNTAX FwServerSEntry
		MAX-ACCESS not-accessible
		STATUS current
		INDEX {
			fwName
		}
		::={ fwServerSTable 1 } 


	FwServerSEntry ::=
		SEQUENCE {
			fwName DisplayString, 
			fwServerCurrConn CounterBasedGauge64,
			totalConn CounterBasedGauge64,
			fwdPkt CounterBasedGauge64,
			revPkt CounterBasedGauge64,
			peakConn CounterBasedGauge64
		}

			fwName OBJECT-TYPE
			SYNTAX  DisplayString 
			MAX-ACCESS read-only 
			STATUS current
			DESCRIPTION  "Server Name" 
			::={ fwServerSEntry 1 } 

			fwServerCurrConn OBJECT-TYPE
			SYNTAX  CounterBasedGauge64 
			MAX-ACCESS read-only 
			STATUS current
			DESCRIPTION  "Current connections" 
			::={ fwServerSEntry 2 } 

			totalConn OBJECT-TYPE
			SYNTAX  CounterBasedGauge64 
			MAX-ACCESS read-only 
			STATUS current
			DESCRIPTION  "Total connections" 
			::={ fwServerSEntry 3 } 

			fwdPkt OBJECT-TYPE
			SYNTAX  CounterBasedGauge64 
			MAX-ACCESS read-only 
			STATUS current
			DESCRIPTION  "Forward packets" 
			::={ fwServerSEntry 4 } 

			revPkt OBJECT-TYPE
			SYNTAX  CounterBasedGauge64 
			MAX-ACCESS read-only 
			STATUS current
			DESCRIPTION  "Reverse Packets" 
			::={ fwServerSEntry 5 } 

			peakConn OBJECT-TYPE
			SYNTAX  CounterBasedGauge64 
			MAX-ACCESS read-only 
			STATUS current
			DESCRIPTION  "Peak connections" 
			::={ fwServerSEntry 6 } 

acosFwServiceGroup                  OBJECT IDENTIFIER ::= { acosFw 4 }
acosFwServiceGroupS                 OBJECT IDENTIFIER ::= { acosFwServiceGroup 1 }

fwServiceGroupSTable OBJECT-TYPE
		SYNTAX SEQUENCE OF FwServiceGroupSEntry
		MAX-ACCESS not-accessible
		STATUS current
		::={ acosFwServiceGroupS 1 } 


	fwServiceGroupSEntry OBJECT-TYPE
		SYNTAX FwServiceGroupSEntry
		MAX-ACCESS not-accessible
		STATUS current
		INDEX {
			fwServiceGroupName
		}
		::={ fwServiceGroupSTable 1 } 


	FwServiceGroupSEntry ::=
		SEQUENCE {
			fwServiceGroupName DisplayString, 
			fwServerSelectionFailDrop CounterBasedGauge64,
			fwServerSelectionFailReset CounterBasedGauge64,
			fwServicePeakConn CounterBasedGauge64
		}

			fwServiceGroupName OBJECT-TYPE
			SYNTAX  DisplayString 
			MAX-ACCESS read-only 
			STATUS current
			DESCRIPTION  "FW Service Name" 
			::={ fwServiceGroupSEntry 1 } 

			fwServerSelectionFailDrop OBJECT-TYPE
			SYNTAX  CounterBasedGauge64 
			MAX-ACCESS read-only 
			STATUS current
			DESCRIPTION  "Service selection fail drop" 
			::={ fwServiceGroupSEntry 2 } 

			fwServerSelectionFailReset OBJECT-TYPE
			SYNTAX  CounterBasedGauge64 
			MAX-ACCESS read-only 
			STATUS current
			DESCRIPTION  "Service selection fail reset" 
			::={ fwServiceGroupSEntry 3 } 

			fwServicePeakConn OBJECT-TYPE
			SYNTAX  CounterBasedGauge64 
			MAX-ACCESS read-only 
			STATUS current
			DESCRIPTION  "Service peak connection" 
			::={ fwServiceGroupSEntry 4 } 

acosFwLogging                       OBJECT IDENTIFIER ::= { acosFw 6 }
acosFwLoggingS                      OBJECT IDENTIFIER ::= { acosFwLogging 1 }

		logMessageSent OBJECT-TYPE
		SYNTAX  CounterBasedGauge64 
		MAX-ACCESS read-only 
		STATUS current
		DESCRIPTION  "Log Packet Sent" 
		::={ acosFwLoggingS 1 } 

		logTypeReset OBJECT-TYPE
		SYNTAX  CounterBasedGauge64 
		MAX-ACCESS read-only 
		STATUS current
		DESCRIPTION  "Log Event Type Reset" 
		::={ acosFwLoggingS 2 } 

		logTypeDeny OBJECT-TYPE
		SYNTAX  CounterBasedGauge64 
		MAX-ACCESS read-only 
		STATUS current
		DESCRIPTION  "Log Event Type Deny" 
		::={ acosFwLoggingS 3 } 

		logTypeSessionClosed OBJECT-TYPE
		SYNTAX  CounterBasedGauge64 
		MAX-ACCESS read-only 
		STATUS current
		DESCRIPTION  "Log Event Type Session Close" 
		::={ acosFwLoggingS 4 } 

		logTypeSessionOpened OBJECT-TYPE
		SYNTAX  CounterBasedGauge64 
		MAX-ACCESS read-only 
		STATUS current
		DESCRIPTION  "Log Event Type Session Open" 
		::={ acosFwLoggingS 5 } 

		ruleNotLogged OBJECT-TYPE
		SYNTAX  CounterBasedGauge64 
		MAX-ACCESS read-only 
		STATUS current
		DESCRIPTION  "Firewall Rule Not Logged" 
		::={ acosFwLoggingS 6 } 

		logDropped OBJECT-TYPE
		SYNTAX  CounterBasedGauge64 
		MAX-ACCESS read-only 
		STATUS current
		DESCRIPTION  "Log Packets Dropped" 
		::={ acosFwLoggingS 7 } 

		tcpSessionCreated OBJECT-TYPE
		SYNTAX  CounterBasedGauge64 
		MAX-ACCESS read-only 
		STATUS current
		DESCRIPTION  "TCP Session Created" 
		::={ acosFwLoggingS 8 } 

		tcpSessionDeleted OBJECT-TYPE
		SYNTAX  CounterBasedGauge64 
		MAX-ACCESS read-only 
		STATUS current
		DESCRIPTION  "TCP Session Deleted" 
		::={ acosFwLoggingS 9 } 

		udpSessionCreated OBJECT-TYPE
		SYNTAX  CounterBasedGauge64 
		MAX-ACCESS read-only 
		STATUS current
		DESCRIPTION  "UDP Session Created" 
		::={ acosFwLoggingS 10 } 

		udpSessionDeleted OBJECT-TYPE
		SYNTAX  CounterBasedGauge64 
		MAX-ACCESS read-only 
		STATUS current
		DESCRIPTION  "UDP Session Deleted" 
		::={ acosFwLoggingS 11 } 

		icmpSessionDeleted OBJECT-TYPE
		SYNTAX  CounterBasedGauge64 
		MAX-ACCESS read-only 
		STATUS current
		DESCRIPTION  "ICMP Session Deleted" 
		::={ acosFwLoggingS 12 } 

		icmpSessionCreated OBJECT-TYPE
		SYNTAX  CounterBasedGauge64 
		MAX-ACCESS read-only 
		STATUS current
		DESCRIPTION  "ICMP Session Created" 
		::={ acosFwLoggingS 13 } 

		icmpv6SessionDeleted OBJECT-TYPE
		SYNTAX  CounterBasedGauge64 
		MAX-ACCESS read-only 
		STATUS current
		DESCRIPTION  "ICMPV6 Session Deleted" 
		::={ acosFwLoggingS 14 } 

		icmpv6SessionCreated OBJECT-TYPE
		SYNTAX  CounterBasedGauge64 
		MAX-ACCESS read-only 
		STATUS current
		DESCRIPTION  "ICMPV6 Session Created" 
		::={ acosFwLoggingS 15 } 

		otherSessionDeleted OBJECT-TYPE
		SYNTAX  CounterBasedGauge64 
		MAX-ACCESS read-only 
		STATUS current
		DESCRIPTION  "Other Session Deleted" 
		::={ acosFwLoggingS 16 } 

		otherSessionCreated OBJECT-TYPE
		SYNTAX  CounterBasedGauge64 
		MAX-ACCESS read-only 
		STATUS current
		DESCRIPTION  "Other Session Created" 
		::={ acosFwLoggingS 17 } 

		httpRequestLogged OBJECT-TYPE
		SYNTAX  CounterBasedGauge64 
		MAX-ACCESS read-only 
		STATUS current
		DESCRIPTION  "HTTP Request Logged" 
		::={ acosFwLoggingS 18 } 

		httpLoggingInvalidFormat OBJECT-TYPE
		SYNTAX  CounterBasedGauge64 
		MAX-ACCESS read-only 
		STATUS current
		DESCRIPTION  "HTTP Logging Invalid Format Error" 
		::={ acosFwLoggingS 19 } 

		dcmsgPermit OBJECT-TYPE
		SYNTAX  CounterBasedGauge64 
		MAX-ACCESS read-only 
		STATUS current
		DESCRIPTION  "Dcmsg Permit" 
		::={ acosFwLoggingS 20 } 

		algOverridePermit OBJECT-TYPE
		SYNTAX  CounterBasedGauge64 
		MAX-ACCESS read-only 
		STATUS current
		DESCRIPTION  "Alg Override Permit" 
		::={ acosFwLoggingS 21 } 

		templateError OBJECT-TYPE
		SYNTAX  CounterBasedGauge64 
		MAX-ACCESS read-only 
		STATUS current
		DESCRIPTION  "Template Error" 
		::={ acosFwLoggingS 22 } 

		ipv4FragApplied OBJECT-TYPE
		SYNTAX  CounterBasedGauge64 
		MAX-ACCESS read-only 
		STATUS current
		DESCRIPTION  "IPv4 Fragmentation Applied" 
		::={ acosFwLoggingS 23 } 

		ipv4FragFailed OBJECT-TYPE
		SYNTAX  CounterBasedGauge64 
		MAX-ACCESS read-only 
		STATUS current
		DESCRIPTION  "IPv4 Fragmentation Failed" 
		::={ acosFwLoggingS 24 } 

		ipv6FragApplied OBJECT-TYPE
		SYNTAX  CounterBasedGauge64 
		MAX-ACCESS read-only 
		STATUS current
		DESCRIPTION  "IPv6 Fragmentation Applied" 
		::={ acosFwLoggingS 25 } 

		ipv6FragFailed OBJECT-TYPE
		SYNTAX  CounterBasedGauge64 
		MAX-ACCESS read-only 
		STATUS current
		DESCRIPTION  "IPv6 Fragmentation Failed" 
		::={ acosFwLoggingS 26 } 

		outOfBuffers OBJECT-TYPE
		SYNTAX  CounterBasedGauge64 
		MAX-ACCESS read-only 
		STATUS current
		DESCRIPTION  "Out of Buffers" 
		::={ acosFwLoggingS 27 } 

		addMsgFailed OBJECT-TYPE
		SYNTAX  CounterBasedGauge64 
		MAX-ACCESS read-only 
		STATUS current
		DESCRIPTION  "Add Message to Buffer Failed" 
		::={ acosFwLoggingS 28 } 

		tcpLoggingConnEstablished OBJECT-TYPE
		SYNTAX  CounterBasedGauge64 
		MAX-ACCESS read-only 
		STATUS current
		DESCRIPTION  "TCP Logging Conn Established" 
		::={ acosFwLoggingS 29 } 

		tcpLoggingConnCreateFailed OBJECT-TYPE
		SYNTAX  CounterBasedGauge64 
		MAX-ACCESS read-only 
		STATUS current
		DESCRIPTION  "TCP Logging Conn Create Failed" 
		::={ acosFwLoggingS 30 } 

		tcpLoggingConnDropped OBJECT-TYPE
		SYNTAX  CounterBasedGauge64 
		MAX-ACCESS read-only 
		STATUS current
		DESCRIPTION  "TCP Logging Conn Dropped" 
		::={ acosFwLoggingS 31 } 

		logMessageTooLong OBJECT-TYPE
		SYNTAX  CounterBasedGauge64 
		MAX-ACCESS read-only 
		STATUS current
		DESCRIPTION  "Log message too long" 
		::={ acosFwLoggingS 32 } 

		httpOutOfOrderDropped OBJECT-TYPE
		SYNTAX  CounterBasedGauge64 
		MAX-ACCESS read-only 
		STATUS current
		DESCRIPTION  "HTTP out-of-order dropped" 
		::={ acosFwLoggingS 33 } 

		httpAllocFailed OBJECT-TYPE
		SYNTAX  CounterBasedGauge64 
		MAX-ACCESS read-only 
		STATUS current
		DESCRIPTION  "HTTP Request Info Allocation Failed" 
		::={ acosFwLoggingS 34 } 

		sctpSessionCreated OBJECT-TYPE
		SYNTAX  CounterBasedGauge64 
		MAX-ACCESS read-only 
		STATUS current
		DESCRIPTION  "SCTP Session Created" 
		::={ acosFwLoggingS 35 } 

		sctpSessionDeleted OBJECT-TYPE
		SYNTAX  CounterBasedGauge64 
		MAX-ACCESS read-only 
		STATUS current
		DESCRIPTION  "SCTP Session Deleted" 
		::={ acosFwLoggingS 36 } 

		logTypeSctpInnerProtoFilter OBJECT-TYPE
		SYNTAX  CounterBasedGauge64 
		MAX-ACCESS read-only 
		STATUS current
		DESCRIPTION  "Log Event Type SCTP Inner Proto Filter" 
		::={ acosFwLoggingS 37 } 

		tcpLoggingPortAllocated OBJECT-TYPE
		SYNTAX  CounterBasedGauge64 
		MAX-ACCESS read-only 
		STATUS current
		DESCRIPTION  "TCP Logging Port Allocated" 
		::={ acosFwLoggingS 40 } 

		tcpLoggingPortFreed OBJECT-TYPE
		SYNTAX  CounterBasedGauge64 
		MAX-ACCESS read-only 
		STATUS current
		DESCRIPTION  "TCP Logging Port Freed" 
		::={ acosFwLoggingS 41 } 

		tcpLoggingPortAllocationFailed OBJECT-TYPE
		SYNTAX  CounterBasedGauge64 
		MAX-ACCESS read-only 
		STATUS current
		DESCRIPTION  "TCP Logging Port Allocation Failed" 
		::={ acosFwLoggingS 42 } 

		iddosBlackholeEntryCreate OBJECT-TYPE
		SYNTAX  CounterBasedGauge64 
		MAX-ACCESS read-only 
		STATUS current
		DESCRIPTION  "iDDoS IP Entry Created" 
		::={ acosFwLoggingS 43 } 

		iddosBlackholeEntryDelete OBJECT-TYPE
		SYNTAX  CounterBasedGauge64 
		MAX-ACCESS read-only 
		STATUS current
		DESCRIPTION  "iDDoS IP Entry Deleted" 
		::={ acosFwLoggingS 44 } 

		sessionLimitExceeded OBJECT-TYPE
		SYNTAX  CounterBasedGauge64 
		MAX-ACCESS read-only 
		STATUS current
		DESCRIPTION  "Session Limit Exceeded" 
		::={ acosFwLoggingS 45 } 

acosFwLoggingGtp                    OBJECT IDENTIFIER ::= { acosFwLogging 2 }
acosFwLoggingGtpS                   OBJECT IDENTIFIER ::= { acosFwLoggingGtp 1 }

		logTypeGtpInvalidTeid OBJECT-TYPE
		SYNTAX  CounterBasedGauge64 
		MAX-ACCESS read-only 
		STATUS current
		DESCRIPTION  "Log Event Type GTP Invalid TEID" 
		::={ acosFwLoggingGtpS 1 } 

		logGtpTypeReservedIePresent OBJECT-TYPE
		SYNTAX  CounterBasedGauge64 
		MAX-ACCESS read-only 
		STATUS current
		DESCRIPTION  "Log Event Type GTP Reserved IE Present" 
		::={ acosFwLoggingGtpS 2 } 

		logTypeGtpMandatoryIeMissing OBJECT-TYPE
		SYNTAX  CounterBasedGauge64 
		MAX-ACCESS read-only 
		STATUS current
		DESCRIPTION  "Log Event Type GTP Mandatory IE Missing" 
		::={ acosFwLoggingGtpS 3 } 

		logTypeGtpMandatoryIeInsideGroupedIeMissing OBJECT-TYPE
		SYNTAX  CounterBasedGauge64 
		MAX-ACCESS read-only 
		STATUS current
		DESCRIPTION  "Log Event Type GTP Mandatory IE Missing Inside Grouped IE" 
		::={ acosFwLoggingGtpS 4 } 

		logTypeGtpMsisdnFiltering OBJECT-TYPE
		SYNTAX  CounterBasedGauge64 
		MAX-ACCESS read-only 
		STATUS current
		DESCRIPTION  "Log Event Type GTP MSISDN Filtering" 
		::={ acosFwLoggingGtpS 5 } 

		logTypeGtpOutOfOrderIe OBJECT-TYPE
		SYNTAX  CounterBasedGauge64 
		MAX-ACCESS read-only 
		STATUS current
		DESCRIPTION  "Log Event Type GTP Out of Order IE V1" 
		::={ acosFwLoggingGtpS 6 } 

		logTypeGtpOutOfStateIe OBJECT-TYPE
		SYNTAX  CounterBasedGauge64 
		MAX-ACCESS read-only 
		STATUS current
		DESCRIPTION  "Log Event Type GTP Out of State IE" 
		::={ acosFwLoggingGtpS 7 } 

		logTypeEnduserIpSpoofed OBJECT-TYPE
		SYNTAX  CounterBasedGauge64 
		MAX-ACCESS read-only 
		STATUS current
		DESCRIPTION  "Log Event Type GTP Enduser IP Spoofed" 
		::={ acosFwLoggingGtpS 8 } 

		logTypeCrosslayerCorrelation OBJECT-TYPE
		SYNTAX  CounterBasedGauge64 
		MAX-ACCESS read-only 
		STATUS current
		DESCRIPTION  "Log Event GTP Crosslayer Correlation" 
		::={ acosFwLoggingGtpS 9 } 

		logTypeMessageNotSupported OBJECT-TYPE
		SYNTAX  CounterBasedGauge64 
		MAX-ACCESS read-only 
		STATUS current
		DESCRIPTION  "Log Event GTP Reserved Message Found" 
		::={ acosFwLoggingGtpS 10 } 

		logTypeOutOfState OBJECT-TYPE
		SYNTAX  CounterBasedGauge64 
		MAX-ACCESS read-only 
		STATUS current
		DESCRIPTION  "Log Event GTP Out of State Message" 
		::={ acosFwLoggingGtpS 11 } 

		logTypeMaxMsgLength OBJECT-TYPE
		SYNTAX  CounterBasedGauge64 
		MAX-ACCESS read-only 
		STATUS current
		DESCRIPTION  "Log Event GTP Message Length Exceeded Max" 
		::={ acosFwLoggingGtpS 12 } 

		logTypeGtpMessageFiltering OBJECT-TYPE
		SYNTAX  CounterBasedGauge64 
		MAX-ACCESS read-only 
		STATUS current
		DESCRIPTION  "Log Event Type GTP Message Filtering" 
		::={ acosFwLoggingGtpS 13 } 

		logTypeGtpApnFiltering OBJECT-TYPE
		SYNTAX  CounterBasedGauge64 
		MAX-ACCESS read-only 
		STATUS current
		DESCRIPTION  "Log Event Type GTP Apn Filtering" 
		::={ acosFwLoggingGtpS 14 } 

		logTypeGtpRatTypeFiltering OBJECT-TYPE
		SYNTAX  CounterBasedGauge64 
		MAX-ACCESS read-only 
		STATUS current
		DESCRIPTION  "Log Event GTP RAT Type Filtering" 
		::={ acosFwLoggingGtpS 15 } 

		logTypeCountryCodeMismatch OBJECT-TYPE
		SYNTAX  CounterBasedGauge64 
		MAX-ACCESS read-only 
		STATUS current
		DESCRIPTION  "Log Event GTP Country Code Mismatch" 
		::={ acosFwLoggingGtpS 16 } 

		logTypeGtpInGtpFiltering OBJECT-TYPE
		SYNTAX  CounterBasedGauge64 
		MAX-ACCESS read-only 
		STATUS current
		DESCRIPTION  "Log Event GTP in GTP Filtering" 
		::={ acosFwLoggingGtpS 17 } 

		logTypeGtpNodeRestart OBJECT-TYPE
		SYNTAX  CounterBasedGauge64 
		MAX-ACCESS read-only 
		STATUS current
		DESCRIPTION  "Log Event GTP SGW/PGW restarted" 
		::={ acosFwLoggingGtpS 18 } 

		logTypeGtpSeqNumMismatch OBJECT-TYPE
		SYNTAX  CounterBasedGauge64 
		MAX-ACCESS read-only 
		STATUS current
		DESCRIPTION  "Log Event GTP Response Sequence number Mismatch" 
		::={ acosFwLoggingGtpS 19 } 

		logTypeGtpRateLimitPeriodic OBJECT-TYPE
		SYNTAX  CounterBasedGauge64 
		MAX-ACCESS read-only 
		STATUS current
		DESCRIPTION  "Log Event GTP Rate Limit Periodic" 
		::={ acosFwLoggingGtpS 20 } 

		logTypeGtpRateLimitPeriodic OBJECT-TYPE
		SYNTAX  CounterBasedGauge64 
		MAX-ACCESS read-only 
		STATUS current
		DESCRIPTION  "Log Event GTP Invalid message length across layers" 
		::={ acosFwLoggingGtpS 21 } 

		logTypeGtpRateLimitPeriodic OBJECT-TYPE
		SYNTAX  CounterBasedGauge64 
		MAX-ACCESS read-only 
		STATUS current
		DESCRIPTION  "Log Event GTP Protocol flag in header" 
		::={ acosFwLoggingGtpS 22 } 

		logTypeGtpRateLimitPeriodic OBJECT-TYPE
		SYNTAX  CounterBasedGauge64 
		MAX-ACCESS read-only 
		STATUS current
		DESCRIPTION  "Log Event GTP invalid spare bits in header" 
		::={ acosFwLoggingGtpS 23 } 

		logTypeGtpRateLimitPeriodic OBJECT-TYPE
		SYNTAX  CounterBasedGauge64 
		MAX-ACCESS read-only 
		STATUS current
		DESCRIPTION  "Log Event GTP invalid piggyback flag in header" 
		::={ acosFwLoggingGtpS 24 } 

		logTypeGtpRateLimitPeriodic OBJECT-TYPE
		SYNTAX  CounterBasedGauge64 
		MAX-ACCESS read-only 
		STATUS current
		DESCRIPTION  "Log Event invalid GTP version" 
		::={ acosFwLoggingGtpS 25 } 

		logTypeGtpRateLimitPeriodic OBJECT-TYPE
		SYNTAX  CounterBasedGauge64 
		MAX-ACCESS read-only 
		STATUS current
		DESCRIPTION  "Log Event mismatch of GTP message and ports" 
		::={ acosFwLoggingGtpS 26 } 

acosFwGlobal                        OBJECT IDENTIFIER ::= { acosFw 7 }
acosFwGlobalS                       OBJECT IDENTIFIER ::= { acosFwGlobal 1 }

		firewallGlobalTcpFullconeCreated OBJECT-TYPE
		SYNTAX  CounterBasedGauge64 
		MAX-ACCESS read-only 
		STATUS current
		DESCRIPTION  "TCP Full-cone Created" 
		::={ acosFwGlobalS 1 } 

		firewallGlobalTcpFullconeFreed OBJECT-TYPE
		SYNTAX  CounterBasedGauge64 
		MAX-ACCESS read-only 
		STATUS current
		DESCRIPTION  "TCP Full-cone Freed" 
		::={ acosFwGlobalS 2 } 

		firewallGlobalUdpFullconeCreated OBJECT-TYPE
		SYNTAX  CounterBasedGauge64 
		MAX-ACCESS read-only 
		STATUS current
		DESCRIPTION  "UDP Full-cone Created" 
		::={ acosFwGlobalS 3 } 

		firewallGlobalUdpFullconeFreed OBJECT-TYPE
		SYNTAX  CounterBasedGauge64 
		MAX-ACCESS read-only 
		STATUS current
		DESCRIPTION  "UDP Full-cone Freed" 
		::={ acosFwGlobalS 4 } 

		firewallGlobalFullconeCreationFailure OBJECT-TYPE
		SYNTAX  CounterBasedGauge64 
		MAX-ACCESS read-only 
		STATUS current
		DESCRIPTION  "Full-Cone Creation Failure" 
		::={ acosFwGlobalS 5 } 

		firewallGlobalDataSessionCreated OBJECT-TYPE
		SYNTAX  CounterBasedGauge64 
		MAX-ACCESS read-only 
		STATUS current
		DESCRIPTION  "Data Session Created" 
		::={ acosFwGlobalS 6 } 

		firewallGlobalDataSessionCreatedLocal OBJECT-TYPE
		SYNTAX  CounterBasedGauge64 
		MAX-ACCESS read-only 
		STATUS current
		DESCRIPTION  "Data Session Created Local" 
		::={ acosFwGlobalS 104 } 

		firewallGlobalDynBlistSessSP OBJECT-TYPE
		SYNTAX  CounterBasedGauge64 
		MAX-ACCESS read-only 
		STATUS current
		DESCRIPTION  "Dynamic Blacklist Session (Slowpath)" 
		::={ acosFwGlobalS 117 } 

		firewallGlobalDataSessionFreed OBJECT-TYPE
		SYNTAX  CounterBasedGauge64 
		MAX-ACCESS read-only 
		STATUS current
		DESCRIPTION  "Data Session Freed" 
		::={ acosFwGlobalS 7 } 

		firewallGlobalDataSessionFreedLocal OBJECT-TYPE
		SYNTAX  CounterBasedGauge64 
		MAX-ACCESS read-only 
		STATUS current
		DESCRIPTION  "Data Session Freed Local" 
		::={ acosFwGlobalS 105 } 

		firewallGlobalDynBlistSessCreated OBJECT-TYPE
		SYNTAX  CounterBasedGauge64 
		MAX-ACCESS read-only 
		STATUS current
		DESCRIPTION  "Dynamic Blacklist Session Created" 
		::={ acosFwGlobalS 112 } 

		firewallGlobalDynBlistSessFreed OBJECT-TYPE
		SYNTAX  CounterBasedGauge64 
		MAX-ACCESS read-only 
		STATUS current
		DESCRIPTION  "Dynamic Blacklist Freed" 
		::={ acosFwGlobalS 113 } 

		firewallGlobalDynBlistPktDrop OBJECT-TYPE
		SYNTAX  CounterBasedGauge64 
		MAX-ACCESS read-only 
		STATUS current
		DESCRIPTION  "Dynamic Blacklist - Packet Drop" 
		::={ acosFwGlobalS 114 } 

		firewallGlobalDynBlistPktRateLow OBJECT-TYPE
		SYNTAX  CounterBasedGauge64 
		MAX-ACCESS read-only 
		STATUS current
		DESCRIPTION  "Dynamic Blacklist - Pkt Rate Low" 
		::={ acosFwGlobalS 115 } 

		firewallGlobalDynBlistPktRateHigh OBJECT-TYPE
		SYNTAX  CounterBasedGauge64 
		MAX-ACCESS read-only 
		STATUS current
		DESCRIPTION  "Dynamic Blacklist - Pkt Rate High" 
		::={ acosFwGlobalS 116 } 

		firewallGlobalDynBlistVersionMismatch OBJECT-TYPE
		SYNTAX  CounterBasedGauge64 
		MAX-ACCESS read-only 
		STATUS current
		DESCRIPTION  "Dynamic Blacklist - Version Mismatch" 
		::={ acosFwGlobalS 118 } 

		firewallGlobalDynBlistNoActivePolicy OBJECT-TYPE
		SYNTAX  CounterBasedGauge64 
		MAX-ACCESS read-only 
		STATUS current
		DESCRIPTION  "Dynamic Blacklist - No Active Policy" 
		::={ acosFwGlobalS 119 } 

		fullconeInDelQ OBJECT-TYPE
		SYNTAX  CounterBasedGauge64 
		MAX-ACCESS read-only 
		STATUS current
		DESCRIPTION  "Full-cone session found in delete queue" 
		::={ acosFwGlobalS 8 } 

		fullconeRetryLookup OBJECT-TYPE
		SYNTAX  CounterBasedGauge64 
		MAX-ACCESS read-only 
		STATUS current
		DESCRIPTION  "Full-cone session retry look-up" 
		::={ acosFwGlobalS 9 } 

		fullconeNotFound OBJECT-TYPE
		SYNTAX  CounterBasedGauge64 
		MAX-ACCESS read-only 
		STATUS current
		DESCRIPTION  "Full-cone session not found" 
		::={ acosFwGlobalS 10 } 

		fullconeOverflowEim OBJECT-TYPE
		SYNTAX  CounterBasedGauge64 
		MAX-ACCESS read-only 
		STATUS current
		DESCRIPTION  "Full-cone Session EIM Overflow" 
		::={ acosFwGlobalS 11 } 

		fullconeOverflowEif OBJECT-TYPE
		SYNTAX  CounterBasedGauge64 
		MAX-ACCESS read-only 
		STATUS current
		DESCRIPTION  "Full-cone Session EIF Overflow" 
		::={ acosFwGlobalS 12 } 

		udpFullconeCreatedShadow OBJECT-TYPE
		SYNTAX  CounterBasedGauge64 
		MAX-ACCESS read-only 
		STATUS current
		DESCRIPTION  "Total UDP Full-cone sessions created" 
		::={ acosFwGlobalS 13 } 

		tcpFullconeCreatedShadow OBJECT-TYPE
		SYNTAX  CounterBasedGauge64 
		MAX-ACCESS read-only 
		STATUS current
		DESCRIPTION  "Total TCP Full-cone sessions created" 
		::={ acosFwGlobalS 14 } 

		udpFullconeFreedShadow OBJECT-TYPE
		SYNTAX  CounterBasedGauge64 
		MAX-ACCESS read-only 
		STATUS current
		DESCRIPTION  "Total UDP Full-cone sessions freed" 
		::={ acosFwGlobalS 15 } 

		tcpFullconeFreedShadow OBJECT-TYPE
		SYNTAX  CounterBasedGauge64 
		MAX-ACCESS read-only 
		STATUS current
		DESCRIPTION  "Total TCP Full-cone sessions freed" 
		::={ acosFwGlobalS 16 } 

		fullconeCreated OBJECT-TYPE
		SYNTAX  CounterBasedGauge64 
		MAX-ACCESS read-only 
		STATUS current
		DESCRIPTION  "Total Full-cone sessions created" 
		::={ acosFwGlobalS 17 } 

		fullconeFreed OBJECT-TYPE
		SYNTAX  CounterBasedGauge64 
		MAX-ACCESS read-only 
		STATUS current
		DESCRIPTION  "Total Full-cone sessions freed" 
		::={ acosFwGlobalS 18 } 

		fullconeExtTooMany OBJECT-TYPE
		SYNTAX  CounterBasedGauge64 
		MAX-ACCESS read-only 
		STATUS current
		DESCRIPTION  "Fullcone Extension Too Many" 
		::={ acosFwGlobalS 19 } 

		fullconeExtMemAllocated OBJECT-TYPE
		SYNTAX  CounterBasedGauge64 
		MAX-ACCESS read-only 
		STATUS current
		DESCRIPTION  "Fullcone Extension Memory Allocated" 
		::={ acosFwGlobalS 20 } 

		fullconeExtMemAllocFailure OBJECT-TYPE
		SYNTAX  CounterBasedGauge64 
		MAX-ACCESS read-only 
		STATUS current
		DESCRIPTION  "Fullcone Extension Memory Allocate Failure" 
		::={ acosFwGlobalS 21 } 

		fullconeExtMemAllocInitFaulure OBJECT-TYPE
		SYNTAX  CounterBasedGauge64 
		MAX-ACCESS read-only 
		STATUS current
		DESCRIPTION  "Fullcone Extension Initialization Failure" 
		::={ acosFwGlobalS 22 } 

		fullconeExtMemFreed OBJECT-TYPE
		SYNTAX  CounterBasedGauge64 
		MAX-ACCESS read-only 
		STATUS current
		DESCRIPTION  "Fullcone Extension Memory Freed" 
		::={ acosFwGlobalS 23 } 

		fullconeExtAdded OBJECT-TYPE
		SYNTAX  CounterBasedGauge64 
		MAX-ACCESS read-only 
		STATUS current
		DESCRIPTION  "Fullcone Extension Added" 
		::={ acosFwGlobalS 24 } 

		haFullconeFailure OBJECT-TYPE
		SYNTAX  CounterBasedGauge64 
		MAX-ACCESS read-only 
		STATUS current
		DESCRIPTION  "HA Full-cone Session Failure" 
		::={ acosFwGlobalS 25 } 

		dataSessionCreatedShadow OBJECT-TYPE
		SYNTAX  CounterBasedGauge64 
		MAX-ACCESS read-only 
		STATUS current
		DESCRIPTION  "Shadow Data Sessions Created" 
		::={ acosFwGlobalS 26 } 

		dataSessionCreatedShadowLocal OBJECT-TYPE
		SYNTAX  CounterBasedGauge64 
		MAX-ACCESS read-only 
		STATUS current
		DESCRIPTION  "Shadow Data Sessions Created Local" 
		::={ acosFwGlobalS 106 } 

		dataSessionFreedShadow OBJECT-TYPE
		SYNTAX  CounterBasedGauge64 
		MAX-ACCESS read-only 
		STATUS current
		DESCRIPTION  "Shadow Data Sessions Freed" 
		::={ acosFwGlobalS 27 } 

		dataSessionFreedShadowLocal OBJECT-TYPE
		SYNTAX  CounterBasedGauge64 
		MAX-ACCESS read-only 
		STATUS current
		DESCRIPTION  "Shadow Data Sessions Freed Local" 
		::={ acosFwGlobalS 107 } 

		firewallGlobalActiveFullconeSessions OBJECT-TYPE
		SYNTAX  CounterBasedGauge64 
		MAX-ACCESS read-only 
		STATUS current
		DESCRIPTION  "Total Active Full-cone sessions" 
		::={ acosFwGlobalS 28 } 

		limitEntryFailure OBJECT-TYPE
		SYNTAX  CounterBasedGauge64 
		MAX-ACCESS read-only 
		STATUS current
		DESCRIPTION  "Limit Entry Creation Failure" 
		::={ acosFwGlobalS 29 } 

		limitEntryAllocated OBJECT-TYPE
		SYNTAX  CounterBasedGauge64 
		MAX-ACCESS read-only 
		STATUS current
		DESCRIPTION  "Limit Entry Allocated" 
		::={ acosFwGlobalS 30 } 

		limitEntryMemFreed OBJECT-TYPE
		SYNTAX  CounterBasedGauge64 
		MAX-ACCESS read-only 
		STATUS current
		DESCRIPTION  "Limit Entry Freed" 
		::={ acosFwGlobalS 31 } 

		limitEntryCreated OBJECT-TYPE
		SYNTAX  CounterBasedGauge64 
		MAX-ACCESS read-only 
		STATUS current
		DESCRIPTION  "Limit Entry Created" 
		::={ acosFwGlobalS 32 } 

		limitEntryFound OBJECT-TYPE
		SYNTAX  CounterBasedGauge64 
		MAX-ACCESS read-only 
		STATUS current
		DESCRIPTION  "Limit Entry Found" 
		::={ acosFwGlobalS 103 } 

		limitEntryNotInBucket OBJECT-TYPE
		SYNTAX  CounterBasedGauge64 
		MAX-ACCESS read-only 
		STATUS current
		DESCRIPTION  "Limit Entry Not in Bucket" 
		::={ acosFwGlobalS 33 } 

		limitEntryDeleted OBJECT-TYPE
		SYNTAX  CounterBasedGauge64 
		MAX-ACCESS read-only 
		STATUS current
		DESCRIPTION  "Limit Entry Marked Deleted" 
		::={ acosFwGlobalS 34 } 

		undeterminedRuleCounter OBJECT-TYPE
		SYNTAX  CounterBasedGauge64 
		MAX-ACCESS read-only 
		STATUS current
		DESCRIPTION  "Undetermined rule detected" 
		::={ acosFwGlobalS 108 } 

		nonSynPktFwdAllowed OBJECT-TYPE
		SYNTAX  CounterBasedGauge64 
		MAX-ACCESS read-only 
		STATUS current
		DESCRIPTION  "Non-SYN pkt forward allowed" 
		::={ acosFwGlobalS 111 } 

		invalidLidDrop OBJECT-TYPE
		SYNTAX  CounterBasedGauge64 
		MAX-ACCESS read-only 
		STATUS current
		DESCRIPTION  "Invalid Lid Drop" 
		::={ acosFwGlobalS 35 } 

		srcSessionLimitExceeded OBJECT-TYPE
		SYNTAX  CounterBasedGauge64 
		MAX-ACCESS read-only 
		STATUS current
		DESCRIPTION  "Concurrent Session Limit Exceeded" 
		::={ acosFwGlobalS 36 } 

		uplinkPpsLimitExceeded OBJECT-TYPE
		SYNTAX  CounterBasedGauge64 
		MAX-ACCESS read-only 
		STATUS current
		DESCRIPTION  "Uplink PPS Limit Exceeded" 
		::={ acosFwGlobalS 95 } 

		downlinkPpsLimitExceeded OBJECT-TYPE
		SYNTAX  CounterBasedGauge64 
		MAX-ACCESS read-only 
		STATUS current
		DESCRIPTION  "Downlink PPS Limit Exceeded" 
		::={ acosFwGlobalS 96 } 

		totalPpsLimitExceeded OBJECT-TYPE
		SYNTAX  CounterBasedGauge64 
		MAX-ACCESS read-only 
		STATUS current
		DESCRIPTION  "Total PPS Limit Exceeded" 
		::={ acosFwGlobalS 97 } 

		uplinkThroughputLimitExceeded OBJECT-TYPE
		SYNTAX  CounterBasedGauge64 
		MAX-ACCESS read-only 
		STATUS current
		DESCRIPTION  "Uplink Throughput Limit Exceeded" 
		::={ acosFwGlobalS 98 } 

		downlinkThroughputLimitExceeded OBJECT-TYPE
		SYNTAX  CounterBasedGauge64 
		MAX-ACCESS read-only 
		STATUS current
		DESCRIPTION  "Downlink Throughput Limit Exceeded" 
		::={ acosFwGlobalS 99 } 

		totalThroughputLimitExceeded OBJECT-TYPE
		SYNTAX  CounterBasedGauge64 
		MAX-ACCESS read-only 
		STATUS current
		DESCRIPTION  "Total Throughput Limit Exceeded" 
		::={ acosFwGlobalS 100 } 

		cpsLimitExceeded OBJECT-TYPE
		SYNTAX  CounterBasedGauge64 
		MAX-ACCESS read-only 
		STATUS current
		DESCRIPTION  "Connections Per Second Limit Exceeded" 
		::={ acosFwGlobalS 101 } 

		limitExceeded OBJECT-TYPE
		SYNTAX  CounterBasedGauge64 
		MAX-ACCESS read-only 
		STATUS current
		DESCRIPTION  "Per Second Limit Exceeded (Deprecated)" 
		::={ acosFwGlobalS 37 } 

		limitEntryPerCpuMemAllocated OBJECT-TYPE
		SYNTAX  CounterBasedGauge64 
		MAX-ACCESS read-only 
		STATUS current
		DESCRIPTION  "Limit Entry Memory Allocated (Deprecated)" 
		::={ acosFwGlobalS 38 } 

		limitEntryPerCpuMemAllocationFailed OBJECT-TYPE
		SYNTAX  CounterBasedGauge64 
		MAX-ACCESS read-only 
		STATUS current
		DESCRIPTION  "Limit Entry Memory Allocation Failed (Deprecated)" 
		::={ acosFwGlobalS 39 } 

		limitEntryPerCpuMemFreed OBJECT-TYPE
		SYNTAX  CounterBasedGauge64 
		MAX-ACCESS read-only 
		STATUS current
		DESCRIPTION  "Limit Entry Memory Freed (Deprecated)" 
		::={ acosFwGlobalS 40 } 

		algDefaultPortDisable OBJECT-TYPE
		SYNTAX  CounterBasedGauge64 
		MAX-ACCESS read-only 
		STATUS current
		DESCRIPTION  "" 
		::={ acosFwGlobalS 41 } 

		noFwdRoute OBJECT-TYPE
		SYNTAX  CounterBasedGauge64 
		MAX-ACCESS read-only 
		STATUS current
		DESCRIPTION  "No Forward Route" 
		::={ acosFwGlobalS 42 } 

		noRevRoute OBJECT-TYPE
		SYNTAX  CounterBasedGauge64 
		MAX-ACCESS read-only 
		STATUS current
		DESCRIPTION  "No Reverse Route" 
		::={ acosFwGlobalS 43 } 

		noFwdL2Dst OBJECT-TYPE
		SYNTAX  CounterBasedGauge64 
		MAX-ACCESS read-only 
		STATUS current
		DESCRIPTION  "No Forward Mac Entry" 
		::={ acosFwGlobalS 44 } 

		noRevL2Dst OBJECT-TYPE
		SYNTAX  CounterBasedGauge64 
		MAX-ACCESS read-only 
		STATUS current
		DESCRIPTION  "No Reverse Mac Entry" 
		::={ acosFwGlobalS 45 } 

		l2DstInOutSame OBJECT-TYPE
		SYNTAX  CounterBasedGauge64 
		MAX-ACCESS read-only 
		STATUS current
		DESCRIPTION  "L2 route to same port as received" 
		::={ acosFwGlobalS 109 } 

		l2VlanChanged OBJECT-TYPE
		SYNTAX  CounterBasedGauge64 
		MAX-ACCESS read-only 
		STATUS current
		DESCRIPTION  "L2 forwarding vlan changed after session create" 
		::={ acosFwGlobalS 110 } 

		urpfPktDrop OBJECT-TYPE
		SYNTAX  CounterBasedGauge64 
		MAX-ACCESS read-only 
		STATUS current
		DESCRIPTION  "URPF check packet drop" 
		::={ acosFwGlobalS 46 } 

		fwdIngressPacketsTcp OBJECT-TYPE
		SYNTAX  CounterBasedGauge64 
		MAX-ACCESS read-only 
		STATUS current
		DESCRIPTION  "Forward Ingress Packets TCP" 
		::={ acosFwGlobalS 47 } 

		fwdEgressPacketsTcp OBJECT-TYPE
		SYNTAX  CounterBasedGauge64 
		MAX-ACCESS read-only 
		STATUS current
		DESCRIPTION  "Forward Egress Packets TCP" 
		::={ acosFwGlobalS 48 } 

		revIngressPacketsTcp OBJECT-TYPE
		SYNTAX  CounterBasedGauge64 
		MAX-ACCESS read-only 
		STATUS current
		DESCRIPTION  "Reverse Ingress Packets TCP" 
		::={ acosFwGlobalS 49 } 

		revEgressPacketsTcp OBJECT-TYPE
		SYNTAX  CounterBasedGauge64 
		MAX-ACCESS read-only 
		STATUS current
		DESCRIPTION  "Reverse Egress Packets TCP" 
		::={ acosFwGlobalS 50 } 

		fwdIngressBytesTcp OBJECT-TYPE
		SYNTAX  CounterBasedGauge64 
		MAX-ACCESS read-only 
		STATUS current
		DESCRIPTION  "Forward Ingress Bytes TCP" 
		::={ acosFwGlobalS 51 } 

		fwdEgressBytesTcp OBJECT-TYPE
		SYNTAX  CounterBasedGauge64 
		MAX-ACCESS read-only 
		STATUS current
		DESCRIPTION  "Forward Egress Bytes TCP" 
		::={ acosFwGlobalS 52 } 

		revIngressBytesTcp OBJECT-TYPE
		SYNTAX  CounterBasedGauge64 
		MAX-ACCESS read-only 
		STATUS current
		DESCRIPTION  "Reverse Ingress Bytes TCP" 
		::={ acosFwGlobalS 53 } 

		revEgressBytesTcp OBJECT-TYPE
		SYNTAX  CounterBasedGauge64 
		MAX-ACCESS read-only 
		STATUS current
		DESCRIPTION  "Reverse Egress Bytes TCP" 
		::={ acosFwGlobalS 54 } 

		fwdIngressPacketsUdp OBJECT-TYPE
		SYNTAX  CounterBasedGauge64 
		MAX-ACCESS read-only 
		STATUS current
		DESCRIPTION  "Forward Ingress Packets UDP" 
		::={ acosFwGlobalS 55 } 

		fwdEgressPacketsUdp OBJECT-TYPE
		SYNTAX  CounterBasedGauge64 
		MAX-ACCESS read-only 
		STATUS current
		DESCRIPTION  "Forward Egress Packets UDP" 
		::={ acosFwGlobalS 56 } 

		revIngressPacketsUdp OBJECT-TYPE
		SYNTAX  CounterBasedGauge64 
		MAX-ACCESS read-only 
		STATUS current
		DESCRIPTION  "Reverse Ingress Packets UDP" 
		::={ acosFwGlobalS 57 } 

		revEgressPacketsUdp OBJECT-TYPE
		SYNTAX  CounterBasedGauge64 
		MAX-ACCESS read-only 
		STATUS current
		DESCRIPTION  "Reverse Egress Packets UDP" 
		::={ acosFwGlobalS 58 } 

		fwdIngressBytesUdp OBJECT-TYPE
		SYNTAX  CounterBasedGauge64 
		MAX-ACCESS read-only 
		STATUS current
		DESCRIPTION  "Forward Ingress Bytes UDP" 
		::={ acosFwGlobalS 59 } 

		fwdEgressBytesUdp OBJECT-TYPE
		SYNTAX  CounterBasedGauge64 
		MAX-ACCESS read-only 
		STATUS current
		DESCRIPTION  "Forward Egress Bytes UDP" 
		::={ acosFwGlobalS 60 } 

		revIngressBytesUdp OBJECT-TYPE
		SYNTAX  CounterBasedGauge64 
		MAX-ACCESS read-only 
		STATUS current
		DESCRIPTION  "Reverse Ingress Bytes UDP" 
		::={ acosFwGlobalS 61 } 

		revEgressBytesUdp OBJECT-TYPE
		SYNTAX  CounterBasedGauge64 
		MAX-ACCESS read-only 
		STATUS current
		DESCRIPTION  "Reverse Egress Bytes UDP" 
		::={ acosFwGlobalS 62 } 

		fwdIngressPacketsIcmp OBJECT-TYPE
		SYNTAX  CounterBasedGauge64 
		MAX-ACCESS read-only 
		STATUS current
		DESCRIPTION  "Forward Ingress Packets ICMP" 
		::={ acosFwGlobalS 63 } 

		fwdEgressPacketsIcmp OBJECT-TYPE
		SYNTAX  CounterBasedGauge64 
		MAX-ACCESS read-only 
		STATUS current
		DESCRIPTION  "Forward Egress Packets ICMP" 
		::={ acosFwGlobalS 64 } 

		revIngressPacketsIcmp OBJECT-TYPE
		SYNTAX  CounterBasedGauge64 
		MAX-ACCESS read-only 
		STATUS current
		DESCRIPTION  "Reverse Ingress Packets ICMP" 
		::={ acosFwGlobalS 65 } 

		revEgressPacketsIcmp OBJECT-TYPE
		SYNTAX  CounterBasedGauge64 
		MAX-ACCESS read-only 
		STATUS current
		DESCRIPTION  "Reverse Egress Packets ICMP" 
		::={ acosFwGlobalS 66 } 

		fwdIngressBytesIcmp OBJECT-TYPE
		SYNTAX  CounterBasedGauge64 
		MAX-ACCESS read-only 
		STATUS current
		DESCRIPTION  "Forward Ingress Bytes ICMP" 
		::={ acosFwGlobalS 67 } 

		fwdEgressBytesIcmp OBJECT-TYPE
		SYNTAX  CounterBasedGauge64 
		MAX-ACCESS read-only 
		STATUS current
		DESCRIPTION  "Forward Egress Bytes ICMP" 
		::={ acosFwGlobalS 68 } 

		revIngressBytesIcmp OBJECT-TYPE
		SYNTAX  CounterBasedGauge64 
		MAX-ACCESS read-only 
		STATUS current
		DESCRIPTION  "Reverse Ingress Bytes ICMP" 
		::={ acosFwGlobalS 69 } 

		revEgressBytesIcmp OBJECT-TYPE
		SYNTAX  CounterBasedGauge64 
		MAX-ACCESS read-only 
		STATUS current
		DESCRIPTION  "Reverse Egress Bytes ICMP" 
		::={ acosFwGlobalS 70 } 

		fwdIngressPacketsOthers OBJECT-TYPE
		SYNTAX  CounterBasedGauge64 
		MAX-ACCESS read-only 
		STATUS current
		DESCRIPTION  "Forward Ingress Packets OTHERS" 
		::={ acosFwGlobalS 71 } 

		fwdEgressPacketsOthers OBJECT-TYPE
		SYNTAX  CounterBasedGauge64 
		MAX-ACCESS read-only 
		STATUS current
		DESCRIPTION  "Forward Egress Packets OTHERS" 
		::={ acosFwGlobalS 72 } 

		revIngressPacketsOthers OBJECT-TYPE
		SYNTAX  CounterBasedGauge64 
		MAX-ACCESS read-only 
		STATUS current
		DESCRIPTION  "Reverse Ingress Packets OTHERS" 
		::={ acosFwGlobalS 73 } 

		revEgressPacketsOthers OBJECT-TYPE
		SYNTAX  CounterBasedGauge64 
		MAX-ACCESS read-only 
		STATUS current
		DESCRIPTION  "Reverse Egress Packets OTHERS" 
		::={ acosFwGlobalS 74 } 

		fwdIngressBytesOthers OBJECT-TYPE
		SYNTAX  CounterBasedGauge64 
		MAX-ACCESS read-only 
		STATUS current
		DESCRIPTION  "Forward Ingress Bytes OTHERS" 
		::={ acosFwGlobalS 75 } 

		fwdEgressBytesOthers OBJECT-TYPE
		SYNTAX  CounterBasedGauge64 
		MAX-ACCESS read-only 
		STATUS current
		DESCRIPTION  "Forward Egress Bytes OTHERS" 
		::={ acosFwGlobalS 76 } 

		revIngressBytesOthers OBJECT-TYPE
		SYNTAX  CounterBasedGauge64 
		MAX-ACCESS read-only 
		STATUS current
		DESCRIPTION  "Reverse Ingress Bytes OTHERS" 
		::={ acosFwGlobalS 77 } 

		revEgressBytesOthers OBJECT-TYPE
		SYNTAX  CounterBasedGauge64 
		MAX-ACCESS read-only 
		STATUS current
		DESCRIPTION  "Reverse Egress Bytes OTHERS" 
		::={ acosFwGlobalS 78 } 

		fwdIngressPktSizeRange1 OBJECT-TYPE
		SYNTAX  CounterBasedGauge64 
		MAX-ACCESS read-only 
		STATUS current
		DESCRIPTION  "Forward Ingress Packet size between 0 and 200" 
		::={ acosFwGlobalS 79 } 

		fwdIngressPktSizeRange2 OBJECT-TYPE
		SYNTAX  CounterBasedGauge64 
		MAX-ACCESS read-only 
		STATUS current
		DESCRIPTION  "Forward Ingress Packet size between 201 and 800" 
		::={ acosFwGlobalS 80 } 

		fwdIngressPktSizeRange3 OBJECT-TYPE
		SYNTAX  CounterBasedGauge64 
		MAX-ACCESS read-only 
		STATUS current
		DESCRIPTION  "Forward Ingress Packet size between 801 and 1550" 
		::={ acosFwGlobalS 81 } 

		fwdIngressPktSizeRange4 OBJECT-TYPE
		SYNTAX  CounterBasedGauge64 
		MAX-ACCESS read-only 
		STATUS current
		DESCRIPTION  "Forward Ingress Packet size between 1551 and 9000" 
		::={ acosFwGlobalS 82 } 

		fwdEgressPktSizeRange1 OBJECT-TYPE
		SYNTAX  CounterBasedGauge64 
		MAX-ACCESS read-only 
		STATUS current
		DESCRIPTION  "Forward Egress Packet size between 0 and 200" 
		::={ acosFwGlobalS 83 } 

		fwdEgressPktSizeRange2 OBJECT-TYPE
		SYNTAX  CounterBasedGauge64 
		MAX-ACCESS read-only 
		STATUS current
		DESCRIPTION  "Forward Egress Packet size between 201 and 800" 
		::={ acosFwGlobalS 84 } 

		fwdEgressPktSizeRange3 OBJECT-TYPE
		SYNTAX  CounterBasedGauge64 
		MAX-ACCESS read-only 
		STATUS current
		DESCRIPTION  "Forward Egress Packet size between 801 and 1550" 
		::={ acosFwGlobalS 85 } 

		fwdEgressPktSizeRange4 OBJECT-TYPE
		SYNTAX  CounterBasedGauge64 
		MAX-ACCESS read-only 
		STATUS current
		DESCRIPTION  "Forward Egress Packet size between 1551 and 9000" 
		::={ acosFwGlobalS 86 } 

		revIngressPktSizeRange1 OBJECT-TYPE
		SYNTAX  CounterBasedGauge64 
		MAX-ACCESS read-only 
		STATUS current
		DESCRIPTION  "Reverse Ingress Packet size between 0 and 200" 
		::={ acosFwGlobalS 87 } 

		revIngressPktSizeRange2 OBJECT-TYPE
		SYNTAX  CounterBasedGauge64 
		MAX-ACCESS read-only 
		STATUS current
		DESCRIPTION  "Reverse Ingress Packet size between 201 and 800" 
		::={ acosFwGlobalS 88 } 

		revIngressPktSizeRange3 OBJECT-TYPE
		SYNTAX  CounterBasedGauge64 
		MAX-ACCESS read-only 
		STATUS current
		DESCRIPTION  "Reverse Ingress Packet size between 801 and 1550" 
		::={ acosFwGlobalS 89 } 

		revIngressPktSizeRange4 OBJECT-TYPE
		SYNTAX  CounterBasedGauge64 
		MAX-ACCESS read-only 
		STATUS current
		DESCRIPTION  "Reverse Ingress Packet size between 1551 and 9000" 
		::={ acosFwGlobalS 90 } 

		revEgressPktSizeRange1 OBJECT-TYPE
		SYNTAX  CounterBasedGauge64 
		MAX-ACCESS read-only 
		STATUS current
		DESCRIPTION  "Reverse Egress Packet size between 0 and 200" 
		::={ acosFwGlobalS 91 } 

		revEgressPktSizeRange2 OBJECT-TYPE
		SYNTAX  CounterBasedGauge64 
		MAX-ACCESS read-only 
		STATUS current
		DESCRIPTION  "Reverse Egress Packet size between 201 and 800" 
		::={ acosFwGlobalS 92 } 

		revEgressPktSizeRange3 OBJECT-TYPE
		SYNTAX  CounterBasedGauge64 
		MAX-ACCESS read-only 
		STATUS current
		DESCRIPTION  "Reverse Egress Packet size between 801 and 1550" 
		::={ acosFwGlobalS 93 } 

		revEgressPktSizeRange4 OBJECT-TYPE
		SYNTAX  CounterBasedGauge64 
		MAX-ACCESS read-only 
		STATUS current
		DESCRIPTION  "Reverse Egress Packet size between 1551 and 9000" 
		::={ acosFwGlobalS 94 } 

acosFwAlg                           OBJECT IDENTIFIER ::= { acosFw 9 }
acosFwAlgFtp                        OBJECT IDENTIFIER ::= { acosFwAlg 2 }
acosFwAlgFtpS                       OBJECT IDENTIFIER ::= { acosFwAlgFtp 1 }

		clientPortRequest OBJECT-TYPE
		SYNTAX  CounterBasedGauge64 
		MAX-ACCESS read-only 
		STATUS current
		DESCRIPTION  "PORT Requests From Client" 
		::={ acosFwAlgFtpS 1 } 

		clientEprtRequest OBJECT-TYPE
		SYNTAX  CounterBasedGauge64 
		MAX-ACCESS read-only 
		STATUS current
		DESCRIPTION  "EPRT Requests From Client" 
		::={ acosFwAlgFtpS 2 } 

		serverPasvReply OBJECT-TYPE
		SYNTAX  CounterBasedGauge64 
		MAX-ACCESS read-only 
		STATUS current
		DESCRIPTION  "PASV Replies From Server" 
		::={ acosFwAlgFtpS 3 } 

		serverEpsvReply OBJECT-TYPE
		SYNTAX  CounterBasedGauge64 
		MAX-ACCESS read-only 
		STATUS current
		DESCRIPTION  "EPSV Replies From Server" 
		::={ acosFwAlgFtpS 4 } 

		portRetransmits OBJECT-TYPE
		SYNTAX  CounterBasedGauge64 
		MAX-ACCESS read-only 
		STATUS current
		DESCRIPTION  "PORT Retransmits" 
		::={ acosFwAlgFtpS 5 } 

		pasvRetransmits OBJECT-TYPE
		SYNTAX  CounterBasedGauge64 
		MAX-ACCESS read-only 
		STATUS current
		DESCRIPTION  "PASV Retransmits" 
		::={ acosFwAlgFtpS 6 } 

		ftpSmpAppTypeMismatch OBJECT-TYPE
		SYNTAX  CounterBasedGauge64 
		MAX-ACCESS read-only 
		STATUS current
		DESCRIPTION  "SMP App Type Mismatch" 
		::={ acosFwAlgFtpS 7 } 

		retransmitSanityCheckFailure OBJECT-TYPE
		SYNTAX  CounterBasedGauge64 
		MAX-ACCESS read-only 
		STATUS current
		DESCRIPTION  "Retransmit Sanity Check Failure" 
		::={ acosFwAlgFtpS 8 } 

		smpConnAllocFailure OBJECT-TYPE
		SYNTAX  CounterBasedGauge64 
		MAX-ACCESS read-only 
		STATUS current
		DESCRIPTION  "SMP Helper Conn Alloc Failure" 
		::={ acosFwAlgFtpS 9 } 

		portHelperCreated OBJECT-TYPE
		SYNTAX  CounterBasedGauge64 
		MAX-ACCESS read-only 
		STATUS current
		DESCRIPTION  "PORT Helper Created" 
		::={ acosFwAlgFtpS 10 } 

		pasvHelperCreated OBJECT-TYPE
		SYNTAX  CounterBasedGauge64 
		MAX-ACCESS read-only 
		STATUS current
		DESCRIPTION  "PASV Helper Created" 
		::={ acosFwAlgFtpS 11 } 

		portHelperAcquireInDelQ OBJECT-TYPE
		SYNTAX  CounterBasedGauge64 
		MAX-ACCESS read-only 
		STATUS current
		DESCRIPTION  "PORT Helper Acquire In Del Queue" 
		::={ acosFwAlgFtpS 12 } 

		portHelperAcquireAlreadyUsed OBJECT-TYPE
		SYNTAX  CounterBasedGauge64 
		MAX-ACCESS read-only 
		STATUS current
		DESCRIPTION  "PORT Helper Acquire Already Used" 
		::={ acosFwAlgFtpS 13 } 

		pasvHelperAcquireInDelQ OBJECT-TYPE
		SYNTAX  CounterBasedGauge64 
		MAX-ACCESS read-only 
		STATUS current
		DESCRIPTION  "PASV Helper Acquire In Del Queue" 
		::={ acosFwAlgFtpS 14 } 

		pasvHelperAcquireAlreadyUsed OBJECT-TYPE
		SYNTAX  CounterBasedGauge64 
		MAX-ACCESS read-only 
		STATUS current
		DESCRIPTION  "PASV Helper Acquire Already Used" 
		::={ acosFwAlgFtpS 15 } 

		portHelperFreedUsed OBJECT-TYPE
		SYNTAX  CounterBasedGauge64 
		MAX-ACCESS read-only 
		STATUS current
		DESCRIPTION  "PORT Helper Freed Used" 
		::={ acosFwAlgFtpS 16 } 

		portHelperFreedUnused OBJECT-TYPE
		SYNTAX  CounterBasedGauge64 
		MAX-ACCESS read-only 
		STATUS current
		DESCRIPTION  "PORT Helper Freed Unused" 
		::={ acosFwAlgFtpS 17 } 

		pasvHelperFreedUsed OBJECT-TYPE
		SYNTAX  CounterBasedGauge64 
		MAX-ACCESS read-only 
		STATUS current
		DESCRIPTION  "PASV Helper Freed Used" 
		::={ acosFwAlgFtpS 18 } 

		pasvHelperFreedUnused OBJECT-TYPE
		SYNTAX  CounterBasedGauge64 
		MAX-ACCESS read-only 
		STATUS current
		DESCRIPTION  "PASV Helper Freed Unused" 
		::={ acosFwAlgFtpS 19 } 

acosFwAlgTftp                       OBJECT IDENTIFIER ::= { acosFwAlg 3 }
acosFwAlgTftpS                      OBJECT IDENTIFIER ::= { acosFwAlgTftp 1 }

		sessionCreated OBJECT-TYPE
		SYNTAX  CounterBasedGauge64 
		MAX-ACCESS read-only 
		STATUS current
		DESCRIPTION  "TFTP Client Sessions Created" 
		::={ acosFwAlgTftpS 1 } 

		helperCreated OBJECT-TYPE
		SYNTAX  CounterBasedGauge64 
		MAX-ACCESS read-only 
		STATUS current
		DESCRIPTION  "TFTP Helper Sessions created" 
		::={ acosFwAlgTftpS 2 } 

		helperFreed OBJECT-TYPE
		SYNTAX  CounterBasedGauge64 
		MAX-ACCESS read-only 
		STATUS current
		DESCRIPTION  "TFTP Helper Sessions freed" 
		::={ acosFwAlgTftpS 3 } 

		helperFreedUsed OBJECT-TYPE
		SYNTAX  CounterBasedGauge64 
		MAX-ACCESS read-only 
		STATUS current
		DESCRIPTION  "TFTP Helper Sessions freed used" 
		::={ acosFwAlgTftpS 4 } 

		helperFreedUnused OBJECT-TYPE
		SYNTAX  CounterBasedGauge64 
		MAX-ACCESS read-only 
		STATUS current
		DESCRIPTION  "TFTP Helper Sessions freed unused" 
		::={ acosFwAlgTftpS 5 } 

		helperAlreadyUsed OBJECT-TYPE
		SYNTAX  CounterBasedGauge64 
		MAX-ACCESS read-only 
		STATUS current
		DESCRIPTION  "TFTP Helper Session already used" 
		::={ acosFwAlgTftpS 6 } 

		helperInRml OBJECT-TYPE
		SYNTAX  CounterBasedGauge64 
		MAX-ACCESS read-only 
		STATUS current
		DESCRIPTION  "TFTP Helper Session in Remove List" 
		::={ acosFwAlgTftpS 7 } 

acosFwAlgRtsp                       OBJECT IDENTIFIER ::= { acosFwAlg 4 }
acosFwAlgRtspS                      OBJECT IDENTIFIER ::= { acosFwAlgRtsp 1 }

		transportInserted OBJECT-TYPE
		SYNTAX  CounterBasedGauge64 
		MAX-ACCESS read-only 
		STATUS current
		DESCRIPTION  "Transport Created" 
		::={ acosFwAlgRtspS 1 } 

		transportFreed OBJECT-TYPE
		SYNTAX  CounterBasedGauge64 
		MAX-ACCESS read-only 
		STATUS current
		DESCRIPTION  "Transport Freed" 
		::={ acosFwAlgRtspS 2 } 

		transportAllocFailure OBJECT-TYPE
		SYNTAX  CounterBasedGauge64 
		MAX-ACCESS read-only 
		STATUS current
		DESCRIPTION  "Transport Alloc Failure" 
		::={ acosFwAlgRtspS 3 } 

		cgnv6StatefullFireWallAlgRtspDataSessionCreated OBJECT-TYPE
		SYNTAX  CounterBasedGauge64 
		MAX-ACCESS read-only 
		STATUS current
		DESCRIPTION  "Data Session Created" 
		::={ acosFwAlgRtspS 4 } 

		cgnv6StatefullFireWallAlgRtspDataSessionFreed OBJECT-TYPE
		SYNTAX  CounterBasedGauge64 
		MAX-ACCESS read-only 
		STATUS current
		DESCRIPTION  "Data Session Freed" 
		::={ acosFwAlgRtspS 5 } 

		extCreationFailure OBJECT-TYPE
		SYNTAX  CounterBasedGauge64 
		MAX-ACCESS read-only 
		STATUS current
		DESCRIPTION  "Extension Creation Failure" 
		::={ acosFwAlgRtspS 6 } 

		transportAddToExt OBJECT-TYPE
		SYNTAX  CounterBasedGauge64 
		MAX-ACCESS read-only 
		STATUS current
		DESCRIPTION  "Transport Added to Extension" 
		::={ acosFwAlgRtspS 7 } 

		transportRemovedFromExt OBJECT-TYPE
		SYNTAX  CounterBasedGauge64 
		MAX-ACCESS read-only 
		STATUS current
		DESCRIPTION  "Transport Removed from Extension" 
		::={ acosFwAlgRtspS 8 } 

		transportTooMany OBJECT-TYPE
		SYNTAX  CounterBasedGauge64 
		MAX-ACCESS read-only 
		STATUS current
		DESCRIPTION  "Too Many Transports for Control Conn" 
		::={ acosFwAlgRtspS 9 } 

		transportAlreadyInExt OBJECT-TYPE
		SYNTAX  CounterBasedGauge64 
		MAX-ACCESS read-only 
		STATUS current
		DESCRIPTION  "Transport Already in Extension" 
		::={ acosFwAlgRtspS 10 } 

		transportExists OBJECT-TYPE
		SYNTAX  CounterBasedGauge64 
		MAX-ACCESS read-only 
		STATUS current
		DESCRIPTION  "Transport Already Exists" 
		::={ acosFwAlgRtspS 11 } 

		transportLinkExtFailureControl OBJECT-TYPE
		SYNTAX  CounterBasedGauge64 
		MAX-ACCESS read-only 
		STATUS current
		DESCRIPTION  "Transport Link to Extension Failure Control" 
		::={ acosFwAlgRtspS 12 } 

		transportLinkExtData OBJECT-TYPE
		SYNTAX  CounterBasedGauge64 
		MAX-ACCESS read-only 
		STATUS current
		DESCRIPTION  "Transport Link to Extension Data" 
		::={ acosFwAlgRtspS 13 } 

		transportLinkExtFailureData OBJECT-TYPE
		SYNTAX  CounterBasedGauge64 
		MAX-ACCESS read-only 
		STATUS current
		DESCRIPTION  "Transport Link to Extension Failure Data" 
		::={ acosFwAlgRtspS 14 } 

		transportInsertedShadow OBJECT-TYPE
		SYNTAX  CounterBasedGauge64 
		MAX-ACCESS read-only 
		STATUS current
		DESCRIPTION  "Transport Inserted Shadow" 
		::={ acosFwAlgRtspS 15 } 

		transportCreationRace OBJECT-TYPE
		SYNTAX  CounterBasedGauge64 
		MAX-ACCESS read-only 
		STATUS current
		DESCRIPTION  "Transport Create Race" 
		::={ acosFwAlgRtspS 16 } 

		transportAllocFailureShadow OBJECT-TYPE
		SYNTAX  CounterBasedGauge64 
		MAX-ACCESS read-only 
		STATUS current
		DESCRIPTION  "Transport Alloc Failure Shadow" 
		::={ acosFwAlgRtspS 17 } 

		transportPutInDelQ OBJECT-TYPE
		SYNTAX  CounterBasedGauge64 
		MAX-ACCESS read-only 
		STATUS current
		DESCRIPTION  "Transport Put in Delete Queue" 
		::={ acosFwAlgRtspS 18 } 

		transportFreedShadow OBJECT-TYPE
		SYNTAX  CounterBasedGauge64 
		MAX-ACCESS read-only 
		STATUS current
		DESCRIPTION  "Transport Freed Shadow" 
		::={ acosFwAlgRtspS 19 } 

		transportAcquiredFromControl OBJECT-TYPE
		SYNTAX  CounterBasedGauge64 
		MAX-ACCESS read-only 
		STATUS current
		DESCRIPTION  "Transport Acquired Control" 
		::={ acosFwAlgRtspS 20 } 

		transportFoundFromPrevControl OBJECT-TYPE
		SYNTAX  CounterBasedGauge64 
		MAX-ACCESS read-only 
		STATUS current
		DESCRIPTION  "Transport Found From Prev Control" 
		::={ acosFwAlgRtspS 21 } 

		transportAcquireFailureFromControl OBJECT-TYPE
		SYNTAX  CounterBasedGauge64 
		MAX-ACCESS read-only 
		STATUS current
		DESCRIPTION  "Transport Acquire Failure Control" 
		::={ acosFwAlgRtspS 22 } 

		transportReleasedFromControl OBJECT-TYPE
		SYNTAX  CounterBasedGauge64 
		MAX-ACCESS read-only 
		STATUS current
		DESCRIPTION  "Transport Released Control" 
		::={ acosFwAlgRtspS 23 } 

		transportDoubleReleaseFromControl OBJECT-TYPE
		SYNTAX  CounterBasedGauge64 
		MAX-ACCESS read-only 
		STATUS current
		DESCRIPTION  "Transport Double Release Control" 
		::={ acosFwAlgRtspS 24 } 

		transportAcquiredFromData OBJECT-TYPE
		SYNTAX  CounterBasedGauge64 
		MAX-ACCESS read-only 
		STATUS current
		DESCRIPTION  "Transport Acquired Data" 
		::={ acosFwAlgRtspS 25 } 

		transportAcquireFailureFromData OBJECT-TYPE
		SYNTAX  CounterBasedGauge64 
		MAX-ACCESS read-only 
		STATUS current
		DESCRIPTION  "Transport Acquire Failure Data" 
		::={ acosFwAlgRtspS 26 } 

		transportReleasedFromData OBJECT-TYPE
		SYNTAX  CounterBasedGauge64 
		MAX-ACCESS read-only 
		STATUS current
		DESCRIPTION  "Transport Released Data" 
		::={ acosFwAlgRtspS 27 } 

		transportDoubleReleaseFromData OBJECT-TYPE
		SYNTAX  CounterBasedGauge64 
		MAX-ACCESS read-only 
		STATUS current
		DESCRIPTION  "Transport Double Release Data" 
		::={ acosFwAlgRtspS 28 } 

		transportRetryLookupOnDataFree OBJECT-TYPE
		SYNTAX  CounterBasedGauge64 
		MAX-ACCESS read-only 
		STATUS current
		DESCRIPTION  "Transport Retry Lookup Data" 
		::={ acosFwAlgRtspS 29 } 

		transportNotFoundOnDataFree OBJECT-TYPE
		SYNTAX  CounterBasedGauge64 
		MAX-ACCESS read-only 
		STATUS current
		DESCRIPTION  "Transport Not Found Data" 
		::={ acosFwAlgRtspS 30 } 

		rstpDataSessionCreatedShadow OBJECT-TYPE
		SYNTAX  CounterBasedGauge64 
		MAX-ACCESS read-only 
		STATUS current
		DESCRIPTION  "Data Session Created Shadow" 
		::={ acosFwAlgRtspS 31 } 

		rstpDataSessionFreedShadow OBJECT-TYPE
		SYNTAX  CounterBasedGauge64 
		MAX-ACCESS read-only 
		STATUS current
		DESCRIPTION  "Data Session Freed Shadow" 
		::={ acosFwAlgRtspS 32 } 

		haControlExtCreationFailure OBJECT-TYPE
		SYNTAX  CounterBasedGauge64 
		MAX-ACCESS read-only 
		STATUS current
		DESCRIPTION  "HA Control Extension Creation Failure" 
		::={ acosFwAlgRtspS 33 } 

		haControlSessionCreated OBJECT-TYPE
		SYNTAX  CounterBasedGauge64 
		MAX-ACCESS read-only 
		STATUS current
		DESCRIPTION  "HA Control Session Created" 
		::={ acosFwAlgRtspS 34 } 

		haDataSessionCreated OBJECT-TYPE
		SYNTAX  CounterBasedGauge64 
		MAX-ACCESS read-only 
		STATUS current
		DESCRIPTION  "HA Data Session Created" 
		::={ acosFwAlgRtspS 35 } 

acosFwAlgPptp                       OBJECT IDENTIFIER ::= { acosFwAlg 5 }
acosFwAlgPptpS                      OBJECT IDENTIFIER ::= { acosFwAlgPptp 1 }

		callsEstablished OBJECT-TYPE
		SYNTAX  CounterBasedGauge64 
		MAX-ACCESS read-only 
		STATUS current
		DESCRIPTION  "Calls Established" 
		::={ acosFwAlgPptpS 1 } 

		callReqPnsCallIdMismatch OBJECT-TYPE
		SYNTAX  CounterBasedGauge64 
		MAX-ACCESS read-only 
		STATUS current
		DESCRIPTION  "Call ID Mismatch on Call Request" 
		::={ acosFwAlgPptpS 2 } 

		callReplyPnsCallIdMismatch OBJECT-TYPE
		SYNTAX  CounterBasedGauge64 
		MAX-ACCESS read-only 
		STATUS current
		DESCRIPTION  "Call ID Mismatch on Call Reply" 
		::={ acosFwAlgPptpS 3 } 

		greSessionCreated OBJECT-TYPE
		SYNTAX  CounterBasedGauge64 
		MAX-ACCESS read-only 
		STATUS current
		DESCRIPTION  "GRE Session Created" 
		::={ acosFwAlgPptpS 4 } 

		greSessionFreed OBJECT-TYPE
		SYNTAX  CounterBasedGauge64 
		MAX-ACCESS read-only 
		STATUS current
		DESCRIPTION  "GRE Session Freed" 
		::={ acosFwAlgPptpS 5 } 

		callReqRetransmit OBJECT-TYPE
		SYNTAX  CounterBasedGauge64 
		MAX-ACCESS read-only 
		STATUS current
		DESCRIPTION  "Call Request Retransmit" 
		::={ acosFwAlgPptpS 6 } 

		callReqNew OBJECT-TYPE
		SYNTAX  CounterBasedGauge64 
		MAX-ACCESS read-only 
		STATUS current
		DESCRIPTION  "Call Request New" 
		::={ acosFwAlgPptpS 7 } 

		callReqExtAllocFailure OBJECT-TYPE
		SYNTAX  CounterBasedGauge64 
		MAX-ACCESS read-only 
		STATUS current
		DESCRIPTION  "Call Request Ext Alloc Failure" 
		::={ acosFwAlgPptpS 8 } 

		callReplyCallIdUnknown OBJECT-TYPE
		SYNTAX  CounterBasedGauge64 
		MAX-ACCESS read-only 
		STATUS current
		DESCRIPTION  "Call Reply Unknown Client Call ID" 
		::={ acosFwAlgPptpS 9 } 

		callReplyRetransmit OBJECT-TYPE
		SYNTAX  CounterBasedGauge64 
		MAX-ACCESS read-only 
		STATUS current
		DESCRIPTION  "Call Reply Retransmit" 
		::={ acosFwAlgPptpS 10 } 

		callReplyExtExtAllocFailure OBJECT-TYPE
		SYNTAX  CounterBasedGauge64 
		MAX-ACCESS read-only 
		STATUS current
		DESCRIPTION  "Call Request Ext Alloc Failure" 
		::={ acosFwAlgPptpS 11 } 

		smpAppTypeMismatch OBJECT-TYPE
		SYNTAX  CounterBasedGauge64 
		MAX-ACCESS read-only 
		STATUS current
		DESCRIPTION  "SMP App Type Mismatch" 
		::={ acosFwAlgPptpS 12 } 

		smpClientCallIdMismatch OBJECT-TYPE
		SYNTAX  CounterBasedGauge64 
		MAX-ACCESS read-only 
		STATUS current
		DESCRIPTION  "SMP Client Call ID Mismatch" 
		::={ acosFwAlgPptpS 13 } 

		smpSessionsCreated OBJECT-TYPE
		SYNTAX  CounterBasedGauge64 
		MAX-ACCESS read-only 
		STATUS current
		DESCRIPTION  "SMP Session Created" 
		::={ acosFwAlgPptpS 14 } 

		smpSessionsFreed OBJECT-TYPE
		SYNTAX  CounterBasedGauge64 
		MAX-ACCESS read-only 
		STATUS current
		DESCRIPTION  "SMP Session Freed" 
		::={ acosFwAlgPptpS 15 } 

		smpAllocFailure OBJECT-TYPE
		SYNTAX  CounterBasedGauge64 
		MAX-ACCESS read-only 
		STATUS current
		DESCRIPTION  "SMP Session Alloc Failure" 
		::={ acosFwAlgPptpS 16 } 

		greConnCreationFailure OBJECT-TYPE
		SYNTAX  CounterBasedGauge64 
		MAX-ACCESS read-only 
		STATUS current
		DESCRIPTION  "GRE Conn Alloc Failure" 
		::={ acosFwAlgPptpS 17 } 

		greConnExtCreationFailure OBJECT-TYPE
		SYNTAX  CounterBasedGauge64 
		MAX-ACCESS read-only 
		STATUS current
		DESCRIPTION  "GRE Conn Ext Alloc Failure" 
		::={ acosFwAlgPptpS 18 } 

		greNoFwdRoute OBJECT-TYPE
		SYNTAX  CounterBasedGauge64 
		MAX-ACCESS read-only 
		STATUS current
		DESCRIPTION  "GRE No Fwd Route" 
		::={ acosFwAlgPptpS 19 } 

		greNoRevRoute OBJECT-TYPE
		SYNTAX  CounterBasedGauge64 
		MAX-ACCESS read-only 
		STATUS current
		DESCRIPTION  "GRE No Rev Route" 
		::={ acosFwAlgPptpS 20 } 

		greNoControlConn OBJECT-TYPE
		SYNTAX  CounterBasedGauge64 
		MAX-ACCESS read-only 
		STATUS current
		DESCRIPTION  "GRE No Control Conn" 
		::={ acosFwAlgPptpS 21 } 

		greConnAlreadyExists OBJECT-TYPE
		SYNTAX  CounterBasedGauge64 
		MAX-ACCESS read-only 
		STATUS current
		DESCRIPTION  "GRE Conn Already Exists" 
		::={ acosFwAlgPptpS 22 } 

		greFreeNoExt OBJECT-TYPE
		SYNTAX  CounterBasedGauge64 
		MAX-ACCESS read-only 
		STATUS current
		DESCRIPTION  "GRE Free No Ext" 
		::={ acosFwAlgPptpS 23 } 

		greFreeNoSmp OBJECT-TYPE
		SYNTAX  CounterBasedGauge64 
		MAX-ACCESS read-only 
		STATUS current
		DESCRIPTION  "GRE Free No SMP" 
		::={ acosFwAlgPptpS 24 } 

		greFreeSmpAppTypeMismatch OBJECT-TYPE
		SYNTAX  CounterBasedGauge64 
		MAX-ACCESS read-only 
		STATUS current
		DESCRIPTION  "GRE Free SMP App Type Mismatch" 
		::={ acosFwAlgPptpS 25 } 

		controlFreed OBJECT-TYPE
		SYNTAX  CounterBasedGauge64 
		MAX-ACCESS read-only 
		STATUS current
		DESCRIPTION  "Control Session Freed" 
		::={ acosFwAlgPptpS 26 } 

		controlFreeNoExt OBJECT-TYPE
		SYNTAX  CounterBasedGauge64 
		MAX-ACCESS read-only 
		STATUS current
		DESCRIPTION  "Control Free No Ext" 
		::={ acosFwAlgPptpS 27 } 

		controlFreeNoSmp OBJECT-TYPE
		SYNTAX  CounterBasedGauge64 
		MAX-ACCESS read-only 
		STATUS current
		DESCRIPTION  "Control Free No SMP" 
		::={ acosFwAlgPptpS 28 } 

		controlFreeSmpAppTypeMismatch OBJECT-TYPE
		SYNTAX  CounterBasedGauge64 
		MAX-ACCESS read-only 
		STATUS current
		DESCRIPTION  "Control Free SMP App Type Mismatch" 
		::={ acosFwAlgPptpS 29 } 

acosFwAlgSip                        OBJECT IDENTIFIER ::= { acosFwAlg 6 }
acosFwAlgSipS                       OBJECT IDENTIFIER ::= { acosFwAlgSip 1 }

		statRequest OBJECT-TYPE
		SYNTAX  CounterBasedGauge64 
		MAX-ACCESS read-only 
		STATUS current
		DESCRIPTION  "Request Received" 
		::={ acosFwAlgSipS 1 } 

		statResponse OBJECT-TYPE
		SYNTAX  CounterBasedGauge64 
		MAX-ACCESS read-only 
		STATUS current
		DESCRIPTION  "Response Received" 
		::={ acosFwAlgSipS 2 } 

		methodRegister OBJECT-TYPE
		SYNTAX  CounterBasedGauge64 
		MAX-ACCESS read-only 
		STATUS current
		DESCRIPTION  "Method REGISTER" 
		::={ acosFwAlgSipS 3 } 

		methodInvite OBJECT-TYPE
		SYNTAX  CounterBasedGauge64 
		MAX-ACCESS read-only 
		STATUS current
		DESCRIPTION  "Method INVITE" 
		::={ acosFwAlgSipS 4 } 

		methodAck OBJECT-TYPE
		SYNTAX  CounterBasedGauge64 
		MAX-ACCESS read-only 
		STATUS current
		DESCRIPTION  "Method ACK" 
		::={ acosFwAlgSipS 5 } 

		methodCancel OBJECT-TYPE
		SYNTAX  CounterBasedGauge64 
		MAX-ACCESS read-only 
		STATUS current
		DESCRIPTION  "Method CANCEL" 
		::={ acosFwAlgSipS 6 } 

		methodBye OBJECT-TYPE
		SYNTAX  CounterBasedGauge64 
		MAX-ACCESS read-only 
		STATUS current
		DESCRIPTION  "Method BYE" 
		::={ acosFwAlgSipS 7 } 

		methodOptions OBJECT-TYPE
		SYNTAX  CounterBasedGauge64 
		MAX-ACCESS read-only 
		STATUS current
		DESCRIPTION  "Method OPTIONS" 
		::={ acosFwAlgSipS 8 } 

		methodPrack OBJECT-TYPE
		SYNTAX  CounterBasedGauge64 
		MAX-ACCESS read-only 
		STATUS current
		DESCRIPTION  "Method PRACK" 
		::={ acosFwAlgSipS 9 } 

		methodSubscribe OBJECT-TYPE
		SYNTAX  CounterBasedGauge64 
		MAX-ACCESS read-only 
		STATUS current
		DESCRIPTION  "Method SUBSCRIBE" 
		::={ acosFwAlgSipS 10 } 

		methodNotify OBJECT-TYPE
		SYNTAX  CounterBasedGauge64 
		MAX-ACCESS read-only 
		STATUS current
		DESCRIPTION  "Method NOTIFY" 
		::={ acosFwAlgSipS 11 } 

		methodPublish OBJECT-TYPE
		SYNTAX  CounterBasedGauge64 
		MAX-ACCESS read-only 
		STATUS current
		DESCRIPTION  "Method PUBLISH" 
		::={ acosFwAlgSipS 12 } 

		methodInfo OBJECT-TYPE
		SYNTAX  CounterBasedGauge64 
		MAX-ACCESS read-only 
		STATUS current
		DESCRIPTION  "Method INFO" 
		::={ acosFwAlgSipS 13 } 

		methodRefer OBJECT-TYPE
		SYNTAX  CounterBasedGauge64 
		MAX-ACCESS read-only 
		STATUS current
		DESCRIPTION  "Method REFER" 
		::={ acosFwAlgSipS 14 } 

		methodMessage OBJECT-TYPE
		SYNTAX  CounterBasedGauge64 
		MAX-ACCESS read-only 
		STATUS current
		DESCRIPTION  "Method MESSAGE" 
		::={ acosFwAlgSipS 15 } 

		methodUpdate OBJECT-TYPE
		SYNTAX  CounterBasedGauge64 
		MAX-ACCESS read-only 
		STATUS current
		DESCRIPTION  "Method UPDATE" 
		::={ acosFwAlgSipS 16 } 

		methodUnknown OBJECT-TYPE
		SYNTAX  CounterBasedGauge64 
		MAX-ACCESS read-only 
		STATUS current
		DESCRIPTION  "Method Unknown" 
		::={ acosFwAlgSipS 17 } 

		parseError OBJECT-TYPE
		SYNTAX  CounterBasedGauge64 
		MAX-ACCESS read-only 
		STATUS current
		DESCRIPTION  "Message Parse Error" 
		::={ acosFwAlgSipS 18 } 

		keepAlive OBJECT-TYPE
		SYNTAX  CounterBasedGauge64 
		MAX-ACCESS read-only 
		STATUS current
		DESCRIPTION  "Keep Alive" 
		::={ acosFwAlgSipS 19 } 

		contactError OBJECT-TYPE
		SYNTAX  CounterBasedGauge64 
		MAX-ACCESS read-only 
		STATUS current
		DESCRIPTION  "Contact Process Error" 
		::={ acosFwAlgSipS 20 } 

		sdpError OBJECT-TYPE
		SYNTAX  CounterBasedGauge64 
		MAX-ACCESS read-only 
		STATUS current
		DESCRIPTION  "SDP Process Error" 
		::={ acosFwAlgSipS 21 } 

		rtpPortNoOp OBJECT-TYPE
		SYNTAX  CounterBasedGauge64 
		MAX-ACCESS read-only 
		STATUS current
		DESCRIPTION  "RTP Port No Op" 
		::={ acosFwAlgSipS 22 } 

		rtpRtcpPortSuccess OBJECT-TYPE
		SYNTAX  CounterBasedGauge64 
		MAX-ACCESS read-only 
		STATUS current
		DESCRIPTION  "RTP RTCP Port Success" 
		::={ acosFwAlgSipS 23 } 

		rtpPortFailure OBJECT-TYPE
		SYNTAX  CounterBasedGauge64 
		MAX-ACCESS read-only 
		STATUS current
		DESCRIPTION  "RTP Port Failure" 
		::={ acosFwAlgSipS 24 } 

		rtcpPortFailure OBJECT-TYPE
		SYNTAX  CounterBasedGauge64 
		MAX-ACCESS read-only 
		STATUS current
		DESCRIPTION  "RTCP Port Failure" 
		::={ acosFwAlgSipS 25 } 

		contactPortNoOp OBJECT-TYPE
		SYNTAX  CounterBasedGauge64 
		MAX-ACCESS read-only 
		STATUS current
		DESCRIPTION  "Contact Port No Op" 
		::={ acosFwAlgSipS 26 } 

		contactPortSuccess OBJECT-TYPE
		SYNTAX  CounterBasedGauge64 
		MAX-ACCESS read-only 
		STATUS current
		DESCRIPTION  "Contact Port Success" 
		::={ acosFwAlgSipS 27 } 

		contactPortFailure OBJECT-TYPE
		SYNTAX  CounterBasedGauge64 
		MAX-ACCESS read-only 
		STATUS current
		DESCRIPTION  "Contact Port Failure" 
		::={ acosFwAlgSipS 28 } 

		contactNew OBJECT-TYPE
		SYNTAX  CounterBasedGauge64 
		MAX-ACCESS read-only 
		STATUS current
		DESCRIPTION  "Contact Alloc" 
		::={ acosFwAlgSipS 29 } 

		contactAllocFailure OBJECT-TYPE
		SYNTAX  CounterBasedGauge64 
		MAX-ACCESS read-only 
		STATUS current
		DESCRIPTION  "Contact Alloc Failure" 
		::={ acosFwAlgSipS 30 } 

		contactEim OBJECT-TYPE
		SYNTAX  CounterBasedGauge64 
		MAX-ACCESS read-only 
		STATUS current
		DESCRIPTION  "Contact EIM" 
		::={ acosFwAlgSipS 31 } 

		contactEimSet OBJECT-TYPE
		SYNTAX  CounterBasedGauge64 
		MAX-ACCESS read-only 
		STATUS current
		DESCRIPTION  "Contact EIM Set" 
		::={ acosFwAlgSipS 32 } 

		rtpNew OBJECT-TYPE
		SYNTAX  CounterBasedGauge64 
		MAX-ACCESS read-only 
		STATUS current
		DESCRIPTION  "RTP Alloc" 
		::={ acosFwAlgSipS 33 } 

		rtpAllocFailure OBJECT-TYPE
		SYNTAX  CounterBasedGauge64 
		MAX-ACCESS read-only 
		STATUS current
		DESCRIPTION  "RTP Alloc Failure" 
		::={ acosFwAlgSipS 34 } 

		rtpEim OBJECT-TYPE
		SYNTAX  CounterBasedGauge64 
		MAX-ACCESS read-only 
		STATUS current
		DESCRIPTION  "RTP EIM" 
		::={ acosFwAlgSipS 35 } 

		helperFound OBJECT-TYPE
		SYNTAX  CounterBasedGauge64 
		MAX-ACCESS read-only 
		STATUS current
		DESCRIPTION  "SMP Helper Conn Found" 
		::={ acosFwAlgSipS 36 } 

		sipHelperCreated OBJECT-TYPE
		SYNTAX  CounterBasedGauge64 
		MAX-ACCESS read-only 
		STATUS current
		DESCRIPTION  "SMP Helper Conn Created" 
		::={ acosFwAlgSipS 37 } 

		sipHelperDeleted OBJECT-TYPE
		SYNTAX  CounterBasedGauge64 
		MAX-ACCESS read-only 
		STATUS current
		DESCRIPTION  "SMP Helper Conn Already Deleted" 
		::={ acosFwAlgSipS 38 } 

		sipHelperFreed OBJECT-TYPE
		SYNTAX  CounterBasedGauge64 
		MAX-ACCESS read-only 
		STATUS current
		DESCRIPTION  "SMP Helper Conn Freed" 
		::={ acosFwAlgSipS 39 } 

		helperFailure OBJECT-TYPE
		SYNTAX  CounterBasedGauge64 
		MAX-ACCESS read-only 
		STATUS current
		DESCRIPTION  "SMP Helper Failure" 
		::={ acosFwAlgSipS 40 } 

acosFwAlgEsp                        OBJECT IDENTIFIER ::= { acosFwAlg 9 }
acosFwAlgEspS                       OBJECT IDENTIFIER ::= { acosFwAlgEsp 1 }

		sessionCreated OBJECT-TYPE
		SYNTAX  CounterBasedGauge64 
		MAX-ACCESS read-only 
		STATUS current
		DESCRIPTION  "ESP Sessions Created" 
		::={ acosFwAlgEspS 1 } 

		helperCreated OBJECT-TYPE
		SYNTAX  CounterBasedGauge64 
		MAX-ACCESS read-only 
		STATUS current
		DESCRIPTION  "ESP Helper Sessions Created" 
		::={ acosFwAlgEspS 2 } 

		helperFreed OBJECT-TYPE
		SYNTAX  CounterBasedGauge64 
		MAX-ACCESS read-only 
		STATUS current
		DESCRIPTION  "ESP Helper Sessions Freed" 
		::={ acosFwAlgEspS 3 } 

		helperFreedUsed OBJECT-TYPE
		SYNTAX  CounterBasedGauge64 
		MAX-ACCESS read-only 
		STATUS current
		DESCRIPTION  "ESP Helper Sessions freed used" 
		::={ acosFwAlgEspS 4 } 

		helperFreedUnused OBJECT-TYPE
		SYNTAX  CounterBasedGauge64 
		MAX-ACCESS read-only 
		STATUS current
		DESCRIPTION  "ESP Helper Sessions freed unused" 
		::={ acosFwAlgEspS 5 } 

		helperAlreadyUsed OBJECT-TYPE
		SYNTAX  CounterBasedGauge64 
		MAX-ACCESS read-only 
		STATUS current
		DESCRIPTION  "ESP Helper Session already used" 
		::={ acosFwAlgEspS 6 } 

		helperInRml OBJECT-TYPE
		SYNTAX  CounterBasedGauge64 
		MAX-ACCESS read-only 
		STATUS current
		DESCRIPTION  "ESP Helper Session in Remove List" 
		::={ acosFwAlgEspS 7 } 

acosFwTcpWindowCheck                OBJECT IDENTIFIER ::= { acosFw 12 }
acosFwTcpWindowCheckS               OBJECT IDENTIFIER ::= { acosFwTcpWindowCheck 1 }

		outsideWindow OBJECT-TYPE
		SYNTAX  CounterBasedGauge64 
		MAX-ACCESS read-only 
		STATUS current
		DESCRIPTION  "packet dropped counter for outside of tcp window" 
		::={ acosFwTcpWindowCheckS 1 } 

acosFwRadius                        OBJECT IDENTIFIER ::= { acosFw 17 }
acosFwRadiusServer                  OBJECT IDENTIFIER ::= { acosFwRadius 1 }
acosFwRadiusServerS                 OBJECT IDENTIFIER ::= { acosFwRadiusServer 1 }

		msisdnReceived OBJECT-TYPE
		SYNTAX  CounterBasedGauge64 
		MAX-ACCESS read-only 
		STATUS current
		DESCRIPTION  "MSISDN Received" 
		::={ acosFwRadiusServerS 1 } 

		imeiReceived OBJECT-TYPE
		SYNTAX  CounterBasedGauge64 
		MAX-ACCESS read-only 
		STATUS current
		DESCRIPTION  "IMEI Received" 
		::={ acosFwRadiusServerS 2 } 

		imsiReceived OBJECT-TYPE
		SYNTAX  CounterBasedGauge64 
		MAX-ACCESS read-only 
		STATUS current
		DESCRIPTION  "IMSI Received" 
		::={ acosFwRadiusServerS 3 } 

		customReceived OBJECT-TYPE
		SYNTAX  CounterBasedGauge64 
		MAX-ACCESS read-only 
		STATUS current
		DESCRIPTION  "Custom attribute Received" 
		::={ acosFwRadiusServerS 4 } 

		radiusRequestReceived OBJECT-TYPE
		SYNTAX  CounterBasedGauge64 
		MAX-ACCESS read-only 
		STATUS current
		DESCRIPTION  "RADIUS Request Received" 
		::={ acosFwRadiusServerS 5 } 

		radiusRequestDropped OBJECT-TYPE
		SYNTAX  CounterBasedGauge64 
		MAX-ACCESS read-only 
		STATUS current
		DESCRIPTION  "RADIUS Request Dropped (Malformed Packet)" 
		::={ acosFwRadiusServerS 6 } 

		requestBadSecretDropped OBJECT-TYPE
		SYNTAX  CounterBasedGauge64 
		MAX-ACCESS read-only 
		STATUS current
		DESCRIPTION  "RADIUS Request Bad Secret Dropped" 
		::={ acosFwRadiusServerS 7 } 

		requestNoKeyVapDropped OBJECT-TYPE
		SYNTAX  CounterBasedGauge64 
		MAX-ACCESS read-only 
		STATUS current
		DESCRIPTION  "RADIUS Request No Key Attribute Dropped" 
		::={ acosFwRadiusServerS 8 } 

		requestMalformedDropped OBJECT-TYPE
		SYNTAX  CounterBasedGauge64 
		MAX-ACCESS read-only 
		STATUS current
		DESCRIPTION  "RADIUS Request Malformed Dropped" 
		::={ acosFwRadiusServerS 9 } 

		requestIgnored OBJECT-TYPE
		SYNTAX  CounterBasedGauge64 
		MAX-ACCESS read-only 
		STATUS current
		DESCRIPTION  "RADIUS Request Table Full Dropped" 
		::={ acosFwRadiusServerS 10 } 

		radiusTableFull OBJECT-TYPE
		SYNTAX  CounterBasedGauge64 
		MAX-ACCESS read-only 
		STATUS current
		DESCRIPTION  "RADIUS Request Dropped (Table Full)" 
		::={ acosFwRadiusServerS 11 } 

		secretNotConfiguredDropped OBJECT-TYPE
		SYNTAX  CounterBasedGauge64 
		MAX-ACCESS read-only 
		STATUS current
		DESCRIPTION  "RADIUS Secret Not Configured Dropped" 
		::={ acosFwRadiusServerS 12 } 

		haStandbyDropped OBJECT-TYPE
		SYNTAX  CounterBasedGauge64 
		MAX-ACCESS read-only 
		STATUS current
		DESCRIPTION  "HA Standby Dropped" 
		::={ acosFwRadiusServerS 13 } 

		ipv6PrefixLengthMismatch OBJECT-TYPE
		SYNTAX  CounterBasedGauge64 
		MAX-ACCESS read-only 
		STATUS current
		DESCRIPTION  "Framed IPV6 Prefix Length Mismatch" 
		::={ acosFwRadiusServerS 14 } 

		invalidKey OBJECT-TYPE
		SYNTAX  CounterBasedGauge64 
		MAX-ACCESS read-only 
		STATUS current
		DESCRIPTION  "Radius Request has Invalid Key Field" 
		::={ acosFwRadiusServerS 15 } 

		smpMemAllocated OBJECT-TYPE
		SYNTAX  CounterBasedGauge64 
		MAX-ACCESS read-only 
		STATUS current
		DESCRIPTION  "RADIUS SMP Memory Allocated" 
		::={ acosFwRadiusServerS 21 } 

		smpMemAllocFailed OBJECT-TYPE
		SYNTAX  CounterBasedGauge64 
		MAX-ACCESS read-only 
		STATUS current
		DESCRIPTION  "RADIUS SMP Memory Allocation Failed" 
		::={ acosFwRadiusServerS 22 } 

		smpMemFreed OBJECT-TYPE
		SYNTAX  CounterBasedGauge64 
		MAX-ACCESS read-only 
		STATUS current
		DESCRIPTION  "RADIUS SMP Memory Freed" 
		::={ acosFwRadiusServerS 23 } 

		smpCreated OBJECT-TYPE
		SYNTAX  CounterBasedGauge64 
		MAX-ACCESS read-only 
		STATUS current
		DESCRIPTION  "RADIUS SMP Created" 
		::={ acosFwRadiusServerS 24 } 

		smpInRml OBJECT-TYPE
		SYNTAX  CounterBasedGauge64 
		MAX-ACCESS read-only 
		STATUS current
		DESCRIPTION  "RADIUS SMP in RML" 
		::={ acosFwRadiusServerS 25 } 

		smpDeleted OBJECT-TYPE
		SYNTAX  CounterBasedGauge64 
		MAX-ACCESS read-only 
		STATUS current
		DESCRIPTION  "RADIUS SMP Deleted" 
		::={ acosFwRadiusServerS 26 } 

		memAllocated OBJECT-TYPE
		SYNTAX  CounterBasedGauge64 
		MAX-ACCESS read-only 
		STATUS current
		DESCRIPTION  "RADIUS Memory Allocated" 
		::={ acosFwRadiusServerS 27 } 

		memAllocFailed OBJECT-TYPE
		SYNTAX  CounterBasedGauge64 
		MAX-ACCESS read-only 
		STATUS current
		DESCRIPTION  "RADIUS Memory Allocation Failed" 
		::={ acosFwRadiusServerS 28 } 

		memFreed OBJECT-TYPE
		SYNTAX  CounterBasedGauge64 
		MAX-ACCESS read-only 
		STATUS current
		DESCRIPTION  "RADIUS Memory Freed" 
		::={ acosFwRadiusServerS 29 } 

		haSyncCreateSent OBJECT-TYPE
		SYNTAX  CounterBasedGauge64 
		MAX-ACCESS read-only 
		STATUS current
		DESCRIPTION  "HA Record Sync Create Sent" 
		::={ acosFwRadiusServerS 30 } 

		haSyncDeleteSent OBJECT-TYPE
		SYNTAX  CounterBasedGauge64 
		MAX-ACCESS read-only 
		STATUS current
		DESCRIPTION  "HA Record Sync Delete Sent" 
		::={ acosFwRadiusServerS 31 } 

		haSyncCreateRecv OBJECT-TYPE
		SYNTAX  CounterBasedGauge64 
		MAX-ACCESS read-only 
		STATUS current
		DESCRIPTION  "HA Record Sync Create Received" 
		::={ acosFwRadiusServerS 32 } 

		haSyncDeleteRecv OBJECT-TYPE
		SYNTAX  CounterBasedGauge64 
		MAX-ACCESS read-only 
		STATUS current
		DESCRIPTION  "HA Record Sync Delete Received" 
		::={ acosFwRadiusServerS 33 } 

		acctOnFiltersFull OBJECT-TYPE
		SYNTAX  CounterBasedGauge64 
		MAX-ACCESS read-only 
		STATUS current
		DESCRIPTION  "RADIUS Acct On Request Ignored(Filters Full)" 
		::={ acosFwRadiusServerS 34 } 

		acctOnDupRequest OBJECT-TYPE
		SYNTAX  CounterBasedGauge64 
		MAX-ACCESS read-only 
		STATUS current
		DESCRIPTION  "Duplicate RADIUS Acct On Request" 
		::={ acosFwRadiusServerS 35 } 

		ipMismatchDelete OBJECT-TYPE
		SYNTAX  CounterBasedGauge64 
		MAX-ACCESS read-only 
		STATUS current
		DESCRIPTION  "Radius Entry IP Mismatch Delete" 
		::={ acosFwRadiusServerS 36 } 

		ipAddRaceDrop OBJECT-TYPE
		SYNTAX  CounterBasedGauge64 
		MAX-ACCESS read-only 
		STATUS current
		DESCRIPTION  "Radius Entry IP Add Race Drop" 
		::={ acosFwRadiusServerS 37 } 

		haSyncNoKeyVapDropped OBJECT-TYPE
		SYNTAX  CounterBasedGauge64 
		MAX-ACCESS read-only 
		STATUS current
		DESCRIPTION  "HA Record Sync No key dropped" 
		::={ acosFwRadiusServerS 38 } 

		interCardMsgFailDrop OBJECT-TYPE
		SYNTAX  CounterBasedGauge64 
		MAX-ACCESS read-only 
		STATUS current
		DESCRIPTION  "Inter-Card Message Fail Drop" 
		::={ acosFwRadiusServerS 39 } 

		radiusPacketsRedirected OBJECT-TYPE
		SYNTAX  CounterBasedGauge64 
		MAX-ACCESS read-only 
		STATUS current
		DESCRIPTION  "RADIUS packets redirected (SO)" 
		::={ acosFwRadiusServerS 40 } 

		radiusPacketsRedirectFailDropped OBJECT-TYPE
		SYNTAX  CounterBasedGauge64 
		MAX-ACCESS read-only 
		STATUS current
		DESCRIPTION  "RADIUS packets dropped due to redirect failure (SO)" 
		::={ acosFwRadiusServerS 41 } 

		radiusPacketsProcessLocal OBJECT-TYPE
		SYNTAX  CounterBasedGauge64 
		MAX-ACCESS read-only 
		STATUS current
		DESCRIPTION  "RADIUS packets processed locally without redirection (SO)" 
		::={ acosFwRadiusServerS 42 } 

		radiusPacketsDroppedNotLo OBJECT-TYPE
		SYNTAX  CounterBasedGauge64 
		MAX-ACCESS read-only 
		STATUS current
		DESCRIPTION  "RADIUS packets dropped dest not loopback (SO)" 
		::={ acosFwRadiusServerS 43 } 

		radiusInterCardDupRedir OBJECT-TYPE
		SYNTAX  CounterBasedGauge64 
		MAX-ACCESS read-only 
		STATUS current
		DESCRIPTION  "RADIUS packet dropped as redirected by other blade (SO)" 
		::={ acosFwRadiusServerS 44 } 

acosFwTcp                           OBJECT IDENTIFIER ::= { acosFw 19 }
acosFwTcpSynCookie                  OBJECT IDENTIFIER ::= { acosFwTcp 3 }
acosFwTcpSynCookieS                 OBJECT IDENTIFIER ::= { acosFwTcpSynCookie 1 }

		synAckSent OBJECT-TYPE
		SYNTAX  CounterBasedGauge64 
		MAX-ACCESS read-only 
		STATUS current
		DESCRIPTION  "SYN cookie SYN ACK sent" 
		::={ acosFwTcpSynCookieS 1 } 

		verificationPassed OBJECT-TYPE
		SYNTAX  CounterBasedGauge64 
		MAX-ACCESS read-only 
		STATUS current
		DESCRIPTION  "SYN cookie verification passed" 
		::={ acosFwTcpSynCookieS 2 } 

		verificationFailed OBJECT-TYPE
		SYNTAX  CounterBasedGauge64 
		MAX-ACCESS read-only 
		STATUS current
		DESCRIPTION  "SYN cookie verification failed" 
		::={ acosFwTcpSynCookieS 3 } 

		connSetupFailed OBJECT-TYPE
		SYNTAX  CounterBasedGauge64 
		MAX-ACCESS read-only 
		STATUS current
		DESCRIPTION  "SYN cookie connection setup failed" 
		::={ acosFwTcpSynCookieS 4 } 

acosFwDdosProtection                OBJECT IDENTIFIER ::= { acosFw 31 }
acosFwDdosProtectionS               OBJECT IDENTIFIER ::= { acosFwDdosProtection 1 }

		ddosEntriesTooMany OBJECT-TYPE
		SYNTAX  CounterBasedGauge64 
		MAX-ACCESS read-only 
		STATUS current
		DESCRIPTION  "Too many DDOS entries" 
		::={ acosFwDdosProtectionS 1 } 

		ddosEntryAdded OBJECT-TYPE
		SYNTAX  CounterBasedGauge64 
		MAX-ACCESS read-only 
		STATUS current
		DESCRIPTION  "DDOS entry added" 
		::={ acosFwDdosProtectionS 2 } 

		ddosEntryRemoved OBJECT-TYPE
		SYNTAX  CounterBasedGauge64 
		MAX-ACCESS read-only 
		STATUS current
		DESCRIPTION  "DDOS entry removed" 
		::={ acosFwDdosProtectionS 3 } 

		ddosEntryAddedToBgp OBJECT-TYPE
		SYNTAX  CounterBasedGauge64 
		MAX-ACCESS read-only 
		STATUS current
		DESCRIPTION  "DDoS Entry added to BGP" 
		::={ acosFwDdosProtectionS 4 } 

		ddosEntryRemovedFromBgp OBJECT-TYPE
		SYNTAX  CounterBasedGauge64 
		MAX-ACCESS read-only 
		STATUS current
		DESCRIPTION  "DDoS Entry Removed from BGP" 
		::={ acosFwDdosProtectionS 5 } 

		ddosEntryAddToBgpFailure OBJECT-TYPE
		SYNTAX  CounterBasedGauge64 
		MAX-ACCESS read-only 
		STATUS current
		DESCRIPTION  "DDoS Entry BGP add failures" 
		::={ acosFwDdosProtectionS 6 } 

		ddosEntryRemoveFromBgpFailure OBJECT-TYPE
		SYNTAX  CounterBasedGauge64 
		MAX-ACCESS read-only 
		STATUS current
		DESCRIPTION  "DDOS entry BGP remove failures" 
		::={ acosFwDdosProtectionS 7 } 

		ddosPacketDropped OBJECT-TYPE
		SYNTAX  CounterBasedGauge64 
		MAX-ACCESS read-only 
		STATUS current
		DESCRIPTION  "DDOS Packet Drop" 
		::={ acosFwDdosProtectionS 8 } 

acosFwPerInstance                   OBJECT IDENTIFIER ::= { acosFw 32 }
acosFwPerInstanceS                  OBJECT IDENTIFIER ::= { acosFwPerInstance 1 }
acosFwGtp                           OBJECT IDENTIFIER ::= { acosFw 25 }
acosFwGtpS                          OBJECT IDENTIFIER ::= { acosFwGtp 1 }

		outOfSessionMemory OBJECT-TYPE
		SYNTAX  CounterBasedGauge64 
		MAX-ACCESS read-only 
		STATUS current
		DESCRIPTION  "Out of Tunnel Memory" 
		::={ acosFwGtpS 1 } 

		gtpNoFwdRoute OBJECT-TYPE
		SYNTAX  CounterBasedGauge64 
		MAX-ACCESS read-only 
		STATUS current
		DESCRIPTION  "No Forward Route" 
		::={ acosFwGtpS 2 } 

		gtpNoRevRoute OBJECT-TYPE
		SYNTAX  CounterBasedGauge64 
		MAX-ACCESS read-only 
		STATUS current
		DESCRIPTION  "No Reverse Route" 
		::={ acosFwGtpS 3 } 

		gtpSmpCreated OBJECT-TYPE
		SYNTAX  CounterBasedGauge64 
		MAX-ACCESS read-only 
		STATUS current
		DESCRIPTION  "GTP SMP Created" 
		::={ acosFwGtpS 4 } 

		gtpSmpMarkedDeleted OBJECT-TYPE
		SYNTAX  CounterBasedGauge64 
		MAX-ACCESS read-only 
		STATUS current
		DESCRIPTION  "GTP SMP Marked Deleted" 
		::={ acosFwGtpS 5 } 

		gtpSmpDeleted OBJECT-TYPE
		SYNTAX  CounterBasedGauge64 
		MAX-ACCESS read-only 
		STATUS current
		DESCRIPTION  "GTP SMP Deleted" 
		::={ acosFwGtpS 6 } 

		smpCreationFailed OBJECT-TYPE
		SYNTAX  CounterBasedGauge64 
		MAX-ACCESS read-only 
		STATUS current
		DESCRIPTION  "GTP-U SMP Helper Session Creation Failed" 
		::={ acosFwGtpS 7 } 

		gtpSmpPathCreated OBJECT-TYPE
		SYNTAX  CounterBasedGauge64 
		MAX-ACCESS read-only 
		STATUS current
		DESCRIPTION  "GTP SMP PATH Created" 
		::={ acosFwGtpS 8 } 

		gtpSmpPathFreed OBJECT-TYPE
		SYNTAX  CounterBasedGauge64 
		MAX-ACCESS read-only 
		STATUS current
		DESCRIPTION  "GTP SMP PATH MEM freed" 
		::={ acosFwGtpS 9 } 

		gtpSmpPathAllocated OBJECT-TYPE
		SYNTAX  CounterBasedGauge64 
		MAX-ACCESS read-only 
		STATUS current
		DESCRIPTION  "GTP SMP PATH MEM allocated" 
		::={ acosFwGtpS 10 } 

		gtpSmpPathCreationFailed OBJECT-TYPE
		SYNTAX  CounterBasedGauge64 
		MAX-ACCESS read-only 
		STATUS current
		DESCRIPTION  "GTP SMP PATH creation Failed" 
		::={ acosFwGtpS 11 } 

		gtpSmpPathCheckFailed OBJECT-TYPE
		SYNTAX  CounterBasedGauge64 
		MAX-ACCESS read-only 
		STATUS current
		DESCRIPTION  "GTP SMP PATH check Failed" 
		::={ acosFwGtpS 136 } 

		gtpSmpCheckFailed OBJECT-TYPE
		SYNTAX  CounterBasedGauge64 
		MAX-ACCESS read-only 
		STATUS current
		DESCRIPTION  "GTP SMP check Failed" 
		::={ acosFwGtpS 137 } 

		gtpSmpSessionCountCheckFailed OBJECT-TYPE
		SYNTAX  CounterBasedGauge64 
		MAX-ACCESS read-only 
		STATUS current
		DESCRIPTION  "GTP-U session count is not in range of 0-11 in GTP-C SMP" 
		::={ acosFwGtpS 138 } 

		gtpCRefCountSmpExceeded OBJECT-TYPE
		SYNTAX  CounterBasedGauge64 
		MAX-ACCESS read-only 
		STATUS current
		DESCRIPTION  "GTP-C session count on C-smp exceeded 2" 
		::={ acosFwGtpS 139 } 

		gtpUSmpInRmlWithSess OBJECT-TYPE
		SYNTAX  CounterBasedGauge64 
		MAX-ACCESS read-only 
		STATUS current
		DESCRIPTION  "GTP-U smp is marked RML with U-session" 
		::={ acosFwGtpS 140 } 

		gtpUPktFwdConnCreate OBJECT-TYPE
		SYNTAX  CounterBasedGauge64 
		MAX-ACCESS read-only 
		STATUS current
		DESCRIPTION  "GTP-U pkt fwded while creating conn with gtp toggling" 
		::={ acosFwGtpS 141 } 

		gtpCPktFwdConnCreate OBJECT-TYPE
		SYNTAX  CounterBasedGauge64 
		MAX-ACCESS read-only 
		STATUS current
		DESCRIPTION  "GTP-C pkt fwded while creating conn with gtp toggling" 
		::={ acosFwGtpS 142 } 

		gtpEchoPktFwdConnCreate OBJECT-TYPE
		SYNTAX  CounterBasedGauge64 
		MAX-ACCESS read-only 
		STATUS current
		DESCRIPTION  "GTP-ECHO pkt fwded while creating conn with gtp toggling" 
		::={ acosFwGtpS 143 } 

		gtpTunnelRateLimitEntryCreateSuccess OBJECT-TYPE
		SYNTAX  CounterBasedGauge64 
		MAX-ACCESS read-only 
		STATUS current
		DESCRIPTION  "GTP Tunnel Level Rate Limit Entry Create Success" 
		::={ acosFwGtpS 12 } 

		gtpTunnelRateLimitEntryCreateFailure OBJECT-TYPE
		SYNTAX  CounterBasedGauge64 
		MAX-ACCESS read-only 
		STATUS current
		DESCRIPTION  "GTP Tunnel Level Rate Limit Entry Create Failure" 
		::={ acosFwGtpS 13 } 

		gtpTunnelRateLimitEntryDeleted OBJECT-TYPE
		SYNTAX  CounterBasedGauge64 
		MAX-ACCESS read-only 
		STATUS current
		DESCRIPTION  "GTP Tunnel Level Rate Limit Entry Deleted" 
		::={ acosFwGtpS 14 } 

		gtpRateLimitSmpCreated OBJECT-TYPE
		SYNTAX  CounterBasedGauge64 
		MAX-ACCESS read-only 
		STATUS current
		DESCRIPTION  "GTP Rate Limit SMP Created" 
		::={ acosFwGtpS 127 } 

		gtpRateLimitSmpFreed OBJECT-TYPE
		SYNTAX  CounterBasedGauge64 
		MAX-ACCESS read-only 
		STATUS current
		DESCRIPTION  "GTP Rate Limit SMP Freed" 
		::={ acosFwGtpS 128 } 

		gtpRateLimitSmpCreateFailure OBJECT-TYPE
		SYNTAX  CounterBasedGauge64 
		MAX-ACCESS read-only 
		STATUS current
		DESCRIPTION  "GTP Rate Limit SMP Create Failure" 
		::={ acosFwGtpS 129 } 

		gtpRateLimitT3CtrCreateFailure OBJECT-TYPE
		SYNTAX  CounterBasedGauge64 
		MAX-ACCESS read-only 
		STATUS current
		DESCRIPTION  "GTP Rate Limit Dynamic Counters Create Failure" 
		::={ acosFwGtpS 130 } 

		gtpRateLimitEntryCreateFailure OBJECT-TYPE
		SYNTAX  CounterBasedGauge64 
		MAX-ACCESS read-only 
		STATUS current
		DESCRIPTION  "GTP Rate Limit Entry Create Failure" 
		::={ acosFwGtpS 131 } 

		gtpEchoConnCreated OBJECT-TYPE
		SYNTAX  CounterBasedGauge64 
		MAX-ACCESS read-only 
		STATUS current
		DESCRIPTION  "GTP Echo Request Conn Created" 
		::={ acosFwGtpS 15 } 

		gtpEchoConnDeleted OBJECT-TYPE
		SYNTAX  CounterBasedGauge64 
		MAX-ACCESS read-only 
		STATUS current
		DESCRIPTION  "GTP Echo Request conn Deleted" 
		::={ acosFwGtpS 16 } 

		gtpNodeRestartEcho OBJECT-TYPE
		SYNTAX  CounterBasedGauge64 
		MAX-ACCESS read-only 
		STATUS current
		DESCRIPTION  "GTP Node Restoration due to Recovery IE in Echo" 
		::={ acosFwGtpS 17 } 

		gtpCEchoPathFailure OBJECT-TYPE
		SYNTAX  CounterBasedGauge64 
		MAX-ACCESS read-only 
		STATUS current
		DESCRIPTION  "GTP-C Path Failure due to Echo" 
		::={ acosFwGtpS 18 } 

		dropVldGtpEchoOutOfState OBJECT-TYPE
		SYNTAX  CounterBasedGauge64 
		MAX-ACCESS read-only 
		STATUS current
		DESCRIPTION  "GTP Echo Out of State Drop" 
		::={ acosFwGtpS 19 } 

		dropVldGtpEchoIeLenExceedMsgLen OBJECT-TYPE
		SYNTAX  CounterBasedGauge64 
		MAX-ACCESS read-only 
		STATUS current
		DESCRIPTION  "GTP Echo IE Length Exceeds Message Length" 
		::={ acosFwGtpS 135 } 

		gtpCreateSessionRequestRetransmit OBJECT-TYPE
		SYNTAX  CounterBasedGauge64 
		MAX-ACCESS read-only 
		STATUS current
		DESCRIPTION  "GTP-C Retransmitted Create Session Request" 
		::={ acosFwGtpS 20 } 

		gtpAddBearerRequestRetransmit OBJECT-TYPE
		SYNTAX  CounterBasedGauge64 
		MAX-ACCESS read-only 
		STATUS current
		DESCRIPTION  "GTP-C Retransmitted Add Bearer Request" 
		::={ acosFwGtpS 21 } 

		gtpDeleteSessionRequestRetransmit OBJECT-TYPE
		SYNTAX  CounterBasedGauge64 
		MAX-ACCESS read-only 
		STATUS current
		DESCRIPTION  "GTP-C Retransmitted Delete Session Request" 
		::={ acosFwGtpS 22 } 

		gtpHandoverRequestRetransmit OBJECT-TYPE
		SYNTAX  CounterBasedGauge64 
		MAX-ACCESS read-only 
		STATUS current
		DESCRIPTION  "GTP Handover Request Retransmit" 
		::={ acosFwGtpS 23 } 

		gtpDelBearerRequestRetransmit OBJECT-TYPE
		SYNTAX  CounterBasedGauge64 
		MAX-ACCESS read-only 
		STATUS current
		DESCRIPTION  "GTP-C Retransmitted Delete Bearer Request" 
		::={ acosFwGtpS 24 } 

		gtpAddBearerResponseRetransmit OBJECT-TYPE
		SYNTAX  CounterBasedGauge64 
		MAX-ACCESS read-only 
		STATUS current
		DESCRIPTION  "GTP-C Retransmitted Add Bearer Response" 
		::={ acosFwGtpS 25 } 

		gtpCreateSessionRequestRetxDrop OBJECT-TYPE
		SYNTAX  CounterBasedGauge64 
		MAX-ACCESS read-only 
		STATUS current
		DESCRIPTION  "GTP-C Retransmitted Create Session Request dropped" 
		::={ acosFwGtpS 134 } 

		gtpUOutOfStateDrop OBJECT-TYPE
		SYNTAX  CounterBasedGauge64 
		MAX-ACCESS read-only 
		STATUS current
		DESCRIPTION  "GTP-U Out of state Drop" 
		::={ acosFwGtpS 26 } 

		gtpCHandoverRequestOutOfStateDrop OBJECT-TYPE
		SYNTAX  CounterBasedGauge64 
		MAX-ACCESS read-only 
		STATUS current
		DESCRIPTION  "GTP-C Handover Request Out of state Drop" 
		::={ acosFwGtpS 27 } 

		gtpV1CNsapiNotFoundInDeleteReq OBJECT-TYPE
		SYNTAX  CounterBasedGauge64 
		MAX-ACCESS read-only 
		STATUS current
		DESCRIPTION  "GTPv1-C NSAPI Not Found in GTP Request" 
		::={ acosFwGtpS 28 } 

		gtpV2CBearerNotFoundInDeleteReq OBJECT-TYPE
		SYNTAX  CounterBasedGauge64 
		MAX-ACCESS read-only 
		STATUS current
		DESCRIPTION  "GTPv2-C Bearer Not Found in GTP Request" 
		::={ acosFwGtpS 29 } 

		gtpV2CBearerNotFoundInDeleteResp OBJECT-TYPE
		SYNTAX  CounterBasedGauge64 
		MAX-ACCESS read-only 
		STATUS current
		DESCRIPTION  "GTPv2-C Bearer Not Found in GTP Response" 
		::={ acosFwGtpS 30 } 

		gtpMultipleHandoverRequest OBJECT-TYPE
		SYNTAX  CounterBasedGauge64 
		MAX-ACCESS read-only 
		STATUS current
		DESCRIPTION  "GTP Multiple Handover Request" 
		::={ acosFwGtpS 31 } 

		gtpRrMessageDrop OBJECT-TYPE
		SYNTAX  CounterBasedGauge64 
		MAX-ACCESS read-only 
		STATUS current
		DESCRIPTION  "GTP Message Dropped in RR Mode" 
		::={ acosFwGtpS 32 } 

		gtpRrEchoMessageDcmsg OBJECT-TYPE
		SYNTAX  CounterBasedGauge64 
		MAX-ACCESS read-only 
		STATUS current
		DESCRIPTION  "GTP Echo Message Sent to home CPU in RR Mode" 
		::={ acosFwGtpS 33 } 

		gtpRrCMessageDcmsg OBJECT-TYPE
		SYNTAX  CounterBasedGauge64 
		MAX-ACCESS read-only 
		STATUS current
		DESCRIPTION  "GTP-C Message Sent to home CPU in RR Mode" 
		::={ acosFwGtpS 34 } 

		dropGtpFragOrJumboPkt OBJECT-TYPE
		SYNTAX  CounterBasedGauge64 
		MAX-ACCESS read-only 
		STATUS current
		DESCRIPTION  "GTP Fragmented or JUMBO packet Drop" 
		::={ acosFwGtpS 35 } 

		responseWithRejectCauseForwarded OBJECT-TYPE
		SYNTAX  CounterBasedGauge64 
		MAX-ACCESS read-only 
		STATUS current
		DESCRIPTION  "GTP-C Response with Reject Cause Forwarded" 
		::={ acosFwGtpS 36 } 

		gtpCMessageForwardedWithoutConn OBJECT-TYPE
		SYNTAX  CounterBasedGauge64 
		MAX-ACCESS read-only 
		STATUS current
		DESCRIPTION  "GTP-C Message Forwarded without Conn" 
		::={ acosFwGtpS 37 } 

		gtpV0CVerNotSupp OBJECT-TYPE
		SYNTAX  CounterBasedGauge64 
		MAX-ACCESS read-only 
		STATUS current
		DESCRIPTION  "GTPv0-C Version not supported indication" 
		::={ acosFwGtpS 38 } 

		gtpV1CVerNotSupp OBJECT-TYPE
		SYNTAX  CounterBasedGauge64 
		MAX-ACCESS read-only 
		STATUS current
		DESCRIPTION  "GTPv1-C Version not supported indication" 
		::={ acosFwGtpS 39 } 

		gtpV2CVerNotSupp OBJECT-TYPE
		SYNTAX  CounterBasedGauge64 
		MAX-ACCESS read-only 
		STATUS current
		DESCRIPTION  "GTPv2-C Version not supported indication" 
		::={ acosFwGtpS 40 } 

		gtpV1ExtnHdtNotif OBJECT-TYPE
		SYNTAX  CounterBasedGauge64 
		MAX-ACCESS read-only 
		STATUS current
		DESCRIPTION  "GTPV1 Supported Extension header notification" 
		::={ acosFwGtpS 41 } 

		gtpUErrorInd OBJECT-TYPE
		SYNTAX  CounterBasedGauge64 
		MAX-ACCESS read-only 
		STATUS current
		DESCRIPTION  "GTP-U Error Indication" 
		::={ acosFwGtpS 42 } 

		gtpCHandoverInProgressWithConn OBJECT-TYPE
		SYNTAX  CounterBasedGauge64 
		MAX-ACCESS read-only 
		STATUS current
		DESCRIPTION  "GTP-C mesg matching conn with HO In Progress" 
		::={ acosFwGtpS 144 } 

		gtpHoInProgressHandoverRequest OBJECT-TYPE
		SYNTAX  CounterBasedGauge64 
		MAX-ACCESS read-only 
		STATUS current
		DESCRIPTION  "GTP-C ho mesg matching conn with HO In Progress" 
		::={ acosFwGtpS 145 } 

		gtpCorrectConnHoInProgressHandoverRequest OBJECT-TYPE
		SYNTAX  CounterBasedGauge64 
		MAX-ACCESS read-only 
		STATUS current
		DESCRIPTION  "GTP-C ho mesg matching correct conn(reuse teid) with HO In Progress" 
		::={ acosFwGtpS 146 } 

		gtpWrongConnHoInProgressHandoverRequest OBJECT-TYPE
		SYNTAX  CounterBasedGauge64 
		MAX-ACCESS read-only 
		STATUS current
		DESCRIPTION  "GTP-C ho mesg matching wrong conn(new teid) with HO In Progress" 
		::={ acosFwGtpS 147 } 

		gtpHoInProgressHandoverResponse OBJECT-TYPE
		SYNTAX  CounterBasedGauge64 
		MAX-ACCESS read-only 
		STATUS current
		DESCRIPTION  "GTP-C ho response matching a conn with HO In Progress" 
		::={ acosFwGtpS 148 } 

		gtpHoInProgressCMesg OBJECT-TYPE
		SYNTAX  CounterBasedGauge64 
		MAX-ACCESS read-only 
		STATUS current
		DESCRIPTION  "GTP-C other than ho mesg matching conn with HO In Progress" 
		::={ acosFwGtpS 149 } 

		gtpUnsetHoFlagReuseTeid OBJECT-TYPE
		SYNTAX  CounterBasedGauge64 
		MAX-ACCESS read-only 
		STATUS current
		DESCRIPTION  "GTP-C SGW reuse teid with ho and unset ho flag" 
		::={ acosFwGtpS 150 } 

		gtpRefreshCConnReuseTeid OBJECT-TYPE
		SYNTAX  CounterBasedGauge64 
		MAX-ACCESS read-only 
		STATUS current
		DESCRIPTION  "GTP-C SGW reuse teid with ho and refresh old conn" 
		::={ acosFwGtpS 151 } 

		gtpRematchSmpMatchingConn OBJECT-TYPE
		SYNTAX  CounterBasedGauge64 
		MAX-ACCESS read-only 
		STATUS current
		DESCRIPTION  "GTP-C rematch smp with packet matching conn" 
		::={ acosFwGtpS 152 } 

		gtpWrongConnHandoverRequest OBJECT-TYPE
		SYNTAX  CounterBasedGauge64 
		MAX-ACCESS read-only 
		STATUS current
		DESCRIPTION  "GTP-C ho mesg matching wrong conn(new teid) with no HO flag" 
		::={ acosFwGtpS 153 } 

		gtpRefreshConnSetHoFlagLatest OBJECT-TYPE
		SYNTAX  CounterBasedGauge64 
		MAX-ACCESS read-only 
		STATUS current
		DESCRIPTION  "GTP-C SGW refresh old conn and set ho flag on latest smp" 
		::={ acosFwGtpS 154 } 

		gtpCProcessPktDrop OBJECT-TYPE
		SYNTAX  CounterBasedGauge64 
		MAX-ACCESS read-only 
		STATUS current
		DESCRIPTION  "GTP-C process pkt drop" 
		::={ acosFwGtpS 155 } 

		gtpCFwdPktDrop OBJECT-TYPE
		SYNTAX  CounterBasedGauge64 
		MAX-ACCESS read-only 
		STATUS current
		DESCRIPTION  "GTP-C fwd pkt drop" 
		::={ acosFwGtpS 156 } 

		gtpCRevPktDrop OBJECT-TYPE
		SYNTAX  CounterBasedGauge64 
		MAX-ACCESS read-only 
		STATUS current
		DESCRIPTION  "GTP-C rev pkt drop" 
		::={ acosFwGtpS 157 } 

		gtpCFwdV1Other OBJECT-TYPE
		SYNTAX  CounterBasedGauge64 
		MAX-ACCESS read-only 
		STATUS current
		DESCRIPTION  "GTP-C fwd v1 other messages" 
		::={ acosFwGtpS 158 } 

		gtpCFwdV2Other OBJECT-TYPE
		SYNTAX  CounterBasedGauge64 
		MAX-ACCESS read-only 
		STATUS current
		DESCRIPTION  "GTP-C fwd v2 other messages" 
		::={ acosFwGtpS 159 } 

		gtpCRevV1Other OBJECT-TYPE
		SYNTAX  CounterBasedGauge64 
		MAX-ACCESS read-only 
		STATUS current
		DESCRIPTION  "GTP-C rev v1 other messages" 
		::={ acosFwGtpS 160 } 

		gtpCRevV2Other OBJECT-TYPE
		SYNTAX  CounterBasedGauge64 
		MAX-ACCESS read-only 
		STATUS current
		DESCRIPTION  "GTP-C rev v2 other messages" 
		::={ acosFwGtpS 161 } 

		gtpCGoingThruFwLookup OBJECT-TYPE
		SYNTAX  CounterBasedGauge64 
		MAX-ACCESS read-only 
		STATUS current
		DESCRIPTION  "GTP-C mesg going thru fw lookup can be resp or l5 mesg not matching smp" 
		::={ acosFwGtpS 162 } 

		gtpCConnCreatePktDrop OBJECT-TYPE
		SYNTAX  CounterBasedGauge64 
		MAX-ACCESS read-only 
		STATUS current
		DESCRIPTION  "GTP-C conn creation drop" 
		::={ acosFwGtpS 163 } 

		gtpCPktFwdConnCreateNoFteid OBJECT-TYPE
		SYNTAX  CounterBasedGauge64 
		MAX-ACCESS read-only 
		STATUS current
		DESCRIPTION  "GTP-C pkt fwded while creating conn when no FTEID" 
		::={ acosFwGtpS 164 } 

		gtpInterPuMstrToBldDcmsgFail OBJECT-TYPE
		SYNTAX  CounterBasedGauge64 
		MAX-ACCESS read-only 
		STATUS current
		DESCRIPTION  "GTP inter-PU dcmsg failed from Master to Blade" 
		::={ acosFwGtpS 165 } 

		gtpInterPuMstrToBldDcmsgSent OBJECT-TYPE
		SYNTAX  CounterBasedGauge64 
		MAX-ACCESS read-only 
		STATUS current
		DESCRIPTION  "GTP inter-PU Master to Blade dcmsg sent" 
		::={ acosFwGtpS 166 } 

		gtpInterPuMstrToBldDcmsgRecv OBJECT-TYPE
		SYNTAX  CounterBasedGauge64 
		MAX-ACCESS read-only 
		STATUS current
		DESCRIPTION  "GTP inter-PU dcmsg received on blade" 
		::={ acosFwGtpS 167 } 

		gtpInterPuMstrToBldQuerySent OBJECT-TYPE
		SYNTAX  CounterBasedGauge64 
		MAX-ACCESS read-only 
		STATUS current
		DESCRIPTION  "GTP inter-PU query sent from Master to Blade" 
		::={ acosFwGtpS 168 } 

		gtpInterPuMstrToBldQueryRecv OBJECT-TYPE
		SYNTAX  CounterBasedGauge64 
		MAX-ACCESS read-only 
		STATUS current
		DESCRIPTION  "GTP inter-PU GTP-C query received on Blade" 
		::={ acosFwGtpS 169 } 

		gtpInterPuMstrToBldQueryRespSent OBJECT-TYPE
		SYNTAX  CounterBasedGauge64 
		MAX-ACCESS read-only 
		STATUS current
		DESCRIPTION  "GTP inter-PU GTP-C query response sent from Master to Blade" 
		::={ acosFwGtpS 170 } 

		gtpInterPuBldToMstrDcmsgFail OBJECT-TYPE
		SYNTAX  CounterBasedGauge64 
		MAX-ACCESS read-only 
		STATUS current
		DESCRIPTION  "GTP inter-PU dcmsg failed from Blade to Master" 
		::={ acosFwGtpS 171 } 

		gtpInterPuBldToMstrDcmsgSent OBJECT-TYPE
		SYNTAX  CounterBasedGauge64 
		MAX-ACCESS read-only 
		STATUS current
		DESCRIPTION  "GTP inter-PU Blade to Master dcmsg sent" 
		::={ acosFwGtpS 172 } 

		gtpInterPuBldToMstrDcmsgRecv OBJECT-TYPE
		SYNTAX  CounterBasedGauge64 
		MAX-ACCESS read-only 
		STATUS current
		DESCRIPTION  "GTP inter-PU dcmsg received on Master" 
		::={ acosFwGtpS 173 } 

		gtpInterPuBldToMstrQuerySent OBJECT-TYPE
		SYNTAX  CounterBasedGauge64 
		MAX-ACCESS read-only 
		STATUS current
		DESCRIPTION  "GTP inter-PU query sent from Blade to Master" 
		::={ acosFwGtpS 174 } 

		gtpInterPuBldToMstrQueryRecv OBJECT-TYPE
		SYNTAX  CounterBasedGauge64 
		MAX-ACCESS read-only 
		STATUS current
		DESCRIPTION  "GTP inter-PU GTP-C query received on Master" 
		::={ acosFwGtpS 175 } 

		gtpInterPuBldToMstrQueryRespSent OBJECT-TYPE
		SYNTAX  CounterBasedGauge64 
		MAX-ACCESS read-only 
		STATUS current
		DESCRIPTION  "GTP inter-PU GTP-C query response sent from Blade to Master" 
		::={ acosFwGtpS 176 } 

		gtpMstrToBldQueryRespFail OBJECT-TYPE
		SYNTAX  CounterBasedGauge64 
		MAX-ACCESS read-only 
		STATUS current
		DESCRIPTION  "GTP inter-PU dcmsg of query response failed from Master to Blade" 
		::={ acosFwGtpS 177 } 

		gtpBldToMstrQueryRespFail OBJECT-TYPE
		SYNTAX  CounterBasedGauge64 
		MAX-ACCESS read-only 
		STATUS current
		DESCRIPTION  "GTP inter-PU dcmsg of query response failed from Blade to Master" 
		::={ acosFwGtpS 178 } 

		gtpV0CUplinkIngressPackets OBJECT-TYPE
		SYNTAX  CounterBasedGauge64 
		MAX-ACCESS read-only 
		STATUS current
		DESCRIPTION  "GTPv0-C Uplink Ingress Packets" 
		::={ acosFwGtpS 43 } 

		gtpV0CUplinkEgressPackets OBJECT-TYPE
		SYNTAX  CounterBasedGauge64 
		MAX-ACCESS read-only 
		STATUS current
		DESCRIPTION  "GTPv0-C Uplink Egress Packets" 
		::={ acosFwGtpS 44 } 

		gtpV0CDownlinkIngressPackets OBJECT-TYPE
		SYNTAX  CounterBasedGauge64 
		MAX-ACCESS read-only 
		STATUS current
		DESCRIPTION  "GTPv0-C Downlink Ingress Packets" 
		::={ acosFwGtpS 45 } 

		gtpV0CDownlinkEgressPackets OBJECT-TYPE
		SYNTAX  CounterBasedGauge64 
		MAX-ACCESS read-only 
		STATUS current
		DESCRIPTION  "GTPv0-C Downlink Egress Packets" 
		::={ acosFwGtpS 46 } 

		gtpV0CUplinkIngressBytes OBJECT-TYPE
		SYNTAX  CounterBasedGauge64 
		MAX-ACCESS read-only 
		STATUS current
		DESCRIPTION  "GTPv0-C Uplink Ingress Bytes" 
		::={ acosFwGtpS 47 } 

		gtpV0CUplinkEgressBytes OBJECT-TYPE
		SYNTAX  CounterBasedGauge64 
		MAX-ACCESS read-only 
		STATUS current
		DESCRIPTION  "GTPv0-C Uplink Egress Bytes" 
		::={ acosFwGtpS 48 } 

		gtpV0CDownlinkIngressBytes OBJECT-TYPE
		SYNTAX  CounterBasedGauge64 
		MAX-ACCESS read-only 
		STATUS current
		DESCRIPTION  "GTPv0-C Downlink Ingress Bytes" 
		::={ acosFwGtpS 49 } 

		gtpV0CDownlinkEgressBytes OBJECT-TYPE
		SYNTAX  CounterBasedGauge64 
		MAX-ACCESS read-only 
		STATUS current
		DESCRIPTION  "GTPv0-C Downlink Egress Bytes" 
		::={ acosFwGtpS 50 } 

		gtpV1CUplinkIngressPackets OBJECT-TYPE
		SYNTAX  CounterBasedGauge64 
		MAX-ACCESS read-only 
		STATUS current
		DESCRIPTION  "GTPv1-C Uplink Ingress Packets" 
		::={ acosFwGtpS 51 } 

		gtpV1CUplinkEgressPackets OBJECT-TYPE
		SYNTAX  CounterBasedGauge64 
		MAX-ACCESS read-only 
		STATUS current
		DESCRIPTION  "GTPv1-C Uplink Egress Packets" 
		::={ acosFwGtpS 52 } 

		gtpV1CDownlinkIngressPackets OBJECT-TYPE
		SYNTAX  CounterBasedGauge64 
		MAX-ACCESS read-only 
		STATUS current
		DESCRIPTION  "GTPv1-C Downlink Ingress Packets" 
		::={ acosFwGtpS 53 } 

		gtpV1CDownlinkEgressPackets OBJECT-TYPE
		SYNTAX  CounterBasedGauge64 
		MAX-ACCESS read-only 
		STATUS current
		DESCRIPTION  "GTPv1-C Downlink Egress Packets" 
		::={ acosFwGtpS 54 } 

		gtpV1CUplinkIngressBytes OBJECT-TYPE
		SYNTAX  CounterBasedGauge64 
		MAX-ACCESS read-only 
		STATUS current
		DESCRIPTION  "GTPv1-C Uplink Ingress Bytes" 
		::={ acosFwGtpS 55 } 

		gtpV1CUplinkEgressBytes OBJECT-TYPE
		SYNTAX  CounterBasedGauge64 
		MAX-ACCESS read-only 
		STATUS current
		DESCRIPTION  "GTPv1-C Uplink Egress Bytes" 
		::={ acosFwGtpS 56 } 

		gtpV1CDownlinkIngressBytes OBJECT-TYPE
		SYNTAX  CounterBasedGauge64 
		MAX-ACCESS read-only 
		STATUS current
		DESCRIPTION  "GTPv1-C Downlink Ingress Bytes" 
		::={ acosFwGtpS 57 } 

		gtpV1CDownlinkEgressBytes OBJECT-TYPE
		SYNTAX  CounterBasedGauge64 
		MAX-ACCESS read-only 
		STATUS current
		DESCRIPTION  "GTPv1-C Downlink Egress Bytes" 
		::={ acosFwGtpS 58 } 

		gtpV2CUplinkIngressPackets OBJECT-TYPE
		SYNTAX  CounterBasedGauge64 
		MAX-ACCESS read-only 
		STATUS current
		DESCRIPTION  "GTPv2-C Uplink Ingress Packets" 
		::={ acosFwGtpS 59 } 

		gtpV2CUplinkEgressPackets OBJECT-TYPE
		SYNTAX  CounterBasedGauge64 
		MAX-ACCESS read-only 
		STATUS current
		DESCRIPTION  "GTPv2-C Uplink Egress Packets" 
		::={ acosFwGtpS 60 } 

		gtpV2CDownlinkIngressPackets OBJECT-TYPE
		SYNTAX  CounterBasedGauge64 
		MAX-ACCESS read-only 
		STATUS current
		DESCRIPTION  "GTPv2-C Downlink Ingress Packets" 
		::={ acosFwGtpS 61 } 

		gtpV2CDownlinkEgressPackets OBJECT-TYPE
		SYNTAX  CounterBasedGauge64 
		MAX-ACCESS read-only 
		STATUS current
		DESCRIPTION  "GTPv2-C Downlink Egress Packets" 
		::={ acosFwGtpS 62 } 

		gtpV2CUplinkIngressBytes OBJECT-TYPE
		SYNTAX  CounterBasedGauge64 
		MAX-ACCESS read-only 
		STATUS current
		DESCRIPTION  "GTPv2-C Uplink Ingress Bytes" 
		::={ acosFwGtpS 63 } 

		gtpV2CUplinkEgressBytes OBJECT-TYPE
		SYNTAX  CounterBasedGauge64 
		MAX-ACCESS read-only 
		STATUS current
		DESCRIPTION  "GTPv2-C Uplink Egress Bytes" 
		::={ acosFwGtpS 64 } 

		gtpV2CDownlinkIngressBytes OBJECT-TYPE
		SYNTAX  CounterBasedGauge64 
		MAX-ACCESS read-only 
		STATUS current
		DESCRIPTION  "GTPv2-C Downlink Ingress Bytes" 
		::={ acosFwGtpS 65 } 

		gtpV2CDownlinkEgressBytes OBJECT-TYPE
		SYNTAX  CounterBasedGauge64 
		MAX-ACCESS read-only 
		STATUS current
		DESCRIPTION  "GTPv2-C Downlink Egress Bytes" 
		::={ acosFwGtpS 66 } 

		gtpUUplinkIngressPackets OBJECT-TYPE
		SYNTAX  CounterBasedGauge64 
		MAX-ACCESS read-only 
		STATUS current
		DESCRIPTION  "GTP-U Uplink Ingress Packets" 
		::={ acosFwGtpS 67 } 

		gtpUUplinkEgressPackets OBJECT-TYPE
		SYNTAX  CounterBasedGauge64 
		MAX-ACCESS read-only 
		STATUS current
		DESCRIPTION  "GTP-U Uplink Egress Packets" 
		::={ acosFwGtpS 68 } 

		gtpUDownlinkIngressPackets OBJECT-TYPE
		SYNTAX  CounterBasedGauge64 
		MAX-ACCESS read-only 
		STATUS current
		DESCRIPTION  "GTP-U Downlink Ingress Packets" 
		::={ acosFwGtpS 69 } 

		gtpUDownlinkEgressPackets OBJECT-TYPE
		SYNTAX  CounterBasedGauge64 
		MAX-ACCESS read-only 
		STATUS current
		DESCRIPTION  "GTP-U Downlink Egress Packets" 
		::={ acosFwGtpS 70 } 

		gtpUUplinkIngressBytes OBJECT-TYPE
		SYNTAX  CounterBasedGauge64 
		MAX-ACCESS read-only 
		STATUS current
		DESCRIPTION  "GTP-U Uplink Ingress Bytes" 
		::={ acosFwGtpS 71 } 

		gtpUUplinkEgressBytes OBJECT-TYPE
		SYNTAX  CounterBasedGauge64 
		MAX-ACCESS read-only 
		STATUS current
		DESCRIPTION  "GTP-U Uplink Egress Bytes" 
		::={ acosFwGtpS 72 } 

		gtpUDownlinkIngressBytes OBJECT-TYPE
		SYNTAX  CounterBasedGauge64 
		MAX-ACCESS read-only 
		STATUS current
		DESCRIPTION  "GTP-U Downlink Ingress Bytes" 
		::={ acosFwGtpS 73 } 

		gtpUDownlinkEgressBytes OBJECT-TYPE
		SYNTAX  CounterBasedGauge64 
		MAX-ACCESS read-only 
		STATUS current
		DESCRIPTION  "GTP-U Downlink Egress Bytes" 
		::={ acosFwGtpS 74 } 

		gtpV0CCreateSynced OBJECT-TYPE
		SYNTAX  CounterBasedGauge64 
		MAX-ACCESS read-only 
		STATUS current
		DESCRIPTION  "GTPv0-C Tunnel Create Synced" 
		::={ acosFwGtpS 75 } 

		gtpV1CCreateSynced OBJECT-TYPE
		SYNTAX  CounterBasedGauge64 
		MAX-ACCESS read-only 
		STATUS current
		DESCRIPTION  "GTPv1-C Tunnel Create Synced" 
		::={ acosFwGtpS 76 } 

		gtpV2CCreateSynced OBJECT-TYPE
		SYNTAX  CounterBasedGauge64 
		MAX-ACCESS read-only 
		STATUS current
		DESCRIPTION  "GTPv2-C Tunnel Create Synced" 
		::={ acosFwGtpS 77 } 

		gtpV0CDeleteSynced OBJECT-TYPE
		SYNTAX  CounterBasedGauge64 
		MAX-ACCESS read-only 
		STATUS current
		DESCRIPTION  "GTPv0-C Tunnel Delete Synced" 
		::={ acosFwGtpS 78 } 

		gtpV1CDeleteSynced OBJECT-TYPE
		SYNTAX  CounterBasedGauge64 
		MAX-ACCESS read-only 
		STATUS current
		DESCRIPTION  "GTPv1-C Tunnel Delete Synced" 
		::={ acosFwGtpS 79 } 

		gtpV2CDeleteSynced OBJECT-TYPE
		SYNTAX  CounterBasedGauge64 
		MAX-ACCESS read-only 
		STATUS current
		DESCRIPTION  "GTPv2-C Tunnel Delete Synced" 
		::={ acosFwGtpS 80 } 

		gtpV0CCreateSyncRx OBJECT-TYPE
		SYNTAX  CounterBasedGauge64 
		MAX-ACCESS read-only 
		STATUS current
		DESCRIPTION  "GTPv0-C Tunnel Create Sync Received on Standby" 
		::={ acosFwGtpS 81 } 

		gtpV1CCreateSyncRx OBJECT-TYPE
		SYNTAX  CounterBasedGauge64 
		MAX-ACCESS read-only 
		STATUS current
		DESCRIPTION  "GTPv1-C Tunnel Create Sync Received on Standby" 
		::={ acosFwGtpS 82 } 

		gtpV2CCreateSyncRx OBJECT-TYPE
		SYNTAX  CounterBasedGauge64 
		MAX-ACCESS read-only 
		STATUS current
		DESCRIPTION  "GTPv2-C Tunnel Create Sync Received on Standby" 
		::={ acosFwGtpS 83 } 

		gtpV0CDeleteSyncRx OBJECT-TYPE
		SYNTAX  CounterBasedGauge64 
		MAX-ACCESS read-only 
		STATUS current
		DESCRIPTION  "GTPv0-C Tunnel Delete Sync Received on Standby" 
		::={ acosFwGtpS 84 } 

		gtpV1CDeleteSyncRx OBJECT-TYPE
		SYNTAX  CounterBasedGauge64 
		MAX-ACCESS read-only 
		STATUS current
		DESCRIPTION  "GTPv1-C Tunnel Delete Sync Received on Standby" 
		::={ acosFwGtpS 85 } 

		gtpV2CDeleteSyncRx OBJECT-TYPE
		SYNTAX  CounterBasedGauge64 
		MAX-ACCESS read-only 
		STATUS current
		DESCRIPTION  "GTPv2-C Tunnel Delete Sync Received on Standby" 
		::={ acosFwGtpS 86 } 

		gtpHandoverSynced OBJECT-TYPE
		SYNTAX  CounterBasedGauge64 
		MAX-ACCESS read-only 
		STATUS current
		DESCRIPTION  "GTP Handover Synced" 
		::={ acosFwGtpS 87 } 

		gtpHandoverSyncRx OBJECT-TYPE
		SYNTAX  CounterBasedGauge64 
		MAX-ACCESS read-only 
		STATUS current
		DESCRIPTION  "GTP Handover Sync Received on Standby" 
		::={ acosFwGtpS 88 } 

		gtpSmpAddBearerSynced OBJECT-TYPE
		SYNTAX  CounterBasedGauge64 
		MAX-ACCESS read-only 
		STATUS current
		DESCRIPTION  "GTP SMP Add Bearer Synced" 
		::={ acosFwGtpS 89 } 

		gtpSmpDelBearerSynced OBJECT-TYPE
		SYNTAX  CounterBasedGauge64 
		MAX-ACCESS read-only 
		STATUS current
		DESCRIPTION  "GTP SMP Del Bearer Synced" 
		::={ acosFwGtpS 90 } 

		gtpSmpAdditionalBearerSynced OBJECT-TYPE
		SYNTAX  CounterBasedGauge64 
		MAX-ACCESS read-only 
		STATUS current
		DESCRIPTION  "GTP SMP Additional Bearer Synced" 
		::={ acosFwGtpS 122 } 

		gtpSmpAddBearerSyncRx OBJECT-TYPE
		SYNTAX  CounterBasedGauge64 
		MAX-ACCESS read-only 
		STATUS current
		DESCRIPTION  "GTP SMP Add Bearer Sync Received on Standby" 
		::={ acosFwGtpS 91 } 

		gtpSmpDelBearerSyncRx OBJECT-TYPE
		SYNTAX  CounterBasedGauge64 
		MAX-ACCESS read-only 
		STATUS current
		DESCRIPTION  "GTP SMP Del Bearer Sync Received on Standby" 
		::={ acosFwGtpS 92 } 

		gtpSmpAdditionalBearerSyncRx OBJECT-TYPE
		SYNTAX  CounterBasedGauge64 
		MAX-ACCESS read-only 
		STATUS current
		DESCRIPTION  "GTP SMP Additional Bearer Sync Received on Standby" 
		::={ acosFwGtpS 123 } 

		gtpAddBearerSyncNotRxOnStandby OBJECT-TYPE
		SYNTAX  CounterBasedGauge64 
		MAX-ACCESS read-only 
		STATUS current
		DESCRIPTION  "GTP Add Bearer Sync Not Received on Standby" 
		::={ acosFwGtpS 93 } 

		gtpAddBearerSyncWithPeriodicUpdateOnStandby OBJECT-TYPE
		SYNTAX  CounterBasedGauge64 
		MAX-ACCESS read-only 
		STATUS current
		DESCRIPTION  "GTP Bearer Added on Standby with Periodic Sync" 
		::={ acosFwGtpS 94 } 

		gtpDeleteBearerSyncWithPeriodicUpdateOnStandby OBJECT-TYPE
		SYNTAX  CounterBasedGauge64 
		MAX-ACCESS read-only 
		STATUS current
		DESCRIPTION  "GTP Bearer Deleted on Standy with Periodic Sync" 
		::={ acosFwGtpS 95 } 

		gtpV0CEchoCreateSynced OBJECT-TYPE
		SYNTAX  CounterBasedGauge64 
		MAX-ACCESS read-only 
		STATUS current
		DESCRIPTION  "GTPv0-C Echo Create Synced" 
		::={ acosFwGtpS 96 } 

		gtpV1CEchoCreateSynced OBJECT-TYPE
		SYNTAX  CounterBasedGauge64 
		MAX-ACCESS read-only 
		STATUS current
		DESCRIPTION  "GTPv1-C Echo Create Synced" 
		::={ acosFwGtpS 97 } 

		gtpV2CEchoCreateSynced OBJECT-TYPE
		SYNTAX  CounterBasedGauge64 
		MAX-ACCESS read-only 
		STATUS current
		DESCRIPTION  "GTPv2-C Echo Create Synced" 
		::={ acosFwGtpS 98 } 

		gtpV0CEchoCreateSyncRx OBJECT-TYPE
		SYNTAX  CounterBasedGauge64 
		MAX-ACCESS read-only 
		STATUS current
		DESCRIPTION  "GTPv0-C-Echo Create Sync Received on Standby" 
		::={ acosFwGtpS 99 } 

		gtpV1CEchoCreateSyncRx OBJECT-TYPE
		SYNTAX  CounterBasedGauge64 
		MAX-ACCESS read-only 
		STATUS current
		DESCRIPTION  "GTPv1-C-Echo Create Sync Received on Standby" 
		::={ acosFwGtpS 100 } 

		gtpV2CEchoCreateSyncRx OBJECT-TYPE
		SYNTAX  CounterBasedGauge64 
		MAX-ACCESS read-only 
		STATUS current
		DESCRIPTION  "GTPv2-C-Echo Create Sync Received on Standby" 
		::={ acosFwGtpS 101 } 

		gtpV0CEchoDelSynced OBJECT-TYPE
		SYNTAX  CounterBasedGauge64 
		MAX-ACCESS read-only 
		STATUS current
		DESCRIPTION  "GTPv0-C Echo Delete Synced" 
		::={ acosFwGtpS 102 } 

		gtpV1CEchoDelSynced OBJECT-TYPE
		SYNTAX  CounterBasedGauge64 
		MAX-ACCESS read-only 
		STATUS current
		DESCRIPTION  "GTPv1-C Echo Delete Synced" 
		::={ acosFwGtpS 103 } 

		gtpV2CEchoDelSynced OBJECT-TYPE
		SYNTAX  CounterBasedGauge64 
		MAX-ACCESS read-only 
		STATUS current
		DESCRIPTION  "GTPv2-C Echo Delete Synced" 
		::={ acosFwGtpS 104 } 

		gtpV0CEchoDelSyncRx OBJECT-TYPE
		SYNTAX  CounterBasedGauge64 
		MAX-ACCESS read-only 
		STATUS current
		DESCRIPTION  "GTPv0-C-Echo Delete Sync Received on Standby" 
		::={ acosFwGtpS 105 } 

		gtpV1CEchoDelSyncRx OBJECT-TYPE
		SYNTAX  CounterBasedGauge64 
		MAX-ACCESS read-only 
		STATUS current
		DESCRIPTION  "GTPv1-C-Echo Delete Sync Received on Standby" 
		::={ acosFwGtpS 106 } 

		gtpV2CEchoDelSyncRx OBJECT-TYPE
		SYNTAX  CounterBasedGauge64 
		MAX-ACCESS read-only 
		STATUS current
		DESCRIPTION  "GTPv2-C-Echo Delete Sync Received on Standby" 
		::={ acosFwGtpS 107 } 

		dropGtpConnCreationStandby OBJECT-TYPE
		SYNTAX  CounterBasedGauge64 
		MAX-ACCESS read-only 
		STATUS current
		DESCRIPTION  "GTP Conn creation on Standby Drop" 
		::={ acosFwGtpS 108 } 

		gtpUSyncedBeforeControl OBJECT-TYPE
		SYNTAX  CounterBasedGauge64 
		MAX-ACCESS read-only 
		STATUS current
		DESCRIPTION  "GTP-U Tunnel synced before corresponding GTP-C" 
		::={ acosFwGtpS 109 } 

		gtpCL5SyncedBeforeL3 OBJECT-TYPE
		SYNTAX  CounterBasedGauge64 
		MAX-ACCESS read-only 
		STATUS current
		DESCRIPTION  "GTP-C L5 conn synced before corresponding L3 GTP-C conn" 
		::={ acosFwGtpS 110 } 

		gtpSmpPathDelSynced OBJECT-TYPE
		SYNTAX  CounterBasedGauge64 
		MAX-ACCESS read-only 
		STATUS current
		DESCRIPTION  "GTP SMP path delete Synced" 
		::={ acosFwGtpS 111 } 

		gtpSmpPathDelSyncRx OBJECT-TYPE
		SYNTAX  CounterBasedGauge64 
		MAX-ACCESS read-only 
		STATUS current
		DESCRIPTION  "GTP SMP path delete Sync Received on Standby" 
		::={ acosFwGtpS 112 } 

		gtpNotEnabledOnStandby OBJECT-TYPE
		SYNTAX  CounterBasedGauge64 
		MAX-ACCESS read-only 
		STATUS current
		DESCRIPTION  "GTP Not Enabled on Standby" 
		::={ acosFwGtpS 125 } 

		gtpIpVersionV4V6 OBJECT-TYPE
		SYNTAX  CounterBasedGauge64 
		MAX-ACCESS read-only 
		STATUS current
		DESCRIPTION  "GTP IP versions of V4&V6 in FTEID" 
		::={ acosFwGtpS 113 } 

		dropGtpIpVersionMismatchFteid OBJECT-TYPE
		SYNTAX  CounterBasedGauge64 
		MAX-ACCESS read-only 
		STATUS current
		DESCRIPTION  "GTP IP version mismatch for req & response FTEIDs" 
		::={ acosFwGtpS 114 } 

		dropGtpIpVersionMismatchHoFteid OBJECT-TYPE
		SYNTAX  CounterBasedGauge64 
		MAX-ACCESS read-only 
		STATUS current
		DESCRIPTION  "GTP IP version mismatch in Handover SGW FTEID" 
		::={ acosFwGtpS 115 } 

		gtpUMessageLengthMismatch OBJECT-TYPE
		SYNTAX  CounterBasedGauge64 
		MAX-ACCESS read-only 
		STATUS current
		DESCRIPTION  "GTP-U Message Length Mismatch Across Layers" 
		::={ acosFwGtpS 116 } 

		gtpPathMessageLengthMismatch OBJECT-TYPE
		SYNTAX  CounterBasedGauge64 
		MAX-ACCESS read-only 
		STATUS current
		DESCRIPTION  "GTP-Path Message Length Mismatch Across Layers" 
		::={ acosFwGtpS 117 } 

		dropGtpMissingCondIeBearerCtx OBJECT-TYPE
		SYNTAX  CounterBasedGauge64 
		MAX-ACCESS read-only 
		STATUS current
		DESCRIPTION  "Missing conditional IE in bearer context Drop" 
		::={ acosFwGtpS 118 } 

		dropGtpBearerNotFoundInResp OBJECT-TYPE
		SYNTAX  CounterBasedGauge64 
		MAX-ACCESS read-only 
		STATUS current
		DESCRIPTION  "GTP Bearer not found in response" 
		::={ acosFwGtpS 119 } 

		gtpStatelessForward OBJECT-TYPE
		SYNTAX  CounterBasedGauge64 
		MAX-ACCESS read-only 
		STATUS current
		DESCRIPTION  "GTP Stateless Forward" 
		::={ acosFwGtpS 120 } 

		gtpL3ConnDeleted OBJECT-TYPE
		SYNTAX  CounterBasedGauge64 
		MAX-ACCESS read-only 
		STATUS current
		DESCRIPTION  "GTP L3 conn deleted" 
		::={ acosFwGtpS 121 } 

		gtpL5ConnCreated OBJECT-TYPE
		SYNTAX  CounterBasedGauge64 
		MAX-ACCESS read-only 
		STATUS current
		DESCRIPTION  "GTP L5 conn created" 
		::={ acosFwGtpS 124 } 

		gtpMonitorForward OBJECT-TYPE
		SYNTAX  CounterBasedGauge64 
		MAX-ACCESS read-only 
		STATUS current
		DESCRIPTION  "GTP messages forwarded via monitor mode" 
		::={ acosFwGtpS 126 } 

		gtpUInnerIpNotPresent OBJECT-TYPE
		SYNTAX  CounterBasedGauge64 
		MAX-ACCESS read-only 
		STATUS current
		DESCRIPTION  "GTP-U inner IP not present" 
		::={ acosFwGtpS 132 } 

		gtpExtHdrIncorrectLength OBJECT-TYPE
		SYNTAX  CounterBasedGauge64 
		MAX-ACCESS read-only 
		STATUS current
		DESCRIPTION  "GTP Extension header incorrect length" 
		::={ acosFwGtpS 133 } 

acosFwGtpApnPrefix                  OBJECT IDENTIFIER ::= { acosFwGtp 5 }
acosFwGtpApnPrefixS                 OBJECT IDENTIFIER ::= { acosFwGtpApnPrefix 1 }
acosFwGtpNetworkElement             OBJECT IDENTIFIER ::= { acosFwGtp 6 }
acosFwGtpNetworkElementS            OBJECT IDENTIFIER ::= { acosFwGtpNetworkElement 1 }
END

ACOS-GSLB-STATS-MIB DEFINITIONS ::= BEGIN
	IMPORTS
		DisplayString, PhysAddress
		FROM SNMPv2-TC
	InetAddressType
		FROM INET-ADDRESS-MIB
	acosRootStats
		FROM A10-AX-MIB
	MODULE-IDENTITY, OBJECT-TYPE, Counter32, Integer32, Counter64, OBJECT-IDENTITY, NOTIFICATION-TYPE
		FROM SNMPv2-SMI;
		acosGslb MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "Gslb OID for ACOS"
				::=  {  acosRootStats 119  }

acosGslbDns                         OBJECT IDENTIFIER ::= { acosGslb 3 }
acosGslbDnsS                        OBJECT IDENTIFIER ::= { acosGslbDns 1 }

		totalQuery OBJECT-TYPE
		SYNTAX  CounterBasedGauge64 
		MAX-ACCESS read-only 
		STATUS current
		DESCRIPTION  "Total number of DNS queries received" 
		::={ acosGslbDnsS 1 } 

		totalResponse OBJECT-TYPE
		SYNTAX  CounterBasedGauge64 
		MAX-ACCESS read-only 
		STATUS current
		DESCRIPTION  "Total number of DNS replies sent to clients" 
		::={ acosGslbDnsS 2 } 

		badPacketQuery OBJECT-TYPE
		SYNTAX  CounterBasedGauge64 
		MAX-ACCESS read-only 
		STATUS current
		DESCRIPTION  "Number of queries with incorrect data length" 
		::={ acosGslbDnsS 3 } 

		badPacketResponse OBJECT-TYPE
		SYNTAX  CounterBasedGauge64 
		MAX-ACCESS read-only 
		STATUS current
		DESCRIPTION  "Number of replies with incorrect data length" 
		::={ acosGslbDnsS 4 } 

		badHeaderQuery OBJECT-TYPE
		SYNTAX  CounterBasedGauge64 
		MAX-ACCESS read-only 
		STATUS current
		DESCRIPTION  "Number of queries with incorrect header" 
		::={ acosGslbDnsS 5 } 

		badHeaderResponse OBJECT-TYPE
		SYNTAX  CounterBasedGauge64 
		MAX-ACCESS read-only 
		STATUS current
		DESCRIPTION  "Number of replies with incorrect header" 
		::={ acosGslbDnsS 6 } 

		badFormatQuery OBJECT-TYPE
		SYNTAX  CounterBasedGauge64 
		MAX-ACCESS read-only 
		STATUS current
		DESCRIPTION  "Number of queries with incorrect format" 
		::={ acosGslbDnsS 7 } 

		badFormatResponse OBJECT-TYPE
		SYNTAX  CounterBasedGauge64 
		MAX-ACCESS read-only 
		STATUS current
		DESCRIPTION  "Number of replies with incorrect format" 
		::={ acosGslbDnsS 8 } 

		badServiceQuery OBJECT-TYPE
		SYNTAX  CounterBasedGauge64 
		MAX-ACCESS read-only 
		STATUS current
		DESCRIPTION  "Number of queries with unknown service" 
		::={ acosGslbDnsS 9 } 

		badServiceResponse OBJECT-TYPE
		SYNTAX  CounterBasedGauge64 
		MAX-ACCESS read-only 
		STATUS current
		DESCRIPTION  "Number of replies with unknown service" 
		::={ acosGslbDnsS 10 } 

		badClassQuery OBJECT-TYPE
		SYNTAX  CounterBasedGauge64 
		MAX-ACCESS read-only 
		STATUS current
		DESCRIPTION  "Number of queries with incorrect class" 
		::={ acosGslbDnsS 11 } 

		badClassResponse OBJECT-TYPE
		SYNTAX  CounterBasedGauge64 
		MAX-ACCESS read-only 
		STATUS current
		DESCRIPTION  "Number of replies with incorrect class" 
		::={ acosGslbDnsS 12 } 

		badTypeQuery OBJECT-TYPE
		SYNTAX  CounterBasedGauge64 
		MAX-ACCESS read-only 
		STATUS current
		DESCRIPTION  "Number of queries with incorrect type" 
		::={ acosGslbDnsS 13 } 

		badTypeResponse OBJECT-TYPE
		SYNTAX  CounterBasedGauge64 
		MAX-ACCESS read-only 
		STATUS current
		DESCRIPTION  "Number of replies with incorrect type" 
		::={ acosGslbDnsS 14 } 

		noAnswer OBJECT-TYPE
		SYNTAX  CounterBasedGauge64 
		MAX-ACCESS read-only 
		STATUS current
		DESCRIPTION  "Number of replies with unknown server IP" 
		::={ acosGslbDnsS 15 } 

		metricHealthCheck OBJECT-TYPE
		SYNTAX  CounterBasedGauge64 
		MAX-ACCESS read-only 
		STATUS current
		DESCRIPTION  "Metric Health Check Hit" 
		::={ acosGslbDnsS 16 } 

		metricWeightedIp OBJECT-TYPE
		SYNTAX  CounterBasedGauge64 
		MAX-ACCESS read-only 
		STATUS current
		DESCRIPTION  "Metric Weighted IP Hit" 
		::={ acosGslbDnsS 17 } 

		metricWeightedSite OBJECT-TYPE
		SYNTAX  CounterBasedGauge64 
		MAX-ACCESS read-only 
		STATUS current
		DESCRIPTION  "Metric Weighted Site Hit" 
		::={ acosGslbDnsS 18 } 

		metricCapacity OBJECT-TYPE
		SYNTAX  CounterBasedGauge64 
		MAX-ACCESS read-only 
		STATUS current
		DESCRIPTION  "Metric Capacity Hit" 
		::={ acosGslbDnsS 19 } 

		metricActiveServer OBJECT-TYPE
		SYNTAX  CounterBasedGauge64 
		MAX-ACCESS read-only 
		STATUS current
		DESCRIPTION  "Metric Active Server Hit" 
		::={ acosGslbDnsS 20 } 

		metricEasyRdt OBJECT-TYPE
		SYNTAX  CounterBasedGauge64 
		MAX-ACCESS read-only 
		STATUS current
		DESCRIPTION  "Metric Easy RDT Hit" 
		::={ acosGslbDnsS 21 } 

		metricActiveRdt OBJECT-TYPE
		SYNTAX  CounterBasedGauge64 
		MAX-ACCESS read-only 
		STATUS current
		DESCRIPTION  "Metric Active RDT Hit" 
		::={ acosGslbDnsS 22 } 

		metricGeographic OBJECT-TYPE
		SYNTAX  CounterBasedGauge64 
		MAX-ACCESS read-only 
		STATUS current
		DESCRIPTION  "Metric Geographic Hit" 
		::={ acosGslbDnsS 23 } 

		metricConnectionLoad OBJECT-TYPE
		SYNTAX  CounterBasedGauge64 
		MAX-ACCESS read-only 
		STATUS current
		DESCRIPTION  "Metric Connection Load Hit" 
		::={ acosGslbDnsS 24 } 

		metricNumberOfSessions OBJECT-TYPE
		SYNTAX  CounterBasedGauge64 
		MAX-ACCESS read-only 
		STATUS current
		DESCRIPTION  "Metric Number of Sessions Hit" 
		::={ acosGslbDnsS 25 } 

		metricActiveWeight OBJECT-TYPE
		SYNTAX  CounterBasedGauge64 
		MAX-ACCESS read-only 
		STATUS current
		DESCRIPTION  "Metric Active Weight Hit" 
		::={ acosGslbDnsS 26 } 

		metricAdminPreference OBJECT-TYPE
		SYNTAX  CounterBasedGauge64 
		MAX-ACCESS read-only 
		STATUS current
		DESCRIPTION  "Metric Admin Preference Hit" 
		::={ acosGslbDnsS 27 } 

		metricBandwidthQuality OBJECT-TYPE
		SYNTAX  CounterBasedGauge64 
		MAX-ACCESS read-only 
		STATUS current
		DESCRIPTION  "Metric Bandwidth Quality Hit" 
		::={ acosGslbDnsS 28 } 

		metricBandwidthCost OBJECT-TYPE
		SYNTAX  CounterBasedGauge64 
		MAX-ACCESS read-only 
		STATUS current
		DESCRIPTION  "Metric Bandwidth Cost Hit" 
		::={ acosGslbDnsS 29 } 

		metricUser OBJECT-TYPE
		SYNTAX  CounterBasedGauge64 
		MAX-ACCESS read-only 
		STATUS current
		DESCRIPTION  "Metric User Hit" 
		::={ acosGslbDnsS 30 } 

		metricLeastReponse OBJECT-TYPE
		SYNTAX  CounterBasedGauge64 
		MAX-ACCESS read-only 
		STATUS current
		DESCRIPTION  "Metric Least Reponse Hit" 
		::={ acosGslbDnsS 31 } 

		metricAdminIp OBJECT-TYPE
		SYNTAX  CounterBasedGauge64 
		MAX-ACCESS read-only 
		STATUS current
		DESCRIPTION  "Metric Admin IP Hit" 
		::={ acosGslbDnsS 32 } 

		metricRoundRobin OBJECT-TYPE
		SYNTAX  CounterBasedGauge64 
		MAX-ACCESS read-only 
		STATUS current
		DESCRIPTION  "Metric Round Robin Hit" 
		::={ acosGslbDnsS 33 } 

acosGslbServiceIp                   OBJECT IDENTIFIER ::= { acosGslb 4 }
acosGslbServiceIpS                  OBJECT IDENTIFIER ::= { acosGslbServiceIp 1 }

gslbServiceIpSTable OBJECT-TYPE
		SYNTAX SEQUENCE OF GslbServiceIpSEntry
		MAX-ACCESS not-accessible
		STATUS current
		::={ acosGslbServiceIpS 1 } 


	gslbServiceIpSEntry OBJECT-TYPE
		SYNTAX GslbServiceIpSEntry
		MAX-ACCESS not-accessible
		STATUS current
		INDEX {
			nodeName
		}
		::={ gslbServiceIpSTable 1 } 


	GslbServiceIpSEntry ::=
		SEQUENCE {
			nodeName DisplayString, 
			gslbServiceIpHits CounterBasedGauge64,
			recent CounterBasedGauge64
		}

			nodeName OBJECT-TYPE
			SYNTAX  DisplayString 
			MAX-ACCESS read-only 
			STATUS current
			DESCRIPTION  "Service-IP Name" 
			::={ gslbServiceIpSEntry 1 } 

			gslbServiceIpHits OBJECT-TYPE
			SYNTAX  CounterBasedGauge64 
			MAX-ACCESS read-only 
			STATUS current
			DESCRIPTION  "Number of times the service IP has been selected" 
			::={ gslbServiceIpSEntry 2 } 

			recent OBJECT-TYPE
			SYNTAX  CounterBasedGauge64 
			MAX-ACCESS read-only 
			STATUS current
			DESCRIPTION  "Recent hits" 
			::={ gslbServiceIpSEntry 3 } 

acosGslbSite                        OBJECT IDENTIFIER ::= { acosGslb 9 }
acosGslbSiteS                       OBJECT IDENTIFIER ::= { acosGslbSite 1 }

gslbSiteSTable OBJECT-TYPE
		SYNTAX SEQUENCE OF GslbSiteSEntry
		MAX-ACCESS not-accessible
		STATUS current
		::={ acosGslbSiteS 1 } 


	gslbSiteSEntry OBJECT-TYPE
		SYNTAX GslbSiteSEntry
		MAX-ACCESS not-accessible
		STATUS current
		INDEX {
			siteName
		}
		::={ gslbSiteSTable 1 } 


	GslbSiteSEntry ::=
		SEQUENCE {
			siteName DisplayString, 
			gslbSiteHits CounterBasedGauge64
		}

			siteName OBJECT-TYPE
			SYNTAX  DisplayString 
			MAX-ACCESS read-only 
			STATUS current
			DESCRIPTION  "Specify GSLB site name" 
			::={ gslbSiteSEntry 1 } 

			gslbSiteHits OBJECT-TYPE
			SYNTAX  CounterBasedGauge64 
			MAX-ACCESS read-only 
			STATUS current
			DESCRIPTION  "Number of times the site was selected" 
			::={ gslbSiteSEntry 2 } 

acosGslbZone                        OBJECT IDENTIFIER ::= { acosGslb 11 }
acosGslbZoneS                       OBJECT IDENTIFIER ::= { acosGslbZone 1 }

gslbZoneSTable OBJECT-TYPE
		SYNTAX SEQUENCE OF GslbZoneSEntry
		MAX-ACCESS not-accessible
		STATUS current
		::={ acosGslbZoneS 1 } 


	gslbZoneSEntry OBJECT-TYPE
		SYNTAX GslbZoneSEntry
		MAX-ACCESS not-accessible
		STATUS current
		INDEX {
			name
		}
		::={ gslbZoneSTable 1 } 


	GslbZoneSEntry ::=
		SEQUENCE {
			name DisplayString, 
			receivedQuery CounterBasedGauge64,
			sentResponse CounterBasedGauge64,
			proxyModeResponse CounterBasedGauge64,
			cacheModeResponse CounterBasedGauge64,
			serverModeResponse CounterBasedGauge64,
			stickyModeResponse CounterBasedGauge64,
			backupModeResponse CounterBasedGauge64
		}

			name OBJECT-TYPE
			SYNTAX  DisplayString 
			MAX-ACCESS read-only 
			STATUS current
			DESCRIPTION  "Specify the name for the DNS zone" 
			::={ gslbZoneSEntry 1 } 

			receivedQuery OBJECT-TYPE
			SYNTAX  CounterBasedGauge64 
			MAX-ACCESS read-only 
			STATUS current
			DESCRIPTION  "Total Number of DNS queries received for the zone" 
			::={ gslbZoneSEntry 2 } 

			sentResponse OBJECT-TYPE
			SYNTAX  CounterBasedGauge64 
			MAX-ACCESS read-only 
			STATUS current
			DESCRIPTION  "Total Number of DNS replies sent to clients for the zone" 
			::={ gslbZoneSEntry 3 } 

			proxyModeResponse OBJECT-TYPE
			SYNTAX  CounterBasedGauge64 
			MAX-ACCESS read-only 
			STATUS current
			DESCRIPTION  "Total Number of DNS replies sent to clients by the ACOS device as a DNS proxy for the zone" 
			::={ gslbZoneSEntry 4 } 

			cacheModeResponse OBJECT-TYPE
			SYNTAX  CounterBasedGauge64 
			MAX-ACCESS read-only 
			STATUS current
			DESCRIPTION  "Total Number of cached DNS replies sent to clients by the ACOS device for the zone. (This statistic applies only if the DNS cac" 
			::={ gslbZoneSEntry 5 } 

			serverModeResponse OBJECT-TYPE
			SYNTAX  CounterBasedGauge64 
			MAX-ACCESS read-only 
			STATUS current
			DESCRIPTION  "Total Number of DNS replies sent to clients by the ACOS device as a DNS server for the zone. (This statistic applies only if th" 
			::={ gslbZoneSEntry 6 } 

			stickyModeResponse OBJECT-TYPE
			SYNTAX  CounterBasedGauge64 
			MAX-ACCESS read-only 
			STATUS current
			DESCRIPTION  "Total Number of DNS replies sent to clients by the ACOS device to keep the clients on the same site. (This statistic applies on" 
			::={ gslbZoneSEntry 7 } 

			backupModeResponse OBJECT-TYPE
			SYNTAX  CounterBasedGauge64 
			MAX-ACCESS read-only 
			STATUS current
			DESCRIPTION  "Total Number of DNS replies sent to clients by the ACOS device in backup mode" 
			::={ gslbZoneSEntry 8 } 

END

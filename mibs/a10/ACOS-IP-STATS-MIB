ACOS-IP-STATS-MIB DEFINITIONS ::= BEGIN
	IMPORTS
		DisplayString, PhysAddress
		FROM SNMPv2-TC
	InetAddressType
		FROM INET-ADDRESS-MIB
	acosRootStats
		FROM A10-AX-MIB
	MODULE-IDENTITY, OBJECT-TYPE, Counter32, Integer32, Counter64, OBJECT-IDENTITY, NOTIFICATION-TYPE
		FROM SNMPv2-SMI;
		acosIp MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "Ip OID for ACOS"
				::=  {  acosRootStats 55  }

acosIpAnomalyDrop                   OBJECT IDENTIFIER ::= { acosIp 5 }
acosIpAnomalyDropS                  OBJECT IDENTIFIER ::= { acosIpAnomalyDrop 1 }

		land OBJECT-TYPE
		SYNTAX  CounterBasedGauge64 
		MAX-ACCESS read-only 
		STATUS current
		DESCRIPTION  "Land Attack Drop" 
		::={ acosIpAnomalyDropS 1 } 

		empFrg OBJECT-TYPE
		SYNTAX  CounterBasedGauge64 
		MAX-ACCESS read-only 
		STATUS current
		DESCRIPTION  "Empty Fragment Drop" 
		::={ acosIpAnomalyDropS 2 } 

		empMicFrg OBJECT-TYPE
		SYNTAX  CounterBasedGauge64 
		MAX-ACCESS read-only 
		STATUS current
		DESCRIPTION  "Micro Fragment Drop" 
		::={ acosIpAnomalyDropS 3 } 

		opt OBJECT-TYPE
		SYNTAX  CounterBasedGauge64 
		MAX-ACCESS read-only 
		STATUS current
		DESCRIPTION  "IPv4 Options Drop" 
		::={ acosIpAnomalyDropS 4 } 

		frg OBJECT-TYPE
		SYNTAX  CounterBasedGauge64 
		MAX-ACCESS read-only 
		STATUS current
		DESCRIPTION  "IPv4 Fragment Drop" 
		::={ acosIpAnomalyDropS 5 } 

		badIpHdrlen OBJECT-TYPE
		SYNTAX  CounterBasedGauge64 
		MAX-ACCESS read-only 
		STATUS current
		DESCRIPTION  "Bad IP Header Len Drop" 
		::={ acosIpAnomalyDropS 6 } 

		badIpFlg OBJECT-TYPE
		SYNTAX  CounterBasedGauge64 
		MAX-ACCESS read-only 
		STATUS current
		DESCRIPTION  "Bad IP Flags Drop" 
		::={ acosIpAnomalyDropS 7 } 

		badIpTtl OBJECT-TYPE
		SYNTAX  CounterBasedGauge64 
		MAX-ACCESS read-only 
		STATUS current
		DESCRIPTION  "Bad IP TTL Drop" 
		::={ acosIpAnomalyDropS 8 } 

		noIpPayload OBJECT-TYPE
		SYNTAX  CounterBasedGauge64 
		MAX-ACCESS read-only 
		STATUS current
		DESCRIPTION  "No IP Payload drop" 
		::={ acosIpAnomalyDropS 9 } 

		overIpPayload OBJECT-TYPE
		SYNTAX  CounterBasedGauge64 
		MAX-ACCESS read-only 
		STATUS current
		DESCRIPTION  "Oversize IP Payload Drop" 
		::={ acosIpAnomalyDropS 10 } 

		badIpPayloadLen OBJECT-TYPE
		SYNTAX  CounterBasedGauge64 
		MAX-ACCESS read-only 
		STATUS current
		DESCRIPTION  "Bad IP Payload Len Drop" 
		::={ acosIpAnomalyDropS 11 } 

		badIpFrgOffset OBJECT-TYPE
		SYNTAX  CounterBasedGauge64 
		MAX-ACCESS read-only 
		STATUS current
		DESCRIPTION  "Bad IP Fragment Offset Drop" 
		::={ acosIpAnomalyDropS 12 } 

		csum OBJECT-TYPE
		SYNTAX  CounterBasedGauge64 
		MAX-ACCESS read-only 
		STATUS current
		DESCRIPTION  "Bad IP Checksum Drop" 
		::={ acosIpAnomalyDropS 13 } 

		pod OBJECT-TYPE
		SYNTAX  CounterBasedGauge64 
		MAX-ACCESS read-only 
		STATUS current
		DESCRIPTION  "ICMP Ping of Death Drop" 
		::={ acosIpAnomalyDropS 14 } 

		badTcpUrgOffset OBJECT-TYPE
		SYNTAX  CounterBasedGauge64 
		MAX-ACCESS read-only 
		STATUS current
		DESCRIPTION  "TCP Bad Urgent Offset Drop" 
		::={ acosIpAnomalyDropS 15 } 

		tcpShtHdr OBJECT-TYPE
		SYNTAX  CounterBasedGauge64 
		MAX-ACCESS read-only 
		STATUS current
		DESCRIPTION  "TCP Short Header Drop" 
		::={ acosIpAnomalyDropS 16 } 

		tcpBadIplen OBJECT-TYPE
		SYNTAX  CounterBasedGauge64 
		MAX-ACCESS read-only 
		STATUS current
		DESCRIPTION  "TCP Bad IP Length Drop" 
		::={ acosIpAnomalyDropS 17 } 

		tcpNullFrg OBJECT-TYPE
		SYNTAX  CounterBasedGauge64 
		MAX-ACCESS read-only 
		STATUS current
		DESCRIPTION  "TCP Null Flags Drop" 
		::={ acosIpAnomalyDropS 18 } 

		tcpNullScan OBJECT-TYPE
		SYNTAX  CounterBasedGauge64 
		MAX-ACCESS read-only 
		STATUS current
		DESCRIPTION  "TCP Null Scan Drop" 
		::={ acosIpAnomalyDropS 19 } 

		tcpSynFin OBJECT-TYPE
		SYNTAX  CounterBasedGauge64 
		MAX-ACCESS read-only 
		STATUS current
		DESCRIPTION  "TCP Syn and Fin Drop" 
		::={ acosIpAnomalyDropS 20 } 

		tcpXmas OBJECT-TYPE
		SYNTAX  CounterBasedGauge64 
		MAX-ACCESS read-only 
		STATUS current
		DESCRIPTION  "TCP XMAS Flags Drop" 
		::={ acosIpAnomalyDropS 21 } 

		tcpXmasScan OBJECT-TYPE
		SYNTAX  CounterBasedGauge64 
		MAX-ACCESS read-only 
		STATUS current
		DESCRIPTION  "TCP XMAS Scan Drop" 
		::={ acosIpAnomalyDropS 22 } 

		tcpSynFrg OBJECT-TYPE
		SYNTAX  CounterBasedGauge64 
		MAX-ACCESS read-only 
		STATUS current
		DESCRIPTION  "TCP Syn Fragment Drop" 
		::={ acosIpAnomalyDropS 23 } 

		tcpFrgHdr OBJECT-TYPE
		SYNTAX  CounterBasedGauge64 
		MAX-ACCESS read-only 
		STATUS current
		DESCRIPTION  "TCP Fragmented Header Drop" 
		::={ acosIpAnomalyDropS 24 } 

		tcpBadCsum OBJECT-TYPE
		SYNTAX  CounterBasedGauge64 
		MAX-ACCESS read-only 
		STATUS current
		DESCRIPTION  "TCP Bad Checksum Drop" 
		::={ acosIpAnomalyDropS 25 } 

		udpSrtHdr OBJECT-TYPE
		SYNTAX  CounterBasedGauge64 
		MAX-ACCESS read-only 
		STATUS current
		DESCRIPTION  "UDP Short Header Drop" 
		::={ acosIpAnomalyDropS 26 } 

		udpBadLen OBJECT-TYPE
		SYNTAX  CounterBasedGauge64 
		MAX-ACCESS read-only 
		STATUS current
		DESCRIPTION  "UDP Bad Length Drop" 
		::={ acosIpAnomalyDropS 27 } 

		udpKerbFrg OBJECT-TYPE
		SYNTAX  CounterBasedGauge64 
		MAX-ACCESS read-only 
		STATUS current
		DESCRIPTION  "UDP Kerberos Fragment Drop" 
		::={ acosIpAnomalyDropS 28 } 

		udpPortLb OBJECT-TYPE
		SYNTAX  CounterBasedGauge64 
		MAX-ACCESS read-only 
		STATUS current
		DESCRIPTION  "UDP Port Loopback Drop" 
		::={ acosIpAnomalyDropS 29 } 

		udpBadCsum OBJECT-TYPE
		SYNTAX  CounterBasedGauge64 
		MAX-ACCESS read-only 
		STATUS current
		DESCRIPTION  "UDP Bad Checksum Drop" 
		::={ acosIpAnomalyDropS 30 } 

		runtIpHdr OBJECT-TYPE
		SYNTAX  CounterBasedGauge64 
		MAX-ACCESS read-only 
		STATUS current
		DESCRIPTION  "Runt IP Header Drop" 
		::={ acosIpAnomalyDropS 31 } 

		runtTcpUdpHdr OBJECT-TYPE
		SYNTAX  CounterBasedGauge64 
		MAX-ACCESS read-only 
		STATUS current
		DESCRIPTION  "Runt TCP/UDP Header Drop" 
		::={ acosIpAnomalyDropS 32 } 

		ipipTnlMsmtch OBJECT-TYPE
		SYNTAX  CounterBasedGauge64 
		MAX-ACCESS read-only 
		STATUS current
		DESCRIPTION  "IP-over-IP Tunnel Mismatch Drop" 
		::={ acosIpAnomalyDropS 33 } 

		tcpOptErr OBJECT-TYPE
		SYNTAX  CounterBasedGauge64 
		MAX-ACCESS read-only 
		STATUS current
		DESCRIPTION  "TCP Option Error Drop" 
		::={ acosIpAnomalyDropS 34 } 

		ipipTnlErr OBJECT-TYPE
		SYNTAX  CounterBasedGauge64 
		MAX-ACCESS read-only 
		STATUS current
		DESCRIPTION  "IP-over-IP Tunnel Error Drop" 
		::={ acosIpAnomalyDropS 35 } 

		vxlanErr OBJECT-TYPE
		SYNTAX  CounterBasedGauge64 
		MAX-ACCESS read-only 
		STATUS current
		DESCRIPTION  "VXLAN Tunnel Error Drop" 
		::={ acosIpAnomalyDropS 36 } 

		nvgreErr OBJECT-TYPE
		SYNTAX  CounterBasedGauge64 
		MAX-ACCESS read-only 
		STATUS current
		DESCRIPTION  "GRE Tunnel Error Drop" 
		::={ acosIpAnomalyDropS 37 } 

		grePptpErr OBJECT-TYPE
		SYNTAX  CounterBasedGauge64 
		MAX-ACCESS read-only 
		STATUS current
		DESCRIPTION  "GRE PPTP Error Drop" 
		::={ acosIpAnomalyDropS 38 } 

acosIpFrag                          OBJECT IDENTIFIER ::= { acosIp 7 }
acosIpFragS                         OBJECT IDENTIFIER ::= { acosIpFrag 1 }

		ipFragSessionInsert OBJECT-TYPE
		SYNTAX  CounterBasedGauge64 
		MAX-ACCESS read-only 
		STATUS current
		DESCRIPTION  "Session Inserted" 
		::={ acosIpFragS 1 } 

		ipFragSessionExpired OBJECT-TYPE
		SYNTAX  CounterBasedGauge64 
		MAX-ACCESS read-only 
		STATUS current
		DESCRIPTION  "Session Expired" 
		::={ acosIpFragS 2 } 

		ipFragIcmpRcv OBJECT-TYPE
		SYNTAX  CounterBasedGauge64 
		MAX-ACCESS read-only 
		STATUS current
		DESCRIPTION  "ICMP Received" 
		::={ acosIpFragS 3 } 

		ipFragIcmpv6Rcv OBJECT-TYPE
		SYNTAX  CounterBasedGauge64 
		MAX-ACCESS read-only 
		STATUS current
		DESCRIPTION  "ICMPv6 Received" 
		::={ acosIpFragS 4 } 

		ipFragUdpRcv OBJECT-TYPE
		SYNTAX  CounterBasedGauge64 
		MAX-ACCESS read-only 
		STATUS current
		DESCRIPTION  "UDP Received" 
		::={ acosIpFragS 5 } 

		ipFragTcpRcv OBJECT-TYPE
		SYNTAX  CounterBasedGauge64 
		MAX-ACCESS read-only 
		STATUS current
		DESCRIPTION  "TCP Received" 
		::={ acosIpFragS 6 } 

		ipFragIpipRcv OBJECT-TYPE
		SYNTAX  CounterBasedGauge64 
		MAX-ACCESS read-only 
		STATUS current
		DESCRIPTION  "IP-in-IP Received" 
		::={ acosIpFragS 7 } 

		ipFragIpv6ipRcv OBJECT-TYPE
		SYNTAX  CounterBasedGauge64 
		MAX-ACCESS read-only 
		STATUS current
		DESCRIPTION  "IPv6-in-IP Received" 
		::={ acosIpFragS 8 } 

		ipFragOtherRcv OBJECT-TYPE
		SYNTAX  CounterBasedGauge64 
		MAX-ACCESS read-only 
		STATUS current
		DESCRIPTION  "Other Received" 
		::={ acosIpFragS 9 } 

		ipFragIcmpDropped OBJECT-TYPE
		SYNTAX  CounterBasedGauge64 
		MAX-ACCESS read-only 
		STATUS current
		DESCRIPTION  "ICMP Dropped" 
		::={ acosIpFragS 10 } 

		ipFragIcmpv6Dropped OBJECT-TYPE
		SYNTAX  CounterBasedGauge64 
		MAX-ACCESS read-only 
		STATUS current
		DESCRIPTION  "ICMPv6 Dropped" 
		::={ acosIpFragS 11 } 

		ipFragUdpDropped OBJECT-TYPE
		SYNTAX  CounterBasedGauge64 
		MAX-ACCESS read-only 
		STATUS current
		DESCRIPTION  "UDP Dropped" 
		::={ acosIpFragS 12 } 

		ipFragTcpDropped OBJECT-TYPE
		SYNTAX  CounterBasedGauge64 
		MAX-ACCESS read-only 
		STATUS current
		DESCRIPTION  "TCP Dropped" 
		::={ acosIpFragS 13 } 

		ipFragIpipDroped OBJECT-TYPE
		SYNTAX  CounterBasedGauge64 
		MAX-ACCESS read-only 
		STATUS current
		DESCRIPTION  "IP-in-IP Dropped" 
		::={ acosIpFragS 14 } 

		ipFragIpv6ipDropped OBJECT-TYPE
		SYNTAX  CounterBasedGauge64 
		MAX-ACCESS read-only 
		STATUS current
		DESCRIPTION  "IPv6-in-IP Dropped" 
		::={ acosIpFragS 15 } 

		ipFragOtherDropped OBJECT-TYPE
		SYNTAX  CounterBasedGauge64 
		MAX-ACCESS read-only 
		STATUS current
		DESCRIPTION  "Other Dropped" 
		::={ acosIpFragS 16 } 

		ipFragOverlapError OBJECT-TYPE
		SYNTAX  CounterBasedGauge64 
		MAX-ACCESS read-only 
		STATUS current
		DESCRIPTION  "Overlapping Fragment Dropped" 
		::={ acosIpFragS 17 } 

		iipFragBadIpLen OBJECT-TYPE
		SYNTAX  CounterBasedGauge64 
		MAX-ACCESS read-only 
		STATUS current
		DESCRIPTION  "Bad IP Length" 
		::={ acosIpFragS 18 } 

		ipFragTooSmall OBJECT-TYPE
		SYNTAX  CounterBasedGauge64 
		MAX-ACCESS read-only 
		STATUS current
		DESCRIPTION  "Fragment Too Small Drop" 
		::={ acosIpFragS 19 } 

		ipFragFirstTcpTooSmall OBJECT-TYPE
		SYNTAX  CounterBasedGauge64 
		MAX-ACCESS read-only 
		STATUS current
		DESCRIPTION  "First TCP Fragment Too Small Drop" 
		::={ acosIpFragS 20 } 

		ipFragFirstL4TooSmall OBJECT-TYPE
		SYNTAX  CounterBasedGauge64 
		MAX-ACCESS read-only 
		STATUS current
		DESCRIPTION  "First L4 Fragment Too Small Drop" 
		::={ acosIpFragS 21 } 

		ipFragTotalSessionsExceeded OBJECT-TYPE
		SYNTAX  CounterBasedGauge64 
		MAX-ACCESS read-only 
		STATUS current
		DESCRIPTION  "Total Sessions Exceeded Drop" 
		::={ acosIpFragS 22 } 

		ipFragNoSessionMemory OBJECT-TYPE
		SYNTAX  CounterBasedGauge64 
		MAX-ACCESS read-only 
		STATUS current
		DESCRIPTION  "Out of Session Memory" 
		::={ acosIpFragS 23 } 

		ipFragFastAgingSet OBJECT-TYPE
		SYNTAX  CounterBasedGauge64 
		MAX-ACCESS read-only 
		STATUS current
		DESCRIPTION  "Fragmentation Fast Aging Set" 
		::={ acosIpFragS 24 } 

		ipFragFastAgingUnset OBJECT-TYPE
		SYNTAX  CounterBasedGauge64 
		MAX-ACCESS read-only 
		STATUS current
		DESCRIPTION  "Fragmentation Fast Aging Unset" 
		::={ acosIpFragS 25 } 

		ipFragFramentQueueSuccess OBJECT-TYPE
		SYNTAX  CounterBasedGauge64 
		MAX-ACCESS read-only 
		STATUS current
		DESCRIPTION  "Fragment Queue Success" 
		::={ acosIpFragS 26 } 

		ipFragUnalignedLen OBJECT-TYPE
		SYNTAX  CounterBasedGauge64 
		MAX-ACCESS read-only 
		STATUS current
		DESCRIPTION  "Payload Length Unaligned" 
		::={ acosIpFragS 27 } 

		ipFragExceededLen OBJECT-TYPE
		SYNTAX  CounterBasedGauge64 
		MAX-ACCESS read-only 
		STATUS current
		DESCRIPTION  "Payload Length Out of Bounds" 
		::={ acosIpFragS 28 } 

		ipFragDuplicateFirstFrag OBJECT-TYPE
		SYNTAX  CounterBasedGauge64 
		MAX-ACCESS read-only 
		STATUS current
		DESCRIPTION  "Duplicate First Fragment" 
		::={ acosIpFragS 29 } 

		ipFragDuplicateLastFrag OBJECT-TYPE
		SYNTAX  CounterBasedGauge64 
		MAX-ACCESS read-only 
		STATUS current
		DESCRIPTION  "Duplicate Last Fragment" 
		::={ acosIpFragS 30 } 

		ipFragTotalFragmentsExceeded OBJECT-TYPE
		SYNTAX  CounterBasedGauge64 
		MAX-ACCESS read-only 
		STATUS current
		DESCRIPTION  "Total Queued Fragments Exceeded" 
		::={ acosIpFragS 31 } 

		ipFragFramentQueueFailure OBJECT-TYPE
		SYNTAX  CounterBasedGauge64 
		MAX-ACCESS read-only 
		STATUS current
		DESCRIPTION  "Fragment Queue Failure" 
		::={ acosIpFragS 32 } 

		ipFragReassemblySucess OBJECT-TYPE
		SYNTAX  CounterBasedGauge64 
		MAX-ACCESS read-only 
		STATUS current
		DESCRIPTION  "Fragment Reassembly Success" 
		::={ acosIpFragS 33 } 

		ipFragMaxLenExeeded OBJECT-TYPE
		SYNTAX  CounterBasedGauge64 
		MAX-ACCESS read-only 
		STATUS current
		DESCRIPTION  "Fragment Max Data Length Exceeded" 
		::={ acosIpFragS 34 } 

		ipFragReassemblyFailure OBJECT-TYPE
		SYNTAX  CounterBasedGauge64 
		MAX-ACCESS read-only 
		STATUS current
		DESCRIPTION  "Fragment Reassembly Failure" 
		::={ acosIpFragS 35 } 

		ipFragPolicyDrop OBJECT-TYPE
		SYNTAX  CounterBasedGauge64 
		MAX-ACCESS read-only 
		STATUS current
		DESCRIPTION  "MTU Exceeded Policy Drop" 
		::={ acosIpFragS 36 } 

		ipFragErrorDrop OBJECT-TYPE
		SYNTAX  CounterBasedGauge64 
		MAX-ACCESS read-only 
		STATUS current
		DESCRIPTION  "Fragment Processing Drop" 
		::={ acosIpFragS 37 } 

		highCpuThreshold OBJECT-TYPE
		SYNTAX  CounterBasedGauge64 
		MAX-ACCESS read-only 
		STATUS current
		DESCRIPTION  "High CPU Threshold Reached" 
		::={ acosIpFragS 38 } 

		lowCpuThreshold OBJECT-TYPE
		SYNTAX  CounterBasedGauge64 
		MAX-ACCESS read-only 
		STATUS current
		DESCRIPTION  "Low CPU Threshold Reached" 
		::={ acosIpFragS 39 } 

		cpuThresholdDrop OBJECT-TYPE
		SYNTAX  CounterBasedGauge64 
		MAX-ACCESS read-only 
		STATUS current
		DESCRIPTION  "High CPU Drop" 
		::={ acosIpFragS 40 } 

		ipdEntryDrop OBJECT-TYPE
		SYNTAX  CounterBasedGauge64 
		MAX-ACCESS read-only 
		STATUS current
		DESCRIPTION  "DDoS Protection Drop" 
		::={ acosIpFragS 41 } 

		ipFragMaxPacketsExceeded OBJECT-TYPE
		SYNTAX  CounterBasedGauge64 
		MAX-ACCESS read-only 
		STATUS current
		DESCRIPTION  "Too Many Packets Per Reassembly Drop" 
		::={ acosIpFragS 42 } 

		ipFragSessionPacketsExceeded OBJECT-TYPE
		SYNTAX  CounterBasedGauge64 
		MAX-ACCESS read-only 
		STATUS current
		DESCRIPTION  "Session Max Packets Exceeded" 
		::={ acosIpFragS 43 } 

		fragSessionCount OBJECT-TYPE
		SYNTAX  CounterBasedGauge64 
		MAX-ACCESS read-only 
		STATUS current
		DESCRIPTION  "Fragmentation Session Count" 
		::={ acosIpFragS 44 } 

		ipFragSctpRcv OBJECT-TYPE
		SYNTAX  CounterBasedGauge64 
		MAX-ACCESS read-only 
		STATUS current
		DESCRIPTION  "SCTP Received" 
		::={ acosIpFragS 45 } 

		ipFragSctpDropped OBJECT-TYPE
		SYNTAX  CounterBasedGauge64 
		MAX-ACCESS read-only 
		STATUS current
		DESCRIPTION  "SCTP Dropped" 
		::={ acosIpFragS 46 } 

		ipFragFirstGTPPacketTooSmall OBJECT-TYPE
		SYNTAX  CounterBasedGauge64 
		MAX-ACCESS read-only 
		STATUS current
		DESCRIPTION  "First GTP Fragment Too Small Drop" 
		::={ acosIpFragS 47 } 

acosIpNat                           OBJECT IDENTIFIER ::= { acosIp 12 }
acosIpNatNatGlobal                  OBJECT IDENTIFIER ::= { acosIpNat 1 }
acosIpNatNatGlobalS                 OBJECT IDENTIFIER ::= { acosIpNatNatGlobal 1 }

		crossCpuHelperCreated OBJECT-TYPE
		SYNTAX  CounterBasedGauge64 
		MAX-ACCESS read-only 
		STATUS current
		DESCRIPTION  "Cross CPU Helper Created" 
		::={ acosIpNatNatGlobalS 1 } 

		crossCpuHelperFree OBJECT-TYPE
		SYNTAX  CounterBasedGauge64 
		MAX-ACCESS read-only 
		STATUS current
		DESCRIPTION  "Cross CPU Helper Free" 
		::={ acosIpNatNatGlobalS 2 } 

		crossCpuSent OBJECT-TYPE
		SYNTAX  CounterBasedGauge64 
		MAX-ACCESS read-only 
		STATUS current
		DESCRIPTION  "Cross CPU Helper Packets Sent" 
		::={ acosIpNatNatGlobalS 3 } 

		crossCpuRcv OBJECT-TYPE
		SYNTAX  CounterBasedGauge64 
		MAX-ACCESS read-only 
		STATUS current
		DESCRIPTION  "Cross CPU Helper Packets Received" 
		::={ acosIpNatNatGlobalS 4 } 

		crossCpuHelperNatPoolStandby OBJECT-TYPE
		SYNTAX  CounterBasedGauge64 
		MAX-ACCESS read-only 
		STATUS current
		DESCRIPTION  "Cross CPU Helper Standby" 
		::={ acosIpNatNatGlobalS 5 } 

		crossCpuHelperCpuMismatch OBJECT-TYPE
		SYNTAX  CounterBasedGauge64 
		MAX-ACCESS read-only 
		STATUS current
		DESCRIPTION  "Cross CPU Helper CPU Mismatch" 
		::={ acosIpNatNatGlobalS 6 } 

		crossCpuBadL3 OBJECT-TYPE
		SYNTAX  CounterBasedGauge64 
		MAX-ACCESS read-only 
		STATUS current
		DESCRIPTION  "Cross CPU Unsupported L3" 
		::={ acosIpNatNatGlobalS 7 } 

		crossCpuBadL4 OBJECT-TYPE
		SYNTAX  CounterBasedGauge64 
		MAX-ACCESS read-only 
		STATUS current
		DESCRIPTION  "Cross CPU Unsupported L4" 
		::={ acosIpNatNatGlobalS 8 } 

		crossCpuNoSession OBJECT-TYPE
		SYNTAX  CounterBasedGauge64 
		MAX-ACCESS read-only 
		STATUS current
		DESCRIPTION  "Cross CPU No Session Found" 
		::={ acosIpNatNatGlobalS 9 } 

		crossCpuHelperDeleted OBJECT-TYPE
		SYNTAX  CounterBasedGauge64 
		MAX-ACCESS read-only 
		STATUS current
		DESCRIPTION  "Cross CPU Helper Deleted" 
		::={ acosIpNatNatGlobalS 10 } 

		crossCpuHelperFreeRetryLookup OBJECT-TYPE
		SYNTAX  CounterBasedGauge64 
		MAX-ACCESS read-only 
		STATUS current
		DESCRIPTION  "Cross CPU Helper Free Retry Lookup" 
		::={ acosIpNatNatGlobalS 11 } 

		crossCpuHelperFreeNotFound OBJECT-TYPE
		SYNTAX  CounterBasedGauge64 
		MAX-ACCESS read-only 
		STATUS current
		DESCRIPTION  "Cross CPU Helper Free Not Found" 
		::={ acosIpNatNatGlobalS 12 } 

acosIpNatPool                       OBJECT IDENTIFIER ::= { acosIpNat 2 }
acosIpNatPoolS                      OBJECT IDENTIFIER ::= { acosIpNatPool 1 }

ipNatPoolSTable OBJECT-TYPE
		SYNTAX SEQUENCE OF IpNatPoolSEntry
		MAX-ACCESS not-accessible
		STATUS current
		::={ acosIpNatPoolS 1 } 


	ipNatPoolSEntry OBJECT-TYPE
		SYNTAX IpNatPoolSEntry
		MAX-ACCESS not-accessible
		STATUS current
		INDEX {
			ipNatPoolName
		}
		::={ ipNatPoolSTable 1 } 


	IpNatPoolSEntry ::=
		SEQUENCE {
			ipNatPoolName DisplayString, 
			ipNatPoolPortUsage CounterBasedGauge64,
			ipNatPoolTotalUsed CounterBasedGauge64,
			ipNatPoolTotalFreed CounterBasedGauge64,
			ipNatPoolFailed CounterBasedGauge64
		}

			ipNatPoolName OBJECT-TYPE
			SYNTAX  DisplayString 
			MAX-ACCESS read-only 
			STATUS current
			DESCRIPTION  "Specify pool name or pool group" 
			::={ ipNatPoolSEntry 1 } 

			ipNatPoolPortUsage OBJECT-TYPE
			SYNTAX  CounterBasedGauge64 
			MAX-ACCESS read-only 
			STATUS current
			DESCRIPTION  "some help string" 
			::={ ipNatPoolSEntry 2 } 

			ipNatPoolTotalUsed OBJECT-TYPE
			SYNTAX  CounterBasedGauge64 
			MAX-ACCESS read-only 
			STATUS current
			DESCRIPTION  "some help string" 
			::={ ipNatPoolSEntry 3 } 

			ipNatPoolTotalFreed OBJECT-TYPE
			SYNTAX  CounterBasedGauge64 
			MAX-ACCESS read-only 
			STATUS current
			DESCRIPTION  "some help string" 
			::={ ipNatPoolSEntry 4 } 

			ipNatPoolFailed OBJECT-TYPE
			SYNTAX  CounterBasedGauge64 
			MAX-ACCESS read-only 
			STATUS current
			DESCRIPTION  "some help string" 
			::={ ipNatPoolSEntry 5 } 

acosIpNatPoolGroup                  OBJECT IDENTIFIER ::= { acosIpNat 3 }
acosIpNatPoolGroupS                 OBJECT IDENTIFIER ::= { acosIpNatPoolGroup 1 }

ipNatPoolGroupSTable OBJECT-TYPE
		SYNTAX SEQUENCE OF IpNatPoolGroupSEntry
		MAX-ACCESS not-accessible
		STATUS current
		::={ acosIpNatPoolGroupS 1 } 


	ipNatPoolGroupSEntry OBJECT-TYPE
		SYNTAX IpNatPoolGroupSEntry
		MAX-ACCESS not-accessible
		STATUS current
		INDEX {
			poolGroupName
		}
		::={ ipNatPoolGroupSTable 1 } 


	IpNatPoolGroupSEntry ::=
		SEQUENCE {
			poolGroupName DisplayString, 
			Failed CounterBasedGauge64
		}

			poolGroupName OBJECT-TYPE
			SYNTAX  DisplayString 
			MAX-ACCESS read-only 
			STATUS current
			DESCRIPTION  "Specify pool group name" 
			::={ ipNatPoolGroupSEntry 1 } 

			Failed OBJECT-TYPE
			SYNTAX  CounterBasedGauge64 
			MAX-ACCESS read-only 
			STATUS current
			DESCRIPTION  "some-help-string" 
			::={ ipNatPoolGroupSEntry 2 } 

acosIpNatAlg                        OBJECT IDENTIFIER ::= { acosIpNat 9 }
acosIpNatAlgPptp                    OBJECT IDENTIFIER ::= { acosIpNatAlg 1 }
acosIpNatAlgPptpS                   OBJECT IDENTIFIER ::= { acosIpNatAlgPptp 1 }

		currentSmpSessions OBJECT-TYPE
		SYNTAX  CounterBasedGauge64 
		MAX-ACCESS read-only 
		STATUS current
		DESCRIPTION  "some help string" 
		::={ acosIpNatAlgPptpS 1 } 

		currentGreSessions OBJECT-TYPE
		SYNTAX  CounterBasedGauge64 
		MAX-ACCESS read-only 
		STATUS current
		DESCRIPTION  "some help string" 
		::={ acosIpNatAlgPptpS 2 } 

		smpSessionCreationFailure OBJECT-TYPE
		SYNTAX  CounterBasedGauge64 
		MAX-ACCESS read-only 
		STATUS current
		DESCRIPTION  "some help string" 
		::={ acosIpNatAlgPptpS 3 } 

		truncatedPnsMessage OBJECT-TYPE
		SYNTAX  CounterBasedGauge64 
		MAX-ACCESS read-only 
		STATUS current
		DESCRIPTION  "some help string" 
		::={ acosIpNatAlgPptpS 4 } 

		truncatedPacMessage OBJECT-TYPE
		SYNTAX  CounterBasedGauge64 
		MAX-ACCESS read-only 
		STATUS current
		DESCRIPTION  "some help string" 
		::={ acosIpNatAlgPptpS 5 } 

		mismatchedPnsCallId OBJECT-TYPE
		SYNTAX  CounterBasedGauge64 
		MAX-ACCESS read-only 
		STATUS current
		DESCRIPTION  "some help string" 
		::={ acosIpNatAlgPptpS 6 } 

		mismatchedPacCallId OBJECT-TYPE
		SYNTAX  CounterBasedGauge64 
		MAX-ACCESS read-only 
		STATUS current
		DESCRIPTION  "some help string" 
		::={ acosIpNatAlgPptpS 7 } 

		retransmittedPnsMessage OBJECT-TYPE
		SYNTAX  CounterBasedGauge64 
		MAX-ACCESS read-only 
		STATUS current
		DESCRIPTION  "some help string" 
		::={ acosIpNatAlgPptpS 8 } 

		retransmittedPacMessage OBJECT-TYPE
		SYNTAX  CounterBasedGauge64 
		MAX-ACCESS read-only 
		STATUS current
		DESCRIPTION  "some help string" 
		::={ acosIpNatAlgPptpS 9 } 

		truncatedGrePacket OBJECT-TYPE
		SYNTAX  CounterBasedGauge64 
		MAX-ACCESS read-only 
		STATUS current
		DESCRIPTION  "some help string" 
		::={ acosIpNatAlgPptpS 10 } 

		unknownGreVersion OBJECT-TYPE
		SYNTAX  CounterBasedGauge64 
		MAX-ACCESS read-only 
		STATUS current
		DESCRIPTION  "some help string" 
		::={ acosIpNatAlgPptpS 11 } 

		noMatchingGreSession OBJECT-TYPE
		SYNTAX  CounterBasedGauge64 
		MAX-ACCESS read-only 
		STATUS current
		DESCRIPTION  "some help string" 
		::={ acosIpNatAlgPptpS 12 } 

END

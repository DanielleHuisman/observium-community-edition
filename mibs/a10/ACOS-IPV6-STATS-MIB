ACOS-IPV6-STATS-MIB DEFINITIONS ::= BEGIN
	IMPORTS
		DisplayString, PhysAddress
		FROM SNMPv2-TC
	InetAddressType
		FROM INET-ADDRESS-MIB
	acosRootStats
		FROM A10-AX-MIB
	MODULE-IDENTITY, OBJECT-TYPE, Counter32, Integer32, Counter64, OBJECT-IDENTITY, NOTIFICATION-TYPE
		FROM SNMPv2-SMI;
		acosIpv6 MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "Ipv6 OID for ACOS"
				::=  {  acosRootStats 57  }

acosIpv6Frag                        OBJECT IDENTIFIER ::= { acosIpv6 4 }
acosIpv6FragS                       OBJECT IDENTIFIER ::= { acosIpv6Frag 1 }

		ipv6FragSessionInserted OBJECT-TYPE
		SYNTAX  CounterBasedGauge64 
		MAX-ACCESS read-only 
		STATUS current
		DESCRIPTION  "Session Inserted" 
		::={ acosIpv6FragS 1 } 

		ipv6FragSessionExpired OBJECT-TYPE
		SYNTAX  CounterBasedGauge64 
		MAX-ACCESS read-only 
		STATUS current
		DESCRIPTION  "Session Expired" 
		::={ acosIpv6FragS 2 } 

		ipv6FragIcmpRcv OBJECT-TYPE
		SYNTAX  CounterBasedGauge64 
		MAX-ACCESS read-only 
		STATUS current
		DESCRIPTION  "ICMP Received" 
		::={ acosIpv6FragS 3 } 

		ipv6FragIcmpv6Rcv OBJECT-TYPE
		SYNTAX  CounterBasedGauge64 
		MAX-ACCESS read-only 
		STATUS current
		DESCRIPTION  "ICMPv6 Received" 
		::={ acosIpv6FragS 4 } 

		ipv6FragUdpRcv OBJECT-TYPE
		SYNTAX  CounterBasedGauge64 
		MAX-ACCESS read-only 
		STATUS current
		DESCRIPTION  "UDP Received" 
		::={ acosIpv6FragS 5 } 

		ipv6FragTcpRcv OBJECT-TYPE
		SYNTAX  CounterBasedGauge64 
		MAX-ACCESS read-only 
		STATUS current
		DESCRIPTION  "TCP Received" 
		::={ acosIpv6FragS 6 } 

		ipv6FragIpipRcv OBJECT-TYPE
		SYNTAX  CounterBasedGauge64 
		MAX-ACCESS read-only 
		STATUS current
		DESCRIPTION  "IP-in-IP Received" 
		::={ acosIpv6FragS 7 } 

		ipv6FragIpv6ipRcv OBJECT-TYPE
		SYNTAX  CounterBasedGauge64 
		MAX-ACCESS read-only 
		STATUS current
		DESCRIPTION  "IPv6-in-IP Received" 
		::={ acosIpv6FragS 8 } 

		ipv6FragOtherRcv OBJECT-TYPE
		SYNTAX  CounterBasedGauge64 
		MAX-ACCESS read-only 
		STATUS current
		DESCRIPTION  "Other Received" 
		::={ acosIpv6FragS 9 } 

		ipv6FragIcmpDropped OBJECT-TYPE
		SYNTAX  CounterBasedGauge64 
		MAX-ACCESS read-only 
		STATUS current
		DESCRIPTION  "ICMP Dropped" 
		::={ acosIpv6FragS 10 } 

		ipv6FragIcmpv6Dropped OBJECT-TYPE
		SYNTAX  CounterBasedGauge64 
		MAX-ACCESS read-only 
		STATUS current
		DESCRIPTION  "ICMPv6 Dropped" 
		::={ acosIpv6FragS 11 } 

		ipv6FragUdpDropped OBJECT-TYPE
		SYNTAX  CounterBasedGauge64 
		MAX-ACCESS read-only 
		STATUS current
		DESCRIPTION  "UDP Dropped" 
		::={ acosIpv6FragS 12 } 

		ipv6FragTcpDropped OBJECT-TYPE
		SYNTAX  CounterBasedGauge64 
		MAX-ACCESS read-only 
		STATUS current
		DESCRIPTION  "TCP Dropped" 
		::={ acosIpv6FragS 13 } 

		ipv6FragIpipDropped OBJECT-TYPE
		SYNTAX  CounterBasedGauge64 
		MAX-ACCESS read-only 
		STATUS current
		DESCRIPTION  "IP-in-IP Dropped" 
		::={ acosIpv6FragS 14 } 

		ipv6FragIpv6ipDropped OBJECT-TYPE
		SYNTAX  CounterBasedGauge64 
		MAX-ACCESS read-only 
		STATUS current
		DESCRIPTION  "IPv6-in-IP Dropped" 
		::={ acosIpv6FragS 15 } 

		ipv6FragOtherDropped OBJECT-TYPE
		SYNTAX  CounterBasedGauge64 
		MAX-ACCESS read-only 
		STATUS current
		DESCRIPTION  "Other Dropped" 
		::={ acosIpv6FragS 16 } 

		ipv6FragOverlapError OBJECT-TYPE
		SYNTAX  CounterBasedGauge64 
		MAX-ACCESS read-only 
		STATUS current
		DESCRIPTION  "Overlapping Fragment Dropped" 
		::={ acosIpv6FragS 17 } 

		ipv6FragBadIpLen OBJECT-TYPE
		SYNTAX  CounterBasedGauge64 
		MAX-ACCESS read-only 
		STATUS current
		DESCRIPTION  "Bad IP Length" 
		::={ acosIpv6FragS 18 } 

		ipv6FragTooSmall OBJECT-TYPE
		SYNTAX  CounterBasedGauge64 
		MAX-ACCESS read-only 
		STATUS current
		DESCRIPTION  "Fragment Too Small Drop" 
		::={ acosIpv6FragS 19 } 

		ipv6FragFirstTcpTooSmall OBJECT-TYPE
		SYNTAX  CounterBasedGauge64 
		MAX-ACCESS read-only 
		STATUS current
		DESCRIPTION  "First TCP Fragment Too Small Drop" 
		::={ acosIpv6FragS 20 } 

		ipv6FragFirstL4TooSmall OBJECT-TYPE
		SYNTAX  CounterBasedGauge64 
		MAX-ACCESS read-only 
		STATUS current
		DESCRIPTION  "First L4 Fragment Too Small Drop" 
		::={ acosIpv6FragS 21 } 

		ipv6FragTotalSessionsExceeded OBJECT-TYPE
		SYNTAX  CounterBasedGauge64 
		MAX-ACCESS read-only 
		STATUS current
		DESCRIPTION  "Total Sessions Exceeded Drop" 
		::={ acosIpv6FragS 22 } 

		ipv6FragNoSessionMemory OBJECT-TYPE
		SYNTAX  CounterBasedGauge64 
		MAX-ACCESS read-only 
		STATUS current
		DESCRIPTION  "Out of Session Memory" 
		::={ acosIpv6FragS 23 } 

		ipv6FragFastAgingSet OBJECT-TYPE
		SYNTAX  CounterBasedGauge64 
		MAX-ACCESS read-only 
		STATUS current
		DESCRIPTION  "Fragmentation Fast Aging Set" 
		::={ acosIpv6FragS 24 } 

		ipv6FragFastAgingUnset OBJECT-TYPE
		SYNTAX  CounterBasedGauge64 
		MAX-ACCESS read-only 
		STATUS current
		DESCRIPTION  "Fragmentation Fast Aging Unset" 
		::={ acosIpv6FragS 25 } 

		ipv6FragFragmentQueueSuccess OBJECT-TYPE
		SYNTAX  CounterBasedGauge64 
		MAX-ACCESS read-only 
		STATUS current
		DESCRIPTION  "Fragment Queue Success" 
		::={ acosIpv6FragS 26 } 

		ipv6FragUnalignedLen OBJECT-TYPE
		SYNTAX  CounterBasedGauge64 
		MAX-ACCESS read-only 
		STATUS current
		DESCRIPTION  "Payload Length Unaligned" 
		::={ acosIpv6FragS 27 } 

		ipv6FragExceededLen OBJECT-TYPE
		SYNTAX  CounterBasedGauge64 
		MAX-ACCESS read-only 
		STATUS current
		DESCRIPTION  "Payload Length Out of Bounds" 
		::={ acosIpv6FragS 28 } 

		ipv6FragDuplicateFirstFrag OBJECT-TYPE
		SYNTAX  CounterBasedGauge64 
		MAX-ACCESS read-only 
		STATUS current
		DESCRIPTION  "Duplicate First Fragment" 
		::={ acosIpv6FragS 29 } 

		ipv6FragDuplicateLastFrag OBJECT-TYPE
		SYNTAX  CounterBasedGauge64 
		MAX-ACCESS read-only 
		STATUS current
		DESCRIPTION  "Duplicate Last Fragment" 
		::={ acosIpv6FragS 30 } 

		ipv6FragTotalFragmentsExceeded OBJECT-TYPE
		SYNTAX  CounterBasedGauge64 
		MAX-ACCESS read-only 
		STATUS current
		DESCRIPTION  "Total Queued Fragments Exceeded" 
		::={ acosIpv6FragS 31 } 

		ipv6FragFragmentQueueFailure OBJECT-TYPE
		SYNTAX  CounterBasedGauge64 
		MAX-ACCESS read-only 
		STATUS current
		DESCRIPTION  "Fragment Queue Failure" 
		::={ acosIpv6FragS 32 } 

		ipv6FragReassemblySuccess OBJECT-TYPE
		SYNTAX  CounterBasedGauge64 
		MAX-ACCESS read-only 
		STATUS current
		DESCRIPTION  "Fragment Reassembly Success" 
		::={ acosIpv6FragS 33 } 

		ipv6FragMaxLenExceeded OBJECT-TYPE
		SYNTAX  CounterBasedGauge64 
		MAX-ACCESS read-only 
		STATUS current
		DESCRIPTION  "Fragment Max Data Length Exceeded" 
		::={ acosIpv6FragS 34 } 

		ipv6FragReassemblyFailure OBJECT-TYPE
		SYNTAX  CounterBasedGauge64 
		MAX-ACCESS read-only 
		STATUS current
		DESCRIPTION  "Fragment Reassembly Failure" 
		::={ acosIpv6FragS 35 } 

		ipv6FragPolicyDrop OBJECT-TYPE
		SYNTAX  CounterBasedGauge64 
		MAX-ACCESS read-only 
		STATUS current
		DESCRIPTION  "MTU Exceeded Policy Drop" 
		::={ acosIpv6FragS 36 } 

		ipv6FragErrorDrop OBJECT-TYPE
		SYNTAX  CounterBasedGauge64 
		MAX-ACCESS read-only 
		STATUS current
		DESCRIPTION  "Fragment Processing Drop" 
		::={ acosIpv6FragS 37 } 

		highCpuThreshold OBJECT-TYPE
		SYNTAX  CounterBasedGauge64 
		MAX-ACCESS read-only 
		STATUS current
		DESCRIPTION  "High CPU Threshold Reached" 
		::={ acosIpv6FragS 38 } 

		lowCpuThreshold OBJECT-TYPE
		SYNTAX  CounterBasedGauge64 
		MAX-ACCESS read-only 
		STATUS current
		DESCRIPTION  "Low CPU Threshold Reached" 
		::={ acosIpv6FragS 39 } 

		cpuThresholdDrop OBJECT-TYPE
		SYNTAX  CounterBasedGauge64 
		MAX-ACCESS read-only 
		STATUS current
		DESCRIPTION  "High CPU Drop" 
		::={ acosIpv6FragS 40 } 

		ipdEntryDrop OBJECT-TYPE
		SYNTAX  CounterBasedGauge64 
		MAX-ACCESS read-only 
		STATUS current
		DESCRIPTION  "DDoS Protection Drop" 
		::={ acosIpv6FragS 41 } 

		ipv6FragMaxPacketsExceeded OBJECT-TYPE
		SYNTAX  CounterBasedGauge64 
		MAX-ACCESS read-only 
		STATUS current
		DESCRIPTION  "Too Many Packets Per Reassembly Drop" 
		::={ acosIpv6FragS 42 } 

		ipv6FragSessionPacketsExceeded OBJECT-TYPE
		SYNTAX  CounterBasedGauge64 
		MAX-ACCESS read-only 
		STATUS current
		DESCRIPTION  "Session Max Packets Exceeded" 
		::={ acosIpv6FragS 43 } 

		fragSessionCount OBJECT-TYPE
		SYNTAX  CounterBasedGauge64 
		MAX-ACCESS read-only 
		STATUS current
		DESCRIPTION  "Fragmentation Session Count" 
		::={ acosIpv6FragS 44 } 

		ipv6FragSctpRcv OBJECT-TYPE
		SYNTAX  CounterBasedGauge64 
		MAX-ACCESS read-only 
		STATUS current
		DESCRIPTION  "SCTP Received" 
		::={ acosIpv6FragS 45 } 

		ipv6FragSctpDropped OBJECT-TYPE
		SYNTAX  CounterBasedGauge64 
		MAX-ACCESS read-only 
		STATUS current
		DESCRIPTION  "SCTP Dropped" 
		::={ acosIpv6FragS 46 } 

		ipFragFirstGTPPacketTooSmall OBJECT-TYPE
		SYNTAX  CounterBasedGauge64 
		MAX-ACCESS read-only 
		STATUS current
		DESCRIPTION  "First GTP Fragment Too Small Drop" 
		::={ acosIpv6FragS 47 } 

acosIpv6Nat                         OBJECT IDENTIFIER ::= { acosIpv6 9 }
acosIpv6NatPool                     OBJECT IDENTIFIER ::= { acosIpv6Nat 1 }
acosIpv6NatPoolS                    OBJECT IDENTIFIER ::= { acosIpv6NatPool 1 }

ipv6NatPoolSTable OBJECT-TYPE
		SYNTAX SEQUENCE OF Ipv6NatPoolSEntry
		MAX-ACCESS not-accessible
		STATUS current
		::={ acosIpv6NatPoolS 1 } 


	ipv6NatPoolSEntry OBJECT-TYPE
		SYNTAX Ipv6NatPoolSEntry
		MAX-ACCESS not-accessible
		STATUS current
		INDEX {
			poolName
		}
		::={ ipv6NatPoolSTable 1 } 


	Ipv6NatPoolSEntry ::=
		SEQUENCE {
			poolName DisplayString, 
			portUsage CounterBasedGauge64,
			totalUsed CounterBasedGauge64,
			totalFreed CounterBasedGauge64,
			failed CounterBasedGauge64
		}

			poolName OBJECT-TYPE
			SYNTAX  DisplayString 
			MAX-ACCESS read-only 
			STATUS current
			DESCRIPTION  "Specify pool name" 
			::={ ipv6NatPoolSEntry 1 } 

			portUsage OBJECT-TYPE
			SYNTAX  CounterBasedGauge64 
			MAX-ACCESS read-only 
			STATUS current
			DESCRIPTION  "some help string" 
			::={ ipv6NatPoolSEntry 2 } 

			totalUsed OBJECT-TYPE
			SYNTAX  CounterBasedGauge64 
			MAX-ACCESS read-only 
			STATUS current
			DESCRIPTION  "some help string" 
			::={ ipv6NatPoolSEntry 3 } 

			totalFreed OBJECT-TYPE
			SYNTAX  CounterBasedGauge64 
			MAX-ACCESS read-only 
			STATUS current
			DESCRIPTION  "some help string" 
			::={ ipv6NatPoolSEntry 4 } 

			failed OBJECT-TYPE
			SYNTAX  CounterBasedGauge64 
			MAX-ACCESS read-only 
			STATUS current
			DESCRIPTION  "some help string" 
			::={ ipv6NatPoolSEntry 5 } 

acosIpv6NatPoolGroup                OBJECT IDENTIFIER ::= { acosIpv6Nat 2 }
acosIpv6NatPoolGroupS               OBJECT IDENTIFIER ::= { acosIpv6NatPoolGroup 1 }

ipv6NatPoolGroupSTable OBJECT-TYPE
		SYNTAX SEQUENCE OF Ipv6NatPoolGroupSEntry
		MAX-ACCESS not-accessible
		STATUS current
		::={ acosIpv6NatPoolGroupS 1 } 


	ipv6NatPoolGroupSEntry OBJECT-TYPE
		SYNTAX Ipv6NatPoolGroupSEntry
		MAX-ACCESS not-accessible
		STATUS current
		INDEX {
			poolGroupName
		}
		::={ ipv6NatPoolGroupSTable 1 } 


	Ipv6NatPoolGroupSEntry ::=
		SEQUENCE {
			poolGroupName DisplayString, 
			Failed CounterBasedGauge64
		}

			poolGroupName OBJECT-TYPE
			SYNTAX  DisplayString 
			MAX-ACCESS read-only 
			STATUS current
			DESCRIPTION  "Specify pool group name" 
			::={ ipv6NatPoolGroupSEntry 1 } 

			Failed OBJECT-TYPE
			SYNTAX  CounterBasedGauge64 
			MAX-ACCESS read-only 
			STATUS current
			DESCRIPTION  "some-help-string" 
			::={ ipv6NatPoolGroupSEntry 2 } 

END

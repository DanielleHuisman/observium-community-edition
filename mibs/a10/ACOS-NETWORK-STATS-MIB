ACOS-NETWORK-STATS-MIB DEFINITIONS ::= BEGIN
	IMPORTS
		DisplayString, PhysAddress
		FROM SNMPv2-TC
	InetAddressType
		FROM INET-ADDRESS-MIB
	acosRootStats
		FROM A10-AX-MIB
	MODULE-IDENTITY, OBJECT-TYPE, Counter32, Integer32, Counter64, OBJECT-IDENTITY, NOTIFICATION-TYPE
		FROM SNMPv2-SMI;
		acosNetwork MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "Network OID for ACOS"
				::=  {  acosRootStats 56  }

acosNetworkVlan                     OBJECT IDENTIFIER ::= { acosNetwork 4 }
acosNetworkVlanS                    OBJECT IDENTIFIER ::= { acosNetworkVlan 1 }

networkVlanSTable OBJECT-TYPE
		SYNTAX SEQUENCE OF NetworkVlanSEntry
		MAX-ACCESS not-accessible
		STATUS current
		::={ acosNetworkVlanS 1 } 


	networkVlanSEntry OBJECT-TYPE
		SYNTAX NetworkVlanSEntry
		MAX-ACCESS not-accessible
		STATUS current
		INDEX {
			vlanNum
		}
		::={ networkVlanSTable 1 } 


	NetworkVlanSEntry ::=
		SEQUENCE {
			vlanNum INTEGER, 
			broadcastCount CounterBasedGauge64,
			multicastCount CounterBasedGauge64,
			ipMulticastCount CounterBasedGauge64,
			unknownUnicastCount CounterBasedGauge64,
			macMovementCount CounterBasedGauge64,
			sharedVlanPartitionSwitchedCounter CounterBasedGauge64
		}

			vlanNum OBJECT-TYPE
			SYNTAX  INTEGER 
			MAX-ACCESS read-only 
			STATUS current
			DESCRIPTION  "VLAN number" 
			::={ networkVlanSEntry 1 } 

			broadcastCount OBJECT-TYPE
			SYNTAX  CounterBasedGauge64 
			MAX-ACCESS read-only 
			STATUS current
			DESCRIPTION  "Broadcast counter" 
			::={ networkVlanSEntry 2 } 

			multicastCount OBJECT-TYPE
			SYNTAX  CounterBasedGauge64 
			MAX-ACCESS read-only 
			STATUS current
			DESCRIPTION  "Multicast counter" 
			::={ networkVlanSEntry 3 } 

			ipMulticastCount OBJECT-TYPE
			SYNTAX  CounterBasedGauge64 
			MAX-ACCESS read-only 
			STATUS current
			DESCRIPTION  "IP Multicast counter" 
			::={ networkVlanSEntry 4 } 

			unknownUnicastCount OBJECT-TYPE
			SYNTAX  CounterBasedGauge64 
			MAX-ACCESS read-only 
			STATUS current
			DESCRIPTION  "Unknown Unicast counter" 
			::={ networkVlanSEntry 5 } 

			macMovementCount OBJECT-TYPE
			SYNTAX  CounterBasedGauge64 
			MAX-ACCESS read-only 
			STATUS current
			DESCRIPTION  "Mac Movement counter" 
			::={ networkVlanSEntry 6 } 

			sharedVlanPartitionSwitchedCounter OBJECT-TYPE
			SYNTAX  CounterBasedGauge64 
			MAX-ACCESS read-only 
			STATUS current
			DESCRIPTION  "SVLAN Partition switched counter" 
			::={ networkVlanSEntry 7 } 

acosNetworkVlanGlobal               OBJECT IDENTIFIER ::= { acosNetwork 9 }
acosNetworkVlanGlobalS              OBJECT IDENTIFIER ::= { acosNetworkVlanGlobal 1 }

		xparentVlanListErr OBJECT-TYPE
		SYNTAX  CounterBasedGauge64 
		MAX-ACCESS read-only 
		STATUS current
		DESCRIPTION  "Transparent Mode VLAN List Errors" 
		::={ acosNetworkVlanGlobalS 1 } 

acosNetworkVirtualWireGlobal        OBJECT IDENTIFIER ::= { acosNetwork 24 }
acosNetworkVirtualWireGlobalS       OBJECT IDENTIFIER ::= { acosNetworkVirtualWireGlobal 1 }

		vlanUpdate OBJECT-TYPE
		SYNTAX  CounterBasedGauge64 
		MAX-ACCESS read-only 
		STATUS current
		DESCRIPTION  "VLAN update" 
		::={ acosNetworkVirtualWireGlobalS 1 } 

		macUpdate OBJECT-TYPE
		SYNTAX  CounterBasedGauge64 
		MAX-ACCESS read-only 
		STATUS current
		DESCRIPTION  "MAC update" 
		::={ acosNetworkVirtualWireGlobalS 2 } 

acosNetworkTwamp                    OBJECT IDENTIFIER ::= { acosNetwork 20 }
acosNetworkTwampResponder           OBJECT IDENTIFIER ::= { acosNetworkTwamp 1 }
acosNetworkTwampResponderIp         OBJECT IDENTIFIER ::= { acosNetworkTwampResponder 2 }
acosNetworkTwampResponderIpS        OBJECT IDENTIFIER ::= { acosNetworkTwampResponderIp 1 }

		rxPkts OBJECT-TYPE
		SYNTAX  CounterBasedGauge64 
		MAX-ACCESS read-only 
		STATUS current
		DESCRIPTION  "Rx IP TWAMP test packets" 
		::={ acosNetworkTwampResponderIpS 1 } 

		txPkts OBJECT-TYPE
		SYNTAX  CounterBasedGauge64 
		MAX-ACCESS read-only 
		STATUS current
		DESCRIPTION  "Tx IP TWAMP test packets" 
		::={ acosNetworkTwampResponderIpS 2 } 

		rxDropNotEnabledV4 OBJECT-TYPE
		SYNTAX  CounterBasedGauge64 
		MAX-ACCESS read-only 
		STATUS current
		DESCRIPTION  "Rx IP disabled drop" 
		::={ acosNetworkTwampResponderIpS 3 } 

		rxAclDrop OBJECT-TYPE
		SYNTAX  CounterBasedGauge64 
		MAX-ACCESS read-only 
		STATUS current
		DESCRIPTION  "Rx IP client-list drop" 
		::={ acosNetworkTwampResponderIpS 4 } 

		twampHdrLenErr OBJECT-TYPE
		SYNTAX  CounterBasedGauge64 
		MAX-ACCESS read-only 
		STATUS current
		DESCRIPTION  "Rx TWAMP hdr length error drop" 
		::={ acosNetworkTwampResponderIpS 5 } 

		noRouteErr OBJECT-TYPE
		SYNTAX  CounterBasedGauge64 
		MAX-ACCESS read-only 
		STATUS current
		DESCRIPTION  "Tx IP no route error drop" 
		::={ acosNetworkTwampResponderIpS 6 } 

		otherErr OBJECT-TYPE
		SYNTAX  CounterBasedGauge64 
		MAX-ACCESS read-only 
		STATUS current
		DESCRIPTION  "IP other error drop" 
		::={ acosNetworkTwampResponderIpS 7 } 

acosNetworkTwampResponderIpv6       OBJECT IDENTIFIER ::= { acosNetworkTwampResponder 3 }
acosNetworkTwampResponderIpv6S      OBJECT IDENTIFIER ::= { acosNetworkTwampResponderIpv6 1 }

		rxPktsV6 OBJECT-TYPE
		SYNTAX  CounterBasedGauge64 
		MAX-ACCESS read-only 
		STATUS current
		DESCRIPTION  "Rx IPv6 TWAMP test packets" 
		::={ acosNetworkTwampResponderIpv6S 8 } 

		txPktsV6 OBJECT-TYPE
		SYNTAX  CounterBasedGauge64 
		MAX-ACCESS read-only 
		STATUS current
		DESCRIPTION  "Tx IPv6 TWAMP test packets" 
		::={ acosNetworkTwampResponderIpv6S 9 } 

		rxDropNotEnabledV6 OBJECT-TYPE
		SYNTAX  CounterBasedGauge64 
		MAX-ACCESS read-only 
		STATUS current
		DESCRIPTION  "Rx IPv6 disabled drop" 
		::={ acosNetworkTwampResponderIpv6S 10 } 

		rxAclDropV6 OBJECT-TYPE
		SYNTAX  CounterBasedGauge64 
		MAX-ACCESS read-only 
		STATUS current
		DESCRIPTION  "Rx IPv6 client-list drop" 
		::={ acosNetworkTwampResponderIpv6S 11 } 

		twampHdrLenErrV6 OBJECT-TYPE
		SYNTAX  CounterBasedGauge64 
		MAX-ACCESS read-only 
		STATUS current
		DESCRIPTION  "Rx IPv6 TWAMP hdr length error drop" 
		::={ acosNetworkTwampResponderIpv6S 12 } 

		noRouteErrV6 OBJECT-TYPE
		SYNTAX  CounterBasedGauge64 
		MAX-ACCESS read-only 
		STATUS current
		DESCRIPTION  "Tx IPv6 no route error drop" 
		::={ acosNetworkTwampResponderIpv6S 13 } 

		otherErrV6 OBJECT-TYPE
		SYNTAX  CounterBasedGauge64 
		MAX-ACCESS read-only 
		STATUS current
		DESCRIPTION  "IPv6 Other error drop" 
		::={ acosNetworkTwampResponderIpv6S 14 } 

END

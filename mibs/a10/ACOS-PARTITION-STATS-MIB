ACOS-PARTITION-STATS-MIB DEFINITIONS ::= BEGIN
	IMPORTS
		DisplayString, PhysAddress
		FROM SNMPv2-TC
	InetAddressType
		FROM INET-ADDRESS-MIB
	acosRootStats
		FROM A10-AX-MIB
	MODULE-IDENTITY, OBJECT-TYPE, Counter32, Integer32, Counter64, OBJECT-IDENTITY, NOTIFICATION-TYPE
		FROM SNMPv2-SMI;
		acosPartition MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "Partition OID for ACOS"
				::=  {  acosRootStats 6  }

acosPartition                       OBJECT IDENTIFIER ::= { acosRootStats 6 }
acosPartitionS                      OBJECT IDENTIFIER ::= { acosPartition 1 }

partitionSTable OBJECT-TYPE
		SYNTAX SEQUENCE OF PartitionSEntry
		MAX-ACCESS not-accessible
		STATUS current
		::={ acosPartitionS 1 } 


	partitionSEntry OBJECT-TYPE
		SYNTAX PartitionSEntry
		MAX-ACCESS not-accessible
		STATUS current
		INDEX {
			partitionName
		}
		::={ partitionSTable 1 } 


	PartitionSEntry ::=
		SEQUENCE {
			partitionName DisplayString, 
			countersCreated CounterBasedGauge64
		}

			partitionName OBJECT-TYPE
			SYNTAX  DisplayString 
			MAX-ACCESS read-only 
			STATUS current
			DESCRIPTION  "Object partition name" 
			::={ partitionSEntry 1 } 

			countersCreated OBJECT-TYPE
			SYNTAX  CounterBasedGauge64 
			MAX-ACCESS read-only 
			STATUS current
			DESCRIPTION  "dummy counter for infra" 
			::={ partitionSEntry 2 } 

END

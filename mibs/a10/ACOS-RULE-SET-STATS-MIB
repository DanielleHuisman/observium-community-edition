ACOS-RULE-SET-STATS-MIB DEFINITIONS ::= BEGIN
	IMPORTS
		DisplayString, PhysAddress
		FROM SNMPv2-TC
	InetAddressType
		FROM INET-ADDRESS-MIB
	acosRootStats
		FROM A10-AX-MIB
	MODULE-IDENTITY, OBJECT-TYPE, Counter32, Integer32, Counter64, OBJECT-IDENTITY, NOTIFICATION-TYPE
		FROM SNMPv2-SMI;
		acosRuleSet MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "RuleSet OID for ACOS"
				::=  {  acosRootStats 138  }

acosRuleSet                         OBJECT IDENTIFIER ::= { acosRootStats 138 }
acosRuleSetS                        OBJECT IDENTIFIER ::= { acosRuleSet 1 }

ruleSetSTable OBJECT-TYPE
		SYNTAX SEQUENCE OF RuleSetSEntry
		MAX-ACCESS not-accessible
		STATUS current
		::={ acosRuleSetS 1 } 


	ruleSetSEntry OBJECT-TYPE
		SYNTAX RuleSetSEntry
		MAX-ACCESS not-accessible
		STATUS current
		INDEX {
			name
		}
		::={ ruleSetSTable 1 } 


	RuleSetSEntry ::=
		SEQUENCE {
			name DisplayString, 
			unmatchedDrops CounterBasedGauge64,
			permit CounterBasedGauge64,
			deny CounterBasedGauge64,
			reset CounterBasedGauge64
		}

			name OBJECT-TYPE
			SYNTAX  DisplayString 
			MAX-ACCESS read-only 
			STATUS current
			DESCRIPTION  "Rule set name" 
			::={ ruleSetSEntry 1 } 

			unmatchedDrops OBJECT-TYPE
			SYNTAX  CounterBasedGauge64 
			MAX-ACCESS read-only 
			STATUS current
			DESCRIPTION  "Unmatched drops counter" 
			::={ ruleSetSEntry 2 } 

			permit OBJECT-TYPE
			SYNTAX  CounterBasedGauge64 
			MAX-ACCESS read-only 
			STATUS current
			DESCRIPTION  "Permitted counter" 
			::={ ruleSetSEntry 3 } 

			deny OBJECT-TYPE
			SYNTAX  CounterBasedGauge64 
			MAX-ACCESS read-only 
			STATUS current
			DESCRIPTION  "Denied counter" 
			::={ ruleSetSEntry 4 } 

			reset OBJECT-TYPE
			SYNTAX  CounterBasedGauge64 
			MAX-ACCESS read-only 
			STATUS current
			DESCRIPTION  "Reset counter" 
			::={ ruleSetSEntry 5 } 

END

ACOS-SCTP-STATS-MIB DEFINITIONS ::= BEGIN
	IMPORTS
		DisplayString, PhysAddress
		FROM SNMPv2-TC
	InetAddressType
		FROM INET-ADDRESS-MIB
	acosRootStats
		FROM A10-AX-MIB
	MODULE-IDENTITY, OBJECT-TYPE, Counter32, Integer32, Counter64, OBJECT-IDENTITY, NOTIFICATION-TYPE
		FROM SNMPv2-SMI;
		acosSctp MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "Sctp OID for ACOS"
				::=  {  acosRootStats 168  }

acosSctpGlobal                      OBJECT IDENTIFIER ::= { acosSctp 1 }
acosSctpGlobalS                     OBJECT IDENTIFIER ::= { acosSctpGlobal 1 }

		sctpStaticNatSessionCreated OBJECT-TYPE
		SYNTAX  CounterBasedGauge64 
		MAX-ACCESS read-only 
		STATUS current
		DESCRIPTION  "SCTP Static NAT Session Created" 
		::={ acosSctpGlobalS 1 } 

		sctpStaticNatSessionDeleted OBJECT-TYPE
		SYNTAX  CounterBasedGauge64 
		MAX-ACCESS read-only 
		STATUS current
		DESCRIPTION  "SCTP Static NAT Session Deleted" 
		::={ acosSctpGlobalS 2 } 

		sctpFirewallSessionCreated OBJECT-TYPE
		SYNTAX  CounterBasedGauge64 
		MAX-ACCESS read-only 
		STATUS current
		DESCRIPTION  "SCTP Firewall Session Created" 
		::={ acosSctpGlobalS 3 } 

		sctpFwSessionDeleted OBJECT-TYPE
		SYNTAX  CounterBasedGauge64 
		MAX-ACCESS read-only 
		STATUS current
		DESCRIPTION  "SCTP Firewall Session Deleted" 
		::={ acosSctpGlobalS 4 } 

		pktErrDrop OBJECT-TYPE
		SYNTAX  CounterBasedGauge64 
		MAX-ACCESS read-only 
		STATUS current
		DESCRIPTION  "Packet Error Drop" 
		::={ acosSctpGlobalS 5 } 

		badCsum OBJECT-TYPE
		SYNTAX  CounterBasedGauge64 
		MAX-ACCESS read-only 
		STATUS current
		DESCRIPTION  "Bad Checksum" 
		::={ acosSctpGlobalS 6 } 

		badPayloadDrop OBJECT-TYPE
		SYNTAX  CounterBasedGauge64 
		MAX-ACCESS read-only 
		STATUS current
		DESCRIPTION  "Bad Payload Drop" 
		::={ acosSctpGlobalS 7 } 

		badAlignmentDrop OBJECT-TYPE
		SYNTAX  CounterBasedGauge64 
		MAX-ACCESS read-only 
		STATUS current
		DESCRIPTION  "Bad Alignment Drop" 
		::={ acosSctpGlobalS 8 } 

		oosPktDrop OBJECT-TYPE
		SYNTAX  CounterBasedGauge64 
		MAX-ACCESS read-only 
		STATUS current
		DESCRIPTION  "Out-of-state Packet Drop" 
		::={ acosSctpGlobalS 9 } 

		maxMultiHomeDrop OBJECT-TYPE
		SYNTAX  CounterBasedGauge64 
		MAX-ACCESS read-only 
		STATUS current
		DESCRIPTION  "Maximum Multi-homing IP Addresses Drop" 
		::={ acosSctpGlobalS 10 } 

		multiHomeRemoveIpSkip OBJECT-TYPE
		SYNTAX  CounterBasedGauge64 
		MAX-ACCESS read-only 
		STATUS current
		DESCRIPTION  "Multi-homing Remove IP Parameter Skip" 
		::={ acosSctpGlobalS 11 } 

		multiHomeAddrNotFoundDrop OBJECT-TYPE
		SYNTAX  CounterBasedGauge64 
		MAX-ACCESS read-only 
		STATUS current
		DESCRIPTION  "Multi-homing IP Address Not Found Drop" 
		::={ acosSctpGlobalS 12 } 

		staticNatCfgNotFound OBJECT-TYPE
		SYNTAX  CounterBasedGauge64 
		MAX-ACCESS read-only 
		STATUS current
		DESCRIPTION  "Static NAT Config Not Found Drop" 
		::={ acosSctpGlobalS 13 } 

		cfgErrDrop OBJECT-TYPE
		SYNTAX  CounterBasedGauge64 
		MAX-ACCESS read-only 
		STATUS current
		DESCRIPTION  "Configuration Error Drop" 
		::={ acosSctpGlobalS 14 } 

		vrrpStandbyDrop OBJECT-TYPE
		SYNTAX  CounterBasedGauge64 
		MAX-ACCESS read-only 
		STATUS current
		DESCRIPTION  "NAT Resource VRRP-A Standby Drop" 
		::={ acosSctpGlobalS 15 } 

		invalidFragChunkDrop OBJECT-TYPE
		SYNTAX  CounterBasedGauge64 
		MAX-ACCESS read-only 
		STATUS current
		DESCRIPTION  "Invalid Fragmented Chunks Drop" 
		::={ acosSctpGlobalS 16 } 

		disallowedChunkFiltered OBJECT-TYPE
		SYNTAX  CounterBasedGauge64 
		MAX-ACCESS read-only 
		STATUS current
		DESCRIPTION  "Disallowed Chunk Filtered" 
		::={ acosSctpGlobalS 17 } 

		disallowedPktDrop OBJECT-TYPE
		SYNTAX  CounterBasedGauge64 
		MAX-ACCESS read-only 
		STATUS current
		DESCRIPTION  "Disallowed Packet Drop" 
		::={ acosSctpGlobalS 18 } 

		rateLimitDrop OBJECT-TYPE
		SYNTAX  CounterBasedGauge64 
		MAX-ACCESS read-only 
		STATUS current
		DESCRIPTION  "Rate-limit Drop" 
		::={ acosSctpGlobalS 19 } 

		sbySessionCreated OBJECT-TYPE
		SYNTAX  CounterBasedGauge64 
		MAX-ACCESS read-only 
		STATUS current
		DESCRIPTION  "Standby Session Created" 
		::={ acosSctpGlobalS 20 } 

		sbySessionCreateFail OBJECT-TYPE
		SYNTAX  CounterBasedGauge64 
		MAX-ACCESS read-only 
		STATUS current
		DESCRIPTION  "Standby Session Create Failed" 
		::={ acosSctpGlobalS 21 } 

		sbySessionUpdated OBJECT-TYPE
		SYNTAX  CounterBasedGauge64 
		MAX-ACCESS read-only 
		STATUS current
		DESCRIPTION  "Standby Session Updated" 
		::={ acosSctpGlobalS 22 } 

		sbySessionUpdateFail OBJECT-TYPE
		SYNTAX  CounterBasedGauge64 
		MAX-ACCESS read-only 
		STATUS current
		DESCRIPTION  "Standby Session Update Failed" 
		::={ acosSctpGlobalS 23 } 

		sbyStaticNatCfgNotFound OBJECT-TYPE
		SYNTAX  CounterBasedGauge64 
		MAX-ACCESS read-only 
		STATUS current
		DESCRIPTION  "Static NAT Config Not Found on Standby" 
		::={ acosSctpGlobalS 24 } 

		sctpOutOfSystemMemory OBJECT-TYPE
		SYNTAX  CounterBasedGauge64 
		MAX-ACCESS read-only 
		STATUS current
		DESCRIPTION  "Out of System Memory" 
		::={ acosSctpGlobalS 25 } 

		connExtSizeMax OBJECT-TYPE
		SYNTAX  CounterBasedGauge64 
		MAX-ACCESS read-only 
		STATUS current
		DESCRIPTION  "Max Conn Extension Size" 
		::={ acosSctpGlobalS 26 } 

		badCsumShadow OBJECT-TYPE
		SYNTAX  CounterBasedGauge64 
		MAX-ACCESS read-only 
		STATUS current
		DESCRIPTION  "Bad Checksum Shadow" 
		::={ acosSctpGlobalS 27 } 

		badPayloadDropShadow OBJECT-TYPE
		SYNTAX  CounterBasedGauge64 
		MAX-ACCESS read-only 
		STATUS current
		DESCRIPTION  "Bad Packet Payload Drop Shadow" 
		::={ acosSctpGlobalS 28 } 

		badAlignmentDropShadow OBJECT-TYPE
		SYNTAX  CounterBasedGauge64 
		MAX-ACCESS read-only 
		STATUS current
		DESCRIPTION  "Bad Packet Alignment Drop Shadow" 
		::={ acosSctpGlobalS 29 } 

		sctpChunkTypeInit OBJECT-TYPE
		SYNTAX  CounterBasedGauge64 
		MAX-ACCESS read-only 
		STATUS current
		DESCRIPTION  "SCTP Chunk Type INIT" 
		::={ acosSctpGlobalS 30 } 

		sctpChunkTypeInitAck OBJECT-TYPE
		SYNTAX  CounterBasedGauge64 
		MAX-ACCESS read-only 
		STATUS current
		DESCRIPTION  "SCTP Chunk Type INIT-ACK" 
		::={ acosSctpGlobalS 31 } 

		sctpChunkTypeCookieEcho OBJECT-TYPE
		SYNTAX  CounterBasedGauge64 
		MAX-ACCESS read-only 
		STATUS current
		DESCRIPTION  "SCTP Chunk Type COOKIE-ECHO" 
		::={ acosSctpGlobalS 32 } 

		sctpChunkTypeCookieAck OBJECT-TYPE
		SYNTAX  CounterBasedGauge64 
		MAX-ACCESS read-only 
		STATUS current
		DESCRIPTION  "SCTP Chunk Type COOKIE-ACK" 
		::={ acosSctpGlobalS 33 } 

		sctpChunkTypeSack OBJECT-TYPE
		SYNTAX  CounterBasedGauge64 
		MAX-ACCESS read-only 
		STATUS current
		DESCRIPTION  "SCTP Chunk Type SACK" 
		::={ acosSctpGlobalS 34 } 

		sctpChunkTypeAsconf OBJECT-TYPE
		SYNTAX  CounterBasedGauge64 
		MAX-ACCESS read-only 
		STATUS current
		DESCRIPTION  "SCTP Chunk Type ASCONF" 
		::={ acosSctpGlobalS 35 } 

		sctpChunkTypeAsconfAck OBJECT-TYPE
		SYNTAX  CounterBasedGauge64 
		MAX-ACCESS read-only 
		STATUS current
		DESCRIPTION  "SCTP Chunk Type ASCONF-ACK" 
		::={ acosSctpGlobalS 36 } 

		sctpChunkTypeData OBJECT-TYPE
		SYNTAX  CounterBasedGauge64 
		MAX-ACCESS read-only 
		STATUS current
		DESCRIPTION  "SCTP Chunk Type DATA" 
		::={ acosSctpGlobalS 37 } 

		sctpChunkTypeAbort OBJECT-TYPE
		SYNTAX  CounterBasedGauge64 
		MAX-ACCESS read-only 
		STATUS current
		DESCRIPTION  "SCTP Chunk Type ABORT" 
		::={ acosSctpGlobalS 38 } 

		sctpChunkTypeShutdown OBJECT-TYPE
		SYNTAX  CounterBasedGauge64 
		MAX-ACCESS read-only 
		STATUS current
		DESCRIPTION  "SCTP Chunk Type SHUTDOWN" 
		::={ acosSctpGlobalS 39 } 

		sctpChunkTypeShutdownAck OBJECT-TYPE
		SYNTAX  CounterBasedGauge64 
		MAX-ACCESS read-only 
		STATUS current
		DESCRIPTION  "SCTP Chunk Type SHUTDOWN-ACK" 
		::={ acosSctpGlobalS 40 } 

		sctpChunkTypeShutdownComplete OBJECT-TYPE
		SYNTAX  CounterBasedGauge64 
		MAX-ACCESS read-only 
		STATUS current
		DESCRIPTION  "SCTP Chunk Type SHUTDOWN-COMPLETE" 
		::={ acosSctpGlobalS 41 } 

		sctpChunkTypeErrorOp OBJECT-TYPE
		SYNTAX  CounterBasedGauge64 
		MAX-ACCESS read-only 
		STATUS current
		DESCRIPTION  "SCTP Chunk Type ERROR-OP" 
		::={ acosSctpGlobalS 42 } 

		sctpChunkTypeHeartbeat OBJECT-TYPE
		SYNTAX  CounterBasedGauge64 
		MAX-ACCESS read-only 
		STATUS current
		DESCRIPTION  "SCTP Chunk Type HEARTBEAT" 
		::={ acosSctpGlobalS 43 } 

		sctpChunkTypeHeartbeatAck OBJECT-TYPE
		SYNTAX  CounterBasedGauge64 
		MAX-ACCESS read-only 
		STATUS current
		DESCRIPTION  "SCTP Chunk Type HEARTBEAT-ACK" 
		::={ acosSctpGlobalS 44 } 

		sctpChunkTypeOther OBJECT-TYPE
		SYNTAX  CounterBasedGauge64 
		MAX-ACCESS read-only 
		STATUS current
		DESCRIPTION  "SCTP Chunk Type OTHER" 
		::={ acosSctpGlobalS 45 } 

		sctpHeartbeatNoTuple OBJECT-TYPE
		SYNTAX  CounterBasedGauge64 
		MAX-ACCESS read-only 
		STATUS current
		DESCRIPTION  "SCTP HEARTBEAT/ACK no tuple found" 
		::={ acosSctpGlobalS 46 } 

		sctpDataNoTuple OBJECT-TYPE
		SYNTAX  CounterBasedGauge64 
		MAX-ACCESS read-only 
		STATUS current
		DESCRIPTION  "SCTP DATA chunk no tuple found" 
		::={ acosSctpGlobalS 47 } 

		sctpDataNoExtMatch OBJECT-TYPE
		SYNTAX  CounterBasedGauge64 
		MAX-ACCESS read-only 
		STATUS current
		DESCRIPTION  "SCTP DATA no extended match found" 
		::={ acosSctpGlobalS 48 } 

		sctpChunkTypeInitDrop OBJECT-TYPE
		SYNTAX  CounterBasedGauge64 
		MAX-ACCESS read-only 
		STATUS current
		DESCRIPTION  "SCTP Chunk Type INIT drop" 
		::={ acosSctpGlobalS 49 } 

		sctpChunkTypeInitAckDrop OBJECT-TYPE
		SYNTAX  CounterBasedGauge64 
		MAX-ACCESS read-only 
		STATUS current
		DESCRIPTION  "SCTP Chunk Type INIT-ACK drop" 
		::={ acosSctpGlobalS 50 } 

		sctpChunkTypeShutdownCompleteDrop OBJECT-TYPE
		SYNTAX  CounterBasedGauge64 
		MAX-ACCESS read-only 
		STATUS current
		DESCRIPTION  "SCTP Chunk Type SHUTDOWN-COMPLETE drop" 
		::={ acosSctpGlobalS 51 } 

		sctpChunkTypeAbortDataDrop OBJECT-TYPE
		SYNTAX  CounterBasedGauge64 
		MAX-ACCESS read-only 
		STATUS current
		DESCRIPTION  "SCTP Chunk Type with ABORT and DATA drop" 
		::={ acosSctpGlobalS 52 } 

		sctpChunkHeartBeatClubbed OBJECT-TYPE
		SYNTAX  CounterBasedGauge64 
		MAX-ACCESS read-only 
		STATUS current
		DESCRIPTION  "SCTP HEARTBEAT chunk with other chunk" 
		::={ acosSctpGlobalS 53 } 

		sctpRetxInitAckDrop OBJECT-TYPE
		SYNTAX  CounterBasedGauge64 
		MAX-ACCESS read-only 
		STATUS current
		DESCRIPTION  "SCTP Chunk Type INIT_ACK with retx mismatched vtag drop" 
		::={ acosSctpGlobalS 54 } 

		sctpRouteErrHeartbeatDrop OBJECT-TYPE
		SYNTAX  CounterBasedGauge64 
		MAX-ACCESS read-only 
		STATUS current
		DESCRIPTION  "SCTP HEARTBEAT ROUTE lookup failed drop" 
		::={ acosSctpGlobalS 55 } 

		sctpRerouteFailover OBJECT-TYPE
		SYNTAX  CounterBasedGauge64 
		MAX-ACCESS read-only 
		STATUS current
		DESCRIPTION  "SCTP REROUTE lookup for chunks other than HEARTBEAT" 
		::={ acosSctpGlobalS 56 } 

		sctpRouteErrDrop OBJECT-TYPE
		SYNTAX  CounterBasedGauge64 
		MAX-ACCESS read-only 
		STATUS current
		DESCRIPTION  "SCTP ROUTE lookup failed for chunks other than HEARTBEAT drop" 
		::={ acosSctpGlobalS 57 } 

		sctpNoExtMatch OBJECT-TYPE
		SYNTAX  CounterBasedGauge64 
		MAX-ACCESS read-only 
		STATUS current
		DESCRIPTION  "SCTP no extended match found" 
		::={ acosSctpGlobalS 58 } 

		sctpRetxInitAck OBJECT-TYPE
		SYNTAX  CounterBasedGauge64 
		MAX-ACCESS read-only 
		STATUS current
		DESCRIPTION  "SCTP Chunk Type INIT_ACK retransmitted" 
		::={ acosSctpGlobalS 59 } 

		sctpRetxInitDrop OBJECT-TYPE
		SYNTAX  CounterBasedGauge64 
		MAX-ACCESS read-only 
		STATUS current
		DESCRIPTION  "SCTP Retransmitted INIT drop" 
		::={ acosSctpGlobalS 60 } 

		sctpRetxInit OBJECT-TYPE
		SYNTAX  CounterBasedGauge64 
		MAX-ACCESS read-only 
		STATUS current
		DESCRIPTION  "SCTP Retransmitted INIT" 
		::={ acosSctpGlobalS 61 } 

		sctpAsconfProcessDrop OBJECT-TYPE
		SYNTAX  CounterBasedGauge64 
		MAX-ACCESS read-only 
		STATUS current
		DESCRIPTION  "SCTP ASCONF process drop" 
		::={ acosSctpGlobalS 62 } 

		sctpInitVtagZeroDrop OBJECT-TYPE
		SYNTAX  CounterBasedGauge64 
		MAX-ACCESS read-only 
		STATUS current
		DESCRIPTION  "SCTP INIT VTAG ZERO drop" 
		::={ acosSctpGlobalS 63 } 

		pktLenErrDrop OBJECT-TYPE
		SYNTAX  CounterBasedGauge64 
		MAX-ACCESS read-only 
		STATUS current
		DESCRIPTION  "Invalid Packet Length Drop" 
		::={ acosSctpGlobalS 64 } 

		pktChunkLenErrDrop OBJECT-TYPE
		SYNTAX  CounterBasedGauge64 
		MAX-ACCESS read-only 
		STATUS current
		DESCRIPTION  "Invalid Chunk Length Drop" 
		::={ acosSctpGlobalS 65 } 

		pktAsconfParamLenErrDrop OBJECT-TYPE
		SYNTAX  CounterBasedGauge64 
		MAX-ACCESS read-only 
		STATUS current
		DESCRIPTION  "Invalid Parameter Length Drop" 
		::={ acosSctpGlobalS 66 } 

END

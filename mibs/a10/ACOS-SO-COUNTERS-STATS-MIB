ACOS-SO-COUNTERS-STATS-MIB DEFINITIONS ::= BEGIN
	IMPORTS
		DisplayString, PhysAddress
		FROM SNMPv2-TC
	InetAddressType
		FROM INET-ADDRESS-MIB
	acosRootStats
		FROM A10-AX-MIB
	MODULE-IDENTITY, OBJECT-TYPE, Counter32, Integer32, Counter64, OBJECT-IDENTITY, NOTIFICATION-TYPE
		FROM SNMPv2-SMI;
		acosSoCounters MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "SoCounters OID for ACOS"
				::=  {  acosRootStats 143  }

acosSoCounters                      OBJECT IDENTIFIER ::= { acosRootStats 143 }
acosSoCountersS                     OBJECT IDENTIFIER ::= { acosSoCounters 1 }

		soPktsRcvd OBJECT-TYPE
		SYNTAX  CounterBasedGauge64 
		MAX-ACCESS read-only 
		STATUS current
		DESCRIPTION  "Total data packets received" 
		::={ acosSoCountersS 1 } 

		soRedirectPktsSent OBJECT-TYPE
		SYNTAX  CounterBasedGauge64 
		MAX-ACCESS read-only 
		STATUS current
		DESCRIPTION  "Total packets redirected out of node" 
		::={ acosSoCountersS 2 } 

		soPktsDropped OBJECT-TYPE
		SYNTAX  CounterBasedGauge64 
		MAX-ACCESS read-only 
		STATUS current
		DESCRIPTION  "Total packets dropped" 
		::={ acosSoCountersS 3 } 

		soRedirectedPktsRcvd OBJECT-TYPE
		SYNTAX  CounterBasedGauge64 
		MAX-ACCESS read-only 
		STATUS current
		DESCRIPTION  "Total redirected packets received on node" 
		::={ acosSoCountersS 4 } 

		soFwShadowSessionCreated OBJECT-TYPE
		SYNTAX  CounterBasedGauge64 
		MAX-ACCESS read-only 
		STATUS current
		DESCRIPTION  "FW Shadow Session created" 
		::={ acosSoCountersS 5 } 

		soPktsTrafficMapNotFoundDrop OBJECT-TYPE
		SYNTAX  CounterBasedGauge64 
		MAX-ACCESS read-only 
		STATUS current
		DESCRIPTION  "Traffic MAP Not Found Drop" 
		::={ acosSoCountersS 6 } 

		soSlbPktsRedirectConnAgedOut OBJECT-TYPE
		SYNTAX  CounterBasedGauge64 
		MAX-ACCESS read-only 
		STATUS current
		DESCRIPTION  "Total SLB redirect conns aged out" 
		::={ acosSoCountersS 7 } 

		soPktsScaleoutNotActiveDrop OBJECT-TYPE
		SYNTAX  CounterBasedGauge64 
		MAX-ACCESS read-only 
		STATUS current
		DESCRIPTION  "Scaleout Not Active Drop" 
		::={ acosSoCountersS 8 } 

		soPktsSlbNatReserveFail OBJECT-TYPE
		SYNTAX  CounterBasedGauge64 
		MAX-ACCESS read-only 
		STATUS current
		DESCRIPTION  "Total SLB NAT reserve failures" 
		::={ acosSoCountersS 9 } 

		soPktsSlbNatReleaseFail OBJECT-TYPE
		SYNTAX  CounterBasedGauge64 
		MAX-ACCESS read-only 
		STATUS current
		DESCRIPTION  "Total SLB NAT release failures" 
		::={ acosSoCountersS 10 } 

		soPktsDestMacMismatchDrop OBJECT-TYPE
		SYNTAX  CounterBasedGauge64 
		MAX-ACCESS read-only 
		STATUS current
		DESCRIPTION  "Destination MAC Mistmatch Drop" 
		::={ acosSoCountersS 11 } 

		soPktsL2redirectDestMacZeroDrop OBJECT-TYPE
		SYNTAX  CounterBasedGauge64 
		MAX-ACCESS read-only 
		STATUS current
		DESCRIPTION  "Destination MAC Address zero Drop" 
		::={ acosSoCountersS 12 } 

		soPktsL2redirectInterfaceNotUp OBJECT-TYPE
		SYNTAX  CounterBasedGauge64 
		MAX-ACCESS read-only 
		STATUS current
		DESCRIPTION  "L2redirect Intf is not UP" 
		::={ acosSoCountersS 13 } 

		soPktsL2redirectInvalidRedirectInfoError OBJECT-TYPE
		SYNTAX  CounterBasedGauge64 
		MAX-ACCESS read-only 
		STATUS current
		DESCRIPTION  "Redirect Table Error due to invalid redirect info" 
		::={ acosSoCountersS 14 } 

		soPktsL3RedirectEncapErrorDrop OBJECT-TYPE
		SYNTAX  CounterBasedGauge64 
		MAX-ACCESS read-only 
		STATUS current
		DESCRIPTION  "L3 Redirect encap error drop during transmission" 
		::={ acosSoCountersS 15 } 

		soPktsL3RedirectInnerMacZeroDrop OBJECT-TYPE
		SYNTAX  CounterBasedGauge64 
		MAX-ACCESS read-only 
		STATUS current
		DESCRIPTION  "L3 Redirect inner mac zero drop during transmission" 
		::={ acosSoCountersS 16 } 

		soPktsL3RedirectDecapVlanSanityDrop OBJECT-TYPE
		SYNTAX  CounterBasedGauge64 
		MAX-ACCESS read-only 
		STATUS current
		DESCRIPTION  "L3 Redirect Decap VLAN Sanity Drop during receipt" 
		::={ acosSoCountersS 17 } 

		soPktsL3RedirectDecapNonIpv4VxlanDrop OBJECT-TYPE
		SYNTAX  CounterBasedGauge64 
		MAX-ACCESS read-only 
		STATUS current
		DESCRIPTION  "L3 Redirect received non ipv4 VXLAN packet" 
		::={ acosSoCountersS 18 } 

		soPktsL3RedirectDecapRxEncapParamsDrop OBJECT-TYPE
		SYNTAX  CounterBasedGauge64 
		MAX-ACCESS read-only 
		STATUS current
		DESCRIPTION  "L3 Redirect decap Rx encap params error Drop" 
		::={ acosSoCountersS 19 } 

		soPktsL3RedirectTableError OBJECT-TYPE
		SYNTAX  CounterBasedGauge64 
		MAX-ACCESS read-only 
		STATUS current
		DESCRIPTION  "L3 Redirect Table error Drop" 
		::={ acosSoCountersS 20 } 

		soPktsL3RedirectRcvdInL2ModeDrop OBJECT-TYPE
		SYNTAX  CounterBasedGauge64 
		MAX-ACCESS read-only 
		STATUS current
		DESCRIPTION  "Recevied l3 redirect packets in L2 mode Drop" 
		::={ acosSoCountersS 21 } 

		soPktsL3RedirectFragmentationError OBJECT-TYPE
		SYNTAX  CounterBasedGauge64 
		MAX-ACCESS read-only 
		STATUS current
		DESCRIPTION  "L3 redirect encap Fragmentation error" 
		::={ acosSoCountersS 22 } 

		soPktsL3RedirectTableNoEntryFound OBJECT-TYPE
		SYNTAX  CounterBasedGauge64 
		MAX-ACCESS read-only 
		STATUS current
		DESCRIPTION  "L3 redirect Table no redirect entry found error" 
		::={ acosSoCountersS 23 } 

		soPktsL3RedirectInvalidDevDir OBJECT-TYPE
		SYNTAX  CounterBasedGauge64 
		MAX-ACCESS read-only 
		STATUS current
		DESCRIPTION  "L3 Redirect Invalid Device direction during transmission" 
		::={ acosSoCountersS 24 } 

		soPktsL3RedirectChassisDestMacError OBJECT-TYPE
		SYNTAX  CounterBasedGauge64 
		MAX-ACCESS read-only 
		STATUS current
		DESCRIPTION  "L3 Redirect RX multi-slot Destination MAC Error" 
		::={ acosSoCountersS 25 } 

		soPktsL3RedirectEncapIpv4JumboFragDrop OBJECT-TYPE
		SYNTAX  CounterBasedGauge64 
		MAX-ACCESS read-only 
		STATUS current
		DESCRIPTION  "L3 Redirect ipv4 packet after encap more than max jumbo size" 
		::={ acosSoCountersS 26 } 

		soPktsL3RedirectEncapIpv6JumboFragDrop OBJECT-TYPE
		SYNTAX  CounterBasedGauge64 
		MAX-ACCESS read-only 
		STATUS current
		DESCRIPTION  "L3 Redirect tx ipv6 packet after encap more than max jumbo size" 
		::={ acosSoCountersS 27 } 

		soPktsL3RedirectTooLargePktsInDrop OBJECT-TYPE
		SYNTAX  CounterBasedGauge64 
		MAX-ACCESS read-only 
		STATUS current
		DESCRIPTION  "Received L3 Redirected fragmented packets too large" 
		::={ acosSoCountersS 28 } 

		soSyncFwShadowSessionCreate OBJECT-TYPE
		SYNTAX  CounterBasedGauge64 
		MAX-ACCESS read-only 
		STATUS current
		DESCRIPTION  "Sent Sync message for FW Shadow session creation" 
		::={ acosSoCountersS 29 } 

		soSyncFwShadowSessionDelete OBJECT-TYPE
		SYNTAX  CounterBasedGauge64 
		MAX-ACCESS read-only 
		STATUS current
		DESCRIPTION  "Sent Sync message for FW Shadow session deletion" 
		::={ acosSoCountersS 30 } 

		soSyncFwShadowExt OBJECT-TYPE
		SYNTAX  CounterBasedGauge64 
		MAX-ACCESS read-only 
		STATUS current
		DESCRIPTION  "Sync FW Shadow extension creation/updation" 
		::={ acosSoCountersS 31 } 

		soSyncShadowStatsToActive OBJECT-TYPE
		SYNTAX  CounterBasedGauge64 
		MAX-ACCESS read-only 
		STATUS current
		DESCRIPTION  "Sync Shadow session stats from shadow to active" 
		::={ acosSoCountersS 32 } 

		soFwInternalRuleCount OBJECT-TYPE
		SYNTAX  CounterBasedGauge64 
		MAX-ACCESS read-only 
		STATUS current
		DESCRIPTION  "FW internal rule count" 
		::={ acosSoCountersS 33 } 

		soHcRegistrationDone OBJECT-TYPE
		SYNTAX  CounterBasedGauge64 
		MAX-ACCESS read-only 
		STATUS current
		DESCRIPTION  "Scaleout stats block registered with HC" 
		::={ acosSoCountersS 34 } 

		soHcDeregistrationDone OBJECT-TYPE
		SYNTAX  CounterBasedGauge64 
		MAX-ACCESS read-only 
		STATUS current
		DESCRIPTION  "Scaleout stats block de-registered with HC" 
		::={ acosSoCountersS 35 } 

		soPktsL2redirectVlanRetrievalError OBJECT-TYPE
		SYNTAX  CounterBasedGauge64 
		MAX-ACCESS read-only 
		STATUS current
		DESCRIPTION  "L2 redirect pkt vlan not retrieved" 
		::={ acosSoCountersS 36 } 

		soPktsL2redirectPortRetrievalError OBJECT-TYPE
		SYNTAX  CounterBasedGauge64 
		MAX-ACCESS read-only 
		STATUS current
		DESCRIPTION  "L2 redirect pkt port not retrieved" 
		::={ acosSoCountersS 37 } 

END

ACOS-SYSTEM-OPER-MIB DEFINITIONS ::= BEGIN
	IMPORTS
		DisplayString, PhysAddress
		FROM SNMPv2-TC
	InetAddressType
		FROM INET-ADDRESS-MIB
	acosRootOper
		FROM A10-AX-MIB
	MODULE-IDENTITY, OBJECT-TYPE, Counter32, Integer32, Counter64, OBJECT-IDENTITY, NOTIFICATION-TYPE
		FROM SNMPv2-SMI;
		acosSystem MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "System OID for ACOS"
				::=  {  acosRootOper 39  }

acosSystem                          OBJECT IDENTIFIER ::= { acosRootOper 39 }
acosSystemMemory                    OBJECT IDENTIFIER ::= { acosSystem 22 }

		Total OBJECT-TYPE
		SYNTAX  CounterBasedGauge64 
		MAX-ACCESS read-only 
		STATUS current
		DESCRIPTION  "" 
		::={ acosSystemMemory 1 } 

acosSystemHardware                  OBJECT IDENTIFIER ::= { acosSystem 32 }

		platformDescription OBJECT-TYPE
		SYNTAX  DisplayString 
		MAX-ACCESS read-only 
		STATUS current
		DESCRIPTION  "" 
		::={ acosSystemHardware 1 } 

		serial OBJECT-TYPE
		SYNTAX  DisplayString 
		MAX-ACCESS read-only 
		STATUS current
		DESCRIPTION  "" 
		::={ acosSystemHardware 2 } 

		cpu OBJECT-TYPE
		SYNTAX  DisplayString 
		MAX-ACCESS read-only 
		STATUS current
		DESCRIPTION  "" 
		::={ acosSystemHardware 3 } 

		cpuCores OBJECT-TYPE
		SYNTAX  CounterBasedGauge64 
		MAX-ACCESS read-only 
		STATUS current
		DESCRIPTION  "" 
		::={ acosSystemHardware 4 } 

		cpuStepping OBJECT-TYPE
		SYNTAX  CounterBasedGauge64 
		MAX-ACCESS read-only 
		STATUS current
		DESCRIPTION  "" 
		::={ acosSystemHardware 5 } 

		storage OBJECT-TYPE
		SYNTAX  DisplayString 
		MAX-ACCESS read-only 
		STATUS current
		DESCRIPTION  "" 
		::={ acosSystemHardware 6 } 

		memory OBJECT-TYPE
		SYNTAX  DisplayString 
		MAX-ACCESS read-only 
		STATUS current
		DESCRIPTION  "" 
		::={ acosSystemHardware 7 } 

END

ACOS-TRAFFIC-CONTROL-STATS-MIB DEFINITIONS ::= BEGIN
	IMPORTS
		DisplayString, PhysAddress
		FROM SNMPv2-TC
	InetAddressType
		FROM INET-ADDRESS-MIB
	acosRootStats
		FROM A10-AX-MIB
	MODULE-IDENTITY, OBJECT-TYPE, Counter32, Integer32, Counter64, OBJECT-IDENTITY, NOTIFICATION-TYPE
		FROM SNMPv2-SMI;
		acosTrafficControl MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "TrafficControl OID for ACOS"
				::=  {  acosRootStats 197  }

acosTrafficControlRuleSet           OBJECT IDENTIFIER ::= { acosTrafficControl 2 }
acosTrafficControlRuleSetS          OBJECT IDENTIFIER ::= { acosTrafficControlRuleSet 1 }

trafficControlRuleSetSTable OBJECT-TYPE
		SYNTAX SEQUENCE OF TrafficControlRuleSetSEntry
		MAX-ACCESS not-accessible
		STATUS current
		::={ acosTrafficControlRuleSetS 1 } 


	trafficControlRuleSetSEntry OBJECT-TYPE
		SYNTAX TrafficControlRuleSetSEntry
		MAX-ACCESS not-accessible
		STATUS current
		INDEX {
			name
		}
		::={ trafficControlRuleSetSTable 1 } 


	TrafficControlRuleSetSEntry ::=
		SEQUENCE {
			name DisplayString, 
			hitCount CounterBasedGauge64
		}

			name OBJECT-TYPE
			SYNTAX  DisplayString 
			MAX-ACCESS read-only 
			STATUS current
			DESCRIPTION  "Rule set name" 
			::={ trafficControlRuleSetSEntry 1 } 

			hitCount OBJECT-TYPE
			SYNTAX  CounterBasedGauge64 
			MAX-ACCESS read-only 
			STATUS current
			DESCRIPTION  "Hit counts" 
			::={ trafficControlRuleSetSEntry 2 } 

END

ACOS-WAF-STATS-MIB DEFINITIONS ::= BEGIN
	IMPORTS
		DisplayString, PhysAddress
		FROM SNMPv2-TC
	InetAddressType
		FROM INET-ADDRESS-MIB
	acosRootStats
		FROM A10-AX-MIB
	MODULE-IDENTITY, OBJECT-TYPE, Counter32, Integer32, Counter64, OBJECT-IDENTITY, NOTIFICATION-TYPE
		FROM SNMPv2-SMI;
		acosWaf MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "Waf OID for ACOS"
				::=  {  acosRootStats 111  }

acosWafGlobal                       OBJECT IDENTIFIER ::= { acosWaf 1 }
acosWafGlobalS                      OBJECT IDENTIFIER ::= { acosWafGlobal 1 }

		totalReq OBJECT-TYPE
		SYNTAX  CounterBasedGauge64 
		MAX-ACCESS read-only 
		STATUS current
		DESCRIPTION  "Total Requests" 
		::={ acosWafGlobalS 1 } 

		reqAllowed OBJECT-TYPE
		SYNTAX  CounterBasedGauge64 
		MAX-ACCESS read-only 
		STATUS current
		DESCRIPTION  "Requests Allowed" 
		::={ acosWafGlobalS 2 } 

		reqDenied OBJECT-TYPE
		SYNTAX  CounterBasedGauge64 
		MAX-ACCESS read-only 
		STATUS current
		DESCRIPTION  "Requests Denied" 
		::={ acosWafGlobalS 3 } 

		respDenied OBJECT-TYPE
		SYNTAX  CounterBasedGauge64 
		MAX-ACCESS read-only 
		STATUS current
		DESCRIPTION  "Responses Denied" 
		::={ acosWafGlobalS 4 } 

		bruteForceSuccess OBJECT-TYPE
		SYNTAX  CounterBasedGauge64 
		MAX-ACCESS read-only 
		STATUS current
		DESCRIPTION  "Brute-Force checks passed" 
		::={ acosWafGlobalS 5 } 

		bruteForceViolation OBJECT-TYPE
		SYNTAX  CounterBasedGauge64 
		MAX-ACCESS read-only 
		STATUS current
		DESCRIPTION  "Brute-Force checks violation" 
		::={ acosWafGlobalS 6 } 

		bruteForceChallengeCookieSent OBJECT-TYPE
		SYNTAX  CounterBasedGauge64 
		MAX-ACCESS read-only 
		STATUS current
		DESCRIPTION  "Cookie Challenge Sent" 
		::={ acosWafGlobalS 7 } 

		bruteForceChallengeCookieSuccess OBJECT-TYPE
		SYNTAX  CounterBasedGauge64 
		MAX-ACCESS read-only 
		STATUS current
		DESCRIPTION  "Cookie Challenge check passed" 
		::={ acosWafGlobalS 8 } 

		bruteForceChallengeCookieViolation OBJECT-TYPE
		SYNTAX  CounterBasedGauge64 
		MAX-ACCESS read-only 
		STATUS current
		DESCRIPTION  "Cookie challenge violation" 
		::={ acosWafGlobalS 9 } 

		bruteForceChallengeJavascriptSent OBJECT-TYPE
		SYNTAX  CounterBasedGauge64 
		MAX-ACCESS read-only 
		STATUS current
		DESCRIPTION  "JavaScript challenge sent" 
		::={ acosWafGlobalS 10 } 

		bruteForceChallengeJavascriptSuccess OBJECT-TYPE
		SYNTAX  CounterBasedGauge64 
		MAX-ACCESS read-only 
		STATUS current
		DESCRIPTION  "JavaScript challenge check passed" 
		::={ acosWafGlobalS 11 } 

		bruteForceChallengeJavascriptViolation OBJECT-TYPE
		SYNTAX  CounterBasedGauge64 
		MAX-ACCESS read-only 
		STATUS current
		DESCRIPTION  "JavaScript challenge violation" 
		::={ acosWafGlobalS 12 } 

		bruteForceChallengeCaptchaSent OBJECT-TYPE
		SYNTAX  CounterBasedGauge64 
		MAX-ACCESS read-only 
		STATUS current
		DESCRIPTION  "Captcha challenge sent" 
		::={ acosWafGlobalS 13 } 

		bruteForceChallengeCaptchaSuccess OBJECT-TYPE
		SYNTAX  CounterBasedGauge64 
		MAX-ACCESS read-only 
		STATUS current
		DESCRIPTION  "Captcha challenge check passed" 
		::={ acosWafGlobalS 14 } 

		bruteForceChallengeCaptchaViolation OBJECT-TYPE
		SYNTAX  CounterBasedGauge64 
		MAX-ACCESS read-only 
		STATUS current
		DESCRIPTION  "Captcha challenge violation" 
		::={ acosWafGlobalS 15 } 

		bruteForceLockoutLimitSuccess OBJECT-TYPE
		SYNTAX  CounterBasedGauge64 
		MAX-ACCESS read-only 
		STATUS current
		DESCRIPTION  "Lockout limit check passed" 
		::={ acosWafGlobalS 16 } 

		bruteForceLockoutLimitViolation OBJECT-TYPE
		SYNTAX  CounterBasedGauge64 
		MAX-ACCESS read-only 
		STATUS current
		DESCRIPTION  "Lockout limit violation" 
		::={ acosWafGlobalS 17 } 

		bruteForceChallengeLimitSuccess OBJECT-TYPE
		SYNTAX  CounterBasedGauge64 
		MAX-ACCESS read-only 
		STATUS current
		DESCRIPTION  "Lockout limit check passed" 
		::={ acosWafGlobalS 18 } 

		bruteForceChallengeLimitViolation OBJECT-TYPE
		SYNTAX  CounterBasedGauge64 
		MAX-ACCESS read-only 
		STATUS current
		DESCRIPTION  "Lockout limit violation" 
		::={ acosWafGlobalS 19 } 

		bruteForceResponseCodesTriggered OBJECT-TYPE
		SYNTAX  CounterBasedGauge64 
		MAX-ACCESS read-only 
		STATUS current
		DESCRIPTION  "Response Codes Triggered" 
		::={ acosWafGlobalS 20 } 

		bruteForceResponseHeadersTriggered OBJECT-TYPE
		SYNTAX  CounterBasedGauge64 
		MAX-ACCESS read-only 
		STATUS current
		DESCRIPTION  "Brute Force Response Headers Triggered" 
		::={ acosWafGlobalS 21 } 

		bruteForceResponseStringTriggered OBJECT-TYPE
		SYNTAX  CounterBasedGauge64 
		MAX-ACCESS read-only 
		STATUS current
		DESCRIPTION  "Brute Force Response string Triggered" 
		::={ acosWafGlobalS 22 } 

		cookieSecurityEncryptSuccess OBJECT-TYPE
		SYNTAX  CounterBasedGauge64 
		MAX-ACCESS read-only 
		STATUS current
		DESCRIPTION  "Cookie Security - encrypt successful" 
		::={ acosWafGlobalS 23 } 

		cookieSecurityEncryptViolation OBJECT-TYPE
		SYNTAX  CounterBasedGauge64 
		MAX-ACCESS read-only 
		STATUS current
		DESCRIPTION  "Cookie Security - encrypt violation" 
		::={ acosWafGlobalS 24 } 

		cookieSecurityEncryptLimitExceeded OBJECT-TYPE
		SYNTAX  CounterBasedGauge64 
		MAX-ACCESS read-only 
		STATUS current
		DESCRIPTION  "Cookie Security - encrypt limit exceeded" 
		::={ acosWafGlobalS 25 } 

		cookieSecurityEncryptSkipRcache OBJECT-TYPE
		SYNTAX  CounterBasedGauge64 
		MAX-ACCESS read-only 
		STATUS current
		DESCRIPTION  "Cookie Security - encrypt skipped - RAM cache" 
		::={ acosWafGlobalS 26 } 

		cookieSecurityDecryptSuccess OBJECT-TYPE
		SYNTAX  CounterBasedGauge64 
		MAX-ACCESS read-only 
		STATUS current
		DESCRIPTION  "Cookie Security - decrypt successful" 
		::={ acosWafGlobalS 27 } 

		cookieSecurityDecryptViolation OBJECT-TYPE
		SYNTAX  CounterBasedGauge64 
		MAX-ACCESS read-only 
		STATUS current
		DESCRIPTION  "Cookie Security - decrypt violation" 
		::={ acosWafGlobalS 28 } 

		cookieSecuritySignSuccess OBJECT-TYPE
		SYNTAX  CounterBasedGauge64 
		MAX-ACCESS read-only 
		STATUS current
		DESCRIPTION  "Cookie Security - signing successful" 
		::={ acosWafGlobalS 29 } 

		cookieSecuritySignViolation OBJECT-TYPE
		SYNTAX  CounterBasedGauge64 
		MAX-ACCESS read-only 
		STATUS current
		DESCRIPTION  "Cookie Security - signing violation" 
		::={ acosWafGlobalS 30 } 

		cookieSecuritySignLimitExceeded OBJECT-TYPE
		SYNTAX  CounterBasedGauge64 
		MAX-ACCESS read-only 
		STATUS current
		DESCRIPTION  "Cookie Security - signing limit exceeded" 
		::={ acosWafGlobalS 31 } 

		cookieSecuritySignSkipRcache OBJECT-TYPE
		SYNTAX  CounterBasedGauge64 
		MAX-ACCESS read-only 
		STATUS current
		DESCRIPTION  "Cookie Security - signing skipped - RAM cache" 
		::={ acosWafGlobalS 32 } 

		cookieSecuritySignatureCheckSuccess OBJECT-TYPE
		SYNTAX  CounterBasedGauge64 
		MAX-ACCESS read-only 
		STATUS current
		DESCRIPTION  "Cookie Security - signature check successful" 
		::={ acosWafGlobalS 33 } 

		cookieSecuritySignatureCheckViolation OBJECT-TYPE
		SYNTAX  CounterBasedGauge64 
		MAX-ACCESS read-only 
		STATUS current
		DESCRIPTION  "Cookie Security - signature check failed" 
		::={ acosWafGlobalS 34 } 

		cookieSecurityAddHttpOnlySuccess OBJECT-TYPE
		SYNTAX  CounterBasedGauge64 
		MAX-ACCESS read-only 
		STATUS current
		DESCRIPTION  "Cookie Security - http-only flag added successfully" 
		::={ acosWafGlobalS 35 } 

		cookieSecurityAddHttpOnlyViolation OBJECT-TYPE
		SYNTAX  CounterBasedGauge64 
		MAX-ACCESS read-only 
		STATUS current
		DESCRIPTION  "Cookie Security - http-only flag violation" 
		::={ acosWafGlobalS 36 } 

		cookieSecurityAddSecureSuccess OBJECT-TYPE
		SYNTAX  CounterBasedGauge64 
		MAX-ACCESS read-only 
		STATUS current
		DESCRIPTION  "Cookie Security - secure flag added successfully" 
		::={ acosWafGlobalS 37 } 

		cookieSecurityAddSecureViolation OBJECT-TYPE
		SYNTAX  CounterBasedGauge64 
		MAX-ACCESS read-only 
		STATUS current
		DESCRIPTION  "Cookie Security - secure flag violation" 
		::={ acosWafGlobalS 38 } 

		cookieSecurityMissingCookieSuccess OBJECT-TYPE
		SYNTAX  CounterBasedGauge64 
		MAX-ACCESS read-only 
		STATUS current
		DESCRIPTION  "Cookie Security - request with missing cookie" 
		::={ acosWafGlobalS 39 } 

		cookieSecurityMissingCookieViolation OBJECT-TYPE
		SYNTAX  CounterBasedGauge64 
		MAX-ACCESS read-only 
		STATUS current
		DESCRIPTION  "Cookie Security - missing cookie violation" 
		::={ acosWafGlobalS 40 } 

		cookieSecurityUnrecognizedCookieSuccess OBJECT-TYPE
		SYNTAX  CounterBasedGauge64 
		MAX-ACCESS read-only 
		STATUS current
		DESCRIPTION  "Cookie Security - request with unrecognized cookie" 
		::={ acosWafGlobalS 41 } 

		cookieSecurityUnrecognizedCookieViolation OBJECT-TYPE
		SYNTAX  CounterBasedGauge64 
		MAX-ACCESS read-only 
		STATUS current
		DESCRIPTION  "Cookie Security - unrecognized cookie violation" 
		::={ acosWafGlobalS 42 } 

		cookieSecurityCookiePolicySuccess OBJECT-TYPE
		SYNTAX  CounterBasedGauge64 
		MAX-ACCESS read-only 
		STATUS current
		DESCRIPTION  "Cookie Security - cookie policy passed" 
		::={ acosWafGlobalS 43 } 

		cookieSecurityCookiePolicyViolation OBJECT-TYPE
		SYNTAX  CounterBasedGauge64 
		MAX-ACCESS read-only 
		STATUS current
		DESCRIPTION  "Cookie Security - cookie policy violation" 
		::={ acosWafGlobalS 44 } 

		cookieSecurityPersistentCookies OBJECT-TYPE
		SYNTAX  CounterBasedGauge64 
		MAX-ACCESS read-only 
		STATUS current
		DESCRIPTION  "Cookie Security - persistent cookies" 
		::={ acosWafGlobalS 45 } 

		cookieSecurityPersistentCookiesEncrypted OBJECT-TYPE
		SYNTAX  CounterBasedGauge64 
		MAX-ACCESS read-only 
		STATUS current
		DESCRIPTION  "Cookie Security - encrypted persistent cookies" 
		::={ acosWafGlobalS 46 } 

		cookieSecurityPersistentCookiesSigned OBJECT-TYPE
		SYNTAX  CounterBasedGauge64 
		MAX-ACCESS read-only 
		STATUS current
		DESCRIPTION  "Cookie Security - signed persistent cookies" 
		::={ acosWafGlobalS 47 } 

		cookieSecuritySessionCookies OBJECT-TYPE
		SYNTAX  CounterBasedGauge64 
		MAX-ACCESS read-only 
		STATUS current
		DESCRIPTION  "Cookie Security - session cookies" 
		::={ acosWafGlobalS 48 } 

		cookieSecuritySessionCookiesEncrypted OBJECT-TYPE
		SYNTAX  CounterBasedGauge64 
		MAX-ACCESS read-only 
		STATUS current
		DESCRIPTION  "Cookie Security - encrypted session cookies" 
		::={ acosWafGlobalS 49 } 

		cookieSecuritySessionCookiesSigned OBJECT-TYPE
		SYNTAX  CounterBasedGauge64 
		MAX-ACCESS read-only 
		STATUS current
		DESCRIPTION  "Cookie Security - signed session cookies" 
		::={ acosWafGlobalS 50 } 

		cookieSecurityAllowedSessionCookies OBJECT-TYPE
		SYNTAX  CounterBasedGauge64 
		MAX-ACCESS read-only 
		STATUS current
		DESCRIPTION  "Cookie Security - allowed session cookies" 
		::={ acosWafGlobalS 51 } 

		cookieSecurityAllowedPersistentCookies OBJECT-TYPE
		SYNTAX  CounterBasedGauge64 
		MAX-ACCESS read-only 
		STATUS current
		DESCRIPTION  "Cookie Security - allowed persistent cookies" 
		::={ acosWafGlobalS 52 } 

		cookieSecurityDisallowedSessionCookies OBJECT-TYPE
		SYNTAX  CounterBasedGauge64 
		MAX-ACCESS read-only 
		STATUS current
		DESCRIPTION  "Cookie Security - disallowed session cookies" 
		::={ acosWafGlobalS 53 } 

		cookieSecurityDisallowedPersistentCookies OBJECT-TYPE
		SYNTAX  CounterBasedGauge64 
		MAX-ACCESS read-only 
		STATUS current
		DESCRIPTION  "Cookie Security - disallowed persistent cookies" 
		::={ acosWafGlobalS 54 } 

		cookieSecurityAllowedSessionSetCookies OBJECT-TYPE
		SYNTAX  CounterBasedGauge64 
		MAX-ACCESS read-only 
		STATUS current
		DESCRIPTION  "Cookie Security - allowed session Set-Cookies" 
		::={ acosWafGlobalS 55 } 

		cookieSecurityAllowedPersistentSetCookies OBJECT-TYPE
		SYNTAX  CounterBasedGauge64 
		MAX-ACCESS read-only 
		STATUS current
		DESCRIPTION  "Cookie Security - allowed persistent Set-Cookies" 
		::={ acosWafGlobalS 56 } 

		cookieSecurityDisallowedSessionSetCookies OBJECT-TYPE
		SYNTAX  CounterBasedGauge64 
		MAX-ACCESS read-only 
		STATUS current
		DESCRIPTION  "Cookie Security - disallowed session Set-Cookies" 
		::={ acosWafGlobalS 57 } 

		cookieSecurityDisallowedPersistentSetCookies OBJECT-TYPE
		SYNTAX  CounterBasedGauge64 
		MAX-ACCESS read-only 
		STATUS current
		DESCRIPTION  "Cookie Security - disallowed persistent Set-Cookies" 
		::={ acosWafGlobalS 58 } 

		cspHeaderViolation OBJECT-TYPE
		SYNTAX  CounterBasedGauge64 
		MAX-ACCESS read-only 
		STATUS current
		DESCRIPTION  "CSP header_missing" 
		::={ acosWafGlobalS 59 } 

		cspHeaderSuccess OBJECT-TYPE
		SYNTAX  CounterBasedGauge64 
		MAX-ACCESS read-only 
		STATUS current
		DESCRIPTION  "CSP header found" 
		::={ acosWafGlobalS 60 } 

		cspHeaderInserted OBJECT-TYPE
		SYNTAX  CounterBasedGauge64 
		MAX-ACCESS read-only 
		STATUS current
		DESCRIPTION  "CSP header Inserted" 
		::={ acosWafGlobalS 61 } 

		formCsrfTagSuccess OBJECT-TYPE
		SYNTAX  CounterBasedGauge64 
		MAX-ACCESS read-only 
		STATUS current
		DESCRIPTION  "Form CSRF tag passed" 
		::={ acosWafGlobalS 62 } 

		formCsrfTagViolation OBJECT-TYPE
		SYNTAX  CounterBasedGauge64 
		MAX-ACCESS read-only 
		STATUS current
		DESCRIPTION  "Form CSRF tag violation" 
		::={ acosWafGlobalS 63 } 

		formConsistencySuccess OBJECT-TYPE
		SYNTAX  CounterBasedGauge64 
		MAX-ACCESS read-only 
		STATUS current
		DESCRIPTION  "Form Consistency passed" 
		::={ acosWafGlobalS 64 } 

		formConsistencyViolation OBJECT-TYPE
		SYNTAX  CounterBasedGauge64 
		MAX-ACCESS read-only 
		STATUS current
		DESCRIPTION  "Form Consistency violation" 
		::={ acosWafGlobalS 65 } 

		formTagInserted OBJECT-TYPE
		SYNTAX  CounterBasedGauge64 
		MAX-ACCESS read-only 
		STATUS current
		DESCRIPTION  "Form A10 Tag Inserted" 
		::={ acosWafGlobalS 66 } 

		formNonSslSuccess OBJECT-TYPE
		SYNTAX  CounterBasedGauge64 
		MAX-ACCESS read-only 
		STATUS current
		DESCRIPTION  "Form Non SSL check passed" 
		::={ acosWafGlobalS 67 } 

		formNonSslViolation OBJECT-TYPE
		SYNTAX  CounterBasedGauge64 
		MAX-ACCESS read-only 
		STATUS current
		DESCRIPTION  "Form Non SSL violation" 
		::={ acosWafGlobalS 68 } 

		formRequestNonPostSuccess OBJECT-TYPE
		SYNTAX  CounterBasedGauge64 
		MAX-ACCESS read-only 
		STATUS current
		DESCRIPTION  "Form Method being Non Post in Request passed" 
		::={ acosWafGlobalS 69 } 

		formRequestNonPostViolation OBJECT-TYPE
		SYNTAX  CounterBasedGauge64 
		MAX-ACCESS read-only 
		STATUS current
		DESCRIPTION  "Form Method being Non Post in Request violation" 
		::={ acosWafGlobalS 70 } 

		formCheckSuccess OBJECT-TYPE
		SYNTAX  CounterBasedGauge64 
		MAX-ACCESS read-only 
		STATUS current
		DESCRIPTION  "Post Form Check passed" 
		::={ acosWafGlobalS 71 } 

		formCheckViolation OBJECT-TYPE
		SYNTAX  CounterBasedGauge64 
		MAX-ACCESS read-only 
		STATUS current
		DESCRIPTION  "Post Form Check violation" 
		::={ acosWafGlobalS 72 } 

		formCheckSanitize OBJECT-TYPE
		SYNTAX  CounterBasedGauge64 
		MAX-ACCESS read-only 
		STATUS current
		DESCRIPTION  "Post Form Check Sanitized" 
		::={ acosWafGlobalS 73 } 

		formNonMaskedPasswordSuccess OBJECT-TYPE
		SYNTAX  CounterBasedGauge64 
		MAX-ACCESS read-only 
		STATUS current
		DESCRIPTION  "Form Non Masked Password check passed" 
		::={ acosWafGlobalS 74 } 

		formNonMaskedPasswordViolation OBJECT-TYPE
		SYNTAX  CounterBasedGauge64 
		MAX-ACCESS read-only 
		STATUS current
		DESCRIPTION  "Form Non Masked Password violation" 
		::={ acosWafGlobalS 75 } 

		formNonSslPasswordSuccess OBJECT-TYPE
		SYNTAX  CounterBasedGauge64 
		MAX-ACCESS read-only 
		STATUS current
		DESCRIPTION  "Form Non SSL Password check passed" 
		::={ acosWafGlobalS 76 } 

		formNonSslPasswordViolation OBJECT-TYPE
		SYNTAX  CounterBasedGauge64 
		MAX-ACCESS read-only 
		STATUS current
		DESCRIPTION  "Form Non SSL Password violation" 
		::={ acosWafGlobalS 77 } 

		formPasswordAutocompleteSuccess OBJECT-TYPE
		SYNTAX  CounterBasedGauge64 
		MAX-ACCESS read-only 
		STATUS current
		DESCRIPTION  "Form Password Autocomplete check passed" 
		::={ acosWafGlobalS 78 } 

		formPasswordAutocompleteViolation OBJECT-TYPE
		SYNTAX  CounterBasedGauge64 
		MAX-ACCESS read-only 
		STATUS current
		DESCRIPTION  "Form Password Autocomplete violation" 
		::={ acosWafGlobalS 79 } 

		formSetNoCacheSuccess OBJECT-TYPE
		SYNTAX  CounterBasedGauge64 
		MAX-ACCESS read-only 
		STATUS current
		DESCRIPTION  "Form Set No Cache check passed" 
		::={ acosWafGlobalS 80 } 

		formSetNoCache OBJECT-TYPE
		SYNTAX  CounterBasedGauge64 
		MAX-ACCESS read-only 
		STATUS current
		DESCRIPTION  "Form Set No Cache violation" 
		::={ acosWafGlobalS 81 } 

		dlpCcnSuccess OBJECT-TYPE
		SYNTAX  CounterBasedGauge64 
		MAX-ACCESS read-only 
		STATUS current
		DESCRIPTION  "Credit Card Number check passed" 
		::={ acosWafGlobalS 82 } 

		dlpCcnAmexViolation OBJECT-TYPE
		SYNTAX  CounterBasedGauge64 
		MAX-ACCESS read-only 
		STATUS current
		DESCRIPTION  "Amex Credit Card Number Detected" 
		::={ acosWafGlobalS 83 } 

		dlpCcnAmexMasked OBJECT-TYPE
		SYNTAX  CounterBasedGauge64 
		MAX-ACCESS read-only 
		STATUS current
		DESCRIPTION  "Amex Credit Card Number Masked" 
		::={ acosWafGlobalS 84 } 

		dlpCcnDinersViolation OBJECT-TYPE
		SYNTAX  CounterBasedGauge64 
		MAX-ACCESS read-only 
		STATUS current
		DESCRIPTION  "Diners Club Credit Card Number Detected" 
		::={ acosWafGlobalS 85 } 

		dlpCcnDinersMasked OBJECT-TYPE
		SYNTAX  CounterBasedGauge64 
		MAX-ACCESS read-only 
		STATUS current
		DESCRIPTION  "Diners Club Credit Card Number Masked" 
		::={ acosWafGlobalS 86 } 

		dlpCcnVisaViolation OBJECT-TYPE
		SYNTAX  CounterBasedGauge64 
		MAX-ACCESS read-only 
		STATUS current
		DESCRIPTION  "Visa Credit Card Number Detected" 
		::={ acosWafGlobalS 87 } 

		dlpCcnVisaMasked OBJECT-TYPE
		SYNTAX  CounterBasedGauge64 
		MAX-ACCESS read-only 
		STATUS current
		DESCRIPTION  "Visa Credit Card Number Masked" 
		::={ acosWafGlobalS 88 } 

		dlpCcnMastercardViolation OBJECT-TYPE
		SYNTAX  CounterBasedGauge64 
		MAX-ACCESS read-only 
		STATUS current
		DESCRIPTION  "MasterCard Credit Card Number Detected" 
		::={ acosWafGlobalS 89 } 

		dlpCcnMastercardMasked OBJECT-TYPE
		SYNTAX  CounterBasedGauge64 
		MAX-ACCESS read-only 
		STATUS current
		DESCRIPTION  "MasterCard Credit Card Number Masked" 
		::={ acosWafGlobalS 90 } 

		dlpCcnDiscoverViolation OBJECT-TYPE
		SYNTAX  CounterBasedGauge64 
		MAX-ACCESS read-only 
		STATUS current
		DESCRIPTION  "Discover Credit Card Number Detected" 
		::={ acosWafGlobalS 91 } 

		dlpCcnDiscoverMasked OBJECT-TYPE
		SYNTAX  CounterBasedGauge64 
		MAX-ACCESS read-only 
		STATUS current
		DESCRIPTION  "Discover Credit Card Number Masked" 
		::={ acosWafGlobalS 92 } 

		dlpCcnJcbViolation OBJECT-TYPE
		SYNTAX  CounterBasedGauge64 
		MAX-ACCESS read-only 
		STATUS current
		DESCRIPTION  "JCB Credit Card Number Detected" 
		::={ acosWafGlobalS 93 } 

		dlpCcnJcbMasked OBJECT-TYPE
		SYNTAX  CounterBasedGauge64 
		MAX-ACCESS read-only 
		STATUS current
		DESCRIPTION  "JCB Credit Card Number Masked" 
		::={ acosWafGlobalS 94 } 

		dlpSsnSuccess OBJECT-TYPE
		SYNTAX  CounterBasedGauge64 
		MAX-ACCESS read-only 
		STATUS current
		DESCRIPTION  "Social Security Number Mask check passed" 
		::={ acosWafGlobalS 95 } 

		dlpSsnViolation OBJECT-TYPE
		SYNTAX  CounterBasedGauge64 
		MAX-ACCESS read-only 
		STATUS current
		DESCRIPTION  "Social Security Number Mask violation" 
		::={ acosWafGlobalS 96 } 

		dlpPcreSuccess OBJECT-TYPE
		SYNTAX  CounterBasedGauge64 
		MAX-ACCESS read-only 
		STATUS current
		DESCRIPTION  "PCRE Mask check passed" 
		::={ acosWafGlobalS 97 } 

		dlpPcreViolation OBJECT-TYPE
		SYNTAX  CounterBasedGauge64 
		MAX-ACCESS read-only 
		STATUS current
		DESCRIPTION  "PCRE Mask violation" 
		::={ acosWafGlobalS 98 } 

		dlpPcreMasked OBJECT-TYPE
		SYNTAX  CounterBasedGauge64 
		MAX-ACCESS read-only 
		STATUS current
		DESCRIPTION  "PCRE Mask violation" 
		::={ acosWafGlobalS 99 } 

		evasionCheckApacheWhitespaceSuccess OBJECT-TYPE
		SYNTAX  CounterBasedGauge64 
		MAX-ACCESS read-only 
		STATUS current
		DESCRIPTION  "Apache Whitespace check passed" 
		::={ acosWafGlobalS 100 } 

		evasionCheckApacheWhitespaceViolation OBJECT-TYPE
		SYNTAX  CounterBasedGauge64 
		MAX-ACCESS read-only 
		STATUS current
		DESCRIPTION  "Apache Whitespace check violation" 
		::={ acosWafGlobalS 101 } 

		evasionCheckDecodeEntitiesSuccess OBJECT-TYPE
		SYNTAX  CounterBasedGauge64 
		MAX-ACCESS read-only 
		STATUS current
		DESCRIPTION  "Decode Entities check passed" 
		::={ acosWafGlobalS 102 } 

		evasionCheckDecodeEntitiesViolation OBJECT-TYPE
		SYNTAX  CounterBasedGauge64 
		MAX-ACCESS read-only 
		STATUS current
		DESCRIPTION  "Decode Entities check violation" 
		::={ acosWafGlobalS 103 } 

		evasionCheckDecodeEscapedCharsSuccess OBJECT-TYPE
		SYNTAX  CounterBasedGauge64 
		MAX-ACCESS read-only 
		STATUS current
		DESCRIPTION  "Decode Escaped Chars check passed" 
		::={ acosWafGlobalS 104 } 

		evasionCheckDecodeEscapedCharsViolation OBJECT-TYPE
		SYNTAX  CounterBasedGauge64 
		MAX-ACCESS read-only 
		STATUS current
		DESCRIPTION  "Decode Escaped Chars check violation" 
		::={ acosWafGlobalS 105 } 

		evasionCheckDecodeUnicodeCharsSuccess OBJECT-TYPE
		SYNTAX  CounterBasedGauge64 
		MAX-ACCESS read-only 
		STATUS current
		DESCRIPTION  "Decode Unicode Chars check passed" 
		::={ acosWafGlobalS 106 } 

		evasionCheckDecodeUnicodeCharsViolation OBJECT-TYPE
		SYNTAX  CounterBasedGauge64 
		MAX-ACCESS read-only 
		STATUS current
		DESCRIPTION  "Decode Unicode Chars check violation" 
		::={ acosWafGlobalS 107 } 

		evasionCheckDirTraversalSuccess OBJECT-TYPE
		SYNTAX  CounterBasedGauge64 
		MAX-ACCESS read-only 
		STATUS current
		DESCRIPTION  "Dir traversal check passed" 
		::={ acosWafGlobalS 108 } 

		evasionCheckDirTraversalViolation OBJECT-TYPE
		SYNTAX  CounterBasedGauge64 
		MAX-ACCESS read-only 
		STATUS current
		DESCRIPTION  "Dir traversal check violation" 
		::={ acosWafGlobalS 109 } 

		evasionCheckHighAsciiBytesSuccess OBJECT-TYPE
		SYNTAX  CounterBasedGauge64 
		MAX-ACCESS read-only 
		STATUS current
		DESCRIPTION  "High Ascii Bytes check passed" 
		::={ acosWafGlobalS 110 } 

		evasionCheckHighAsciiBytesViolation OBJECT-TYPE
		SYNTAX  CounterBasedGauge64 
		MAX-ACCESS read-only 
		STATUS current
		DESCRIPTION  "High Ascii Bytes check violation" 
		::={ acosWafGlobalS 111 } 

		evasionCheckInvalidHexEncodingSuccess OBJECT-TYPE
		SYNTAX  CounterBasedGauge64 
		MAX-ACCESS read-only 
		STATUS current
		DESCRIPTION  "Invalid Hex Encoding check passed" 
		::={ acosWafGlobalS 112 } 

		evasionCheckInvalidHexEncodingViolation OBJECT-TYPE
		SYNTAX  CounterBasedGauge64 
		MAX-ACCESS read-only 
		STATUS current
		DESCRIPTION  "Invalid Hex Encoding check violation" 
		::={ acosWafGlobalS 113 } 

		evasionCheckMultipleEncodingLevelsSuccess OBJECT-TYPE
		SYNTAX  CounterBasedGauge64 
		MAX-ACCESS read-only 
		STATUS current
		DESCRIPTION  "Multiple Encoding Levels check passed" 
		::={ acosWafGlobalS 114 } 

		evasionCheckMultipleEncodingLevelsViolation OBJECT-TYPE
		SYNTAX  CounterBasedGauge64 
		MAX-ACCESS read-only 
		STATUS current
		DESCRIPTION  "Multiple Encoding Levels check violation" 
		::={ acosWafGlobalS 115 } 

		evasionCheckMultipleSlashesSuccess OBJECT-TYPE
		SYNTAX  CounterBasedGauge64 
		MAX-ACCESS read-only 
		STATUS current
		DESCRIPTION  "Multiple Slashes check passed" 
		::={ acosWafGlobalS 116 } 

		evasionCheckMultipleSlashesViolation OBJECT-TYPE
		SYNTAX  CounterBasedGauge64 
		MAX-ACCESS read-only 
		STATUS current
		DESCRIPTION  "Multiple Slashes check violation" 
		::={ acosWafGlobalS 117 } 

		evasionCheckMaxLevelsSuccess OBJECT-TYPE
		SYNTAX  CounterBasedGauge64 
		MAX-ACCESS read-only 
		STATUS current
		DESCRIPTION  "Max Levels check passed" 
		::={ acosWafGlobalS 118 } 

		evasionCheckMaxLevelsViolation OBJECT-TYPE
		SYNTAX  CounterBasedGauge64 
		MAX-ACCESS read-only 
		STATUS current
		DESCRIPTION  "Max Levels check violation" 
		::={ acosWafGlobalS 119 } 

		evasionCheckRemoveCommentsSuccess OBJECT-TYPE
		SYNTAX  CounterBasedGauge64 
		MAX-ACCESS read-only 
		STATUS current
		DESCRIPTION  "Remove Comments check passed" 
		::={ acosWafGlobalS 120 } 

		evasionCheckRemoveCommentsViolation OBJECT-TYPE
		SYNTAX  CounterBasedGauge64 
		MAX-ACCESS read-only 
		STATUS current
		DESCRIPTION  "Remove Comments check violation" 
		::={ acosWafGlobalS 121 } 

		evasionCheckRemoveSpacesSuccess OBJECT-TYPE
		SYNTAX  CounterBasedGauge64 
		MAX-ACCESS read-only 
		STATUS current
		DESCRIPTION  "Remove Spaces check passed" 
		::={ acosWafGlobalS 122 } 

		evasionCheckRemoveSpacesViolation OBJECT-TYPE
		SYNTAX  CounterBasedGauge64 
		MAX-ACCESS read-only 
		STATUS current
		DESCRIPTION  "Remove Spaces check violation" 
		::={ acosWafGlobalS 123 } 

		httpLimitMaxContentLengthSuccess OBJECT-TYPE
		SYNTAX  CounterBasedGauge64 
		MAX-ACCESS read-only 
		STATUS current
		DESCRIPTION  "MAX content-length check passed" 
		::={ acosWafGlobalS 124 } 

		httpLimitMaxContentLengthViolation OBJECT-TYPE
		SYNTAX  CounterBasedGauge64 
		MAX-ACCESS read-only 
		STATUS current
		DESCRIPTION  "MAX content-length check violation" 
		::={ acosWafGlobalS 125 } 

		httpLimitMaxCookieHeaderLengthSuccess OBJECT-TYPE
		SYNTAX  CounterBasedGauge64 
		MAX-ACCESS read-only 
		STATUS current
		DESCRIPTION  "MAX cookie header length check passed" 
		::={ acosWafGlobalS 126 } 

		httpLimitMaxCookieHeaderLengthViolation OBJECT-TYPE
		SYNTAX  CounterBasedGauge64 
		MAX-ACCESS read-only 
		STATUS current
		DESCRIPTION  "MAX cookie header length violation" 
		::={ acosWafGlobalS 127 } 

		httpLimitMaxCookieNameLengthSuccess OBJECT-TYPE
		SYNTAX  CounterBasedGauge64 
		MAX-ACCESS read-only 
		STATUS current
		DESCRIPTION  "MAX cookie name length check passed" 
		::={ acosWafGlobalS 128 } 

		httpLimitMaxCookieNameLengthViolation OBJECT-TYPE
		SYNTAX  CounterBasedGauge64 
		MAX-ACCESS read-only 
		STATUS current
		DESCRIPTION  "MAX cookie name length violation" 
		::={ acosWafGlobalS 129 } 

		httpLimitMaxCookieValueLengthSuccess OBJECT-TYPE
		SYNTAX  CounterBasedGauge64 
		MAX-ACCESS read-only 
		STATUS current
		DESCRIPTION  "MAX cookie value length check passed" 
		::={ acosWafGlobalS 130 } 

		httpLimitMaxCookieValueLengthViolation OBJECT-TYPE
		SYNTAX  CounterBasedGauge64 
		MAX-ACCESS read-only 
		STATUS current
		DESCRIPTION  "MAX cookie value length violation" 
		::={ acosWafGlobalS 131 } 

		httpLimitMaxCookiesSuccess OBJECT-TYPE
		SYNTAX  CounterBasedGauge64 
		MAX-ACCESS read-only 
		STATUS current
		DESCRIPTION  "Max Cookies check passed" 
		::={ acosWafGlobalS 132 } 

		httpLimitMaxCookiesViolation OBJECT-TYPE
		SYNTAX  CounterBasedGauge64 
		MAX-ACCESS read-only 
		STATUS current
		DESCRIPTION  "Max Cookies violation" 
		::={ acosWafGlobalS 133 } 

		httpLimitMaxCookiesLengthSuccess OBJECT-TYPE
		SYNTAX  CounterBasedGauge64 
		MAX-ACCESS read-only 
		STATUS current
		DESCRIPTION  "MAX cookies length check passed" 
		::={ acosWafGlobalS 134 } 

		httpLimitMaxCookiesLengthViolation OBJECT-TYPE
		SYNTAX  CounterBasedGauge64 
		MAX-ACCESS read-only 
		STATUS current
		DESCRIPTION  "MAX cookies length violation" 
		::={ acosWafGlobalS 135 } 

		httpLimitMaxDataParseSuccess OBJECT-TYPE
		SYNTAX  CounterBasedGauge64 
		MAX-ACCESS read-only 
		STATUS current
		DESCRIPTION  "Buffer Overflow - Max Data Parse check passed" 
		::={ acosWafGlobalS 136 } 

		httpLimitMaxDataParseViolation OBJECT-TYPE
		SYNTAX  CounterBasedGauge64 
		MAX-ACCESS read-only 
		STATUS current
		DESCRIPTION  "Buffer Overflow - Max Data Parse violation" 
		::={ acosWafGlobalS 137 } 

		httpLimitMaxEntitiesSuccess OBJECT-TYPE
		SYNTAX  CounterBasedGauge64 
		MAX-ACCESS read-only 
		STATUS current
		DESCRIPTION  "Max Entities check passed" 
		::={ acosWafGlobalS 138 } 

		httpLimitMaxEntitiesViolation OBJECT-TYPE
		SYNTAX  CounterBasedGauge64 
		MAX-ACCESS read-only 
		STATUS current
		DESCRIPTION  "Max Entities violation" 
		::={ acosWafGlobalS 139 } 

		httpLimitMaxHeaderLengthSuccess OBJECT-TYPE
		SYNTAX  CounterBasedGauge64 
		MAX-ACCESS read-only 
		STATUS current
		DESCRIPTION  "MAX header length check passed" 
		::={ acosWafGlobalS 140 } 

		httpLimitMaxHeaderLengthViolation OBJECT-TYPE
		SYNTAX  CounterBasedGauge64 
		MAX-ACCESS read-only 
		STATUS current
		DESCRIPTION  "MAX header length check violation" 
		::={ acosWafGlobalS 141 } 

		httpLimitMaxHeaderNameLengthSuccess OBJECT-TYPE
		SYNTAX  CounterBasedGauge64 
		MAX-ACCESS read-only 
		STATUS current
		DESCRIPTION  "MAX header name length check passed" 
		::={ acosWafGlobalS 142 } 

		httpLimitMaxHeaderNameLengthViolation OBJECT-TYPE
		SYNTAX  CounterBasedGauge64 
		MAX-ACCESS read-only 
		STATUS current
		DESCRIPTION  "MAX header name length check violation" 
		::={ acosWafGlobalS 143 } 

		httpLimitMaxHeaderValueLengthSuccess OBJECT-TYPE
		SYNTAX  CounterBasedGauge64 
		MAX-ACCESS read-only 
		STATUS current
		DESCRIPTION  "MAX header value length check passed" 
		::={ acosWafGlobalS 144 } 

		httpLimitMaxHeaderValueLengthViolation OBJECT-TYPE
		SYNTAX  CounterBasedGauge64 
		MAX-ACCESS read-only 
		STATUS current
		DESCRIPTION  "MAX header value length check violation" 
		::={ acosWafGlobalS 145 } 

		httpLimitMaxHeadersSuccess OBJECT-TYPE
		SYNTAX  CounterBasedGauge64 
		MAX-ACCESS read-only 
		STATUS current
		DESCRIPTION  "MAX headers count check passed" 
		::={ acosWafGlobalS 146 } 

		httpLimitMaxHeadersViolation OBJECT-TYPE
		SYNTAX  CounterBasedGauge64 
		MAX-ACCESS read-only 
		STATUS current
		DESCRIPTION  "Max Headers violation" 
		::={ acosWafGlobalS 147 } 

		httpLimitMaxHeadersLengthSuccess OBJECT-TYPE
		SYNTAX  CounterBasedGauge64 
		MAX-ACCESS read-only 
		STATUS current
		DESCRIPTION  "MAX headers length check passed" 
		::={ acosWafGlobalS 148 } 

		httpLimitMaxHeadersLengthViolation OBJECT-TYPE
		SYNTAX  CounterBasedGauge64 
		MAX-ACCESS read-only 
		STATUS current
		DESCRIPTION  "MAX headers length check violation" 
		::={ acosWafGlobalS 149 } 

		httpLimitMaxParamNameLengthSuccess OBJECT-TYPE
		SYNTAX  CounterBasedGauge64 
		MAX-ACCESS read-only 
		STATUS current
		DESCRIPTION  "Limit check - MAX parameter name length check passed" 
		::={ acosWafGlobalS 150 } 

		httpLimitMaxParamNameLengthViolation OBJECT-TYPE
		SYNTAX  CounterBasedGauge64 
		MAX-ACCESS read-only 
		STATUS current
		DESCRIPTION  "Limit check - MAX parameter name length violation" 
		::={ acosWafGlobalS 151 } 

		httpLimitMaxParamValueLengthSuccess OBJECT-TYPE
		SYNTAX  CounterBasedGauge64 
		MAX-ACCESS read-only 
		STATUS current
		DESCRIPTION  "Limit check - MAX parameter value length check passed" 
		::={ acosWafGlobalS 152 } 

		httpLimitMaxParamValueLengthViolation OBJECT-TYPE
		SYNTAX  CounterBasedGauge64 
		MAX-ACCESS read-only 
		STATUS current
		DESCRIPTION  "Limit check - MAX parameter value length violation" 
		::={ acosWafGlobalS 153 } 

		httpLimitMaxParamsSuccess OBJECT-TYPE
		SYNTAX  CounterBasedGauge64 
		MAX-ACCESS read-only 
		STATUS current
		DESCRIPTION  "Limit check - MAX parameters check passed" 
		::={ acosWafGlobalS 154 } 

		httpLimitMaxParamsViolation OBJECT-TYPE
		SYNTAX  CounterBasedGauge64 
		MAX-ACCESS read-only 
		STATUS current
		DESCRIPTION  "Limit check - MAX parameters violation" 
		::={ acosWafGlobalS 155 } 

		httpLimitMaxParamsLengthSuccess OBJECT-TYPE
		SYNTAX  CounterBasedGauge64 
		MAX-ACCESS read-only 
		STATUS current
		DESCRIPTION  "Limit check - MAX parameters total length check passed" 
		::={ acosWafGlobalS 156 } 

		httpLimitMaxParamsLengthViolation OBJECT-TYPE
		SYNTAX  CounterBasedGauge64 
		MAX-ACCESS read-only 
		STATUS current
		DESCRIPTION  "Limit check - MAX parameters total length violation" 
		::={ acosWafGlobalS 157 } 

		httpLimitMaxPostLengthSuccess OBJECT-TYPE
		SYNTAX  CounterBasedGauge64 
		MAX-ACCESS read-only 
		STATUS current
		DESCRIPTION  "MAX POST length check passed" 
		::={ acosWafGlobalS 158 } 

		httpLimitMaxPostLengthViolation OBJECT-TYPE
		SYNTAX  CounterBasedGauge64 
		MAX-ACCESS read-only 
		STATUS current
		DESCRIPTION  "MAX POST length violation" 
		::={ acosWafGlobalS 159 } 

		httpLimitMaxQueryLengthSuccess OBJECT-TYPE
		SYNTAX  CounterBasedGauge64 
		MAX-ACCESS read-only 
		STATUS current
		DESCRIPTION  "Limit check - MAX query length check passed" 
		::={ acosWafGlobalS 160 } 

		httpLimitMaxQueryLengthViolation OBJECT-TYPE
		SYNTAX  CounterBasedGauge64 
		MAX-ACCESS read-only 
		STATUS current
		DESCRIPTION  "Limit check - MAX query length violation" 
		::={ acosWafGlobalS 161 } 

		httpLimitMaxRequestLengthSuccess OBJECT-TYPE
		SYNTAX  CounterBasedGauge64 
		MAX-ACCESS read-only 
		STATUS current
		DESCRIPTION  "Limit check - MAX request length check passed" 
		::={ acosWafGlobalS 162 } 

		httpLimitMaxRequestLengthViolation OBJECT-TYPE
		SYNTAX  CounterBasedGauge64 
		MAX-ACCESS read-only 
		STATUS current
		DESCRIPTION  "Limit check - MAX request length violation" 
		::={ acosWafGlobalS 163 } 

		httpLimitMaxRequestLineLengthSuccess OBJECT-TYPE
		SYNTAX  CounterBasedGauge64 
		MAX-ACCESS read-only 
		STATUS current
		DESCRIPTION  "Limit check - MAX request line length check passed" 
		::={ acosWafGlobalS 164 } 

		httpLimitMaxRequestLineLengthViolation OBJECT-TYPE
		SYNTAX  CounterBasedGauge64 
		MAX-ACCESS read-only 
		STATUS current
		DESCRIPTION  "Limit check - MAX request line length violation" 
		::={ acosWafGlobalS 165 } 

		maxUrlLengthSuccess OBJECT-TYPE
		SYNTAX  CounterBasedGauge64 
		MAX-ACCESS read-only 
		STATUS current
		DESCRIPTION  "Limit check - MAX URL length check passed" 
		::={ acosWafGlobalS 166 } 

		maxUrlLengthViolation OBJECT-TYPE
		SYNTAX  CounterBasedGauge64 
		MAX-ACCESS read-only 
		STATUS current
		DESCRIPTION  "Limit check - MAX URL length violation" 
		::={ acosWafGlobalS 167 } 

		httpProtocolAllowedHeadersSuccess OBJECT-TYPE
		SYNTAX  CounterBasedGauge64 
		MAX-ACCESS read-only 
		STATUS current
		DESCRIPTION  "HTTP headers check passed" 
		::={ acosWafGlobalS 168 } 

		httpProtocolAllowedHeadersViolation OBJECT-TYPE
		SYNTAX  CounterBasedGauge64 
		MAX-ACCESS read-only 
		STATUS current
		DESCRIPTION  "HTTP headers check violation" 
		::={ acosWafGlobalS 169 } 

		httpProtocolAllowedVersionsSuccess OBJECT-TYPE
		SYNTAX  CounterBasedGauge64 
		MAX-ACCESS read-only 
		STATUS current
		DESCRIPTION  "HTTP versions check passed" 
		::={ acosWafGlobalS 170 } 

		httpProtocolAllowedVersionsViolation OBJECT-TYPE
		SYNTAX  CounterBasedGauge64 
		MAX-ACCESS read-only 
		STATUS current
		DESCRIPTION  "HTTP versions check violation" 
		::={ acosWafGlobalS 171 } 

		httpProtocolAllowedMethodCheckSuccess OBJECT-TYPE
		SYNTAX  CounterBasedGauge64 
		MAX-ACCESS read-only 
		STATUS current
		DESCRIPTION  "HTTP Method Check passed" 
		::={ acosWafGlobalS 172 } 

		httpProtocolAllowedMethodCheckViolation OBJECT-TYPE
		SYNTAX  CounterBasedGauge64 
		MAX-ACCESS read-only 
		STATUS current
		DESCRIPTION  "HTTP Method Check violation" 
		::={ acosWafGlobalS 173 } 

		httpProtocolBadMultipartRequestSuccess OBJECT-TYPE
		SYNTAX  CounterBasedGauge64 
		MAX-ACCESS read-only 
		STATUS current
		DESCRIPTION  "Bad multi-part request check passed" 
		::={ acosWafGlobalS 174 } 

		httpProtocolBadMultipartRequestViolation OBJECT-TYPE
		SYNTAX  CounterBasedGauge64 
		MAX-ACCESS read-only 
		STATUS current
		DESCRIPTION  "Bad multi-part request check violation" 
		::={ acosWafGlobalS 175 } 

		httpProtocolGetWithContentSuccess OBJECT-TYPE
		SYNTAX  CounterBasedGauge64 
		MAX-ACCESS read-only 
		STATUS current
		DESCRIPTION  "GET with content check passed" 
		::={ acosWafGlobalS 176 } 

		httpProtocolGetWithContentViolation OBJECT-TYPE
		SYNTAX  CounterBasedGauge64 
		MAX-ACCESS read-only 
		STATUS current
		DESCRIPTION  "GET with content check violation" 
		::={ acosWafGlobalS 177 } 

		httpProtocolHeadWithContentSuccess OBJECT-TYPE
		SYNTAX  CounterBasedGauge64 
		MAX-ACCESS read-only 
		STATUS current
		DESCRIPTION  "HEAD with content check passed" 
		::={ acosWafGlobalS 178 } 

		httpProtocolHeadWithContentViolation OBJECT-TYPE
		SYNTAX  CounterBasedGauge64 
		MAX-ACCESS read-only 
		STATUS current
		DESCRIPTION  "HEAD with content check violation" 
		::={ acosWafGlobalS 179 } 

		httpProtocolHostHeaderWithIpSuccess OBJECT-TYPE
		SYNTAX  CounterBasedGauge64 
		MAX-ACCESS read-only 
		STATUS current
		DESCRIPTION  "Host header with IP check passed" 
		::={ acosWafGlobalS 180 } 

		httpProtocolHostHeaderWithIpViolation OBJECT-TYPE
		SYNTAX  CounterBasedGauge64 
		MAX-ACCESS read-only 
		STATUS current
		DESCRIPTION  "Host header with IP check violation" 
		::={ acosWafGlobalS 181 } 

		httpProtocolInvalidUrlEncodingSuccess OBJECT-TYPE
		SYNTAX  CounterBasedGauge64 
		MAX-ACCESS read-only 
		STATUS current
		DESCRIPTION  "Invalid url encoding check passed" 
		::={ acosWafGlobalS 182 } 

		httpProtocolInvalidUrlEncodingViolation OBJECT-TYPE
		SYNTAX  CounterBasedGauge64 
		MAX-ACCESS read-only 
		STATUS current
		DESCRIPTION  "Invalid url encoding check violation" 
		::={ acosWafGlobalS 183 } 

		httpProtocolMalformedContentLengthSuccess OBJECT-TYPE
		SYNTAX  CounterBasedGauge64 
		MAX-ACCESS read-only 
		STATUS current
		DESCRIPTION  "Malformed content-length check passed" 
		::={ acosWafGlobalS 184 } 

		httpProtocolMalformedContentLengthViolation OBJECT-TYPE
		SYNTAX  CounterBasedGauge64 
		MAX-ACCESS read-only 
		STATUS current
		DESCRIPTION  "Malformed content-length check violation" 
		::={ acosWafGlobalS 185 } 

		httpProtocolMalformedHeaderSuccess OBJECT-TYPE
		SYNTAX  CounterBasedGauge64 
		MAX-ACCESS read-only 
		STATUS current
		DESCRIPTION  "Malformed header check passed" 
		::={ acosWafGlobalS 186 } 

		httpProtocolMalformedHeaderViolation OBJECT-TYPE
		SYNTAX  CounterBasedGauge64 
		MAX-ACCESS read-only 
		STATUS current
		DESCRIPTION  "Malformed header check passed" 
		::={ acosWafGlobalS 187 } 

		httpProtocolMalformedParameterSuccess OBJECT-TYPE
		SYNTAX  CounterBasedGauge64 
		MAX-ACCESS read-only 
		STATUS current
		DESCRIPTION  "Malformed parameter check passed" 
		::={ acosWafGlobalS 188 } 

		httpProtocolMalformedParameterViolation OBJECT-TYPE
		SYNTAX  CounterBasedGauge64 
		MAX-ACCESS read-only 
		STATUS current
		DESCRIPTION  "Malformed parameter check violation" 
		::={ acosWafGlobalS 189 } 

		httpProtocolMalformedRequestSuccess OBJECT-TYPE
		SYNTAX  CounterBasedGauge64 
		MAX-ACCESS read-only 
		STATUS current
		DESCRIPTION  "Malformed request check passed" 
		::={ acosWafGlobalS 190 } 

		httpProtocolMalformedRequestViolation OBJECT-TYPE
		SYNTAX  CounterBasedGauge64 
		MAX-ACCESS read-only 
		STATUS current
		DESCRIPTION  "Malformed request check violation" 
		::={ acosWafGlobalS 191 } 

		httpProtocolMalformedRequestLineSuccess OBJECT-TYPE
		SYNTAX  CounterBasedGauge64 
		MAX-ACCESS read-only 
		STATUS current
		DESCRIPTION  "Malformed request line check passed" 
		::={ acosWafGlobalS 192 } 

		httpProtocolMalformedRequestLineViolation OBJECT-TYPE
		SYNTAX  CounterBasedGauge64 
		MAX-ACCESS read-only 
		STATUS current
		DESCRIPTION  "Malformed request line check violation" 
		::={ acosWafGlobalS 193 } 

		httpProtocolMissingHeaderValueSuccess OBJECT-TYPE
		SYNTAX  CounterBasedGauge64 
		MAX-ACCESS read-only 
		STATUS current
		DESCRIPTION  "Missing header value check violation" 
		::={ acosWafGlobalS 194 } 

		httpProtocolMissingHeaderValueViolation OBJECT-TYPE
		SYNTAX  CounterBasedGauge64 
		MAX-ACCESS read-only 
		STATUS current
		DESCRIPTION  "Missing header value check violation" 
		::={ acosWafGlobalS 195 } 

		httpProtocolMissingHostHeaderSuccess OBJECT-TYPE
		SYNTAX  CounterBasedGauge64 
		MAX-ACCESS read-only 
		STATUS current
		DESCRIPTION  "Missing host header check passed" 
		::={ acosWafGlobalS 196 } 

		httpProtocolMissingHostHeaderViolation OBJECT-TYPE
		SYNTAX  CounterBasedGauge64 
		MAX-ACCESS read-only 
		STATUS current
		DESCRIPTION  "Missing host header check violation" 
		::={ acosWafGlobalS 197 } 

		httpProtocolMultipleContentLengthSuccess OBJECT-TYPE
		SYNTAX  CounterBasedGauge64 
		MAX-ACCESS read-only 
		STATUS current
		DESCRIPTION  "Multiple content-length headers check passed" 
		::={ acosWafGlobalS 198 } 

		httpProtocolMultipleContentLengthViolation OBJECT-TYPE
		SYNTAX  CounterBasedGauge64 
		MAX-ACCESS read-only 
		STATUS current
		DESCRIPTION  "Multiple content-length headers check violation" 
		::={ acosWafGlobalS 199 } 

		httpProtocolPostWith0ContentSuccess OBJECT-TYPE
		SYNTAX  CounterBasedGauge64 
		MAX-ACCESS read-only 
		STATUS current
		DESCRIPTION  "POST with 0 content check passed" 
		::={ acosWafGlobalS 200 } 

		httpProtocolPostWith0ContentViolation OBJECT-TYPE
		SYNTAX  CounterBasedGauge64 
		MAX-ACCESS read-only 
		STATUS current
		DESCRIPTION  "POST with 0 content check violation" 
		::={ acosWafGlobalS 201 } 

		httpProtocolPostWithoutContentSuccess OBJECT-TYPE
		SYNTAX  CounterBasedGauge64 
		MAX-ACCESS read-only 
		STATUS current
		DESCRIPTION  "POST without content check passed" 
		::={ acosWafGlobalS 202 } 

		httpProtocolPostWithoutContentViolation OBJECT-TYPE
		SYNTAX  CounterBasedGauge64 
		MAX-ACCESS read-only 
		STATUS current
		DESCRIPTION  "POST without content check violation" 
		::={ acosWafGlobalS 203 } 

		httpProtocolSuccess OBJECT-TYPE
		SYNTAX  CounterBasedGauge64 
		MAX-ACCESS read-only 
		STATUS current
		DESCRIPTION  "HTTP Check passed" 
		::={ acosWafGlobalS 204 } 

		httpProtocolViolation OBJECT-TYPE
		SYNTAX  CounterBasedGauge64 
		MAX-ACCESS read-only 
		STATUS current
		DESCRIPTION  "HTTP Check violation" 
		::={ acosWafGlobalS 205 } 

		jsonCheckFormatSuccess OBJECT-TYPE
		SYNTAX  CounterBasedGauge64 
		MAX-ACCESS read-only 
		STATUS current
		DESCRIPTION  "JSON Check passed" 
		::={ acosWafGlobalS 206 } 

		jsonCheckFormatViolation OBJECT-TYPE
		SYNTAX  CounterBasedGauge64 
		MAX-ACCESS read-only 
		STATUS current
		DESCRIPTION  "JSON Check violation" 
		::={ acosWafGlobalS 207 } 

		jsonCheckMaxArrayValueCountSuccess OBJECT-TYPE
		SYNTAX  CounterBasedGauge64 
		MAX-ACCESS read-only 
		STATUS current
		DESCRIPTION  "JSON Limit Array Value Count check passed" 
		::={ acosWafGlobalS 208 } 

		jsonCheckMaxArrayValueCountViolation OBJECT-TYPE
		SYNTAX  CounterBasedGauge64 
		MAX-ACCESS read-only 
		STATUS current
		DESCRIPTION  "JSON Limit Array Value Count violation" 
		::={ acosWafGlobalS 209 } 

		jsonCheckMaxDepthSuccess OBJECT-TYPE
		SYNTAX  CounterBasedGauge64 
		MAX-ACCESS read-only 
		STATUS current
		DESCRIPTION  "JSON Limit Depth check passed" 
		::={ acosWafGlobalS 210 } 

		jsonCheckMaxDepthViolation OBJECT-TYPE
		SYNTAX  CounterBasedGauge64 
		MAX-ACCESS read-only 
		STATUS current
		DESCRIPTION  "JSON Limit Depth violation" 
		::={ acosWafGlobalS 211 } 

		jsonCheckMaxObjectMemberCountSuccess OBJECT-TYPE
		SYNTAX  CounterBasedGauge64 
		MAX-ACCESS read-only 
		STATUS current
		DESCRIPTION  "JSON Limit Object Number Count check passed" 
		::={ acosWafGlobalS 212 } 

		jsonCheckMaxObjectMemberCountViolation OBJECT-TYPE
		SYNTAX  CounterBasedGauge64 
		MAX-ACCESS read-only 
		STATUS current
		DESCRIPTION  "JSON Limit Object Number Count violation" 
		::={ acosWafGlobalS 213 } 

		jsonCheckMaxStringSuccess OBJECT-TYPE
		SYNTAX  CounterBasedGauge64 
		MAX-ACCESS read-only 
		STATUS current
		DESCRIPTION  "JSON Limit String check passed" 
		::={ acosWafGlobalS 214 } 

		jsonCheckMaxStringViolation OBJECT-TYPE
		SYNTAX  CounterBasedGauge64 
		MAX-ACCESS read-only 
		STATUS current
		DESCRIPTION  "JSON Limit String violation" 
		::={ acosWafGlobalS 215 } 

		requestCheckBotSuccess OBJECT-TYPE
		SYNTAX  CounterBasedGauge64 
		MAX-ACCESS read-only 
		STATUS current
		DESCRIPTION  "Bot check passed" 
		::={ acosWafGlobalS 216 } 

		requestCheckBotViolation OBJECT-TYPE
		SYNTAX  CounterBasedGauge64 
		MAX-ACCESS read-only 
		STATUS current
		DESCRIPTION  "Bot check violation" 
		::={ acosWafGlobalS 217 } 

		requestCheckRedirectWlistSuccess OBJECT-TYPE
		SYNTAX  CounterBasedGauge64 
		MAX-ACCESS read-only 
		STATUS current
		DESCRIPTION  "Redirect Whitelist passed" 
		::={ acosWafGlobalS 218 } 

		requestCheckRedirectWlistViolation OBJECT-TYPE
		SYNTAX  CounterBasedGauge64 
		MAX-ACCESS read-only 
		STATUS current
		DESCRIPTION  "Redirect Whitelist violation" 
		::={ acosWafGlobalS 219 } 

		requestCheckRedirectWlistLearn OBJECT-TYPE
		SYNTAX  CounterBasedGauge64 
		MAX-ACCESS read-only 
		STATUS current
		DESCRIPTION  "Redirect Whitelist Learn" 
		::={ acosWafGlobalS 220 } 

		requestCheckRefererSuccess OBJECT-TYPE
		SYNTAX  CounterBasedGauge64 
		MAX-ACCESS read-only 
		STATUS current
		DESCRIPTION  "Referer Check passed" 
		::={ acosWafGlobalS 221 } 

		requestCheckRefererViolation OBJECT-TYPE
		SYNTAX  CounterBasedGauge64 
		MAX-ACCESS read-only 
		STATUS current
		DESCRIPTION  "Referer Check violation" 
		::={ acosWafGlobalS 222 } 

		requestCheckRefererRedirect OBJECT-TYPE
		SYNTAX  CounterBasedGauge64 
		MAX-ACCESS read-only 
		STATUS current
		DESCRIPTION  "Referer Check Redirect" 
		::={ acosWafGlobalS 223 } 

		requestCheckSessionCheckNone OBJECT-TYPE
		SYNTAX  CounterBasedGauge64 
		MAX-ACCESS read-only 
		STATUS current
		DESCRIPTION  "Session Created" 
		::={ acosWafGlobalS 224 } 

		requestCheckSessionCheckSuccess OBJECT-TYPE
		SYNTAX  CounterBasedGauge64 
		MAX-ACCESS read-only 
		STATUS current
		DESCRIPTION  "Session Check passed" 
		::={ acosWafGlobalS 225 } 

		requestCheckSessionCheckViolation OBJECT-TYPE
		SYNTAX  CounterBasedGauge64 
		MAX-ACCESS read-only 
		STATUS current
		DESCRIPTION  "Session Check violation" 
		::={ acosWafGlobalS 226 } 

		requestCheckSqliaUrlSuccess OBJECT-TYPE
		SYNTAX  CounterBasedGauge64 
		MAX-ACCESS read-only 
		STATUS current
		DESCRIPTION  "SQLIA Check URL passed" 
		::={ acosWafGlobalS 227 } 

		requestCheckSqliaUrlViolation OBJECT-TYPE
		SYNTAX  CounterBasedGauge64 
		MAX-ACCESS read-only 
		STATUS current
		DESCRIPTION  "SQLIA Check URL violation" 
		::={ acosWafGlobalS 228 } 

		requestCheckSqliaUrlSanitize OBJECT-TYPE
		SYNTAX  CounterBasedGauge64 
		MAX-ACCESS read-only 
		STATUS current
		DESCRIPTION  "SQLIA Check URL Sanitized" 
		::={ acosWafGlobalS 229 } 

		requestCheckSqliaPostBodySuccess OBJECT-TYPE
		SYNTAX  CounterBasedGauge64 
		MAX-ACCESS read-only 
		STATUS current
		DESCRIPTION  "SQLIA Check Post passed" 
		::={ acosWafGlobalS 230 } 

		requestCheckSqliaPostBodyViolation OBJECT-TYPE
		SYNTAX  CounterBasedGauge64 
		MAX-ACCESS read-only 
		STATUS current
		DESCRIPTION  "SQLIA Check Post violation" 
		::={ acosWafGlobalS 231 } 

		requestCheckSqliaPostBodySanitize OBJECT-TYPE
		SYNTAX  CounterBasedGauge64 
		MAX-ACCESS read-only 
		STATUS current
		DESCRIPTION  "SQLIA Check Post Sanitized" 
		::={ acosWafGlobalS 232 } 

		requestCheckUrlListSuccess OBJECT-TYPE
		SYNTAX  CounterBasedGauge64 
		MAX-ACCESS read-only 
		STATUS current
		DESCRIPTION  "URL Check passed" 
		::={ acosWafGlobalS 233 } 

		requestCheckUrlListViolation OBJECT-TYPE
		SYNTAX  CounterBasedGauge64 
		MAX-ACCESS read-only 
		STATUS current
		DESCRIPTION  "URL Check violation" 
		::={ acosWafGlobalS 234 } 

		requestCheckUrlListLearn OBJECT-TYPE
		SYNTAX  CounterBasedGauge64 
		MAX-ACCESS read-only 
		STATUS current
		DESCRIPTION  "URL Check Learn" 
		::={ acosWafGlobalS 235 } 

		requestCheckUrlWhitelistSuccess OBJECT-TYPE
		SYNTAX  CounterBasedGauge64 
		MAX-ACCESS read-only 
		STATUS current
		DESCRIPTION  "URI White List passed" 
		::={ acosWafGlobalS 236 } 

		requestCheckUrlWhitelistViolation OBJECT-TYPE
		SYNTAX  CounterBasedGauge64 
		MAX-ACCESS read-only 
		STATUS current
		DESCRIPTION  "URI White List violation" 
		::={ acosWafGlobalS 237 } 

		requestCheckUrlBlacklistSuccess OBJECT-TYPE
		SYNTAX  CounterBasedGauge64 
		MAX-ACCESS read-only 
		STATUS current
		DESCRIPTION  "URI Black List passed" 
		::={ acosWafGlobalS 238 } 

		requestCheckUrlBlacklistViolation OBJECT-TYPE
		SYNTAX  CounterBasedGauge64 
		MAX-ACCESS read-only 
		STATUS current
		DESCRIPTION  "URI Black List violation" 
		::={ acosWafGlobalS 239 } 

		requestCheckXssCookieSuccess OBJECT-TYPE
		SYNTAX  CounterBasedGauge64 
		MAX-ACCESS read-only 
		STATUS current
		DESCRIPTION  "XSS Check Cookie passed" 
		::={ acosWafGlobalS 240 } 

		requestCheckXssCookieViolation OBJECT-TYPE
		SYNTAX  CounterBasedGauge64 
		MAX-ACCESS read-only 
		STATUS current
		DESCRIPTION  "XSS Check Cookie violation" 
		::={ acosWafGlobalS 241 } 

		requestCheckXssCookieSanitize OBJECT-TYPE
		SYNTAX  CounterBasedGauge64 
		MAX-ACCESS read-only 
		STATUS current
		DESCRIPTION  "XSS Check Cookie Sanitized" 
		::={ acosWafGlobalS 242 } 

		requestCheckXssUrlSuccess OBJECT-TYPE
		SYNTAX  CounterBasedGauge64 
		MAX-ACCESS read-only 
		STATUS current
		DESCRIPTION  "XSS Check URL passed" 
		::={ acosWafGlobalS 243 } 

		requestCheckXssUrlViolation OBJECT-TYPE
		SYNTAX  CounterBasedGauge64 
		MAX-ACCESS read-only 
		STATUS current
		DESCRIPTION  "XSS Check URL violation" 
		::={ acosWafGlobalS 244 } 

		requestCheckXssUrlSanitize OBJECT-TYPE
		SYNTAX  CounterBasedGauge64 
		MAX-ACCESS read-only 
		STATUS current
		DESCRIPTION  "XSS Check URL Sanitized" 
		::={ acosWafGlobalS 245 } 

		requestCheckXssPostBodySuccess OBJECT-TYPE
		SYNTAX  CounterBasedGauge64 
		MAX-ACCESS read-only 
		STATUS current
		DESCRIPTION  "XSS Check Post passed" 
		::={ acosWafGlobalS 246 } 

		requestCheckXssPostBodyViolation OBJECT-TYPE
		SYNTAX  CounterBasedGauge64 
		MAX-ACCESS read-only 
		STATUS current
		DESCRIPTION  "XSS Check Post violation" 
		::={ acosWafGlobalS 247 } 

		requestCheckXssPostBodySanitize OBJECT-TYPE
		SYNTAX  CounterBasedGauge64 
		MAX-ACCESS read-only 
		STATUS current
		DESCRIPTION  "XSS Check Post Sanitized" 
		::={ acosWafGlobalS 248 } 

		responseCloakingHideStatusCodeSuccess OBJECT-TYPE
		SYNTAX  CounterBasedGauge64 
		MAX-ACCESS read-only 
		STATUS current
		DESCRIPTION  "Response Hide Code check passed" 
		::={ acosWafGlobalS 249 } 

		responseCloakingHideStatusCodeViolation OBJECT-TYPE
		SYNTAX  CounterBasedGauge64 
		MAX-ACCESS read-only 
		STATUS current
		DESCRIPTION  "Response Hide Code violation" 
		::={ acosWafGlobalS 250 } 

		responseCloakingFilterHeadersSuccess OBJECT-TYPE
		SYNTAX  CounterBasedGauge64 
		MAX-ACCESS read-only 
		STATUS current
		DESCRIPTION  "Response Headers Filter check passed" 
		::={ acosWafGlobalS 251 } 

		responseCloakingFilterHeadersViolation OBJECT-TYPE
		SYNTAX  CounterBasedGauge64 
		MAX-ACCESS read-only 
		STATUS current
		DESCRIPTION  "Response Headers Filter violation" 
		::={ acosWafGlobalS 252 } 

		soapCheckSuccess OBJECT-TYPE
		SYNTAX  CounterBasedGauge64 
		MAX-ACCESS read-only 
		STATUS current
		DESCRIPTION  "Soap Check passed" 
		::={ acosWafGlobalS 253 } 

		soapCheckViolation OBJECT-TYPE
		SYNTAX  CounterBasedGauge64 
		MAX-ACCESS read-only 
		STATUS current
		DESCRIPTION  "Soap Check violation" 
		::={ acosWafGlobalS 254 } 

		xmlCheckFormatSuccess OBJECT-TYPE
		SYNTAX  CounterBasedGauge64 
		MAX-ACCESS read-only 
		STATUS current
		DESCRIPTION  "XML Check passed" 
		::={ acosWafGlobalS 255 } 

		xmlCheckFormatViolation OBJECT-TYPE
		SYNTAX  CounterBasedGauge64 
		MAX-ACCESS read-only 
		STATUS current
		DESCRIPTION  "XML Check violation" 
		::={ acosWafGlobalS 256 } 

		xmlCheckMaxAttrSuccess OBJECT-TYPE
		SYNTAX  CounterBasedGauge64 
		MAX-ACCESS read-only 
		STATUS current
		DESCRIPTION  "XML Limit Attribute check passed" 
		::={ acosWafGlobalS 257 } 

		xmlCheckMaxAttrViolation OBJECT-TYPE
		SYNTAX  CounterBasedGauge64 
		MAX-ACCESS read-only 
		STATUS current
		DESCRIPTION  "XML Limit Attribute violation" 
		::={ acosWafGlobalS 258 } 

		xmlCheckMaxAttrNameLenSuccess OBJECT-TYPE
		SYNTAX  CounterBasedGauge64 
		MAX-ACCESS read-only 
		STATUS current
		DESCRIPTION  "XML Limit Name Length check passed" 
		::={ acosWafGlobalS 259 } 

		xmlCheckMaxAttrNameLenViolation OBJECT-TYPE
		SYNTAX  CounterBasedGauge64 
		MAX-ACCESS read-only 
		STATUS current
		DESCRIPTION  "XML Limit Name Length violation" 
		::={ acosWafGlobalS 260 } 

		xmlCheckMaxAttrValueLenSuccess OBJECT-TYPE
		SYNTAX  CounterBasedGauge64 
		MAX-ACCESS read-only 
		STATUS current
		DESCRIPTION  "XML Limit Value Length check passed" 
		::={ acosWafGlobalS 261 } 

		xmlCheckMaxAttrValueLenViolation OBJECT-TYPE
		SYNTAX  CounterBasedGauge64 
		MAX-ACCESS read-only 
		STATUS current
		DESCRIPTION  "XML Limit Value Length violation" 
		::={ acosWafGlobalS 262 } 

		xmlCheckMaxCdataLenSuccess OBJECT-TYPE
		SYNTAX  CounterBasedGauge64 
		MAX-ACCESS read-only 
		STATUS current
		DESCRIPTION  "XML Limit CData Length check passed" 
		::={ acosWafGlobalS 263 } 

		xmlCheckMaxCdataLenViolation OBJECT-TYPE
		SYNTAX  CounterBasedGauge64 
		MAX-ACCESS read-only 
		STATUS current
		DESCRIPTION  "XML Limit CData Length violation" 
		::={ acosWafGlobalS 264 } 

		xmlCheckMaxElemSuccess OBJECT-TYPE
		SYNTAX  CounterBasedGauge64 
		MAX-ACCESS read-only 
		STATUS current
		DESCRIPTION  "XML Limit Element check passed" 
		::={ acosWafGlobalS 265 } 

		xmlCheckMaxElemViolation OBJECT-TYPE
		SYNTAX  CounterBasedGauge64 
		MAX-ACCESS read-only 
		STATUS current
		DESCRIPTION  "XML Limit Element violation" 
		::={ acosWafGlobalS 266 } 

		xmlCheckMaxElemChildSuccess OBJECT-TYPE
		SYNTAX  CounterBasedGauge64 
		MAX-ACCESS read-only 
		STATUS current
		DESCRIPTION  "XML Limit Element Child check passed" 
		::={ acosWafGlobalS 267 } 

		xmlCheckMaxElemChildViolation OBJECT-TYPE
		SYNTAX  CounterBasedGauge64 
		MAX-ACCESS read-only 
		STATUS current
		DESCRIPTION  "XML Limit Element Child violation" 
		::={ acosWafGlobalS 268 } 

		xmlCheckMaxElemDepthSuccess OBJECT-TYPE
		SYNTAX  CounterBasedGauge64 
		MAX-ACCESS read-only 
		STATUS current
		DESCRIPTION  "XML Limit Element Depth check passed" 
		::={ acosWafGlobalS 269 } 

		xmlCheckMaxElemDepthViolation OBJECT-TYPE
		SYNTAX  CounterBasedGauge64 
		MAX-ACCESS read-only 
		STATUS current
		DESCRIPTION  "XML Limit Element Depth violation" 
		::={ acosWafGlobalS 270 } 

		xmlCheckMaxElemNameLenSuccess OBJECT-TYPE
		SYNTAX  CounterBasedGauge64 
		MAX-ACCESS read-only 
		STATUS current
		DESCRIPTION  "XML Limit Element Name Length check passed" 
		::={ acosWafGlobalS 271 } 

		xmlCheckMaxElemNameLenViolation OBJECT-TYPE
		SYNTAX  CounterBasedGauge64 
		MAX-ACCESS read-only 
		STATUS current
		DESCRIPTION  "XML Limit Element Name Length violation" 
		::={ acosWafGlobalS 272 } 

		xmlCheckMaxEntityExpSuccess OBJECT-TYPE
		SYNTAX  CounterBasedGauge64 
		MAX-ACCESS read-only 
		STATUS current
		DESCRIPTION  "XML Limit Entity Expansions check passed" 
		::={ acosWafGlobalS 273 } 

		xmlCheckMaxEntityExpViolation OBJECT-TYPE
		SYNTAX  CounterBasedGauge64 
		MAX-ACCESS read-only 
		STATUS current
		DESCRIPTION  "XML Limit Entity Expansions violation" 
		::={ acosWafGlobalS 274 } 

		xmlCheckMaxEntityExpDepthSuccess OBJECT-TYPE
		SYNTAX  CounterBasedGauge64 
		MAX-ACCESS read-only 
		STATUS current
		DESCRIPTION  "XML Limit Entities Depth check passed" 
		::={ acosWafGlobalS 275 } 

		xmlCheckMaxEntityExpDepthViolation OBJECT-TYPE
		SYNTAX  CounterBasedGauge64 
		MAX-ACCESS read-only 
		STATUS current
		DESCRIPTION  "XML Limit Entities Depth violation" 
		::={ acosWafGlobalS 276 } 

		xmlCheckMaxNamespaceSuccess OBJECT-TYPE
		SYNTAX  CounterBasedGauge64 
		MAX-ACCESS read-only 
		STATUS current
		DESCRIPTION  "XML Limit Namespace check passed" 
		::={ acosWafGlobalS 277 } 

		xmlCheckMaxNamespaceViolation OBJECT-TYPE
		SYNTAX  CounterBasedGauge64 
		MAX-ACCESS read-only 
		STATUS current
		DESCRIPTION  "XML Limit Namespace violation" 
		::={ acosWafGlobalS 278 } 

		xmlCheckNamespaceUriLenSuccess OBJECT-TYPE
		SYNTAX  CounterBasedGauge64 
		MAX-ACCESS read-only 
		STATUS current
		DESCRIPTION  "XML Limit Namespace URI Length check passed" 
		::={ acosWafGlobalS 279 } 

		xmlCheckNamespaceUriLenViolation OBJECT-TYPE
		SYNTAX  CounterBasedGauge64 
		MAX-ACCESS read-only 
		STATUS current
		DESCRIPTION  "XML Limit Namespace URI Length violation" 
		::={ acosWafGlobalS 280 } 

		xmlCheckSqliaSuccess OBJECT-TYPE
		SYNTAX  CounterBasedGauge64 
		MAX-ACCESS read-only 
		STATUS current
		DESCRIPTION  "XML Sqlia Check passed" 
		::={ acosWafGlobalS 281 } 

		xmlCheckSqliaViolation OBJECT-TYPE
		SYNTAX  CounterBasedGauge64 
		MAX-ACCESS read-only 
		STATUS current
		DESCRIPTION  "XML Sqlia Check violation" 
		::={ acosWafGlobalS 282 } 

		xmlCheckXssSuccess OBJECT-TYPE
		SYNTAX  CounterBasedGauge64 
		MAX-ACCESS read-only 
		STATUS current
		DESCRIPTION  "XML XSS Check passed" 
		::={ acosWafGlobalS 283 } 

		xmlCheckXssViolation OBJECT-TYPE
		SYNTAX  CounterBasedGauge64 
		MAX-ACCESS read-only 
		STATUS current
		DESCRIPTION  "XML XSS Check violation" 
		::={ acosWafGlobalS 284 } 

		xmlContentCheckSchemaSuccess OBJECT-TYPE
		SYNTAX  CounterBasedGauge64 
		MAX-ACCESS read-only 
		STATUS current
		DESCRIPTION  "XML Schema passed" 
		::={ acosWafGlobalS 285 } 

		xmlContentCheckSchemaViolation OBJECT-TYPE
		SYNTAX  CounterBasedGauge64 
		MAX-ACCESS read-only 
		STATUS current
		DESCRIPTION  "XML Schema violation" 
		::={ acosWafGlobalS 286 } 

		xmlContentCheckWsdlSuccess OBJECT-TYPE
		SYNTAX  CounterBasedGauge64 
		MAX-ACCESS read-only 
		STATUS current
		DESCRIPTION  "WSDL passed" 
		::={ acosWafGlobalS 287 } 

		xmlContentCheckWsdlViolation OBJECT-TYPE
		SYNTAX  CounterBasedGauge64 
		MAX-ACCESS read-only 
		STATUS current
		DESCRIPTION  "WSDL violation" 
		::={ acosWafGlobalS 288 } 

		learningListFull OBJECT-TYPE
		SYNTAX  CounterBasedGauge64 
		MAX-ACCESS read-only 
		STATUS current
		DESCRIPTION  "Learning list is full" 
		::={ acosWafGlobalS 289 } 

		actionAllow OBJECT-TYPE
		SYNTAX  CounterBasedGauge64 
		MAX-ACCESS read-only 
		STATUS current
		DESCRIPTION  "Request Action allowed" 
		::={ acosWafGlobalS 290 } 

		actionDeny200 OBJECT-TYPE
		SYNTAX  CounterBasedGauge64 
		MAX-ACCESS read-only 
		STATUS current
		DESCRIPTION  "Request Deny with 200" 
		::={ acosWafGlobalS 291 } 

		actionDeny403 OBJECT-TYPE
		SYNTAX  CounterBasedGauge64 
		MAX-ACCESS read-only 
		STATUS current
		DESCRIPTION  "Request Deny with 403" 
		::={ acosWafGlobalS 292 } 

		actionDenyRedirect OBJECT-TYPE
		SYNTAX  CounterBasedGauge64 
		MAX-ACCESS read-only 
		STATUS current
		DESCRIPTION  "Request Deny with Redirect" 
		::={ acosWafGlobalS 293 } 

		actionDenyReset OBJECT-TYPE
		SYNTAX  CounterBasedGauge64 
		MAX-ACCESS read-only 
		STATUS current
		DESCRIPTION  "Request Deny with Resets" 
		::={ acosWafGlobalS 294 } 

		actionDrop OBJECT-TYPE
		SYNTAX  CounterBasedGauge64 
		MAX-ACCESS read-only 
		STATUS current
		DESCRIPTION  "Number of Dropped Requests" 
		::={ acosWafGlobalS 295 } 

		actionDenyCustomResponse OBJECT-TYPE
		SYNTAX  CounterBasedGauge64 
		MAX-ACCESS read-only 
		STATUS current
		DESCRIPTION  "Request Deny with custom response" 
		::={ acosWafGlobalS 296 } 

		actionLearn OBJECT-TYPE
		SYNTAX  CounterBasedGauge64 
		MAX-ACCESS read-only 
		STATUS current
		DESCRIPTION  "Request Learning Updates" 
		::={ acosWafGlobalS 297 } 

		actionLog OBJECT-TYPE
		SYNTAX  CounterBasedGauge64 
		MAX-ACCESS read-only 
		STATUS current
		DESCRIPTION  "Log request violation" 
		::={ acosWafGlobalS 298 } 

		policyLimitExceeded OBJECT-TYPE
		SYNTAX  CounterBasedGauge64 
		MAX-ACCESS read-only 
		STATUS current
		DESCRIPTION  "Policy limit exceeded" 
		::={ acosWafGlobalS 299 } 

		sessionsAlloc OBJECT-TYPE
		SYNTAX  CounterBasedGauge64 
		MAX-ACCESS read-only 
		STATUS current
		DESCRIPTION  "Sessions allocated" 
		::={ acosWafGlobalS 300 } 

		sessionsFreed OBJECT-TYPE
		SYNTAX  CounterBasedGauge64 
		MAX-ACCESS read-only 
		STATUS current
		DESCRIPTION  "Sessions freed" 
		::={ acosWafGlobalS 301 } 

		outOfSessions OBJECT-TYPE
		SYNTAX  CounterBasedGauge64 
		MAX-ACCESS read-only 
		STATUS current
		DESCRIPTION  "Out of sessions" 
		::={ acosWafGlobalS 302 } 

		tooManySessions OBJECT-TYPE
		SYNTAX  CounterBasedGauge64 
		MAX-ACCESS read-only 
		STATUS current
		DESCRIPTION  "Too many sessions consumed" 
		::={ acosWafGlobalS 303 } 

		regexViolation OBJECT-TYPE
		SYNTAX  CounterBasedGauge64 
		MAX-ACCESS read-only 
		STATUS current
		DESCRIPTION  "Regular expression failure" 
		::={ acosWafGlobalS 304 } 

		requestCheckCommandInjectionCookiesSuccess OBJECT-TYPE
		SYNTAX  CounterBasedGauge64 
		MAX-ACCESS read-only 
		STATUS current
		DESCRIPTION  "Command Injection Check cookies passed" 
		::={ acosWafGlobalS 305 } 

		requestCheckCommandInjectionCookiesViolation OBJECT-TYPE
		SYNTAX  CounterBasedGauge64 
		MAX-ACCESS read-only 
		STATUS current
		DESCRIPTION  "Command Injection Check cookies violation" 
		::={ acosWafGlobalS 306 } 

		requestCheckCommandInjectionHeadersSuccess OBJECT-TYPE
		SYNTAX  CounterBasedGauge64 
		MAX-ACCESS read-only 
		STATUS current
		DESCRIPTION  "Command Injection Check headers passed" 
		::={ acosWafGlobalS 307 } 

		requestCheckCommandInjectionHeadersViolation OBJECT-TYPE
		SYNTAX  CounterBasedGauge64 
		MAX-ACCESS read-only 
		STATUS current
		DESCRIPTION  "Command Injection Check headers violation" 
		::={ acosWafGlobalS 308 } 

		requestCheckCommandInjectionUriQuerySuccess OBJECT-TYPE
		SYNTAX  CounterBasedGauge64 
		MAX-ACCESS read-only 
		STATUS current
		DESCRIPTION  "Command Injection Check url query arguments passed" 
		::={ acosWafGlobalS 309 } 

		requestCheckCommandInjectionUriQueryViolation OBJECT-TYPE
		SYNTAX  CounterBasedGauge64 
		MAX-ACCESS read-only 
		STATUS current
		DESCRIPTION  "Command Injection Check url query arguments violation" 
		::={ acosWafGlobalS 310 } 

		requestCheckCommandInjectionFormBodySuccess OBJECT-TYPE
		SYNTAX  CounterBasedGauge64 
		MAX-ACCESS read-only 
		STATUS current
		DESCRIPTION  "Command Injection Check form body arguments passed" 
		::={ acosWafGlobalS 311 } 

		requestCheckCommandInjectionFormBodyViolation OBJECT-TYPE
		SYNTAX  CounterBasedGauge64 
		MAX-ACCESS read-only 
		STATUS current
		DESCRIPTION  "Command Injection Check form body arguments violation" 
		::={ acosWafGlobalS 312 } 

		cookieSecurityDecryptInGracePeriodViolation OBJECT-TYPE
		SYNTAX  CounterBasedGauge64 
		MAX-ACCESS read-only 
		STATUS current
		DESCRIPTION  "Cookie Decrypt violation but in grace period" 
		::={ acosWafGlobalS 313 } 

		formResponseNonPostSuccess OBJECT-TYPE
		SYNTAX  CounterBasedGauge64 
		MAX-ACCESS read-only 
		STATUS current
		DESCRIPTION  "Response form method was POST" 
		::={ acosWafGlobalS 314 } 

		formResponseNonPostViolation OBJECT-TYPE
		SYNTAX  CounterBasedGauge64 
		MAX-ACCESS read-only 
		STATUS current
		DESCRIPTION  "Response form method was not POST" 
		::={ acosWafGlobalS 315 } 

		formResponseNonPostSanitize OBJECT-TYPE
		SYNTAX  CounterBasedGauge64 
		MAX-ACCESS read-only 
		STATUS current
		DESCRIPTION  "Changed response form method to POST" 
		::={ acosWafGlobalS 316 } 

		xmlCheckMaxEntityDeclSuccess OBJECT-TYPE
		SYNTAX  CounterBasedGauge64 
		MAX-ACCESS read-only 
		STATUS current
		DESCRIPTION  "XML Limit Entity Decl check passed" 
		::={ acosWafGlobalS 317 } 

		xmlCheckMaxEntityDeclViolation OBJECT-TYPE
		SYNTAX  CounterBasedGauge64 
		MAX-ACCESS read-only 
		STATUS current
		DESCRIPTION  "XML Limit Entity Decl violation" 
		::={ acosWafGlobalS 318 } 

		xmlCheckMaxEntityDepthSuccess OBJECT-TYPE
		SYNTAX  CounterBasedGauge64 
		MAX-ACCESS read-only 
		STATUS current
		DESCRIPTION  "XML Limit Entity Depth check passed" 
		::={ acosWafGlobalS 319 } 

		xmlCheckMaxEntityDepthViolation OBJECT-TYPE
		SYNTAX  CounterBasedGauge64 
		MAX-ACCESS read-only 
		STATUS current
		DESCRIPTION  "XML Limit Entity Depth violation" 
		::={ acosWafGlobalS 320 } 

		actionResponseAllow OBJECT-TYPE
		SYNTAX  CounterBasedGauge64 
		MAX-ACCESS read-only 
		STATUS current
		DESCRIPTION  "Response Action allowed" 
		::={ acosWafGlobalS 321 } 

		actionResponseDeny200 OBJECT-TYPE
		SYNTAX  CounterBasedGauge64 
		MAX-ACCESS read-only 
		STATUS current
		DESCRIPTION  "Response Deny with 200" 
		::={ acosWafGlobalS 322 } 

		actionResponseDeny403 OBJECT-TYPE
		SYNTAX  CounterBasedGauge64 
		MAX-ACCESS read-only 
		STATUS current
		DESCRIPTION  "Response Deny with 403" 
		::={ acosWafGlobalS 323 } 

		actionResponseDenyRedirect OBJECT-TYPE
		SYNTAX  CounterBasedGauge64 
		MAX-ACCESS read-only 
		STATUS current
		DESCRIPTION  "Response Deny with Redirect" 
		::={ acosWafGlobalS 324 } 

		actionResponseDenyReset OBJECT-TYPE
		SYNTAX  CounterBasedGauge64 
		MAX-ACCESS read-only 
		STATUS current
		DESCRIPTION  "Deny with Resets" 
		::={ acosWafGlobalS 325 } 

		actionResponseDrop OBJECT-TYPE
		SYNTAX  CounterBasedGauge64 
		MAX-ACCESS read-only 
		STATUS current
		DESCRIPTION  "Number of Dropped Responses" 
		::={ acosWafGlobalS 326 } 

		actionResponseDenyCustomResponse OBJECT-TYPE
		SYNTAX  CounterBasedGauge64 
		MAX-ACCESS read-only 
		STATUS current
		DESCRIPTION  "Response Deny with custom response" 
		::={ acosWafGlobalS 327 } 

		actionResponseLearn OBJECT-TYPE
		SYNTAX  CounterBasedGauge64 
		MAX-ACCESS read-only 
		STATUS current
		DESCRIPTION  "Response Learning Updates" 
		::={ acosWafGlobalS 328 } 

		actionResponseLog OBJECT-TYPE
		SYNTAX  CounterBasedGauge64 
		MAX-ACCESS read-only 
		STATUS current
		DESCRIPTION  "Log response violation" 
		::={ acosWafGlobalS 329 } 

		httpProtocolPostWithoutContentTypeSuccess OBJECT-TYPE
		SYNTAX  CounterBasedGauge64 
		MAX-ACCESS read-only 
		STATUS current
		DESCRIPTION  "POST without content type check passed" 
		::={ acosWafGlobalS 330 } 

		httpProtocolPostWithoutContentTypeViolation OBJECT-TYPE
		SYNTAX  CounterBasedGauge64 
		MAX-ACCESS read-only 
		STATUS current
		DESCRIPTION  "POST without content type check violation" 
		::={ acosWafGlobalS 331 } 

		httpProtocolBodyWithoutContentTypeSuccess OBJECT-TYPE
		SYNTAX  CounterBasedGauge64 
		MAX-ACCESS read-only 
		STATUS current
		DESCRIPTION  "Body without content type check passed" 
		::={ acosWafGlobalS 332 } 

		httpProtocolBodyWithoutContentTypeViolation OBJECT-TYPE
		SYNTAX  CounterBasedGauge64 
		MAX-ACCESS read-only 
		STATUS current
		DESCRIPTION  "Body without content type check violation" 
		::={ acosWafGlobalS 333 } 

		httpProtocolNonSslCookiePrefixSuccess OBJECT-TYPE
		SYNTAX  CounterBasedGauge64 
		MAX-ACCESS read-only 
		STATUS current
		DESCRIPTION  "Cookie Name Prefix check passed" 
		::={ acosWafGlobalS 334 } 

		httpProtocolNonSslCookiePrefixViolation OBJECT-TYPE
		SYNTAX  CounterBasedGauge64 
		MAX-ACCESS read-only 
		STATUS current
		DESCRIPTION  "Cookie Name Prefix check violation" 
		::={ acosWafGlobalS 335 } 

		cookieSecurityAddSamesiteSuccess OBJECT-TYPE
		SYNTAX  CounterBasedGauge64 
		MAX-ACCESS read-only 
		STATUS current
		DESCRIPTION  "Cookie Security - samesite attribute added successfully" 
		::={ acosWafGlobalS 336 } 

		cookieSecurityAddSamesiteViolation OBJECT-TYPE
		SYNTAX  CounterBasedGauge64 
		MAX-ACCESS read-only 
		STATUS current
		DESCRIPTION  "Cookie Security - samesite attribute violation" 
		::={ acosWafGlobalS 337 } 

		ruleSetRequest OBJECT-TYPE
		SYNTAX  CounterBasedGauge64 
		MAX-ACCESS read-only 
		STATUS current
		DESCRIPTION  "Requests hanlded by WAF rule set" 
		::={ acosWafGlobalS 338 } 

		ruleSetResponse OBJECT-TYPE
		SYNTAX  CounterBasedGauge64 
		MAX-ACCESS read-only 
		STATUS current
		DESCRIPTION  "Responses hanlded by WAF rule set" 
		::={ acosWafGlobalS 339 } 

		phase1Pass OBJECT-TYPE
		SYNTAX  CounterBasedGauge64 
		MAX-ACCESS read-only 
		STATUS current
		DESCRIPTION  "WAF rule set pass hits in phase 1" 
		::={ acosWafGlobalS 340 } 

		phase1Allow OBJECT-TYPE
		SYNTAX  CounterBasedGauge64 
		MAX-ACCESS read-only 
		STATUS current
		DESCRIPTION  "WAF rule set allow hits in phase 1" 
		::={ acosWafGlobalS 341 } 

		phase1Deny OBJECT-TYPE
		SYNTAX  CounterBasedGauge64 
		MAX-ACCESS read-only 
		STATUS current
		DESCRIPTION  "WAF rule set deny hits in phase 1" 
		::={ acosWafGlobalS 342 } 

		phase1Drop OBJECT-TYPE
		SYNTAX  CounterBasedGauge64 
		MAX-ACCESS read-only 
		STATUS current
		DESCRIPTION  "WAF rule set drop hits in phase 1" 
		::={ acosWafGlobalS 343 } 

		phase1Redirect OBJECT-TYPE
		SYNTAX  CounterBasedGauge64 
		MAX-ACCESS read-only 
		STATUS current
		DESCRIPTION  "WAF rule set redirect hits in phase 1" 
		::={ acosWafGlobalS 344 } 

		phase1Other OBJECT-TYPE
		SYNTAX  CounterBasedGauge64 
		MAX-ACCESS read-only 
		STATUS current
		DESCRIPTION  "WAF rule set other hits in phase 1" 
		::={ acosWafGlobalS 345 } 

		phase2Pass OBJECT-TYPE
		SYNTAX  CounterBasedGauge64 
		MAX-ACCESS read-only 
		STATUS current
		DESCRIPTION  "WAF rule set pass hits in phase 2" 
		::={ acosWafGlobalS 346 } 

		phase2Allow OBJECT-TYPE
		SYNTAX  CounterBasedGauge64 
		MAX-ACCESS read-only 
		STATUS current
		DESCRIPTION  "WAF rule set allow hits in phase 2" 
		::={ acosWafGlobalS 347 } 

		phase2Deny OBJECT-TYPE
		SYNTAX  CounterBasedGauge64 
		MAX-ACCESS read-only 
		STATUS current
		DESCRIPTION  "WAF rule set deny hits in phase 2" 
		::={ acosWafGlobalS 348 } 

		phase2Drop OBJECT-TYPE
		SYNTAX  CounterBasedGauge64 
		MAX-ACCESS read-only 
		STATUS current
		DESCRIPTION  "WAF rule set drop hits in phase 2" 
		::={ acosWafGlobalS 349 } 

		phase2Redirect OBJECT-TYPE
		SYNTAX  CounterBasedGauge64 
		MAX-ACCESS read-only 
		STATUS current
		DESCRIPTION  "WAF rule set redirect hits in phase 2" 
		::={ acosWafGlobalS 350 } 

		phase2Other OBJECT-TYPE
		SYNTAX  CounterBasedGauge64 
		MAX-ACCESS read-only 
		STATUS current
		DESCRIPTION  "WAF rule set other hits in phase 2" 
		::={ acosWafGlobalS 351 } 

		phase3Pass OBJECT-TYPE
		SYNTAX  CounterBasedGauge64 
		MAX-ACCESS read-only 
		STATUS current
		DESCRIPTION  "WAF rule set pass hits in phase 3" 
		::={ acosWafGlobalS 352 } 

		phase3Allow OBJECT-TYPE
		SYNTAX  CounterBasedGauge64 
		MAX-ACCESS read-only 
		STATUS current
		DESCRIPTION  "WAF rule set allow hits in phase 3" 
		::={ acosWafGlobalS 353 } 

		phase3Deny OBJECT-TYPE
		SYNTAX  CounterBasedGauge64 
		MAX-ACCESS read-only 
		STATUS current
		DESCRIPTION  "WAF rule set deny hits in phase 3" 
		::={ acosWafGlobalS 354 } 

		phase3Drop OBJECT-TYPE
		SYNTAX  CounterBasedGauge64 
		MAX-ACCESS read-only 
		STATUS current
		DESCRIPTION  "WAF rule set drop hits in phase 3" 
		::={ acosWafGlobalS 355 } 

		phase3Redirect OBJECT-TYPE
		SYNTAX  CounterBasedGauge64 
		MAX-ACCESS read-only 
		STATUS current
		DESCRIPTION  "WAF rule set redirect hits in phase 3" 
		::={ acosWafGlobalS 356 } 

		phase3Other OBJECT-TYPE
		SYNTAX  CounterBasedGauge64 
		MAX-ACCESS read-only 
		STATUS current
		DESCRIPTION  "WAF rule set other hits in phase 3" 
		::={ acosWafGlobalS 357 } 

		phase4Pass OBJECT-TYPE
		SYNTAX  CounterBasedGauge64 
		MAX-ACCESS read-only 
		STATUS current
		DESCRIPTION  "WAF rule set pass hits in phase 4" 
		::={ acosWafGlobalS 358 } 

		phase4Allow OBJECT-TYPE
		SYNTAX  CounterBasedGauge64 
		MAX-ACCESS read-only 
		STATUS current
		DESCRIPTION  "WAF rule set allow hits in phase 4" 
		::={ acosWafGlobalS 359 } 

		phase4Deny OBJECT-TYPE
		SYNTAX  CounterBasedGauge64 
		MAX-ACCESS read-only 
		STATUS current
		DESCRIPTION  "WAF rule set deny hits in phase 4" 
		::={ acosWafGlobalS 360 } 

		phase4Drop OBJECT-TYPE
		SYNTAX  CounterBasedGauge64 
		MAX-ACCESS read-only 
		STATUS current
		DESCRIPTION  "WAF rule set drop hits in phase 4" 
		::={ acosWafGlobalS 361 } 

		phase4Redirect OBJECT-TYPE
		SYNTAX  CounterBasedGauge64 
		MAX-ACCESS read-only 
		STATUS current
		DESCRIPTION  "WAF rule set redirect hits in phase 4" 
		::={ acosWafGlobalS 362 } 

		phase4Other OBJECT-TYPE
		SYNTAX  CounterBasedGauge64 
		MAX-ACCESS read-only 
		STATUS current
		DESCRIPTION  "WAF rule set other hits in phase 4" 
		::={ acosWafGlobalS 363 } 

acosWafTemplate                     OBJECT IDENTIFIER ::= { acosWaf 5 }
acosWafTemplateS                    OBJECT IDENTIFIER ::= { acosWafTemplate 1 }

wafTemplateSTable OBJECT-TYPE
		SYNTAX SEQUENCE OF WafTemplateSEntry
		MAX-ACCESS not-accessible
		STATUS current
		::={ acosWafTemplateS 1 } 


	wafTemplateSEntry OBJECT-TYPE
		SYNTAX WafTemplateSEntry
		MAX-ACCESS not-accessible
		STATUS current
		INDEX {
			wafTemplateName
		}
		::={ wafTemplateSTable 1 } 


	WafTemplateSEntry ::=
		SEQUENCE {
			wafTemplateName DisplayString, 
			wafTemplatetotalReq CounterBasedGauge64,
			wafTemplatereqAllowed CounterBasedGauge64,
			wafTemplatereqDenied CounterBasedGauge64,
			wafTemplaterespDenied CounterBasedGauge64,
			wafTemplatebruteForceSuccess CounterBasedGauge64,
			wafTemplatebruteForceViolation CounterBasedGauge64,
			wafTemplatebruteForceChallengeCookieSent CounterBasedGauge64,
			wafTemplatebruteForceChallengeCookieSuccess CounterBasedGauge64,
			wafTemplatebruteForceChallengeCookieViolation CounterBasedGauge64,
			wafTemplatebruteForceChallengeJavascriptSent CounterBasedGauge64,
			wafTemplatebruteForceChallengeJavascriptSuccess CounterBasedGauge64,
			wafTemplatebruteForceChallengeJavascriptViolation CounterBasedGauge64,
			wafTemplatebruteForceChallengeCaptchaSent CounterBasedGauge64,
			wafTemplatebruteForceChallengeCaptchaSuccess CounterBasedGauge64,
			wafTemplatebruteForceChallengeCaptchaViolation CounterBasedGauge64,
			wafTemplatebruteForceLockoutLimitSuccess CounterBasedGauge64,
			wafTemplatebruteForceLockoutLimitViolation CounterBasedGauge64,
			wafTemplatebruteForceChallengeLimitSuccess CounterBasedGauge64,
			wafTemplatebruteForceChallengeLimitViolation CounterBasedGauge64,
			wafTemplatebruteForceResponseCodesTriggered CounterBasedGauge64,
			wafTemplatebruteForceResponseHeadersTriggered CounterBasedGauge64,
			wafTemplatebruteForceResponseStringTriggered CounterBasedGauge64,
			wafTemplatecookieSecurityEncryptSuccess CounterBasedGauge64,
			wafTemplatecookieSecurityEncryptViolation CounterBasedGauge64,
			wafTemplatecookieSecurityEncryptLimitExceeded CounterBasedGauge64,
			wafTemplatecookieSecurityEncryptSkipRcache CounterBasedGauge64,
			wafTemplatecookieSecurityDecryptSuccess CounterBasedGauge64,
			wafTemplatecookieSecurityDecryptViolation CounterBasedGauge64,
			wafTemplatecookieSecuritySignSuccess CounterBasedGauge64,
			wafTemplatecookieSecuritySignViolation CounterBasedGauge64,
			wafTemplatecookieSecuritySignLimitExceeded CounterBasedGauge64,
			wafTemplatecookieSecuritySignSkipRcache CounterBasedGauge64,
			wafTemplatecookieSecuritySignatureCheckSuccess CounterBasedGauge64,
			wafTemplatecookieSecuritySignatureCheckViolation CounterBasedGauge64,
			wafTemplatecookieSecurityAddHttpOnlySuccess CounterBasedGauge64,
			wafTemplatecookieSecurityAddHttpOnlyViolation CounterBasedGauge64,
			wafTemplatecookieSecurityAddSecureSuccess CounterBasedGauge64,
			wafTemplatecookieSecurityAddSecureViolation CounterBasedGauge64,
			wafTemplatecookieSecurityMissingCookieSuccess CounterBasedGauge64,
			wafTemplatecookieSecurityMissingCookieViolation CounterBasedGauge64,
			wafTemplatecookieSecurityUnrecognizedCookieSuccess CounterBasedGauge64,
			wafTemplatecookieSecurityUnrecognizedCookieViolation CounterBasedGauge64,
			wafTemplatecookieSecurityCookiePolicySuccess CounterBasedGauge64,
			wafTemplatecookieSecurityCookiePolicyViolation CounterBasedGauge64,
			wafTemplatecookieSecurityPersistentCookies CounterBasedGauge64,
			wafTemplatecookieSecurityPersistentCookiesEncrypted CounterBasedGauge64,
			wafTemplatecookieSecurityPersistentCookiesSigned CounterBasedGauge64,
			wafTemplatecookieSecuritySessionCookies CounterBasedGauge64,
			wafTemplatecookieSecuritySessionCookiesEncrypted CounterBasedGauge64,
			wafTemplatecookieSecuritySessionCookiesSigned CounterBasedGauge64,
			wafTemplatecookieSecurityAllowedSessionCookies CounterBasedGauge64,
			wafTemplatecookieSecurityAllowedPersistentCookies CounterBasedGauge64,
			wafTemplatecookieSecurityDisallowedSessionCookies CounterBasedGauge64,
			wafTemplatecookieSecurityDisallowedPersistentCookies CounterBasedGauge64,
			wafTemplatecookieSecurityAllowedSessionSetCookies CounterBasedGauge64,
			wafTemplatecookieSecurityAllowedPersistentSetCookies CounterBasedGauge64,
			wafTemplatecookieSecurityDisallowedSessionSetCookies CounterBasedGauge64,
			wafTemplatecookieSecurityDisallowedPersistentSetCookies CounterBasedGauge64,
			wafTemplatecspHeaderViolation CounterBasedGauge64,
			wafTemplatecspHeaderSuccess CounterBasedGauge64,
			wafTemplatecspHeaderInserted CounterBasedGauge64,
			wafTemplateformCsrfTagSuccess CounterBasedGauge64,
			wafTemplateformCsrfTagViolation CounterBasedGauge64,
			wafTemplateformConsistencySuccess CounterBasedGauge64,
			wafTemplateformConsistencyViolation CounterBasedGauge64,
			wafTemplateformTagInserted CounterBasedGauge64,
			wafTemplateformNonSslSuccess CounterBasedGauge64,
			wafTemplateformNonSslViolation CounterBasedGauge64,
			wafTemplateformNonPostSuccess CounterBasedGauge64,
			wafTemplateformNonPostViolation CounterBasedGauge64,
			wafTemplateformCheckSuccess CounterBasedGauge64,
			wafTemplateformCheckViolation CounterBasedGauge64,
			wafTemplateformCheckSanitize CounterBasedGauge64,
			wafTemplateformNonMaskedPasswordSuccess CounterBasedGauge64,
			wafTemplateformNonMaskedPasswordViolation CounterBasedGauge64,
			wafTemplateformNonSslPasswordSuccess CounterBasedGauge64,
			wafTemplateformNonSslPasswordViolation CounterBasedGauge64,
			wafTemplateformPasswordAutocompleteSuccess CounterBasedGauge64,
			wafTemplateformPasswordAutocompleteViolation CounterBasedGauge64,
			wafTemplateformSetNoCacheSuccess CounterBasedGauge64,
			wafTemplateformSetNoCache CounterBasedGauge64,
			wafTemplatedlpCcnSuccess CounterBasedGauge64,
			wafTemplatedlpCcnAmexViolation CounterBasedGauge64,
			wafTemplatedlpCcnAmexMasked CounterBasedGauge64,
			wafTemplatedlpCcnDinersViolation CounterBasedGauge64,
			wafTemplatedlpCcnDinersMasked CounterBasedGauge64,
			wafTemplatedlpCcnVisaViolation CounterBasedGauge64,
			wafTemplatedlpCcnVisaMasked CounterBasedGauge64,
			wafTemplatedlpCcnMastercardViolation CounterBasedGauge64,
			wafTemplatedlpCcnMastercardMasked CounterBasedGauge64,
			wafTemplatedlpCcnDiscoverViolation CounterBasedGauge64,
			wafTemplatedlpCcnDiscoverMasked CounterBasedGauge64,
			wafTemplatedlpCcnJcbViolation CounterBasedGauge64,
			wafTemplatedlpCcnJcbMasked CounterBasedGauge64,
			wafTemplatedlpSsnSuccess CounterBasedGauge64,
			wafTemplatedlpSsnViolation CounterBasedGauge64,
			wafTemplatedlpPcreSuccess CounterBasedGauge64,
			wafTemplatedlpPcreViolation CounterBasedGauge64,
			wafTemplatedlpPcreMasked CounterBasedGauge64,
			wafTemplateevasionCheckApacheWhitespaceSuccess CounterBasedGauge64,
			wafTemplateevasionCheckApacheWhitespaceViolation CounterBasedGauge64,
			wafTemplateevasionCheckDecodeEntitiesSuccess CounterBasedGauge64,
			wafTemplateevasionCheckDecodeEntitiesViolation CounterBasedGauge64,
			wafTemplateevasionCheckDecodeEscapedCharsSuccess CounterBasedGauge64,
			wafTemplateevasionCheckDecodeEscapedCharsViolation CounterBasedGauge64,
			wafTemplateevasionCheckDecodeUnicodeCharsSuccess CounterBasedGauge64,
			wafTemplateevasionCheckDecodeUnicodeCharsViolation CounterBasedGauge64,
			wafTemplateevasionCheckDirTraversalSuccess CounterBasedGauge64,
			wafTemplateevasionCheckDirTraversalViolation CounterBasedGauge64,
			wafTemplateevasionCheckHighAsciiBytesSuccess CounterBasedGauge64,
			wafTemplateevasionCheckHighAsciiBytesViolation CounterBasedGauge64,
			wafTemplateevasionCheckInvalidHexEncodingSuccess CounterBasedGauge64,
			wafTemplateevasionCheckInvalidHexEncodingViolation CounterBasedGauge64,
			wafTemplateevasionCheckMultipleEncodingLevelsSuccess CounterBasedGauge64,
			wafTemplateevasionCheckMultipleEncodingLevelsViolation CounterBasedGauge64,
			wafTemplateevasionCheckMultipleSlashesSuccess CounterBasedGauge64,
			wafTemplateevasionCheckMultipleSlashesViolation CounterBasedGauge64,
			wafTemplateevasionCheckMaxLevelsSuccess CounterBasedGauge64,
			wafTemplateevasionCheckMaxLevelsViolation CounterBasedGauge64,
			wafTemplateevasionCheckRemoveCommentsSuccess CounterBasedGauge64,
			wafTemplateevasionCheckRemoveCommentsViolation CounterBasedGauge64,
			wafTemplateevasionCheckRemoveSpacesSuccess CounterBasedGauge64,
			wafTemplateevasionCheckRemoveSpacesViolation CounterBasedGauge64,
			wafTemplatehttpLimitMaxContentLengthSuccess CounterBasedGauge64,
			wafTemplatehttpLimitMaxContentLengthViolation CounterBasedGauge64,
			wafTemplatehttpLimitMaxCookieHeaderLengthSuccess CounterBasedGauge64,
			wafTemplatehttpLimitMaxCookieHeaderLengthViolation CounterBasedGauge64,
			wafTemplatehttpLimitMaxCookieNameLengthSuccess CounterBasedGauge64,
			wafTemplatehttpLimitMaxCookieNameLengthViolation CounterBasedGauge64,
			wafTemplatehttpLimitMaxCookieValueLengthSuccess CounterBasedGauge64,
			wafTemplatehttpLimitMaxCookieValueLengthViolation CounterBasedGauge64,
			wafTemplatehttpLimitMaxCookiesSuccess CounterBasedGauge64,
			wafTemplatehttpLimitMaxCookiesViolation CounterBasedGauge64,
			wafTemplatehttpLimitMaxCookiesLengthSuccess CounterBasedGauge64,
			wafTemplatehttpLimitMaxCookiesLengthViolation CounterBasedGauge64,
			wafTemplatehttpLimitMaxDataParseSuccess CounterBasedGauge64,
			wafTemplatehttpLimitMaxDataParseViolation CounterBasedGauge64,
			wafTemplatehttpLimitMaxEntitiesSuccess CounterBasedGauge64,
			wafTemplatehttpLimitMaxEntitiesViolation CounterBasedGauge64,
			wafTemplatehttpLimitMaxHeaderLengthSuccess CounterBasedGauge64,
			wafTemplatehttpLimitMaxHeaderLengthViolation CounterBasedGauge64,
			wafTemplatehttpLimitMaxHeaderNameLengthSuccess CounterBasedGauge64,
			wafTemplatehttpLimitMaxHeaderNameLengthViolation CounterBasedGauge64,
			wafTemplatehttpLimitMaxHeaderValueLengthSuccess CounterBasedGauge64,
			wafTemplatehttpLimitMaxHeaderValueLengthViolation CounterBasedGauge64,
			wafTemplatehttpLimitMaxHeadersSuccess CounterBasedGauge64,
			wafTemplatehttpLimitMaxHeadersViolation CounterBasedGauge64,
			wafTemplatehttpLimitMaxHeadersLengthSuccess CounterBasedGauge64,
			wafTemplatehttpLimitMaxHeadersLengthViolation CounterBasedGauge64,
			wafTemplatehttpLimitMaxParamNameLengthSuccess CounterBasedGauge64,
			wafTemplatehttpLimitMaxParamNameLengthViolation CounterBasedGauge64,
			wafTemplatehttpLimitMaxParamValueLengthSuccess CounterBasedGauge64,
			wafTemplatehttpLimitMaxParamValueLengthViolation CounterBasedGauge64,
			wafTemplatehttpLimitMaxParamsSuccess CounterBasedGauge64,
			wafTemplatehttpLimitMaxParamsViolation CounterBasedGauge64,
			wafTemplatehttpLimitMaxParamsLengthSuccess CounterBasedGauge64,
			wafTemplatehttpLimitMaxParamsLengthViolation CounterBasedGauge64,
			wafTemplatehttpLimitMaxPostLengthSuccess CounterBasedGauge64,
			wafTemplatehttpLimitMaxPostLengthViolation CounterBasedGauge64,
			wafTemplatehttpLimitMaxQueryLengthSuccess CounterBasedGauge64,
			wafTemplatehttpLimitMaxQueryLengthViolation CounterBasedGauge64,
			wafTemplatehttpLimitMaxRequestLengthSuccess CounterBasedGauge64,
			wafTemplatehttpLimitMaxRequestLengthViolation CounterBasedGauge64,
			wafTemplatehttpLimitMaxRequestLineLengthSuccess CounterBasedGauge64,
			wafTemplatehttpLimitMaxRequestLineLengthViolation CounterBasedGauge64,
			wafTemplatemaxUrlLengthSuccess CounterBasedGauge64,
			wafTemplatemaxUrlLengthViolation CounterBasedGauge64,
			wafTemplatehttpProtocolAllowedHeadersSuccess CounterBasedGauge64,
			wafTemplatehttpProtocolAllowedHeadersViolation CounterBasedGauge64,
			wafTemplatehttpProtocolAllowedVersionsSuccess CounterBasedGauge64,
			wafTemplatehttpProtocolAllowedVersionsViolation CounterBasedGauge64,
			wafTemplatehttpProtocolAllowedMethodCheckSuccess CounterBasedGauge64,
			wafTemplatehttpProtocolAllowedMethodCheckViolation CounterBasedGauge64,
			wafTemplatehttpProtocolBadMultipartRequestSuccess CounterBasedGauge64,
			wafTemplatehttpProtocolBadMultipartRequestViolation CounterBasedGauge64,
			wafTemplatehttpProtocolGetWithContentSuccess CounterBasedGauge64,
			wafTemplatehttpProtocolGetWithContentViolation CounterBasedGauge64,
			wafTemplatehttpProtocolHeadWithContentSuccess CounterBasedGauge64,
			wafTemplatehttpProtocolHeadWithContentViolation CounterBasedGauge64,
			wafTemplatehttpProtocolHostHeaderWithIpSuccess CounterBasedGauge64,
			wafTemplatehttpProtocolHostHeaderWithIpViolation CounterBasedGauge64,
			wafTemplatehttpProtocolInvalidUrlEncodingSuccess CounterBasedGauge64,
			wafTemplatehttpProtocolInvalidUrlEncodingViolation CounterBasedGauge64,
			wafTemplatehttpProtocolMalformedContentLengthSuccess CounterBasedGauge64,
			wafTemplatehttpProtocolMalformedContentLengthViolation CounterBasedGauge64,
			wafTemplatehttpProtocolMalformedHeaderSuccess CounterBasedGauge64,
			wafTemplatehttpProtocolMalformedHeaderViolation CounterBasedGauge64,
			wafTemplatehttpProtocolMalformedParameterSuccess CounterBasedGauge64,
			wafTemplatehttpProtocolMalformedParameterViolation CounterBasedGauge64,
			wafTemplatehttpProtocolMalformedRequestSuccess CounterBasedGauge64,
			wafTemplatehttpProtocolMalformedRequestViolation CounterBasedGauge64,
			wafTemplatehttpProtocolMalformedRequestLineSuccess CounterBasedGauge64,
			wafTemplatehttpProtocolMalformedRequestLineViolation CounterBasedGauge64,
			wafTemplatehttpProtocolMissingHeaderValueSuccess CounterBasedGauge64,
			wafTemplatehttpProtocolMissingHeaderValueViolation CounterBasedGauge64,
			wafTemplatehttpProtocolMissingHostHeaderSuccess CounterBasedGauge64,
			wafTemplatehttpProtocolMissingHostHeaderViolation CounterBasedGauge64,
			wafTemplatehttpProtocolMultipleContentLengthSuccess CounterBasedGauge64,
			wafTemplatehttpProtocolMultipleContentLengthViolation CounterBasedGauge64,
			wafTemplatehttpProtocolPostWith0ContentSuccess CounterBasedGauge64,
			wafTemplatehttpProtocolPostWith0ContentViolation CounterBasedGauge64,
			wafTemplatehttpProtocolPostWithoutContentSuccess CounterBasedGauge64,
			wafTemplatehttpProtocolPostWithoutContentViolation CounterBasedGauge64,
			wafTemplatehttpProtocolSuccess CounterBasedGauge64,
			wafTemplatehttpProtocolViolation CounterBasedGauge64,
			wafTemplatejsonCheckFormatSuccess CounterBasedGauge64,
			wafTemplatejsonCheckFormatViolation CounterBasedGauge64,
			wafTemplatejsonCheckMaxArrayValueCountSuccess CounterBasedGauge64,
			wafTemplatejsonCheckMaxArrayValueCountViolation CounterBasedGauge64,
			wafTemplatejsonCheckMaxDepthSuccess CounterBasedGauge64,
			wafTemplatejsonCheckMaxDepthViolation CounterBasedGauge64,
			wafTemplatejsonCheckMaxObjectMemberCountSuccess CounterBasedGauge64,
			wafTemplatejsonCheckMaxObjectMemberCountViolation CounterBasedGauge64,
			wafTemplatejsonCheckMaxStringSuccess CounterBasedGauge64,
			wafTemplatejsonCheckMaxStringViolation CounterBasedGauge64,
			wafTemplaterequestCheckBotSuccess CounterBasedGauge64,
			wafTemplaterequestCheckBotViolation CounterBasedGauge64,
			wafTemplaterequestCheckRedirectWlistSuccess CounterBasedGauge64,
			wafTemplaterequestCheckRedirectWlistViolation CounterBasedGauge64,
			wafTemplaterequestCheckRedirectWlistLearn CounterBasedGauge64,
			wafTemplaterequestCheckRefererSuccess CounterBasedGauge64,
			wafTemplaterequestCheckRefererViolation CounterBasedGauge64,
			wafTemplaterequestCheckRefererRedirect CounterBasedGauge64,
			wafTemplaterequestCheckSessionCheckNone CounterBasedGauge64,
			wafTemplaterequestCheckSessionCheckSuccess CounterBasedGauge64,
			wafTemplaterequestCheckSessionCheckViolation CounterBasedGauge64,
			wafTemplaterequestCheckSqliaUrlSuccess CounterBasedGauge64,
			wafTemplaterequestCheckSqliaUrlViolation CounterBasedGauge64,
			wafTemplaterequestCheckSqliaUrlSanitize CounterBasedGauge64,
			wafTemplaterequestCheckSqliaPostBodySuccess CounterBasedGauge64,
			wafTemplaterequestCheckSqliaPostBodyViolation CounterBasedGauge64,
			wafTemplaterequestCheckSqliaPostBodySanitize CounterBasedGauge64,
			wafTemplaterequestCheckUrlListSuccess CounterBasedGauge64,
			wafTemplaterequestCheckUrlListViolation CounterBasedGauge64,
			wafTemplaterequestCheckUrlListLearn CounterBasedGauge64,
			wafTemplaterequestCheckUrlWhitelistSuccess CounterBasedGauge64,
			wafTemplaterequestCheckUrlWhitelistViolation CounterBasedGauge64,
			wafTemplaterequestCheckUrlBlacklistSuccess CounterBasedGauge64,
			wafTemplaterequestCheckUrlBlacklistViolation CounterBasedGauge64,
			wafTemplaterequestCheckXssCookieSuccess CounterBasedGauge64,
			wafTemplaterequestCheckXssCookieViolation CounterBasedGauge64,
			wafTemplaterequestCheckXssCookieSanitize CounterBasedGauge64,
			wafTemplaterequestCheckXssUrlSuccess CounterBasedGauge64,
			wafTemplaterequestCheckXssUrlViolation CounterBasedGauge64,
			wafTemplaterequestCheckXssUrlSanitize CounterBasedGauge64,
			wafTemplaterequestCheckXssPostBodySuccess CounterBasedGauge64,
			wafTemplaterequestCheckXssPostBodyViolation CounterBasedGauge64,
			wafTemplaterequestCheckXssPostBodySanitize CounterBasedGauge64,
			wafTemplateresponseCloakingHideStatusCodeSuccess CounterBasedGauge64,
			wafTemplateresponseCloakingHideStatusCodeViolation CounterBasedGauge64,
			wafTemplateresponseCloakingFilterHeadersSuccess CounterBasedGauge64,
			wafTemplateresponseCloakingFilterHeadersViolation CounterBasedGauge64,
			wafTemplatesoapCheckSuccess CounterBasedGauge64,
			wafTemplatesoapCheckViolation CounterBasedGauge64,
			wafTemplatexmlCheckFormatSuccess CounterBasedGauge64,
			wafTemplatexmlCheckFormatViolation CounterBasedGauge64,
			wafTemplatexmlCheckMaxAttrSuccess CounterBasedGauge64,
			wafTemplatexmlCheckMaxAttrViolation CounterBasedGauge64,
			wafTemplatexmlCheckMaxAttrNameLenSuccess CounterBasedGauge64,
			wafTemplatexmlCheckMaxAttrNameLenViolation CounterBasedGauge64,
			wafTemplatexmlCheckMaxAttrValueLenSuccess CounterBasedGauge64,
			wafTemplatexmlCheckMaxAttrValueLenViolation CounterBasedGauge64,
			wafTemplatexmlCheckMaxCdataLenSuccess CounterBasedGauge64,
			wafTemplatexmlCheckMaxCdataLenViolation CounterBasedGauge64,
			wafTemplatexmlCheckMaxElemSuccess CounterBasedGauge64,
			wafTemplatexmlCheckMaxElemViolation CounterBasedGauge64,
			wafTemplatexmlCheckMaxElemChildSuccess CounterBasedGauge64,
			wafTemplatexmlCheckMaxElemChildViolation CounterBasedGauge64,
			wafTemplatexmlCheckMaxElemDepthSuccess CounterBasedGauge64,
			wafTemplatexmlCheckMaxElemDepthViolation CounterBasedGauge64,
			wafTemplatexmlCheckMaxElemNameLenSuccess CounterBasedGauge64,
			wafTemplatexmlCheckMaxElemNameLenViolation CounterBasedGauge64,
			wafTemplatexmlCheckMaxEntityExpSuccess CounterBasedGauge64,
			wafTemplatexmlCheckMaxEntityExpViolation CounterBasedGauge64,
			wafTemplatexmlCheckMaxEntityExpDepthSuccess CounterBasedGauge64,
			wafTemplatexmlCheckMaxEntityExpDepthViolation CounterBasedGauge64,
			wafTemplatexmlCheckMaxNamespaceSuccess CounterBasedGauge64,
			wafTemplatexmlCheckMaxNamespaceViolation CounterBasedGauge64,
			wafTemplatexmlCheckNamespaceUriLenSuccess CounterBasedGauge64,
			wafTemplatexmlCheckNamespaceUriLenViolation CounterBasedGauge64,
			wafTemplatexmlCheckSqliaSuccess CounterBasedGauge64,
			wafTemplatexmlCheckSqliaViolation CounterBasedGauge64,
			wafTemplatexmlCheckXssSuccess CounterBasedGauge64,
			wafTemplatexmlCheckXssViolation CounterBasedGauge64,
			wafTemplatexmlContentCheckSchemaSuccess CounterBasedGauge64,
			wafTemplatexmlContentCheckSchemaViolation CounterBasedGauge64,
			wafTemplatexmlContentCheckWsdlSuccess CounterBasedGauge64,
			wafTemplatexmlContentCheckWsdlViolation CounterBasedGauge64,
			wafTemplatelearningListFull CounterBasedGauge64,
			wafTemplateactionAllow CounterBasedGauge64,
			wafTemplateactionDeny200 CounterBasedGauge64,
			wafTemplateactionDeny403 CounterBasedGauge64,
			wafTemplateactionDenyRedirect CounterBasedGauge64,
			wafTemplateactionDenyReset CounterBasedGauge64,
			wafTemplateactionDrop CounterBasedGauge64,
			wafTemplateactionDenyCustomResponse CounterBasedGauge64,
			wafTemplateactionLearn CounterBasedGauge64,
			wafTemplateactionLog CounterBasedGauge64,
			wafTemplatepolicyLimitExceeded CounterBasedGauge64,
			wafTemplatesessionsAlloc CounterBasedGauge64,
			wafTemplatesessionsFreed CounterBasedGauge64,
			wafTemplateoutOfSessions CounterBasedGauge64,
			wafTemplatetooManySessions CounterBasedGauge64,
			wafTemplateregexViolation CounterBasedGauge64,
			wafTemplateRequestCheckCommandInjectionCookiesSuccess CounterBasedGauge64,
			wafTemplateRequestCheckCommandInjectionCookiesViolation CounterBasedGauge64,
			wafTemplateRequestCheckCommandInjectionHeadersSuccess CounterBasedGauge64,
			wafTemplateRequestCheckCommandInjectionHeadersViolation CounterBasedGauge64,
			wafTemplateRequestCheckCommandInjectionUrlQuerySuccess CounterBasedGauge64,
			wafTemplateRequestCheckCommandInjectionUrlQueryViolation CounterBasedGauge64,
			wafTemplateRequestCheckCommandInjectionFormBodySuccess CounterBasedGauge64,
			wafTemplateRequestCheckCommandInjectionFormBodyViolation CounterBasedGauge64,
			wafTemplatecookieSecurityDecryptInGracePeriodViolation CounterBasedGauge64,
			wafTemplateformResponseNonPostSuccess CounterBasedGauge64,
			wafTemplateformResponseNonPostViolation CounterBasedGauge64,
			wafTemplateformResponseNonPostSanitize CounterBasedGauge64,
			wafTemplatexmlCheckMaxEntityDeclSuccess CounterBasedGauge64,
			wafTemplatexmlCheckMaxEntityDeclViolation CounterBasedGauge64,
			wafTemplatexmlCheckMaxEntityDepthSuccess CounterBasedGauge64,
			wafTemplatexmlCheckMaxEntityDepthViolation CounterBasedGauge64,
			wafTemplateResponseActionAllow CounterBasedGauge64,
			wafTemplateResponseActionDeny200 CounterBasedGauge64,
			wafTemplateResponseActionDeny403 CounterBasedGauge64,
			wafTemplateResponseActionDenyRedirect CounterBasedGauge64,
			wafTemplateResponseActionDenyReset CounterBasedGauge64,
			wafTemplateResponseActionDrop CounterBasedGauge64,
			wafTemplateResponseActionDenyCustomResponse CounterBasedGauge64,
			wafTemplateResponseActionLearn CounterBasedGauge64,
			wafTemplateResponseActionLog CounterBasedGauge64,
			wafTemplatehttpProtocolPostWithoutContentTypeSuccess CounterBasedGauge64,
			wafTemplatehttpProtocolPostWithoutContentTypeViolation CounterBasedGauge64,
			wafTemplatehttpProtocolBodyWithoutContentTypeSuccess CounterBasedGauge64,
			wafTemplatehttpProtocolBodyWithoutContentTypeViolation CounterBasedGauge64,
			wafTemplatehttpProtocolNonSslCookiePrefixSuccess CounterBasedGauge64,
			wafTemplatehttpProtocolNonSslCookiePrefixViolation CounterBasedGauge64,
			wafTemplatecookieSecurityAddSamesiteSuccess CounterBasedGauge64,
			wafTemplatecookieSecurityAddSamesiteViolation CounterBasedGauge64,
			ruleSetRequest CounterBasedGauge64,
			ruleSetResponse CounterBasedGauge64,
			phase1Pass CounterBasedGauge64,
			phase1Allow CounterBasedGauge64,
			phase1Deny CounterBasedGauge64,
			phase1Drop CounterBasedGauge64,
			phase1Redirect CounterBasedGauge64,
			phase1Other CounterBasedGauge64,
			phase2Pass CounterBasedGauge64,
			phase2Allow CounterBasedGauge64,
			phase2Deny CounterBasedGauge64,
			phase2Drop CounterBasedGauge64,
			phase2Redirect CounterBasedGauge64,
			phase2Other CounterBasedGauge64,
			phase3Pass CounterBasedGauge64,
			phase3Allow CounterBasedGauge64,
			phase3Deny CounterBasedGauge64,
			phase3Drop CounterBasedGauge64,
			phase3Redirect CounterBasedGauge64,
			phase3Other CounterBasedGauge64,
			phase4Pass CounterBasedGauge64,
			phase4Allow CounterBasedGauge64,
			phase4Deny CounterBasedGauge64,
			phase4Drop CounterBasedGauge64,
			phase4Redirect CounterBasedGauge64,
			phase4Other CounterBasedGauge64
		}

			wafTemplateName OBJECT-TYPE
			SYNTAX  DisplayString 
			MAX-ACCESS read-only 
			STATUS current
			DESCRIPTION  "WAF Template Name" 
			::={ wafTemplateSEntry 1 } 

			wafTemplatetotalReq OBJECT-TYPE
			SYNTAX  CounterBasedGauge64 
			MAX-ACCESS read-only 
			STATUS current
			DESCRIPTION  "Total Requests" 
			::={ wafTemplateSEntry 2 } 

			wafTemplatereqAllowed OBJECT-TYPE
			SYNTAX  CounterBasedGauge64 
			MAX-ACCESS read-only 
			STATUS current
			DESCRIPTION  "Requests Allowed" 
			::={ wafTemplateSEntry 3 } 

			wafTemplatereqDenied OBJECT-TYPE
			SYNTAX  CounterBasedGauge64 
			MAX-ACCESS read-only 
			STATUS current
			DESCRIPTION  "Requests Denied" 
			::={ wafTemplateSEntry 4 } 

			wafTemplaterespDenied OBJECT-TYPE
			SYNTAX  CounterBasedGauge64 
			MAX-ACCESS read-only 
			STATUS current
			DESCRIPTION  "Responses Denied" 
			::={ wafTemplateSEntry 5 } 

			wafTemplatebruteForceSuccess OBJECT-TYPE
			SYNTAX  CounterBasedGauge64 
			MAX-ACCESS read-only 
			STATUS current
			DESCRIPTION  "Brute-Force checks passed" 
			::={ wafTemplateSEntry 6 } 

			wafTemplatebruteForceViolation OBJECT-TYPE
			SYNTAX  CounterBasedGauge64 
			MAX-ACCESS read-only 
			STATUS current
			DESCRIPTION  "Brute-Force checks violation" 
			::={ wafTemplateSEntry 7 } 

			wafTemplatebruteForceChallengeCookieSent OBJECT-TYPE
			SYNTAX  CounterBasedGauge64 
			MAX-ACCESS read-only 
			STATUS current
			DESCRIPTION  "Cookie Challenge Sent" 
			::={ wafTemplateSEntry 8 } 

			wafTemplatebruteForceChallengeCookieSuccess OBJECT-TYPE
			SYNTAX  CounterBasedGauge64 
			MAX-ACCESS read-only 
			STATUS current
			DESCRIPTION  "Cookie Challenge check passed" 
			::={ wafTemplateSEntry 9 } 

			wafTemplatebruteForceChallengeCookieViolation OBJECT-TYPE
			SYNTAX  CounterBasedGauge64 
			MAX-ACCESS read-only 
			STATUS current
			DESCRIPTION  "Cookie challenge violation" 
			::={ wafTemplateSEntry 10 } 

			wafTemplatebruteForceChallengeJavascriptSent OBJECT-TYPE
			SYNTAX  CounterBasedGauge64 
			MAX-ACCESS read-only 
			STATUS current
			DESCRIPTION  "JavaScript challenge sent" 
			::={ wafTemplateSEntry 11 } 

			wafTemplatebruteForceChallengeJavascriptSuccess OBJECT-TYPE
			SYNTAX  CounterBasedGauge64 
			MAX-ACCESS read-only 
			STATUS current
			DESCRIPTION  "JavaScript challenge check passed" 
			::={ wafTemplateSEntry 12 } 

			wafTemplatebruteForceChallengeJavascriptViolation OBJECT-TYPE
			SYNTAX  CounterBasedGauge64 
			MAX-ACCESS read-only 
			STATUS current
			DESCRIPTION  "JavaScript challenge violation" 
			::={ wafTemplateSEntry 13 } 

			wafTemplatebruteForceChallengeCaptchaSent OBJECT-TYPE
			SYNTAX  CounterBasedGauge64 
			MAX-ACCESS read-only 
			STATUS current
			DESCRIPTION  "Captcha challenge sent" 
			::={ wafTemplateSEntry 14 } 

			wafTemplatebruteForceChallengeCaptchaSuccess OBJECT-TYPE
			SYNTAX  CounterBasedGauge64 
			MAX-ACCESS read-only 
			STATUS current
			DESCRIPTION  "Captcha challenge check passed" 
			::={ wafTemplateSEntry 15 } 

			wafTemplatebruteForceChallengeCaptchaViolation OBJECT-TYPE
			SYNTAX  CounterBasedGauge64 
			MAX-ACCESS read-only 
			STATUS current
			DESCRIPTION  "Captcha challenge violation" 
			::={ wafTemplateSEntry 16 } 

			wafTemplatebruteForceLockoutLimitSuccess OBJECT-TYPE
			SYNTAX  CounterBasedGauge64 
			MAX-ACCESS read-only 
			STATUS current
			DESCRIPTION  "Lockout limit check passed" 
			::={ wafTemplateSEntry 17 } 

			wafTemplatebruteForceLockoutLimitViolation OBJECT-TYPE
			SYNTAX  CounterBasedGauge64 
			MAX-ACCESS read-only 
			STATUS current
			DESCRIPTION  "Lockout limit violation" 
			::={ wafTemplateSEntry 18 } 

			wafTemplatebruteForceChallengeLimitSuccess OBJECT-TYPE
			SYNTAX  CounterBasedGauge64 
			MAX-ACCESS read-only 
			STATUS current
			DESCRIPTION  "Lockout limit check passed" 
			::={ wafTemplateSEntry 19 } 

			wafTemplatebruteForceChallengeLimitViolation OBJECT-TYPE
			SYNTAX  CounterBasedGauge64 
			MAX-ACCESS read-only 
			STATUS current
			DESCRIPTION  "Lockout limit violation" 
			::={ wafTemplateSEntry 20 } 

			wafTemplatebruteForceResponseCodesTriggered OBJECT-TYPE
			SYNTAX  CounterBasedGauge64 
			MAX-ACCESS read-only 
			STATUS current
			DESCRIPTION  "Response Codes Triggered" 
			::={ wafTemplateSEntry 21 } 

			wafTemplatebruteForceResponseHeadersTriggered OBJECT-TYPE
			SYNTAX  CounterBasedGauge64 
			MAX-ACCESS read-only 
			STATUS current
			DESCRIPTION  "Brute Force Response Headers Triggered" 
			::={ wafTemplateSEntry 22 } 

			wafTemplatebruteForceResponseStringTriggered OBJECT-TYPE
			SYNTAX  CounterBasedGauge64 
			MAX-ACCESS read-only 
			STATUS current
			DESCRIPTION  "Brute Force Response string Triggered" 
			::={ wafTemplateSEntry 23 } 

			wafTemplatecookieSecurityEncryptSuccess OBJECT-TYPE
			SYNTAX  CounterBasedGauge64 
			MAX-ACCESS read-only 
			STATUS current
			DESCRIPTION  "Cookie Security - encrypt successful" 
			::={ wafTemplateSEntry 24 } 

			wafTemplatecookieSecurityEncryptViolation OBJECT-TYPE
			SYNTAX  CounterBasedGauge64 
			MAX-ACCESS read-only 
			STATUS current
			DESCRIPTION  "Cookie Security - encrypt violation" 
			::={ wafTemplateSEntry 25 } 

			wafTemplatecookieSecurityEncryptLimitExceeded OBJECT-TYPE
			SYNTAX  CounterBasedGauge64 
			MAX-ACCESS read-only 
			STATUS current
			DESCRIPTION  "Cookie Security - encrypt limit exceeded" 
			::={ wafTemplateSEntry 26 } 

			wafTemplatecookieSecurityEncryptSkipRcache OBJECT-TYPE
			SYNTAX  CounterBasedGauge64 
			MAX-ACCESS read-only 
			STATUS current
			DESCRIPTION  "Cookie Security - encrypt skipped - RAM cache" 
			::={ wafTemplateSEntry 27 } 

			wafTemplatecookieSecurityDecryptSuccess OBJECT-TYPE
			SYNTAX  CounterBasedGauge64 
			MAX-ACCESS read-only 
			STATUS current
			DESCRIPTION  "Cookie Security - decrypt successful" 
			::={ wafTemplateSEntry 28 } 

			wafTemplatecookieSecurityDecryptViolation OBJECT-TYPE
			SYNTAX  CounterBasedGauge64 
			MAX-ACCESS read-only 
			STATUS current
			DESCRIPTION  "Cookie Security - decrypt violation" 
			::={ wafTemplateSEntry 29 } 

			wafTemplatecookieSecuritySignSuccess OBJECT-TYPE
			SYNTAX  CounterBasedGauge64 
			MAX-ACCESS read-only 
			STATUS current
			DESCRIPTION  "Cookie Security - signing successful" 
			::={ wafTemplateSEntry 30 } 

			wafTemplatecookieSecuritySignViolation OBJECT-TYPE
			SYNTAX  CounterBasedGauge64 
			MAX-ACCESS read-only 
			STATUS current
			DESCRIPTION  "Cookie Security - signing violation" 
			::={ wafTemplateSEntry 31 } 

			wafTemplatecookieSecuritySignLimitExceeded OBJECT-TYPE
			SYNTAX  CounterBasedGauge64 
			MAX-ACCESS read-only 
			STATUS current
			DESCRIPTION  "Cookie Security - signing limit exceeded" 
			::={ wafTemplateSEntry 32 } 

			wafTemplatecookieSecuritySignSkipRcache OBJECT-TYPE
			SYNTAX  CounterBasedGauge64 
			MAX-ACCESS read-only 
			STATUS current
			DESCRIPTION  "Cookie Security - signing skipped - RAM Cache" 
			::={ wafTemplateSEntry 33 } 

			wafTemplatecookieSecuritySignatureCheckSuccess OBJECT-TYPE
			SYNTAX  CounterBasedGauge64 
			MAX-ACCESS read-only 
			STATUS current
			DESCRIPTION  "Cookie Security - signature check successful" 
			::={ wafTemplateSEntry 34 } 

			wafTemplatecookieSecuritySignatureCheckViolation OBJECT-TYPE
			SYNTAX  CounterBasedGauge64 
			MAX-ACCESS read-only 
			STATUS current
			DESCRIPTION  "Cookie Security - signature check violation" 
			::={ wafTemplateSEntry 35 } 

			wafTemplatecookieSecurityAddHttpOnlySuccess OBJECT-TYPE
			SYNTAX  CounterBasedGauge64 
			MAX-ACCESS read-only 
			STATUS current
			DESCRIPTION  "Cookie Security - http-only flag added" 
			::={ wafTemplateSEntry 36 } 

			wafTemplatecookieSecurityAddHttpOnlyViolation OBJECT-TYPE
			SYNTAX  CounterBasedGauge64 
			MAX-ACCESS read-only 
			STATUS current
			DESCRIPTION  "Cookie Security - http-only flag violation" 
			::={ wafTemplateSEntry 37 } 

			wafTemplatecookieSecurityAddSecureSuccess OBJECT-TYPE
			SYNTAX  CounterBasedGauge64 
			MAX-ACCESS read-only 
			STATUS current
			DESCRIPTION  "Cookie Security - secure flag added" 
			::={ wafTemplateSEntry 38 } 

			wafTemplatecookieSecurityAddSecureViolation OBJECT-TYPE
			SYNTAX  CounterBasedGauge64 
			MAX-ACCESS read-only 
			STATUS current
			DESCRIPTION  "Cookie Security - secure flag violation" 
			::={ wafTemplateSEntry 39 } 

			wafTemplatecookieSecurityMissingCookieSuccess OBJECT-TYPE
			SYNTAX  CounterBasedGauge64 
			MAX-ACCESS read-only 
			STATUS current
			DESCRIPTION  "Cookie Security - request with missing cookie" 
			::={ wafTemplateSEntry 40 } 

			wafTemplatecookieSecurityMissingCookieViolation OBJECT-TYPE
			SYNTAX  CounterBasedGauge64 
			MAX-ACCESS read-only 
			STATUS current
			DESCRIPTION  "Cookie Security - missing cookie violation" 
			::={ wafTemplateSEntry 41 } 

			wafTemplatecookieSecurityUnrecognizedCookieSuccess OBJECT-TYPE
			SYNTAX  CounterBasedGauge64 
			MAX-ACCESS read-only 
			STATUS current
			DESCRIPTION  "Cookie Security - request with unrecognized cookie" 
			::={ wafTemplateSEntry 42 } 

			wafTemplatecookieSecurityUnrecognizedCookieViolation OBJECT-TYPE
			SYNTAX  CounterBasedGauge64 
			MAX-ACCESS read-only 
			STATUS current
			DESCRIPTION  "Cookie Security - unrecognized cookie violation" 
			::={ wafTemplateSEntry 43 } 

			wafTemplatecookieSecurityCookiePolicySuccess OBJECT-TYPE
			SYNTAX  CounterBasedGauge64 
			MAX-ACCESS read-only 
			STATUS current
			DESCRIPTION  "Cookie Security - cookie policy passed" 
			::={ wafTemplateSEntry 44 } 

			wafTemplatecookieSecurityCookiePolicyViolation OBJECT-TYPE
			SYNTAX  CounterBasedGauge64 
			MAX-ACCESS read-only 
			STATUS current
			DESCRIPTION  "Cookie Security - cookie policy violation" 
			::={ wafTemplateSEntry 45 } 

			wafTemplatecookieSecurityPersistentCookies OBJECT-TYPE
			SYNTAX  CounterBasedGauge64 
			MAX-ACCESS read-only 
			STATUS current
			DESCRIPTION  "Cookie Security - persistent cookies" 
			::={ wafTemplateSEntry 46 } 

			wafTemplatecookieSecurityPersistentCookiesEncrypted OBJECT-TYPE
			SYNTAX  CounterBasedGauge64 
			MAX-ACCESS read-only 
			STATUS current
			DESCRIPTION  "Cookie Security - encrypted persistent cookies" 
			::={ wafTemplateSEntry 47 } 

			wafTemplatecookieSecurityPersistentCookiesSigned OBJECT-TYPE
			SYNTAX  CounterBasedGauge64 
			MAX-ACCESS read-only 
			STATUS current
			DESCRIPTION  "Cookie Security - signed persistent cookies" 
			::={ wafTemplateSEntry 48 } 

			wafTemplatecookieSecuritySessionCookies OBJECT-TYPE
			SYNTAX  CounterBasedGauge64 
			MAX-ACCESS read-only 
			STATUS current
			DESCRIPTION  "Cookie Security - session cookies" 
			::={ wafTemplateSEntry 49 } 

			wafTemplatecookieSecuritySessionCookiesEncrypted OBJECT-TYPE
			SYNTAX  CounterBasedGauge64 
			MAX-ACCESS read-only 
			STATUS current
			DESCRIPTION  "Cookie Security - encrypted session cookies" 
			::={ wafTemplateSEntry 50 } 

			wafTemplatecookieSecuritySessionCookiesSigned OBJECT-TYPE
			SYNTAX  CounterBasedGauge64 
			MAX-ACCESS read-only 
			STATUS current
			DESCRIPTION  "Cookie Security - signed session cookies" 
			::={ wafTemplateSEntry 51 } 

			wafTemplatecookieSecurityAllowedSessionCookies OBJECT-TYPE
			SYNTAX  CounterBasedGauge64 
			MAX-ACCESS read-only 
			STATUS current
			DESCRIPTION  "Cookie Security - allowed session cookies" 
			::={ wafTemplateSEntry 52 } 

			wafTemplatecookieSecurityAllowedPersistentCookies OBJECT-TYPE
			SYNTAX  CounterBasedGauge64 
			MAX-ACCESS read-only 
			STATUS current
			DESCRIPTION  "Cookie Security - allowed persistent cookies" 
			::={ wafTemplateSEntry 53 } 

			wafTemplatecookieSecurityDisallowedSessionCookies OBJECT-TYPE
			SYNTAX  CounterBasedGauge64 
			MAX-ACCESS read-only 
			STATUS current
			DESCRIPTION  "Cookie Security - disallowed session cookies" 
			::={ wafTemplateSEntry 54 } 

			wafTemplatecookieSecurityDisallowedPersistentCookies OBJECT-TYPE
			SYNTAX  CounterBasedGauge64 
			MAX-ACCESS read-only 
			STATUS current
			DESCRIPTION  "Cookie Security - disallowed persistent cookies" 
			::={ wafTemplateSEntry 55 } 

			wafTemplatecookieSecurityAllowedSessionSetCookies OBJECT-TYPE
			SYNTAX  CounterBasedGauge64 
			MAX-ACCESS read-only 
			STATUS current
			DESCRIPTION  "Cookie Security - disallowed session Set-Cookies" 
			::={ wafTemplateSEntry 56 } 

			wafTemplatecookieSecurityAllowedPersistentSetCookies OBJECT-TYPE
			SYNTAX  CounterBasedGauge64 
			MAX-ACCESS read-only 
			STATUS current
			DESCRIPTION  "Cookie Security - disallowed persistent Set-Cookies" 
			::={ wafTemplateSEntry 57 } 

			wafTemplatecookieSecurityDisallowedSessionSetCookies OBJECT-TYPE
			SYNTAX  CounterBasedGauge64 
			MAX-ACCESS read-only 
			STATUS current
			DESCRIPTION  "Cookie Security - disallowed session Set-Cookies" 
			::={ wafTemplateSEntry 58 } 

			wafTemplatecookieSecurityDisallowedPersistentSetCookies OBJECT-TYPE
			SYNTAX  CounterBasedGauge64 
			MAX-ACCESS read-only 
			STATUS current
			DESCRIPTION  "Cookie Security - disallowed persistent Set-Cookies" 
			::={ wafTemplateSEntry 59 } 

			wafTemplatecspHeaderViolation OBJECT-TYPE
			SYNTAX  CounterBasedGauge64 
			MAX-ACCESS read-only 
			STATUS current
			DESCRIPTION  "CSP header missing" 
			::={ wafTemplateSEntry 60 } 

			wafTemplatecspHeaderSuccess OBJECT-TYPE
			SYNTAX  CounterBasedGauge64 
			MAX-ACCESS read-only 
			STATUS current
			DESCRIPTION  "CSP header found" 
			::={ wafTemplateSEntry 61 } 

			wafTemplatecspHeaderInserted OBJECT-TYPE
			SYNTAX  CounterBasedGauge64 
			MAX-ACCESS read-only 
			STATUS current
			DESCRIPTION  "CSP header Inserted" 
			::={ wafTemplateSEntry 62 } 

			wafTemplateformCsrfTagSuccess OBJECT-TYPE
			SYNTAX  CounterBasedGauge64 
			MAX-ACCESS read-only 
			STATUS current
			DESCRIPTION  "Form CSRF tag passed" 
			::={ wafTemplateSEntry 63 } 

			wafTemplateformCsrfTagViolation OBJECT-TYPE
			SYNTAX  CounterBasedGauge64 
			MAX-ACCESS read-only 
			STATUS current
			DESCRIPTION  "Form CSRF tag violation" 
			::={ wafTemplateSEntry 64 } 

			wafTemplateformConsistencySuccess OBJECT-TYPE
			SYNTAX  CounterBasedGauge64 
			MAX-ACCESS read-only 
			STATUS current
			DESCRIPTION  "Form Consistency passed" 
			::={ wafTemplateSEntry 65 } 

			wafTemplateformConsistencyViolation OBJECT-TYPE
			SYNTAX  CounterBasedGauge64 
			MAX-ACCESS read-only 
			STATUS current
			DESCRIPTION  "Form Consistency violation" 
			::={ wafTemplateSEntry 66 } 

			wafTemplateformTagInserted OBJECT-TYPE
			SYNTAX  CounterBasedGauge64 
			MAX-ACCESS read-only 
			STATUS current
			DESCRIPTION  "Form A10 Tag Inserted" 
			::={ wafTemplateSEntry 67 } 

			wafTemplateformNonSslSuccess OBJECT-TYPE
			SYNTAX  CounterBasedGauge64 
			MAX-ACCESS read-only 
			STATUS current
			DESCRIPTION  "Form Non SSL check passed" 
			::={ wafTemplateSEntry 68 } 

			wafTemplateformNonSslViolation OBJECT-TYPE
			SYNTAX  CounterBasedGauge64 
			MAX-ACCESS read-only 
			STATUS current
			DESCRIPTION  "Form Non SSL violation" 
			::={ wafTemplateSEntry 69 } 

			wafTemplateformNonPostSuccess OBJECT-TYPE
			SYNTAX  CounterBasedGauge64 
			MAX-ACCESS read-only 
			STATUS current
			DESCRIPTION  "Form Method being Non Post in Request passed" 
			::={ wafTemplateSEntry 70 } 

			wafTemplateformNonPostViolation OBJECT-TYPE
			SYNTAX  CounterBasedGauge64 
			MAX-ACCESS read-only 
			STATUS current
			DESCRIPTION  "Form Method being Non Post in Request violation" 
			::={ wafTemplateSEntry 71 } 

			wafTemplateformCheckSuccess OBJECT-TYPE
			SYNTAX  CounterBasedGauge64 
			MAX-ACCESS read-only 
			STATUS current
			DESCRIPTION  "Post Form Check passed" 
			::={ wafTemplateSEntry 72 } 

			wafTemplateformCheckViolation OBJECT-TYPE
			SYNTAX  CounterBasedGauge64 
			MAX-ACCESS read-only 
			STATUS current
			DESCRIPTION  "Post Form Check violation" 
			::={ wafTemplateSEntry 73 } 

			wafTemplateformCheckSanitize OBJECT-TYPE
			SYNTAX  CounterBasedGauge64 
			MAX-ACCESS read-only 
			STATUS current
			DESCRIPTION  "Post Form Check Sanitized" 
			::={ wafTemplateSEntry 74 } 

			wafTemplateformNonMaskedPasswordSuccess OBJECT-TYPE
			SYNTAX  CounterBasedGauge64 
			MAX-ACCESS read-only 
			STATUS current
			DESCRIPTION  "Form Non Masked Password check passed" 
			::={ wafTemplateSEntry 75 } 

			wafTemplateformNonMaskedPasswordViolation OBJECT-TYPE
			SYNTAX  CounterBasedGauge64 
			MAX-ACCESS read-only 
			STATUS current
			DESCRIPTION  "Form Non Masked Password violation" 
			::={ wafTemplateSEntry 76 } 

			wafTemplateformNonSslPasswordSuccess OBJECT-TYPE
			SYNTAX  CounterBasedGauge64 
			MAX-ACCESS read-only 
			STATUS current
			DESCRIPTION  "Form Non SSL Password check passed" 
			::={ wafTemplateSEntry 77 } 

			wafTemplateformNonSslPasswordViolation OBJECT-TYPE
			SYNTAX  CounterBasedGauge64 
			MAX-ACCESS read-only 
			STATUS current
			DESCRIPTION  "Form Non SSL Password violation" 
			::={ wafTemplateSEntry 78 } 

			wafTemplateformPasswordAutocompleteSuccess OBJECT-TYPE
			SYNTAX  CounterBasedGauge64 
			MAX-ACCESS read-only 
			STATUS current
			DESCRIPTION  "Form Password Autocomplete check passed" 
			::={ wafTemplateSEntry 79 } 

			wafTemplateformPasswordAutocompleteViolation OBJECT-TYPE
			SYNTAX  CounterBasedGauge64 
			MAX-ACCESS read-only 
			STATUS current
			DESCRIPTION  "Form Password Autocomplete violation" 
			::={ wafTemplateSEntry 80 } 

			wafTemplateformSetNoCacheSuccess OBJECT-TYPE
			SYNTAX  CounterBasedGauge64 
			MAX-ACCESS read-only 
			STATUS current
			DESCRIPTION  "Form Set No Cache check passed" 
			::={ wafTemplateSEntry 81 } 

			wafTemplateformSetNoCache OBJECT-TYPE
			SYNTAX  CounterBasedGauge64 
			MAX-ACCESS read-only 
			STATUS current
			DESCRIPTION  "Form Set No Cache violation" 
			::={ wafTemplateSEntry 82 } 

			wafTemplatedlpCcnSuccess OBJECT-TYPE
			SYNTAX  CounterBasedGauge64 
			MAX-ACCESS read-only 
			STATUS current
			DESCRIPTION  "Credit Card Number check passed" 
			::={ wafTemplateSEntry 83 } 

			wafTemplatedlpCcnAmexViolation OBJECT-TYPE
			SYNTAX  CounterBasedGauge64 
			MAX-ACCESS read-only 
			STATUS current
			DESCRIPTION  "Amex Credit Card Number Detected" 
			::={ wafTemplateSEntry 84 } 

			wafTemplatedlpCcnAmexMasked OBJECT-TYPE
			SYNTAX  CounterBasedGauge64 
			MAX-ACCESS read-only 
			STATUS current
			DESCRIPTION  "Amex Credit Card Number Masked" 
			::={ wafTemplateSEntry 85 } 

			wafTemplatedlpCcnDinersViolation OBJECT-TYPE
			SYNTAX  CounterBasedGauge64 
			MAX-ACCESS read-only 
			STATUS current
			DESCRIPTION  "Diners Club Credit Card Number Detected" 
			::={ wafTemplateSEntry 86 } 

			wafTemplatedlpCcnDinersMasked OBJECT-TYPE
			SYNTAX  CounterBasedGauge64 
			MAX-ACCESS read-only 
			STATUS current
			DESCRIPTION  "Diners Club Credit Card Number Masked" 
			::={ wafTemplateSEntry 87 } 

			wafTemplatedlpCcnVisaViolation OBJECT-TYPE
			SYNTAX  CounterBasedGauge64 
			MAX-ACCESS read-only 
			STATUS current
			DESCRIPTION  "Visa Credit Card Number Detected" 
			::={ wafTemplateSEntry 88 } 

			wafTemplatedlpCcnVisaMasked OBJECT-TYPE
			SYNTAX  CounterBasedGauge64 
			MAX-ACCESS read-only 
			STATUS current
			DESCRIPTION  "Visa Credit Card Number Masked" 
			::={ wafTemplateSEntry 89 } 

			wafTemplatedlpCcnMastercardViolation OBJECT-TYPE
			SYNTAX  CounterBasedGauge64 
			MAX-ACCESS read-only 
			STATUS current
			DESCRIPTION  "MasterCard Credit Card Number Detected" 
			::={ wafTemplateSEntry 90 } 

			wafTemplatedlpCcnMastercardMasked OBJECT-TYPE
			SYNTAX  CounterBasedGauge64 
			MAX-ACCESS read-only 
			STATUS current
			DESCRIPTION  "MasterCard Credit Card Number Masked" 
			::={ wafTemplateSEntry 91 } 

			wafTemplatedlpCcnDiscoverViolation OBJECT-TYPE
			SYNTAX  CounterBasedGauge64 
			MAX-ACCESS read-only 
			STATUS current
			DESCRIPTION  "Discover Credit Card Number Detected" 
			::={ wafTemplateSEntry 92 } 

			wafTemplatedlpCcnDiscoverMasked OBJECT-TYPE
			SYNTAX  CounterBasedGauge64 
			MAX-ACCESS read-only 
			STATUS current
			DESCRIPTION  "Discover Credit Card Number Masked" 
			::={ wafTemplateSEntry 93 } 

			wafTemplatedlpCcnJcbViolation OBJECT-TYPE
			SYNTAX  CounterBasedGauge64 
			MAX-ACCESS read-only 
			STATUS current
			DESCRIPTION  "JCB Credit Card Number Detected" 
			::={ wafTemplateSEntry 94 } 

			wafTemplatedlpCcnJcbMasked OBJECT-TYPE
			SYNTAX  CounterBasedGauge64 
			MAX-ACCESS read-only 
			STATUS current
			DESCRIPTION  "JCB Credit Card Number Masked" 
			::={ wafTemplateSEntry 95 } 

			wafTemplatedlpSsnSuccess OBJECT-TYPE
			SYNTAX  CounterBasedGauge64 
			MAX-ACCESS read-only 
			STATUS current
			DESCRIPTION  "Social Security Number Mask check passed" 
			::={ wafTemplateSEntry 96 } 

			wafTemplatedlpSsnViolation OBJECT-TYPE
			SYNTAX  CounterBasedGauge64 
			MAX-ACCESS read-only 
			STATUS current
			DESCRIPTION  "Social Security Number Mask violation" 
			::={ wafTemplateSEntry 97 } 

			wafTemplatedlpPcreSuccess OBJECT-TYPE
			SYNTAX  CounterBasedGauge64 
			MAX-ACCESS read-only 
			STATUS current
			DESCRIPTION  "PCRE Mask check passed" 
			::={ wafTemplateSEntry 98 } 

			wafTemplatedlpPcreViolation OBJECT-TYPE
			SYNTAX  CounterBasedGauge64 
			MAX-ACCESS read-only 
			STATUS current
			DESCRIPTION  "PCRE Mask violation" 
			::={ wafTemplateSEntry 99 } 

			wafTemplatedlpPcreMasked OBJECT-TYPE
			SYNTAX  CounterBasedGauge64 
			MAX-ACCESS read-only 
			STATUS current
			DESCRIPTION  "PCRE Mask violation" 
			::={ wafTemplateSEntry 100 } 

			wafTemplateevasionCheckApacheWhitespaceSuccess OBJECT-TYPE
			SYNTAX  CounterBasedGauge64 
			MAX-ACCESS read-only 
			STATUS current
			DESCRIPTION  "Apache Whitespace check passed" 
			::={ wafTemplateSEntry 101 } 

			wafTemplateevasionCheckApacheWhitespaceViolation OBJECT-TYPE
			SYNTAX  CounterBasedGauge64 
			MAX-ACCESS read-only 
			STATUS current
			DESCRIPTION  "Apache Whitespace check violation" 
			::={ wafTemplateSEntry 102 } 

			wafTemplateevasionCheckDecodeEntitiesSuccess OBJECT-TYPE
			SYNTAX  CounterBasedGauge64 
			MAX-ACCESS read-only 
			STATUS current
			DESCRIPTION  "Decode Entities check passed" 
			::={ wafTemplateSEntry 103 } 

			wafTemplateevasionCheckDecodeEntitiesViolation OBJECT-TYPE
			SYNTAX  CounterBasedGauge64 
			MAX-ACCESS read-only 
			STATUS current
			DESCRIPTION  "Decode Entities check violation" 
			::={ wafTemplateSEntry 104 } 

			wafTemplateevasionCheckDecodeEscapedCharsSuccess OBJECT-TYPE
			SYNTAX  CounterBasedGauge64 
			MAX-ACCESS read-only 
			STATUS current
			DESCRIPTION  "Decode Escaped Chars check passed" 
			::={ wafTemplateSEntry 105 } 

			wafTemplateevasionCheckDecodeEscapedCharsViolation OBJECT-TYPE
			SYNTAX  CounterBasedGauge64 
			MAX-ACCESS read-only 
			STATUS current
			DESCRIPTION  "Decode Escaped Chars check violation" 
			::={ wafTemplateSEntry 106 } 

			wafTemplateevasionCheckDecodeUnicodeCharsSuccess OBJECT-TYPE
			SYNTAX  CounterBasedGauge64 
			MAX-ACCESS read-only 
			STATUS current
			DESCRIPTION  "Decode Unicode Chars check passed" 
			::={ wafTemplateSEntry 107 } 

			wafTemplateevasionCheckDecodeUnicodeCharsViolation OBJECT-TYPE
			SYNTAX  CounterBasedGauge64 
			MAX-ACCESS read-only 
			STATUS current
			DESCRIPTION  "Decode Unicode Chars check violation" 
			::={ wafTemplateSEntry 108 } 

			wafTemplateevasionCheckDirTraversalSuccess OBJECT-TYPE
			SYNTAX  CounterBasedGauge64 
			MAX-ACCESS read-only 
			STATUS current
			DESCRIPTION  "Dir traversal check passed" 
			::={ wafTemplateSEntry 109 } 

			wafTemplateevasionCheckDirTraversalViolation OBJECT-TYPE
			SYNTAX  CounterBasedGauge64 
			MAX-ACCESS read-only 
			STATUS current
			DESCRIPTION  "Dir traversal check violation" 
			::={ wafTemplateSEntry 110 } 

			wafTemplateevasionCheckHighAsciiBytesSuccess OBJECT-TYPE
			SYNTAX  CounterBasedGauge64 
			MAX-ACCESS read-only 
			STATUS current
			DESCRIPTION  "High Ascii Bytes check passed" 
			::={ wafTemplateSEntry 111 } 

			wafTemplateevasionCheckHighAsciiBytesViolation OBJECT-TYPE
			SYNTAX  CounterBasedGauge64 
			MAX-ACCESS read-only 
			STATUS current
			DESCRIPTION  "High Ascii Bytes check violation" 
			::={ wafTemplateSEntry 112 } 

			wafTemplateevasionCheckInvalidHexEncodingSuccess OBJECT-TYPE
			SYNTAX  CounterBasedGauge64 
			MAX-ACCESS read-only 
			STATUS current
			DESCRIPTION  "Invalid Hex Encoding check passed" 
			::={ wafTemplateSEntry 113 } 

			wafTemplateevasionCheckInvalidHexEncodingViolation OBJECT-TYPE
			SYNTAX  CounterBasedGauge64 
			MAX-ACCESS read-only 
			STATUS current
			DESCRIPTION  "Invalid Hex Encoding check violation" 
			::={ wafTemplateSEntry 114 } 

			wafTemplateevasionCheckMultipleEncodingLevelsSuccess OBJECT-TYPE
			SYNTAX  CounterBasedGauge64 
			MAX-ACCESS read-only 
			STATUS current
			DESCRIPTION  "Multiple Encoding Levels check passed" 
			::={ wafTemplateSEntry 115 } 

			wafTemplateevasionCheckMultipleEncodingLevelsViolation OBJECT-TYPE
			SYNTAX  CounterBasedGauge64 
			MAX-ACCESS read-only 
			STATUS current
			DESCRIPTION  "Multiple Encoding Levels check violation" 
			::={ wafTemplateSEntry 116 } 

			wafTemplateevasionCheckMultipleSlashesSuccess OBJECT-TYPE
			SYNTAX  CounterBasedGauge64 
			MAX-ACCESS read-only 
			STATUS current
			DESCRIPTION  "Multiple Slashes check passed" 
			::={ wafTemplateSEntry 117 } 

			wafTemplateevasionCheckMultipleSlashesViolation OBJECT-TYPE
			SYNTAX  CounterBasedGauge64 
			MAX-ACCESS read-only 
			STATUS current
			DESCRIPTION  "Multiple Slashes check violation" 
			::={ wafTemplateSEntry 118 } 

			wafTemplateevasionCheckMaxLevelsSuccess OBJECT-TYPE
			SYNTAX  CounterBasedGauge64 
			MAX-ACCESS read-only 
			STATUS current
			DESCRIPTION  "Max Levels check passed" 
			::={ wafTemplateSEntry 119 } 

			wafTemplateevasionCheckMaxLevelsViolation OBJECT-TYPE
			SYNTAX  CounterBasedGauge64 
			MAX-ACCESS read-only 
			STATUS current
			DESCRIPTION  "Max Levels check violation" 
			::={ wafTemplateSEntry 120 } 

			wafTemplateevasionCheckRemoveCommentsSuccess OBJECT-TYPE
			SYNTAX  CounterBasedGauge64 
			MAX-ACCESS read-only 
			STATUS current
			DESCRIPTION  "Remove Comments check passed" 
			::={ wafTemplateSEntry 121 } 

			wafTemplateevasionCheckRemoveCommentsViolation OBJECT-TYPE
			SYNTAX  CounterBasedGauge64 
			MAX-ACCESS read-only 
			STATUS current
			DESCRIPTION  "Remove Comments check violation" 
			::={ wafTemplateSEntry 122 } 

			wafTemplateevasionCheckRemoveSpacesSuccess OBJECT-TYPE
			SYNTAX  CounterBasedGauge64 
			MAX-ACCESS read-only 
			STATUS current
			DESCRIPTION  "Remove Spaces check passed" 
			::={ wafTemplateSEntry 123 } 

			wafTemplateevasionCheckRemoveSpacesViolation OBJECT-TYPE
			SYNTAX  CounterBasedGauge64 
			MAX-ACCESS read-only 
			STATUS current
			DESCRIPTION  "Remove Spaces check violation" 
			::={ wafTemplateSEntry 124 } 

			wafTemplatehttpLimitMaxContentLengthSuccess OBJECT-TYPE
			SYNTAX  CounterBasedGauge64 
			MAX-ACCESS read-only 
			STATUS current
			DESCRIPTION  "MAX content-length check passed" 
			::={ wafTemplateSEntry 125 } 

			wafTemplatehttpLimitMaxContentLengthViolation OBJECT-TYPE
			SYNTAX  CounterBasedGauge64 
			MAX-ACCESS read-only 
			STATUS current
			DESCRIPTION  "MAX content-length check violation" 
			::={ wafTemplateSEntry 126 } 

			wafTemplatehttpLimitMaxCookieHeaderLengthSuccess OBJECT-TYPE
			SYNTAX  CounterBasedGauge64 
			MAX-ACCESS read-only 
			STATUS current
			DESCRIPTION  "MAX cookie header length check passed" 
			::={ wafTemplateSEntry 127 } 

			wafTemplatehttpLimitMaxCookieHeaderLengthViolation OBJECT-TYPE
			SYNTAX  CounterBasedGauge64 
			MAX-ACCESS read-only 
			STATUS current
			DESCRIPTION  "MAX cookie header length violation" 
			::={ wafTemplateSEntry 128 } 

			wafTemplatehttpLimitMaxCookieNameLengthSuccess OBJECT-TYPE
			SYNTAX  CounterBasedGauge64 
			MAX-ACCESS read-only 
			STATUS current
			DESCRIPTION  "MAX cookie name length check passed" 
			::={ wafTemplateSEntry 129 } 

			wafTemplatehttpLimitMaxCookieNameLengthViolation OBJECT-TYPE
			SYNTAX  CounterBasedGauge64 
			MAX-ACCESS read-only 
			STATUS current
			DESCRIPTION  "MAX cookie name length violation" 
			::={ wafTemplateSEntry 130 } 

			wafTemplatehttpLimitMaxCookieValueLengthSuccess OBJECT-TYPE
			SYNTAX  CounterBasedGauge64 
			MAX-ACCESS read-only 
			STATUS current
			DESCRIPTION  "MAX cookie value length check passed" 
			::={ wafTemplateSEntry 131 } 

			wafTemplatehttpLimitMaxCookieValueLengthViolation OBJECT-TYPE
			SYNTAX  CounterBasedGauge64 
			MAX-ACCESS read-only 
			STATUS current
			DESCRIPTION  "MAX cookie value length violation" 
			::={ wafTemplateSEntry 132 } 

			wafTemplatehttpLimitMaxCookiesSuccess OBJECT-TYPE
			SYNTAX  CounterBasedGauge64 
			MAX-ACCESS read-only 
			STATUS current
			DESCRIPTION  "Max Cookies check passed" 
			::={ wafTemplateSEntry 133 } 

			wafTemplatehttpLimitMaxCookiesViolation OBJECT-TYPE
			SYNTAX  CounterBasedGauge64 
			MAX-ACCESS read-only 
			STATUS current
			DESCRIPTION  "Max Cookies violation" 
			::={ wafTemplateSEntry 134 } 

			wafTemplatehttpLimitMaxCookiesLengthSuccess OBJECT-TYPE
			SYNTAX  CounterBasedGauge64 
			MAX-ACCESS read-only 
			STATUS current
			DESCRIPTION  "MAX cookies length check passed" 
			::={ wafTemplateSEntry 135 } 

			wafTemplatehttpLimitMaxCookiesLengthViolation OBJECT-TYPE
			SYNTAX  CounterBasedGauge64 
			MAX-ACCESS read-only 
			STATUS current
			DESCRIPTION  "MAX cookies length violation" 
			::={ wafTemplateSEntry 136 } 

			wafTemplatehttpLimitMaxDataParseSuccess OBJECT-TYPE
			SYNTAX  CounterBasedGauge64 
			MAX-ACCESS read-only 
			STATUS current
			DESCRIPTION  "Buffer Overflow - Max Data Parse check passed" 
			::={ wafTemplateSEntry 137 } 

			wafTemplatehttpLimitMaxDataParseViolation OBJECT-TYPE
			SYNTAX  CounterBasedGauge64 
			MAX-ACCESS read-only 
			STATUS current
			DESCRIPTION  "Buffer Overflow - Max Data Parse violation" 
			::={ wafTemplateSEntry 138 } 

			wafTemplatehttpLimitMaxEntitiesSuccess OBJECT-TYPE
			SYNTAX  CounterBasedGauge64 
			MAX-ACCESS read-only 
			STATUS current
			DESCRIPTION  "Max Entities check passed" 
			::={ wafTemplateSEntry 139 } 

			wafTemplatehttpLimitMaxEntitiesViolation OBJECT-TYPE
			SYNTAX  CounterBasedGauge64 
			MAX-ACCESS read-only 
			STATUS current
			DESCRIPTION  "Max Entities violation" 
			::={ wafTemplateSEntry 140 } 

			wafTemplatehttpLimitMaxHeaderLengthSuccess OBJECT-TYPE
			SYNTAX  CounterBasedGauge64 
			MAX-ACCESS read-only 
			STATUS current
			DESCRIPTION  "MAX header length check passed" 
			::={ wafTemplateSEntry 141 } 

			wafTemplatehttpLimitMaxHeaderLengthViolation OBJECT-TYPE
			SYNTAX  CounterBasedGauge64 
			MAX-ACCESS read-only 
			STATUS current
			DESCRIPTION  "MAX header length check violation" 
			::={ wafTemplateSEntry 142 } 

			wafTemplatehttpLimitMaxHeaderNameLengthSuccess OBJECT-TYPE
			SYNTAX  CounterBasedGauge64 
			MAX-ACCESS read-only 
			STATUS current
			DESCRIPTION  "MAX header name length check passed" 
			::={ wafTemplateSEntry 143 } 

			wafTemplatehttpLimitMaxHeaderNameLengthViolation OBJECT-TYPE
			SYNTAX  CounterBasedGauge64 
			MAX-ACCESS read-only 
			STATUS current
			DESCRIPTION  "MAX header name length check violation" 
			::={ wafTemplateSEntry 144 } 

			wafTemplatehttpLimitMaxHeaderValueLengthSuccess OBJECT-TYPE
			SYNTAX  CounterBasedGauge64 
			MAX-ACCESS read-only 
			STATUS current
			DESCRIPTION  "MAX header value length check passed" 
			::={ wafTemplateSEntry 145 } 

			wafTemplatehttpLimitMaxHeaderValueLengthViolation OBJECT-TYPE
			SYNTAX  CounterBasedGauge64 
			MAX-ACCESS read-only 
			STATUS current
			DESCRIPTION  "MAX header value length check violation" 
			::={ wafTemplateSEntry 146 } 

			wafTemplatehttpLimitMaxHeadersSuccess OBJECT-TYPE
			SYNTAX  CounterBasedGauge64 
			MAX-ACCESS read-only 
			STATUS current
			DESCRIPTION  "MAX headers count check passed" 
			::={ wafTemplateSEntry 147 } 

			wafTemplatehttpLimitMaxHeadersViolation OBJECT-TYPE
			SYNTAX  CounterBasedGauge64 
			MAX-ACCESS read-only 
			STATUS current
			DESCRIPTION  "Max Headers violation" 
			::={ wafTemplateSEntry 148 } 

			wafTemplatehttpLimitMaxHeadersLengthSuccess OBJECT-TYPE
			SYNTAX  CounterBasedGauge64 
			MAX-ACCESS read-only 
			STATUS current
			DESCRIPTION  "MAX headers length check passed" 
			::={ wafTemplateSEntry 149 } 

			wafTemplatehttpLimitMaxHeadersLengthViolation OBJECT-TYPE
			SYNTAX  CounterBasedGauge64 
			MAX-ACCESS read-only 
			STATUS current
			DESCRIPTION  "MAX headers length check violation" 
			::={ wafTemplateSEntry 150 } 

			wafTemplatehttpLimitMaxParamNameLengthSuccess OBJECT-TYPE
			SYNTAX  CounterBasedGauge64 
			MAX-ACCESS read-only 
			STATUS current
			DESCRIPTION  "Limit check - MAX parameter name length check passed" 
			::={ wafTemplateSEntry 151 } 

			wafTemplatehttpLimitMaxParamNameLengthViolation OBJECT-TYPE
			SYNTAX  CounterBasedGauge64 
			MAX-ACCESS read-only 
			STATUS current
			DESCRIPTION  "Limit check - MAX parameter name length violation" 
			::={ wafTemplateSEntry 152 } 

			wafTemplatehttpLimitMaxParamValueLengthSuccess OBJECT-TYPE
			SYNTAX  CounterBasedGauge64 
			MAX-ACCESS read-only 
			STATUS current
			DESCRIPTION  "Limit check - MAX parameter value length check passed" 
			::={ wafTemplateSEntry 153 } 

			wafTemplatehttpLimitMaxParamValueLengthViolation OBJECT-TYPE
			SYNTAX  CounterBasedGauge64 
			MAX-ACCESS read-only 
			STATUS current
			DESCRIPTION  "Limit check - MAX parameter value length violation" 
			::={ wafTemplateSEntry 154 } 

			wafTemplatehttpLimitMaxParamsSuccess OBJECT-TYPE
			SYNTAX  CounterBasedGauge64 
			MAX-ACCESS read-only 
			STATUS current
			DESCRIPTION  "Limit check - MAX parameters check passed" 
			::={ wafTemplateSEntry 155 } 

			wafTemplatehttpLimitMaxParamsViolation OBJECT-TYPE
			SYNTAX  CounterBasedGauge64 
			MAX-ACCESS read-only 
			STATUS current
			DESCRIPTION  "Limit check - MAX parameters violation" 
			::={ wafTemplateSEntry 156 } 

			wafTemplatehttpLimitMaxParamsLengthSuccess OBJECT-TYPE
			SYNTAX  CounterBasedGauge64 
			MAX-ACCESS read-only 
			STATUS current
			DESCRIPTION  "Limit check - MAX parameters total length check passed" 
			::={ wafTemplateSEntry 157 } 

			wafTemplatehttpLimitMaxParamsLengthViolation OBJECT-TYPE
			SYNTAX  CounterBasedGauge64 
			MAX-ACCESS read-only 
			STATUS current
			DESCRIPTION  "Limit check - MAX parameters total length violation" 
			::={ wafTemplateSEntry 158 } 

			wafTemplatehttpLimitMaxPostLengthSuccess OBJECT-TYPE
			SYNTAX  CounterBasedGauge64 
			MAX-ACCESS read-only 
			STATUS current
			DESCRIPTION  "MAX POST length check passed" 
			::={ wafTemplateSEntry 159 } 

			wafTemplatehttpLimitMaxPostLengthViolation OBJECT-TYPE
			SYNTAX  CounterBasedGauge64 
			MAX-ACCESS read-only 
			STATUS current
			DESCRIPTION  "MAX POST length violation" 
			::={ wafTemplateSEntry 160 } 

			wafTemplatehttpLimitMaxQueryLengthSuccess OBJECT-TYPE
			SYNTAX  CounterBasedGauge64 
			MAX-ACCESS read-only 
			STATUS current
			DESCRIPTION  "Limit check - MAX query length check passed" 
			::={ wafTemplateSEntry 161 } 

			wafTemplatehttpLimitMaxQueryLengthViolation OBJECT-TYPE
			SYNTAX  CounterBasedGauge64 
			MAX-ACCESS read-only 
			STATUS current
			DESCRIPTION  "Limit check - MAX query length violation" 
			::={ wafTemplateSEntry 162 } 

			wafTemplatehttpLimitMaxRequestLengthSuccess OBJECT-TYPE
			SYNTAX  CounterBasedGauge64 
			MAX-ACCESS read-only 
			STATUS current
			DESCRIPTION  "Limit check - MAX request length check passed" 
			::={ wafTemplateSEntry 163 } 

			wafTemplatehttpLimitMaxRequestLengthViolation OBJECT-TYPE
			SYNTAX  CounterBasedGauge64 
			MAX-ACCESS read-only 
			STATUS current
			DESCRIPTION  "Limit check - MAX request length violation" 
			::={ wafTemplateSEntry 164 } 

			wafTemplatehttpLimitMaxRequestLineLengthSuccess OBJECT-TYPE
			SYNTAX  CounterBasedGauge64 
			MAX-ACCESS read-only 
			STATUS current
			DESCRIPTION  "Limit check - MAX request line length check passed" 
			::={ wafTemplateSEntry 165 } 

			wafTemplatehttpLimitMaxRequestLineLengthViolation OBJECT-TYPE
			SYNTAX  CounterBasedGauge64 
			MAX-ACCESS read-only 
			STATUS current
			DESCRIPTION  "Limit check - MAX request line length violation" 
			::={ wafTemplateSEntry 166 } 

			wafTemplatemaxUrlLengthSuccess OBJECT-TYPE
			SYNTAX  CounterBasedGauge64 
			MAX-ACCESS read-only 
			STATUS current
			DESCRIPTION  "Limit check - MAX URL length check passed" 
			::={ wafTemplateSEntry 167 } 

			wafTemplatemaxUrlLengthViolation OBJECT-TYPE
			SYNTAX  CounterBasedGauge64 
			MAX-ACCESS read-only 
			STATUS current
			DESCRIPTION  "Limit check - MAX URL length violation" 
			::={ wafTemplateSEntry 168 } 

			wafTemplatehttpProtocolAllowedHeadersSuccess OBJECT-TYPE
			SYNTAX  CounterBasedGauge64 
			MAX-ACCESS read-only 
			STATUS current
			DESCRIPTION  "HTTP headers check passed" 
			::={ wafTemplateSEntry 169 } 

			wafTemplatehttpProtocolAllowedHeadersViolation OBJECT-TYPE
			SYNTAX  CounterBasedGauge64 
			MAX-ACCESS read-only 
			STATUS current
			DESCRIPTION  "HTTP headers check violation" 
			::={ wafTemplateSEntry 170 } 

			wafTemplatehttpProtocolAllowedVersionsSuccess OBJECT-TYPE
			SYNTAX  CounterBasedGauge64 
			MAX-ACCESS read-only 
			STATUS current
			DESCRIPTION  "HTTP versions check passed" 
			::={ wafTemplateSEntry 171 } 

			wafTemplatehttpProtocolAllowedVersionsViolation OBJECT-TYPE
			SYNTAX  CounterBasedGauge64 
			MAX-ACCESS read-only 
			STATUS current
			DESCRIPTION  "HTTP versions check violation" 
			::={ wafTemplateSEntry 172 } 

			wafTemplatehttpProtocolAllowedMethodCheckSuccess OBJECT-TYPE
			SYNTAX  CounterBasedGauge64 
			MAX-ACCESS read-only 
			STATUS current
			DESCRIPTION  "HTTP Method Check passed" 
			::={ wafTemplateSEntry 173 } 

			wafTemplatehttpProtocolAllowedMethodCheckViolation OBJECT-TYPE
			SYNTAX  CounterBasedGauge64 
			MAX-ACCESS read-only 
			STATUS current
			DESCRIPTION  "HTTP Method Check violation" 
			::={ wafTemplateSEntry 174 } 

			wafTemplatehttpProtocolBadMultipartRequestSuccess OBJECT-TYPE
			SYNTAX  CounterBasedGauge64 
			MAX-ACCESS read-only 
			STATUS current
			DESCRIPTION  "Bad multi-part request check passed" 
			::={ wafTemplateSEntry 175 } 

			wafTemplatehttpProtocolBadMultipartRequestViolation OBJECT-TYPE
			SYNTAX  CounterBasedGauge64 
			MAX-ACCESS read-only 
			STATUS current
			DESCRIPTION  "Bad multi-part request check violation" 
			::={ wafTemplateSEntry 176 } 

			wafTemplatehttpProtocolGetWithContentSuccess OBJECT-TYPE
			SYNTAX  CounterBasedGauge64 
			MAX-ACCESS read-only 
			STATUS current
			DESCRIPTION  "GET with content check passed" 
			::={ wafTemplateSEntry 177 } 

			wafTemplatehttpProtocolGetWithContentViolation OBJECT-TYPE
			SYNTAX  CounterBasedGauge64 
			MAX-ACCESS read-only 
			STATUS current
			DESCRIPTION  "GET with content check violation" 
			::={ wafTemplateSEntry 178 } 

			wafTemplatehttpProtocolHeadWithContentSuccess OBJECT-TYPE
			SYNTAX  CounterBasedGauge64 
			MAX-ACCESS read-only 
			STATUS current
			DESCRIPTION  "HEAD with content check passed" 
			::={ wafTemplateSEntry 179 } 

			wafTemplatehttpProtocolHeadWithContentViolation OBJECT-TYPE
			SYNTAX  CounterBasedGauge64 
			MAX-ACCESS read-only 
			STATUS current
			DESCRIPTION  "HEAD with content check violation" 
			::={ wafTemplateSEntry 180 } 

			wafTemplatehttpProtocolHostHeaderWithIpSuccess OBJECT-TYPE
			SYNTAX  CounterBasedGauge64 
			MAX-ACCESS read-only 
			STATUS current
			DESCRIPTION  "Host header with IP check passed" 
			::={ wafTemplateSEntry 181 } 

			wafTemplatehttpProtocolHostHeaderWithIpViolation OBJECT-TYPE
			SYNTAX  CounterBasedGauge64 
			MAX-ACCESS read-only 
			STATUS current
			DESCRIPTION  "Host header with IP check violation" 
			::={ wafTemplateSEntry 182 } 

			wafTemplatehttpProtocolInvalidUrlEncodingSuccess OBJECT-TYPE
			SYNTAX  CounterBasedGauge64 
			MAX-ACCESS read-only 
			STATUS current
			DESCRIPTION  "Invalid url encoding check passed" 
			::={ wafTemplateSEntry 183 } 

			wafTemplatehttpProtocolInvalidUrlEncodingViolation OBJECT-TYPE
			SYNTAX  CounterBasedGauge64 
			MAX-ACCESS read-only 
			STATUS current
			DESCRIPTION  "Invalid url encoding check violation" 
			::={ wafTemplateSEntry 184 } 

			wafTemplatehttpProtocolMalformedContentLengthSuccess OBJECT-TYPE
			SYNTAX  CounterBasedGauge64 
			MAX-ACCESS read-only 
			STATUS current
			DESCRIPTION  "Malformed content-length check passed" 
			::={ wafTemplateSEntry 185 } 

			wafTemplatehttpProtocolMalformedContentLengthViolation OBJECT-TYPE
			SYNTAX  CounterBasedGauge64 
			MAX-ACCESS read-only 
			STATUS current
			DESCRIPTION  "Malformed content-length check violation" 
			::={ wafTemplateSEntry 186 } 

			wafTemplatehttpProtocolMalformedHeaderSuccess OBJECT-TYPE
			SYNTAX  CounterBasedGauge64 
			MAX-ACCESS read-only 
			STATUS current
			DESCRIPTION  "Malformed header check passed" 
			::={ wafTemplateSEntry 187 } 

			wafTemplatehttpProtocolMalformedHeaderViolation OBJECT-TYPE
			SYNTAX  CounterBasedGauge64 
			MAX-ACCESS read-only 
			STATUS current
			DESCRIPTION  "Malformed header check passed" 
			::={ wafTemplateSEntry 188 } 

			wafTemplatehttpProtocolMalformedParameterSuccess OBJECT-TYPE
			SYNTAX  CounterBasedGauge64 
			MAX-ACCESS read-only 
			STATUS current
			DESCRIPTION  "Malformed parameter check passed" 
			::={ wafTemplateSEntry 189 } 

			wafTemplatehttpProtocolMalformedParameterViolation OBJECT-TYPE
			SYNTAX  CounterBasedGauge64 
			MAX-ACCESS read-only 
			STATUS current
			DESCRIPTION  "Malformed parameter check violation" 
			::={ wafTemplateSEntry 190 } 

			wafTemplatehttpProtocolMalformedRequestSuccess OBJECT-TYPE
			SYNTAX  CounterBasedGauge64 
			MAX-ACCESS read-only 
			STATUS current
			DESCRIPTION  "Malformed request check passed" 
			::={ wafTemplateSEntry 191 } 

			wafTemplatehttpProtocolMalformedRequestViolation OBJECT-TYPE
			SYNTAX  CounterBasedGauge64 
			MAX-ACCESS read-only 
			STATUS current
			DESCRIPTION  "Malformed request check violation" 
			::={ wafTemplateSEntry 192 } 

			wafTemplatehttpProtocolMalformedRequestLineSuccess OBJECT-TYPE
			SYNTAX  CounterBasedGauge64 
			MAX-ACCESS read-only 
			STATUS current
			DESCRIPTION  "Malformed request line check passed" 
			::={ wafTemplateSEntry 193 } 

			wafTemplatehttpProtocolMalformedRequestLineViolation OBJECT-TYPE
			SYNTAX  CounterBasedGauge64 
			MAX-ACCESS read-only 
			STATUS current
			DESCRIPTION  "Malformed request line check violation" 
			::={ wafTemplateSEntry 194 } 

			wafTemplatehttpProtocolMissingHeaderValueSuccess OBJECT-TYPE
			SYNTAX  CounterBasedGauge64 
			MAX-ACCESS read-only 
			STATUS current
			DESCRIPTION  "Missing header value check violation" 
			::={ wafTemplateSEntry 195 } 

			wafTemplatehttpProtocolMissingHeaderValueViolation OBJECT-TYPE
			SYNTAX  CounterBasedGauge64 
			MAX-ACCESS read-only 
			STATUS current
			DESCRIPTION  "Missing header value check violation" 
			::={ wafTemplateSEntry 196 } 

			wafTemplatehttpProtocolMissingHostHeaderSuccess OBJECT-TYPE
			SYNTAX  CounterBasedGauge64 
			MAX-ACCESS read-only 
			STATUS current
			DESCRIPTION  "Missing host header check passed" 
			::={ wafTemplateSEntry 197 } 

			wafTemplatehttpProtocolMissingHostHeaderViolation OBJECT-TYPE
			SYNTAX  CounterBasedGauge64 
			MAX-ACCESS read-only 
			STATUS current
			DESCRIPTION  "Missing host header check violation" 
			::={ wafTemplateSEntry 198 } 

			wafTemplatehttpProtocolMultipleContentLengthSuccess OBJECT-TYPE
			SYNTAX  CounterBasedGauge64 
			MAX-ACCESS read-only 
			STATUS current
			DESCRIPTION  "Multiple content-length headers check passed" 
			::={ wafTemplateSEntry 199 } 

			wafTemplatehttpProtocolMultipleContentLengthViolation OBJECT-TYPE
			SYNTAX  CounterBasedGauge64 
			MAX-ACCESS read-only 
			STATUS current
			DESCRIPTION  "Multiple content-length headers check violation" 
			::={ wafTemplateSEntry 200 } 

			wafTemplatehttpProtocolPostWith0ContentSuccess OBJECT-TYPE
			SYNTAX  CounterBasedGauge64 
			MAX-ACCESS read-only 
			STATUS current
			DESCRIPTION  "POST with 0 content check passed" 
			::={ wafTemplateSEntry 201 } 

			wafTemplatehttpProtocolPostWith0ContentViolation OBJECT-TYPE
			SYNTAX  CounterBasedGauge64 
			MAX-ACCESS read-only 
			STATUS current
			DESCRIPTION  "POST with 0 content check violation" 
			::={ wafTemplateSEntry 202 } 

			wafTemplatehttpProtocolPostWithoutContentSuccess OBJECT-TYPE
			SYNTAX  CounterBasedGauge64 
			MAX-ACCESS read-only 
			STATUS current
			DESCRIPTION  "POST without content check passed" 
			::={ wafTemplateSEntry 203 } 

			wafTemplatehttpProtocolPostWithoutContentViolation OBJECT-TYPE
			SYNTAX  CounterBasedGauge64 
			MAX-ACCESS read-only 
			STATUS current
			DESCRIPTION  "POST without content check violation" 
			::={ wafTemplateSEntry 204 } 

			wafTemplatehttpProtocolSuccess OBJECT-TYPE
			SYNTAX  CounterBasedGauge64 
			MAX-ACCESS read-only 
			STATUS current
			DESCRIPTION  "HTTP Check passed" 
			::={ wafTemplateSEntry 205 } 

			wafTemplatehttpProtocolViolation OBJECT-TYPE
			SYNTAX  CounterBasedGauge64 
			MAX-ACCESS read-only 
			STATUS current
			DESCRIPTION  "HTTP Check violation" 
			::={ wafTemplateSEntry 206 } 

			wafTemplatejsonCheckFormatSuccess OBJECT-TYPE
			SYNTAX  CounterBasedGauge64 
			MAX-ACCESS read-only 
			STATUS current
			DESCRIPTION  "JSON Check passed" 
			::={ wafTemplateSEntry 207 } 

			wafTemplatejsonCheckFormatViolation OBJECT-TYPE
			SYNTAX  CounterBasedGauge64 
			MAX-ACCESS read-only 
			STATUS current
			DESCRIPTION  "JSON Check violation" 
			::={ wafTemplateSEntry 208 } 

			wafTemplatejsonCheckMaxArrayValueCountSuccess OBJECT-TYPE
			SYNTAX  CounterBasedGauge64 
			MAX-ACCESS read-only 
			STATUS current
			DESCRIPTION  "JSON Limit Array Value Count check passed" 
			::={ wafTemplateSEntry 209 } 

			wafTemplatejsonCheckMaxArrayValueCountViolation OBJECT-TYPE
			SYNTAX  CounterBasedGauge64 
			MAX-ACCESS read-only 
			STATUS current
			DESCRIPTION  "JSON Limit Array Value Count violation" 
			::={ wafTemplateSEntry 210 } 

			wafTemplatejsonCheckMaxDepthSuccess OBJECT-TYPE
			SYNTAX  CounterBasedGauge64 
			MAX-ACCESS read-only 
			STATUS current
			DESCRIPTION  "JSON Limit Depth check passed" 
			::={ wafTemplateSEntry 211 } 

			wafTemplatejsonCheckMaxDepthViolation OBJECT-TYPE
			SYNTAX  CounterBasedGauge64 
			MAX-ACCESS read-only 
			STATUS current
			DESCRIPTION  "JSON Limit Depth violation" 
			::={ wafTemplateSEntry 212 } 

			wafTemplatejsonCheckMaxObjectMemberCountSuccess OBJECT-TYPE
			SYNTAX  CounterBasedGauge64 
			MAX-ACCESS read-only 
			STATUS current
			DESCRIPTION  "JSON Limit Object Number Count check passed" 
			::={ wafTemplateSEntry 213 } 

			wafTemplatejsonCheckMaxObjectMemberCountViolation OBJECT-TYPE
			SYNTAX  CounterBasedGauge64 
			MAX-ACCESS read-only 
			STATUS current
			DESCRIPTION  "JSON Limit Object Number Count violation" 
			::={ wafTemplateSEntry 214 } 

			wafTemplatejsonCheckMaxStringSuccess OBJECT-TYPE
			SYNTAX  CounterBasedGauge64 
			MAX-ACCESS read-only 
			STATUS current
			DESCRIPTION  "JSON Limit String check passed" 
			::={ wafTemplateSEntry 215 } 

			wafTemplatejsonCheckMaxStringViolation OBJECT-TYPE
			SYNTAX  CounterBasedGauge64 
			MAX-ACCESS read-only 
			STATUS current
			DESCRIPTION  "JSON Limit String violation" 
			::={ wafTemplateSEntry 216 } 

			wafTemplaterequestCheckBotSuccess OBJECT-TYPE
			SYNTAX  CounterBasedGauge64 
			MAX-ACCESS read-only 
			STATUS current
			DESCRIPTION  "Bot check passed" 
			::={ wafTemplateSEntry 217 } 

			wafTemplaterequestCheckBotViolation OBJECT-TYPE
			SYNTAX  CounterBasedGauge64 
			MAX-ACCESS read-only 
			STATUS current
			DESCRIPTION  "Bot check violation" 
			::={ wafTemplateSEntry 218 } 

			wafTemplaterequestCheckRedirectWlistSuccess OBJECT-TYPE
			SYNTAX  CounterBasedGauge64 
			MAX-ACCESS read-only 
			STATUS current
			DESCRIPTION  "Redirect Whitelist passed" 
			::={ wafTemplateSEntry 219 } 

			wafTemplaterequestCheckRedirectWlistViolation OBJECT-TYPE
			SYNTAX  CounterBasedGauge64 
			MAX-ACCESS read-only 
			STATUS current
			DESCRIPTION  "Redirect Whitelist violation" 
			::={ wafTemplateSEntry 220 } 

			wafTemplaterequestCheckRedirectWlistLearn OBJECT-TYPE
			SYNTAX  CounterBasedGauge64 
			MAX-ACCESS read-only 
			STATUS current
			DESCRIPTION  "Redirect Whitelist Learn" 
			::={ wafTemplateSEntry 221 } 

			wafTemplaterequestCheckRefererSuccess OBJECT-TYPE
			SYNTAX  CounterBasedGauge64 
			MAX-ACCESS read-only 
			STATUS current
			DESCRIPTION  "Referer Check passed" 
			::={ wafTemplateSEntry 222 } 

			wafTemplaterequestCheckRefererViolation OBJECT-TYPE
			SYNTAX  CounterBasedGauge64 
			MAX-ACCESS read-only 
			STATUS current
			DESCRIPTION  "Referer Check violation" 
			::={ wafTemplateSEntry 223 } 

			wafTemplaterequestCheckRefererRedirect OBJECT-TYPE
			SYNTAX  CounterBasedGauge64 
			MAX-ACCESS read-only 
			STATUS current
			DESCRIPTION  "Referer Check Redirect" 
			::={ wafTemplateSEntry 224 } 

			wafTemplaterequestCheckSessionCheckNone OBJECT-TYPE
			SYNTAX  CounterBasedGauge64 
			MAX-ACCESS read-only 
			STATUS current
			DESCRIPTION  "Session Created" 
			::={ wafTemplateSEntry 225 } 

			wafTemplaterequestCheckSessionCheckSuccess OBJECT-TYPE
			SYNTAX  CounterBasedGauge64 
			MAX-ACCESS read-only 
			STATUS current
			DESCRIPTION  "Session Check passed" 
			::={ wafTemplateSEntry 226 } 

			wafTemplaterequestCheckSessionCheckViolation OBJECT-TYPE
			SYNTAX  CounterBasedGauge64 
			MAX-ACCESS read-only 
			STATUS current
			DESCRIPTION  "Session Check violation" 
			::={ wafTemplateSEntry 227 } 

			wafTemplaterequestCheckSqliaUrlSuccess OBJECT-TYPE
			SYNTAX  CounterBasedGauge64 
			MAX-ACCESS read-only 
			STATUS current
			DESCRIPTION  "SQLIA Check URL passed" 
			::={ wafTemplateSEntry 228 } 

			wafTemplaterequestCheckSqliaUrlViolation OBJECT-TYPE
			SYNTAX  CounterBasedGauge64 
			MAX-ACCESS read-only 
			STATUS current
			DESCRIPTION  "SQLIA Check URL violation" 
			::={ wafTemplateSEntry 229 } 

			wafTemplaterequestCheckSqliaUrlSanitize OBJECT-TYPE
			SYNTAX  CounterBasedGauge64 
			MAX-ACCESS read-only 
			STATUS current
			DESCRIPTION  "SQLIA Check URL Sanitized" 
			::={ wafTemplateSEntry 230 } 

			wafTemplaterequestCheckSqliaPostBodySuccess OBJECT-TYPE
			SYNTAX  CounterBasedGauge64 
			MAX-ACCESS read-only 
			STATUS current
			DESCRIPTION  "SQLIA Check Post passed" 
			::={ wafTemplateSEntry 231 } 

			wafTemplaterequestCheckSqliaPostBodyViolation OBJECT-TYPE
			SYNTAX  CounterBasedGauge64 
			MAX-ACCESS read-only 
			STATUS current
			DESCRIPTION  "SQLIA Check Post violation" 
			::={ wafTemplateSEntry 232 } 

			wafTemplaterequestCheckSqliaPostBodySanitize OBJECT-TYPE
			SYNTAX  CounterBasedGauge64 
			MAX-ACCESS read-only 
			STATUS current
			DESCRIPTION  "SQLIA Check Post Sanitized" 
			::={ wafTemplateSEntry 233 } 

			wafTemplaterequestCheckUrlListSuccess OBJECT-TYPE
			SYNTAX  CounterBasedGauge64 
			MAX-ACCESS read-only 
			STATUS current
			DESCRIPTION  "URL Check passed" 
			::={ wafTemplateSEntry 234 } 

			wafTemplaterequestCheckUrlListViolation OBJECT-TYPE
			SYNTAX  CounterBasedGauge64 
			MAX-ACCESS read-only 
			STATUS current
			DESCRIPTION  "URL Check violation" 
			::={ wafTemplateSEntry 235 } 

			wafTemplaterequestCheckUrlListLearn OBJECT-TYPE
			SYNTAX  CounterBasedGauge64 
			MAX-ACCESS read-only 
			STATUS current
			DESCRIPTION  "URL Check Learn" 
			::={ wafTemplateSEntry 236 } 

			wafTemplaterequestCheckUrlWhitelistSuccess OBJECT-TYPE
			SYNTAX  CounterBasedGauge64 
			MAX-ACCESS read-only 
			STATUS current
			DESCRIPTION  "URI White List passed" 
			::={ wafTemplateSEntry 237 } 

			wafTemplaterequestCheckUrlWhitelistViolation OBJECT-TYPE
			SYNTAX  CounterBasedGauge64 
			MAX-ACCESS read-only 
			STATUS current
			DESCRIPTION  "URI White List violation" 
			::={ wafTemplateSEntry 238 } 

			wafTemplaterequestCheckUrlBlacklistSuccess OBJECT-TYPE
			SYNTAX  CounterBasedGauge64 
			MAX-ACCESS read-only 
			STATUS current
			DESCRIPTION  "URI Black List passed" 
			::={ wafTemplateSEntry 239 } 

			wafTemplaterequestCheckUrlBlacklistViolation OBJECT-TYPE
			SYNTAX  CounterBasedGauge64 
			MAX-ACCESS read-only 
			STATUS current
			DESCRIPTION  "URI Black List violation" 
			::={ wafTemplateSEntry 240 } 

			wafTemplaterequestCheckXssCookieSuccess OBJECT-TYPE
			SYNTAX  CounterBasedGauge64 
			MAX-ACCESS read-only 
			STATUS current
			DESCRIPTION  "XSS Check Cookie passed" 
			::={ wafTemplateSEntry 241 } 

			wafTemplaterequestCheckXssCookieViolation OBJECT-TYPE
			SYNTAX  CounterBasedGauge64 
			MAX-ACCESS read-only 
			STATUS current
			DESCRIPTION  "XSS Check Cookie violation" 
			::={ wafTemplateSEntry 242 } 

			wafTemplaterequestCheckXssCookieSanitize OBJECT-TYPE
			SYNTAX  CounterBasedGauge64 
			MAX-ACCESS read-only 
			STATUS current
			DESCRIPTION  "XSS Check Cookie Sanitized" 
			::={ wafTemplateSEntry 243 } 

			wafTemplaterequestCheckXssUrlSuccess OBJECT-TYPE
			SYNTAX  CounterBasedGauge64 
			MAX-ACCESS read-only 
			STATUS current
			DESCRIPTION  "XSS Check URL passed" 
			::={ wafTemplateSEntry 244 } 

			wafTemplaterequestCheckXssUrlViolation OBJECT-TYPE
			SYNTAX  CounterBasedGauge64 
			MAX-ACCESS read-only 
			STATUS current
			DESCRIPTION  "XSS Check URL violation" 
			::={ wafTemplateSEntry 245 } 

			wafTemplaterequestCheckXssUrlSanitize OBJECT-TYPE
			SYNTAX  CounterBasedGauge64 
			MAX-ACCESS read-only 
			STATUS current
			DESCRIPTION  "XSS Check URL Sanitized" 
			::={ wafTemplateSEntry 246 } 

			wafTemplaterequestCheckXssPostBodySuccess OBJECT-TYPE
			SYNTAX  CounterBasedGauge64 
			MAX-ACCESS read-only 
			STATUS current
			DESCRIPTION  "XSS Check Post passed" 
			::={ wafTemplateSEntry 247 } 

			wafTemplaterequestCheckXssPostBodyViolation OBJECT-TYPE
			SYNTAX  CounterBasedGauge64 
			MAX-ACCESS read-only 
			STATUS current
			DESCRIPTION  "XSS Check Post violation" 
			::={ wafTemplateSEntry 248 } 

			wafTemplaterequestCheckXssPostBodySanitize OBJECT-TYPE
			SYNTAX  CounterBasedGauge64 
			MAX-ACCESS read-only 
			STATUS current
			DESCRIPTION  "XSS Check Post Sanitized" 
			::={ wafTemplateSEntry 249 } 

			wafTemplateresponseCloakingHideStatusCodeSuccess OBJECT-TYPE
			SYNTAX  CounterBasedGauge64 
			MAX-ACCESS read-only 
			STATUS current
			DESCRIPTION  "Response Hide Code check passed" 
			::={ wafTemplateSEntry 250 } 

			wafTemplateresponseCloakingHideStatusCodeViolation OBJECT-TYPE
			SYNTAX  CounterBasedGauge64 
			MAX-ACCESS read-only 
			STATUS current
			DESCRIPTION  "Response Hide Code violation" 
			::={ wafTemplateSEntry 251 } 

			wafTemplateresponseCloakingFilterHeadersSuccess OBJECT-TYPE
			SYNTAX  CounterBasedGauge64 
			MAX-ACCESS read-only 
			STATUS current
			DESCRIPTION  "Response Headers Filter check passed" 
			::={ wafTemplateSEntry 252 } 

			wafTemplateresponseCloakingFilterHeadersViolation OBJECT-TYPE
			SYNTAX  CounterBasedGauge64 
			MAX-ACCESS read-only 
			STATUS current
			DESCRIPTION  "Response Headers Filter violation" 
			::={ wafTemplateSEntry 253 } 

			wafTemplatesoapCheckSuccess OBJECT-TYPE
			SYNTAX  CounterBasedGauge64 
			MAX-ACCESS read-only 
			STATUS current
			DESCRIPTION  "Soap Check passed" 
			::={ wafTemplateSEntry 254 } 

			wafTemplatesoapCheckViolation OBJECT-TYPE
			SYNTAX  CounterBasedGauge64 
			MAX-ACCESS read-only 
			STATUS current
			DESCRIPTION  "Soap Check violation" 
			::={ wafTemplateSEntry 255 } 

			wafTemplatexmlCheckFormatSuccess OBJECT-TYPE
			SYNTAX  CounterBasedGauge64 
			MAX-ACCESS read-only 
			STATUS current
			DESCRIPTION  "XML Check passed" 
			::={ wafTemplateSEntry 256 } 

			wafTemplatexmlCheckFormatViolation OBJECT-TYPE
			SYNTAX  CounterBasedGauge64 
			MAX-ACCESS read-only 
			STATUS current
			DESCRIPTION  "XML Check violation" 
			::={ wafTemplateSEntry 257 } 

			wafTemplatexmlCheckMaxAttrSuccess OBJECT-TYPE
			SYNTAX  CounterBasedGauge64 
			MAX-ACCESS read-only 
			STATUS current
			DESCRIPTION  "XML Limit Attribute check passed" 
			::={ wafTemplateSEntry 258 } 

			wafTemplatexmlCheckMaxAttrViolation OBJECT-TYPE
			SYNTAX  CounterBasedGauge64 
			MAX-ACCESS read-only 
			STATUS current
			DESCRIPTION  "XML Limit Attribute violation" 
			::={ wafTemplateSEntry 259 } 

			wafTemplatexmlCheckMaxAttrNameLenSuccess OBJECT-TYPE
			SYNTAX  CounterBasedGauge64 
			MAX-ACCESS read-only 
			STATUS current
			DESCRIPTION  "XML Limit Name Length check passed" 
			::={ wafTemplateSEntry 260 } 

			wafTemplatexmlCheckMaxAttrNameLenViolation OBJECT-TYPE
			SYNTAX  CounterBasedGauge64 
			MAX-ACCESS read-only 
			STATUS current
			DESCRIPTION  "XML Limit Name Length violation" 
			::={ wafTemplateSEntry 261 } 

			wafTemplatexmlCheckMaxAttrValueLenSuccess OBJECT-TYPE
			SYNTAX  CounterBasedGauge64 
			MAX-ACCESS read-only 
			STATUS current
			DESCRIPTION  "XML Limit Value Length check passed" 
			::={ wafTemplateSEntry 262 } 

			wafTemplatexmlCheckMaxAttrValueLenViolation OBJECT-TYPE
			SYNTAX  CounterBasedGauge64 
			MAX-ACCESS read-only 
			STATUS current
			DESCRIPTION  "XML Limit Value Length violation" 
			::={ wafTemplateSEntry 263 } 

			wafTemplatexmlCheckMaxCdataLenSuccess OBJECT-TYPE
			SYNTAX  CounterBasedGauge64 
			MAX-ACCESS read-only 
			STATUS current
			DESCRIPTION  "XML Limit CData Length check passed" 
			::={ wafTemplateSEntry 264 } 

			wafTemplatexmlCheckMaxCdataLenViolation OBJECT-TYPE
			SYNTAX  CounterBasedGauge64 
			MAX-ACCESS read-only 
			STATUS current
			DESCRIPTION  "XML Limit CData Length violation" 
			::={ wafTemplateSEntry 265 } 

			wafTemplatexmlCheckMaxElemSuccess OBJECT-TYPE
			SYNTAX  CounterBasedGauge64 
			MAX-ACCESS read-only 
			STATUS current
			DESCRIPTION  "XML Limit Element check passed" 
			::={ wafTemplateSEntry 266 } 

			wafTemplatexmlCheckMaxElemViolation OBJECT-TYPE
			SYNTAX  CounterBasedGauge64 
			MAX-ACCESS read-only 
			STATUS current
			DESCRIPTION  "XML Limit Element violation" 
			::={ wafTemplateSEntry 267 } 

			wafTemplatexmlCheckMaxElemChildSuccess OBJECT-TYPE
			SYNTAX  CounterBasedGauge64 
			MAX-ACCESS read-only 
			STATUS current
			DESCRIPTION  "XML Limit Element Child check passed" 
			::={ wafTemplateSEntry 268 } 

			wafTemplatexmlCheckMaxElemChildViolation OBJECT-TYPE
			SYNTAX  CounterBasedGauge64 
			MAX-ACCESS read-only 
			STATUS current
			DESCRIPTION  "XML Limit Element Child violation" 
			::={ wafTemplateSEntry 269 } 

			wafTemplatexmlCheckMaxElemDepthSuccess OBJECT-TYPE
			SYNTAX  CounterBasedGauge64 
			MAX-ACCESS read-only 
			STATUS current
			DESCRIPTION  "XML Limit Element Depth check passed" 
			::={ wafTemplateSEntry 270 } 

			wafTemplatexmlCheckMaxElemDepthViolation OBJECT-TYPE
			SYNTAX  CounterBasedGauge64 
			MAX-ACCESS read-only 
			STATUS current
			DESCRIPTION  "XML Limit Element Depth violation" 
			::={ wafTemplateSEntry 271 } 

			wafTemplatexmlCheckMaxElemNameLenSuccess OBJECT-TYPE
			SYNTAX  CounterBasedGauge64 
			MAX-ACCESS read-only 
			STATUS current
			DESCRIPTION  "XML Limit Element Name Length check passed" 
			::={ wafTemplateSEntry 272 } 

			wafTemplatexmlCheckMaxElemNameLenViolation OBJECT-TYPE
			SYNTAX  CounterBasedGauge64 
			MAX-ACCESS read-only 
			STATUS current
			DESCRIPTION  "XML Limit Element Name Length violation" 
			::={ wafTemplateSEntry 273 } 

			wafTemplatexmlCheckMaxEntityExpSuccess OBJECT-TYPE
			SYNTAX  CounterBasedGauge64 
			MAX-ACCESS read-only 
			STATUS current
			DESCRIPTION  "XML Limit Entity Decl check passed" 
			::={ wafTemplateSEntry 274 } 

			wafTemplatexmlCheckMaxEntityExpViolation OBJECT-TYPE
			SYNTAX  CounterBasedGauge64 
			MAX-ACCESS read-only 
			STATUS current
			DESCRIPTION  "XML Limit Entity Decl violation" 
			::={ wafTemplateSEntry 275 } 

			wafTemplatexmlCheckMaxEntityExpDepthSuccess OBJECT-TYPE
			SYNTAX  CounterBasedGauge64 
			MAX-ACCESS read-only 
			STATUS current
			DESCRIPTION  "XML Limit Entities Depth check passed" 
			::={ wafTemplateSEntry 276 } 

			wafTemplatexmlCheckMaxEntityExpDepthViolation OBJECT-TYPE
			SYNTAX  CounterBasedGauge64 
			MAX-ACCESS read-only 
			STATUS current
			DESCRIPTION  "XML Limit Entities Depth violation" 
			::={ wafTemplateSEntry 277 } 

			wafTemplatexmlCheckMaxNamespaceSuccess OBJECT-TYPE
			SYNTAX  CounterBasedGauge64 
			MAX-ACCESS read-only 
			STATUS current
			DESCRIPTION  "XML Limit Namespace check passed" 
			::={ wafTemplateSEntry 278 } 

			wafTemplatexmlCheckMaxNamespaceViolation OBJECT-TYPE
			SYNTAX  CounterBasedGauge64 
			MAX-ACCESS read-only 
			STATUS current
			DESCRIPTION  "XML Limit Namespace violation" 
			::={ wafTemplateSEntry 279 } 

			wafTemplatexmlCheckNamespaceUriLenSuccess OBJECT-TYPE
			SYNTAX  CounterBasedGauge64 
			MAX-ACCESS read-only 
			STATUS current
			DESCRIPTION  "XML Limit Namespace URI Length check passed" 
			::={ wafTemplateSEntry 280 } 

			wafTemplatexmlCheckNamespaceUriLenViolation OBJECT-TYPE
			SYNTAX  CounterBasedGauge64 
			MAX-ACCESS read-only 
			STATUS current
			DESCRIPTION  "XML Limit Namespace URI Length violation" 
			::={ wafTemplateSEntry 281 } 

			wafTemplatexmlCheckSqliaSuccess OBJECT-TYPE
			SYNTAX  CounterBasedGauge64 
			MAX-ACCESS read-only 
			STATUS current
			DESCRIPTION  "XML Sqlia Check passed" 
			::={ wafTemplateSEntry 282 } 

			wafTemplatexmlCheckSqliaViolation OBJECT-TYPE
			SYNTAX  CounterBasedGauge64 
			MAX-ACCESS read-only 
			STATUS current
			DESCRIPTION  "XML Sqlia Check violation" 
			::={ wafTemplateSEntry 283 } 

			wafTemplatexmlCheckXssSuccess OBJECT-TYPE
			SYNTAX  CounterBasedGauge64 
			MAX-ACCESS read-only 
			STATUS current
			DESCRIPTION  "XML XSS Check passed" 
			::={ wafTemplateSEntry 284 } 

			wafTemplatexmlCheckXssViolation OBJECT-TYPE
			SYNTAX  CounterBasedGauge64 
			MAX-ACCESS read-only 
			STATUS current
			DESCRIPTION  "XML XSS Check violation" 
			::={ wafTemplateSEntry 285 } 

			wafTemplatexmlContentCheckSchemaSuccess OBJECT-TYPE
			SYNTAX  CounterBasedGauge64 
			MAX-ACCESS read-only 
			STATUS current
			DESCRIPTION  "XML Schema passed" 
			::={ wafTemplateSEntry 286 } 

			wafTemplatexmlContentCheckSchemaViolation OBJECT-TYPE
			SYNTAX  CounterBasedGauge64 
			MAX-ACCESS read-only 
			STATUS current
			DESCRIPTION  "XML Schema violation" 
			::={ wafTemplateSEntry 287 } 

			wafTemplatexmlContentCheckWsdlSuccess OBJECT-TYPE
			SYNTAX  CounterBasedGauge64 
			MAX-ACCESS read-only 
			STATUS current
			DESCRIPTION  "WSDL passed" 
			::={ wafTemplateSEntry 288 } 

			wafTemplatexmlContentCheckWsdlViolation OBJECT-TYPE
			SYNTAX  CounterBasedGauge64 
			MAX-ACCESS read-only 
			STATUS current
			DESCRIPTION  "WSDL violation" 
			::={ wafTemplateSEntry 289 } 

			wafTemplatelearningListFull OBJECT-TYPE
			SYNTAX  CounterBasedGauge64 
			MAX-ACCESS read-only 
			STATUS current
			DESCRIPTION  "Learning list is full" 
			::={ wafTemplateSEntry 290 } 

			wafTemplateactionAllow OBJECT-TYPE
			SYNTAX  CounterBasedGauge64 
			MAX-ACCESS read-only 
			STATUS current
			DESCRIPTION  "Request Action allowed" 
			::={ wafTemplateSEntry 291 } 

			wafTemplateactionDeny200 OBJECT-TYPE
			SYNTAX  CounterBasedGauge64 
			MAX-ACCESS read-only 
			STATUS current
			DESCRIPTION  "Request Deny with 200" 
			::={ wafTemplateSEntry 292 } 

			wafTemplateactionDeny403 OBJECT-TYPE
			SYNTAX  CounterBasedGauge64 
			MAX-ACCESS read-only 
			STATUS current
			DESCRIPTION  "Request Deny with 403" 
			::={ wafTemplateSEntry 293 } 

			wafTemplateactionDenyRedirect OBJECT-TYPE
			SYNTAX  CounterBasedGauge64 
			MAX-ACCESS read-only 
			STATUS current
			DESCRIPTION  "Request Deny with Redirect" 
			::={ wafTemplateSEntry 294 } 

			wafTemplateactionDenyReset OBJECT-TYPE
			SYNTAX  CounterBasedGauge64 
			MAX-ACCESS read-only 
			STATUS current
			DESCRIPTION  "Request Deny with Resets" 
			::={ wafTemplateSEntry 295 } 

			wafTemplateactionDrop OBJECT-TYPE
			SYNTAX  CounterBasedGauge64 
			MAX-ACCESS read-only 
			STATUS current
			DESCRIPTION  "Number of Dropped Requests" 
			::={ wafTemplateSEntry 296 } 

			wafTemplateactionDenyCustomResponse OBJECT-TYPE
			SYNTAX  CounterBasedGauge64 
			MAX-ACCESS read-only 
			STATUS current
			DESCRIPTION  "Request Deny with custom response" 
			::={ wafTemplateSEntry 297 } 

			wafTemplateactionLearn OBJECT-TYPE
			SYNTAX  CounterBasedGauge64 
			MAX-ACCESS read-only 
			STATUS current
			DESCRIPTION  "Request Learning Updates" 
			::={ wafTemplateSEntry 298 } 

			wafTemplateactionLog OBJECT-TYPE
			SYNTAX  CounterBasedGauge64 
			MAX-ACCESS read-only 
			STATUS current
			DESCRIPTION  "Log request violation" 
			::={ wafTemplateSEntry 299 } 

			wafTemplatepolicyLimitExceeded OBJECT-TYPE
			SYNTAX  CounterBasedGauge64 
			MAX-ACCESS read-only 
			STATUS current
			DESCRIPTION  "Policy limit exceeded" 
			::={ wafTemplateSEntry 300 } 

			wafTemplatesessionsAlloc OBJECT-TYPE
			SYNTAX  CounterBasedGauge64 
			MAX-ACCESS read-only 
			STATUS current
			DESCRIPTION  "Sessions allocated" 
			::={ wafTemplateSEntry 301 } 

			wafTemplatesessionsFreed OBJECT-TYPE
			SYNTAX  CounterBasedGauge64 
			MAX-ACCESS read-only 
			STATUS current
			DESCRIPTION  "Sessions freed" 
			::={ wafTemplateSEntry 302 } 

			wafTemplateoutOfSessions OBJECT-TYPE
			SYNTAX  CounterBasedGauge64 
			MAX-ACCESS read-only 
			STATUS current
			DESCRIPTION  "Out of sessions" 
			::={ wafTemplateSEntry 303 } 

			wafTemplatetooManySessions OBJECT-TYPE
			SYNTAX  CounterBasedGauge64 
			MAX-ACCESS read-only 
			STATUS current
			DESCRIPTION  "Too many sessions consumed" 
			::={ wafTemplateSEntry 304 } 

			wafTemplateregexViolation OBJECT-TYPE
			SYNTAX  CounterBasedGauge64 
			MAX-ACCESS read-only 
			STATUS current
			DESCRIPTION  "Regular expression failure" 
			::={ wafTemplateSEntry 305 } 

			wafTemplateRequestCheckCommandInjectionCookiesSuccess OBJECT-TYPE
			SYNTAX  CounterBasedGauge64 
			MAX-ACCESS read-only 
			STATUS current
			DESCRIPTION  "Command Injection Check cookies passed" 
			::={ wafTemplateSEntry 306 } 

			wafTemplateRequestCheckCommandInjectionCookiesViolation OBJECT-TYPE
			SYNTAX  CounterBasedGauge64 
			MAX-ACCESS read-only 
			STATUS current
			DESCRIPTION  "Command Injection Check cookies violation" 
			::={ wafTemplateSEntry 307 } 

			wafTemplateRequestCheckCommandInjectionHeadersSuccess OBJECT-TYPE
			SYNTAX  CounterBasedGauge64 
			MAX-ACCESS read-only 
			STATUS current
			DESCRIPTION  "Command Injection Check headers passed" 
			::={ wafTemplateSEntry 308 } 

			wafTemplateRequestCheckCommandInjectionHeadersViolation OBJECT-TYPE
			SYNTAX  CounterBasedGauge64 
			MAX-ACCESS read-only 
			STATUS current
			DESCRIPTION  "Command Injection Check headers violation" 
			::={ wafTemplateSEntry 309 } 

			wafTemplateRequestCheckCommandInjectionUrlQuerySuccess OBJECT-TYPE
			SYNTAX  CounterBasedGauge64 
			MAX-ACCESS read-only 
			STATUS current
			DESCRIPTION  "Command Injection Check url query arguments passed" 
			::={ wafTemplateSEntry 310 } 

			wafTemplateRequestCheckCommandInjectionUrlQueryViolation OBJECT-TYPE
			SYNTAX  CounterBasedGauge64 
			MAX-ACCESS read-only 
			STATUS current
			DESCRIPTION  "Command Injection Check url query arguments violation" 
			::={ wafTemplateSEntry 311 } 

			wafTemplateRequestCheckCommandInjectionFormBodySuccess OBJECT-TYPE
			SYNTAX  CounterBasedGauge64 
			MAX-ACCESS read-only 
			STATUS current
			DESCRIPTION  "Command Injection Check form body arguments passed" 
			::={ wafTemplateSEntry 312 } 

			wafTemplateRequestCheckCommandInjectionFormBodyViolation OBJECT-TYPE
			SYNTAX  CounterBasedGauge64 
			MAX-ACCESS read-only 
			STATUS current
			DESCRIPTION  "Command Injection Check form body arguments violation" 
			::={ wafTemplateSEntry 313 } 

			wafTemplatecookieSecurityDecryptInGracePeriodViolation OBJECT-TYPE
			SYNTAX  CounterBasedGauge64 
			MAX-ACCESS read-only 
			STATUS current
			DESCRIPTION  "Cookie Decrypt violation but in grace period" 
			::={ wafTemplateSEntry 314 } 

			wafTemplateformResponseNonPostSuccess OBJECT-TYPE
			SYNTAX  CounterBasedGauge64 
			MAX-ACCESS read-only 
			STATUS current
			DESCRIPTION  "Response form method was POST" 
			::={ wafTemplateSEntry 315 } 

			wafTemplateformResponseNonPostViolation OBJECT-TYPE
			SYNTAX  CounterBasedGauge64 
			MAX-ACCESS read-only 
			STATUS current
			DESCRIPTION  "Response form method was not POST" 
			::={ wafTemplateSEntry 316 } 

			wafTemplateformResponseNonPostSanitize OBJECT-TYPE
			SYNTAX  CounterBasedGauge64 
			MAX-ACCESS read-only 
			STATUS current
			DESCRIPTION  "Changed response form method to POST" 
			::={ wafTemplateSEntry 317 } 

			wafTemplatexmlCheckMaxEntityDeclSuccess OBJECT-TYPE
			SYNTAX  CounterBasedGauge64 
			MAX-ACCESS read-only 
			STATUS current
			DESCRIPTION  "XML Limit Entity Decl check passed" 
			::={ wafTemplateSEntry 318 } 

			wafTemplatexmlCheckMaxEntityDeclViolation OBJECT-TYPE
			SYNTAX  CounterBasedGauge64 
			MAX-ACCESS read-only 
			STATUS current
			DESCRIPTION  "XML Limit Entity Decl violation" 
			::={ wafTemplateSEntry 319 } 

			wafTemplatexmlCheckMaxEntityDepthSuccess OBJECT-TYPE
			SYNTAX  CounterBasedGauge64 
			MAX-ACCESS read-only 
			STATUS current
			DESCRIPTION  "XML Limit Entity Depth check passed" 
			::={ wafTemplateSEntry 320 } 

			wafTemplatexmlCheckMaxEntityDepthViolation OBJECT-TYPE
			SYNTAX  CounterBasedGauge64 
			MAX-ACCESS read-only 
			STATUS current
			DESCRIPTION  "XML Limit Entity Depth violation" 
			::={ wafTemplateSEntry 321 } 

			wafTemplateResponseActionAllow OBJECT-TYPE
			SYNTAX  CounterBasedGauge64 
			MAX-ACCESS read-only 
			STATUS current
			DESCRIPTION  "Response Action allowed" 
			::={ wafTemplateSEntry 322 } 

			wafTemplateResponseActionDeny200 OBJECT-TYPE
			SYNTAX  CounterBasedGauge64 
			MAX-ACCESS read-only 
			STATUS current
			DESCRIPTION  "Response Deny with 200" 
			::={ wafTemplateSEntry 323 } 

			wafTemplateResponseActionDeny403 OBJECT-TYPE
			SYNTAX  CounterBasedGauge64 
			MAX-ACCESS read-only 
			STATUS current
			DESCRIPTION  "Response Deny with 403" 
			::={ wafTemplateSEntry 324 } 

			wafTemplateResponseActionDenyRedirect OBJECT-TYPE
			SYNTAX  CounterBasedGauge64 
			MAX-ACCESS read-only 
			STATUS current
			DESCRIPTION  "Response Deny with Redirect" 
			::={ wafTemplateSEntry 325 } 

			wafTemplateResponseActionDenyReset OBJECT-TYPE
			SYNTAX  CounterBasedGauge64 
			MAX-ACCESS read-only 
			STATUS current
			DESCRIPTION  "Response Deny with Resets" 
			::={ wafTemplateSEntry 326 } 

			wafTemplateResponseActionDrop OBJECT-TYPE
			SYNTAX  CounterBasedGauge64 
			MAX-ACCESS read-only 
			STATUS current
			DESCRIPTION  "Number of Dropped Responses" 
			::={ wafTemplateSEntry 327 } 

			wafTemplateResponseActionDenyCustomResponse OBJECT-TYPE
			SYNTAX  CounterBasedGauge64 
			MAX-ACCESS read-only 
			STATUS current
			DESCRIPTION  "Response Deny with custom response" 
			::={ wafTemplateSEntry 328 } 

			wafTemplateResponseActionLearn OBJECT-TYPE
			SYNTAX  CounterBasedGauge64 
			MAX-ACCESS read-only 
			STATUS current
			DESCRIPTION  "Response Learning Updates" 
			::={ wafTemplateSEntry 329 } 

			wafTemplateResponseActionLog OBJECT-TYPE
			SYNTAX  CounterBasedGauge64 
			MAX-ACCESS read-only 
			STATUS current
			DESCRIPTION  "Log response violation" 
			::={ wafTemplateSEntry 330 } 

			wafTemplatehttpProtocolPostWithoutContentTypeSuccess OBJECT-TYPE
			SYNTAX  CounterBasedGauge64 
			MAX-ACCESS read-only 
			STATUS current
			DESCRIPTION  "POST without content type check passed" 
			::={ wafTemplateSEntry 331 } 

			wafTemplatehttpProtocolPostWithoutContentTypeViolation OBJECT-TYPE
			SYNTAX  CounterBasedGauge64 
			MAX-ACCESS read-only 
			STATUS current
			DESCRIPTION  "POST without content type check violation" 
			::={ wafTemplateSEntry 332 } 

			wafTemplatehttpProtocolBodyWithoutContentTypeSuccess OBJECT-TYPE
			SYNTAX  CounterBasedGauge64 
			MAX-ACCESS read-only 
			STATUS current
			DESCRIPTION  "Body without content type check passed" 
			::={ wafTemplateSEntry 333 } 

			wafTemplatehttpProtocolBodyWithoutContentTypeViolation OBJECT-TYPE
			SYNTAX  CounterBasedGauge64 
			MAX-ACCESS read-only 
			STATUS current
			DESCRIPTION  "Body without content type check violation" 
			::={ wafTemplateSEntry 334 } 

			wafTemplatehttpProtocolNonSslCookiePrefixSuccess OBJECT-TYPE
			SYNTAX  CounterBasedGauge64 
			MAX-ACCESS read-only 
			STATUS current
			DESCRIPTION  "Cookie Name Prefix check passed" 
			::={ wafTemplateSEntry 335 } 

			wafTemplatehttpProtocolNonSslCookiePrefixViolation OBJECT-TYPE
			SYNTAX  CounterBasedGauge64 
			MAX-ACCESS read-only 
			STATUS current
			DESCRIPTION  "Cookie Name Prefix check violation" 
			::={ wafTemplateSEntry 336 } 

			wafTemplatecookieSecurityAddSamesiteSuccess OBJECT-TYPE
			SYNTAX  CounterBasedGauge64 
			MAX-ACCESS read-only 
			STATUS current
			DESCRIPTION  "Cookie Security - samesite attribute added successfully" 
			::={ wafTemplateSEntry 337 } 

			wafTemplatecookieSecurityAddSamesiteViolation OBJECT-TYPE
			SYNTAX  CounterBasedGauge64 
			MAX-ACCESS read-only 
			STATUS current
			DESCRIPTION  "Cookie Security - samesite attribute violation" 
			::={ wafTemplateSEntry 338 } 

			ruleSetRequest OBJECT-TYPE
			SYNTAX  CounterBasedGauge64 
			MAX-ACCESS read-only 
			STATUS current
			DESCRIPTION  "Requests hanlded by WAF rule set" 
			::={ wafTemplateSEntry 339 } 

			ruleSetResponse OBJECT-TYPE
			SYNTAX  CounterBasedGauge64 
			MAX-ACCESS read-only 
			STATUS current
			DESCRIPTION  "Responses hanlded by WAF rule set" 
			::={ wafTemplateSEntry 340 } 

			phase1Pass OBJECT-TYPE
			SYNTAX  CounterBasedGauge64 
			MAX-ACCESS read-only 
			STATUS current
			DESCRIPTION  "WAF rule set pass hits in phase 1" 
			::={ wafTemplateSEntry 341 } 

			phase1Allow OBJECT-TYPE
			SYNTAX  CounterBasedGauge64 
			MAX-ACCESS read-only 
			STATUS current
			DESCRIPTION  "WAF rule set allow hits in phase 1" 
			::={ wafTemplateSEntry 342 } 

			phase1Deny OBJECT-TYPE
			SYNTAX  CounterBasedGauge64 
			MAX-ACCESS read-only 
			STATUS current
			DESCRIPTION  "WAF rule set deny hits in phase 1" 
			::={ wafTemplateSEntry 343 } 

			phase1Drop OBJECT-TYPE
			SYNTAX  CounterBasedGauge64 
			MAX-ACCESS read-only 
			STATUS current
			DESCRIPTION  "WAF rule set drop hits in phase 1" 
			::={ wafTemplateSEntry 344 } 

			phase1Redirect OBJECT-TYPE
			SYNTAX  CounterBasedGauge64 
			MAX-ACCESS read-only 
			STATUS current
			DESCRIPTION  "WAF rule set redirect hits in phase 1" 
			::={ wafTemplateSEntry 345 } 

			phase1Other OBJECT-TYPE
			SYNTAX  CounterBasedGauge64 
			MAX-ACCESS read-only 
			STATUS current
			DESCRIPTION  "WAF rule set other hits in phase 1" 
			::={ wafTemplateSEntry 346 } 

			phase2Pass OBJECT-TYPE
			SYNTAX  CounterBasedGauge64 
			MAX-ACCESS read-only 
			STATUS current
			DESCRIPTION  "WAF rule set pass hits in phase 2" 
			::={ wafTemplateSEntry 347 } 

			phase2Allow OBJECT-TYPE
			SYNTAX  CounterBasedGauge64 
			MAX-ACCESS read-only 
			STATUS current
			DESCRIPTION  "WAF rule set allow hits in phase 2" 
			::={ wafTemplateSEntry 348 } 

			phase2Deny OBJECT-TYPE
			SYNTAX  CounterBasedGauge64 
			MAX-ACCESS read-only 
			STATUS current
			DESCRIPTION  "WAF rule set deny hits in phase 2" 
			::={ wafTemplateSEntry 349 } 

			phase2Drop OBJECT-TYPE
			SYNTAX  CounterBasedGauge64 
			MAX-ACCESS read-only 
			STATUS current
			DESCRIPTION  "WAF rule set drop hits in phase 2" 
			::={ wafTemplateSEntry 350 } 

			phase2Redirect OBJECT-TYPE
			SYNTAX  CounterBasedGauge64 
			MAX-ACCESS read-only 
			STATUS current
			DESCRIPTION  "WAF rule set redirect hits in phase 2" 
			::={ wafTemplateSEntry 351 } 

			phase2Other OBJECT-TYPE
			SYNTAX  CounterBasedGauge64 
			MAX-ACCESS read-only 
			STATUS current
			DESCRIPTION  "WAF rule set other hits in phase 2" 
			::={ wafTemplateSEntry 352 } 

			phase3Pass OBJECT-TYPE
			SYNTAX  CounterBasedGauge64 
			MAX-ACCESS read-only 
			STATUS current
			DESCRIPTION  "WAF rule set pass hits in phase 3" 
			::={ wafTemplateSEntry 353 } 

			phase3Allow OBJECT-TYPE
			SYNTAX  CounterBasedGauge64 
			MAX-ACCESS read-only 
			STATUS current
			DESCRIPTION  "WAF rule set allow hits in phase 3" 
			::={ wafTemplateSEntry 354 } 

			phase3Deny OBJECT-TYPE
			SYNTAX  CounterBasedGauge64 
			MAX-ACCESS read-only 
			STATUS current
			DESCRIPTION  "WAF rule set deny hits in phase 3" 
			::={ wafTemplateSEntry 355 } 

			phase3Drop OBJECT-TYPE
			SYNTAX  CounterBasedGauge64 
			MAX-ACCESS read-only 
			STATUS current
			DESCRIPTION  "WAF rule set drop hits in phase 3" 
			::={ wafTemplateSEntry 356 } 

			phase3Redirect OBJECT-TYPE
			SYNTAX  CounterBasedGauge64 
			MAX-ACCESS read-only 
			STATUS current
			DESCRIPTION  "WAF rule set redirect hits in phase 3" 
			::={ wafTemplateSEntry 357 } 

			phase3Other OBJECT-TYPE
			SYNTAX  CounterBasedGauge64 
			MAX-ACCESS read-only 
			STATUS current
			DESCRIPTION  "WAF rule set other hits in phase 3" 
			::={ wafTemplateSEntry 358 } 

			phase4Pass OBJECT-TYPE
			SYNTAX  CounterBasedGauge64 
			MAX-ACCESS read-only 
			STATUS current
			DESCRIPTION  "WAF rule set pass hits in phase 4" 
			::={ wafTemplateSEntry 359 } 

			phase4Allow OBJECT-TYPE
			SYNTAX  CounterBasedGauge64 
			MAX-ACCESS read-only 
			STATUS current
			DESCRIPTION  "WAF rule set allow hits in phase 4" 
			::={ wafTemplateSEntry 360 } 

			phase4Deny OBJECT-TYPE
			SYNTAX  CounterBasedGauge64 
			MAX-ACCESS read-only 
			STATUS current
			DESCRIPTION  "WAF rule set deny hits in phase 4" 
			::={ wafTemplateSEntry 361 } 

			phase4Drop OBJECT-TYPE
			SYNTAX  CounterBasedGauge64 
			MAX-ACCESS read-only 
			STATUS current
			DESCRIPTION  "WAF rule set drop hits in phase 4" 
			::={ wafTemplateSEntry 362 } 

			phase4Redirect OBJECT-TYPE
			SYNTAX  CounterBasedGauge64 
			MAX-ACCESS read-only 
			STATUS current
			DESCRIPTION  "WAF rule set redirect hits in phase 4" 
			::={ wafTemplateSEntry 363 } 

			phase4Other OBJECT-TYPE
			SYNTAX  CounterBasedGauge64 
			MAX-ACCESS read-only 
			STATUS current
			DESCRIPTION  "WAF rule set other hits in phase 4" 
			::={ wafTemplateSEntry 364 } 

END

ACOS-WEB-CATEGORY-STATS-MIB DEFINITIONS ::= BEGIN
	IMPORTS
		DisplayString, PhysAddress
		FROM SNMPv2-TC
	InetAddressType
		FROM INET-ADDRESS-MIB
	acosRootStats
		FROM A10-AX-MIB
	MODULE-IDENTITY, OBJECT-TYPE, Counter32, Integer32, Counter64, OBJECT-IDENTITY, NOTIFICATION-TYPE
		FROM SNMPv2-SMI;
		acosWebCategory MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "WebCategory OID for ACOS"
				::=  {  acosRootStats 106  }

acosWebCategory                     OBJECT IDENTIFIER ::= { acosRootStats 106 }
acosWebCategoryCategoryList         OBJECT IDENTIFIER ::= { acosWebCategory 7 }
acosWebCategoryCategoryListS        OBJECT IDENTIFIER ::= { acosWebCategoryCategoryList 1 }

webCategoryCategoryListSTable OBJECT-TYPE
		SYNTAX SEQUENCE OF WebCategoryCategoryListSEntry
		MAX-ACCESS not-accessible
		STATUS current
		::={ acosWebCategoryCategoryListS 1 } 


	webCategoryCategoryListSEntry OBJECT-TYPE
		SYNTAX WebCategoryCategoryListSEntry
		MAX-ACCESS not-accessible
		STATUS current
		INDEX {
			name
		}
		::={ webCategoryCategoryListSTable 1 } 


	WebCategoryCategoryListSEntry ::=
		SEQUENCE {
			name DisplayString, 
			uncategorized CounterBasedGauge64,
			realEstate CounterBasedGauge64,
			computerAndInternetSecurity CounterBasedGauge64,
			financialServices CounterBasedGauge64,
			businessAndEconomy CounterBasedGauge64,
			computerAndInternetInfo CounterBasedGauge64,
			auctions CounterBasedGauge64,
			shopping CounterBasedGauge64,
			cultAndOccult CounterBasedGauge64,
			travel CounterBasedGauge64,
			drugs CounterBasedGauge64,
			adultAndPornography CounterBasedGauge64,
			homeAndGarden CounterBasedGauge64,
			military CounterBasedGauge64,
			socialNetwork CounterBasedGauge64,
			deadSites CounterBasedGauge64,
			stockAdviceAndTools CounterBasedGauge64,
			trainingAndTools CounterBasedGauge64,
			dating CounterBasedGauge64,
			sexEducation CounterBasedGauge64,
			religion CounterBasedGauge64,
			entertainmentAndArts CounterBasedGauge64,
			personalSitesAndBlogs CounterBasedGauge64,
			legal CounterBasedGauge64,
			localInformation CounterBasedGauge64,
			streamingMedia CounterBasedGauge64,
			jobSearch CounterBasedGauge64,
			gambling CounterBasedGauge64,
			translation CounterBasedGauge64,
			referenceAndResearch CounterBasedGauge64,
			sharewareAndFreeware CounterBasedGauge64,
			peerToPeer CounterBasedGauge64,
			marijuana CounterBasedGauge64,
			hacking CounterBasedGauge64,
			games CounterBasedGauge64,
			philosophyAndPolitics CounterBasedGauge64,
			weapons CounterBasedGauge64,
			payToSurf CounterBasedGauge64,
			huntingAndFishing CounterBasedGauge64,
			society CounterBasedGauge64,
			educationalInstitutions CounterBasedGauge64,
			onlineGreetingCards CounterBasedGauge64,
			sports CounterBasedGauge64,
			swimsuitsAndIntimateApparel CounterBasedGauge64,
			questionable CounterBasedGauge64,
			kids CounterBasedGauge64,
			hateAndRacism CounterBasedGauge64,
			personalStorage CounterBasedGauge64,
			violence CounterBasedGauge64,
			keyloggersAndMonitoring CounterBasedGauge64,
			searchEngines CounterBasedGauge64,
			internetPortals CounterBasedGauge64,
			webAdvertisements CounterBasedGauge64,
			cheating CounterBasedGauge64,
			gross CounterBasedGauge64,
			webBasedEmail CounterBasedGauge64,
			malwareSites CounterBasedGauge64,
			phishingAndOtherFraud CounterBasedGauge64,
			proxyAvoidAndAnonymizers CounterBasedGauge64,
			spywareAndAdware CounterBasedGauge64,
			music CounterBasedGauge64,
			government CounterBasedGauge64,
			nudity CounterBasedGauge64,
			newsAndMedia CounterBasedGauge64,
			illegal CounterBasedGauge64,
			cDNs CounterBasedGauge64,
			internetCommunications CounterBasedGauge64,
			botNets CounterBasedGauge64,
			abortion CounterBasedGauge64,
			healthAndMedicine CounterBasedGauge64,
			confirmedSPAMSources CounterBasedGauge64,
			spamUrls CounterBasedGauge64,
			unconfirmedSPAMSources CounterBasedGauge64,
			openHTTPProxies CounterBasedGauge64,
			dynamicComment CounterBasedGauge64,
			parkedDomains CounterBasedGauge64,
			alcoholAndTobacco CounterBasedGauge64,
			privateIPAddresses CounterBasedGauge64,
			imageAndVideoSearch CounterBasedGauge64,
			fashionAndBeauty CounterBasedGauge64,
			recreationAndHobbies CounterBasedGauge64,
			motorVehicles CounterBasedGauge64,
			webHostingSites CounterBasedGauge64,
			foodAndDining CounterBasedGauge64,
			nudityArtistic CounterBasedGauge64,
			illegalPornography CounterBasedGauge64
		}

			name OBJECT-TYPE
			SYNTAX  DisplayString 
			MAX-ACCESS read-only 
			STATUS current
			DESCRIPTION  "Web Category List name" 
			::={ webCategoryCategoryListSEntry 1 } 

			uncategorized OBJECT-TYPE
			SYNTAX  CounterBasedGauge64 
			MAX-ACCESS read-only 
			STATUS current
			DESCRIPTION  "uncategorized category" 
			::={ webCategoryCategoryListSEntry 2 } 

			realEstate OBJECT-TYPE
			SYNTAX  CounterBasedGauge64 
			MAX-ACCESS read-only 
			STATUS current
			DESCRIPTION  "real estate category" 
			::={ webCategoryCategoryListSEntry 3 } 

			computerAndInternetSecurity OBJECT-TYPE
			SYNTAX  CounterBasedGauge64 
			MAX-ACCESS read-only 
			STATUS current
			DESCRIPTION  "computer and internet security category" 
			::={ webCategoryCategoryListSEntry 4 } 

			financialServices OBJECT-TYPE
			SYNTAX  CounterBasedGauge64 
			MAX-ACCESS read-only 
			STATUS current
			DESCRIPTION  "financial services category" 
			::={ webCategoryCategoryListSEntry 5 } 

			businessAndEconomy OBJECT-TYPE
			SYNTAX  CounterBasedGauge64 
			MAX-ACCESS read-only 
			STATUS current
			DESCRIPTION  "business and economy category" 
			::={ webCategoryCategoryListSEntry 6 } 

			computerAndInternetInfo OBJECT-TYPE
			SYNTAX  CounterBasedGauge64 
			MAX-ACCESS read-only 
			STATUS current
			DESCRIPTION  "computer and internet info category" 
			::={ webCategoryCategoryListSEntry 7 } 

			auctions OBJECT-TYPE
			SYNTAX  CounterBasedGauge64 
			MAX-ACCESS read-only 
			STATUS current
			DESCRIPTION  "auctions category" 
			::={ webCategoryCategoryListSEntry 8 } 

			shopping OBJECT-TYPE
			SYNTAX  CounterBasedGauge64 
			MAX-ACCESS read-only 
			STATUS current
			DESCRIPTION  "shopping category" 
			::={ webCategoryCategoryListSEntry 9 } 

			cultAndOccult OBJECT-TYPE
			SYNTAX  CounterBasedGauge64 
			MAX-ACCESS read-only 
			STATUS current
			DESCRIPTION  "cult and occult category" 
			::={ webCategoryCategoryListSEntry 10 } 

			travel OBJECT-TYPE
			SYNTAX  CounterBasedGauge64 
			MAX-ACCESS read-only 
			STATUS current
			DESCRIPTION  "travel category" 
			::={ webCategoryCategoryListSEntry 11 } 

			drugs OBJECT-TYPE
			SYNTAX  CounterBasedGauge64 
			MAX-ACCESS read-only 
			STATUS current
			DESCRIPTION  "drugs category" 
			::={ webCategoryCategoryListSEntry 12 } 

			adultAndPornography OBJECT-TYPE
			SYNTAX  CounterBasedGauge64 
			MAX-ACCESS read-only 
			STATUS current
			DESCRIPTION  "adult and pornography category" 
			::={ webCategoryCategoryListSEntry 13 } 

			homeAndGarden OBJECT-TYPE
			SYNTAX  CounterBasedGauge64 
			MAX-ACCESS read-only 
			STATUS current
			DESCRIPTION  "home and garden category" 
			::={ webCategoryCategoryListSEntry 14 } 

			military OBJECT-TYPE
			SYNTAX  CounterBasedGauge64 
			MAX-ACCESS read-only 
			STATUS current
			DESCRIPTION  "military category" 
			::={ webCategoryCategoryListSEntry 15 } 

			socialNetwork OBJECT-TYPE
			SYNTAX  CounterBasedGauge64 
			MAX-ACCESS read-only 
			STATUS current
			DESCRIPTION  "social network category" 
			::={ webCategoryCategoryListSEntry 16 } 

			deadSites OBJECT-TYPE
			SYNTAX  CounterBasedGauge64 
			MAX-ACCESS read-only 
			STATUS current
			DESCRIPTION  "dead sites category" 
			::={ webCategoryCategoryListSEntry 17 } 

			stockAdviceAndTools OBJECT-TYPE
			SYNTAX  CounterBasedGauge64 
			MAX-ACCESS read-only 
			STATUS current
			DESCRIPTION  "stock advice and tools category" 
			::={ webCategoryCategoryListSEntry 18 } 

			trainingAndTools OBJECT-TYPE
			SYNTAX  CounterBasedGauge64 
			MAX-ACCESS read-only 
			STATUS current
			DESCRIPTION  "training and tools category" 
			::={ webCategoryCategoryListSEntry 19 } 

			dating OBJECT-TYPE
			SYNTAX  CounterBasedGauge64 
			MAX-ACCESS read-only 
			STATUS current
			DESCRIPTION  "dating category" 
			::={ webCategoryCategoryListSEntry 20 } 

			sexEducation OBJECT-TYPE
			SYNTAX  CounterBasedGauge64 
			MAX-ACCESS read-only 
			STATUS current
			DESCRIPTION  "sex education category" 
			::={ webCategoryCategoryListSEntry 21 } 

			religion OBJECT-TYPE
			SYNTAX  CounterBasedGauge64 
			MAX-ACCESS read-only 
			STATUS current
			DESCRIPTION  "religion category" 
			::={ webCategoryCategoryListSEntry 22 } 

			entertainmentAndArts OBJECT-TYPE
			SYNTAX  CounterBasedGauge64 
			MAX-ACCESS read-only 
			STATUS current
			DESCRIPTION  "entertainment and arts category" 
			::={ webCategoryCategoryListSEntry 23 } 

			personalSitesAndBlogs OBJECT-TYPE
			SYNTAX  CounterBasedGauge64 
			MAX-ACCESS read-only 
			STATUS current
			DESCRIPTION  "personal sites and blogs category" 
			::={ webCategoryCategoryListSEntry 24 } 

			legal OBJECT-TYPE
			SYNTAX  CounterBasedGauge64 
			MAX-ACCESS read-only 
			STATUS current
			DESCRIPTION  "legal category" 
			::={ webCategoryCategoryListSEntry 25 } 

			localInformation OBJECT-TYPE
			SYNTAX  CounterBasedGauge64 
			MAX-ACCESS read-only 
			STATUS current
			DESCRIPTION  "local information category" 
			::={ webCategoryCategoryListSEntry 26 } 

			streamingMedia OBJECT-TYPE
			SYNTAX  CounterBasedGauge64 
			MAX-ACCESS read-only 
			STATUS current
			DESCRIPTION  "streaming media category" 
			::={ webCategoryCategoryListSEntry 27 } 

			jobSearch OBJECT-TYPE
			SYNTAX  CounterBasedGauge64 
			MAX-ACCESS read-only 
			STATUS current
			DESCRIPTION  "job search category" 
			::={ webCategoryCategoryListSEntry 28 } 

			gambling OBJECT-TYPE
			SYNTAX  CounterBasedGauge64 
			MAX-ACCESS read-only 
			STATUS current
			DESCRIPTION  "gambling category" 
			::={ webCategoryCategoryListSEntry 29 } 

			translation OBJECT-TYPE
			SYNTAX  CounterBasedGauge64 
			MAX-ACCESS read-only 
			STATUS current
			DESCRIPTION  "translation category" 
			::={ webCategoryCategoryListSEntry 30 } 

			referenceAndResearch OBJECT-TYPE
			SYNTAX  CounterBasedGauge64 
			MAX-ACCESS read-only 
			STATUS current
			DESCRIPTION  "reference and research category" 
			::={ webCategoryCategoryListSEntry 31 } 

			sharewareAndFreeware OBJECT-TYPE
			SYNTAX  CounterBasedGauge64 
			MAX-ACCESS read-only 
			STATUS current
			DESCRIPTION  "shareware and freeware category" 
			::={ webCategoryCategoryListSEntry 32 } 

			peerToPeer OBJECT-TYPE
			SYNTAX  CounterBasedGauge64 
			MAX-ACCESS read-only 
			STATUS current
			DESCRIPTION  "peer to peer category" 
			::={ webCategoryCategoryListSEntry 33 } 

			marijuana OBJECT-TYPE
			SYNTAX  CounterBasedGauge64 
			MAX-ACCESS read-only 
			STATUS current
			DESCRIPTION  "marijuana category" 
			::={ webCategoryCategoryListSEntry 34 } 

			hacking OBJECT-TYPE
			SYNTAX  CounterBasedGauge64 
			MAX-ACCESS read-only 
			STATUS current
			DESCRIPTION  "hacking category" 
			::={ webCategoryCategoryListSEntry 35 } 

			games OBJECT-TYPE
			SYNTAX  CounterBasedGauge64 
			MAX-ACCESS read-only 
			STATUS current
			DESCRIPTION  "games category" 
			::={ webCategoryCategoryListSEntry 36 } 

			philosophyAndPolitics OBJECT-TYPE
			SYNTAX  CounterBasedGauge64 
			MAX-ACCESS read-only 
			STATUS current
			DESCRIPTION  "philosophy and politics category" 
			::={ webCategoryCategoryListSEntry 37 } 

			weapons OBJECT-TYPE
			SYNTAX  CounterBasedGauge64 
			MAX-ACCESS read-only 
			STATUS current
			DESCRIPTION  "weapons category" 
			::={ webCategoryCategoryListSEntry 38 } 

			payToSurf OBJECT-TYPE
			SYNTAX  CounterBasedGauge64 
			MAX-ACCESS read-only 
			STATUS current
			DESCRIPTION  "pay to surf category" 
			::={ webCategoryCategoryListSEntry 39 } 

			huntingAndFishing OBJECT-TYPE
			SYNTAX  CounterBasedGauge64 
			MAX-ACCESS read-only 
			STATUS current
			DESCRIPTION  "hunting and fishing category" 
			::={ webCategoryCategoryListSEntry 40 } 

			society OBJECT-TYPE
			SYNTAX  CounterBasedGauge64 
			MAX-ACCESS read-only 
			STATUS current
			DESCRIPTION  "society category" 
			::={ webCategoryCategoryListSEntry 41 } 

			educationalInstitutions OBJECT-TYPE
			SYNTAX  CounterBasedGauge64 
			MAX-ACCESS read-only 
			STATUS current
			DESCRIPTION  "educational institutions category" 
			::={ webCategoryCategoryListSEntry 42 } 

			onlineGreetingCards OBJECT-TYPE
			SYNTAX  CounterBasedGauge64 
			MAX-ACCESS read-only 
			STATUS current
			DESCRIPTION  "online greeting cards category" 
			::={ webCategoryCategoryListSEntry 43 } 

			sports OBJECT-TYPE
			SYNTAX  CounterBasedGauge64 
			MAX-ACCESS read-only 
			STATUS current
			DESCRIPTION  "sports category" 
			::={ webCategoryCategoryListSEntry 44 } 

			swimsuitsAndIntimateApparel OBJECT-TYPE
			SYNTAX  CounterBasedGauge64 
			MAX-ACCESS read-only 
			STATUS current
			DESCRIPTION  "swimsuits and intimate apparel category" 
			::={ webCategoryCategoryListSEntry 45 } 

			questionable OBJECT-TYPE
			SYNTAX  CounterBasedGauge64 
			MAX-ACCESS read-only 
			STATUS current
			DESCRIPTION  "questionable category" 
			::={ webCategoryCategoryListSEntry 46 } 

			kids OBJECT-TYPE
			SYNTAX  CounterBasedGauge64 
			MAX-ACCESS read-only 
			STATUS current
			DESCRIPTION  "kids category" 
			::={ webCategoryCategoryListSEntry 47 } 

			hateAndRacism OBJECT-TYPE
			SYNTAX  CounterBasedGauge64 
			MAX-ACCESS read-only 
			STATUS current
			DESCRIPTION  "hate and racism category" 
			::={ webCategoryCategoryListSEntry 48 } 

			personalStorage OBJECT-TYPE
			SYNTAX  CounterBasedGauge64 
			MAX-ACCESS read-only 
			STATUS current
			DESCRIPTION  "personal storage category" 
			::={ webCategoryCategoryListSEntry 49 } 

			violence OBJECT-TYPE
			SYNTAX  CounterBasedGauge64 
			MAX-ACCESS read-only 
			STATUS current
			DESCRIPTION  "violence category" 
			::={ webCategoryCategoryListSEntry 50 } 

			keyloggersAndMonitoring OBJECT-TYPE
			SYNTAX  CounterBasedGauge64 
			MAX-ACCESS read-only 
			STATUS current
			DESCRIPTION  "keyloggers and monitoring category" 
			::={ webCategoryCategoryListSEntry 51 } 

			searchEngines OBJECT-TYPE
			SYNTAX  CounterBasedGauge64 
			MAX-ACCESS read-only 
			STATUS current
			DESCRIPTION  "search engines category" 
			::={ webCategoryCategoryListSEntry 52 } 

			internetPortals OBJECT-TYPE
			SYNTAX  CounterBasedGauge64 
			MAX-ACCESS read-only 
			STATUS current
			DESCRIPTION  "internet portals category" 
			::={ webCategoryCategoryListSEntry 53 } 

			webAdvertisements OBJECT-TYPE
			SYNTAX  CounterBasedGauge64 
			MAX-ACCESS read-only 
			STATUS current
			DESCRIPTION  "web advertisements category" 
			::={ webCategoryCategoryListSEntry 54 } 

			cheating OBJECT-TYPE
			SYNTAX  CounterBasedGauge64 
			MAX-ACCESS read-only 
			STATUS current
			DESCRIPTION  "cheating category" 
			::={ webCategoryCategoryListSEntry 55 } 

			gross OBJECT-TYPE
			SYNTAX  CounterBasedGauge64 
			MAX-ACCESS read-only 
			STATUS current
			DESCRIPTION  "gross category" 
			::={ webCategoryCategoryListSEntry 56 } 

			webBasedEmail OBJECT-TYPE
			SYNTAX  CounterBasedGauge64 
			MAX-ACCESS read-only 
			STATUS current
			DESCRIPTION  "web based email category" 
			::={ webCategoryCategoryListSEntry 57 } 

			malwareSites OBJECT-TYPE
			SYNTAX  CounterBasedGauge64 
			MAX-ACCESS read-only 
			STATUS current
			DESCRIPTION  "malware sites category" 
			::={ webCategoryCategoryListSEntry 58 } 

			phishingAndOtherFraud OBJECT-TYPE
			SYNTAX  CounterBasedGauge64 
			MAX-ACCESS read-only 
			STATUS current
			DESCRIPTION  "phishing and other fraud category" 
			::={ webCategoryCategoryListSEntry 59 } 

			proxyAvoidAndAnonymizers OBJECT-TYPE
			SYNTAX  CounterBasedGauge64 
			MAX-ACCESS read-only 
			STATUS current
			DESCRIPTION  "proxy avoid and anonymizers category" 
			::={ webCategoryCategoryListSEntry 60 } 

			spywareAndAdware OBJECT-TYPE
			SYNTAX  CounterBasedGauge64 
			MAX-ACCESS read-only 
			STATUS current
			DESCRIPTION  "spyware and adware category" 
			::={ webCategoryCategoryListSEntry 61 } 

			music OBJECT-TYPE
			SYNTAX  CounterBasedGauge64 
			MAX-ACCESS read-only 
			STATUS current
			DESCRIPTION  "music category" 
			::={ webCategoryCategoryListSEntry 62 } 

			government OBJECT-TYPE
			SYNTAX  CounterBasedGauge64 
			MAX-ACCESS read-only 
			STATUS current
			DESCRIPTION  "government category" 
			::={ webCategoryCategoryListSEntry 63 } 

			nudity OBJECT-TYPE
			SYNTAX  CounterBasedGauge64 
			MAX-ACCESS read-only 
			STATUS current
			DESCRIPTION  "nudity category" 
			::={ webCategoryCategoryListSEntry 64 } 

			newsAndMedia OBJECT-TYPE
			SYNTAX  CounterBasedGauge64 
			MAX-ACCESS read-only 
			STATUS current
			DESCRIPTION  "news and media category" 
			::={ webCategoryCategoryListSEntry 65 } 

			illegal OBJECT-TYPE
			SYNTAX  CounterBasedGauge64 
			MAX-ACCESS read-only 
			STATUS current
			DESCRIPTION  "illegal category" 
			::={ webCategoryCategoryListSEntry 66 } 

			cDNs OBJECT-TYPE
			SYNTAX  CounterBasedGauge64 
			MAX-ACCESS read-only 
			STATUS current
			DESCRIPTION  "content delivery networks category" 
			::={ webCategoryCategoryListSEntry 67 } 

			internetCommunications OBJECT-TYPE
			SYNTAX  CounterBasedGauge64 
			MAX-ACCESS read-only 
			STATUS current
			DESCRIPTION  "internet communications category" 
			::={ webCategoryCategoryListSEntry 68 } 

			botNets OBJECT-TYPE
			SYNTAX  CounterBasedGauge64 
			MAX-ACCESS read-only 
			STATUS current
			DESCRIPTION  "bot nets category" 
			::={ webCategoryCategoryListSEntry 69 } 

			abortion OBJECT-TYPE
			SYNTAX  CounterBasedGauge64 
			MAX-ACCESS read-only 
			STATUS current
			DESCRIPTION  "abortion category" 
			::={ webCategoryCategoryListSEntry 70 } 

			healthAndMedicine OBJECT-TYPE
			SYNTAX  CounterBasedGauge64 
			MAX-ACCESS read-only 
			STATUS current
			DESCRIPTION  "health and medicine category" 
			::={ webCategoryCategoryListSEntry 71 } 

			confirmedSPAMSources OBJECT-TYPE
			SYNTAX  CounterBasedGauge64 
			MAX-ACCESS read-only 
			STATUS current
			DESCRIPTION  "confirmed SPAM sources category" 
			::={ webCategoryCategoryListSEntry 72 } 

			spamUrls OBJECT-TYPE
			SYNTAX  CounterBasedGauge64 
			MAX-ACCESS read-only 
			STATUS current
			DESCRIPTION  "SPAM URLs category" 
			::={ webCategoryCategoryListSEntry 73 } 

			unconfirmedSPAMSources OBJECT-TYPE
			SYNTAX  CounterBasedGauge64 
			MAX-ACCESS read-only 
			STATUS current
			DESCRIPTION  "unconfirmed SPAM sources category" 
			::={ webCategoryCategoryListSEntry 74 } 

			openHTTPProxies OBJECT-TYPE
			SYNTAX  CounterBasedGauge64 
			MAX-ACCESS read-only 
			STATUS current
			DESCRIPTION  "open HTTP proxies category" 
			::={ webCategoryCategoryListSEntry 75 } 

			dynamicComment OBJECT-TYPE
			SYNTAX  CounterBasedGauge64 
			MAX-ACCESS read-only 
			STATUS current
			DESCRIPTION  "dynamic comment category" 
			::={ webCategoryCategoryListSEntry 76 } 

			parkedDomains OBJECT-TYPE
			SYNTAX  CounterBasedGauge64 
			MAX-ACCESS read-only 
			STATUS current
			DESCRIPTION  "parked domains category" 
			::={ webCategoryCategoryListSEntry 77 } 

			alcoholAndTobacco OBJECT-TYPE
			SYNTAX  CounterBasedGauge64 
			MAX-ACCESS read-only 
			STATUS current
			DESCRIPTION  "alcohol and tobacco category" 
			::={ webCategoryCategoryListSEntry 78 } 

			privateIPAddresses OBJECT-TYPE
			SYNTAX  CounterBasedGauge64 
			MAX-ACCESS read-only 
			STATUS current
			DESCRIPTION  "private IP addresses category" 
			::={ webCategoryCategoryListSEntry 79 } 

			imageAndVideoSearch OBJECT-TYPE
			SYNTAX  CounterBasedGauge64 
			MAX-ACCESS read-only 
			STATUS current
			DESCRIPTION  "image and video search category" 
			::={ webCategoryCategoryListSEntry 80 } 

			fashionAndBeauty OBJECT-TYPE
			SYNTAX  CounterBasedGauge64 
			MAX-ACCESS read-only 
			STATUS current
			DESCRIPTION  "fashion and beauty category" 
			::={ webCategoryCategoryListSEntry 81 } 

			recreationAndHobbies OBJECT-TYPE
			SYNTAX  CounterBasedGauge64 
			MAX-ACCESS read-only 
			STATUS current
			DESCRIPTION  "recreation and hobbies category" 
			::={ webCategoryCategoryListSEntry 82 } 

			motorVehicles OBJECT-TYPE
			SYNTAX  CounterBasedGauge64 
			MAX-ACCESS read-only 
			STATUS current
			DESCRIPTION  "motor vehicles category" 
			::={ webCategoryCategoryListSEntry 83 } 

			webHostingSites OBJECT-TYPE
			SYNTAX  CounterBasedGauge64 
			MAX-ACCESS read-only 
			STATUS current
			DESCRIPTION  "web hosting sites category" 
			::={ webCategoryCategoryListSEntry 84 } 

			foodAndDining OBJECT-TYPE
			SYNTAX  CounterBasedGauge64 
			MAX-ACCESS read-only 
			STATUS current
			DESCRIPTION  "food and dining category" 
			::={ webCategoryCategoryListSEntry 85 } 

			nudityArtistic OBJECT-TYPE
			SYNTAX  CounterBasedGauge64 
			MAX-ACCESS read-only 
			STATUS current
			DESCRIPTION  "nudity join entertainment and arts" 
			::={ webCategoryCategoryListSEntry 86 } 

			illegalPornography OBJECT-TYPE
			SYNTAX  CounterBasedGauge64 
			MAX-ACCESS read-only 
			STATUS current
			DESCRIPTION  "illegal join adult and pornography" 
			::={ webCategoryCategoryListSEntry 87 } 

acosWebCategoryStatistics           OBJECT IDENTIFIER ::= { acosWebCategory 8 }
acosWebCategoryStatisticsS          OBJECT IDENTIFIER ::= { acosWebCategoryStatistics 1 }

		dbLookup OBJECT-TYPE
		SYNTAX  CounterBasedGauge64 
		MAX-ACCESS read-only 
		STATUS current
		DESCRIPTION  "some help string" 
		::={ acosWebCategoryStatisticsS 1 } 

		cloudCacheLookup OBJECT-TYPE
		SYNTAX  CounterBasedGauge64 
		MAX-ACCESS read-only 
		STATUS current
		DESCRIPTION  "some help string" 
		::={ acosWebCategoryStatisticsS 2 } 

		cloudLookup OBJECT-TYPE
		SYNTAX  CounterBasedGauge64 
		MAX-ACCESS read-only 
		STATUS current
		DESCRIPTION  "some help string" 
		::={ acosWebCategoryStatisticsS 3 } 

		rtuLookup OBJECT-TYPE
		SYNTAX  CounterBasedGauge64 
		MAX-ACCESS read-only 
		STATUS current
		DESCRIPTION  "some help string" 
		::={ acosWebCategoryStatisticsS 4 } 

		lookupLatency OBJECT-TYPE
		SYNTAX  CounterBasedGauge64 
		MAX-ACCESS read-only 
		STATUS current
		DESCRIPTION  "some help string" 
		::={ acosWebCategoryStatisticsS 5 } 

		dbMem OBJECT-TYPE
		SYNTAX  CounterBasedGauge64 
		MAX-ACCESS read-only 
		STATUS current
		DESCRIPTION  "some help string" 
		::={ acosWebCategoryStatisticsS 6 } 

		rtuCacheMem OBJECT-TYPE
		SYNTAX  CounterBasedGauge64 
		MAX-ACCESS read-only 
		STATUS current
		DESCRIPTION  "some help string" 
		::={ acosWebCategoryStatisticsS 7 } 

		lookupCacheMem OBJECT-TYPE
		SYNTAX  CounterBasedGauge64 
		MAX-ACCESS read-only 
		STATUS current
		DESCRIPTION  "some help string" 
		::={ acosWebCategoryStatisticsS 8 } 

acosWebCategoryReputationScope      OBJECT IDENTIFIER ::= { acosWebCategory 9 }
acosWebCategoryReputationScopeS     OBJECT IDENTIFIER ::= { acosWebCategoryReputationScope 1 }

webCategoryReputationScopeSTable OBJECT-TYPE
		SYNTAX SEQUENCE OF WebCategoryReputationScopeSEntry
		MAX-ACCESS not-accessible
		STATUS current
		::={ acosWebCategoryReputationScopeS 1 } 


	webCategoryReputationScopeSEntry OBJECT-TYPE
		SYNTAX WebCategoryReputationScopeSEntry
		MAX-ACCESS not-accessible
		STATUS current
		INDEX {
			name
		}
		::={ webCategoryReputationScopeSTable 1 } 


	WebCategoryReputationScopeSEntry ::=
		SEQUENCE {
			name DisplayString, 
			trustworthy CounterBasedGauge64,
			lowRisk CounterBasedGauge64,
			moderateRisk CounterBasedGauge64,
			suspicious CounterBasedGauge64,
			malicious CounterBasedGauge64
		}

			name OBJECT-TYPE
			SYNTAX  DisplayString 
			MAX-ACCESS read-only 
			STATUS current
			DESCRIPTION  "Reputation Scope name" 
			::={ webCategoryReputationScopeSEntry 1 } 

			trustworthy OBJECT-TYPE
			SYNTAX  CounterBasedGauge64 
			MAX-ACCESS read-only 
			STATUS current
			DESCRIPTION  "Trustworthy level(81-100)" 
			::={ webCategoryReputationScopeSEntry 2 } 

			lowRisk OBJECT-TYPE
			SYNTAX  CounterBasedGauge64 
			MAX-ACCESS read-only 
			STATUS current
			DESCRIPTION  "Low-risk level(61-80)" 
			::={ webCategoryReputationScopeSEntry 3 } 

			moderateRisk OBJECT-TYPE
			SYNTAX  CounterBasedGauge64 
			MAX-ACCESS read-only 
			STATUS current
			DESCRIPTION  "Moderate-risk level(41-60)" 
			::={ webCategoryReputationScopeSEntry 4 } 

			suspicious OBJECT-TYPE
			SYNTAX  CounterBasedGauge64 
			MAX-ACCESS read-only 
			STATUS current
			DESCRIPTION  "Suspicious level(21-40)" 
			::={ webCategoryReputationScopeSEntry 5 } 

			malicious OBJECT-TYPE
			SYNTAX  CounterBasedGauge64 
			MAX-ACCESS read-only 
			STATUS current
			DESCRIPTION  "Malicious level(1-20)" 
			::={ webCategoryReputationScopeSEntry 6 } 

END

--	3Com Bridge Group 
--	Version 1.0.0
--	February 13, 1998
 
--	3Com Corporation
--	80 Central Street
--	Boxborough, MA 01719
--	(508) 264-1400
 
----------------------------------------------------------------------------------------
--  7/12/99 - tmeiczin   Fixed type in AddressIsStatic Description 
--  6/30/99 - tmeiczin   Changed ReceiveMulticastLimit from 65535 to 200000
--  4/27/99 - tmeiczin   Pulled from 3cSys.mib
---------------------------------------------------------------------------------------- 
A3COM-SWITCHING-SYSTEMS-BRIDGE-MIB DEFINITIONS ::= BEGIN
 
IMPORTS
	enterprises, Counter, IpAddress
		 FROM RFC1155-SMI
	DisplayString
                 FROM RFC1213-MIB
	OBJECT-TYPE
                 FROM RFC-1212
	TRAP-TYPE
                 FROM RFC-1215;

a3Com                               OBJECT IDENTIFIER ::= { enterprises 43 } 
switchingSystemsMibs                OBJECT IDENTIFIER ::= { a3Com 29 } 
a3ComSwitchingSystemsMib            OBJECT IDENTIFIER ::= { switchingSystemsMibs 4 } 
a3ComSysBridge                      OBJECT IDENTIFIER ::= { a3ComSwitchingSystemsMib 10 } 
 
-- The Switching Systems MIB bridge group.  Implementation of this group 
-- is mandatory for agents which manage bridge resources. 
 
a3ComSysBridgeCount  OBJECT-TYPE 
    SYNTAX  INTEGER 
    ACCESS  read-only 
    STATUS  mandatory 
    DESCRIPTION   
            "The count of bridges managed by this agent." 
::= { a3ComSysBridge 1 } 
 
-- The Switching Systems MIB bridge table. 
 
a3ComSysBridgeTable  OBJECT-TYPE 
    SYNTAX  SEQUENCE OF A3ComSysBridgeEntry 
    ACCESS  not-accessible 
    STATUS  mandatory 
    DESCRIPTION   
            "A list of bridge entries.  A single entry exists in this 
            list for each bridge managed by this agent." 
::= { a3ComSysBridge 2 } 
 
a3ComSysBridgeEntry  OBJECT-TYPE 
    SYNTAX  A3ComSysBridgeEntry 
    ACCESS  not-accessible 
    STATUS  mandatory 
    DESCRIPTION   
            "A bridge entry contains information about a particular 
            bridge managed by this agent." 
    INDEX  { a3ComSysBridgeIndex } 
::= { a3ComSysBridgeTable 1 } 
						 
A3ComSysBridgeEntry ::= 
    SEQUENCE { 
		a3ComSysBridgeIndex 
			INTEGER, 
		a3ComSysBridgePortCount 
			INTEGER, 
		a3ComSysBridgeAddressTableSize 
			INTEGER, 
		a3ComSysBridgeAddressTableCount 
			INTEGER, 
		a3ComSysBridgeAddressTablePeakCount 
			INTEGER, 
		a3ComSysBridgeAddressThreshold 
			INTEGER, 
		a3ComSysBridgeMode 
			INTEGER, 
		a3ComSysBridgeBackbonePort 
			INTEGER, 
		a3ComSysBridgeIpFragmentationEnabled 
			INTEGER, 
		a3ComSysBridgeTrFddiTranslationMode 
			INTEGER, 
		a3ComSysBridgeSTPGroupAddress  
			OCTET STRING, 
		a3ComSysBridgeSTPEnable 
			INTEGER, 
		a3ComSysBridgeIpxSnapTranslationEnable 
			INTEGER, 
		a3ComSysBridgeLowLatencyEnable 
			INTEGER, 
		a3ComSysBridgeVlanMode 
			INTEGER, 
        a3ComSysBridgeRateLimitReceiveMulticast
			INTEGER,
        a3ComSysBridgeRateLimitReceiveBroadcast
            INTEGER,
        a3ComSysBridgeRateLimitReceiveFlood
            INTEGER,
        a3ComSysBridgeAddressLearnMode
			INTEGER,
        a3ComSysBridgeAddressAgingInterval
            INTEGER,
        a3ComSysBridgeLoopDetectMode
			INTEGER,
		a3ComSysBridgeLoopDetectSrcAddress
			OCTET STRING 
		} 
 
a3ComSysBridgeIndex  OBJECT-TYPE 
    SYNTAX  INTEGER (1..65535) 
    ACCESS  read-only 
    STATUS  mandatory 
    DESCRIPTION   
            "The index of the bridge identified by this entry, 
            relative to this agent." 
::= { a3ComSysBridgeEntry 1 } 
 
a3ComSysBridgePortCount  OBJECT-TYPE 
    SYNTAX  INTEGER 
    ACCESS  read-only 
    STATUS  mandatory 
    DESCRIPTION   
            "The number of bridge ports that the bridge identified by 
            this entry controls." 
::= { a3ComSysBridgeEntry 2 } 
 
a3ComSysBridgeAddressTableSize  OBJECT-TYPE 
    SYNTAX  INTEGER  
    ACCESS  read-only 
    STATUS  mandatory 
    DESCRIPTION   
            "The size of the address table for the bridge identified 
            by this entry." 
::= { a3ComSysBridgeEntry 3 } 
 
a3ComSysBridgeAddressTableCount  OBJECT-TYPE 
    SYNTAX  INTEGER  
    ACCESS  read-only 
    STATUS  mandatory 
    DESCRIPTION   
            "The current count of addresses in the address table for 
            the bridge identified by this entry." 
::= { a3ComSysBridgeEntry 4 } 
 
a3ComSysBridgeAddressTablePeakCount  OBJECT-TYPE 
    SYNTAX  INTEGER  
    ACCESS  read-only 
    STATUS  mandatory 
    DESCRIPTION   
            "The peak count of addresses in the address table for the 
            bridge identified by this entry, since the system was last 
            initialized." 
::= { a3ComSysBridgeEntry 5 } 
 
a3ComSysBridgeAddressThreshold  OBJECT-TYPE 
    SYNTAX  INTEGER  
    ACCESS  read-write 
    STATUS  mandatory 
    DESCRIPTION   
            "A reporting threshold for the total number of addresses 
            known for the bridge identified by this entry.  When this 
            threshold is reached, the event 
            a3ComSysBridgeAddressThresholdEvent is generated.  The range of 
            valid values for setting this object is between 1 and the 
            corresponding value reported by a3ComSysBridgeAddressTableSize 
            + 1 (Note that this range applies to values issued in set 
            requests.  The current value may be outside this range, 
            for example if the corresponding value of a3ComSysBridgeMode is 
            changed). Setting this object to one greater than the 
            address table size disables the generation of 
            a3ComSysBridgeAddressThresholdEvents since the limit will never 
            be reached." 
::= { a3ComSysBridgeEntry 6 } 
 
a3ComSysBridgeMode  OBJECT-TYPE 
    SYNTAX  INTEGER { 
              expressMode(1), 
              ieee8021dBridgeMode(2), 
              notSupported(3), 
              ieee8021dSRTBridgeMode(4), 
              ieee8021dSRBridgeMode(5), 
              ibmSRBridgeMode(6), 
              srtBBridgeMode(7), 
              srExpressBridgeMode(8) 
            } 
    ACCESS  read-write 
    STATUS  mandatory 
    DESCRIPTION   
            "The operational mode of the bridge identified by this 
            entry.  Note that bridges which report notSupported(3) 
            will not support sets of this object, and that the value 
            notSupported(3) is not a valid value for a set operation." 
::= { a3ComSysBridgeEntry 7 } 
 
a3ComSysBridgeBackbonePort  OBJECT-TYPE 
    SYNTAX  INTEGER 
    ACCESS  read-write 
    STATUS  mandatory 
    DESCRIPTION   
            "The number of the port selected as the backbone segment 
            port when the corresponding value of a3ComSysBridgeMode is 
            is expressMode(1).  The value of this object can range 
            from 1 to the corresponding value of a3ComSysBridgePortCount, 
            however, some bridges may support only a subset of ports 
            as backbone ports.  If the corresponding value of 
            a3ComSysBridgeMode is not expressMode(1), the value of this 
            object is ignored." 
::= { a3ComSysBridgeEntry 8 } 
 
a3ComSysBridgeIpFragmentationEnabled  OBJECT-TYPE 
    SYNTAX  INTEGER { 
              true(1), 
              false(2), 
              notSupported(3) 
            } 
    ACCESS  read-write 
    STATUS  mandatory 
    DESCRIPTION   
            "A flag indicating whether or not IP fragmentation is 
            enabled on this bridge.  Note that bridges which report 
            notSupported(3) will not support sets of this object, and 
            that the value notSupported(3) is not a valid value for a 
            set operation." 
::= { a3ComSysBridgeEntry 9 } 
 
a3ComSysBridgeTrFddiTranslationMode  OBJECT-TYPE 
    SYNTAX  INTEGER { 
              native(1), 
              backbone(2) 
            } 
    ACCESS  read-write 
    STATUS  mandatory 
    DESCRIPTION   
            "The mode used to describe whether the embedded MAC 
            addresses are byte-conjugated in order to convert them 
            from Token Ring format to native FDDI format (and vice 
            versa), or whether they are left alone (used for traffic 
            flowing	across a FDDI backbone to/from Token Ring end 
            stations)." 
::= { a3ComSysBridgeEntry 10 } 
 
a3ComSysBridgeSTPGroupAddress  OBJECT-TYPE 
	SYNTAX	OCTET STRING (SIZE (6)) -- 6 octet address in "canonical" order 
    ACCESS  read-write 
    STATUS  mandatory 
    DESCRIPTION   
            "Spanning tree bridge group address. The address cannot be  
            changed if the spanning tree is enabled (a3ComSysBridgeStpEnabled)." 
::= { a3ComSysBridgeEntry 11 } 
 
a3ComSysBridgeSTPEnable  OBJECT-TYPE 
    SYNTAX  INTEGER { 
              true(1), 
              false(2) 
            } 
    ACCESS  read-write 
    STATUS  mandatory 
    DESCRIPTION   
            "This object indicates if spanning tree bridge feature is 
            enabled or disabled.  If enabled this value will equal true(1)." 
::= { a3ComSysBridgeEntry 12 } 
 
a3ComSysBridgeIpxSnapTranslationEnable  OBJECT-TYPE 
    SYNTAX  INTEGER { 
              true(1), 
              false(2) 
            } 
    ACCESS  read-write 
    STATUS  mandatory 
    DESCRIPTION   
            "This object indicates if the IPX 802.3-FDDI SNAP Translation 
            bridge feature is enabled or disabled.  If enabled this 
            value will equal true(1). Note, this object may not be 
            supported on all bridges." 
::= { a3ComSysBridgeEntry 13 } 
 
a3ComSysBridgeLowLatencyEnable  OBJECT-TYPE 
    SYNTAX  INTEGER { 
              true(1), 
              false(2) 
            } 
    ACCESS  read-write 
    STATUS  mandatory 
    DESCRIPTION   
            "This object indicates if the bridge low latency 
            feature is enabled or disabled.  If enabled this 
            value will equal true(1). Note, this object may not be 
            supported on all bridges." 
::= { a3ComSysBridgeEntry 14 } 
 
a3ComSysBridgeVlanMode  OBJECT-TYPE 
    SYNTAX  INTEGER { 
              open(1), 
              closed(2), 
              mixed(3), 
              notSupported(4) 
            } 
    ACCESS  read-write 
    STATUS  mandatory 
    DESCRIPTION   
            "This object indicates the VLAN types that this 
            bridge will support.  Open mode means that each VLAN 
            within this bridge will be of the Open type; all VLANs 
            within this bridge will share the same address table. 
            Closed mode means that each VLAN within this bridge 
            will be of the Closed type; each VLAN within this 
            bridge will have its own address table.  Mixed mode 
            means that each VLAN within this bridge with be of 
            either the Open or Closed type; all Open VLANs will 
            share the same address table and each Closed VLAN 
            will have its own address table." 
::= { a3ComSysBridgeEntry 15 } 

a3ComSysBridgeRateLimitReceiveMulticast  OBJECT-TYPE
    SYNTAX  INTEGER (1..65535)
    ACCESS  read-write
    STATUS  mandatory
    DESCRIPTION
            "This object limits the number of multicast frames forwarded
             by this port over a 1 second interval.  The value is set
             across all ports on the device."
::= { a3ComSysBridgeEntry 16 }

a3ComSysBridgeRateLimitReceiveBroadcast  OBJECT-TYPE
    SYNTAX  INTEGER (1..65535)
    ACCESS  read-write
    STATUS  mandatory
    DESCRIPTION
            "This object limits the number of broadcast frames forwarded
             by this port over a 1 second interval.  The value is set
             across all ports on the device."
::= { a3ComSysBridgeEntry 17 }

a3ComSysBridgeRateLimitReceiveFlood  OBJECT-TYPE
    SYNTAX  INTEGER (1..65535)
    ACCESS  read-write
    STATUS  mandatory
    DESCRIPTION
            "This object limits the number of frames forwarded that
             would normally be flooded by this port over a 1 second 
             interval.  The value is set across all ports on the device."
::= { a3ComSysBridgeEntry 18 }
 
a3ComSysBridgeAddressLearnMode  OBJECT-TYPE
    SYNTAX  INTEGER {
                   normal(1),
                   secure(2)
            }
    ACCESS  read-write
    STATUS  mandatory
    DESCRIPTION
           "This object determins the behavior of address management

            normal(1) - The device will learn dynamic addresses and
                        static entries can be added.

            secure(2) - Static, management, and control addresses can
                        be added to a database.  If a dynamic address
                        is seen that does not match an entry in the
                        database, then the port will be disabled."
::= { a3ComSysBridgeEntry 19 }

a3ComSysBridgeAddressAgingInterval  OBJECT-TYPE
    SYNTAX  INTEGER (1..65535)
    ACCESS  read-write
    STATUS  mandatory
    DESCRIPTION
           "This object determines how long (in seconds) a dynamic entry is kept
            in the database."
::= { a3ComSysBridgeEntry 20 }

a3ComSysBridgeLoopDetectMode  OBJECT-TYPE
    SYNTAX  INTEGER {
                   enabled(1),
                   disabled(2),
                   immediate(3)
            }
    ACCESS  read-write
    STATUS  mandatory
    DESCRIPTION
            "This object determines the behavior of loop detection

             enabled(1)   - The DA will detect loops and disable
                            the apporiate port.
             disabled(2)  - No loop detection mechanism will be enabled.
             immediate(3) - If a BPDU is received on a front panel port
                            then a front panel port will be disabled.
             The default value for this object disabled(2)."
::= { a3ComSysBridgeEntry 21 }

a3ComSysBridgeLoopDetectSrcAddress  OBJECT-TYPE
    SYNTAX  OCTET STRING
    ACCESS  read-only
    STATUS  mandatory
    DESCRIPTION
            "This object returns the source address that is used to
             determine if a loop is present between client ports"
::= { a3ComSysBridgeEntry 22 }

-- The Switching Systems MIB bridge port table. 
 
a3ComSysBridgePortTable  OBJECT-TYPE 
    SYNTAX  SEQUENCE OF A3ComSysBridgePortEntry 
    ACCESS  not-accessible 
    STATUS  mandatory 
    DESCRIPTION   
            "A list of bridge port entries.  A single entry exists in 
            this list for each bridge port managed by this agent." 
::= { a3ComSysBridge 3 } 
 
a3ComSysBridgePortEntry  OBJECT-TYPE 
    SYNTAX  A3ComSysBridgePortEntry 
    ACCESS  not-accessible 
    STATUS  mandatory 
    DESCRIPTION   
            "A bridge port entry contains information about a 
            particular bridge port managed by this agent." 
    INDEX  { a3ComSysBridgePortBridgeIndex, 
            a3ComSysBridgePortIndex } 
::= { a3ComSysBridgePortTable 1 } 
 
A3ComSysBridgePortEntry ::= 
    SEQUENCE { 
		a3ComSysBridgePortBridgeIndex 
			INTEGER, 
		a3ComSysBridgePortIndex 
			INTEGER, 
		a3ComSysBridgePortIfIndex 
			INTEGER, 
		a3ComSysBridgePortReceiveMulticastLimit 
			INTEGER, 
		a3ComSysBridgePortAddressAction 
			INTEGER, 
		a3ComSysBridgePortSpanningTreeFrameReceivedCounts 
			Counter, 
		a3ComSysBridgePortReceiveBlockedDiscards 
			Counter, 
		a3ComSysBridgePortReceiveMulticastLimitExceededs 
			Counter, 
		a3ComSysBridgePortReceiveMulticastLimitExceededDiscards 
			Counter, 
		a3ComSysBridgePortReceiveSecurityDiscards 
			Counter, 
		a3ComSysBridgePortReceiveUnknownDiscards 
			Counter, 
		a3ComSysBridgePortReceiveOtherDiscards 
			Counter, 
		a3ComSysBridgePortReceiveErrorDiscards 
			Counter, 
		a3ComSysBridgePortSameSegmentDiscards 
			Counter, 
		a3ComSysBridgePortTransmitBlockedDiscards 
			Counter, 
		a3ComSysBridgePortReceiveAllPathFilteredFrames 
			Counter, 
		a3ComSysBridgePortReceiveMulticastPathFilteredFrames 
			Counter, 
		a3ComSysBridgePortTransmitAllPathFilteredFrames 
			Counter, 
		a3ComSysBridgePortTransmitMulticastPathFilteredFrames 
			Counter, 
		a3ComSysBridgePortForwardedUnicastFrames 
			Counter, 
		a3ComSysBridgePortForwardedUnicastOctets 
			Counter, 
		a3ComSysBridgePortForwardedMulticastFrames 
			Counter, 
		a3ComSysBridgePortForwardedMulticastOctets 
			Counter, 
		a3ComSysBridgePortFloodedUnicastFrames 
			Counter, 
		a3ComSysBridgePortFloodedUnicastOctets 
			Counter, 
		a3ComSysBridgePortStpMode 
			INTEGER, 
		a3ComSysBridgePortReceiveMulticastLimitFrameType 
			INTEGER, 
		a3ComSysBridgePortForwardedFrames 
			Counter, 
		a3ComSysBridgePortReceiveMulticastLimitMultiplier 
			INTEGER,
        a3ComSysBridgePortRateLimitReceiveMulticastEnabled
            INTEGER,
        a3ComSysBridgePortRateLimitReceiveBroadcastEnabled
            INTEGER,
        a3ComSysBridgePortRateLimitReceiveFloodEnabled
            INTEGER,
        a3ComSysBridgePortRateLimitReceiveState
            INTEGER,
        a3ComSysBridgePortLoopDetectState
            INTEGER,
        a3ComSysBridgePortAddressMaxLimit
            INTEGER,
        a3ComSysBridgePortAddressState
            INTEGER,
		a3ComSysBridgePortReceiveInternalPathFilteredFrames 
			Counter
	} 
 
a3ComSysBridgePortBridgeIndex  OBJECT-TYPE 
    SYNTAX  INTEGER (1..65535) 
    ACCESS  read-only 
    STATUS  mandatory 
    DESCRIPTION   
            "The index of the bridge identified by this entry, 
            relative to this agent." 
::= { a3ComSysBridgePortEntry 1 } 
 
a3ComSysBridgePortIndex  OBJECT-TYPE 
    SYNTAX  INTEGER (1..65535) 
    ACCESS  read-only 
    STATUS  mandatory 
    DESCRIPTION   
            "The index of the bridge port identified by this entry, 
            within the bridge identified by this entry." 
::= { a3ComSysBridgePortEntry 2 } 
 
a3ComSysBridgePortIfIndex  OBJECT-TYPE 
    SYNTAX  INTEGER (1..65535) 
    ACCESS  read-only 
    STATUS  mandatory 
    DESCRIPTION   
            "The value of the MIB-II ifIndex corresponding to the 
            bridge port identified by this entry." 
::= { a3ComSysBridgePortEntry 3 } 
 
a3ComSysBridgePortReceiveMulticastLimit  OBJECT-TYPE 
    SYNTAX  INTEGER (0..200000) 
    ACCESS  read-write 
    STATUS  mandatory 
    DESCRIPTION   
            "This variable limits the number of multicast frames forwarded 
            by this port over a 1 second interval.  The minimum threshold 
            limit may vary between platforms, but can be determined by multiplying 
            this value by the swSysBridgePortReceiveMulticastLimitMultiplier 
            value.  For example if this value equals 2, and the 
            swSysBridgePortReceiveMulticastLimitMultiplier equals 1000 then no 
            more than 2000 multicast frames per second will be forwarded by this port. 
 
            The default value for this object is zero which an infinite rate."	 
::= { a3ComSysBridgePortEntry 4 } 
 
a3ComSysBridgePortAddressAction  OBJECT-TYPE 
    SYNTAX  INTEGER { 
              other(1), 
              freezeAddress(2), 
              flushAddress(3), 
              flushDynamicAddress(4) 
            } 
    ACCESS  read-write 
    STATUS  mandatory 
    DESCRIPTION   
            "This object, when read, always returns the value 
            other(1).  The behavior of setting this object to each of 
            the acceptable values is as follows: 
 
            freezeAddress:	causes all the learned dynamic 
            addresses to be converted into static 
            addresses. 
 
            flushAddress:   causes all the addresses to be flushed 
            from the address list for the bridge 
            port identified by this entry. 
 
            flushDynamicAddress: 
            causes all dynamic addresses to be 
            flushed from the address list for the 
            bridge port identified by this entry." 
::= { a3ComSysBridgePortEntry 5 } 
 
a3ComSysBridgePortSpanningTreeFrameReceivedCounts  OBJECT-TYPE 
    SYNTAX  Counter 
    ACCESS  read-only 
    STATUS  mandatory 
    DESCRIPTION   
            "The number of spanning tree frames received by the 
            bridge port identified by this entry." 
::= { a3ComSysBridgePortEntry 6 } 
 
a3ComSysBridgePortReceiveBlockedDiscards  OBJECT-TYPE 
    SYNTAX  Counter 
    ACCESS  read-only 
    STATUS  mandatory 
    DESCRIPTION   
            "The number of frames discarded by the bridge port 
            identified by this entry because the receiving bridge port 
            was not in the 'forwarding' state." 
::= { a3ComSysBridgePortEntry 7 } 
 
a3ComSysBridgePortReceiveMulticastLimitExceededs  OBJECT-TYPE 
    SYNTAX  Counter 
    ACCESS  read-only 
    STATUS  mandatory 
    DESCRIPTION   
            "The number of times the value of 
            a3ComSysBridgePortReceiveMulticastLimit was exceeded for the 
            port identified by this entry." 
::= { a3ComSysBridgePortEntry 8 } 
 
a3ComSysBridgePortReceiveMulticastLimitExceededDiscards  OBJECT-TYPE 
    SYNTAX  Counter 
    ACCESS  read-only 
    STATUS  mandatory 
    DESCRIPTION   
            "The number of multicast/broadcast frames discarded by the 
            bridge port identified by this entry because the 
            corresponding value of a3ComSysBridgePortReceiveMulticastLimit 
            was exceeded." 
::= { a3ComSysBridgePortEntry 9 } 
 
a3ComSysBridgePortReceiveSecurityDiscards  OBJECT-TYPE 
    SYNTAX  Counter 
    ACCESS  read-only 
    STATUS  mandatory 
    DESCRIPTION   
            "The number of frames discarded by the bridge port 
            identified by this entry because they contained source 
            addresses which were statically configured on another 
            bridge port.  A statically configured address (station), 
            which is not allowed to move, appears to have moved." 
::= { a3ComSysBridgePortEntry 10 } 
 
a3ComSysBridgePortReceiveUnknownDiscards  OBJECT-TYPE 
    SYNTAX  Counter 
    ACCESS  read-only 
    STATUS  mandatory 
    DESCRIPTION   
            "The number of frames discarded by the bridge port 
            identified by this entry because the destination address 
            was unknown.  Note that this counter is only valid for 
            backbone ports, and only when the bridge is operating in 
            express mode." 
::= { a3ComSysBridgePortEntry 11 } 
 
a3ComSysBridgePortReceiveOtherDiscards  OBJECT-TYPE 
    SYNTAX  Counter 
    ACCESS  read-only 
    STATUS  mandatory 
    DESCRIPTION   
            "The number of frames discarded by the bridge port 
            identified by this entry because they contained either 
            invalid (group) source addresses or source addresses 
            belonging to this bridge (indicative of network loops)." 
::= { a3ComSysBridgePortEntry 12 } 
 
a3ComSysBridgePortReceiveErrorDiscards  OBJECT-TYPE 
    SYNTAX  Counter 
    ACCESS  read-only 
    STATUS  mandatory 
    DESCRIPTION   
            "The number of frames discarded by the bridge port 
            identified by this entry because of internal bridge system 
            errors (e.g., hardware and software address table 
            discrepencies)." 
::= { a3ComSysBridgePortEntry 13 } 
 
a3ComSysBridgePortSameSegmentDiscards  OBJECT-TYPE 
    SYNTAX  Counter 
    ACCESS  read-only 
    STATUS  mandatory 
    DESCRIPTION   
            "The number of frames discarded by the bridge port 
            identified by this entry because the destination address 
            is known on the same network segment as the source address, 
            i.e., the frame does not need to be bridged." 
::= { a3ComSysBridgePortEntry 14 } 
 
a3ComSysBridgePortTransmitBlockedDiscards  OBJECT-TYPE 
    SYNTAX  Counter 
    ACCESS  read-only 
    STATUS  mandatory 
    DESCRIPTION   
            "The number of frames discarded by the bridge port 
            identified by this entry because the transmitting bridge 
            port was not in the 'forwarding' state." 
::= { a3ComSysBridgePortEntry 15 } 
 
a3ComSysBridgePortReceiveAllPathFilteredFrames  OBJECT-TYPE 
    SYNTAX  Counter 
    ACCESS  read-only 
    STATUS  mandatory 
    DESCRIPTION   
            "The number of frames discarded by the bridge port 
            identified by this entry due to user defined receive all 
            path filters." 
::= { a3ComSysBridgePortEntry 16 } 
 
a3ComSysBridgePortReceiveMulticastPathFilteredFrames  OBJECT-TYPE 
    SYNTAX  Counter 
    ACCESS  read-only 
    STATUS  mandatory 
    DESCRIPTION   
            "The number of frames discarded by the bridge port 
            identified by this entry due to user defined receive 
            multicast path filters." 
::= { a3ComSysBridgePortEntry 17 } 
 
a3ComSysBridgePortTransmitAllPathFilteredFrames  OBJECT-TYPE 
    SYNTAX  Counter 
    ACCESS  read-only 
    STATUS  mandatory 
    DESCRIPTION   
            "The number of frames discarded by the bridge port 
            identified by this entry due to user defined transmit all 
            path filters." 
::= { a3ComSysBridgePortEntry 18 } 
 
a3ComSysBridgePortTransmitMulticastPathFilteredFrames  OBJECT-TYPE 
    SYNTAX  Counter 
    ACCESS  read-only 
    STATUS  mandatory 
    DESCRIPTION   
            "The number of frames discarded by the bridge port 
            identified by this entry due to user defined transmit 
            multicast path filters." 
::= { a3ComSysBridgePortEntry 19 } 
 
a3ComSysBridgePortForwardedUnicastFrames  OBJECT-TYPE 
    SYNTAX  Counter 
    ACCESS  read-only 
    STATUS  mandatory 
    DESCRIPTION   
            "The number of unicast frames which this port forwarded 
            to a single destination port." 
::= { a3ComSysBridgePortEntry 20 } 
 
a3ComSysBridgePortForwardedUnicastOctets  OBJECT-TYPE 
    SYNTAX  Counter 
    ACCESS  read-only 
    STATUS  mandatory 
    DESCRIPTION   
            "The number of octets contained in unicast frames 
            which this port forwarded to a single destination port." 
::= { a3ComSysBridgePortEntry 21 } 
 
a3ComSysBridgePortForwardedMulticastFrames  OBJECT-TYPE 
    SYNTAX  Counter 
    ACCESS  read-only 
    STATUS  mandatory 
    DESCRIPTION   
            "The number of multicast frames which this port forwarded." 
::= { a3ComSysBridgePortEntry 22 } 
 
a3ComSysBridgePortForwardedMulticastOctets  OBJECT-TYPE 
    SYNTAX  Counter 
    ACCESS  read-only 
    STATUS  mandatory 
    DESCRIPTION   
            "The number of octets contained in multicast frames which 
            this port forwarded." 
::= { a3ComSysBridgePortEntry 23 } 
 
a3ComSysBridgePortFloodedUnicastFrames  OBJECT-TYPE 
    SYNTAX  Counter 
    ACCESS  read-only 
    STATUS  mandatory 
    DESCRIPTION   
            "The number of unicast frames which this port flooded to 
            all other ports in the bridge." 
::= { a3ComSysBridgePortEntry 24 } 
 
a3ComSysBridgePortFloodedUnicastOctets  OBJECT-TYPE 
    SYNTAX  Counter 
    ACCESS  read-only 
    STATUS  mandatory 
    DESCRIPTION   
            "The number of octets contained in unicast frames which 
            this port flooded to all other ports in the bridge." 
::= { a3ComSysBridgePortEntry 25 } 
 
 
a3ComSysBridgePortStpMode  OBJECT-TYPE 
    SYNTAX  INTEGER { 
              enable(1), 
              disable(2), 
              remove(3) 
            } 
    ACCESS  read-write 
    STATUS  mandatory 
    DESCRIPTION   
            "The mode of the bridge port." 
            REFERENCE 
            "IEEE 802.1D-1990: Section 4.5.5.2 for enable and disable modes." 
::= { a3ComSysBridgePortEntry 26 } 
 
a3ComSysBridgePortReceiveMulticastLimitFrameType  OBJECT-TYPE 
    SYNTAX  INTEGER { 
              broadcastAndMulticast(1), 
              broadcastOnly(2) 
            } 
    ACCESS  read-write 
    STATUS  mandatory 
    DESCRIPTION   
            "This object identifies the frames type(s) that are to be 
            counted when determining if the receive multicast limit 
            has been exceeded for this bridge port.  Devices attached 
            to networks with predominantly high multicast traffic 
            (e.g. video) should set this value to broadcastOnly(2) 
            to detect broadcast storms." 
::= { a3ComSysBridgePortEntry 27 } 
 
a3ComSysBridgePortForwardedFrames  OBJECT-TYPE 
    SYNTAX  Counter 
    ACCESS  read-only 
    STATUS  mandatory 
    DESCRIPTION   
            "The number of frames which this port forwarded." 
::= { a3ComSysBridgePortEntry 28 } 
 
a3ComSysBridgePortReceiveMulticastLimitMultiplier  OBJECT-TYPE 
    SYNTAX  INTEGER 
    ACCESS  read-only 
    STATUS  mandatory 
    DESCRIPTION   
            "This variable determines the minimum setting for the multicast 
            limit threshold.  For example if this value equals 1000, and the 
            a3ComSysBridgePortReceiveMulticastLimit variable equals 2 then 
            no more than 2000 multicast frames per second will be forwarded 
            by this port." 
::= { a3ComSysBridgePortEntry 29 } 
 
a3ComSysBridgePortRateLimitReceiveMulticastEnabled  OBJECT-TYPE
    SYNTAX  INTEGER {
                    enabled(1),
                    disabled(2)
            }
    ACCESS  read-write
    STATUS  mandatory
    DESCRIPTION
            "This object determines whether a port participates
             in multicast rate limiting set by the object
             a3ComSysBridgeRateLimitReceiveMulticast"
::= { a3ComSysBridgePortEntry 30 }

a3ComSysBridgePortRateLimitReceiveBroadcastEnabled  OBJECT-TYPE
    SYNTAX  INTEGER {
                    enabled(1),
                    disabled(2)
            }
    ACCESS  read-write
    STATUS  mandatory
    DESCRIPTION
            "This object determines whether a port participates
             in broadcast rate limiting set by the object
             a3ComSysBridgeRateLimitReceiveBroadcast"
::= { a3ComSysBridgePortEntry 31 }

a3ComSysBridgePortRateLimitReceiveFloodEnabled  OBJECT-TYPE
    SYNTAX  INTEGER {
                    enabled(1),
                    disabled(2)
            }
    ACCESS  read-write
    STATUS  mandatory
    DESCRIPTION
            "This object determines whether a port participates
             in flood rate limiting set by the object
             a3ComSysBridgeRateLimitReceiveFlood"
::= { a3ComSysBridgePortEntry 32 }
 
a3ComSysBridgePortRateLimitReceiveState  OBJECT-TYPE
    SYNTAX  INTEGER {
                    enabled(1),
                    disabled(2),
                    bmfrl-disabled(3)
             }
    ACCESS  read-only
    STATUS  mandatory
    DESCRIPTION
            "This object returns the bmfrl state of the port 
             
                    enabled(1) - port is up
                   disabled(2) - port is down, but not as
                                 a result of BMFRL
             bmfrl-disabled(3) - port was disabled
                                 by rate limit software"
::= { a3ComSysBridgePortEntry 33 }

a3ComSysBridgePortLoopDetectState  OBJECT-TYPE
    SYNTAX  INTEGER {
                    active(1),
                    loopDetected(2),
                    bpduDetected(3)
            }
    ACCESS  read-only
    STATUS  mandatory
    DESCRIPTION
           "This object returns a reason code that will indicate why
            a given port was disable by the Loop Detection software."
::= { a3ComSysBridgePortEntry 34 }

a3ComSysBridgePortAddressMaxLimit  OBJECT-TYPE
    SYNTAX  INTEGER (1..65535)
    ACCESS  read-write
    STATUS  mandatory
    DESCRIPTION
           "This object controls the maximum number of unicast addresses
            that can be learned or configured on a port.  This value is
            set on a per port basis.  The value can't be set lower than
            the current number of addresses on a port."
::= { a3ComSysBridgePortEntry 35 }

a3ComSysBridgePortAddressState  OBJECT-TYPE
    SYNTAX  INTEGER {
                    active(1),
                    limitationExceeded(2),
                    securityViolation(3)
            }
    ACCESS  read-only
    STATUS  mandatory
    DESCRIPTION
           "This object returns a reason code that will indicate why
            a given port was disable, when a3ComDaAddressMode is set
            to secure."
::= { a3ComSysBridgePortEntry 36 }

a3ComSysBridgePortReceiveInternalPathFilteredFrames  OBJECT-TYPE 
    SYNTAX  Counter 
    ACCESS  read-only 
    STATUS  mandatory 
    DESCRIPTION   
            "The number of frames discarded by the bridge port 
            identified by this entry due to receive internal 
            path filters." 
::= { a3ComSysBridgePortEntry 37 } 

--	::= { a3ComSysBridge 4 } Reserved.  Do not use. 
 
 
-- The Switching Systems MIB bridge port address table 
 
a3ComSysBridgePortAddressTable  OBJECT-TYPE 
    SYNTAX  SEQUENCE OF A3ComSysBridgePortAddressEntry 
    ACCESS  not-accessible 
    STATUS  mandatory 
    DESCRIPTION   
            "A list of bridge port address information.  A single 
            entry exists in this list for each learned address, 
            accross all bridge ports and all bridges managed by this 
            agent." 
::= { a3ComSysBridge 5 } 
 
a3ComSysBridgePortAddressEntry  OBJECT-TYPE 
    SYNTAX  A3ComSysBridgePortAddressEntry 
    ACCESS  not-accessible 
    STATUS  mandatory 
    DESCRIPTION   
            "An bridge port address entry contains information about a 
            particular bridge port address.  To create a new entry, 
            set an instance of a3ComSysBridgePortAddressRemoteAddress with 
            the address index portion of the instance set to 0, to a 
            valid value.  To remove an entry, set the instance of the 
            a3ComSysBridgePortAddressType for the entry to invalid(2)." 
    INDEX  { a3ComSysBridgePortAddressBridgeIndex,  
            a3ComSysBridgePortAddressPortIndex,  
            a3ComSysBridgePortAddressIndex } 
::= { a3ComSysBridgePortAddressTable 1 } 
 
A3ComSysBridgePortAddressEntry ::= 
    SEQUENCE { 
		a3ComSysBridgePortAddressBridgeIndex 
			INTEGER, 
		a3ComSysBridgePortAddressPortIndex 
			INTEGER, 
		a3ComSysBridgePortAddressIndex 
			INTEGER, 
		a3ComSysBridgePortAddressRemoteAddress 
			OCTET STRING, 
		a3ComSysBridgePortAddressType 
			INTEGER, 
		a3ComSysBridgePortAddressIsStatic 
			INTEGER, 
		a3ComSysBridgePortAddressStaticPort 
			INTEGER, 
		a3ComSysBridgePortAddressAge 
			INTEGER 
	} 
 
a3ComSysBridgePortAddressBridgeIndex  OBJECT-TYPE 
    SYNTAX  INTEGER (1..65535) 
    ACCESS  read-only 
    STATUS  mandatory 
    DESCRIPTION   
            "The index of the bridge identified by this entry, 
            relative to this agent." 
::= { a3ComSysBridgePortAddressEntry 1 } 
 
a3ComSysBridgePortAddressPortIndex  OBJECT-TYPE 
    SYNTAX  INTEGER (1..65535) 
    ACCESS  read-only 
    STATUS  mandatory 
    DESCRIPTION   
            "The index of the bridge port identified by this entry, 
            within the bridge identified by this entry." 
::= { a3ComSysBridgePortAddressEntry 2 } 
 
a3ComSysBridgePortAddressIndex  OBJECT-TYPE 
    SYNTAX  INTEGER (1..65535) 
    ACCESS  read-only 
    STATUS  mandatory 
    DESCRIPTION   
            "The index of this address entry within the bridge address 
            table for the bridge identified by this entry.  This index 
            ranges from 1 to the corresponding value of 
            a3ComSysBridgeAddressTableSize."  
::= { a3ComSysBridgePortAddressEntry 3 } 
 
a3ComSysBridgePortAddressRemoteAddress  OBJECT-TYPE 
	SYNTAX	OCTET STRING (SIZE (6)) -- 6 octet address in "canonical" order 
    ACCESS  read-write 
    STATUS  mandatory 
    DESCRIPTION   
            "The remote MAC address detected on the bridge port 
            identified by to this entry.  Setting this object results 
            in an attempt to create a new entry in the table.  Since 
            the value of a3ComSysBridgePortAddressIndex is determined 
            automatically internal to the bridge, a set is only 
            successful if the index value specified for 
            a3ComSysBridgePortAddressIndex is zero.  A get-next 
            using the values of a3ComSysBridgePortAddressTypeIndex and 
            a3ComSysBridgePortAddressPortIndex can be used to determine the 
            address index assigned to the newly added address entry." 
::= { a3ComSysBridgePortAddressEntry 4 } 
 
a3ComSysBridgePortAddressType  OBJECT-TYPE 
    SYNTAX  INTEGER { 
              valid(1), 
              invalid(2) 
            } 
    ACCESS  read-write 
    STATUS  mandatory 
    DESCRIPTION   
            "This object, when read, always returns the value valid(1). 
            Setting this object to invalid(2) will remove the 
            corresponding address entry from the table." 
::= { a3ComSysBridgePortAddressEntry 5 } 
 
a3ComSysBridgePortAddressIsStatic  OBJECT-TYPE 
    SYNTAX  INTEGER { 
              isStatic(1), 
              isDynamic(2) 
            } 
    ACCESS  read-write 
    STATUS  mandatory 
    DESCRIPTION   
            "A value indicating whether this MAC address was 
            statically configured or was dynamically learned.  Note 
            that isStatic(1) is only valid for set operations." 
::= { a3ComSysBridgePortAddressEntry 6 } 
 
a3ComSysBridgePortAddressStaticPort  OBJECT-TYPE 
    SYNTAX  INTEGER 
    ACCESS  read-only 
    STATUS  mandatory 
    DESCRIPTION   
            "If the corresponding value of the object  
            a3ComSysBridgePortAddressIsStatic is isStatic(1), this object 
            indicates the local bridge port index (as reported by 
            a3ComSysBridgePortLocalIndex) for which this address MAC was 
            statically configured.  If the object 
            a3ComSysBridgePortAddressIsStatic has the value isDynamic(2), 
            the value of this object is 0." 
::= { a3ComSysBridgePortAddressEntry 7 } 
 
a3ComSysBridgePortAddressAge  OBJECT-TYPE 
    SYNTAX  INTEGER 
    ACCESS  read-only 
    STATUS  mandatory 
    DESCRIPTION   
            "This object indicates the time, in seconds, elapsed since 
            a packet containing this address as a source was last seen 
            on the bridge port identified by this entry." 
::= { a3ComSysBridgePortAddressEntry 8 } 
 
a3ComSysBridgeStpGroupAddress  OBJECT-TYPE 
	SYNTAX	OCTET STRING (SIZE (6)) -- 6 octet address in "canonical" order 
    ACCESS  read-write 
    STATUS  obsolete 
    DESCRIPTION   
            "Spanning tree bridge group address. The address cannot be  
            changed if the spanning tree is enabled (a3ComSysBridgeStpEnabled). 
            This object can now be found under the a3ComSysBridgeTable  
            as a3ComSysBridgeSTPGroupAddress." 
::= { a3ComSysBridge 6 } 
 
a3ComSysBridgeStpEnable  OBJECT-TYPE 
    SYNTAX  INTEGER { 
              true(1), 
              false(2) 
            } 
    ACCESS  read-write 
    STATUS  obsolete 
    DESCRIPTION   
            "This object indicates if spanning tree bridge feature is 
            enabled or disabled.  If enabled this value will equal true(1). 
            This object can now be found under the a3ComSysBridgeTable  
            as a3ComSysBridgeSTPEnable." 
::= { a3ComSysBridge 7 } 
 

-- The Switching Systems MIB bridge vlan port address table

a3ComSysBridgeVlanPortAddressTable OBJECT-TYPE
    SYNTAX  SEQUENCE OF A3ComSysBridgeVlanPortAddressEntry
    ACCESS  not-accessible
    STATUS  mandatory
    DESCRIPTION
            "A list of vlan bridge port address information.  A single
            entry exists in this list for each learned address,
            across all vlan bridge ports and all vlan bridges managed
            by this agent."
::= { a3ComSysBridge 8 }

a3ComSysBridgeVlanPortAddressEntry OBJECT-TYPE
    SYNTAX  A3ComSysBridgeVlanPortAddressEntry
    ACCESS  not-accessible
    STATUS  mandatory
    DESCRIPTION
            "A bridge vlan port address entry contains information about a
            particular bridge vlan port address.  To create a new entry,
            set an instance of a3ComSysBridgeVlanPortAddressRemoteAddress with
            the address index portion of the instance set to 0, to a
            valid value.  To remove an entry, set the instance of the
            a3ComSysBridgeVlanPortAddressType for the entry to invalid(2)."
    INDEX   { a3ComSysBridgeVlanPortAddressBridgeIndex, 
                  a3ComSysBridgeVlanPortAddressVlanIndex,
                  a3ComSysBridgeVlanPortAddressPortIndex, 
                  a3ComSysBridgeVlanPortAddressIndex }
::= { a3ComSysBridgeVlanPortAddressTable 1 }

A3ComSysBridgeVlanPortAddressEntry ::=
    SEQUENCE {
                a3ComSysBridgeVlanPortAddressBridgeIndex
                        INTEGER,
                a3ComSysBridgeVlanPortAddressVlanIndex
                        INTEGER,
                a3ComSysBridgeVlanPortAddressPortIndex
                        INTEGER,
                a3ComSysBridgeVlanPortAddressIndex
                        INTEGER,
                a3ComSysBridgeVlanPortAddressRemoteAddress
                        OCTET STRING,
                a3ComSysBridgeVlanPortAddressType
                        INTEGER,
                a3ComSysBridgeVlanPortAddressIsStatic
                        INTEGER,
                a3ComSysBridgeVlanPortAddressStaticPort
                        INTEGER,
                a3ComSysBridgeVlanPortAddressAge
                        INTEGER
        }

a3ComSysBridgeVlanPortAddressBridgeIndex OBJECT-TYPE
    SYNTAX  INTEGER
    ACCESS  read-only
    STATUS  mandatory
    DESCRIPTION
            "The index of the bridge vlan identified by this entry,
             relative to this agent."
::= { a3ComSysBridgeVlanPortAddressEntry 1 }

a3ComSysBridgeVlanPortAddressVlanIndex OBJECT-TYPE
    SYNTAX  INTEGER
    ACCESS  read-only
    STATUS  mandatory
    DESCRIPTION
            "The index of the vlan identified by this entry,
            within the bridge identified by this entry."
::= { a3ComSysBridgeVlanPortAddressEntry 2 }

a3ComSysBridgeVlanPortAddressPortIndex OBJECT-TYPE
    SYNTAX  INTEGER
    ACCESS  read-only
    STATUS  mandatory
    DESCRIPTION
                        "The index of the bridge vlan port identified by this entry,
                        within the bridge vlan identified by this entry."
::= { a3ComSysBridgeVlanPortAddressEntry 3 }

a3ComSysBridgeVlanPortAddressIndex OBJECT-TYPE
    SYNTAX  INTEGER
    ACCESS  read-only
    STATUS  mandatory
    DESCRIPTION
            "The index of this address entry within the bridge vlan address
            table for the bridge identified by this entry.  This index
            ranges from 1 to the corresponding value of
            a3ComSysBridgeAddressTableSize." 
::= { a3ComSysBridgeVlanPortAddressEntry 4 }

a3ComSysBridgeVlanPortAddressRemoteAddress OBJECT-TYPE
    SYNTAX  OCTET STRING (SIZE (6)) -- 6 octet address in "canonical" order
    ACCESS  read-write
    STATUS  mandatory
    DESCRIPTION
            "The remote MAC address detected on the bridge vlan port
            identified by to this entry.  Setting this object results
            in an attempt to create a new entry in the table.  Since
            the value of a3ComSysBridgeVlanPortAddressIndex is determined
            automatically internal to the bridge vlan, a set is only
            successful if the index value specified for
            a3ComSysBridgeVlanPortAddressIndex is zero.  A get-next
            using the values of a3ComSysBridgeVlanPortAddressTypeIndex and
            a3ComSysBridgeVlanPortAddressPortIndex can be used to determine the
            address index assigned to the newly added address entry."
::= { a3ComSysBridgeVlanPortAddressEntry 5 }

a3ComSysBridgeVlanPortAddressType OBJECT-TYPE
    SYNTAX INTEGER {
              valid(1),
              invalid(2)
            }
    ACCESS  read-write
    STATUS  mandatory
    DESCRIPTION
            "This object, when read, always returns the value valid(1).
            Setting this object to invalid(2) will remove the
            corresponding address entry from the table."
::= { a3ComSysBridgeVlanPortAddressEntry 6 }

a3ComSysBridgeVlanPortAddressIsStatic OBJECT-TYPE
    SYNTAX  INTEGER {
              isStatic(1),
              isDynamic(2)
            }
    ACCESS  read-write
    STATUS  mandatory
    DESCRIPTION
            "A value indicating whether this MAC address was
            statically configured or was dynamically learned.  Note
            that isStatic(1) is only valid for set operations."
::= { a3ComSysBridgeVlanPortAddressEntry 7 }

a3ComSysBridgeVlanPortAddressStaticPort OBJECT-TYPE
    SYNTAX  INTEGER
    ACCESS  read-only
    STATUS  mandatory
    DESCRIPTION
            "If the corresponding value of the object 
            a3ComSysBridgeVlanPortAddressIsStatic is isStatic(1), this object
            indicates the local bridge port index (as reported by
            a3ComSysBridgePortLocalIndex) for which this address MAC was
            statically configured.  If the object
            a3ComSysBridgeVlanPortAddressIsStatic has the value isDynamic(2),
            the value of this object is 0."
::= { a3ComSysBridgeVlanPortAddressEntry 8 }

a3ComSysBridgeVlanPortAddressAge OBJECT-TYPE
    SYNTAX  INTEGER
    ACCESS  read-only
    STATUS  mandatory
    DESCRIPTION
            "This object indicates the time, in seconds, elapsed since
            a packet containing this address as a source was last seen
            on the bridge vlan port identified by this entry."
::= { a3ComSysBridgeVlanPortAddressEntry 9 }

--
-- The Bridge Group MIB traps.
--

a3ComSysBridgeAddressThresholdEvent TRAP-TYPE 
    ENTERPRISE  a3ComSwitchingSystemsMib  
    VARIABLES   { a3ComSysBridgeIndex } 
    DESCRIPTION   
            "The trap that is generated when the number of addresses 
            stored in the bridge reaches a3ComSysBridgeAddressThreshold." 
::= 6 

a3ComSysBridgePortLearnEvent TRAP-TYPE
    ENTERPRISE  a3ComSysBridge
    VARIABLES   { a3ComSysBridgePortIndex,
                  a3ComSysBridgePortAddressState }
    DESCRIPTION
            "The Trap is generated to inform the network manager of the misbehaved
             port.  The misbehavior is reported in the Address State."
::= 60

a3ComSysBridgePortRateLimitEvent TRAP-TYPE
    ENTERPRISE  a3ComSysBridge
    VARIABLES   { a3ComSysBridgePortIndex,
                  a3ComSysBridgePortRateLimitReceiveState }
    DESCRIPTION
            "The Trap is generated to inform the network manager of a misbehaved
             port. The port has exceeded one of the port based rate limiting
             thresholds and has been placed into the reported state."
::= 61

a3ComSysBridgePortLoopDetectEvent TRAP-TYPE
    ENTERPRISE  a3ComSysBridge
    VARIABLES   { a3ComSysBridgePortIndex,
                  a3ComSysBridgePortLoopDetectState }
    DESCRIPTION
            "The Trap is generated to inform the network manager of the misbehaved
             port.  A loop has been detected on this port and the port has been
             placed into the reported state."
::= 62

END

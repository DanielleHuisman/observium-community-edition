--  3Com Switching Systems Management Information Base
--  Version 1.0.0
--  February 13, 1998

--  3Com Corporation
--  80 Central Street
--  Boxborough, MA 01719
--  (508) 264-1400

----------------------------------------------------------------------------------------
--  04/27/99 - tmeiczin moved a3ComSysTokenRing into 3cSysTokenRing.mib file
--
----------------------------------------------------------------------------------------

A3COM-SWITCHING-SYSTEMS-TOKEN-RING-MIB DEFINITIONS ::= BEGIN

IMPORTS
    enterprises, Counter, IpAddress
         FROM RFC1155-SMI
    DisplayString
                 FROM RFC1213-MIB
    OBJECT-TYPE
                 FROM RFC-1212
    TRAP-TYPE
                 FROM RFC-1215;

a3Com                               OBJECT IDENTIFIER ::= { enterprises 43 }
switchingSystemsMibs                OBJECT IDENTIFIER ::= { a3Com 29 }
a3ComSwitchingSystemsMib            OBJECT IDENTIFIER ::= { switchingSystemsMibs 4 }
a3ComSysTokenRingPort               OBJECT IDENTIFIER ::= { a3ComSwitchingSystemsMib 13 }

-- The Switching Systems MIB token ring port group.  Implementation of
-- this group is mandatory for agents which manage token ring port
-- resources.

a3ComSysTokenRingPortCount  OBJECT-TYPE
    SYNTAX  INTEGER
    ACCESS  read-only
    STATUS  mandatory
    DESCRIPTION
            "The count of token ring ports managed by this agent."
::= { a3ComSysTokenRingPort 1 }


-- The Switching Systems MIB token ring port table.

a3ComSysTokenRingPortTable  OBJECT-TYPE
    SYNTAX  SEQUENCE OF A3ComSysTokenRingPortEntry
    ACCESS  not-accessible
    STATUS  mandatory
    DESCRIPTION
            "A list of token ring port entries.  A single entry exists
            in this list for each token ring port managed by this agent."
::= { a3ComSysTokenRingPort 2 }

a3ComSysTokenRingPortEntry  OBJECT-TYPE
    SYNTAX  A3ComSysTokenRingPortEntry
    ACCESS  not-accessible
    STATUS  mandatory
    DESCRIPTION
            "A token ring port entry contains information about a
            particular token ring port managed by this agent."
    INDEX  { a3ComSysTokenRingPortIndex }
::= { a3ComSysTokenRingPortTable 1 }

A3ComSysTokenRingPortEntry ::=
    SEQUENCE {
        a3ComSysTokenRingPortIndex          INTEGER,
        a3ComSysTokenRingPortIfIndex        INTEGER,
        a3ComSysTokenRingPortLabel          DisplayString,
        a3ComSysTokenRingPortInsertStatus   INTEGER,
        a3ComSysTokenRingPortType           INTEGER,
        a3ComSysTokenRingPortMode           INTEGER,
        a3ComSysTokenRingPortSpeed          INTEGER,
        a3ComSysTokenRingPortLineErrors Counter,
        a3ComSysTokenRingPortBurstErrors    Counter,
        a3ComSysTokenRingPortACErrors       Counter,
        a3ComSysTokenRingPortAbortTransErrors   Counter,
        a3ComSysTokenRingPortInternalErrors Counter,
        a3ComSysTokenRingPortLostFrameErrors    Counter,
        a3ComSysTokenRingPortReceiveCongestionErrors    Counter,
        a3ComSysTokenRingPortFrameCopiedErrors  Counter,
        a3ComSysTokenRingPortTokenErrors        Counter,
        a3ComSysTokenRingPortSoftErrors     Counter,
        a3ComSysTokenRingPortHardErrors     Counter,
        a3ComSysTokenRingPortTransmitBeacons    Counter,
        a3ComSysTokenRingPortLobeWires          Counter,
        a3ComSysTokenRingPortRemoves            Counter,
        a3ComSysTokenRingPortSingles            Counter,
        a3ComSysTokenRingPortFreqErrors     Counter,
        a3ComSysTokenRingPortRingStatus     INTEGER
    }

a3ComSysTokenRingPortIndex  OBJECT-TYPE
    SYNTAX  INTEGER (1..65535)
    ACCESS  read-only
    STATUS  mandatory
    DESCRIPTION
            "The index of the token ring port identified by this entry,
            relative to this agent."
::= { a3ComSysTokenRingPortEntry 1 }

a3ComSysTokenRingPortIfIndex  OBJECT-TYPE
    SYNTAX  INTEGER (1..65535)
    ACCESS  read-only
    STATUS  mandatory
    DESCRIPTION
            "The value of the MIB-II ifIndex corresponding to the
            token ring port identified by this entry."
::= { a3ComSysTokenRingPortEntry 2 }

a3ComSysTokenRingPortLabel  OBJECT-TYPE
    SYNTAX  DisplayString (SIZE (0..31))
    ACCESS  read-write
    STATUS  mandatory
    DESCRIPTION
            "An ASCII text string describing the token ring port
            identified by this entry."
::= { a3ComSysTokenRingPortEntry 3 }

a3ComSysTokenRingPortInsertStatus  OBJECT-TYPE
    SYNTAX  INTEGER {
              inserted(1),
              deinserted(2)
            }
    ACCESS  read-only
    STATUS  mandatory
    DESCRIPTION
            "The current value of the link status for the token ring port
            identified by this entry."
::= { a3ComSysTokenRingPortEntry 4 }

a3ComSysTokenRingPortType  OBJECT-TYPE
    SYNTAX  INTEGER {
              rj45(1),
              other(2)
            }
    ACCESS  read-only
    STATUS  mandatory
    DESCRIPTION
            "Specific port type description for the token ring port
            identified by this entry."
::= { a3ComSysTokenRingPortEntry 5 }

a3ComSysTokenRingPortMode  OBJECT-TYPE
    SYNTAX  INTEGER {
              station(1),
              lobe(2)
            }
    ACCESS  read-write
    STATUS  mandatory
    DESCRIPTION
            "The current mode of the port. The default mode (station) is
            used to connect a hub to the port.  Lobe mode is used to direct
            connect a Token Ring station into the port.  This selection
            can only be made on ports 1 and 2 of the module."
::= { a3ComSysTokenRingPortEntry 6 }

a3ComSysTokenRingPortSpeed  OBJECT-TYPE
    SYNTAX  INTEGER {
              fourMegabit(1),
              sixteenMegabit(2),
              sixteenMegabitETR(3)
            }
    ACCESS  read-write
    STATUS  mandatory
    DESCRIPTION
            "The current speed of the port. The default speed is
            sixteenMegabit."
::= { a3ComSysTokenRingPortEntry 7 }

a3ComSysTokenRingPortLineErrors  OBJECT-TYPE
    SYNTAX  Counter
    ACCESS  read-only
    STATUS  mandatory
    DESCRIPTION
            "This counter is incremented when a frame
            or token is copied or repeated by a
            station, the E bit is zero in the frame
            or token and one of the following
            conditions exists: 1) there is a
            non-data bit (J or K bit) between the SD
            and the ED of the frame or token, or
            2) there is an FCS error in the frame."
::= { a3ComSysTokenRingPortEntry 8 }

a3ComSysTokenRingPortBurstErrors  OBJECT-TYPE
    SYNTAX  Counter
    ACCESS  read-only
    STATUS  mandatory
    DESCRIPTION
            "This counter is incremented when a station
            detects the absence of transitions for five
            half-bit timers (burst-five error)."
::= { a3ComSysTokenRingPortEntry 9 }

a3ComSysTokenRingPortACErrors  OBJECT-TYPE
    SYNTAX  Counter
    ACCESS  read-only
    STATUS  mandatory
    DESCRIPTION
            "This counter is incremented when a station
            receives an AMP or SMP frame in which A is
            equal to C is equal to 0, and then receives
            another SMP frame with A is equal to C is
            equal to 0 without first receiving an AMP
            frame. It denotes a station that cannot set
            the AC bits properly."
::= { a3ComSysTokenRingPortEntry 10 }

a3ComSysTokenRingPortAbortTransErrors  OBJECT-TYPE
    SYNTAX  Counter
    ACCESS  read-only
    STATUS  mandatory
    DESCRIPTION
            "This counter is incremented when a station
            transmits an abort delimiter while
            transmitting."
::= { a3ComSysTokenRingPortEntry 11 }

a3ComSysTokenRingPortInternalErrors  OBJECT-TYPE
    SYNTAX  Counter
    ACCESS  read-only
    STATUS  mandatory
    DESCRIPTION
            "This counter is incremented when a station
            recognizes an internal error."
::= { a3ComSysTokenRingPortEntry 12 }

a3ComSysTokenRingPortLostFrameErrors  OBJECT-TYPE
    SYNTAX  Counter
    ACCESS  read-only
    STATUS  mandatory
    DESCRIPTION
            "This counter is incremented when a station
            is transmitting and its TRR timer expires.
            This condition denotes a condition where a
            transmitting station in strip mode does not
            receive the trailer of the frame before the
            TRR timer goes off."
::= { a3ComSysTokenRingPortEntry 13 }

a3ComSysTokenRingPortReceiveCongestionErrors  OBJECT-TYPE
    SYNTAX  Counter
    ACCESS  read-only
    STATUS  mandatory
    DESCRIPTION
            "This counter is incremented when a station
            recognizes a frame addressed to its
            specific address, but has no available
            buffer space indicating that the station
            is congested."
::= { a3ComSysTokenRingPortEntry 14 }

a3ComSysTokenRingPortFrameCopiedErrors  OBJECT-TYPE
    SYNTAX  Counter
    ACCESS  read-only
    STATUS  mandatory
    DESCRIPTION
            "This counter is incremented when a station
            recognizes a frame addressed to its
            specific address and detects that the FS
            field A bits are set to 1 indicating a
            possible line hit or duplicate address."
::= { a3ComSysTokenRingPortEntry 15 }

a3ComSysTokenRingPortTokenErrors  OBJECT-TYPE
    SYNTAX  Counter
    ACCESS  read-only
    STATUS  mandatory
    DESCRIPTION
            "This counter is incremented when a station
            acting as the active monitor recognizes an
            error condition that needs a token
            transmitted."
::= { a3ComSysTokenRingPortEntry 16 }

a3ComSysTokenRingPortSoftErrors  OBJECT-TYPE
    SYNTAX  Counter
    ACCESS  read-only
    STATUS  mandatory
    DESCRIPTION
            "The number of Soft Errors the interface
            has detected. It directly corresponds to
            the number of Report Error MAC frames
            that this interface has transmitted.
            Soft Errors are those which are
            recoverable by the MAC layer protocols."
::= { a3ComSysTokenRingPortEntry 17 }

a3ComSysTokenRingPortHardErrors  OBJECT-TYPE
    SYNTAX  Counter
    ACCESS  read-only
    STATUS  mandatory
    DESCRIPTION
            "The number of times this interface has
            detected an immediately recoverable
            fatal error.  It denotes the number of
            times this interface is either
            transmitting or receiving beacon MAC
            frames."
::= { a3ComSysTokenRingPortEntry 18 }

a3ComSysTokenRingPortTransmitBeacons  OBJECT-TYPE
    SYNTAX  Counter
    ACCESS  read-only
    STATUS  mandatory
    DESCRIPTION
            "The number of times this interface has
            transmitted a beacon frame."
::= { a3ComSysTokenRingPortEntry 19 }

a3ComSysTokenRingPortLobeWires  OBJECT-TYPE
    SYNTAX  Counter
    ACCESS  read-only
    STATUS  mandatory
    DESCRIPTION
            "The number of times the interface has
            detected an open or short circuit in the
            lobe data path.  The adapter will be closed
            when this condition occurs."
::= { a3ComSysTokenRingPortEntry 20 }

a3ComSysTokenRingPortRemoves  OBJECT-TYPE
    SYNTAX  Counter
    ACCESS  read-only
    STATUS  mandatory
    DESCRIPTION
            "The number of times the interface has
            received a Remove Ring Station MAC frame
            request.  When this frame is received
            the interface will enter the close state."
::= { a3ComSysTokenRingPortEntry 21 }

a3ComSysTokenRingPortSingles  OBJECT-TYPE
    SYNTAX  Counter
    ACCESS  read-only
    STATUS  mandatory
    DESCRIPTION
            "The number of times the interface has
            sensed that it is the only station on the
            ring.  This will happen if the interface
            is the first one up on a ring, or if
            there is a hardware problem."
::= { a3ComSysTokenRingPortEntry 22 }

a3ComSysTokenRingPortFreqErrors  OBJECT-TYPE
    SYNTAX  Counter
    ACCESS  read-only
    STATUS  mandatory
    DESCRIPTION
            "The number of times the interface has
            detected that the frequency of the
            incoming signal differs from the expected
            frequency."
::= { a3ComSysTokenRingPortEntry 23 }

a3ComSysTokenRingPortRingStatus  OBJECT-TYPE
    SYNTAX  INTEGER
    ACCESS  read-only
    STATUS  mandatory
    DESCRIPTION
            "The current interface status which can
            be used to diagnose fluctuating problems
            that can occur on token rings, after a
            station has successfully been added to
            the ring.
            Before an open is completed, this
            object has the value for the 'no status'
            condition.  This object is useful for
            debugging problems when the station
            can not even enter the ring.
            The object's value is a sum of
            values, one for each currently applicable
            condition.  The following values are
            defined for various conditions:
            0 = No Problems detected
            32 = Ring Recovery
            64 = Single Station
            256 = Remove Received
            512 = reserved
            1024 = Auto-Removal Error
            2048 = Lobe Wire Fault
            4096 = Transmit Beacon
            8192 = Soft Error
            16384 = Hard Error
            32768 = Signal Loss
            131072 = no status, open not completed."
::= { a3ComSysTokenRingPortEntry 24 }

END

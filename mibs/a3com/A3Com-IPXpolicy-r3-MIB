-- Copyright 1995 by 3Com Corporation.  All rights reserved.
-- MIB file name:  a3Com-ipxPolicy
-- available in these 3Com devices:  NETBuilder bridge/routers
-- For support or more info, check 3Com's web page at http://www.3com.com

--
--
-- This MIB is for 3Com intermediate systems that support IPX
--
-- The 3Com Enterprise Products Proprietary MIB Extensions
--
-- Copyright 3Com Corporation, 1993. All rights reserved.
--
-- changes FOR software release 8.0 (r2 of MIB):
-- 22-may-94: kxy updated mib to conform to ipx_changes.
--            specifically: all current IPX Neighbor - related
--                          parameters have been deprecated.
--                          They've been replaced by (similar)
--                          parameters which are applied seperately
--                          to IPX RIPs and SAPs. (The previous params
--                          applied to both).
--                          o a3ipxPCNbrAdvCtl, a3ipxPCNbrRcvCtl, and
--                            a3ipxPCNbrRcvType have been deprecated.
--                          o Their functionality has been replaced by
--                            a3ipxPolRipNbrCtlTable and 
--                            a3ipxPolSapNbrCtlTable.
--                          o a3ipxPolNbrTable has been deprecated.
--                          o Its functionality has been replaced by
--                            a3ipxRipPolNbrTable and a3ipxSapPolNbrTable.
--
-- 25-may-94: kxy deprecated a3ipxPCPolicyOverride and replaced it with
--            a3ipxPCRipPolOverride and a3ipxPCSapPolOverride
--
-- changes FOR software release 8.2 (r3 of MIB):
-- 20-mar-95: kxy updated description of a3ipxPolRteNet1 to include info
--            about the default route. 
-- 

       A3Com-IPXpolicy-r3-MIB DEFINITIONS ::= BEGIN

       IMPORTS
               enterprises 
                   FROM RFC1155-SMI
               MacAddress
                   FROM RFC1286-MIB
               DisplayString 
                   FROM RFC1213-MIB
               OBJECT-TYPE
                   FROM RFC-1212;

        --
        -- This MIB is for 3Com products that implement IPX routing
        -- policy features
        --

          a3Com          OBJECT IDENTIFIER ::= { enterprises 43 }
          brouterMIB     OBJECT IDENTIFIER ::= { a3Com 2 }
          a3ComIPXpol    OBJECT IDENTIFIER ::= { brouterMIB 11 }
          a3ipxPolNbr    OBJECT IDENTIFIER ::= { a3ComIPXpol 5 }

      --
      --

      RowStatus ::= INTEGER {
                         active(1),
                         notInService(2),
                         notReady(3),                               
                         createAndGo(4),
                         createAndWait(5),
                         destroy(6)
      }

      --This data type, which has the same semantics as the RowStatus
      --textual convention used in SNMPv2, is used to add and 
      --delete entries from a table.
      --
      --The tables in this MIB allow a subset of the functionality
      --provided by the RowStatus textual convention.  In particular
      --row creation is allowed using only the createAndGo method.
      --
      --That is, when adding entries to this table, this object
      --must be set to createAndGo(4).  The instance identifier
      --for this object will define the values of the columns 
      --that make up the index.  
      --
      --In the same PDU, the appropriate remaining columns
      --of that row must be set as well.  The agent
      --will immediately set the value of this object to
      --active(1) if the row is correct.  If not, the agent
      --will refuse the SET request and return an
      --error code.
      --
      --To modify an existing entry, it must be removed
      --and another entry with the desired changes added. 
      --
      --There may be some elements of these tables that are
      --allowed to be set while the row is active.  These
      --will be noted in the DESCRIPTION clauses for the
      --appropriate objects.
      --                   
      --To remove an entry, set the value of this object
      --to destroy(6).

      --
      -- IPX Network Number
      --
    
      IPXNET ::= OCTET STRING (SIZE(4))


      a3ipxPolControlTable  OBJECT-TYPE
          SYNTAX  SEQUENCE OF A3ipxPolControlEntry
          ACCESS  not-accessible
          STATUS  mandatory
          DESCRIPTION
                  "This table enables and disables the use of policies,
                   policy attributes and the use of trusted neighbors
                   and their attributes."
      ::= { a3ComIPXpol 1 }

      a3ipxPolControlEntry OBJECT-TYPE
          SYNTAX  A3ipxPolControlEntry
          ACCESS  not-accessible
          STATUS  mandatory
          DESCRIPTION
                 "A single entry in the Policy Control Table"
          INDEX   { a3ipxPCPort }
      ::= { a3ipxPolControlTable 1 }

      A3ipxPolControlEntry ::= SEQUENCE {
          a3ipxPCPort                 INTEGER,
          a3ipxPCRteAdvCtl            INTEGER,
          a3ipxPCRteAdvType           INTEGER,
          a3ipxPCRteRcvCtl            INTEGER,
          a3ipxPCRteRcvType           INTEGER,
          a3ipxPCSvcAdvCtl            INTEGER,
          a3ipxPCSvcAdvType           INTEGER,
          a3ipxPCSvcRcvCtl            INTEGER,
          a3ipxPCSvcRcvType           INTEGER,
          a3ipxPCNbrAdvCtl            INTEGER,
          a3ipxPCNbrRcvCtl            INTEGER,
          a3ipxPCNbrRcvType           INTEGER,
          a3ipxPCPolicyOverride       INTEGER,
          a3ipxPCSvrRplyCtl           INTEGER,
          a3ipxPCRipPolOverride       INTEGER,
          a3ipxPCSapPolOverride       INTEGER
      }

      a3ipxPCPort  OBJECT-TYPE
          SYNTAX  INTEGER
          ACCESS  read-only
          STATUS  mandatory
          DESCRIPTION
                  "The port to which this Policy Control entry applies."
      ::= { a3ipxPolControlEntry 1 }

      a3ipxPCRteAdvCtl  OBJECT-TYPE
          SYNTAX  INTEGER {
               enable  (1),
               disable (2)
          }
          ACCESS  read-write
          STATUS  mandatory
          DESCRIPTION
                  "The object enables or disables the use of the
                   'advertisable' entries in the Route Policy Table."
          DEFVAL { disable }
      ::= { a3ipxPolControlEntry 2 }

      a3ipxPCRteAdvType  OBJECT-TYPE
          SYNTAX  INTEGER {
               normal  (1),
               inverse (2)
          }
          ACCESS  read-write
          STATUS  mandatory
          DESCRIPTION
                  "The object specifies whether only those routes listed
                   as 'advertisable' in the Route Policy Table are 
                   advertised from this port (normal), or if only those 
                   routes that are not listed as 'advertisable' in the 
                   Route Policy Table are advertised (inverse)."
          DEFVAL { normal }
      ::= { a3ipxPolControlEntry 3 }

      a3ipxPCRteRcvCtl  OBJECT-TYPE
          SYNTAX  INTEGER {
               enable  (1),
               disable (2)
          }
          ACCESS  read-write
          STATUS  mandatory
          DESCRIPTION
                  "The object enables or disables the use of the
                   'receivable' entries in the Route Policy Table."
          DEFVAL { disable }
      ::= { a3ipxPolControlEntry 4 }

      a3ipxPCRteRcvType  OBJECT-TYPE
          SYNTAX  INTEGER {
               normal  (1),
               inverse (2)
          }
          ACCESS  read-write
          STATUS  mandatory
          DESCRIPTION
                  "The object specifies whether only those routes listed
                   as 'receivable' in the Route Policy Table are accepted 
                   from this port (normal), or if only those routes that 
                   are not listed as 'receivable' in the Route Policy Table
                   are accepted (inverse)."
          DEFVAL { normal }
      ::= { a3ipxPolControlEntry 5 }

      a3ipxPCSvcAdvCtl  OBJECT-TYPE
          SYNTAX  INTEGER {
               enable  (1),
               disable (2)
          }
          ACCESS  read-write
          STATUS  mandatory
          DESCRIPTION
                  "The object enables or disables the use of the
                  'advertisable' entries in the Service Policy Table."
          DEFVAL { disable }
      ::= { a3ipxPolControlEntry 6 }

      a3ipxPCSvcAdvType  OBJECT-TYPE
          SYNTAX  INTEGER {
               normal  (1),
               inverse (2)
          }
          ACCESS  read-write
          STATUS  mandatory
          DESCRIPTION
                  "The object specifies whether only those routes listed
                   as 'advertisable' in the Service Policy Table are 
                   advertised from this port (normal), or if only those 
                   routes that are not listed as 'advertisable' in the 
                   Service Policy Table are advertised (inverse)."
          DEFVAL { normal }
      ::= { a3ipxPolControlEntry 7 }

      a3ipxPCSvcRcvCtl  OBJECT-TYPE
          SYNTAX  INTEGER {
               enable  (1),
               disable (2)
          }
          ACCESS  read-write
          STATUS  mandatory
          DESCRIPTION
                  "The object enables or disables the use of the
                   'receivable' entries in the Service Policy Table."
          DEFVAL { disable }
      ::= { a3ipxPolControlEntry 8 }

      a3ipxPCSvcRcvType  OBJECT-TYPE
          SYNTAX  INTEGER {
               normal  (1),
               inverse (2)
          }
          ACCESS  read-write
          STATUS  mandatory
          DESCRIPTION
                  "The object specifies whether only those routes listed
                   as 'receivable' in the Service Policy Table are 
                   accepted from this port (normal), or if only those 
                   routes that are not listed as 'receivable' in the 
                   Service Policy Table are accepted (inverse)."
          DEFVAL { normal }
      ::= { a3ipxPolControlEntry 9 }

      a3ipxPCNbrAdvCtl  OBJECT-TYPE
          SYNTAX  INTEGER {
               enable  (1),
               disable (2)
          }
          ACCESS  read-write
          STATUS  deprecated
          DESCRIPTION
                  "This object enables or disables the use of the
                  entries in the Neighbor Policy Table that apply
                  to neighbors to which routing and service
                  reachability information is advertised.

                  In other words, this object enables or disables
                  the use of those entries in the Neighbor Policy
                  Table for which a3ipxPolNbrType = advertise(2)
                  or both(3).

                  NOTE: this object is not supported by NETBuilders
                  running sw version 8.0 and greater.  Its functionality
                  has been replaced by a3ipxRipPolNbrCtlTable and
                  a3ipxSapPolNbrCtlTable."
          DEFVAL { disable }
      ::= { a3ipxPolControlEntry 10 }

      a3ipxPCNbrRcvCtl  OBJECT-TYPE
          SYNTAX  INTEGER {
               enable  (1),
               disable (2)
          }
          ACCESS  read-write
          STATUS  deprecated
          DESCRIPTION
                  "The object enables or disables the use of the
                  entries in the Neighbor Policy Table that apply
                  to neighbors from which routing and service
                  reachability information is allowed to be received.

                  In other words, this object enables or disables
                  the use of those entries in the Neighbor Policy
                  Table for which a3ipxPolNbrType = receive(2)
                  or both(3).

                  NOTE: this object is not supported by NETBuilders
                  running sw version 8.0 and greater.  Its functionality
                  has been replaced by a3ipxRipPolNbrCtlTable and
                  a3ipxSapPolNbrCtlTable."
          DEFVAL { disable }
      ::= { a3ipxPolControlEntry 11 }

      a3ipxPCNbrRcvType  OBJECT-TYPE
          SYNTAX  INTEGER {
               normal  (1),
               inverse (2)
          }
          ACCESS  read-write
          STATUS  deprecated
          DESCRIPTION
                  "If this object is set to normal(1), then route
                  and service reachability information is accepted
                  only from those neighbors listed in the Neighbor
                  Policy Table for which a3ipxPolNbrType = receive(2)
                  or both(3).

                  If this object is set to inverse(2), then route
                  and service reachability information is accepted
                  from any neighbor except those neighbors listed
                  in the Neighbor Policy Table for which 
                  a3ipxPolNbrType = receive(2) or both(3).

                  NOTE: this object is not supported by NETBuilders
                  running sw version 8.0 and greater.  Its functionality
                  has been replaced by a3ipxRipPolNbrCtlTable and
                  a3ipxSapPolNbrCtlTable."
          DEFVAL { normal }
      ::= { a3ipxPolControlEntry 12 }

      a3ipxPCPolicyOverride OBJECT-TYPE
          SYNTAX  INTEGER {
                     policyOverride (1),
                     noPolicyOverride (2)
          }
          ACCESS  read-write
          STATUS  deprecated
          DESCRIPTION
                  "Policy Override is used to override the configured 
                  policies when the router issues responses to specific
                  RIP or SAP requests.   The configured policies are
                  always applied for regular RIP or SAP updates.

                  NOTE: this object is no longer support by NETBuilders 
                  running sw version 8.0 and greater.  Its functionality
                  has been replaced by a3ipxPCRipPolOverride and 
                  a3ipxPCSapPolOverride."
          DEFVAL { noPolicyOverride }
      ::= { a3ipxPolControlEntry 13 }

      a3ipxPCSvrRplyCtl OBJECT-TYPE
          SYNTAX  INTEGER {
                     bestSvrReply   (1),
                     noBestSvrReply (2)
          }
          ACCESS  read-write
          STATUS  mandatory
          DESCRIPTION
                  "This controls whether or not the router is
                  permitted to respond to 'get nearest server'
                  requests.  If this object has the value
                  bestSvrReply(1), then this router is permitted
                  to respond to these requests.  If this object
                  has the value noBestSvrReply(2), this this
                  router is not permitted to respond to these
                  requests." 
      ::= { a3ipxPolControlEntry 14 }

      a3ipxPCRipPolOverride OBJECT-TYPE
          SYNTAX  INTEGER {
                     policyOverride (1),
                     noPolicyOverride (2)
          }
          ACCESS  read-write
          STATUS  mandatory
          DESCRIPTION
                  "RIP Policy Override is used to override the configured 
                  RIP policies when the router issues responses to specific
                  RIP requests.   The configured policies are always 
                  applied for regular RIP updates."
          DEFVAL { noPolicyOverride }
      ::= { a3ipxPolControlEntry 15 }

      a3ipxPCSapPolOverride OBJECT-TYPE
          SYNTAX  INTEGER {
                     policyOverride (1),
                     noPolicyOverride (2)
          }
          ACCESS  read-write
          STATUS  mandatory
          DESCRIPTION
                  "SAP Policy Override is used to override the configured 
                  policies when the router issues responses to specific
                  SAP requests.   The configured policies are always 
                  applied for regular SAP updates."
          DEFVAL { noPolicyOverride }
      ::= { a3ipxPolControlEntry 16 }



      a3ipxPolRteTable OBJECT-TYPE
          SYNTAX  SEQUENCE OF A3ipxPolRteEntry
          ACCESS  not-accessible
          STATUS  mandatory
          DESCRIPTION
                 "The IPX Route Policy Table controls the acceptance
                 of route reachability information from neighbors and
                 the advertisement of route reachability information
                 to neighbors.

                 If a3ipxPCRteRcvType is configured as normal, a route
                 is accepted if the network number for the route is in
                 the list of 'receivable' networks specified in this
                 table.  If a3ipxPCRteRcvType is configure as inverse, a
                 route is not accepted if the network number for the 
                 route is in the list of 'receivable' networks specified 
                 in this table.

                 If a3ipxPCRteAdvType is configured as normal, a route
                 is advertised if the network number for the route is in
                 the list of 'advertisable' networks specified in this
                 table.  If a3ipxPCRteAdvType is configure as inverse, a
                 route is not advertised if the network number for the 
                 route is in the list of 'advertisable' networks specified 
                 in this table.

                 Note, since this table allows ranges of routes to be
                 specified, all the entries should be examined when
                 determining if a specific route is affected by these
                 policies.  It is not sufficient to search for an instance
                 of a3ipxPolRteNet1 that matches the route in question."
      ::= { a3ComIPXpol 2 }

      a3ipxPolRteEntry OBJECT-TYPE
          SYNTAX  A3ipxPolRteEntry
          ACCESS  not-accessible
          STATUS  mandatory
          DESCRIPTION
                 "A single entry in the Route Policy table"
          INDEX   { a3ipxPolRtePort, a3ipxPolRteNet1, a3ipxPolRteNet2 }
      ::= { a3ipxPolRteTable 1 }

      A3ipxPolRteEntry ::= SEQUENCE {
          a3ipxPolRtePort       INTEGER,
          a3ipxPolRteType       INTEGER,
          a3ipxPolRteNet1       IPXNET,
          a3ipxPolRteNet2       IPXNET,
          a3ipxPolRteStatus     RowStatus
      }

      a3ipxPolRtePort OBJECT-TYPE
          SYNTAX  INTEGER
          ACCESS  read-only
          STATUS  mandatory
          DESCRIPTION
                  "The IPX port to which this Receive Route Policy
                  entry applies."
      ::= { a3ipxPolRteEntry 1 }

      a3ipxPolRteType  OBJECT-TYPE
          SYNTAX  INTEGER {
                     advertise (1),
                     receive   (2),
                     both      (3)
          }
          ACCESS  read-write
          STATUS  mandatory
          DESCRIPTION
                  "This object specifies whether this entry applies
                  to receiving routes, advertising routes, or both."
      ::= { a3ipxPolRteEntry 2 }
                   
      a3ipxPolRteNet1 OBJECT-TYPE
          SYNTAX  IPXNET
          ACCESS  read-only
          STATUS  mandatory
          DESCRIPTION
                  "The IPX Network Number for which route information
                  is accepted or rejected for this port.  The value
                  0xfffffffe is used to represent the default route."
      ::= { a3ipxPolRteEntry 3 }

      a3ipxPolRteNet2 OBJECT-TYPE
          SYNTAX  IPXNET
          ACCESS  read-only
          STATUS  mandatory
          DESCRIPTION
                  "When the value of this object is a valid IPX
                  network and different from a3ipxPolRteNet1, then 
                  this table entries specifies a range of IPX 
                  networks, with the value of a3ipxPolRteNet1 
                  identifying the lower end of the range.

                  If the value of this object is the same as 
                  a3ipxPolRteNet1, then this table entry 
                  specifies a single IPX network identified by 
                  the value of a3ipxPolRteNet1."
      ::= { a3ipxPolRteEntry 4 }

      a3ipxPolRteStatus OBJECT-TYPE
          SYNTAX RowStatus
          ACCESS read-write
          STATUS mandatory
          DESCRIPTION
                 "This object is used to add and delete entries
                 in this table.  See the notes describing
                 RowStatus at the beginning of this MIB."
      ::= { a3ipxPolRteEntry 5 }





      a3ipxPolSvcTable OBJECT-TYPE
          SYNTAX  SEQUENCE OF A3ipxPolSvcEntry
          ACCESS  not-accessible
          STATUS  mandatory
          DESCRIPTION
                 "The IPX Policy Services Table controls the acceptance
                 of service reachability information from neighbors
                 and the advertisement of that information to neighbors.

                 If a3ipxPCSvcRcvType is configured as normal, a service
                 is accepted if its port number, server name, and
                 service type is in the list of tuples specified as 
                 'receivable' by this table.  If a3ipxPCSvcRcvType is 
                 configured as inverse, a service is not accepted if its 
                 port number, server name, and service type is in 
                 the list of tuples specified as 'receivable' by this 
                 table.

                 If a3ipxPCSvcAdvType is configured as normal, a service
                 is advertised if its network port, server name, and
                 service type is in the list of tuples specified as 
                 'advertisable' by this table.  If a3ipxPCSvcAdvType is 
                 configured as inverse, a service is not advertised if its 
                 port number, server name, and service type is in 
                 the list of tuples specified as 'advertisable' by this 
                 table."
      ::= { a3ComIPXpol 3 }

      a3ipxPolSvcEntry OBJECT-TYPE
          SYNTAX  A3ipxPolSvcEntry
          ACCESS  not-accessible
          STATUS  mandatory
          DESCRIPTION
                 "A single entry in the Receive Services Policy table."
          INDEX   { a3ipxPolSvcPort, a3ipxPolSvcSvrName, a3ipxPolSvcType }
      ::= { a3ipxPolSvcTable 1 }

      A3ipxPolSvcEntry ::= SEQUENCE {
          a3ipxPolSvcPort      INTEGER,
          a3ipxPolSvcEntryType INTEGER,
          a3ipxPolSvcSvrName   DisplayString,
          a3ipxPolSvcType      OCTET STRING (SIZE(2)),
          a3ipxPolSvcStatus    RowStatus
      }

      a3ipxPolSvcPort OBJECT-TYPE
          SYNTAX  INTEGER
          ACCESS  read-only
          STATUS  mandatory
          DESCRIPTION
                  "The IPX port to which this Receive Svc Pol
                  entry applies."
      ::= { a3ipxPolSvcEntry 1 }

      a3ipxPolSvcEntryType  OBJECT-TYPE
          SYNTAX  INTEGER {
                     advertise (1),
                     receive   (2),
                     both      (3)
          }
          ACCESS  read-write
          STATUS  mandatory
          DESCRIPTION
                  "This object specifies whether this entry applies
                  to receiving services, advertising services, or both."
      ::= { a3ipxPolSvcEntry 2 }

      a3ipxPolSvcSvrName OBJECT-TYPE
          SYNTAX  DisplayString (SIZE(0..15))
          ACCESS  read-only
          STATUS  mandatory
          DESCRIPTION
                  "This object contains the name of a server.  

                  A single wildcard (*) is allowed at the end of
                  the name."
      ::= { a3ipxPolSvcEntry 3 }
       
      a3ipxPolSvcType OBJECT-TYPE
          SYNTAX  OCTET STRING (SIZE(2))
          ACCESS  read-only
          STATUS  mandatory
          DESCRIPTION
                  "The type of service for which information is accepted
                  or rejected by this port. The value 'FFFF' acts
                  as a wildcard for all service types."
      ::= { a3ipxPolSvcEntry 4 }

      a3ipxPolSvcStatus OBJECT-TYPE
          SYNTAX RowStatus
          ACCESS read-write
          STATUS mandatory
          DESCRIPTION
                 "This object is used to add and delete entries
                 in this table.  See the notes describing
                 RowStatus at the beginning of this MIB."
      ::= { a3ipxPolSvcEntry 5 }



      a3ipxPolNbrTable OBJECT-TYPE
          SYNTAX  SEQUENCE OF A3ipxPolNbrEntry
          ACCESS  not-accessible 
          STATUS  deprecated
          DESCRIPTION
                  "This table defines a set of neighbors to which
                   the route and service reachability information is 
                   advertised.  This table also defines a set of
                   neighbors from which route and service reachability
                   information is accepted.

                   NOTE: this table is not supported by NETBuilders
                   running sw version 8.0 and greater.  The functionality
                   provided by this table has been replaced by
                   a3ipxPolRipNbrTable and a3ipxPolSapNbrTable."
      ::= { a3ComIPXpol 4 }

      a3ipxPolNbrEntry OBJECT-TYPE
          SYNTAX  A3ipxPolNbrEntry
          ACCESS  not-accessible
          STATUS  deprecated
          DESCRIPTION
                 "A single entry in the Policy Neighbor Table"
          INDEX   { a3ipxPolNbrPort, a3ipxPolNbrNet, a3ipxPolNbrAddress }
      ::= { a3ipxPolNbrTable 1 }

      A3ipxPolNbrEntry ::= SEQUENCE {
          a3ipxPolNbrPort      INTEGER,
          a3ipxPolNbrType      INTEGER,
          a3ipxPolNbrNet       IPXNET,
          a3ipxPolNbrAddress   MacAddress,
          a3ipxPolNbrStatus    RowStatus
      }

      a3ipxPolNbrPort OBJECT-TYPE
          SYNTAX  INTEGER
          ACCESS  read-only
          STATUS  deprecated
          DESCRIPTION
                  "The IPX port over which the Trusted Neighbor identified
                   by this table entry can be reached."
      ::= { a3ipxPolNbrEntry 1 }

      a3ipxPolNbrType OBJECT-TYPE
          SYNTAX  INTEGER {
                     advertise (1),
                     receive   (2),
                     both      (3)
          }
          ACCESS  read-write
          STATUS  deprecated
          DESCRIPTION
                  "This object specifies whether this entry applies
                  to receiving information, advertising information, 
                  or both."
      ::= { a3ipxPolNbrEntry 2 }

      a3ipxPolNbrNet OBJECT-TYPE
          SYNTAX  IPXNET
          ACCESS  read-only
          STATUS  deprecated
          DESCRIPTION
                  "The IPX Network number identifying the network
                  to which the neighbor identified by this table
                  entry is attached."
      ::= { a3ipxPolNbrEntry 3 }

      a3ipxPolNbrAddress OBJECT-TYPE
          SYNTAX  MacAddress
          ACCESS  read-only
          STATUS  deprecated
          DESCRIPTION
                  "The Mac Address of the Neighbor to whom route and service
                  reachability information is to be advertised and from which
                  route and service reachability information is accepted."
      ::= { a3ipxPolNbrEntry 4 }

      a3ipxPolNbrStatus OBJECT-TYPE
          SYNTAX RowStatus
          ACCESS read-write
          STATUS deprecated
          DESCRIPTION
                 "This object is used to add and delete entries
                 in this table.  See the notes describing
                 RowStatus at the beginning of this MIB."
      ::= { a3ipxPolNbrEntry 5 }


--
-- This next section controls the configuration of IPX Neighbors
-- that are sent RIP and SAP updates as well as those IPX
-- Neighbors from which RIP and SAP updates are accepted.
--

--
--    These next two tables are RIP specific
--

      a3ipxPolRipNbrCtlTable OBJECT-TYPE
          SYNTAX SEQUENCE OF A3ipxPolRipNbrCtlEntry
          ACCESS not-accessible
          STATUS mandatory
          DESCRIPTION
                 "This table enables or disables the use of
                 the entries in a3ipxPolRipNbrTable.  If
                 the use of the entries in that table is enabled,
                 this table also controls how they are interpreted.
                 In one case, RIP updates are accepted only from those 
                 IPX Neighbors listed in a3ipxPolRipNbrTable.  In the
                 other case, RIP updates are accepted only from those
                 IPX Neighbors not listed in a3ipxPolRipNbrTable."
      ::= { a3ipxPolNbr 1 }

      a3ipxPolRipNbrCtlEntry OBJECT-TYPE
          SYNTAX A3ipxPolRipNbrCtlEntry
          ACCESS not-accessible
          STATUS mandatory
          DESCRIPTION
                 "Each entry in this table applies to a separate
                 NETBuilder port and controls those entries in
                 a3ipxPolRipNbrTable that correspond to the same
                 port." 
          INDEX { a3ipxPolRipNbrCtlPort }
      ::= { a3ipxPolRipNbrCtlTable 1 }

      A3ipxPolRipNbrCtlEntry ::= SEQUENCE {
          a3ipxPolRipNbrCtlPort       INTEGER,
          a3ipxPolRipNbrCtlAdvCtl     INTEGER,
          a3ipxPolRipNbrCtlRcvCtl     INTEGER,
          a3ipxPolRipNbrCtlRcvType    INTEGER
      }

      a3ipxPolRipNbrCtlPort OBJECT-TYPE
          SYNTAX INTEGER
          ACCESS read-only
          STATUS mandatory
          DESCRIPTION
                 "This NETBuilder port to which this RIP Neighbor
                 Control entry applies."
      ::= { a3ipxPolRipNbrCtlEntry 1 } 

      a3ipxPolRipNbrCtlAdvCtl OBJECT-TYPE
          SYNTAX INTEGER {               
               enable  (1),
               disable (2)
          }
          ACCESS  read-write
          STATUS  mandatory
          DESCRIPTION
                  "This object enables or disables the use of the
                  entries in the RIP Neighbor Policy Table 
                  (a3ipxPolRipNbrTable) that apply to neighbors 
                  to which routing information is advertised.

                  In other words, this object enables or disables
                  the use of those entries in the Neighbor Policy
                  Table for which a3ipxPolRipNbrType = advertise(2)
                  or both(3)."
          DEFVAL { disable }
      ::= { a3ipxPolRipNbrCtlEntry 2 } 

      a3ipxPolRipNbrCtlRcvCtl OBJECT-TYPE
          SYNTAX  INTEGER {
               enable  (1),
               disable (2)
          }
          ACCESS  read-write
          STATUS  mandatory
          DESCRIPTION
                  "The object enables or disables the use of the
                  entries in the Neighbor Policy Table that apply
                  to neighbors from which routing information is 
                  allowed to be received.

                  In other words, this object enables or disables
                  the use of those entries in the Neighbor Policy
                  Table for which a3ipxPolRipNbrType = receive(2)
                  or both(3)."
          DEFVAL { disable }
      ::= { a3ipxPolRipNbrCtlEntry 3 } 

      a3ipxPolRipNbrCtlRcvType OBJECT-TYPE
          SYNTAX  INTEGER {
               normal  (1),
               inverse (2)
          }
          ACCESS  read-write
          STATUS  mandatory
          DESCRIPTION
                  "If this object is set to normal(1), then route
                  information is accepted only from those neighbors 
                  listed in the Neighbor Policy Table for which 
                  a3ipxPolRipNbrType = receive(2) or both(3).

                  If this object is set to inverse(2), then route
                  information is accepted from any neighbor except 
                  those neighbors listed in the Neighbor Policy Table 
                  for which a3ipxPolRipNbrType = receive(2) or both(3)."
          DEFVAL { normal }
      ::= { a3ipxPolRipNbrCtlEntry 4 } 


      a3ipxPolRipNbrTable OBJECT-TYPE
          SYNTAX  SEQUENCE OF A3ipxPolRipNbrEntry
          ACCESS  not-accessible
          STATUS  mandatory
          DESCRIPTION
                  "This table defines a set of neighbors to which
                   the route information is advertised.  This table 
                   also defines a set of neighbors from which route 
                   information is accepted."
      ::= { a3ipxPolNbr 2 }

      a3ipxPolRipNbrEntry OBJECT-TYPE
          SYNTAX  A3ipxPolRipNbrEntry
          ACCESS  not-accessible
          STATUS  mandatory
          DESCRIPTION
                 "A single entry in the Policy Neighbor Table"
          INDEX   { a3ipxPolRipNbrPort, a3ipxPolRipNbrNet, a3ipxPolRipNbrAddress }
      ::= { a3ipxPolRipNbrTable 1 }

      A3ipxPolRipNbrEntry ::= SEQUENCE {
          a3ipxPolRipNbrPort     INTEGER,
          a3ipxPolRipNbrType     INTEGER,
          a3ipxPolRipNbrNet      IPXNET,
          a3ipxPolRipNbrAddress  MacAddress,
          a3ipxPolRipNbrStatus   RowStatus
      }

      a3ipxPolRipNbrPort OBJECT-TYPE
          SYNTAX  INTEGER
          ACCESS  read-only
          STATUS  mandatory
          DESCRIPTION
                  "The IPX port over which the Trusted Neighbor identified
                   by this table entry can be reached."
      ::= { a3ipxPolRipNbrEntry 1 }

      a3ipxPolRipNbrType OBJECT-TYPE
          SYNTAX  INTEGER {
                     advertise (1),
                     receive   (2),
                     both      (3)
          }
          ACCESS  read-write
          STATUS  mandatory
          DESCRIPTION
                  "This object specifies whether this entry applies
                  to receiving information, advertising information,
                  or both."
      ::= { a3ipxPolRipNbrEntry 2 }

      a3ipxPolRipNbrNet OBJECT-TYPE
          SYNTAX  IPXNET
          ACCESS  read-only
          STATUS  mandatory
          DESCRIPTION
                  "The IPX Network number identifying the network
                  to which the neighbor identified by this table
                  entry is attached."
      ::= { a3ipxPolRipNbrEntry 3 }

      a3ipxPolRipNbrAddress OBJECT-TYPE
          SYNTAX  MacAddress
          ACCESS  read-only
          STATUS  mandatory
          DESCRIPTION
                  "The Mac Address of the Neighbor to whom route 
                  information is to be advertised and from which
                  route information is accepted."
      ::= { a3ipxPolRipNbrEntry 4 }

      a3ipxPolRipNbrStatus OBJECT-TYPE
          SYNTAX RowStatus
          ACCESS read-write
          STATUS mandatory
          DESCRIPTION
                 "This object is used to add and delete entries
                 in this table.  See the notes describing
                 RowStatus at the beginning of this MIB."
      ::= { a3ipxPolRipNbrEntry 5 }



--
-- These next two tables are SAP specific
--

      a3ipxPolSapNbrCtlTable OBJECT-TYPE
          SYNTAX SEQUENCE OF A3ipxPolSapNbrCtlEntry
          ACCESS not-accessible
          STATUS mandatory
          DESCRIPTION
                 "This table enables or disables the use of
                 the entries in a3ipxPolSapNbrTable.  If
                 the use of the entries in that table is enabled,
                 this table also controls how they are interpreted.
                 In one case, SAP updates are accepted only from those 
                 IPX Neighbors listed in a3ipxPolSapNbrTable.  In the
                 case, SAP updates are accepted only from those
                 IPX Neighbors not listed in a3ipxPolSapNbrTable."
      ::= { a3ipxPolNbr 3 }

      a3ipxPolSapNbrCtlEntry OBJECT-TYPE
          SYNTAX A3ipxPolSapNbrCtlEntry
          ACCESS not-accessible
          STATUS mandatory
          DESCRIPTION
                 "Each entry in this table applies to a separate
                 NETBuilder port and controls those entries in
                 a3ipxPolSapNbrTable that correspond to the same
                 port." 
          INDEX { a3ipxPolSapNbrCtlPort }
      ::= { a3ipxPolSapNbrCtlTable 1 }

      A3ipxPolSapNbrCtlEntry ::= SEQUENCE {
          a3ipxPolSapNbrCtlPort       INTEGER,
          a3ipxPolSapNbrCtlAdvCtl     INTEGER,
          a3ipxPolSapNbrCtlRcvCtl     INTEGER,
          a3ipxPolSapNbrCtlRcvType    INTEGER
      }

      a3ipxPolSapNbrCtlPort OBJECT-TYPE
          SYNTAX INTEGER
          ACCESS read-only
          STATUS mandatory
          DESCRIPTION
                 "This NETBuilder port to which this SAP Neighbor
                 Control entry applies."
      ::= { a3ipxPolSapNbrCtlEntry 1 } 

      a3ipxPolSapNbrCtlAdvCtl OBJECT-TYPE
          SYNTAX INTEGER {               
               enable  (1),
               disable (2)
          }
          ACCESS  read-write
          STATUS  mandatory
          DESCRIPTION
                  "This object enables or disables the use of the
                  entries in the SAP Neighbor Policy Table 
                  (a3ipxPolSapNbrTable) that apply to neighbors 
                  to which service reachability information 
                  is advertised.

                  In other words, this object enables or disables
                  the use of those entries in the Neighbor Policy
                  Table for which a3ipxPolSapNbrType = advertise(2)
                  or both(3)."
          DEFVAL { disable }
      ::= { a3ipxPolSapNbrCtlEntry 2 } 

      a3ipxPolSapNbrCtlRcvCtl OBJECT-TYPE
          SYNTAX  INTEGER {
               enable  (1),
               disable (2)
          }
          ACCESS  read-write
          STATUS  mandatory
          DESCRIPTION
                  "The object enables or disables the use of the
                  entries in the Neighbor Policy Table that apply
                  to neighbors from which service reachability 
                  information is allowed to be received.

                  In other words, this object enables or disables
                  the use of those entries in the Neighbor Policy
                  Table for which a3ipxPolSapNbrType = receive(2)
                  or both(3)."
          DEFVAL { disable }
      ::= { a3ipxPolSapNbrCtlEntry 3 } 

      a3ipxPolSapNbrCtlRcvType OBJECT-TYPE
          SYNTAX  INTEGER {
               normal  (1),
               inverse (2)
          }
          ACCESS  read-write
          STATUS  mandatory
          DESCRIPTION
                  "If this object is set to normal(1), then 
                  service reachability information is accepted
                  only from those neighbors listed in the Neighbor
                  Policy Table for which a3ipxPolSapNbrType = receive(2)
                  or both(3).

                  If this object is set to inverse(2), then 
                  service reachability information is accepted
                  from any neighbor except those neighbors listed
                  in the Neighbor Policy Table for which
                  a3ipxPolSapNbrType = receive(2) or both(3)."
          DEFVAL { normal }
      ::= { a3ipxPolSapNbrCtlEntry 4 } 


      a3ipxPolSapNbrTable OBJECT-TYPE
          SYNTAX  SEQUENCE OF A3ipxPolSapNbrEntry
          ACCESS  not-accessible
          STATUS  mandatory
          DESCRIPTION
                  "This table defines a set of neighbors to which
                   the service reachability information is advertised.  
                   This table also defines a set of neighbors from which 
                   service reachability information is accepted."
      ::= { a3ipxPolNbr 4 }

      a3ipxPolSapNbrEntry OBJECT-TYPE
          SYNTAX  A3ipxPolSapNbrEntry
          ACCESS  not-accessible
          STATUS  mandatory
          DESCRIPTION
                 "A single entry in the Policy Neighbor Table"
          INDEX   { a3ipxPolSapNbrPort, a3ipxPolSapNbrNet, a3ipxPolSapNbrAddress }
      ::= { a3ipxPolSapNbrTable 1 }

      A3ipxPolSapNbrEntry ::= SEQUENCE {
          a3ipxPolSapNbrPort     INTEGER,
          a3ipxPolSapNbrType     INTEGER,
          a3ipxPolSapNbrNet      IPXNET,
          a3ipxPolSapNbrAddress  MacAddress,
          a3ipxPolSapNbrStatus   RowStatus
      }

      a3ipxPolSapNbrPort OBJECT-TYPE
          SYNTAX  INTEGER
          ACCESS  read-only
          STATUS  mandatory
          DESCRIPTION
                  "The IPX port over which the Trusted Neighbor identified
                   by this table entry can be reached."
      ::= { a3ipxPolSapNbrEntry 1 }

      a3ipxPolSapNbrType OBJECT-TYPE
          SYNTAX  INTEGER {
                     advertise (1),
                     receive   (2),
                     both      (3)
          }
          ACCESS  read-write
          STATUS  mandatory
          DESCRIPTION
                  "This object specifies whether this entry applies
                  to receiving information, advertising information,
                  or both."
      ::= { a3ipxPolSapNbrEntry 2 }

      a3ipxPolSapNbrNet OBJECT-TYPE
          SYNTAX  IPXNET
          ACCESS  read-only
          STATUS  mandatory
          DESCRIPTION
                  "The IPX Network number identifying the network
                  to which the neighbor identified by this table
                  entry is attached."
      ::= { a3ipxPolSapNbrEntry 3 }

      a3ipxPolSapNbrAddress OBJECT-TYPE
          SYNTAX  MacAddress
          ACCESS  read-only
          STATUS  mandatory
          DESCRIPTION
                  "The Mac Address of the Neighbor to whom service
                  reachability information is to be advertised and from which
                  service reachability information is accepted."
      ::= { a3ipxPolSapNbrEntry 4 }

      a3ipxPolSapNbrStatus OBJECT-TYPE
          SYNTAX RowStatus
          ACCESS read-write
          STATUS mandatory
          DESCRIPTION
                 "This object is used to add and delete entries
                 in this table.  See the notes describing
                 RowStatus at the beginning of this MIB."
      ::= { a3ipxPolSapNbrEntry 5 }


END

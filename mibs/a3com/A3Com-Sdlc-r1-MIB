A3Com-Sdlc-r1-MIB DEFINITIONS ::= BEGIN

IMPORTS
    enterprises, Counter, TimeTicks
        FROM RFC1155-SMI
		  
	Integer32 FROM SNMPv2-SMI

    TRAP-TYPE 
        FROM RFC-1215

    DisplayString, ifIndex, ifAdminStatus, ifOperStatus
        FROM RFC1213-MIB

    OBJECT-TYPE
        FROM RFC-1212;

--
--  The following data link controls are modelled in this MIB module:
--
--     1. SDLC
--

a3com       OBJECT IDENTIFIER ::= { enterprises 43 }
brouterMIB  OBJECT IDENTIFIER ::= { a3com 2 }
sdlc        OBJECT IDENTIFIER ::= { brouterMIB 25 }

-- All representations of MAC addresses in this MIB Module use,
-- as a textual convention (i.e. this convention does not affect
-- their encoding), the data type:

MacAddress ::= OCTET STRING (SIZE(6))

-- indistinguishable from INTEGER, but never needs more than
-- 32-bits for a two's complement representation
-- [Next line commented out by HP to work with 4.1 version of xnmloadmib]
-- Integer32 ::= INTEGER (-2147483648..2147483647)

--
--  THE SDLC GROUP
--  ==============
--
--  The following resources are modelled in the SDLC group of this
--  MIB module:
--
--     1. PORTS
--     2. LINK STATIONS
--     3. MAPS (3COM PROPRIETARY)

sdlcPortGroup OBJECT IDENTIFIER ::= { sdlc 1 } -- Physical Ports
sdlcLSGroup   OBJECT IDENTIFIER ::= { sdlc 2 } -- Logical Link Stations

sdlcMapGroup  OBJECT IDENTIFIER ::= { sdlc 3 } -- Link Conversion Mappings

--
--  THE SDLC PORT GROUP
--  ===================
--
--  The following classes of information is modelled for each SDLC port:
--
--     1.  ADMINISTRATIVE ( read/write)
--     2.  OPERATIONAL    ( read-only)
--     3.  STATISTICS     ( read-only)

--  Information not found in this group is found in tables described in
--  the following RFCs:
--
--    1.  RFC1213  - MIB-II
--
--            TABLE                      INDEX
--            ====================       ====================
--        a.  ifTable                    ifIndex
--
--    2.  RFC1659  - The RS232-like MIB
--
--            TABLE                      INDEX
--            ====================       ====================
--        a.  rs232PortTable             rs232PortIndex
--        b.  rs232SyncPortTable         rs232SyncPortIndex
--        c.  rs232InSigTable            rs232InSigPortIndex,
--                                       rs232InSigName
--        d.  rs232OutSigTable           rs232OutSigPortIndex,
--                                       rs232OutSigName
--     ** e.  rs232AsyncPortTable        rs232AsyncPortIndex
--
--     ** rs232AsyncPortTable for ISO 3309.3 ( Start-Stop SDLC).


--  *************************************************************
--  *                                                           *
--  *           THE SDLC PORT ADMINISTRATIVE TABLE              *
--  *                                                           *
--  *************************************************************

sdlcPortAdminTable  OBJECT-TYPE
                    SYNTAX      SEQUENCE OF SdlcPortAdminEntry
                    ACCESS      not-accessible
                    STATUS      mandatory
                    DESCRIPTION
                        "This table contains objects that can be
                        changed to manage an SDLC port.    Changing one
                        of these parameters may take effect in the
                        operating port immediately or may wait until
                        the interface is restarted depending on the
                        details of the implementation.

                        Most of the objects in this read-write table
                        have corresponding read-only objects in the
                        sdlcPortOperTable that return the current
                        operating value.

                        The operating values may be different from
                        these configured values if  a configured
                        parameter was changed after the interface was
                        started."

                     ::= { sdlcPortGroup 1 }

sdlcPortAdminEntry  OBJECT-TYPE
                    SYNTAX      SdlcPortAdminEntry
                    ACCESS      not-accessible
                    STATUS      mandatory
                    DESCRIPTION
                        "A list of configured values for an SDLC port."
                    INDEX   { ifIndex }

                    ::= { sdlcPortAdminTable 1 }

SdlcPortAdminEntry  ::= SEQUENCE
                {
                        sdlcPortAdminName           DisplayString,
                        sdlcPortAdminRole           INTEGER,
                        sdlcPortAdminType           INTEGER,
                        sdlcPortAdminTopology       INTEGER,
                        sdlcPortAdminACTIVTO        TimeTicks,
                        sdlcPortAdminPAUSE          TimeTicks,
                        sdlcPortAdminSlowPollTimer  TimeTicks
                }

sdlcPortAdminName   OBJECT-TYPE
                    SYNTAX      DisplayString (SIZE (1..10))
                    ACCESS      read-only
                    STATUS      mandatory
                    DESCRIPTION
                        "An octet string that defines the physical port
                        to which this interface is assigned.  It has
                        implementation-specific significance. Its value
                        shall be unique within the administered
                        system.  It must contain only ASCII printable
                        characters.  Should an implementation choose to
                        accept a write operation  for this object, it
                        causes the logical port definition associated
                        with the table instance to be moved to  a
                        different physical port.  A write operation
                        shall not take effect until the port is cycled
                        inactive."

                    ::= { sdlcPortAdminEntry 1 }

sdlcPortAdminRole   OBJECT-TYPE
                    SYNTAX      INTEGER
                    {
                        primary(1),
                        secondary(2),
                        negotiable(3)
                    }
                    ACCESS      read-write
                    STATUS      mandatory
                    DESCRIPTION
                        "This object describes the role that the link
                        station shall assume the next time a connection
                        is established.

                        Even though this is defined as a port object,
                        it is a link station attribute in the sense
                        that a role is per link station.  However, it
                        is not possible to vary link station roles on a
                        particular port.  For example, if an SDLC port
                        is configured to primary, all link stations on
                        that port must be primary."

                    ::= { sdlcPortAdminEntry 2 }

sdlcPortAdminType   OBJECT-TYPE
                    SYNTAX      INTEGER
                    {
                         leased(1),
                         switched(2)
                    }
                    ACCESS      read-write
                    STATUS      mandatory
                    DESCRIPTION
                        "This parameter defines whether the SDLC port
                        is to connect to a leased or switched line.  A
                        write operation to this administrative  value
                        shall not take effect until the SDLC port has
                        been cycled inactive."
                    DEFVAL { leased }

                    ::= { sdlcPortAdminEntry 3 }

sdlcPortAdminTopology  OBJECT-TYPE
                    SYNTAX      INTEGER
                    {
                         pointToPoint(1),
                         multipoint(2)
                    }
                    ACCESS      read-write
                    STATUS      mandatory
                    DESCRIPTION
                        "This parameter defines whether the SDLC port is
                        capable of operating in either a point-to-point
                        or multipoint topology.

                        sdlcPortAdminTopology == multipoint implies the
                        port can also operate in a point-to-point
                        topology.  sdlcPortAdminTopology ==
                        pointToPoint does not imply the port can
                        operate in a multipoint topology.

                        A write operation to this administrative value
                        shall not take effect until the SDLC port has
                        been cycled inactive."
                    DEFVAL { pointToPoint }

                    ::= { sdlcPortAdminEntry 4 }

sdlcPortAdminACTIVTO    OBJECT-TYPE
                    SYNTAX      TimeTicks
                    ACCESS      read-write
                    STATUS      mandatory
                    DESCRIPTION
                        "This parameter defines the period of time (in
                        1/100ths of a second) that the port will allow a
                        switched line to remain inactive before
                        disconnecting.  A switched line is considered
                        to be inactive if there are no I-Frames being
                        transferred.  A value of zero indicates no
                        timeout.  Depending on the implementation, a
                        write operation to this administered value may
                        not take effect until the port is cycled
                        inactive.

                        This object only has meaning for SDLC ports
                        where sdlcPortAdminType == switched

                        The object descriptor contains the name of an
                        NCP configuration parameter, ACTIVTO.  Please
                        note that the value of this object represents
                        1/100ths of a second while the NCP ACTIVTO is
                        represented in seconds."
                    DEFVAL { 0 }

                    ::= { sdlcPortAdminEntry 5 }

sdlcPortAdminPAUSE  OBJECT-TYPE
                    SYNTAX      TimeTicks
                    ACCESS      read-write
                    STATUS      mandatory
                    DESCRIPTION
                        "This object defines the minimum elapsed time
                        (in 1/100ths of a second) between any two
                        traversals of the poll list for a primary SDLC
                        port.  Depending on the implementation, a write
                        operation to this administered value  may not
                        take effect until the port is cycled inactive.

                        The object descriptor contains the name of an
                        NCP configuration parameter, PAUSE.  Please
                        note that the value of this object represents
                        1/100ths of a second while the NCP PAUSE is
                        represented in 1/10ths of a second.

                        This object only has meaning for SDLC ports
                        where sdlcPortAdminRole == primary "
                    DEFVAL { 200 }

                    ::= { sdlcPortAdminEntry 6 }

sdlcPortAdminSlowPollTimer OBJECT-TYPE
                    SYNTAX      TimeTicks
                    ACCESS      read-write
                    STATUS      mandatory
                    DESCRIPTION
                        "This object describes the elapsed time (in
                        1/100ths of a second) between polls for failed
                        secondary link station addresses.  Depending
                        on the implementation, a write operation to
                        this administered value  may not take effect
                        until the port is cycled inactive.

                        This object only has meaning for SDLC ports
                        where
                            sdlcPortAdminRole == primary
                        and
                            sdlcPortAdminTopology == multipoint "
                    DEFVAL { 2000 }

                    ::= { sdlcPortAdminEntry 7 }

--  *************************************************************
--  *                                                           *
--  *                THE SDLC PORT OPERATIONAL TABLE            *
--  *                                                           *
--  *************************************************************

sdlcPortOperTable   OBJECT-TYPE
                    SYNTAX      SEQUENCE OF SdlcPortOperEntry
                    ACCESS      not-accessible
                    STATUS      mandatory
                    DESCRIPTION
                        "This table contains current SDLC port
                        parameters.  Many of these objects have
                        corresponding objects in the sdlcPortAdminTable."

                    ::= { sdlcPortGroup 2 }

sdlcPortOperEntry   OBJECT-TYPE
                    SYNTAX      SdlcPortOperEntry
                    ACCESS      not-accessible
                    STATUS      mandatory
                    DESCRIPTION
                        "Currently set parameters for a specific SDLC
                        port."
                    INDEX   { ifIndex }

                    ::= { sdlcPortOperTable 1 }

SdlcPortOperEntry   ::= SEQUENCE
                {
                        sdlcPortOperName            DisplayString,
                        sdlcPortOperRole            INTEGER,
                        sdlcPortOperType            INTEGER,
                        sdlcPortOperTopology        INTEGER,
                        sdlcPortOperACTIVTO         TimeTicks,
                        sdlcPortOperPAUSE           TimeTicks,
                        sdlcPortOperSlowPollMethod  INTEGER,
                        sdlcPortOperSlowPollTimer   TimeTicks,
                        sdlcPortOperLastFailTime    TimeTicks,
                        sdlcPortOperLastFailCause   INTEGER
                }

sdlcPortOperName    OBJECT-TYPE
                    SYNTAX      DisplayString (SIZE (1..8))
                    ACCESS      read-only
                    STATUS      mandatory
                    DESCRIPTION
                        "An octet string that describes the physical
                        port to which this interface is currently
                        attached.  It has  implementation-specific
                        significance."

                    ::= { sdlcPortOperEntry 1 }

sdlcPortOperRole    OBJECT-TYPE
                    SYNTAX      INTEGER
                    {
                        primary(1),
                        secondary(2),
                        undefined(3)
                    }
                    ACCESS      read-only
                    STATUS      mandatory
                    DESCRIPTION
                        "This object describes the role that the link
                        station has assumed on this connection.

                        Even though this is defined as a port object,
                        it is a link station attribute in the sense
                        that a role is per link station.  However, it
                        is not possible to vary link station roles on a
                        particular port.  For example, if an SDLC port
                        is configured to primary, all link stations on
                        that port must be primary.

                        The value of sdlcPortOperRole is undefined(3)
                        whenever the link station role has not yet been
                        established by the mode setting command."

                    ::= { sdlcPortOperEntry 2 }

sdlcPortOperType    OBJECT-TYPE
                    SYNTAX      INTEGER
                    {
                         leased(1),
                         switched(2)
                    }
                    ACCESS      read-only
                    STATUS      mandatory
                    DESCRIPTION
                        "This parameter defines whether the SDLC port
                        is currently operating as though connected to a
                        leased or switched line."

                    ::= { sdlcPortOperEntry 3 }

sdlcPortOperTopology  OBJECT-TYPE
                    SYNTAX      INTEGER
                    {
                         pointToPoint(1),
                         multipoint(2)
                    }
                    ACCESS      read-only
                    STATUS      mandatory
                    DESCRIPTION
                        "This parameter defines whether the SDLC port is
                        mandatoryly operating in a point-to-point or
                        multipoint topology."

                    ::= { sdlcPortOperEntry 4 }

sdlcPortOperACTIVTO OBJECT-TYPE
                    SYNTAX      TimeTicks
                    ACCESS      read-only
                    STATUS      mandatory
                    DESCRIPTION
                        "This parameter defines the period of time (in
                        100ths of a second) that the port will allow a
                        switched line to remain inactive before
                        disconnecting.  A switched line is considered
                        to be inactive if there are no I-Frames being
                        transferred.

                        The object descriptor contains the name of an
                        NCP configuration parameter, ACTIVTO.  Please
                        note that the value of this object represents
                        1/100ths of a second while the NCP ACTIVTO is
                        represented in seconds.

                        A value of zero indicates no timeout."

                    ::= { sdlcPortOperEntry 5 }

sdlcPortOperPAUSE   OBJECT-TYPE
                    SYNTAX      TimeTicks
                    ACCESS      read-only
                    STATUS      mandatory
                    DESCRIPTION
                        "This object describes the current minimum
                        elapsed time (in 1/100ths of a second) between
                        any two traversals of the poll list for a
                        primary SDLC port.

                        The object descriptor contains the name of an
                        NCP configuration parameter, PAUSE.  Please
                        note that the value of this object represents
                        1/100ths of a second while the NCP PAUSE is
                        represented in 1/10ths of a second.

                        This object only has meaning for SDLC ports
                        where
                            sdlcPortAdminRole == primary "

                    ::= { sdlcPortOperEntry 6 }

sdlcPortOperSlowPollMethod OBJECT-TYPE
                    SYNTAX      INTEGER
                    {
                         servlim(1),
                         pollpause(2),
                         other(3)
                    }
                    ACCESS      read-only
                    STATUS      mandatory
                    DESCRIPTION
                        "This object defines the exact method that is in
                        effect for periodically polling failed secondary
                        link station addresses.

                        If sdlcPortOperSlowPollMethod == servlim, then
                        sdlcPortOperSERVLIM defines the actual polling
                        characteristics.

                        If sdlcPortOperSlowPollMethod == pollpause,
                        then sdlcPortOperSlowPollTimer defines the
                        actual polling characteristics.

                        If sdlcPortOperSlowPollMethod == other, then
                        the polling characteristics are modeled in
                        vendor-specific objects.

                        This object only has meaning for SDLC ports
                        where
                            sdlcPortOperRole == primary
                        and
                            sdlcPortOperTopology == multipoint "

                    ::= { sdlcPortOperEntry 7 }

sdlcPortOperSlowPollTimer OBJECT-TYPE
                    SYNTAX      TimeTicks
                    ACCESS      read-only
                    STATUS      mandatory
                    DESCRIPTION
                        "This object describes the elapsed time (in
                        1/100ths of a second) between polls for failed
                        secondary link station addresses.

                        This object only has meaning for SDLC ports
                        where
                            sdlcPortOperRole == primary
                        and
                            sdlcPortOperTopology == multipoint "

                    ::= { sdlcPortOperEntry 8 }

sdlcPortOperLastFailTime    OBJECT-TYPE
                    SYNTAX      TimeTicks
                    ACCESS      read-only
                    STATUS      mandatory
                    DESCRIPTION
                        "This object describes the value of sysUpTime
                        when this SDLC port last failed.  If the port
                        has not failed, then this value shall be zero."

                    ::= { sdlcPortOperEntry 9 }

sdlcPortOperLastFailCause    OBJECT-TYPE
                    SYNTAX      INTEGER
                    {
                        undefined(1),
                        physical(2)
                    }
                    ACCESS      read-only
                    STATUS      mandatory
                    DESCRIPTION
                        "This enumerated object describes the cause of
                        the last failure of this SDLC port.  If the
                        port has not failed, then this object has a
                        value of undefined(1)."
                    DEFVAL { undefined }

                    ::= { sdlcPortOperEntry 10 }


--  *************************************************************
--  *                                                           *
--  *           THE SDLC PORT STATISTICS TABLE                  *
--  *                                                           *
--  *************************************************************

sdlcPortStatsTable  OBJECT-TYPE
                    SYNTAX      SEQUENCE OF SdlcPortStatsEntry
                    ACCESS      not-accessible
                    STATUS      mandatory
                    DESCRIPTION
                        "Each entry in this table contains statistics
                        for a specific SDLC port."

                     ::= { sdlcPortGroup 3 }

sdlcPortStatsEntry  OBJECT-TYPE
                    SYNTAX      SdlcPortStatsEntry
                    ACCESS      not-accessible
                    STATUS      mandatory
                    DESCRIPTION
                        "A list of statistics for an SDLC port."
                    INDEX   { ifIndex }

                    ::= { sdlcPortStatsTable 1 }

SdlcPortStatsEntry ::= SEQUENCE
                {
                        sdlcPortStatsPhysicalFailures Counter,
                        sdlcPortStatsInvalidAddresses Counter,
                        sdlcPortStatsDwarfFrames      Counter
                }

sdlcPortStatsPhysicalFailures OBJECT-TYPE
                    SYNTAX      Counter
                    ACCESS      read-only
                    STATUS      mandatory
                    DESCRIPTION
                        "This object reflects the total number of times
                        this port has failed due to its physical media
                        since port startup.  At port startup time,
                        this object must be initialized to zero."

                    ::= { sdlcPortStatsEntry 1 }

sdlcPortStatsInvalidAddresses OBJECT-TYPE
                    SYNTAX      Counter
                    ACCESS      read-only
                    STATUS      mandatory
                    DESCRIPTION
                        "This object reflects the total number of
                        frames received by this port with invalid link
                        station addresses."

                    ::= { sdlcPortStatsEntry 2 }

sdlcPortStatsDwarfFrames OBJECT-TYPE
                    SYNTAX      Counter
                    ACCESS      read-only
                    STATUS      mandatory
                    DESCRIPTION
                        "This object reflects the total number of
                        frames received by this port which were
                        delivered intact by the physical layer but were
                        too short to be legal.

                        Ignoring the frame check sequence (FCS), a
                        frame is considered to be too short if it
                        is less than 2 bytes for sdlcLSOperMODULO of
                        eight, or if it is less than 3 bytes for
                        sdlcLSOperMODULO of onetwentyeight."

                    ::= { sdlcPortStatsEntry 3 }


--
--  THE SDLC LINK STATION GROUP
--  ===========================
--

--  The following classes of information is modelled for each SDLC link
--  station:
--
--     1.  ADMINISTRATIVE ( read-write/read-only )
--     2.  OPERATIONAL    ( read-only)
--     3.  STATISTICS     ( read-only)

--  *************************************************************
--  *                                                           *
--  *        THE SDLC LINK STATION ADMINISTRATIVE TABLE         *
--  *                                                           *
--  *************************************************************

sdlcLSAdminTable  OBJECT-TYPE
                    SYNTAX      SEQUENCE OF SdlcLSAdminEntry
                    ACCESS      not-accessible
                    STATUS      mandatory
                    DESCRIPTION
                        "This table contains objects that can be
                        changed to manage an SDLC link station.
                        Changing one of these parameters may take
                        effect in the operating link immediately or may
                        wait until the link is restarted depending on
                        the details of the implementation.

                        Most of the objects in this read-write table
                        have corresponding read-only objects in the
                        sdlcLSOperTable that reflect the current
                        operating value.

                        The operating values may be different from
                        these configured values if changed by XID
                        negotiation or if a configured parameter was
                        changed after the link was started."

                    ::= { sdlcLSGroup 1 }

sdlcLSAdminEntry    OBJECT-TYPE
                    SYNTAX      SdlcLSAdminEntry
                    ACCESS      not-accessible
                    STATUS      mandatory
                    DESCRIPTION
                         "A list of configured values for an SDLC link
                         station."
                    INDEX   { ifIndex, sdlcLSAddress }

                    ::= { sdlcLSAdminTable 1 }

SdlcLSAdminEntry ::= SEQUENCE
                {
                        sdlcLSAddress           INTEGER,
                        sdlcLSAdminName         DisplayString,
                        sdlcLSAdminState        INTEGER,
                        sdlcLSAdminMAXDATA      Integer32,
                        sdlcLSAdminREPLYTO      TimeTicks,
                        sdlcLSAdminMAXIN        INTEGER,
                        sdlcLSAdminMAXOUT       INTEGER,
                        sdlcLSAdminMODULO       INTEGER,
                        sdlcLSAdminRETRIESm     INTEGER,
                        sdlcLSAdminRETRIESt     TimeTicks,
                        sdlcLSAdminRETRIESn     Integer32,
                        sdlcLSAdminRNRLIMIT     TimeTicks,
                        sdlcLSAdminDATMODE      INTEGER,
                        sdlcLSAdminGPoll        INTEGER,
                        sdlcLSAdminSimRim       INTEGER
                }

sdlcLSAddress  OBJECT-TYPE
                    SYNTAX      INTEGER (1..255)
                    ACCESS      read-write
                    STATUS      mandatory
                    DESCRIPTION
                         "This value is the poll address of the
                         secondary link station for this SDLC link.  It
                         uniquely identifies the SDLC link station
                         within a single SDLC port."

                    ::= { sdlcLSAdminEntry 1 }

sdlcLSAdminName     OBJECT-TYPE
                    SYNTAX      DisplayString (SIZE (1..10))
                    ACCESS      read-write
                    STATUS      mandatory
                    DESCRIPTION
                        "An octet string that defines the local name of
                        the SDLC link station.  This field may be sent
                        in the XID3 control vector 0x0E, type 0xF7."

                    ::= { sdlcLSAdminEntry 2 }

sdlcLSAdminState    OBJECT-TYPE
                    SYNTAX      INTEGER
                    {
                         inactive(1),
                         active(2)
                    }
                    ACCESS      read-write
                    STATUS      mandatory
                    DESCRIPTION
                        "This object controls the desired state of the
                        SDLC station.  The managed system shall attempt
                        to keep the operational state, sdlcLSOperState,
                        consistent with this value."
                    DEFVAL { active }

                    ::= { sdlcLSAdminEntry 3 }

sdlcLSAdminMAXDATA  OBJECT-TYPE
                    SYNTAX      Integer32
                    ACCESS      read-only
                    STATUS      mandatory
                    DESCRIPTION
                        "This object contains the maximum PDU size that
                        the local link station thinks it can send to
                        the adjacent link station before having
                        received any XID from the ALS.  After the
                        maximum PDU size that the ALS can receive is
                        known (via XID exchange) that value is
                        reflected in sdlcLSOperMAXDATASend and takes
                        precedence over this object.

                        This value includes the Transmission Header
                        (TH) and the Request Header (RH)."

                    ::= { sdlcLSAdminEntry 4 }

sdlcLSAdminREPLYTO  OBJECT-TYPE
                    SYNTAX      TimeTicks
                    ACCESS      read-write
                    STATUS      mandatory
                    DESCRIPTION
                        "This object controls the reply timeout (in
                        1/100ths of a second) for an SDLC link
                        station.  If the link station does not receive
                        a response to a poll or message before the
                        specified time expires then the appropriate
                        error recovery shall be initiated.

                        The object descriptor contains the name of an
                        NCP configuration parameter, REPLYTO.  Please
                        note that the value of this object represents
                        1/100ths of a second while the NCP REPLYTO is
                        represented in 1/10ths of a second.

                        Depending on the implementation, a write
                        operation to this administered value  may not
                        change the operational value, sdlcLSOperREPLYTO,
                        until the link station is cycled inactive.

                        This object only has meaning for SDLC ports
                        where sdlcPortAdminRole == primary "
                    DEFVAL { 100 }

                    ::= { sdlcLSAdminEntry 5 }

sdlcLSAdminMAXIN    OBJECT-TYPE
                    SYNTAX      INTEGER (1..127)
                    ACCESS      read-only
                    STATUS      mandatory
                    DESCRIPTION
                        "This object controls the maximum number of
                        unacknowledged I-frames which an SDLC link
                        station may receive.  This should range from 1
                        to (sdlcLSAdminMODULO - 1).  This value is sent
                        in the XID to the ALS."
                    DEFVAL { 7 }

                    ::= { sdlcLSAdminEntry 6 }

sdlcLSAdminMAXOUT   OBJECT-TYPE
                    SYNTAX      INTEGER (1..127)
                    ACCESS      read-write
                    STATUS      mandatory
                    DESCRIPTION
                        "This object controls the maximum number of
                        consecutive unacknowledged I-frames which an
                        SDLC link station shall send without an
                        acknowledgement.  This shall range from 1 to
                        (sdlcLSAdminMODULO - 1).

                        For link stations on switched SDLC lines,
                        certain implementations may choose to override
                        this administered value with the value
                        received in the XID exchange.

                        Depending on the implementation, a write
                        operation to this administered value  may not
                        change the operational value, sdlcLSOperMAXOUT,
                        until the link station is cycled inactive."
                    DEFVAL { 1 }

                    ::= { sdlcLSAdminEntry 7 }

sdlcLSAdminMODULO   OBJECT-TYPE
                    SYNTAX      INTEGER
                    {
                        eight(8),
                        onetwentyeight(128)
                    }
                    ACCESS      read-only
                    STATUS      mandatory
                    DESCRIPTION
                        "This object controls the modulus for an SDLC
                        link station.  This modulus determines the size
                        of the rotating acknowledgement window used the
                        SDLC link station pair.

                        An implementation can support only modulo 8,
                        only modulo 128, or both."
                    DEFVAL { eight }

                    ::= { sdlcLSAdminEntry 8 }

sdlcLSAdminRETRIESm OBJECT-TYPE
                    SYNTAX      INTEGER (0..128)
                    ACCESS      read-only
                    STATUS      mandatory
                    DESCRIPTION
                        "This object controls number of retries in a
                        retry sequence for the local SDLC link
                        station.  A retry sequence is a series of
                        retransmitted frames ( data or control) for
                        which no positive acknowledgement is received.

                        The number of times that the retry sequence is
                        to be repeated is controlled by the object:
                        sdlcLSAdminRETRIESn.  The interval between retry
                        sequences is controlled by the object:
                        sdlcLSAdminRETRIESt.

                        A value of zero indicates no retries. If the
                        value of sdlcLSAdminRETRIESm is zero, then the
                        values of sdlcLSAdminRETRIESt and
                        sdlcLSAdminRETRIESn should also be zero."
                    DEFVAL { 15 }

                    ::= { sdlcLSAdminEntry 9 }

sdlcLSAdminRETRIESt OBJECT-TYPE
                    SYNTAX      TimeTicks
                    ACCESS      read-write
                    STATUS      mandatory
                    DESCRIPTION
                        "This object controls the interval (in 1/100ths
                        of a second) between retry sequences for the
                        local SDLC link station if multiple retry
                        sequences are specified .  A retry sequence is
                        a series of retransmitted frames ( data or
                        control) for which no positive acknowledgement
                        is received.

                        The number of repeated retries sequences is
                        controlled by the object: sdlcLSAdminRETRIESn.
                        The retries per sequence is controlled by the
                        object:  sdlcLSAdminRETRIESm.

                        The object descriptor contains the name of an
                        NCP configuration parameter, RETRIESt.  Please
                        note that the value of this object represents
                        1/100ths of a second while the NCP RETRIESt is
                        represented in seconds.

                        Depending on the implementation, a write
                        operation to this administered value  may not
                        change the operational value, sdlcLSOperRETRIESt,
                        until the link station is cycled inactive."
                    DEFVAL { 0 }

                    ::= { sdlcLSAdminEntry 10 }

sdlcLSAdminRETRIESn OBJECT-TYPE
                    SYNTAX      Integer32
                    ACCESS      read-write
                    STATUS      mandatory
                    DESCRIPTION
                        "This object controls the number of times that
                        a retry sequence is repeated for the local SDLC
                        link station.  A retry sequence is a series of
                        retransmitted frames ( data or control) for
                        which no positive acknowledgement is received.

                        The interval between retry sequences is
                        controlled by the object: sdlcLSAdminRETRIESt.

                        The retries per sequence is controlled by the
                        object:  sdlcLSAdminRETRIESm.

                        Depending on the implementation, a write
                        operation to this administered value  may not
                        change the operational value, sdlcLSOperRETRIESn,
                        until the link station is cycled inactive."
                    DEFVAL { 0 }

                    ::= { sdlcLSAdminEntry 11 }

sdlcLSAdminRNRLIMIT OBJECT-TYPE
                    SYNTAX      TimeTicks
                    ACCESS      read-write
                    STATUS      mandatory
                    DESCRIPTION
                        "This object controls the length of time (in
                        1/100ths of a second) that an SDLC link station
                        will allow its adjacent link station to remain
                        in a busy (RNR) state before declaring it
                        inoperative.

                        A value of sdlcLSAdminRNRLIMIT == 0 means there
                        is no limit.

                        The object descriptor contains the name of an
                        NCP configuration parameter, RNRLIMIT.  Please
                        note that the value of this object represents
                        1/100ths of a second while the NCP RNRLIMIT is
                        represented in minutes.

                        Depending on the implementation, a write
                        operation to this administered value  may not
                        change the operational value, sdlcLSOperRNRLIMIT,
                        until the link station is cycled inactive."
                    DEFVAL { 18000 }

                    ::= { sdlcLSAdminEntry 12 }

sdlcLSAdminDATMODE  OBJECT-TYPE
                    SYNTAX      INTEGER
                    {
                        half(1),
                        full(2)
                    }
                    ACCESS      read-only
                    STATUS      mandatory
                    DESCRIPTION
                        "This object controls whether communications
                        mode with the adjacent link station is
                        two-way-alternate (half) or two-way-simultaneous
                        (full)."
                    DEFVAL { half }

                    ::= { sdlcLSAdminEntry 13 }

sdlcLSAdminGPoll    OBJECT-TYPE
                    SYNTAX      INTEGER (0..254)
                    ACCESS      read-write
                    STATUS      mandatory
                    DESCRIPTION
                        "This object describes the group poll address
                        for this link station instance.  If group poll
                        is not in effect for this link station
                        instance, the value for sdlcLSAdminGPoll should
                        be zero.

                        Depending on the implementation, a write
                        operation to this administered value  may not
                        change the operational value, sdlcLSOperGPoll,
                        until the link station is cycled inactive."
                    ::= { sdlcLSAdminEntry 14 }

sdlcLSAdminSimRim   OBJECT-TYPE
                    SYNTAX      INTEGER
                    {
                         no(1),
                         yes(2)
                    }
                    ACCESS      read-only
                    STATUS      mandatory
                    DESCRIPTION
                        "This object controls the support for
                        transmission and receipt of SIM and RIM control
                        frames for this link station.  The value of
                        this object controls the setting of the
                        transmit-receive capability sent in the XID
                        field."
                    DEFVAL { no }

                    ::= { sdlcLSAdminEntry 15 }

--  *************************************************************
--  *                                                           *
--  *           THE SDLC LINK STATION OPERATIONAL TABLE         *
--  *                                                           *
--  *************************************************************

sdlcLSOperTable     OBJECT-TYPE
                    SYNTAX      SEQUENCE OF SdlcLSOperEntry
                    ACCESS      not-accessible
                    STATUS      mandatory
                    DESCRIPTION
                          "This table contains current SDLC link
                          parameters.  Many of these objects have
                          corresponding objects in the
                          sdlcLSAdminTable."

                    ::= { sdlcLSGroup 2 }

sdlcLSOperEntry     OBJECT-TYPE
                    SYNTAX      SdlcLSOperEntry
                    ACCESS      not-accessible
                    STATUS      mandatory
                    DESCRIPTION
                         "A list of status and control values for an
                         SDLC link station."
                    INDEX   { ifIndex, sdlcLSAddress }

                    ::= { sdlcLSOperTable 1 }

SdlcLSOperEntry     ::= SEQUENCE
                {
                        sdlcLSOperName                  DisplayString,
                        sdlcLSOperRole                  INTEGER,
                        sdlcLSOperState                 INTEGER,
                        sdlcLSOperMAXDATA               INTEGER,
                        sdlcLSOperREPLYTO               TimeTicks,
                        sdlcLSOperMAXIN                 INTEGER,
                        sdlcLSOperMAXOUT                INTEGER,
                        sdlcLSOperMODULO                INTEGER,
                        sdlcLSOperRETRIESm              INTEGER,
                        sdlcLSOperRETRIESt              TimeTicks,
                        sdlcLSOperRETRIESn              INTEGER,
                        sdlcLSOperRNRLIMIT              TimeTicks,
                        sdlcLSOperDATMODE               INTEGER,
                        sdlcLSOperLastFailTime          TimeTicks,
                        sdlcLSOperLastFailCause         INTEGER,
                        sdlcLSOperLastFailCtrlIn        OCTET STRING,
                        sdlcLSOperLastFailCtrlOut       OCTET STRING,
                        sdlcLSOperLastFailFRMRInfo      OCTET STRING,
                        sdlcLSOperLastFailREPLYTOs      Counter,
                        sdlcLSOperGPoll                 INTEGER,
                        sdlcLSOperSimRim                INTEGER
                }

sdlcLSOperName      OBJECT-TYPE
                    SYNTAX      DisplayString (SIZE (1..8))
                    ACCESS      read-only
                    STATUS      mandatory
                    DESCRIPTION
                         "An octet string that defines the name of the
                         remote SDLC link station.  This field is
                         received in the XID3 control vector 0x0E, type
                         0xF7."

                    ::= { sdlcLSOperEntry 1 }
 
sdlcLSOperRole      OBJECT-TYPE
                    SYNTAX      INTEGER
                    {
                        primary(1),
                        secondary(2),
                        undefined(3)
                    }
                    ACCESS      read-only
                    STATUS      mandatory
                    DESCRIPTION
                        "This object reflects the current role that the
                        link station is assuming.

                        The value of sdlcLSOperRole is undefined(3)
                        whenever the link station role has not yet been
                        established by the mode setting command."

                    ::= { sdlcLSOperEntry 2 }

sdlcLSOperState     OBJECT-TYPE
                    SYNTAX      INTEGER
                    {
                        discontacted(1),
                        contactPending(2),
                        contacted(3),
                        discontactPending(4)
                    }
                    ACCESS      read-only
                    STATUS      mandatory
                    DESCRIPTION
                        "This object describes the operational state of
                        the SDLC link station.  The managed system
                        shall attempt to keep this value consistent
                        with the administered state, sdlcLSAdminState"

                    ::= { sdlcLSOperEntry 3 }

sdlcLSOperMAXDATA   OBJECT-TYPE
                    SYNTAX      INTEGER
                    ACCESS      read-only
                    STATUS      mandatory
                    DESCRIPTION
                        "This object contains the actual maximum PDU
                        size that the local link station can send to
                        the adjacent link station.  This object is
                        established from the value received in the XID
                        from the adjacent link station.  If no XID
                        is received, then this value is implementation
                        dependent (for instance, it could be the value
                        of sdlcLSAdminMAXDATA).

                        This value includes the Transmission Header
                        (TH) and the Request Header (RH)."

                    ::= { sdlcLSOperEntry 4 }

sdlcLSOperREPLYTO   OBJECT-TYPE
                    SYNTAX      TimeTicks
                    ACCESS      read-only
                    STATUS      mandatory
                    DESCRIPTION
                        "This object reflects the current reply timeout
                        (in 1/100ths of a second) for an SDLC link
                        station.  If the link station does not receive
                        a response to a poll or message before the
                        specified time expires then the appropriate
                        error recovery shall be initiated.

                        The object descriptor contains the name of an
                        NCP configuration parameter, REPLYTO.  Please
                        note that the value of this object represents
                        1/100ths of a second while the NCP REPLYTO is
                        represented in 1/10ths of a second.

                        This object only has meaning for SDLC ports
                        where sdlcPortOperRole == primary "

                    ::= { sdlcLSOperEntry 5 }

sdlcLSOperMAXIN    OBJECT-TYPE
                    SYNTAX      INTEGER (1..127)
                    ACCESS      read-only
                    STATUS      mandatory
                    DESCRIPTION
                        "This object reflects the current maximum
                        number of unacknowledged I-frames which an SDLC
                        link station may receive.  This shall range
                        from 1 to (sdlcLSOperMODULO - 1)."

                    ::= { sdlcLSOperEntry 6 }

sdlcLSOperMAXOUT    OBJECT-TYPE
                    SYNTAX      INTEGER (1..127)
                    ACCESS      read-only
                    STATUS      mandatory
                    DESCRIPTION
                        "This object controls the maximum number of
                        consecutive unacknowledged I-frames which an
                        SDLC link station shall send without an
                        acknowledgement.  This shall range from 1 to
                        (sdlcLSAdminMODULO - 1).

                        This value may controlled by the administered
                        MAXOUT, sdlcLSAdminMAXOUT, or by the MAXIN value
                        received during the XID exchange."

                    ::= { sdlcLSOperEntry 7 }

sdlcLSOperMODULO   OBJECT-TYPE
                    SYNTAX      INTEGER
                    {
                        eight(8),
                        onetwentyeight(128)
                    }
                    ACCESS      read-only
                    STATUS      mandatory
                    DESCRIPTION
                        "This object reflects the current modulus for
                        an SDLC link station.  This modulus determines
                        the size of rotating acknowledgement window
                        used by the SDLC link station pair."
                     DEFVAL { eight }

                    ::= { sdlcLSOperEntry 8 }

sdlcLSOperRETRIESm  OBJECT-TYPE
                    SYNTAX      INTEGER (0..128)
                    ACCESS      read-only
                    STATUS      mandatory
                    DESCRIPTION
                        "This object controls number of retries in a
                        retry sequence for an SDLC link station.  A
                        retry sequence is a series of retransmitted
                        frames ( data or control) for which no positive
                        acknowledgement is received.

                        The current number of times that the retry
                        sequence is to be repeated is reflected by the
                        object:  sdlcLSOperRETRIESn.  The current
                        interval between retry sequences is reflected
                        by the object:  sdlcLSOperRETRIESt."

                    ::= { sdlcLSOperEntry 9 }

sdlcLSOperRETRIESt  OBJECT-TYPE
                    SYNTAX      TimeTicks
                    ACCESS      read-only
                    STATUS      mandatory
                    DESCRIPTION
                        "This object reflects the current interval (in
                        1/100ths of a second) between retry sequences
                        for an SDLC link station if multiple retry
                        sequences are specified.  A retry sequence is a
                        series of retransmitted frames ( data or
                        control) for which no positive acknowledgement
                        is received.

                        The object descriptor contains the name of an
                        NCP configuration parameter, RETRIESt.  Please
                        note that the value of this object represents
                        1/100ths of a second while the NCP RETRIESt is
                        represented in seconds.

                        The current number of repeated retries
                        sequences is reflected by the object:
                        sdlcLSOperRETRIESn.  The current retries per
                        sequence is reflected by the object:
                        sdlcLSOperRETRIESm."

                    ::= { sdlcLSOperEntry 10 }

sdlcLSOperRETRIESn OBJECT-TYPE
                    SYNTAX      INTEGER (0..127)
                    ACCESS      read-only
                    STATUS      mandatory
                    DESCRIPTION
                        "This object reflects the current number of
                        times that a retry sequence is repeated for an
                        SDLC link station.  A retry sequence is a
                        series of retransmitted frames ( data or
                        control) for which no positive acknowledgement
                        is received.

                        The current interval between retry sequences is
                        reflected by the object: sdlcLSOperRETRIESn.
                        The current retries per sequence is reflected
                        by the object:  sdlcLSOperRETRIESm."

                    ::= { sdlcLSOperEntry 11 }

sdlcLSOperRNRLIMIT  OBJECT-TYPE
                    SYNTAX      TimeTicks
                    ACCESS      read-only
                    STATUS      mandatory
                    DESCRIPTION
                        "This object reflects the current length of
                        time (in 1/100ths of a second) that an SDLC
                        link station will allow its adjacent link
                        station to remain in a busy (RNR) state before
                        declaring it inoperative.

                        The object descriptor contains the name of an
                        NCP configuration parameter, RNRLIMIT.  Please
                        note that the value of this object represents
                        1/100ths of a second while the NCP RNRLIMIT is
                        represented in minutes.

                        A value of sdlcLSOperRNRLIMIT == 0 means there
                        is no limit."

                    ::= { sdlcLSOperEntry 12 }

sdlcLSOperDATMODE   OBJECT-TYPE
                    SYNTAX      INTEGER
                    {
                        half(1),
                        full(2)
                    }
                    ACCESS      read-only
                    STATUS      mandatory
                    DESCRIPTION
                        "This object reflects whether the current
                        communications mode with the adjacent link
                        station is two-way-alternate (half) or
                        two-way-simultaneous (full)."

                    ::= { sdlcLSOperEntry 13 }

sdlcLSOperLastFailTime    OBJECT-TYPE
                    SYNTAX      TimeTicks
                    ACCESS      read-only
                    STATUS      mandatory
                    DESCRIPTION
                        "This object describes the value of sysUpTime
                         when this SDLC link station last failed.  If
                         the link station has not failed, then this
                         value shall be zero."

                    ::= { sdlcLSOperEntry 14 }

sdlcLSOperLastFailCause    OBJECT-TYPE
                    SYNTAX      INTEGER
                    {
                        undefined(1),
                        rxFRMR(2),
                        txFRMR(3),
                        noResponse(4),
                        protocolErr(5),
                        noActivity(6),
                        rnrLimit(7),
                        retriesExpired(8)
                    }
                    ACCESS      read-only
                    STATUS      mandatory
                    DESCRIPTION
                        "This enumerated object reflects the cause of
                        the last failure of this SDLC link station.  If
                        the link station has not failed, then this
                        object will have a value of undefined(1)."
                    DEFVAL { undefined }

                    ::= { sdlcLSOperEntry 15 }

sdlcLSOperLastFailCtrlIn  OBJECT-TYPE
                    SYNTAX      OCTET STRING (SIZE(1..2))
                    ACCESS      read-only
                    STATUS      mandatory
                    DESCRIPTION
                        "This object reflects the last control octet or
                        octets (depending on modulus) received by this
                        SDLC link station at the time of the last
                        failure.  If the link station has not failed,
                        then this value has no meaning."

                    ::= { sdlcLSOperEntry 16 }

sdlcLSOperLastFailCtrlOut  OBJECT-TYPE
                    SYNTAX      OCTET STRING (SIZE(1..2))
                    ACCESS      read-only
                    STATUS      mandatory
                    DESCRIPTION
                        "This object reflects the last control octet or
                        octets (depending on modulus) sent by this SDLC
                        link station at the time of the last failure.
                        If the link station has not failed, then this
                        value has no meaning."

                    ::= { sdlcLSOperEntry 17 }

sdlcLSOperLastFailFRMRInfo  OBJECT-TYPE
                    SYNTAX      OCTET STRING (SIZE(5))
                    ACCESS      read-only
                    STATUS      mandatory
                    DESCRIPTION
                        "This object reflects the information field of
                        the FRMR frame if the last failure for this
                        SDLC link station was as a result of an invalid
                        frame.  Otherwise, this field has no meaning."

                    ::= { sdlcLSOperEntry 18 }

sdlcLSOperLastFailREPLYTOs  OBJECT-TYPE
                    SYNTAX      Counter
                    ACCESS      read-only
                    STATUS      mandatory
                    DESCRIPTION
                        "This object reflects the number of times that
                        the REPLYTO timer had expired for an SDLC link
                        station at the time of the last failure. If the
                        link station has not failed, then this value
                        has no meaning."

                    ::= { sdlcLSOperEntry 19 }

sdlcLSOperGPoll     OBJECT-TYPE
                    SYNTAX      INTEGER (0..254)
                    ACCESS      read-only
                    STATUS      mandatory
                    DESCRIPTION
                        "This object describes the group poll address
                        in effect for this link station instance."
                    DEFVAL { 0 }

                    ::= { sdlcLSOperEntry 20 }

sdlcLSOperSimRim    OBJECT-TYPE
                    SYNTAX      INTEGER
                    {
                         no(1),
                         yes(2)
                    }
                    ACCESS      read-only
                    STATUS      mandatory
                    DESCRIPTION
                        "This object reflects the support for
                        transmission and receipt of SIM and RIM control
                        frames for the adjacent link station.  The
                        value of this object is set from the XID field
                        received from the adjacent link station."
                    DEFVAL { no }

                    ::= { sdlcLSOperEntry 21 }

--  *************************************************************
--  *                                                           *
--  *           THE SDLC LINK STATION STATISTICS TABLE          *
--  *                                                           *
--  *************************************************************

sdlcLSStatsTable  OBJECT-TYPE
                    SYNTAX      SEQUENCE OF SdlcLSStatsEntry
                    ACCESS      not-accessible
                    STATUS      mandatory
                    DESCRIPTION
                        "Each entry in this table contains statistics
                        for a specific SDLC link station."

                     ::= { sdlcLSGroup 3 }

sdlcLSStatsEntry  OBJECT-TYPE
                    SYNTAX      SdlcLSStatsEntry
                    ACCESS      not-accessible
                    STATUS      mandatory
                    DESCRIPTION
                        "A list of statistics for an SDLC link station."
                    INDEX   { ifIndex, sdlcLSAddress }

                    ::= { sdlcLSStatsTable 1 }

SdlcLSStatsEntry ::= SEQUENCE
                {
                        sdlcLSStatsBLUsIn             Counter,
                        sdlcLSStatsBLUsOut            Counter,
                        sdlcLSStatsOctetsIn           Counter,
                        sdlcLSStatsOctetsOut          Counter,
                        sdlcLSStatsPollsOut           Counter,
                        sdlcLSStatsPollRspsOut        Counter,
                        sdlcLSStatsLocalBusies        Counter,
                        sdlcLSStatsRemoteBusies       Counter,
                        sdlcLSStatsIFramesIn          Counter,
                        sdlcLSStatsIFramesOut         Counter,
                        sdlcLSStatsRetransmits        Counter,
                        sdlcLSStatsIOctetsIn          Counter,
                        sdlcLSStatsIOctetsOut         Counter,
                        sdlcLSStatsUIFramesIn         Counter,
                        sdlcLSStatsUIFramesOut        Counter,
                        sdlcLSStatsXIDsIn             Counter,
                        sdlcLSStatsXIDsOut            Counter,
                        sdlcLSStatsTESTsIn            Counter,
                        sdlcLSStatsTESTsOut           Counter,
                        sdlcLSStatsREJsIn             Counter,
                        sdlcLSStatsREJsOut            Counter,
                        sdlcLSStatsFRMRsIn            Counter,
                        sdlcLSStatsFRMRsOut           Counter,
                        sdlcLSStatsSIMsIn             Counter,
                        sdlcLSStatsSIMsOut            Counter,
                        sdlcLSStatsRIMsIn             Counter,
                        sdlcLSStatsRIMsOut            Counter,
                        sdlcLSStatsProtocolErrs       Counter,
                        sdlcLSStatsActivityTOs        Counter,
                        sdlcLSStatsRNRLIMITs          Counter,
                        sdlcLSStatsRetriesExps        Counter
                }

sdlcLSStatsBLUsIn   OBJECT-TYPE
                    SYNTAX      Counter
                    ACCESS      read-only
                    STATUS      mandatory
                    DESCRIPTION
                        "This object reflects the total basic link
                        units (BLUs; frames) received from an adjacent
                        SDLC link station since link station startup.
                        At link station startup time, this object must
                        be initialized to zero."

                    ::= { sdlcLSStatsEntry 1 }

sdlcLSStatsBLUsOut   OBJECT-TYPE
                    SYNTAX      Counter
                    ACCESS      read-only
                    STATUS      mandatory
                    DESCRIPTION
                        "This object reflects the total basic link
                        units (BLUs; frames), transmitted to an
                        adjacent SDLC link station since link station
                        startup.  At link station startup time, this
                        object must be initialized to zero."

                    ::= { sdlcLSStatsEntry 2 }

sdlcLSStatsOctetsIn OBJECT-TYPE
                    SYNTAX      Counter
                    ACCESS      read-only
                    STATUS      mandatory
                    DESCRIPTION
                        "This object reflects the total octets received
                        from an adjacent SDLC link station since link
                        station startup.  This object covers the
                        address, control, and information field of
                        I-Frames only.  At link station startup time,
                        this object must be initialized to zero."

                    ::= { sdlcLSStatsEntry 3 }

sdlcLSStatsOctetsOut OBJECT-TYPE
                    SYNTAX      Counter
                    ACCESS      read-only
                    STATUS      mandatory
                    DESCRIPTION
                        "This object reflects the total octets
                        transmitted to an adjacent SDLC link station
                        since link station startup.  This object covers
                        the address, control, and information field of
                        I-Frames only.  At link station startup time,
                        this object must be initialized to zero."

                    ::= { sdlcLSStatsEntry 4 }

sdlcLSStatsPollsOut OBJECT-TYPE
                    SYNTAX      Counter
                    ACCESS      read-only
                    STATUS      mandatory
                    DESCRIPTION
                        "This object reflects the total polls sent to
                        an adjacent SDLC link station since link
                        station startup.  At link station startup time,
                        this object must be initialized to zero."

                    ::= { sdlcLSStatsEntry 5 }

sdlcLSStatsPollRspsOut OBJECT-TYPE
                    SYNTAX      Counter
                    ACCESS      read-only
                    STATUS      mandatory
                    DESCRIPTION
                        "This object reflects the total number of poll
                        responses sent to the adjacent SDLC link
                        station since link station startup.  This value
                        includes I-frames that are sent in response to
                        a poll.

                        At link station startup time, this object must
                        be initialized to zero."

                    ::= { sdlcLSStatsEntry 6 }

sdlcLSStatsLocalBusies OBJECT-TYPE
                    SYNTAX      Counter
                    ACCESS      read-only
                    STATUS      mandatory
                    DESCRIPTION
                        "This object reflects the total number of times
                        that the local SDLC link station has entered a
                        busy state (RNR) since link station startup.
                        At link station startup time, this object must
                        be initialized to zero."

                    ::= { sdlcLSStatsEntry 7 }

sdlcLSStatsRemoteBusies OBJECT-TYPE
                    SYNTAX      Counter
                    ACCESS      read-only
                    STATUS      mandatory
                    DESCRIPTION
                        "This object reflects the total number of times
                        that an adjacent ( remote) SDLC link station
                        has entered a busy state (RNR) since link
                        station startup.  At link station startup time,
                        this object must be initialized to zero."

                    ::= { sdlcLSStatsEntry 8 }

sdlcLSStatsIFramesIn OBJECT-TYPE
                    SYNTAX      Counter
                    ACCESS      read-only
                    STATUS      mandatory
                    DESCRIPTION
                        "This object reflects the total I-frames
                        received from an adjacent SDLC link station
                        since link station startup.  At link station
                        startup time, this object must be initialized
                        to zero."

                    ::= { sdlcLSStatsEntry 9 }

sdlcLSStatsIFramesOut OBJECT-TYPE
                    SYNTAX      Counter
                    ACCESS      read-only
                    STATUS      mandatory
                    DESCRIPTION
                        "This object reflects the total I-frames
                        transmitted to an adjacent SDLC link station
                        since link station startup.  At link station
                        startup time, this object must be initialized
                        to zero."

                    ::= { sdlcLSStatsEntry 10 }

sdlcLSStatsRetransmits OBJECT-TYPE
                    SYNTAX      Counter
                    ACCESS      read-only
                    STATUS      mandatory
                    DESCRIPTION
                        "This object reflects the total number of
                         information frames retransmitted to a remote
                         link station because the N(r) received from
                         that link station indicated that one or more
                         information frames sent to that station were
                         lost. This event causes the first missing
                         information frame of a window and all
                         subsequent information frames to be
                         retransmitted.  At link station startup time,
                         this object must be initialized to zero.

                         Management: If the value of
                         sdlcLSStatsRetransmits grows over time,
                         then the quality of the serial line is in
                         question.  You might want to look at
                         decreasing the value for sdlcLSAdminMAXDATA
                         to compensate for the lower quality line."

                    ::= { sdlcLSStatsEntry 11 }

sdlcLSStatsIOctetsIn OBJECT-TYPE
                    SYNTAX      Counter
                    ACCESS      read-only
                    STATUS      mandatory
                    DESCRIPTION
                        "This object reflects the octets received
                        in I-frames from an adjacent SDLC link station
			since link station startup.  This object covers
			valid, retried, and out-of-order I-Frames.
			At link station startup time, this object must
			be initialized to zero."

                    ::= { sdlcLSStatsEntry 12 }

sdlcLSStatsIOctetsOut OBJECT-TYPE
                    SYNTAX      Counter
                    ACCESS      read-only
                    STATUS      mandatory
                    DESCRIPTION
                        "This object reflects the octets transmitted 
                        in I-frames to an adjacent SDLC link station
			since link station startup.  This object covers
			valid, retried, and out-of-order I-Frames.
			At link station startup time, this object must
			be initialized to zero."

                    ::= { sdlcLSStatsEntry 13 }

sdlcLSStatsUIFramesIn OBJECT-TYPE
                    SYNTAX      Counter
                    ACCESS      read-only
                    STATUS      mandatory
                    DESCRIPTION
                        "This object reflects the total UI-frames
                        received from an adjacent SDLC link station
                        since link station startup."

                    ::= { sdlcLSStatsEntry 14 }

sdlcLSStatsUIFramesOut OBJECT-TYPE
                    SYNTAX      Counter
                    ACCESS      read-only
                    STATUS      mandatory
                    DESCRIPTION
                       "This object reflects the total UI-frames
                       transmitted to an adjacent SDLC link station
                       since link station startup."

                    ::= { sdlcLSStatsEntry 15 }

sdlcLSStatsXIDsIn   OBJECT-TYPE
                    SYNTAX      Counter
                    ACCESS      read-only
                    STATUS      mandatory
                    DESCRIPTION
                        "This object reflects the total XID frames
                        received from an adjacent SDLC link station
                        since link station startup."

                    ::= { sdlcLSStatsEntry 16 }

sdlcLSStatsXIDsOut  OBJECT-TYPE
                    SYNTAX      Counter
                    ACCESS      read-only
                    STATUS      mandatory
                    DESCRIPTION
                        "This object reflects the total XID frames
                        transmitted to an adjacent SDLC link station
                        since link station startup."

                    ::= { sdlcLSStatsEntry 17 }

sdlcLSStatsTESTsIn   OBJECT-TYPE
                    SYNTAX      Counter
                    ACCESS      read-only
                    STATUS      mandatory
                    DESCRIPTION
                        "This object reflects the total TEST frames,
                        commands or responses, received from an
                        adjacent SDLC link station since link station
                        startup."

                    ::= { sdlcLSStatsEntry 18 }

sdlcLSStatsTESTsOut  OBJECT-TYPE
                    SYNTAX      Counter
                    ACCESS      read-only
                    STATUS      mandatory
                    DESCRIPTION
                        "This object reflects the total TEST frames,
                        commands or responses, transmitted to an
                        adjacent SDLC link station since link station
                        startup."

                    ::= { sdlcLSStatsEntry 19 }

sdlcLSStatsREJsIn   OBJECT-TYPE
                    SYNTAX      Counter
                    ACCESS      read-only
                    STATUS      mandatory
                    DESCRIPTION
                        "This object reflects the total REJ frames
                        received from an adjacent SDLC link station
                        since link station startup."

                    ::= { sdlcLSStatsEntry 20 }

sdlcLSStatsREJsOut  OBJECT-TYPE
                    SYNTAX      Counter
                    ACCESS      read-only
                    STATUS      mandatory
                    DESCRIPTION
                        "This object reflects the total REJ frames
                        transmitted to an adjacent SDLC link station
                        since link station startup."

                    ::= { sdlcLSStatsEntry 21 }

sdlcLSStatsFRMRsIn  OBJECT-TYPE
                    SYNTAX      Counter
                    ACCESS      read-only
                    STATUS      mandatory
                    DESCRIPTION
                        "This object reflects the total frame reject
                        (FRMR) frames received from an adjacent SDLC
                        link station since link station startup."

                    ::= { sdlcLSStatsEntry 22 }

sdlcLSStatsFRMRsOut  OBJECT-TYPE
                    SYNTAX      Counter
                    ACCESS      read-only
                    STATUS      mandatory
                    DESCRIPTION
                        "This object reflects the total frame reject
                        (FRMR) frames transmitted to an adjacent SDLC
                        link station since link station startup."

                    ::= { sdlcLSStatsEntry 23 }

sdlcLSStatsSIMsIn   OBJECT-TYPE
                    SYNTAX      Counter
                    ACCESS      read-only
                    STATUS      mandatory
                    DESCRIPTION
                        "This object reflects the total set
                        initialization mode (SIM) frames received from
                        an adjacent SDLC link station since link station
                        startup."

                    ::= { sdlcLSStatsEntry 24 }

sdlcLSStatsSIMsOut  OBJECT-TYPE
                    SYNTAX      Counter
                    ACCESS      read-only
                    STATUS      mandatory
                    DESCRIPTION
                        "This object reflects the total set
                        initialization mode (SIM) frames transmitted to
                        an adjacent SDLC link station since link station
                        startup.  At link station startup time, this
                        object must be initialized to zero."

                    ::= { sdlcLSStatsEntry 25 }

sdlcLSStatsRIMsIn   OBJECT-TYPE
                    SYNTAX      Counter
                    ACCESS      read-only
                    STATUS      mandatory
                    DESCRIPTION
                        "This object reflects the total request
                        initialization mode (RIM) frames received from
                        an adjacent SDLC link station since link station
                        startup.  At link station startup time, this
                        object must be initialized to zero."

                    ::= { sdlcLSStatsEntry 26 }

sdlcLSStatsRIMsOut  OBJECT-TYPE
                    SYNTAX      Counter
                    ACCESS      read-only
                    STATUS      mandatory
                    DESCRIPTION
                        "This object reflects the total request
                        initialization mode (RIM) frames transmitted to
                        an adjacent SDLC link station since link station
                        startup.  At link station startup time, this
                        object must be initialized to zero."

                    ::= { sdlcLSStatsEntry 27 }

sdlcLSStatsProtocolErrs OBJECT-TYPE
                    SYNTAX      Counter
                    ACCESS      read-only
                    STATUS      mandatory
                    DESCRIPTION
                        "This object reflects the total occurrences,
                        since link station startup, where this SDLC
                        link station has inactivated the link as a
                        result of receiving a frame from its adjacent
                        link station which was in violation of the
                        protocol.  At link station startup time, this
                        object must be initialized to zero."

                    ::= { sdlcLSStatsEntry 28 }

sdlcLSStatsActivityTOs OBJECT-TYPE
                    SYNTAX      Counter
                    ACCESS      read-only
                    STATUS      mandatory
                    DESCRIPTION
                        "This object reflects the total occurrences,
                        since startup, where this SDLC link station has
                        inactivated the link as a result of no activity
                        on the link.  At link station startup time,
                        this object must be initialized to zero."

                    ::= { sdlcLSStatsEntry 29 }

sdlcLSStatsRNRLIMITs OBJECT-TYPE
                    SYNTAX      Counter
                    ACCESS      read-only
                    STATUS      mandatory
                    DESCRIPTION
                        "This object reflects the total occurrences,
                        since startup, where this SDLC link station has
                        inactivated the link as a result of its
                        RNRLIMIT timer expiring.  At link station
                        startup time, this object must be initialized
                        to zero."

                    ::= { sdlcLSStatsEntry 30 }

sdlcLSStatsRetriesExps OBJECT-TYPE
                    SYNTAX      Counter
                    ACCESS      read-only
                    STATUS      mandatory
                    DESCRIPTION
                        "This object reflects the total occurrences,
                        since startup, where this SDLC link station has
                        inactivated the link as a result of a retry
                        sequence being exhausted.  At link station
                        startup time, this object must be initialized
                        to zero."

                    ::= { sdlcLSStatsEntry 31 }

--
--  THE SDLC MAP GROUP
--  ===================
--

--  +++++++++++++++++++++++++++++++++++++++++++++++++++++++++++++
--  +                                                           +
--  +                THE SDLC MAP TABLE                         +
--  +                 3COM PROPRIETARY                          +
--  +                                                           +
--  +++++++++++++++++++++++++++++++++++++++++++++++++++++++++++++

sdlcMapTable  OBJECT-TYPE
                    SYNTAX      SEQUENCE OF SdlcMapEntry
                    ACCESS      not-accessible
                    STATUS      mandatory
                    DESCRIPTION
                        "This table contains objects that indicate
                        how SDLC poll addresses are mapped to LLC2 MAC/SAP
			addresses within the router. The mapping indicates
			whether the SDLC device is locally or remotely
			attached.

			This table is proprietary to 3Com Inc. and is
			not part of the standard SDLC MIB."

                     ::= { sdlcMapGroup 1 }

sdlcMapEntry  OBJECT-TYPE
                    SYNTAX      SdlcMapEntry
                    ACCESS      not-accessible
                    STATUS      mandatory
                    DESCRIPTION
                        "A list of configured values for mappings between
			SDLC and LLC2 links."
                    INDEX   { INTEGER }

                    ::= { sdlcMapTable 1 }

SdlcMapEntry  ::= SEQUENCE
                {
                        sdlcMapPollAddress          INTEGER,
                        sdlcMapLocalMacAddress      MacAddress,
                        sdlcMapLocalSap             OCTET STRING,
                        sdlcMapRemoteMacAddress     MacAddress,
                        sdlcMapRemoteSap            OCTET STRING,
                        sdlcMapName                 DisplayString,
                        sdlcMapPortState            INTEGER,
                        sdlcMapLSState              INTEGER
                }

sdlcMapPollAddress  OBJECT-TYPE
                    SYNTAX      INTEGER (1..255)
                    ACCESS      read-only
                    STATUS      mandatory
                    DESCRIPTION
                         "This value is the poll address of the
                         link station.  It uniquely identifies
			 the SDLC link station to which frames are
			 to be delivered after traversing the network."

                    ::= { sdlcMapEntry 1 }

sdlcMapLocalMacAddress OBJECT-TYPE
                    SYNTAX  MacAddress
                    ACCESS  read-only
                    STATUS  mandatory
                    DESCRIPTION
                         "The local MAC address with which this control unit
			 is associated. This address is taken from the
			 'CULocalMac' UI configuration parameter."

                    ::= { sdlcMapEntry 2 }

sdlcMapLocalSap OBJECT-TYPE
                    SYNTAX  OCTET STRING (SIZE (1))
                    ACCESS  read-only
                    STATUS  mandatory
                    DESCRIPTION
                         "The local Service Access Point with which
			 this control unit is associated. This SAP is 
			 taken from the 'CULocalSap' UI configuration
			 parameter."

                    ::= { sdlcMapEntry 3 }

sdlcMapRemoteMacAddress OBJECT-TYPE
                    SYNTAX  MacAddress
                    ACCESS  read-only
                    STATUS  mandatory
                    DESCRIPTION
                         "The remote MAC address with which this control unit
			 is associated. This address is taken from the
			 'CURemoteMac' UI configuration parameter."

                    ::= { sdlcMapEntry 4 }

sdlcMapRemoteSap OBJECT-TYPE
                    SYNTAX  OCTET STRING (SIZE (1))
                    ACCESS  read-only
                    STATUS  mandatory
                    DESCRIPTION
                         "The remote Service Access Point with which this
			 control unit is associated. This SAP is taken
			 from the 'CURemoteSap' UI configuration
			 parameter."

                    ::= { sdlcMapEntry 5 }

sdlcMapName OBJECT-TYPE
                    SYNTAX  DisplayString (SIZE (1..10))
                    ACCESS  read-only
                    STATUS  mandatory
                    DESCRIPTION
                         "An octet string that indicates the name assigned to
			 the control unit associated with this poll address."

                    ::= { sdlcMapEntry 6 }

sdlcMapPortState OBJECT-TYPE
                    SYNTAX      INTEGER
                    {
                        disable(1),
                        enable(2)
                    }
                    ACCESS  read-only
                    STATUS  mandatory
                    DESCRIPTION
                         "This object reflects the state of the port
			 to which this control unit is attached."

                    ::= { sdlcMapEntry 7 }

sdlcMapLSState OBJECT-TYPE
                    SYNTAX      INTEGER
                    {
                        disable(1),
                        enable(2)
                    }
                    ACCESS  read-only
                    STATUS  mandatory
                    DESCRIPTION
                         "This object reflects the state of the link station
			 with which this control unit is associated."

                    ::= { sdlcMapEntry 8 }

--  +++++++++++++++++++++++++++++++++++++++++++++++++++++++++++++
--  +                                                           +
--  +              END OF SDLC MAP TABLE                        +
--  +                 3COM PROPRIETARY                          +
--  +                                                           +
--  +++++++++++++++++++++++++++++++++++++++++++++++++++++++++++++

--
--  TRAP DEFINITIONS
--

--
--  Notifications
--

sdlcPortStatusChange TRAP-TYPE
		     ENTERPRISE sdlc
                     VARIABLES  { ifIndex,
                                  ifAdminStatus,
                                  ifOperStatus,
                                  sdlcPortOperLastFailTime,
                                  sdlcPortOperLastFailCause
                                }
                     DESCRIPTION
                         "This trap indicates that the state of an SDLC
                         port has transitioned to active or inactive."

                     ::= 1

sdlcLSStatusChange   TRAP-TYPE
		     ENTERPRISE sdlc
                     VARIABLES  { ifIndex,
                                  sdlcLSAddress,
                                  sdlcLSOperState,
                                  sdlcLSAdminState,
                                  sdlcLSOperLastFailTime,
                                  sdlcLSOperLastFailCause,
                                  sdlcLSOperLastFailFRMRInfo,
                                  sdlcLSOperLastFailCtrlIn,
                                  sdlcLSOperLastFailCtrlOut,
                                  sdlcLSOperLastFailREPLYTOs
                                }
                     DESCRIPTION
                         "This trap indicates that the state of an SDLC
                         link station has transitioned to contacted or
                         discontacted."

                     ::= 2

END

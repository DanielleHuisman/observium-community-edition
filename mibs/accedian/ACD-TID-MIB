--
-- Accedian Enterprise Specific MIB
--
-- Copyright (c) 2005-2012, Accedian Networks, Inc.
-- All rights reserved.
--
-- The contents of this document are subject to change without notice.
--


ACD-TID-MIB DEFINITIONS ::= BEGIN

IMPORTS
    MODULE-IDENTITY, OBJECT-TYPE,
    Unsigned32,
    NOTIFICATION-TYPE
        FROM SNMPv2-SMI
    DisplayString, TEXTUAL-CONVENTION
        FROM SNMPv2-TC
    MODULE-COMPLIANCE, OBJECT-GROUP,
    NOTIFICATION-GROUP
        FROM SNMPv2-CONF

    acdMibs
        FROM ACCEDIAN-SMI;

acdTid MODULE-IDENTITY

    LAST-UPDATED "201211052200Z"
    ORGANIZATION "Accedian Networks, Inc."
    CONTACT-INFO
            "Accedian Technical Assistance Center
             Accedian Networks, Inc.
             2351 Alfred-Nobel blvd., Suite N-410
             Saint-Laurent, Quebec Canada H4S 2A9
             E-mail: support@accedian.com"
    DESCRIPTION
            "The Transaction ID database for this Accedian Networks device."

    REVISION "201111110100Z"        -- 11 November 2011
    DESCRIPTION
            "Initial version of MIB module ACD-TID-MIB."
    REVISION "201211052200Z"        -- 05 November 2012
    DESCRIPTION
            "Add global configuration change notification."

    ::= { acdMibs 14 }

acdTidNotifications     OBJECT IDENTIFIER ::= { acdTid 0 }
acdTidMIBObjects        OBJECT IDENTIFIER ::= { acdTid 1 }
acdTidConformance       OBJECT IDENTIFIER ::= { acdTid 2 }

acdTidGeneral           OBJECT IDENTIFIER ::= { acdTidMIBObjects 1 }
acdTidInfo              OBJECT IDENTIFIER ::= { acdTidMIBObjects 2 }
acdTidGlobalCfg         OBJECT IDENTIFIER ::= { acdTidMIBObjects 3 }

---------------------------------------------------------------------------
-- Textual conventions
---------------------------------------------------------------------------

AcdTidType ::= TEXTUAL-CONVENTION
    STATUS      current
    DESCRIPTION
       "Indicate if the object is covers by the acdTidCfgLastChangeTid or
        or by the acdTidStatusLastChangeTid transaction identifier."
    SYNTAX      INTEGER {
                    configuration(1),
                    status(2)
    }

---------------------------------------------------------------------------
 -- Transaction Identifier General onfiguration
 -- 
---------------------------------------------------------------------------

acdTidCfgLastChangeTid OBJECT-TYPE
    SYNTAX      Unsigned32
    MAX-ACCESS  read-only
    STATUS      current
    DESCRIPTION
       "This is the transaction ID of the last change of a configuration
        object.  If this value is different since the last read this is 
        indicate a change."
    ::= { acdTidGeneral 1 }

acdTidStatusLastChangeTid OBJECT-TYPE
    SYNTAX      Unsigned32
    MAX-ACCESS  read-only
    STATUS      current
    DESCRIPTION
       "This is the transaction ID of the last change of a status object.
        If this value is different since the last read this is indicate 
        a change."
    ::= { acdTidGeneral 2 }

---------------------------------------------------------------------------
 -- Table of all object covers by Transaction Identifier feature.
 ---------------------------------------------------------------------------

acdTidInfoTable OBJECT-TYPE
    SYNTAX     SEQUENCE OF AcdTidInfoEntry
    MAX-ACCESS not-accessible
    STATUS     current
    DESCRIPTION
            "Table of all object covers by Transaction Identifier feature."
    ::= { acdTidInfo 1 }

acdTidInfoEntry OBJECT-TYPE
    SYNTAX     AcdTidInfoEntry
    MAX-ACCESS not-accessible
    STATUS     current
    DESCRIPTION
            "An entry contains information applicble to a specific object."
    INDEX      { acdTidInfoIndex }
    ::= { acdTidInfoTable 1 }

AcdTidInfoEntry ::= SEQUENCE {
    acdTidInfoIndex             Unsigned32,
    acdTidInfoOID               OBJECT IDENTIFIER,
    acdTidInfoType              AcdTidType,
    acdTidInfoDescr             DisplayString,
    acdTidInfoLastChangeTid     Unsigned32
}

acdTidInfoIndex OBJECT-TYPE
    SYNTAX      Unsigned32
    MAX-ACCESS  not-accessible
    STATUS      current
    DESCRIPTION
        "A unique value, greater than zero, for each entry."
    ::= { acdTidInfoEntry 1 }

acdTidInfoOID OBJECT-TYPE
    SYNTAX     OBJECT IDENTIFIER
    MAX-ACCESS read-only
    STATUS     current
    DESCRIPTION
            "This object identifies the OID covers by this transaction
             Identifier."
    ::= { acdTidInfoEntry 2 }

acdTidInfoType OBJECT-TYPE
    SYNTAX     AcdTidType
    MAX-ACCESS read-only
    STATUS     current
    DESCRIPTION
       "Indicate if the object is covers by the acdTidCfgLastChangeTid or
        or by the acdTidStatusLastChangeTid transaction identifier."
    ::= { acdTidInfoEntry 3 }

acdTidInfoDescr OBJECT-TYPE
    SYNTAX     DisplayString
    MAX-ACCESS read-only
    STATUS     current
    DESCRIPTION
       "A textual description of the object point by acdTidInfoOID."
    ::= { acdTidInfoEntry 4 }

acdTidInfoLastChangeTid OBJECT-TYPE
    SYNTAX      Unsigned32
    MAX-ACCESS  read-only
    STATUS      current
    DESCRIPTION
       "This is the transaction ID of the last change of a the object
        point by acdTidInfoOID. If this value is different since the 
        last read this is indicate a change."
    ::= { acdTidInfoEntry 5 }

---------------------------------------------------------------------------
 -- Transaction Identifier Global Configuration change
 -- 
---------------------------------------------------------------------------

acdTidglobalCfgChangeCount OBJECT-TYPE
    SYNTAX      Unsigned32
    MAX-ACCESS  read-only
    STATUS      current
    DESCRIPTION
       "This is the number of times a configuration change was detected.
        There may be more than one change per detected event."
    ::= { acdTidGlobalCfg 2 }


-- ***********************************************************
--        ACD-TID-MIB Module -  N O T I F I C A T I O N S
-- *********************************************************** 
acdTidNotificationPrefix OBJECT IDENTIFIER ::= { acdTidNotifications 0 }

acdTidGlobalCfgChange NOTIFICATION-TYPE
    OBJECTS {
        acdTidglobalCfgChangeCount
    }
    STATUS        current
    DESCRIPTION
            "A Configuration Change notification is sent when the system
            has detected that a monitored configuration item has changed

            Note that transmission of acdTidConfigChange notifications
            are throttled by the agent and by the system. The count given
            in actTidCfgChangeCount represent the number of times a change
            was detected by the system. Timing in the agent may skip some
            changes as it is desired not to flood the network with configuration
            changes."
   ::= { acdTidNotificationPrefix 1 }

---------------------------------------------------------------------------
 -- ACD-TID-MIB Module - Conformance Information
---------------------------------------------------------------------------

acdTidCompliances   OBJECT IDENTIFIER ::= { acdTidConformance 1 }
acdTidGroups        OBJECT IDENTIFIER ::= { acdTidConformance 2 }

---------------------------------------------------------------------------
 -- Units of conformance
---------------------------------------------------------------------------

acdTidGeneralGroup OBJECT-GROUP
    OBJECTS {
        acdTidCfgLastChangeTid,
        acdTidStatusLastChangeTid
    }
    STATUS      current
    DESCRIPTION
       "List of scalars to monitior changes in supported object."
    ::= { acdTidGroups 1 }

acdTidTableGroup OBJECT-GROUP
    OBJECTS {
        acdTidInfoOID,
        acdTidInfoType,
        acdTidInfoDescr,
        acdTidInfoLastChangeTid
    }
    STATUS      current
    DESCRIPTION
       "Group for the acdTidTable."
    ::= { acdTidGroups 2 }

acdTidGlobalCfgGroup OBJECT-GROUP
    OBJECTS {
        acdTidglobalCfgChangeCount
    }
    STATUS      current
    DESCRIPTION
       "Group for the acdTidGlobalCfgChange."
    ::= { acdTidGroups 3 }

acdTidNotificationsGroup  NOTIFICATION-GROUP
    NOTIFICATIONS {
        acdTidGlobalCfgChange 
    }
    STATUS      current
    DESCRIPTION
       "Group for the acdTidGlobalConfig."
    ::= { acdTidGroups 4 }

acdTidCompliance MODULE-COMPLIANCE
    STATUS      current
    DESCRIPTION
       "The compliance statement for support of the ACD-TID-MIB module."
    MODULE
        MANDATORY-GROUPS {
            acdTidGeneralGroup,
            acdTidTableGroup,
            acdTidGlobalCfgGroup,
            acdTidNotificationsGroup
         }

    ::= { acdTidCompliances 1 }

END

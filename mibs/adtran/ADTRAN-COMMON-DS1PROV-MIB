ADTRAN-COMMON-DS1PROV-MIB  DEFINITIONS ::= BEGIN

    -- This MIB defines the common DS1 Provisioning MIB.

    IMPORTS
           MODULE-IDENTITY, OBJECT-TYPE
                  FROM SNMPv2-SMI
           ifIndex
                  FROM IF-MIB
           adGenTa5kCommonDs1Prov, adGenTa5kCommonDs1ProvID
                  FROM ADTRAN-GENTA5K-MIB
           ;

adGenCommonDs1ProvMIB MODULE-IDENTITY
        LAST-UPDATED "200711062117Z"
        ORGANIZATION
            "ADTRAN, Inc."
        CONTACT-INFO
            "CND Tech Support
                Postal: ADTRAN, Inc.
                        901 Explorer Blvd.
                        Huntsville, AL  35806
                        Tel: +1 800 726-8663
                        Fax: +1 256 963 6217
                        E-mail: support@adtran.com"
        DESCRIPTION
            "Common DS1 Prov MIB"
        ::= {adGenTa5kCommonDs1ProvID 1}

-- OBJECT IDENTIFIERS

adDs1vgDs1Mgmt                       OBJECT IDENTIFIER ::= { adGenTa5kCommonDs1Prov 1 }

-- ----------------------------------------------------------------------------
--
-- DS1VG Specific Provisioning
--
-- This group contains provisioning information that is specific
-- to DS1VG.
--
-- ----------------------------------------------------------------------------
     adDs1vgT1InterfaceProvisioningTable OBJECT-TYPE
        SYNTAX  SEQUENCE OF AdDs1vgT1InterfaceProvisioningTableEntry
        MAX-ACCESS  not-accessible
        STATUS  current
        DESCRIPTION
            "Table of DS1VG Configuration Table info."
        ::= { adDs1vgDs1Mgmt 1 }

     adDs1vgT1InterfaceProvisioningTableEntry OBJECT-TYPE
        SYNTAX  AdDs1vgT1InterfaceProvisioningTableEntry
        MAX-ACCESS  not-accessible
        STATUS  current
        DESCRIPTION
                   ""
        INDEX   { ifIndex }
        ::= { adDs1vgT1InterfaceProvisioningTable 1 }

    AdDs1vgT1InterfaceProvisioningTableEntry ::=
        SEQUENCE {
           adDs1vgT1InterfaceProvTableLineBuildout
               INTEGER,
           -- adDs1vgT1InterfaceProvTableLineCoding
           --     INTEGER,
           -- adDs1vgT1InterfaceProvTableLineType
           --     INTEGER,
           adDs1vgT1InterfaceProvTableLineMode
               INTEGER,
           -- adDs1vgT1InterfaceProvTableLineStatus
           --     INTEGER
           --adDs1vgT1InterfaceProvTableSetLoopback
           --    INTEGER
           adDs1vgT1InterfaceClearPMCounters
               INTEGER
        }

    adDs1vgT1InterfaceProvTableLineBuildout OBJECT-TYPE
        SYNTAX  INTEGER {
                lineLength0ft(1),
                lineLength0133ft(2),
                lineLength133266ft(3),
                lineLength266399ft(4),
                lineLength399533ft(5),
                lineLength533655ft(6)
                }
        MAX-ACCESS  read-write
        STATUS  current
        DESCRIPTION
            "The line buildout for T1 interface."
        ::= { adDs1vgT1InterfaceProvisioningTableEntry 1 }

   --adDs1vgT1InterfaceProvTableLineCoding OBJECT-TYPE
   --     SYNTAX  INTEGER {
   --             b8zs(2),
   --             ami(5)
   --             }
   --     MAX-ACCESS  read-write
   --     STATUS  current
   --     DESCRIPTION
   --         "The line coding for T1 interface."
   --     ::= { adDs1vgT1InterfaceProvisioningTableEntry 2 }

   --adDs1vgT1InterfaceProvTableLineType OBJECT-TYPE
   --     SYNTAX  INTEGER {
   --             esf(2),
   --             d4(3)
   --             }
   --     MAX-ACCESS  read-write
   --     STATUS  current
   --     DESCRIPTION
   --         "The line type for T1 interface."
   --     ::= { adDs1vgT1InterfaceProvisioningTableEntry 3 }

   adDs1vgT1InterfaceProvTableLineMode OBJECT-TYPE
        SYNTAX  INTEGER {
                gr303cesop(1),
                satop(2)
                }
        MAX-ACCESS  read-write
        STATUS  current
        DESCRIPTION
            "The line mode for T1 interface."
        ::= { adDs1vgT1InterfaceProvisioningTableEntry 2 }

   --adDs1vgT1InterfaceProvTableLineStatus OBJECT-TYPE
   --     SYNTAX  INTEGER {
   --             noalarm(1),
   --             rai(2),
   --             ais(8),
   --             lof(32),
   --             los(64)
   --             }
   --     MAX-ACCESS  read-only
   --     STATUS  current
   --     DESCRIPTION
   --         "The line status for T1 interface."
   --     ::= { adDs1vgT1InterfaceProvisioningTableEntry 3 }

   -- adDs1vgT1InterfaceProvTableLineServiceState OBJECT-TYPE
   --     SYNTAX  INTEGER {
   --             inservice(1),
   --             outofservice(2),
   --             outofserviceunassigned(3)
   --             }
   --     MAX-ACCESS  read-write
   --     STATUS  current
   --     DESCRIPTION
   --         "The line mode for T1 interface."
   --     ::= { adDs1vgT1InterfaceProvisioningTableEntry 4 }

   --adDs1vgT1InterfaceProvTableSetLoopback OBJECT-TYPE
   --     SYNTAX  INTEGER {
   --             noloop(1),
   --             payloadloop(2),
   --             lineloop(3),
   --             localloop(4)
   --             }
   --     MAX-ACCESS  read-write
   --     STATUS  current
   --     DESCRIPTION
   --         "Set T1 loopback for tests."
   --     ::= { adDs1vgT1InterfaceProvisioningTableEntry 3 }

   adDs1vgT1InterfaceClearPMCounters OBJECT-TYPE
        SYNTAX  INTEGER (1)
        MAX-ACCESS  read-write
        STATUS  current
        DESCRIPTION
            "Clear PM counter for T1 interface."
        ::= { adDs1vgT1InterfaceProvisioningTableEntry 3 }
END

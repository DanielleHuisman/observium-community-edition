ADTRAN-COMMON-ERROR-OID-MIB  DEFINITIONS ::= BEGIN

    -- This MIB defines the common DS1 Provisioning MIB.

    IMPORTS
           MODULE-IDENTITY, OBJECT-TYPE
                  FROM SNMPv2-SMI
           DisplayString
                  FROM SNMPv2-TC
           adGenSlotInfoIndex
                  FROM ADTRAN-GENSLOT-MIB
           adGenTa5kErrorOid, adGenTa5kSErrorOidID
                  FROM ADTRAN-GENTA5K-MIB
           ;

adGenCommonErrorOidMIB MODULE-IDENTITY
        LAST-UPDATED "200711062117Z"
        ORGANIZATION
            "ADTRAN, Inc."
        CONTACT-INFO
            "CND Tech Support
                Postal: ADTRAN, Inc.
                        901 Explorer Blvd.
                        Huntsville, AL  35806
                        Tel: +1 800 726-8663
                        Fax: +1 256 963 6217
                        E-mail: support@adtran.com"
        DESCRIPTION
            "Common Error Oid MIB"
        ::= {adGenTa5kSErrorOidID 1}

-- OBJECT IDENTIFIERS

adTa5kErrorOidMgmt                       OBJECT IDENTIFIER ::= { adGenTa5kErrorOid 1 }

     adTa5kErrorOidTable OBJECT-TYPE
        SYNTAX  SEQUENCE OF AdTa5kErrorOidTableEntry
        MAX-ACCESS  not-accessible
        STATUS  current
        DESCRIPTION
            "Table of TA5K common error OIDs."
        ::= { adTa5kErrorOidMgmt 1 }

     adTa5kErrorOidTableEntry OBJECT-TYPE
        SYNTAX  AdTa5kErrorOidTableEntry
        MAX-ACCESS  not-accessible
        STATUS  current
        DESCRIPTION
                   ""
        INDEX   { adGenSlotInfoIndex }
        ::= { adTa5kErrorOidTable 1 }

    AdTa5kErrorOidTableEntry ::=
        SEQUENCE {
           adTa5kDuplicateIndexErrorReporting
               DisplayString,
           adTa5kPseudowireErrorReporting
               DisplayString,
           adTa5kPhysicalDs1ErrorReporting
               DisplayString
        }

    adTa5kDuplicateIndexErrorReporting OBJECT-TYPE
        SYNTAX  DisplayString (SIZE (0..31))
        MAX-ACCESS  read-only
        STATUS  current
        DESCRIPTION
            "Duplicate Index Error Reporting."
        ::= { adTa5kErrorOidTableEntry 1 }

    adTa5kPseudowireErrorReporting OBJECT-TYPE
        SYNTAX  DisplayString (SIZE (0..31))
        MAX-ACCESS  read-only
        STATUS  current
        DESCRIPTION
            "Pseudowire Error Reporting."
        ::= { adTa5kErrorOidTableEntry 2 }

    adTa5kPhysicalDs1ErrorReporting OBJECT-TYPE
        SYNTAX  DisplayString (SIZE (0..31))
        MAX-ACCESS  read-only
        STATUS  current
        DESCRIPTION
            "Physical DS1 Error Reporting."
        ::= { adTa5kErrorOidTableEntry 3 }
END

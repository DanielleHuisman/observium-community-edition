ADTRAN-EFM-MIB

-- TITLE:     The ADTRAN EFM MIB
-- PRODUCT:   ADTRAN EFM PRODUCTS
-- VERSION:   1.0
-- DATE:      2/28/06
-- AUTHOR:    Joey Boyd
-- STATUS:    PRELIMINARY

-- This MIB defines the object identifier (OID) for the
-- ADTRAN EFM MIB objects

-- HISTORY:
-- 02/28/06 jlb STATUS: PRELIMINARY.
-- 03/03/06 jlb Updated to latest requirements.
-- 03/27/06 jlb Added adGenEfmProvGroupSkewThreshold, adGenEfmProvGroupXCVThreshold, and adGenEfmStatGroupStatus.
-- 04/03/06 jlb Added adGenEfmStatGroupSize, adGenEfmStatNumActiveLinks, adGenEfmStatLinkNeTcSync,
--			    and adGenEfmStatLinkFeTcSync
-- 04/04/06 jlb Split adGenEfmPerfGroupCurrTable and adGenEfmPerfLinkCurrTable into 15-Minute and 24-Hour tables.
-- 04/12/06 jlb Changed adGenEfmPerfGroup15MinIntNumber, adGenEfmPerfGroup24HrIntNumber, adGenEfmPerfLink15MinIntNumber,
--				and adGenEfmPerfLink24HrIntNumber to not-accessible access.
--              Added adGenEfmPerfGroup15MinValidIntervals, adGenEfmPerfGroup24HrValidIntervals, adGenEfmPerfLink15MinValidIntervals,
--				and adGenEfmPerfLink24HrValidIntervals.
-- 04/12/06 jlb Moved the ValidIntervals variables to the proper tables.
-- 09/29/06 jlb Added adGenEfmPerfResetGroupData and adGenEfmPerfResetLinkData
-- 10/09/06 jlb Fixed complier errors
-- 01/19/07 jlb Added upPartial(5) to adGenEfmStatGroupStatus
-- 04/05/07 jlb Converted from SNMPv1 to SNMPv2
-- 05/18/07 jlb Added PM thresholds and alarms.
-- 05/29/07 jlb Added adGenEfmProvGroupName
-- 06/08/07 jlb Modified the alarms to be compatible with existing v1 implementation and
--              all future v2 implementations.
-- 06/13/07 SS  Added an entry for Skew status - adGenEfmStatLinkSkew
-- 06/13/07 smm Added the group CRC mode
-- 06/14/07 SS  Added some group and link alarm descriptions.
-- 08/31/07 twc Fixed SMIC compiler errors
-- 10/03/07 jlb Fixed compiler errors
-- 11/06/07 jlb Added comments to the Status table describing which ifIndex types to use.
-- 11/07/07 twc Added the following alarms:
--					adGenEfmGroupDownstreamBandwidthAct
--					adGenEfmGroupUpstreamBandwidthAct
--					adGenEfmGroupDownstream4xRateViolationAct
--					adGenEfmGroupUpstream4xRateViolationAct
-- 03/26/08 jlb Added adGenEfmTestOamRemoteLoopbackTimeout.
-- 03/27/08 jlb Added adGenEfmPerfGroupReset and adGenEfmPerfLinkReset.
-- 04/03/08 jlb Added adGenEfmProvGroupXCVLinkRemoval and updated comments for adGenEfmProvGroupXCVThreshold.
-- 03/13/09 jlb Added adGenEfmProvGroupLoopbackDetection
--              SMIC verified.
-- 04/09/09 jlb Added adGenEfmProvLinkIfAssignment.
--			    SMIC verified.
-- 03/17/10 tkr Added tx and rx percent utilization stats for efm-groups on 15 min and 24 hour current and previous intervals

-- ******************************************************************************************

DEFINITIONS ::= BEGIN

    IMPORTS
        Gauge32,
        TimeTicks,
        Unsigned32,
	Integer32,
        Counter32,
        OBJECT-TYPE,
        MODULE-IDENTITY,
        NOTIFICATION-TYPE
            FROM SNMPv2-SMI
	OBJECT-GROUP,
        NOTIFICATION-GROUP
            FROM SNMPv2-CONF
        sysName
            FROM SNMPv2-MIB
        DisplayString, TruthValue
            FROM SNMPv2-TC
        ifIndex,
		InterfaceIndex
            FROM IF-MIB
        adTrapInformSeqNum
            FROM ADTRAN-GENTRAPINFORM-MIB
        adGenSlotInfoIndex
            FROM ADTRAN-GENSLOT-MIB
       	adGenPortTrapIdentifier
            FROM ADTRAN-GENPORT-MIB
        adGenEfm,
        adGenEfmID
            FROM ADTRAN-SHARED-EFM-MIB
        ;

adGenEfmMIB MODULE-IDENTITY
   LAST-UPDATED "202005110000Z"
   ORGANIZATION "Adtran, Inc."
   CONTACT-INFO "http://www.adtran.com"
   DESCRIPTION
      "This MIB defines the objects for the EFM MIB."

   REVISION "202005110000Z"
   DESCRIPTION "Added support for configuring the EFM group down and group partial
                alarm severities"

   REVISION "201808290000Z"
   DESCRIPTION "Added support for enabling an EFM group to be used as a downlink"

   REVISION "201301180000Z"
   DESCRIPTION "Added support for disabling EFM link down, EFM group down and
                EFM group partial traps."

   REVISION "201112090000Z"
   DESCRIPTION "Added support for free rolling counts."

   REVISION "200704050000Z"
   DESCRIPTION "Created"
::= { adGenEfmID 1 }

-- OBJECT IDENTIFIERS
adGenEfmIndex           	OBJECT IDENTIFIER ::= {adGenEfm 1}
adGenEfmConfiguration   	OBJECT IDENTIFIER ::= {adGenEfm 2}
adGenEfmProvisioning    	OBJECT IDENTIFIER ::= {adGenEfm 3}
adGenEfmStatus          	OBJECT IDENTIFIER ::= {adGenEfm 4}
adGenEfmTest            	OBJECT IDENTIFIER ::= {adGenEfm 5}
adGenEfmPerformance     	OBJECT IDENTIFIER ::= {adGenEfm 6}
adGenEfmMibConformance          OBJECT IDENTIFIER ::= {adGenEfm 7 }
adGenEfmMibGroups               OBJECT IDENTIFIER ::= {adGenEfmMibConformance 1 }

adGenEfmAlarmsPrefix            OBJECT IDENTIFIER ::= {adGenEfm 10}
adGenEfmAlarms                  OBJECT IDENTIFIER ::= {adGenEfmAlarmsPrefix 0}


-- ******************************************************************************************
-- Index
-- ******************************************************************************************

adGenEfmIndexTable OBJECT-TYPE
   SYNTAX      SEQUENCE OF AdGenEfmIndexEntry
   MAX-ACCESS  not-accessible
   STATUS      current
   DESCRIPTION
     "This table declares the indeces to be used in this MIB."
   ::= { adGenEfmIndex 1 }

adGenEfmIndexEntry OBJECT-TYPE
   SYNTAX      AdGenEfmIndexEntry
   MAX-ACCESS  not-accessible
   STATUS      current
   DESCRIPTION
     "An entry in the adGenEfmIndexTable."
   INDEX { ifIndex, adGenEfmUnitIndex }
   ::= { adGenEfmIndexTable 1 }

AdGenEfmIndexEntry ::=
   SEQUENCE
   {
    adGenEfmUnitIndex                           INTEGER
   }

adGenEfmUnitIndex OBJECT-TYPE
   SYNTAX       INTEGER
   				{
				cot(1),        			-- -O subtype from EFM spec, -C from xDSL
				rt(2)                   -- -R subtype from EFM spec, -R from xDSL
				}
   MAX-ACCESS   read-only
   STATUS       current
   DESCRIPTION
     "Each of these represents an element in the EFM span.
	  These will be used to index to the appropriate unit."
   ::= { adGenEfmIndexEntry 1 }


-- ******************************************************************************************
-- Configuration
-- ******************************************************************************************

adGenEfmConfTable OBJECT-TYPE
   SYNTAX      SEQUENCE OF AdGenEfmConfEntry
   MAX-ACCESS  not-accessible
   STATUS      current
   DESCRIPTION
     "This table supports configuration parameters."
   ::= { adGenEfmConfiguration 1 }

adGenEfmConfEntry OBJECT-TYPE
   SYNTAX      AdGenEfmConfEntry
   MAX-ACCESS  not-accessible
   STATUS      current
   DESCRIPTION
     "An entry in the adGenEfmConfTable."
   INDEX { ifIndex, adGenEfmUnitIndex}
   ::= { adGenEfmConfTable 1 }

AdGenEfmConfEntry ::=
   SEQUENCE
   {
   adGenEfmConfMaxGroups			Integer32,
   adGenEfmConfMaxGroupSize			Integer32
   }

adGenEfmConfMaxGroups OBJECT-TYPE
   SYNTAX      	Integer32
   MAX-ACCESS   read-only
   STATUS       current
   DESCRIPTION
     "This object returns the maximum number of
	  EFM groups supported by this unit."
   ::= { adGenEfmConfEntry 1 }

adGenEfmConfMaxGroupSize OBJECT-TYPE
   SYNTAX      	Integer32
   MAX-ACCESS   read-only
   STATUS       current
   DESCRIPTION
     "This object returns the maximum EFM group
	  size supported by this unit."
   ::= { adGenEfmConfEntry 2 }

-- ******************************************************************************************
-- Provisioning
-- ******************************************************************************************

-- ********************************************
-- Unit Provisioning
-- ********************************************
adGenEfmProvTable OBJECT-TYPE
   SYNTAX      SEQUENCE OF AdGenEfmProvEntry
   MAX-ACCESS  not-accessible
   STATUS      current
   DESCRIPTION
     "This table supports unit provisioning variables."
   ::= { adGenEfmProvisioning 1 }

adGenEfmProvEntry OBJECT-TYPE
   SYNTAX      AdGenEfmProvEntry
   MAX-ACCESS  not-accessible
   STATUS      current
   DESCRIPTION
     "An entry in the adGenEfmProvTable."
   INDEX { ifIndex, adGenEfmUnitIndex }
   ::= { adGenEfmProvTable 1 }

AdGenEfmProvEntry ::=
   SEQUENCE
   {
	adGenEfmProvErrorString				OCTET STRING
   }

adGenEfmProvErrorString OBJECT-TYPE
   SYNTAX      	OCTET STRING
   MAX-ACCESS   read-only
   STATUS       current
   DESCRIPTION
     "A textual representation of the error encountered
	  when a provisioning SET returns a generic error."
   ::= { adGenEfmProvEntry 1 }

-- ********************************************
-- EFM Group Provisioning
-- ********************************************
adGenEfmProvGroupTable OBJECT-TYPE
   SYNTAX      SEQUENCE OF AdGenEfmProvGroupEntry
   MAX-ACCESS  not-accessible
   STATUS      current
   DESCRIPTION
     "This table supports EFM Group provisioning variables."
   ::= { adGenEfmProvisioning 2 }

adGenEfmProvGroupEntry OBJECT-TYPE
   SYNTAX      AdGenEfmProvGroupEntry
   MAX-ACCESS  not-accessible
   STATUS      current
   DESCRIPTION
     "An entry in the adGenEfmProvGroupTable."
   INDEX { ifIndex, adGenEfmUnitIndex }
   ::= { adGenEfmProvGroupTable 1 }

AdGenEfmProvGroupEntry ::=
   SEQUENCE
   {
        adGenEfmProvGroupServiceState                INTEGER,
        adGenEfmProvGroupFragmentSize                Integer32,
        adGenEfmProvGroupSkewThreshold               Integer32,
        adGenEfmProvGroupXCVThreshold                INTEGER,
        adGenEfmProvGroupName                        DisplayString,
        adGenEfmProvGroupCRCMode                     INTEGER,
        adGenEfmProvGroupXCVLinkRemoval              INTEGER,
        adGenEfmProvGroupLoopbackDetection           INTEGER,
        adGenEfmProvGroupTrapReportingGroupDown      INTEGER,
        adGenEfmProvGroupTrapReportingGroupPartial   INTEGER,
        adGenEfmProvGroupDownlinkEnable              TruthValue
   }

adGenEfmProvGroupServiceState OBJECT-TYPE
   SYNTAX       INTEGER
               	{
			   	inService(1),
			   	oosUnassigned(2),
			   	oosMaintenance(3)
               	}
   MAX-ACCESS   read-write
   STATUS       current
   DESCRIPTION
     "This entry gets/sets the service state of the selected
	  EFM Group."
   ::= { adGenEfmProvGroupEntry 1 }

adGenEfmProvGroupFragmentSize OBJECT-TYPE
   SYNTAX      	Integer32
   MAX-ACCESS   read-write
   STATUS       current
   DESCRIPTION
     "This entry gets/sets the fragment size used in the EFM
	  Group.  Valid ranges are 64 to 512 bytes."
   ::= { adGenEfmProvGroupEntry 2 }

adGenEfmProvGroupSkewThreshold OBJECT-TYPE
   SYNTAX  Integer32
   MAX-ACCESS  read-write
   STATUS  current
   DESCRIPTION
     "This option is used to enter the maximum allowable skew
      threshold (in milliseconds) for each bonding group.  To disable
      this option, enter 0.  Skew thresholds from 1 millisecond
      to 16 milliseconds (in 1 millisecond intervals) can be selected.
      The default skew threshold is 4 milliseconds.

      A link will automatically be removed from a EFM group if the
      relative skew exceeds the specified threshold.  The link will
      automatically be added back to the group once the relative skew
      is below the threshold (plus 0.50 millisecond of hysteresis)."
   ::= { adGenEfmProvGroupEntry 3 }

adGenEfmProvGroupXCVThreshold OBJECT-TYPE
   SYNTAX  INTEGER
   		   {
    	   disabled(1),
           rate1Eto8(2),
           rate1Eto7(3),
           rate1Eto6(4),
           rate1Eto5(5),
           rate1Eto4(6),
           rate1Eto3(7)
           }
   MAX-ACCESS  read-write
   STATUS  current
   DESCRIPTION
     "This option is used to select the XCV threshold.  A link will
      automatically be removed from a bonding group if the XCV rate
      exceeds the specified threshold.  The link will automatically
      be added back to the group once the XCV rate is below the
      threshold.

      For System Release 4.0 EoCu and EoTDM products, the applicable
      XCV threshold settings will be rate1Eto7, rate1Eto6, and rate1Eto5."
   ::= { adGenEfmProvGroupEntry 4 }

adGenEfmProvGroupName OBJECT-TYPE
   SYNTAX  DisplayString
   MAX-ACCESS  read-write
   STATUS  current
   DESCRIPTION
     "This object sets a display name associated with the selected
      EFM group."
   ::= { adGenEfmProvGroupEntry 5 }

adGenEfmProvGroupCRCMode OBJECT-TYPE
   SYNTAX       INTEGER
                {
                crc16(1),
                crc32(2)
                }
   MAX-ACCESS   read-write
   STATUS       current
   DESCRIPTION
     "This option is used to read or write the EFM fragment CRC
      mode for each bonding group."
   ::= { adGenEfmProvGroupEntry 6 }

adGenEfmProvGroupXCVLinkRemoval OBJECT-TYPE
   SYNTAX       INTEGER
                {
                disabled(1),
                enabled(2)
                }
   MAX-ACCESS   read-write
   STATUS       current
   DESCRIPTION
     "This option is used to specify if a link is to be
      removed from the group when the XCV threshold has been
      exceeded."
   ::= { adGenEfmProvGroupEntry 7 }

adGenEfmProvGroupLoopbackDetection OBJECT-TYPE
   SYNTAX       INTEGER
                {
                disabled(1),
                enabled(2)
                }
   MAX-ACCESS   read-write
   STATUS       current
   DESCRIPTION
     "This option is used to specify if loopback detection is
	  used on each link in the EFM group."
   ::= { adGenEfmProvGroupEntry 8 }

adGenEfmProvGroupTrapReportingGroupDown OBJECT-TYPE
   SYNTAX       INTEGER
                {
                disabled(1),
                enabled(2)
                }
   MAX-ACCESS   read-write
   STATUS       current
   DESCRIPTION
     "This entry is used to disable the EFM group down trap.  This
      object is enabled(2) by default."
   ::= { adGenEfmProvGroupEntry 9 }

adGenEfmProvGroupTrapReportingGroupPartial OBJECT-TYPE
   SYNTAX       INTEGER
                {
                disabled(1),
                enabled(2)
                }
   MAX-ACCESS   read-write
   STATUS       current
   DESCRIPTION
     "This entry is used to disable the EFM group partial trap.  This
      object is enabled(2) by default."
   ::= { adGenEfmProvGroupEntry 10 }

adGenEfmProvGroupDownlinkEnable OBJECT-TYPE
   SYNTAX       TruthValue
   MAX-ACCESS   read-write
   STATUS       current
   DESCRIPTION
     "This entry is used to enable or disable the downlink functionality of an EFM group.
      If set to true, then downstream tree networking will be enabled for the EFM group.
      This object is false by default."
   DEFVAL     { false }
   ::= { adGenEfmProvGroupEntry 11 }

-- ********************************************
-- EFM Link Provisioning
-- ********************************************
adGenEfmProvLinkTable OBJECT-TYPE
   SYNTAX      SEQUENCE OF AdGenEfmProvLinkEntry
   MAX-ACCESS  not-accessible
   STATUS      current
   DESCRIPTION
     "This table supports EFM Link provisioning variables."
   ::= { adGenEfmProvisioning 3 }

adGenEfmProvLinkEntry OBJECT-TYPE
   SYNTAX      AdGenEfmProvLinkEntry
   MAX-ACCESS  not-accessible
   STATUS      current
   DESCRIPTION
     "An entry in the adGenEfmProvLinkTable."
   INDEX { ifIndex, adGenEfmUnitIndex }
   ::= { adGenEfmProvLinkTable 1 }

AdGenEfmProvLinkEntry ::=
   SEQUENCE
   {
    adGenEfmProvLinkAssignment              Integer32,
    adGenEfmProvLinkIfAssignment            InterfaceIndex,
    adGenEfmProvLinkTrapReportingLinkDown   INTEGER
   }

adGenEfmProvLinkAssignment OBJECT-TYPE
   SYNTAX      	Integer32
   MAX-ACCESS   read-write
   STATUS       current
   DESCRIPTION
     "This entry is used to assign a link to a particular
	  EFM Group using the group's logical interface number to
	  identify it.  If a GET returns a 0, it means the link
	  is currently unassigned.  A SET of 0 unassigns the
	  link from its currently assigned group.  If a SET
	  results in a generic error, a GET of adGenEfmProvErrorString
	  will detail the error encountered.  Refer to adGenEfmConfMaxGroupSize
	  to determine the maximum number of links that can
	  be assigned to a group."
   ::= { adGenEfmProvLinkEntry 1 }

adGenEfmProvLinkIfAssignment OBJECT-TYPE
   SYNTAX      	InterfaceIndex
   MAX-ACCESS   read-write
   STATUS       current
   DESCRIPTION
     "This entry is used to assign a link to a particular
	  EFM Group using the group's ifIndex to identify it.
      If a GET returns a 0, it means the link
	  is currently unassigned.  A SET of 0 unassigns the
	  link from its currently assigned group.  If a SET
	  results in a generic error, a GET of adGenEfmProvErrorString
	  will detail the error encountered.  Refer to adGenEfmConfMaxGroupSize
	  to determine the maximum number of links that can
	  be assigned to a group."
   ::= { adGenEfmProvLinkEntry 2 }

adGenEfmProvLinkTrapReportingLinkDown OBJECT-TYPE
   SYNTAX      	INTEGER
                {
                disabled(1),
                enabled(2)
                }
   MAX-ACCESS   read-write
   STATUS       current
   DESCRIPTION
     "This entry is used to disable the EFM Link down trap.  This
      object is enabled(2) by default."
   ::= { adGenEfmProvLinkEntry 3 }

-- ********************************************
-- EFM Group Slot Alarm Provisioning
-- ********************************************
adGenEfmProvGroupAlarmSlotTable    OBJECT-TYPE
   SYNTAX          SEQUENCE OF AdGenEfmProvGroupAlarmSlotEntry
   MAX-ACCESS      not-accessible
   STATUS          current
   DESCRIPTION
      "This table sets alarm severity for all EFM Group interfaces."
   ::= { adGenEfmProvisioning 4 }

adGenEfmProvGroupAlarmSlotEntry    OBJECT-TYPE
   SYNTAX          AdGenEfmProvGroupAlarmSlotEntry
   MAX-ACCESS      not-accessible
   STATUS          current
   DESCRIPTION
      ""
   INDEX { adGenSlotInfoIndex }
   ::= { adGenEfmProvGroupAlarmSlotTable 1}

AdGenEfmProvGroupAlarmSlotEntry ::=
   SEQUENCE {
       adGenEfmProvGroupAlarmSlotGroupDownSeverity               INTEGER,
       adGenEfmProvGroupAlarmSlotGroupPartialSeverity            INTEGER
}

adGenEfmProvGroupAlarmSlotGroupDownSeverity OBJECT-TYPE
   SYNTAX INTEGER {
                        info(2),
                        alert(3),
                        minor(4),
                        major(5),
                        critical(6)
                  }
   MAX-ACCESS read-write
   STATUS current
   DESCRIPTION
        "Sets the Group Down alarm severity (affects all EFM Groups)"
   DEFVAL    { major }
   ::= { adGenEfmProvGroupAlarmSlotEntry 1 }

adGenEfmProvGroupAlarmSlotGroupPartialSeverity OBJECT-TYPE
   SYNTAX INTEGER {
                        info(2),
                        alert(3),
                        minor(4),
                        major(5),
                        critical(6)
                  }
   MAX-ACCESS read-write
   STATUS current
   DESCRIPTION
        "Sets the Group Partial alarm severity (affects all EFM Groups)"
   DEFVAL    { minor }
   ::= { adGenEfmProvGroupAlarmSlotEntry 2 }


-- ******************************************************************************************
-- Status
-- ******************************************************************************************
adGenEfmStatTable OBJECT-TYPE
   SYNTAX      SEQUENCE OF AdGenEfmStatEntry
   MAX-ACCESS  not-accessible
   STATUS      current
   DESCRIPTION
     "This table supports unit level status. The existance of columnar objects in each row
      is determined by the type of ifIndex used to access rows. Group ifIndexes can access
      group objects, and link ifIndexes can access link objects. These are specifically
      identified in each object."

   ::= { adGenEfmStatus 1 }

adGenEfmStatEntry OBJECT-TYPE
   SYNTAX      AdGenEfmStatEntry
   MAX-ACCESS  not-accessible
   STATUS      current
   DESCRIPTION
     "An entry in the adGenEfmStatTable."
   INDEX { ifIndex }
   ::= { adGenEfmStatTable 1 }

AdGenEfmStatEntry ::=
   SEQUENCE
   {
   adGenEfmStatGroupStatus                      INTEGER,
   adGenEfmStatGroupSize			Integer32,
   adGenEfmStatNumActiveLinks		Integer32,
   adGenEfmStatLinkNeTcSync                     INTEGER,
   adGenEfmStatLinkFeTcSync                     INTEGER,
   adGenEfmStatLinkSkew             Integer32
   }

adGenEfmStatGroupStatus OBJECT-TYPE
   SYNTAX      INTEGER
   			   {
			   up(1),
			   down(2),
			   testing(3),
			   noLinksInGroup(4),
			   upPartial(5)
			   }
   MAX-ACCESS  read-only
   STATUS      current
   DESCRIPTION
     "The current status of the selected group.  Uses the group ifIndex."
   ::= { adGenEfmStatEntry 1 }

adGenEfmStatGroupSize OBJECT-TYPE
   SYNTAX      Integer32
   MAX-ACCESS  read-only
   STATUS      current
   DESCRIPTION
     "Returns the number of links currently
          assigned to this group.  Uses the group ifIndex."
   ::= { adGenEfmStatEntry 2 }

adGenEfmStatNumActiveLinks OBJECT-TYPE
   SYNTAX      Integer32
   MAX-ACCESS  read-only
   STATUS      current
   DESCRIPTION
     "Returns the number of links, assigned to
          this group, that are currently active.  Uses the group ifIndex."
   ::= { adGenEfmStatEntry 3 }

adGenEfmStatLinkNeTcSync OBJECT-TYPE
   SYNTAX      INTEGER
   			   {
			   yes(1),
			   no(2)
			   }
   MAX-ACCESS  read-only
   STATUS      current
   DESCRIPTION
     "Returns whether or not the near-end of
	  the selected link has achieved 64/65
          octet synchronization.  Uses the link ifIndex."
   ::= { adGenEfmStatEntry 4 }

adGenEfmStatLinkFeTcSync OBJECT-TYPE
   SYNTAX      INTEGER
   			   {
			   yes(1),
			   no(2)
			   }
   MAX-ACCESS  read-only
   STATUS      current
   DESCRIPTION
     "Returns whether or not the far-end of
	  the selected link has achieved 64/65
          octet synchronization.  Uses the link ifIndex."
   ::= { adGenEfmStatEntry 5 }

adGenEfmStatLinkSkew OBJECT-TYPE
   SYNTAX      Integer32
   MAX-ACCESS  read-only
   STATUS      current
   DESCRIPTION
     "Returns the skew of the link in the group.  Uses the link ifIndex."
   ::= { adGenEfmStatEntry 6 }

-- ******************************************************************************************
-- Test
-- ******************************************************************************************
adGenEfmTestTable OBJECT-TYPE
   SYNTAX      SEQUENCE OF AdGenEfmTestEntry
   MAX-ACCESS  not-accessible
   STATUS      current
   DESCRIPTION
     "This table supports EFM test parameters."
   ::= { adGenEfmTest 1 }

adGenEfmTestEntry OBJECT-TYPE
   SYNTAX      AdGenEfmTestEntry
   MAX-ACCESS  not-accessible
   STATUS      current
   DESCRIPTION
     "An entry in the adGenEfmTestTable."
   INDEX { ifIndex }
   ::= { adGenEfmTestTable 1 }

AdGenEfmTestEntry ::=
   SEQUENCE
   {
        adGenEfmTestOamRemoteLoopback           INTEGER,
        adGenEfmTestOamRemoteLoopbackTimeout    Integer32
   }

adGenEfmTestOamRemoteLoopback OBJECT-TYPE
   SYNTAX       INTEGER
   				{
				enable(1),
				disable(2)
				}
   MAX-ACCESS   read-write
   STATUS       current
   DESCRIPTION
     "Causes the COT to send a IEEE 802.3ah OAM Remote
	  Loopback message to the RT."
	::= { adGenEfmTestEntry 1 }

adGenEfmTestOamRemoteLoopbackTimeout OBJECT-TYPE
   SYNTAX       Integer32
   MAX-ACCESS   read-write
   STATUS       current
   DESCRIPTION
     "Optional timeout for taking down the loopback once in place.
        Values are 0 to 60 minutes where 0 means the timeout is disabled."
        ::= { adGenEfmTestEntry 2 }



-- ******************************************************************************************
-- Performance
-- ******************************************************************************************

-- ********************************************
-- EFM Group Performance, Current 15-Minute
-- ********************************************
adGenEfmPerfGroupCurr15MinTable OBJECT-TYPE
   SYNTAX      SEQUENCE OF AdGenEfmPerfGroupCurr15MinEntry
   MAX-ACCESS  not-accessible
   STATUS      current
   DESCRIPTION
     "This table supports EFM Group Current Performance"
   ::= { adGenEfmPerformance 1 }

adGenEfmPerfGroupCurr15MinEntry OBJECT-TYPE
   SYNTAX      AdGenEfmPerfGroupCurr15MinEntry
   MAX-ACCESS  not-accessible
   STATUS      current
   DESCRIPTION
     "An entry in the adGenEfmPerfGroupCurr15MinTable."
   INDEX { ifIndex, adGenEfmUnitIndex }
   ::= { adGenEfmPerfGroupCurr15MinTable 1 }

AdGenEfmPerfGroupCurr15MinEntry ::=
   SEQUENCE
   {
        adGenEfmPerfGroupCurr15MinTxOctets              Gauge32,
        adGenEfmPerfGroupCurr15MinTxFrames                      Gauge32,
        adGenEfmPerfGroupCurr15MinRxOctets              Gauge32,
        adGenEfmPerfGroupCurr15MinRxFrames              Gauge32,
        adGenEfmPerfGroupCurr15MinRxBadFragments        Gauge32,
        adGenEfmPerfGroupCurr15MinRxLostFragments   Gauge32,
        adGenEfmPerfGroupCurr15MinRxLostStarts      Gauge32,
        adGenEfmPerfGroupCurr15MinRxLostEnds        Gauge32,
		adGenEfmPerfGroup15MinValidIntervals		Integer32,
		adGenEfmPerfGroupCurr15MinTxPercUtil			Gauge32,
		adGenEfmPerfGroupCurr15MinRxPercUtil			Gauge32
   }

adGenEfmPerfGroupCurr15MinTxOctets OBJECT-TYPE
   SYNTAX       Gauge32
   MAX-ACCESS   read-only
   STATUS       current
   DESCRIPTION
     "The number of octets transmitted over this EFM group
	  during the current 15-Minute interval."
   ::= { adGenEfmPerfGroupCurr15MinEntry 1 }

adGenEfmPerfGroupCurr15MinTxFrames OBJECT-TYPE
   SYNTAX       Gauge32
   MAX-ACCESS   read-only
   STATUS       current
   DESCRIPTION
     "The number of frames transmitted over this EFM group
	  during the current 15-Minute interval."
   ::= { adGenEfmPerfGroupCurr15MinEntry 2 }

adGenEfmPerfGroupCurr15MinRxOctets OBJECT-TYPE
   SYNTAX       Gauge32
   MAX-ACCESS   read-only
   STATUS       current
   DESCRIPTION
     "The number of octets received over this EFM group
	  during the current 15-Minute interval."
   ::= { adGenEfmPerfGroupCurr15MinEntry 3 }

adGenEfmPerfGroupCurr15MinRxFrames OBJECT-TYPE
   SYNTAX       Gauge32
   MAX-ACCESS   read-only
   STATUS       current
   DESCRIPTION
     "The number of frames received over this EFM group
	  during the current 15-Minute interval."
   ::= { adGenEfmPerfGroupCurr15MinEntry 4 }

adGenEfmPerfGroupCurr15MinRxBadFragments OBJECT-TYPE
   SYNTAX       Gauge32
   MAX-ACCESS   read-only
   STATUS       current
   DESCRIPTION
     "The number of fragment sequence errors over this
	  EFM group during the current 15-Minute interval."
   ::= { adGenEfmPerfGroupCurr15MinEntry 5 }

adGenEfmPerfGroupCurr15MinRxLostFragments OBJECT-TYPE
   SYNTAX       Gauge32
   MAX-ACCESS   read-only
   STATUS       current
   DESCRIPTION
     "The number of gaps in the sequence of frames that
	  have been received across the gamma interface
	  during the current 15-Minute interval."
   ::= { adGenEfmPerfGroupCurr15MinEntry 6 }

adGenEfmPerfGroupCurr15MinRxLostStarts OBJECT-TYPE
   SYNTAX       Gauge32
   MAX-ACCESS   read-only
   STATUS       current
   DESCRIPTION
     "The number of missing StartOfPacket indicators
	  during the current 15-Minute interval."
   ::= { adGenEfmPerfGroupCurr15MinEntry 7 }

adGenEfmPerfGroupCurr15MinRxLostEnds OBJECT-TYPE
   SYNTAX       Gauge32
   MAX-ACCESS   read-only
   STATUS       current
   DESCRIPTION
     "The number of missing EndOfPacket indicators
	  during the current 15-Minute interval."
   ::= { adGenEfmPerfGroupCurr15MinEntry 8 }

adGenEfmPerfGroup15MinValidIntervals OBJECT-TYPE
   SYNTAX      	Integer32
   MAX-ACCESS   read-only
   STATUS       current
   DESCRIPTION
     "The number of valid 15-Minute intervals."
   ::= { adGenEfmPerfGroupCurr15MinEntry 9 }

adGenEfmPerfGroupCurr15MinTxPercUtil OBJECT-TYPE
SYNTAX       Gauge32
UNITS		"0.01%"
MAX-ACCESS   read-only
STATUS       current
DESCRIPTION
 "The percentage utilization of bits sent vs
  Tx bits available during the current 15-min interval."
	::= { adGenEfmPerfGroupCurr15MinEntry 10 }

adGenEfmPerfGroupCurr15MinRxPercUtil OBJECT-TYPE
SYNTAX       Gauge32
UNITS		"0.01%"
MAX-ACCESS   read-only
STATUS       current
DESCRIPTION
 "The percentage utilization of bits received vs
  Rx bits available during the current 15-min interval."
	::= { adGenEfmPerfGroupCurr15MinEntry 11 }


-- ********************************************
-- EFM Group Performance, Current 24-Hour
-- ********************************************
adGenEfmPerfGroupCurr24HrTable OBJECT-TYPE
   SYNTAX      SEQUENCE OF AdGenEfmPerfGroupCurr24HrEntry
   MAX-ACCESS  not-accessible
   STATUS      current
   DESCRIPTION
     "This table supports EFM Group Current Performance"
   ::= { adGenEfmPerformance 2 }

adGenEfmPerfGroupCurr24HrEntry OBJECT-TYPE
   SYNTAX      AdGenEfmPerfGroupCurr24HrEntry
   MAX-ACCESS  not-accessible
   STATUS      current
   DESCRIPTION
     "An entry in the adGenEfmPerfGroupCurr24HrTable."
   INDEX { ifIndex, adGenEfmUnitIndex }
   ::= { adGenEfmPerfGroupCurr24HrTable 1 }

AdGenEfmPerfGroupCurr24HrEntry ::=
   SEQUENCE
   {
        adGenEfmPerfGroupCurr24HrTxOctets                       Gauge32,
        adGenEfmPerfGroupCurr24HrTxFrames                       Gauge32,
        adGenEfmPerfGroupCurr24HrRxOctets                       Gauge32,
        adGenEfmPerfGroupCurr24HrRxFrames                       Gauge32,
        adGenEfmPerfGroupCurr24HrRxBadFragments         Gauge32,
        adGenEfmPerfGroupCurr24HrRxLostFragments        Gauge32,
        adGenEfmPerfGroupCurr24HrRxLostStarts           Gauge32,
        adGenEfmPerfGroupCurr24HrRxLostEnds             Gauge32,
	    adGenEfmPerfGroup24HrValidIntervals			Integer32,
		adGenEfmPerfGroupCurr24HrTxPercUtil			Gauge32,
		adGenEfmPerfGroupCurr24HrRxPercUtil			Gauge32
   }

adGenEfmPerfGroupCurr24HrTxOctets OBJECT-TYPE
   SYNTAX       Gauge32
   MAX-ACCESS   read-only
   STATUS       current
   DESCRIPTION
     "The number of octets transmitted over this EFM group
	  during the current 24-Hour interval."
   ::= { adGenEfmPerfGroupCurr24HrEntry 1 }

adGenEfmPerfGroupCurr24HrTxFrames OBJECT-TYPE
   SYNTAX       Gauge32
   MAX-ACCESS   read-only
   STATUS       current
   DESCRIPTION
     "The number of frames transmitted over this EFM group
	  during the current 24-Hour interval."
   ::= { adGenEfmPerfGroupCurr24HrEntry 2 }

adGenEfmPerfGroupCurr24HrRxOctets OBJECT-TYPE
   SYNTAX       Gauge32
   MAX-ACCESS   read-only
   STATUS       current
   DESCRIPTION
     "The number of octets received over this EFM group
	  during the current 24-Hour interval."
   ::= { adGenEfmPerfGroupCurr24HrEntry 3 }

adGenEfmPerfGroupCurr24HrRxFrames OBJECT-TYPE
   SYNTAX       Gauge32
   MAX-ACCESS   read-only
   STATUS       current
   DESCRIPTION
     "The number of frames received over this EFM group
	  during the current 24-Hour interval."
   ::= { adGenEfmPerfGroupCurr24HrEntry 4 }

adGenEfmPerfGroupCurr24HrRxBadFragments OBJECT-TYPE
   SYNTAX       Gauge32
   MAX-ACCESS   read-only
   STATUS       current
   DESCRIPTION
     "The number of fragment sequence errors over this
	  EFM group during the current 24-Hour interval."
   ::= { adGenEfmPerfGroupCurr24HrEntry 5 }

adGenEfmPerfGroupCurr24HrRxLostFragments OBJECT-TYPE
   SYNTAX       Gauge32
   MAX-ACCESS   read-only
   STATUS       current
   DESCRIPTION
     "The number of gaps in the sequence of frames that
	  have been received across the gamma interface
	  during the current 24-Hour interval."
   ::= { adGenEfmPerfGroupCurr24HrEntry 6 }

adGenEfmPerfGroupCurr24HrRxLostStarts OBJECT-TYPE
   SYNTAX       Gauge32
   MAX-ACCESS   read-only
   STATUS       current
   DESCRIPTION
     "The number of missing StartOfPacket indicators
	  during the current 24-Hour interval."
   ::= { adGenEfmPerfGroupCurr24HrEntry 7 }

adGenEfmPerfGroupCurr24HrRxLostEnds OBJECT-TYPE
   SYNTAX       Gauge32
   MAX-ACCESS   read-only
   STATUS       current
   DESCRIPTION
     "The number of missing EndOfPacket indicators
	  during the current 24-Hour interval."
   ::= { adGenEfmPerfGroupCurr24HrEntry 8 }

adGenEfmPerfGroup24HrValidIntervals OBJECT-TYPE
   SYNTAX      	Integer32
   MAX-ACCESS   read-only
   STATUS       current
   DESCRIPTION
     "The number of valid 24-Hour intervals."
   ::= { adGenEfmPerfGroupCurr24HrEntry 9 }

adGenEfmPerfGroupCurr24HrTxPercUtil OBJECT-TYPE
SYNTAX      	Gauge32
UNITS		"0.01%"
MAX-ACCESS   read-only
STATUS       current
DESCRIPTION
 "Percent utilization of bits transmitted vs bits available
 during current 24-Hour interval."
::= { adGenEfmPerfGroupCurr24HrEntry 10 }

adGenEfmPerfGroupCurr24HrRxPercUtil OBJECT-TYPE
SYNTAX      	Gauge32
UNITS		"0.01%"
MAX-ACCESS   read-only
STATUS       current
DESCRIPTION
 "Percent utilization of bits received vs bits available
 during current 24-Hour interval."
::= { adGenEfmPerfGroupCurr24HrEntry 11 }



-- ********************************************
-- EFM Group Performance, 15-Minute Interval
-- ********************************************
adGenEfmPerfGroup15MinIntTable OBJECT-TYPE
   SYNTAX      SEQUENCE OF AdGenEfmPerfGroup15MinIntEntry
   MAX-ACCESS  not-accessible
   STATUS      current
   DESCRIPTION
     "This table supports EFM Group 15-Minute Interval Performance"
   ::= { adGenEfmPerformance 3 }

adGenEfmPerfGroup15MinIntEntry OBJECT-TYPE
   SYNTAX      AdGenEfmPerfGroup15MinIntEntry
   MAX-ACCESS  not-accessible
   STATUS      current
   DESCRIPTION
     "An entry in the adGenEfmPerfGroup15MinIntTable."
   INDEX { ifIndex, adGenEfmUnitIndex, adGenEfmPerfGroup15MinIntNumber }
   ::= { adGenEfmPerfGroup15MinIntTable 1 }

AdGenEfmPerfGroup15MinIntEntry ::=
   SEQUENCE
   {
        adGenEfmPerfGroup15MinIntNumber                         Gauge32,
        adGenEfmPerfGroup15MinIntTxOctets                       Gauge32,
        adGenEfmPerfGroup15MinIntTxFrames                       Gauge32,
        adGenEfmPerfGroup15MinIntRxOctets                       Gauge32,
        adGenEfmPerfGroup15MinIntRxFrames                       Gauge32,
        adGenEfmPerfGroup15MinIntRxBadFragments         Gauge32,
        adGenEfmPerfGroup15MinIntRxLostFragments    Gauge32,
        adGenEfmPerfGroup15MinIntRxLostStarts       Gauge32,
        adGenEfmPerfGroup15MinIntRxLostEnds         Gauge32,
		adGenEfmPerfGroup15MinIntTxPercUtil       Gauge32,
        adGenEfmPerfGroup15MinIntRxPercUtil         Gauge32
   }

adGenEfmPerfGroup15MinIntNumber OBJECT-TYPE
   SYNTAX       Gauge32
   MAX-ACCESS   read-only
   STATUS       current
   DESCRIPTION
     "15-minute performance interval.  Interval 1 represents the most recent
	  previous interval.  Interval 96 represents 24 hours ago.  Intervals 2
	  through 96 are optional."
   ::= { adGenEfmPerfGroup15MinIntEntry 1 }

adGenEfmPerfGroup15MinIntTxOctets OBJECT-TYPE
   SYNTAX       Gauge32
   MAX-ACCESS   read-only
   STATUS       current
   DESCRIPTION
     "The number of octets transmitted over this EFM group
	  during the selected 15-Minute interval."
   ::= { adGenEfmPerfGroup15MinIntEntry 2 }

adGenEfmPerfGroup15MinIntTxFrames OBJECT-TYPE
   SYNTAX       Gauge32
   MAX-ACCESS   read-only
   STATUS       current
   DESCRIPTION
     "The number of frames transmitted over this EFM group
	  during the selected 15-Minute interval."
   ::= { adGenEfmPerfGroup15MinIntEntry 3 }

adGenEfmPerfGroup15MinIntRxOctets OBJECT-TYPE
   SYNTAX       Gauge32
   MAX-ACCESS   read-only
   STATUS       current
   DESCRIPTION
     "The number of octets received over this EFM group
	  during the selected 15-Minute interval."
   ::= { adGenEfmPerfGroup15MinIntEntry 4 }

adGenEfmPerfGroup15MinIntRxFrames OBJECT-TYPE
   SYNTAX       Gauge32
   MAX-ACCESS   read-only
   STATUS       current
   DESCRIPTION
     "The number of frames received over this EFM group
	  during the selected 15-Minute interval."
   ::= { adGenEfmPerfGroup15MinIntEntry 5 }

adGenEfmPerfGroup15MinIntRxBadFragments OBJECT-TYPE
   SYNTAX       Gauge32
   MAX-ACCESS   read-only
   STATUS       current
   DESCRIPTION
     "The number of fragment sequence errors over this
	  EFM group during the selected 15-Minute interval."
   ::= { adGenEfmPerfGroup15MinIntEntry 6 }

adGenEfmPerfGroup15MinIntRxLostFragments OBJECT-TYPE
   SYNTAX       Gauge32
   MAX-ACCESS   read-only
   STATUS       current
   DESCRIPTION
     "The number of gaps in the sequence of frames that
	  have been received across the gamma interface
	  during the selected 15-Minute interval."
   ::= { adGenEfmPerfGroup15MinIntEntry 7 }

adGenEfmPerfGroup15MinIntRxLostStarts OBJECT-TYPE
   SYNTAX       Gauge32
   MAX-ACCESS   read-only
   STATUS       current
   DESCRIPTION
     "The number of missing StartOfPacket indicators
	  during the selected 15-Minute interval."
   ::= { adGenEfmPerfGroup15MinIntEntry 8 }

adGenEfmPerfGroup15MinIntRxLostEnds OBJECT-TYPE
   SYNTAX       Gauge32
   MAX-ACCESS   read-only
   STATUS       current
   DESCRIPTION
     "The number of missing EndOfPacket indicators
	  during the selected 15-Minute interval."
   ::= { adGenEfmPerfGroup15MinIntEntry 9 }

adGenEfmPerfGroup15MinIntTxPercUtil OBJECT-TYPE
   SYNTAX       Gauge32
   UNITS		"0.01%"
   MAX-ACCESS   read-only
   STATUS       current
   DESCRIPTION
     "The percent utilization of bits available vs
	 bits Tx'd during the selected 15-Minute interval."
::= { adGenEfmPerfGroup15MinIntEntry 10 }

adGenEfmPerfGroup15MinIntRxPercUtil OBJECT-TYPE
   SYNTAX       Gauge32
   UNITS		"0.01%"
   MAX-ACCESS   read-only
   STATUS       current
   DESCRIPTION
     "The percent utilization of bits available vs
	 bits Rx'd during the selected 15-Minute interval."
::= { adGenEfmPerfGroup15MinIntEntry 11 }


-- ********************************************
-- EFM Group Performance, 24-Hour Interval
-- ********************************************
adGenEfmPerfGroup24HrIntTable OBJECT-TYPE
   SYNTAX      SEQUENCE OF AdGenEfmPerfGroup24HrIntEntry
   MAX-ACCESS  not-accessible
   STATUS      current
   DESCRIPTION
     "This table supports EFM Group 24-Hour Interval Performance"
   ::= { adGenEfmPerformance 4 }

adGenEfmPerfGroup24HrIntEntry OBJECT-TYPE
   SYNTAX      AdGenEfmPerfGroup24HrIntEntry
   MAX-ACCESS  not-accessible
   STATUS      current
   DESCRIPTION
     "An entry in the adGenEfmPerfGroup24HrIntTable."
   INDEX { ifIndex, adGenEfmUnitIndex, adGenEfmPerfGroup24HrIntNumber }
   ::= { adGenEfmPerfGroup24HrIntTable 1 }

AdGenEfmPerfGroup24HrIntEntry ::=
   SEQUENCE
   {
        adGenEfmPerfGroup24HrIntNumber                          Gauge32,
        adGenEfmPerfGroup24HrIntTxOctets                        Gauge32,
        adGenEfmPerfGroup24HrIntTxFrames                        Gauge32,
        adGenEfmPerfGroup24HrIntRxOctets                        Gauge32,
        adGenEfmPerfGroup24HrIntRxFrames                        Gauge32,
        adGenEfmPerfGroup24HrIntRxBadFragments          Gauge32,
        adGenEfmPerfGroup24HrIntRxLostFragments     Gauge32,
        adGenEfmPerfGroup24HrIntRxLostStarts        Gauge32,
        adGenEfmPerfGroup24HrIntRxLostEnds          Gauge32,
		adGenEfmPerfGroup24HrIntTxPercUtil        Gauge32,
        adGenEfmPerfGroup24HrIntRxPercUtil          Gauge32
   }

adGenEfmPerfGroup24HrIntNumber OBJECT-TYPE
   SYNTAX       Gauge32
   MAX-ACCESS   read-only
   STATUS       current
   DESCRIPTION
     "24-hour performance interval.  Interval 1 represents the most recent
	  previous interval.  Interval 30 represents 30 days ago.  Intervals 2
	  through 30 are optional."
   ::= { adGenEfmPerfGroup24HrIntEntry 1 }

adGenEfmPerfGroup24HrIntTxOctets OBJECT-TYPE
   SYNTAX       Gauge32
   MAX-ACCESS   read-only
   STATUS       current
   DESCRIPTION
     "The number of octets transmitted over this EFM group
	  during the selected 24-Hour interval."
   ::= { adGenEfmPerfGroup24HrIntEntry 2 }

adGenEfmPerfGroup24HrIntTxFrames OBJECT-TYPE
   SYNTAX       Gauge32
   MAX-ACCESS   read-only
   STATUS       current
   DESCRIPTION
     "The number of frames transmitted over this EFM group
	  during the selected 24-Hour interval."
   ::= { adGenEfmPerfGroup24HrIntEntry 3 }

adGenEfmPerfGroup24HrIntRxOctets OBJECT-TYPE
   SYNTAX       Gauge32
   MAX-ACCESS   read-only
   STATUS       current
   DESCRIPTION
     "The number of octets received over this EFM group
	  during the selected 24-Hour interval."
   ::= { adGenEfmPerfGroup24HrIntEntry 4 }

adGenEfmPerfGroup24HrIntRxFrames OBJECT-TYPE
   SYNTAX       Gauge32
   MAX-ACCESS   read-only
   STATUS       current
   DESCRIPTION
     "The number of frames received over this EFM group
	  during the selected 24-Hour interval."
   ::= { adGenEfmPerfGroup24HrIntEntry 5 }

adGenEfmPerfGroup24HrIntRxBadFragments OBJECT-TYPE
   SYNTAX       Gauge32
   MAX-ACCESS   read-only
   STATUS       current
   DESCRIPTION
     "The number of fragment sequence errors over this
	  EFM group during the selected 24-Hour interval."
   ::= { adGenEfmPerfGroup24HrIntEntry 6 }

adGenEfmPerfGroup24HrIntRxLostFragments OBJECT-TYPE
   SYNTAX       Gauge32
   MAX-ACCESS   read-only
   STATUS       current
   DESCRIPTION
     "The number of gaps in the sequence of frames that
	  have been received across the gamma interface
	  during the selected 24-Hour interval."
   ::= { adGenEfmPerfGroup24HrIntEntry 7 }

adGenEfmPerfGroup24HrIntRxLostStarts OBJECT-TYPE
   SYNTAX       Gauge32
   MAX-ACCESS   read-only
   STATUS       current
   DESCRIPTION
     "The number of missing StartOfPacket indicators
	  during the selected 24-Hour interval."
   ::= { adGenEfmPerfGroup24HrIntEntry 8 }

adGenEfmPerfGroup24HrIntRxLostEnds OBJECT-TYPE
   SYNTAX       Gauge32
   MAX-ACCESS   read-only
   STATUS       current
   DESCRIPTION
     "The number of missing EndOfPacket indicators
	  during the selected 24-Hour interval."
   ::= { adGenEfmPerfGroup24HrIntEntry 9 }

adGenEfmPerfGroup24HrIntTxPercUtil OBJECT-TYPE
   SYNTAX       Gauge32
   UNITS		"0.01%"
   MAX-ACCESS   read-only
   STATUS       current
   DESCRIPTION
     "The percent utilization of bits Tx'd vs
	  Bits available during the selected 24-Hour interval."
   ::= { adGenEfmPerfGroup24HrIntEntry 10 }

adGenEfmPerfGroup24HrIntRxPercUtil OBJECT-TYPE
   SYNTAX       Gauge32
   UNITS		"0.01%"
   MAX-ACCESS   read-only
   STATUS       current
   DESCRIPTION
     "The percent utilization of bits Rx'd vs
	  Bits available during the selected 24-Hour interval."
   ::= { adGenEfmPerfGroup24HrIntEntry 11 }

-- ********************************************
-- EFM Link Performance, Current 15-Minute
-- ********************************************
adGenEfmPerfLinkCurr15MinTable OBJECT-TYPE
   SYNTAX      SEQUENCE OF AdGenEfmPerfLinkCurr15MinEntry
   MAX-ACCESS  not-accessible
   STATUS      current
   DESCRIPTION
     "This table supports EFM Link Current Performance"
   ::= { adGenEfmPerformance 5 }

adGenEfmPerfLinkCurr15MinEntry OBJECT-TYPE
   SYNTAX      AdGenEfmPerfLinkCurr15MinEntry
   MAX-ACCESS  not-accessible
   STATUS      current
   DESCRIPTION
     "An entry in the adGenEfmPerfLinkCurr15MinTable."
   INDEX { ifIndex, adGenEfmUnitIndex }
   ::= { adGenEfmPerfLinkCurr15MinTable 1 }

AdGenEfmPerfLinkCurr15MinEntry ::=
   SEQUENCE
   {
        adGenEfmPerfLinkCurr15MinTxFragments                    Gauge32,
        adGenEfmPerfLinkCurr15MinRxFragments                    Gauge32,
        adGenEfmPerfLinkCurr15MinRxErroredFragments     Gauge32,
        adGenEfmPerfLinkCurr15MinRxSmallFragments               Gauge32,
        adGenEfmPerfLinkCurr15MinRxLargeFragments       Gauge32,
        adGenEfmPerfLinkCurr15MinRxDiscardedFragments   Gauge32,
        adGenEfmPerfLinkCurr15MinRxFcsErrors                    Gauge32,
        adGenEfmPerfLinkCurr15MinRxCodingErrors                 Gauge32,
	adGenEfmPerfLink15MinValidIntervals				Integer32
   }

adGenEfmPerfLinkCurr15MinTxFragments OBJECT-TYPE
   SYNTAX       Gauge32
   MAX-ACCESS   read-only
   STATUS       current
   DESCRIPTION
     "The number of fragments transmitted over this EFM Link
	  during the current 15-Minute interval."
   ::= { adGenEfmPerfLinkCurr15MinEntry 1 }

adGenEfmPerfLinkCurr15MinRxFragments OBJECT-TYPE
   SYNTAX       Gauge32
   MAX-ACCESS   read-only
   STATUS       current
   DESCRIPTION
     "The number of fragments received over this EFM Link
	  during the current 15-Minute interval."
   ::= { adGenEfmPerfLinkCurr15MinEntry 2 }

adGenEfmPerfLinkCurr15MinRxErroredFragments OBJECT-TYPE
   SYNTAX       Gauge32
   MAX-ACCESS   read-only
   STATUS       current
   DESCRIPTION
     "The number of errored fragments received over this EFM Link
	  during the current 15-Minute interval."
   ::= { adGenEfmPerfLinkCurr15MinEntry 3 }

adGenEfmPerfLinkCurr15MinRxSmallFragments OBJECT-TYPE
   SYNTAX       Gauge32
   MAX-ACCESS   read-only
   STATUS       current
   DESCRIPTION
     "The number of fragments received over this EFM Link
	  during the current 15-Minute interval that are smaller
	  than the minimum fragment size (64 bytes)."
   ::= { adGenEfmPerfLinkCurr15MinEntry 4 }

adGenEfmPerfLinkCurr15MinRxLargeFragments OBJECT-TYPE
   SYNTAX       Gauge32
   MAX-ACCESS   read-only
   STATUS       current
   DESCRIPTION
     "The number of fragments received over this EFM Link
	  during the current 15-Minute interval that are larger
	  than the maximum fragment size (512 bytes)."
   ::= { adGenEfmPerfLinkCurr15MinEntry 5 }

adGenEfmPerfLinkCurr15MinRxDiscardedFragments OBJECT-TYPE
   SYNTAX       Gauge32
   MAX-ACCESS   read-only
   STATUS       current
   DESCRIPTION
     "The number of received fragments that have been
	  discarded due to errors during the current
	  15-Minute interval."
   ::= { adGenEfmPerfLinkCurr15MinEntry 6 }

adGenEfmPerfLinkCurr15MinRxFcsErrors OBJECT-TYPE
   SYNTAX       Gauge32
   MAX-ACCESS   read-only
   STATUS       current
   DESCRIPTION
     "The number of FCS errros detected by the 64/65-octet
	  receive function during the current 15-Minute interval."
   ::= { adGenEfmPerfLinkCurr15MinEntry 7 }

adGenEfmPerfLinkCurr15MinRxCodingErrors OBJECT-TYPE
   SYNTAX       Gauge32
   MAX-ACCESS   read-only
   STATUS       current
   DESCRIPTION
     "The number of 64/65-octet encapsulation errors detected
	  by the 64/65-octet receive function during the current
	  15-Minute interval."
   ::= { adGenEfmPerfLinkCurr15MinEntry 8 }

adGenEfmPerfLink15MinValidIntervals OBJECT-TYPE
   SYNTAX      	Integer32
   MAX-ACCESS   read-only
   STATUS       current
   DESCRIPTION
     "The number of valid 15-Minute intervals."
   ::= { adGenEfmPerfLinkCurr15MinEntry 9 }


-- ********************************************
-- EFM Link Performance, Current 24-Hour
-- ********************************************
adGenEfmPerfLinkCurr24HrTable OBJECT-TYPE
   SYNTAX      SEQUENCE OF AdGenEfmPerfLinkCurr24HrEntry
   MAX-ACCESS  not-accessible
   STATUS      current
   DESCRIPTION
     "This table supports EFM Link Current Performance"
   ::= { adGenEfmPerformance 6 }

adGenEfmPerfLinkCurr24HrEntry OBJECT-TYPE
   SYNTAX      AdGenEfmPerfLinkCurr24HrEntry
   MAX-ACCESS  not-accessible
   STATUS      current
   DESCRIPTION
     "An entry in the adGenEfmPerfLinkCurr24HrTable."
   INDEX { ifIndex, adGenEfmUnitIndex }
   ::= { adGenEfmPerfLinkCurr24HrTable 1 }

AdGenEfmPerfLinkCurr24HrEntry ::=
   SEQUENCE
   {
        adGenEfmPerfLinkCurr24HrTxFragments                             Gauge32,
        adGenEfmPerfLinkCurr24HrRxFragments                             Gauge32,
        adGenEfmPerfLinkCurr24HrRxErroredFragments              Gauge32,
        adGenEfmPerfLinkCurr24HrRxSmallFragments                Gauge32,
        adGenEfmPerfLinkCurr24HrRxLargeFragments                Gauge32,
        adGenEfmPerfLinkCurr24HrRxDiscardedFragments    Gauge32,
        adGenEfmPerfLinkCurr24HrRxFcsErrors                             Gauge32,
        adGenEfmPerfLinkCurr24HrRxCodingErrors                  Gauge32,
	adGenEfmPerfLink24HrValidIntervals				Integer32
   }

adGenEfmPerfLinkCurr24HrTxFragments OBJECT-TYPE
   SYNTAX       Gauge32
   MAX-ACCESS   read-only
   STATUS       current
   DESCRIPTION
     "The number of fragments transmitted over this EFM Link
	  during the current 24-Hour interval."
   ::= { adGenEfmPerfLinkCurr24HrEntry 1 }

adGenEfmPerfLinkCurr24HrRxFragments OBJECT-TYPE
   SYNTAX       Gauge32
   MAX-ACCESS   read-only
   STATUS       current
   DESCRIPTION
     "The number of fragments received over this EFM Link
	  during the current 24-Hour interval."
   ::= { adGenEfmPerfLinkCurr24HrEntry 2 }

adGenEfmPerfLinkCurr24HrRxErroredFragments OBJECT-TYPE
   SYNTAX       Gauge32
   MAX-ACCESS   read-only
   STATUS       current
   DESCRIPTION
     "The number of errored fragments received over this EFM Link
	  during the current 24-Hour interval."
   ::= { adGenEfmPerfLinkCurr24HrEntry 3 }

adGenEfmPerfLinkCurr24HrRxSmallFragments OBJECT-TYPE
   SYNTAX       Gauge32
   MAX-ACCESS   read-only
   STATUS       current
   DESCRIPTION
     "The number of fragments received over this EFM Link
	  during the current 24-Hour interval that are smaller
	  than the minimum fragment size (64 bytes)."
   ::= { adGenEfmPerfLinkCurr24HrEntry 4 }

adGenEfmPerfLinkCurr24HrRxLargeFragments OBJECT-TYPE
   SYNTAX       Gauge32
   MAX-ACCESS   read-only
   STATUS       current
   DESCRIPTION
     "The number of fragments received over this EFM Link
	  during the current 24-Hour interval that are larger
	  than the maximum fragment size (512 bytes)."
   ::= { adGenEfmPerfLinkCurr24HrEntry 5 }

adGenEfmPerfLinkCurr24HrRxDiscardedFragments OBJECT-TYPE
   SYNTAX       Gauge32
   MAX-ACCESS   read-only
   STATUS       current
   DESCRIPTION
     "The number of received fragments that have been
	  discarded due to errors during the current
	  24-Hour interval."
   ::= { adGenEfmPerfLinkCurr24HrEntry 6 }

adGenEfmPerfLinkCurr24HrRxFcsErrors OBJECT-TYPE
   SYNTAX       Gauge32
   MAX-ACCESS   read-only
   STATUS       current
   DESCRIPTION
     "The number of FCS errros detected by the 64/65-octet
	  receive function during the current 24-Hour interval."
   ::= { adGenEfmPerfLinkCurr24HrEntry 7 }

adGenEfmPerfLinkCurr24HrRxCodingErrors OBJECT-TYPE
   SYNTAX       Gauge32
   MAX-ACCESS   read-only
   STATUS       current
   DESCRIPTION
     "The number of 64/65-octet encapsulation errors detected
	  by the 64/65-octet receive function during the current
	  24-Hour interval."
   ::= { adGenEfmPerfLinkCurr24HrEntry 8 }

adGenEfmPerfLink24HrValidIntervals OBJECT-TYPE
   SYNTAX      	Integer32
   MAX-ACCESS   read-only
   STATUS       current
   DESCRIPTION
     "The number of valid 24-Hour intervals."
   ::= { adGenEfmPerfLinkCurr24HrEntry 9 }


-- ********************************************
-- EFM Link Performance, 15-Minute Interval
-- ********************************************
adGenEfmPerfLink15MinIntTable OBJECT-TYPE
   SYNTAX      SEQUENCE OF AdGenEfmPerfLink15MinIntEntry
   MAX-ACCESS  not-accessible
   STATUS      current
   DESCRIPTION
     "This table supports EFM Link Current Performance"
   ::= { adGenEfmPerformance 7 }

adGenEfmPerfLink15MinIntEntry OBJECT-TYPE
   SYNTAX      AdGenEfmPerfLink15MinIntEntry
   MAX-ACCESS  not-accessible
   STATUS      current
   DESCRIPTION
     "An entry in the adGenEfmPerfLink15MinIntTable."
   INDEX { ifIndex, adGenEfmUnitIndex, adGenEfmPerfLink15MinIntNumber }
   ::= { adGenEfmPerfLink15MinIntTable 1 }

AdGenEfmPerfLink15MinIntEntry ::=
   SEQUENCE
   {
        adGenEfmPerfLink15MinIntNumber                          Gauge32,
        adGenEfmPerfLink15MinIntTxFragments                             Gauge32,
        adGenEfmPerfLink15MinIntRxFragments                             Gauge32,
        adGenEfmPerfLink15MinIntRxErroredFragments              Gauge32,
        adGenEfmPerfLink15MinIntRxSmallFragments                Gauge32,
        adGenEfmPerfLink15MinIntRxLargeFragments                Gauge32,
        adGenEfmPerfLink15MinIntRxDiscardedFragments    Gauge32,
        adGenEfmPerfLink15MinIntRxFcsErrors                             Gauge32,
        adGenEfmPerfLink15MinIntRxCodingErrors                  Gauge32
   }

adGenEfmPerfLink15MinIntNumber OBJECT-TYPE
   SYNTAX       Gauge32
   MAX-ACCESS   read-only
   STATUS       current
   DESCRIPTION
     "15-minute performance interval.  Interval 1 represents the most recent
	  previous interval.  Interval 96 represents 24 hours ago.  Intervals 2
	  through 96 are optional."
   ::= { adGenEfmPerfLink15MinIntEntry 1 }

adGenEfmPerfLink15MinIntTxFragments OBJECT-TYPE
   SYNTAX       Gauge32
   MAX-ACCESS   read-only
   STATUS       current
   DESCRIPTION
     "The number of fragments transmitted over this EFM Link
	  during the selected 15-Minute interval."
   ::= { adGenEfmPerfLink15MinIntEntry 2 }

adGenEfmPerfLink15MinIntRxFragments OBJECT-TYPE
   SYNTAX       Gauge32
   MAX-ACCESS   read-only
   STATUS       current
   DESCRIPTION
     "The number of fragments received over this EFM Link
	  during the selected 15-Minute interval."
   ::= { adGenEfmPerfLink15MinIntEntry 3 }

adGenEfmPerfLink15MinIntRxErroredFragments OBJECT-TYPE
   SYNTAX       Gauge32
   MAX-ACCESS   read-only
   STATUS       current
   DESCRIPTION
     "The number of errored fragments received over this EFM Link
	  during the selected 15-Minute interval."
   ::= { adGenEfmPerfLink15MinIntEntry 4 }

adGenEfmPerfLink15MinIntRxSmallFragments OBJECT-TYPE
   SYNTAX       Gauge32
   MAX-ACCESS   read-only
   STATUS       current
   DESCRIPTION
     "The number of fragments received over this EFM Link
	  during the selected 15-Minute interval that are smaller
	  than the minimum fragment size (64 bytes)."
   ::= { adGenEfmPerfLink15MinIntEntry 5 }

adGenEfmPerfLink15MinIntRxLargeFragments OBJECT-TYPE
   SYNTAX       Gauge32
   MAX-ACCESS   read-only
   STATUS       current
   DESCRIPTION
     "The number of fragments received over this EFM Link
	  during the selected 15-Minute interval that are larger
	  than the maximum fragment size (512 bytes)."
   ::= { adGenEfmPerfLink15MinIntEntry 6 }

adGenEfmPerfLink15MinIntRxDiscardedFragments OBJECT-TYPE
   SYNTAX       Gauge32
   MAX-ACCESS   read-only
   STATUS       current
   DESCRIPTION
     "The number of received fragments that have been
	  discarded due to errors during the selected
	  15-Minute interval."
   ::= { adGenEfmPerfLink15MinIntEntry 7 }

adGenEfmPerfLink15MinIntRxFcsErrors OBJECT-TYPE
   SYNTAX       Gauge32
   MAX-ACCESS   read-only
   STATUS       current
   DESCRIPTION
     "The number of FCS errros detected by the 64/65-octet
	  receive function during the selected 15-Minute interval."
   ::= { adGenEfmPerfLink15MinIntEntry 8 }

adGenEfmPerfLink15MinIntRxCodingErrors OBJECT-TYPE
   SYNTAX       Gauge32
   MAX-ACCESS   read-only
   STATUS       current
   DESCRIPTION
     "The number of 64/65-octet encapsulation errors detected
	  by the 64/65-octet receive function during the selected
	  15-Minute interval."
   ::= { adGenEfmPerfLink15MinIntEntry 9 }


-- ********************************************
-- EFM Link Performance, 24-Hour Interval
-- ********************************************
adGenEfmPerfLink24HrIntTable OBJECT-TYPE
   SYNTAX      SEQUENCE OF AdGenEfmPerfLink24HrIntEntry
   MAX-ACCESS  not-accessible
   STATUS      current
   DESCRIPTION
     "This table supports EFM Link Current Performance"
   ::= { adGenEfmPerformance 8 }

adGenEfmPerfLink24HrIntEntry OBJECT-TYPE
   SYNTAX      AdGenEfmPerfLink24HrIntEntry
   MAX-ACCESS  not-accessible
   STATUS      current
   DESCRIPTION
     "An entry in the adGenEfmPerfLink24HrIntTable."
   INDEX { ifIndex, adGenEfmUnitIndex, adGenEfmPerfLink24HrIntNumber }
   ::= { adGenEfmPerfLink24HrIntTable 1 }

AdGenEfmPerfLink24HrIntEntry ::=
   SEQUENCE
   {
        adGenEfmPerfLink24HrIntNumber                           Gauge32,
        adGenEfmPerfLink24HrIntTxFragments                              Gauge32,
        adGenEfmPerfLink24HrIntRxFragments                              Gauge32,
        adGenEfmPerfLink24HrIntRxErroredFragments               Gauge32,
        adGenEfmPerfLink24HrIntRxSmallFragments                 Gauge32,
        adGenEfmPerfLink24HrIntRxLargeFragments                 Gauge32,
        adGenEfmPerfLink24HrIntRxDiscardedFragments     Gauge32,
        adGenEfmPerfLink24HrIntRxFcsErrors                              Gauge32,
        adGenEfmPerfLink24HrIntRxCodingErrors                   Gauge32
   }

adGenEfmPerfLink24HrIntNumber OBJECT-TYPE
   SYNTAX       Gauge32
   MAX-ACCESS   read-only
   STATUS       current
   DESCRIPTION
     "24-hour performance interval.  Interval 1 represents the most recent
	  previous interval.  Interval 30 represents 30 days ago.  Intervals 2
	  through 30 are optional."
   ::= { adGenEfmPerfLink24HrIntEntry 1 }

adGenEfmPerfLink24HrIntTxFragments OBJECT-TYPE
   SYNTAX       Gauge32
   MAX-ACCESS   read-only
   STATUS       current
   DESCRIPTION
     "The number of fragments transmitted over this EFM Link
	  during the selected 24-Hour interval."
   ::= { adGenEfmPerfLink24HrIntEntry 2 }

adGenEfmPerfLink24HrIntRxFragments OBJECT-TYPE
   SYNTAX       Gauge32
   MAX-ACCESS   read-only
   STATUS       current
   DESCRIPTION
     "The number of fragments received over this EFM Link
	  during the selected 24-Hour interval."
   ::= { adGenEfmPerfLink24HrIntEntry 3 }

adGenEfmPerfLink24HrIntRxErroredFragments OBJECT-TYPE
   SYNTAX       Gauge32
   MAX-ACCESS   read-only
   STATUS       current
   DESCRIPTION
     "The number of errored fragments received over this EFM Link
	  during the selected 24-Hour interval."
   ::= { adGenEfmPerfLink24HrIntEntry 4 }

adGenEfmPerfLink24HrIntRxSmallFragments OBJECT-TYPE
   SYNTAX       Gauge32
   MAX-ACCESS   read-only
   STATUS       current
   DESCRIPTION
     "The number of fragments received over this EFM Link
	  during the selected 24-Hour interval that are smaller
	  than the minimum fragment size (64 bytes)."
   ::= { adGenEfmPerfLink24HrIntEntry 5 }

adGenEfmPerfLink24HrIntRxLargeFragments OBJECT-TYPE
   SYNTAX       Gauge32
   MAX-ACCESS   read-only
   STATUS       current
   DESCRIPTION
     "The number of fragments received over this EFM Link
	  during the selected 24-Hour interval that are larger
	  than the maximum fragment size (512 bytes)."
   ::= { adGenEfmPerfLink24HrIntEntry 6 }

adGenEfmPerfLink24HrIntRxDiscardedFragments OBJECT-TYPE
   SYNTAX       Gauge32
   MAX-ACCESS   read-only
   STATUS       current
   DESCRIPTION
     "The number of received fragments that have been
	  discarded due to errors during the selected
	  24-Hour interval."
   ::= { adGenEfmPerfLink24HrIntEntry 7 }

adGenEfmPerfLink24HrIntRxFcsErrors OBJECT-TYPE
   SYNTAX       Gauge32
   MAX-ACCESS   read-only
   STATUS       current
   DESCRIPTION
     "The number of FCS errros detected by the 64/65-octet
	  receive function during the selected 24-Hour interval."
   ::= { adGenEfmPerfLink24HrIntEntry 8 }

adGenEfmPerfLink24HrIntRxCodingErrors OBJECT-TYPE
   SYNTAX       Gauge32
   MAX-ACCESS   read-only
   STATUS       current
   DESCRIPTION
     "The number of 64/65-octet encapsulation errors detected
	  by the 64/65-octet receive function during the selected
	  24-Hour interval."
   ::= { adGenEfmPerfLink24HrIntEntry 9 }


-- ********************************************
-- EFM Performance, Reset Table
-- ********************************************
adGenEfmPerfResetTable OBJECT-TYPE
   SYNTAX      SEQUENCE OF AdGenEfmPerfResetEntry
   MAX-ACCESS  not-accessible
   STATUS      current
   DESCRIPTION
     "This table supports the resetting of EFM Performance"
   ::= { adGenEfmPerformance 9 }

adGenEfmPerfResetEntry OBJECT-TYPE
   SYNTAX      AdGenEfmPerfResetEntry
   MAX-ACCESS  not-accessible
   STATUS      current
   DESCRIPTION
     "An entry in the adGenEfmPerfResetTable."
   INDEX { ifIndex, adGenEfmUnitIndex }
   ::= { adGenEfmPerfResetTable 1 }

AdGenEfmPerfResetEntry ::=
   SEQUENCE
   {
        adGenEfmPerfResetGroupData              INTEGER,
        adGenEfmPerfResetLinkData               INTEGER
   }

adGenEfmPerfResetGroupData OBJECT-TYPE
   SYNTAX       INTEGER
   				{
				reset(1)
				}
   MAX-ACCESS   read-write
   STATUS       current
   DESCRIPTION
     "Resets the group performance data on the selected interface."
   ::= { adGenEfmPerfResetEntry 1 }

adGenEfmPerfResetLinkData OBJECT-TYPE
   SYNTAX       INTEGER
   				{
				reset(1)
				}
   MAX-ACCESS   read-write
   STATUS       current
   DESCRIPTION
     "Resets the link performance data on the selected interface."
   ::= { adGenEfmPerfResetEntry 2 }

-- *************************************************
-- EFM Performance, 15-Minute Group Threshold Table
-- *************************************************
adGenEfmPerfGroup15MinThreshTable OBJECT-TYPE
   SYNTAX      SEQUENCE OF AdGenEfmPerfGroup15MinThreshEntry
   MAX-ACCESS  not-accessible
   STATUS      current
   DESCRIPTION
     "This table supports EFM Group Current Performance"
   ::= { adGenEfmPerformance 10 }

adGenEfmPerfGroup15MinThreshEntry OBJECT-TYPE
   SYNTAX      AdGenEfmPerfGroup15MinThreshEntry
   MAX-ACCESS  not-accessible
   STATUS      current
   DESCRIPTION
     "An entry in the adGenEfmPerfGroup15MinThreshTable."
   INDEX { ifIndex, adGenEfmUnitIndex }
   ::= { adGenEfmPerfGroup15MinThreshTable 1 }

AdGenEfmPerfGroup15MinThreshEntry ::=
   SEQUENCE
   {
        adGenEfmPerfGroup15MinThreshRxBadFragments    Unsigned32,
        adGenEfmPerfGroup15MinThreshRxLostFragments   Unsigned32,
        adGenEfmPerfGroup15MinThreshRxLostStarts      Unsigned32,
        adGenEfmPerfGroup15MinThreshRxLostEnds        Unsigned32
   }

adGenEfmPerfGroup15MinThreshRxBadFragments OBJECT-TYPE
   SYNTAX       Unsigned32
   MAX-ACCESS   read-write
   STATUS       current
   DESCRIPTION
     "The threshold for the number of fragment sequence errors over this
	  EFM group during the current 15-Minute interval."
   ::= { adGenEfmPerfGroup15MinThreshEntry 1 }

adGenEfmPerfGroup15MinThreshRxLostFragments OBJECT-TYPE
   SYNTAX       Unsigned32
   MAX-ACCESS   read-write
   STATUS       current
   DESCRIPTION
     "The threshold for the number of gaps in the sequence of frames that
	  have been received across the gamma interface
	  during the current 15-Minute interval."
   ::= { adGenEfmPerfGroup15MinThreshEntry 2 }

adGenEfmPerfGroup15MinThreshRxLostStarts OBJECT-TYPE
   SYNTAX       Unsigned32
   MAX-ACCESS   read-write
   STATUS       current
   DESCRIPTION
     "The threshold for the number of missing StartOfPacket indicators
	  during the current 15-Minute interval."
   ::= { adGenEfmPerfGroup15MinThreshEntry 3 }

adGenEfmPerfGroup15MinThreshRxLostEnds OBJECT-TYPE
   SYNTAX       Unsigned32
   MAX-ACCESS   read-write
   STATUS       current
   DESCRIPTION
     "The threshold for the number of missing EndOfPacket indicators
	  during the current 15-Minute interval."
   ::= { adGenEfmPerfGroup15MinThreshEntry 4 }

-- *************************************************
-- EFM Performance, 24-Hour Group Threshold Table
-- *************************************************
adGenEfmPerfGroup24HrThreshTable OBJECT-TYPE
   SYNTAX      SEQUENCE OF AdGenEfmPerfGroup24HrThreshEntry
   MAX-ACCESS  not-accessible
   STATUS      current
   DESCRIPTION
     "This table supports EFM Group Current Performance"
   ::= { adGenEfmPerformance 11 }

adGenEfmPerfGroup24HrThreshEntry OBJECT-TYPE
   SYNTAX      AdGenEfmPerfGroup24HrThreshEntry
   MAX-ACCESS  not-accessible
   STATUS      current
   DESCRIPTION
     "An entry in the adGenEfmPerfGroup24HrThreshTable."
   INDEX { ifIndex, adGenEfmUnitIndex }
   ::= { adGenEfmPerfGroup24HrThreshTable 1 }

AdGenEfmPerfGroup24HrThreshEntry ::=
   SEQUENCE
   {
        adGenEfmPerfGroup24HrThreshRxBadFragments    Unsigned32,
        adGenEfmPerfGroup24HrThreshRxLostFragments   Unsigned32,
        adGenEfmPerfGroup24HrThreshRxLostStarts      Unsigned32,
        adGenEfmPerfGroup24HrThreshRxLostEnds        Unsigned32
   }

adGenEfmPerfGroup24HrThreshRxBadFragments OBJECT-TYPE
   SYNTAX       Unsigned32
   MAX-ACCESS   read-write
   STATUS       current
   DESCRIPTION
     "The threshold for the number of fragment sequence errors over this
          EFM group during the current 24-Hour interval."
   ::= { adGenEfmPerfGroup24HrThreshEntry 1 }

adGenEfmPerfGroup24HrThreshRxLostFragments OBJECT-TYPE
   SYNTAX       Unsigned32
   MAX-ACCESS   read-write
   STATUS       current
   DESCRIPTION
     "The threshold for the number of gaps in the sequence of frames that
	  have been received across the gamma interface
          during the current 24-Hour interval."
   ::= { adGenEfmPerfGroup24HrThreshEntry 2 }

adGenEfmPerfGroup24HrThreshRxLostStarts OBJECT-TYPE
   SYNTAX       Unsigned32
   MAX-ACCESS   read-write
   STATUS       current
   DESCRIPTION
     "The threshold for the number of missing StartOfPacket indicators
          during the current 24-Hour interval."
   ::= { adGenEfmPerfGroup24HrThreshEntry 3 }

adGenEfmPerfGroup24HrThreshRxLostEnds OBJECT-TYPE
   SYNTAX       Unsigned32
   MAX-ACCESS   read-write
   STATUS       current
   DESCRIPTION
     "The threshold for the number of missing EndOfPacket indicators
          during the current 24-Hour interval."
   ::= { adGenEfmPerfGroup24HrThreshEntry 4 }

-- ************************************************
-- EFM Link Performance, 15-Minute Threshold Table
-- ************************************************
adGenEfmPerfLink15MinThreshTable OBJECT-TYPE
   SYNTAX      SEQUENCE OF AdGenEfmPerfLink15MinThreshEntry
   MAX-ACCESS  not-accessible
   STATUS      current
   DESCRIPTION
     "This table supports EFM Link Current Performance"
   ::= { adGenEfmPerformance 12 }

adGenEfmPerfLink15MinThreshEntry OBJECT-TYPE
   SYNTAX      AdGenEfmPerfLink15MinThreshEntry
   MAX-ACCESS  not-accessible
   STATUS      current
   DESCRIPTION
     "An entry in the adGenEfmPerfLink15MinThreshTable."
   INDEX { ifIndex, adGenEfmUnitIndex }
   ::= { adGenEfmPerfLink15MinThreshTable 1 }

AdGenEfmPerfLink15MinThreshEntry ::=
   SEQUENCE
   {
        adGenEfmPerfLink15MinThreshRxErroredFragments     Unsigned32,
        adGenEfmPerfLink15MinThreshRxSmallFragments       Unsigned32,
        adGenEfmPerfLink15MinThreshRxLargeFragments       Unsigned32,
        adGenEfmPerfLink15MinThreshRxDiscardedFragments   Unsigned32,
        adGenEfmPerfLink15MinThreshRxFcsErrors            Unsigned32,
        adGenEfmPerfLink15MinThreshRxCodingErrors         Unsigned32
   }

adGenEfmPerfLink15MinThreshRxErroredFragments OBJECT-TYPE
   SYNTAX       Unsigned32
   MAX-ACCESS   read-write
   STATUS       current
   DESCRIPTION
     "The threshold for the number of errored fragments received over this EFM Link
	  during the current 15-Minute interval."
   ::= { adGenEfmPerfLink15MinThreshEntry 1 }

adGenEfmPerfLink15MinThreshRxSmallFragments OBJECT-TYPE
   SYNTAX       Unsigned32
   MAX-ACCESS   read-write
   STATUS       current
   DESCRIPTION
     "The threshold for the number of fragments received over this EFM Link
	  during the current 15-Minute interval that are smaller
	  than the minimum fragment size (64 bytes)."
   ::= { adGenEfmPerfLink15MinThreshEntry 2 }

adGenEfmPerfLink15MinThreshRxLargeFragments OBJECT-TYPE
   SYNTAX       Unsigned32
   MAX-ACCESS   read-write
   STATUS       current
   DESCRIPTION
     "The threshold for the number of fragments received over this EFM Link
	  during the current 15-Minute interval that are larger
	  than the maximum fragment size (512 bytes)."
   ::= { adGenEfmPerfLink15MinThreshEntry 3 }

adGenEfmPerfLink15MinThreshRxDiscardedFragments OBJECT-TYPE
   SYNTAX       Unsigned32
   MAX-ACCESS   read-write
   STATUS       current
   DESCRIPTION
     "The threshold for the number of received fragments that have been
	  discarded due to errors during the current
	  15-Minute interval."
   ::= { adGenEfmPerfLink15MinThreshEntry 4 }

adGenEfmPerfLink15MinThreshRxFcsErrors OBJECT-TYPE
   SYNTAX       Unsigned32
   MAX-ACCESS   read-write
   STATUS       current
   DESCRIPTION
     "The threshold for the number of FCS errros detected by the 64/65-octet
	  receive function during the current 15-Minute interval."
   ::= { adGenEfmPerfLink15MinThreshEntry 5 }

adGenEfmPerfLink15MinThreshRxCodingErrors OBJECT-TYPE
   SYNTAX       Unsigned32
   MAX-ACCESS   read-write
   STATUS       current
   DESCRIPTION
     "The threshold for the number of 64/65-octet encapsulation errors detected
	  by the 64/65-octet receive function during the current
	  15-Minute interval."
   ::= { adGenEfmPerfLink15MinThreshEntry 6 }

-- ************************************************
-- EFM Link Performance, 24-Hour Threshold Table
-- ************************************************
adGenEfmPerfLink24HrThreshTable OBJECT-TYPE
   SYNTAX      SEQUENCE OF AdGenEfmPerfLink24HrThreshEntry
   MAX-ACCESS  not-accessible
   STATUS      current
   DESCRIPTION
     "This table supports EFM Link Current Performance"
   ::= { adGenEfmPerformance 13 }

adGenEfmPerfLink24HrThreshEntry OBJECT-TYPE
   SYNTAX      AdGenEfmPerfLink24HrThreshEntry
   MAX-ACCESS  not-accessible
   STATUS      current
   DESCRIPTION
     "An entry in the adGenEfmPerfLink24HrThreshTable."
   INDEX { ifIndex, adGenEfmUnitIndex }
   ::= { adGenEfmPerfLink24HrThreshTable 1 }

AdGenEfmPerfLink24HrThreshEntry ::=
   SEQUENCE
   {
        adGenEfmPerfLink24HrThreshRxErroredFragments     Unsigned32,
        adGenEfmPerfLink24HrThreshRxSmallFragments       Unsigned32,
        adGenEfmPerfLink24HrThreshRxLargeFragments       Unsigned32,
        adGenEfmPerfLink24HrThreshRxDiscardedFragments   Unsigned32,
        adGenEfmPerfLink24HrThreshRxFcsErrors            Unsigned32,
        adGenEfmPerfLink24HrThreshRxCodingErrors         Unsigned32
   }

adGenEfmPerfLink24HrThreshRxErroredFragments OBJECT-TYPE
   SYNTAX       Unsigned32
   MAX-ACCESS   read-write
   STATUS       current
   DESCRIPTION
     "The threshold for the number of errored fragments received over this EFM Link
          during the current 24-Hour interval."
   ::= { adGenEfmPerfLink24HrThreshEntry 1 }

adGenEfmPerfLink24HrThreshRxSmallFragments OBJECT-TYPE
   SYNTAX       Unsigned32
   MAX-ACCESS   read-write
   STATUS       current
   DESCRIPTION
     "The threshold for the number of fragments received over this EFM Link
          during the current 24-Hour interval that are smaller
	  than the minimum fragment size (64 bytes)."
   ::= { adGenEfmPerfLink24HrThreshEntry 2 }

adGenEfmPerfLink24HrThreshRxLargeFragments OBJECT-TYPE
   SYNTAX       Unsigned32
   MAX-ACCESS   read-write
   STATUS       current
   DESCRIPTION
     "The threshold for the number of fragments received over this EFM Link
          during the current 24-Hour interval that are larger
	  than the maximum fragment size (512 bytes)."
   ::= { adGenEfmPerfLink24HrThreshEntry 3 }

adGenEfmPerfLink24HrThreshRxDiscardedFragments OBJECT-TYPE
   SYNTAX       Unsigned32
   MAX-ACCESS   read-write
   STATUS       current
   DESCRIPTION
     "The threshold for the number of received fragments that have been
	  discarded due to errors during the current
          24-Hour interval."
   ::= { adGenEfmPerfLink24HrThreshEntry 4 }

adGenEfmPerfLink24HrThreshRxFcsErrors OBJECT-TYPE
   SYNTAX       Unsigned32
   MAX-ACCESS   read-write
   STATUS       current
   DESCRIPTION
     "The threshold for the number of FCS errros detected by the 64/65-octet
          receive function during the current 24-Hour interval."
   ::= { adGenEfmPerfLink24HrThreshEntry 5 }

adGenEfmPerfLink24HrThreshRxCodingErrors OBJECT-TYPE
   SYNTAX       Unsigned32
   MAX-ACCESS   read-write
   STATUS       current
   DESCRIPTION
     "The threshold for the number of 64/65-octet encapsulation errors detected
	  by the 64/65-octet receive function during the current
          24-Hour interval."
   ::= { adGenEfmPerfLink24HrThreshEntry 6 }

-- ********************************************
-- EFM Performance, Group Reset Table
-- ********************************************
adGenEfmPerfGroupResetTable OBJECT-TYPE
   SYNTAX      SEQUENCE OF AdGenEfmPerfGroupResetEntry
   MAX-ACCESS  not-accessible
   STATUS      current
   DESCRIPTION
     "This table supports the resetting of EFM Group Performance"
   ::= { adGenEfmPerformance 14 }

adGenEfmPerfGroupResetEntry OBJECT-TYPE
   SYNTAX      AdGenEfmPerfGroupResetEntry
   MAX-ACCESS  not-accessible
   STATUS      current
   DESCRIPTION
     "An entry in the adGenEfmPerfGroupResetTable."
   INDEX { ifIndex }
   ::= { adGenEfmPerfGroupResetTable 1 }

AdGenEfmPerfGroupResetEntry ::=
   SEQUENCE
   {
        adGenEfmPerfGroupReset  INTEGER
   }

adGenEfmPerfGroupReset OBJECT-TYPE
   SYNTAX       INTEGER
                {
                reset(1)
                }
   MAX-ACCESS   read-write
   STATUS       current
   DESCRIPTION
     "Resets the group performance data on the selected interface."
   ::= { adGenEfmPerfGroupResetEntry 1 }

-- ********************************************
-- EFM Performance, Link Reset Table
-- ********************************************
adGenEfmPerfLinkResetTable OBJECT-TYPE
   SYNTAX      SEQUENCE OF AdGenEfmPerfLinkResetEntry
   MAX-ACCESS  not-accessible
   STATUS      current
   DESCRIPTION
     "This table supports the resetting of EFM Link Performance"
   ::= { adGenEfmPerformance 15 }

adGenEfmPerfLinkResetEntry OBJECT-TYPE
   SYNTAX      AdGenEfmPerfLinkResetEntry
   MAX-ACCESS  not-accessible
   STATUS      current
   DESCRIPTION
     "An entry in the adGenEfmPerfLinkResetTable."
   INDEX { ifIndex }
   ::= { adGenEfmPerfLinkResetTable 1 }

AdGenEfmPerfLinkResetEntry ::=
   SEQUENCE
   {
        adGenEfmPerfLinkReset  INTEGER
   }

adGenEfmPerfLinkReset OBJECT-TYPE
   SYNTAX       INTEGER
                {
                reset(1)
                }
   MAX-ACCESS   read-write
   STATUS       current
   DESCRIPTION
     "Resets the Link performance data on the selected interface."
   ::= { adGenEfmPerfLinkResetEntry 1 }

-- ********************************************
-- EFM Group Performance, Free Rolling Counts
-- ********************************************
adGenEfmPerfGroupFreeRollingCountTable OBJECT-TYPE
   SYNTAX      SEQUENCE OF AdGenEfmPerfGroupFreeRollingCountEntry
   MAX-ACCESS  not-accessible
   STATUS      current
   DESCRIPTION
     "This table supports EFM Group Performance"
   ::= { adGenEfmPerformance 16 }

adGenEfmPerfGroupFreeRollingCountEntry OBJECT-TYPE
   SYNTAX      AdGenEfmPerfGroupFreeRollingCountEntry
   MAX-ACCESS  not-accessible
   STATUS      current
   DESCRIPTION
     "An entry in the adGenEfmPerfGroupFreeRollingCountTable."
   INDEX { ifIndex }
   ::= { adGenEfmPerfGroupFreeRollingCountTable 1 }

AdGenEfmPerfGroupFreeRollingCountEntry ::=
   SEQUENCE
   {
        adGenEfmPerfGroupFreeRollingCountRxBadFragments        		Counter32,
        adGenEfmPerfGroupFreeRollingCountRxLostFragments   			Counter32,
        adGenEfmPerfGroupFreeRollingCountRxLostStarts      			Counter32,
        adGenEfmPerfGroupFreeRollingCountRxLostEnds        			Counter32
   }

adGenEfmPerfGroupFreeRollingCountRxBadFragments OBJECT-TYPE
   SYNTAX       Counter32
   MAX-ACCESS   read-only
   STATUS       current
   DESCRIPTION
     "The number of fragment sequence errors over this
	  EFM group."
   ::= { adGenEfmPerfGroupFreeRollingCountEntry 1 }

adGenEfmPerfGroupFreeRollingCountRxLostFragments OBJECT-TYPE
   SYNTAX       Counter32
   MAX-ACCESS   read-only
   STATUS       current
   DESCRIPTION
     "The number of gaps in the sequence of frames that
	  have been received across the gamma interface."
   ::= { adGenEfmPerfGroupFreeRollingCountEntry 2 }

adGenEfmPerfGroupFreeRollingCountRxLostStarts OBJECT-TYPE
   SYNTAX       Counter32
   MAX-ACCESS   read-only
   STATUS       current
   DESCRIPTION
     "The number of missing StartOfPacket indicators."
   ::= { adGenEfmPerfGroupFreeRollingCountEntry 3 }

adGenEfmPerfGroupFreeRollingCountRxLostEnds OBJECT-TYPE
   SYNTAX       Counter32
   MAX-ACCESS   read-only
   STATUS       current
   DESCRIPTION
     "The number of missing EndOfPacket indicators."
   ::= { adGenEfmPerfGroupFreeRollingCountEntry 4 }

-- ********************************************
-- EFM Link Performance, Free Rolling Counts
-- ********************************************
adGenEfmPerfLinkFreeRollingCountTable OBJECT-TYPE
   SYNTAX      SEQUENCE OF AdGenEfmPerfLinkFreeRollingCountEntry
   MAX-ACCESS  not-accessible
   STATUS      current
   DESCRIPTION
     "This table supports EFM Link Performance"
   ::= { adGenEfmPerformance 17 }

adGenEfmPerfLinkFreeRollingCountEntry OBJECT-TYPE
   SYNTAX      AdGenEfmPerfLinkFreeRollingCountEntry
   MAX-ACCESS  not-accessible
   STATUS      current
   DESCRIPTION
     "An entry in the adGenEfmPerfLinkFreeRollingCountTable."
   INDEX { ifIndex }
   ::= { adGenEfmPerfLinkFreeRollingCountTable 1 }

AdGenEfmPerfLinkFreeRollingCountEntry ::=
   SEQUENCE
   {
        adGenEfmPerfLinkFreeRollingCountTxFragments					Counter32,
        adGenEfmPerfLinkFreeRollingCountRxFragments					Counter32,
        adGenEfmPerfLinkFreeRollingCountRxErroredFragments			Counter32,
        adGenEfmPerfLinkFreeRollingCountRxSmallFragments			Counter32,
        adGenEfmPerfLinkFreeRollingCountRxLargeFragments			Counter32,
        adGenEfmPerfLinkFreeRollingCountRxDiscardedFragments		Counter32,
        adGenEfmPerfLinkFreeRollingCountRxFcsErrors					Counter32,
        adGenEfmPerfLinkFreeRollingCountRxCodingErrors				Counter32
   }

adGenEfmPerfLinkFreeRollingCountTxFragments OBJECT-TYPE
   SYNTAX       Counter32
   MAX-ACCESS   read-only
   STATUS       current
   DESCRIPTION
     "The number of fragments transmitted over this EFM Link."
   ::= { adGenEfmPerfLinkFreeRollingCountEntry 1 }

adGenEfmPerfLinkFreeRollingCountRxFragments OBJECT-TYPE
   SYNTAX       Counter32
   MAX-ACCESS   read-only
   STATUS       current
   DESCRIPTION
     "The number of fragments received over this EFM Link."
   ::= { adGenEfmPerfLinkFreeRollingCountEntry 2 }

adGenEfmPerfLinkFreeRollingCountRxErroredFragments OBJECT-TYPE
   SYNTAX       Counter32
   MAX-ACCESS   read-only
   STATUS       current
   DESCRIPTION
     "The number of errored fragments received over this EFM Link."
   ::= { adGenEfmPerfLinkFreeRollingCountEntry 3 }

adGenEfmPerfLinkFreeRollingCountRxSmallFragments OBJECT-TYPE
   SYNTAX       Counter32
   MAX-ACCESS   read-only
   STATUS       current
   DESCRIPTION
     "The number of fragments received over this EFM Link
	  that are smaller than the minimum fragment size (64 bytes)."
   ::= { adGenEfmPerfLinkFreeRollingCountEntry 4 }

adGenEfmPerfLinkFreeRollingCountRxLargeFragments OBJECT-TYPE
   SYNTAX       Counter32
   MAX-ACCESS   read-only
   STATUS       current
   DESCRIPTION
     "The number of fragments received over this EFM Link
	  that are larger than the maximum fragment size (512 bytes)."
   ::= { adGenEfmPerfLinkFreeRollingCountEntry 5 }

adGenEfmPerfLinkFreeRollingCountRxDiscardedFragments OBJECT-TYPE
   SYNTAX       Counter32
   MAX-ACCESS   read-only
   STATUS       current
   DESCRIPTION
     "The number of received fragments that have been
	  discarded due to errors."
   ::= { adGenEfmPerfLinkFreeRollingCountEntry 6 }

adGenEfmPerfLinkFreeRollingCountRxFcsErrors OBJECT-TYPE
   SYNTAX       Counter32
   MAX-ACCESS   read-only
   STATUS       current
   DESCRIPTION
     "The number of FCS errros detected by the 64/65-octet
	  receive function."
   ::= { adGenEfmPerfLinkFreeRollingCountEntry 7 }

adGenEfmPerfLinkFreeRollingCountRxCodingErrors OBJECT-TYPE
   SYNTAX       Counter32
   MAX-ACCESS   read-only
   STATUS       current
   DESCRIPTION
     "The number of 64/65-octet encapsulation errors detected
	  by the 64/65-octet receive function."
   ::= { adGenEfmPerfLinkFreeRollingCountEntry 8 }

-- ******************************************************************************************
-- MIB Groups
-- ******************************************************************************************
adGenEfmIndexGroup OBJECT-GROUP
   OBJECTS
   {
        adGenEfmUnitIndex
   }
   STATUS current
   DESCRIPTION
     "These objects provide support for EFM indexing."
   ::= { adGenEfmMibGroups 1 }

adGenEfmCfgGroup OBJECT-GROUP
   OBJECTS
   {
        adGenEfmConfMaxGroups,
        adGenEfmConfMaxGroupSize
   }
   STATUS current
   DESCRIPTION
     "These objects provide support for EFM configuration."
   ::= { adGenEfmMibGroups 2 }

adGenEfmProvGroup OBJECT-GROUP
   OBJECTS
   {
        adGenEfmProvErrorString,
        adGenEfmProvGroupServiceState,
        adGenEfmProvGroupFragmentSize,
        adGenEfmProvGroupSkewThreshold,
        adGenEfmProvGroupXCVThreshold,
        adGenEfmProvLinkAssignment,
        adGenEfmProvGroupName,
		adGenEfmProvGroupXCVLinkRemoval,
		adGenEfmProvGroupLoopbackDetection,
		adGenEfmProvLinkIfAssignment
   }
   STATUS current
   DESCRIPTION
     "These objects provide support for the provisioning of
      of EFM groups and links"
   ::= { adGenEfmMibGroups 3}

adGenEfmStatGroup OBJECT-GROUP
   OBJECTS
   {
        adGenEfmStatGroupStatus,
        adGenEfmStatGroupSize,
        adGenEfmStatNumActiveLinks,
        adGenEfmStatLinkNeTcSync,
        adGenEfmStatLinkFeTcSync
   }
   STATUS current
   DESCRIPTION
     "These objects provide support for the reporting of status
      of EFM groups and links"
   ::= { adGenEfmMibGroups 4}

adGenEfmTestGroup OBJECT-GROUP
   OBJECTS
   {
        adGenEfmTestOamRemoteLoopback,
        adGenEfmTestOamRemoteLoopbackTimeout
   }
   STATUS current
   DESCRIPTION
     "These objects provide access for the testing
      of EFM groups and links"
   ::= { adGenEfmMibGroups 5}

adGenEfmCurr15MinPerfGroup OBJECT-GROUP
   OBJECTS
   {
        adGenEfmPerfGroupCurr15MinTxOctets,
        adGenEfmPerfGroupCurr15MinTxFrames,
        adGenEfmPerfGroupCurr15MinRxOctets,
        adGenEfmPerfGroupCurr15MinRxFrames,
        adGenEfmPerfGroupCurr15MinRxBadFragments,
        adGenEfmPerfGroupCurr15MinRxLostFragments,
        adGenEfmPerfGroupCurr15MinRxLostStarts,
        adGenEfmPerfGroupCurr15MinRxLostEnds,
        adGenEfmPerfGroup15MinValidIntervals,
		adGenEfmPerfGroupCurr15MinTxPercUtil,
		adGenEfmPerfGroupCurr15MinRxPercUtil,
        adGenEfmPerfLinkCurr15MinTxFragments,
        adGenEfmPerfLinkCurr15MinRxFragments,
        adGenEfmPerfLinkCurr15MinRxErroredFragments,
        adGenEfmPerfLinkCurr15MinRxSmallFragments,
        adGenEfmPerfLinkCurr15MinRxLargeFragments,
        adGenEfmPerfLinkCurr15MinRxDiscardedFragments,
        adGenEfmPerfLinkCurr15MinRxFcsErrors,
        adGenEfmPerfLinkCurr15MinRxCodingErrors,
        adGenEfmPerfLink15MinValidIntervals
   }
   STATUS current
   DESCRIPTION
     "These objects provide support for the reporting of the
      current 15 minute interval of PM data."
   ::= { adGenEfmMibGroups 6}

adGenEfmCurr24HrPerfGroup OBJECT-GROUP
   OBJECTS
   {
        adGenEfmPerfGroupCurr24HrTxOctets,
        adGenEfmPerfGroupCurr24HrTxFrames,
        adGenEfmPerfGroupCurr24HrRxOctets,
        adGenEfmPerfGroupCurr24HrRxFrames,
        adGenEfmPerfGroupCurr24HrRxBadFragments,
        adGenEfmPerfGroupCurr24HrRxLostFragments,
        adGenEfmPerfGroupCurr24HrRxLostStarts,
        adGenEfmPerfGroupCurr24HrRxLostEnds,
        adGenEfmPerfGroup24HrValidIntervals,
		adGenEfmPerfGroupCurr24HrTxPercUtil,
		adGenEfmPerfGroupCurr24HrRxPercUtil,
        adGenEfmPerfLinkCurr24HrTxFragments,
        adGenEfmPerfLinkCurr24HrRxFragments,
        adGenEfmPerfLinkCurr24HrRxErroredFragments,
        adGenEfmPerfLinkCurr24HrRxSmallFragments,
        adGenEfmPerfLinkCurr24HrRxLargeFragments,
        adGenEfmPerfLinkCurr24HrRxDiscardedFragments,
        adGenEfmPerfLinkCurr24HrRxFcsErrors,
        adGenEfmPerfLinkCurr24HrRxCodingErrors,
        adGenEfmPerfLink24HrValidIntervals
   }
   STATUS current
   DESCRIPTION
     "These objects provide support for the reporting of the
      current 24 hour interval of PM data."
   ::= { adGenEfmMibGroups 7}

adGenEfmInt15MinPerfGroup OBJECT-GROUP
   OBJECTS
   {
        adGenEfmPerfGroup15MinIntTxOctets,
        adGenEfmPerfGroup15MinIntTxFrames,
        adGenEfmPerfGroup15MinIntRxOctets,
        adGenEfmPerfGroup15MinIntRxFrames,
        adGenEfmPerfGroup15MinIntRxBadFragments,
        adGenEfmPerfGroup15MinIntRxLostFragments,
        adGenEfmPerfGroup15MinIntRxLostStarts,
        adGenEfmPerfGroup15MinIntRxLostEnds,
		adGenEfmPerfGroup15MinIntTxPercUtil,
        adGenEfmPerfGroup15MinIntRxPercUtil,
        adGenEfmPerfLink15MinIntTxFragments,
        adGenEfmPerfLink15MinIntRxFragments,
        adGenEfmPerfLink15MinIntRxErroredFragments,
        adGenEfmPerfLink15MinIntRxSmallFragments,
        adGenEfmPerfLink15MinIntRxLargeFragments,
        adGenEfmPerfLink15MinIntRxDiscardedFragments,
        adGenEfmPerfLink15MinIntRxFcsErrors,
        adGenEfmPerfLink15MinIntRxCodingErrors
   }
   STATUS current
   DESCRIPTION
     "These objects provide support for the reporting of the
      selected 15 minute interval of PM data."
   ::= { adGenEfmMibGroups 8}

adGenEfmInt24HrPerfGroup OBJECT-GROUP
   OBJECTS
   {
        adGenEfmPerfGroup24HrIntTxOctets,
        adGenEfmPerfGroup24HrIntTxFrames,
        adGenEfmPerfGroup24HrIntRxOctets,
        adGenEfmPerfGroup24HrIntRxFrames,
        adGenEfmPerfGroup24HrIntRxBadFragments,
        adGenEfmPerfGroup24HrIntRxLostFragments,
        adGenEfmPerfGroup24HrIntRxLostStarts,
        adGenEfmPerfGroup24HrIntRxLostEnds,
        adGenEfmPerfLink24HrIntTxFragments,
        adGenEfmPerfLink24HrIntRxFragments,
        adGenEfmPerfLink24HrIntRxErroredFragments,
        adGenEfmPerfLink24HrIntRxSmallFragments,
        adGenEfmPerfLink24HrIntRxLargeFragments,
        adGenEfmPerfLink24HrIntRxDiscardedFragments,
        adGenEfmPerfLink24HrIntRxFcsErrors,
        adGenEfmPerfLink24HrIntRxCodingErrors
   }
   STATUS current
   DESCRIPTION
     "These objects provide support for the reporting of the
      selected 24 hour interval of PM data."
   ::= { adGenEfmMibGroups 9}

adGenEfmResetPerfGroup OBJECT-GROUP
   OBJECTS
   {
        adGenEfmPerfResetGroupData,
        adGenEfmPerfResetLinkData,
        adGenEfmPerfGroupReset,
        adGenEfmPerfLinkReset
   }
   STATUS current
   DESCRIPTION
     "These objects provide support for resetting of PM data."
   ::= { adGenEfmMibGroups 10}

adGenEfmEventGroup  NOTIFICATION-GROUP
   NOTIFICATIONS  {
        adGenEfmGroupDownClr,
        adGenEfmGroupDownAct,
        adGenEfmLinkDownClr,
        adGenEfmLinkDownAct,
        adGenEfmGroupDownPartialClr,
        adGenEfmGroupDownPartialAct,
	adGenEfmGroupDownstreamBandwidthClr,
	adGenEfmGroupDownstreamBandwidthAct,
	adGenEfmGroupUpstreamBandwidthClr,
	adGenEfmGroupUpstreamBandwidthAct,
	adGenEfmGroupDownstream4xRateViolationClr,
	adGenEfmGroupDownstream4xRateViolationAct,
	adGenEfmGroupUpstream4xRateViolationClr,
	adGenEfmGroupUpstream4xRateViolationAct,
        adGenEfmGroup15MinRxBadFragmentsAct,
        adGenEfmGroup15MinRxLostFragmentsAct,
        adGenEfmGroup15MinRxLostStartsAct,
        adGenEfmGroup15MinRxLostEndsAct,
        adGenEfmGroup24HrRxBadFragmentsAct,
        adGenEfmGroup24HrRxLostFragmentsAct,
        adGenEfmGroup24HrRxLostStartsAct,
        adGenEfmGroup24HrRxLostEndsAct,
        adGenEfmLink15MinRxErroredFragmentsAct,
        adGenEfmLink15MinRxSmallFragmentsAct,
        adGenEfmLink15MinRxLargeFragmentsAct,
        adGenEfmLink15MinRxDiscardedFragmentsAct,
        adGenEfmLink15MinRxFcsErrorsAct,
        adGenEfmLink15MinRxCodingErrorsAct,
        adGenEfmLink24HrRxErroredFragmentsAct,
        adGenEfmLink24HrRxSmallFragmentsAct,
        adGenEfmLink24HrRxLargeFragmentsAct,
        adGenEfmLink24HrRxDiscardedFragmentsAct,
        adGenEfmLink24HrRxFcsErrorsAct,
        adGenEfmLink24HrRxCodingErrorsAct
 }
 STATUS current
 DESCRIPTION "GenEFM Notification Group"
 ::= {adGenEfmMibGroups 11}

adGenEfm15MinThreshPerfGroup OBJECT-GROUP
   OBJECTS
   {
        adGenEfmPerfGroup15MinThreshRxBadFragments,
        adGenEfmPerfGroup15MinThreshRxLostFragments,
        adGenEfmPerfGroup15MinThreshRxLostStarts,
        adGenEfmPerfGroup15MinThreshRxLostEnds,
        adGenEfmPerfLink15MinThreshRxErroredFragments,
        adGenEfmPerfLink15MinThreshRxSmallFragments,
        adGenEfmPerfLink15MinThreshRxLargeFragments,
        adGenEfmPerfLink15MinThreshRxDiscardedFragments,
        adGenEfmPerfLink15MinThreshRxFcsErrors,
        adGenEfmPerfLink15MinThreshRxCodingErrors
   }
   STATUS current
   DESCRIPTION
     "These objects provide support for the provisioning of
      15 minute thresholds."
   ::= { adGenEfmMibGroups 12}

adGenEfm24HrThreshPerfGroup OBJECT-GROUP
   OBJECTS
   {
        adGenEfmPerfGroup24HrThreshRxBadFragments,
        adGenEfmPerfGroup24HrThreshRxLostFragments,
        adGenEfmPerfGroup24HrThreshRxLostStarts,
        adGenEfmPerfGroup24HrThreshRxLostEnds,
        adGenEfmPerfLink24HrThreshRxErroredFragments,
        adGenEfmPerfLink24HrThreshRxSmallFragments,
        adGenEfmPerfLink24HrThreshRxLargeFragments,
        adGenEfmPerfLink24HrThreshRxDiscardedFragments,
        adGenEfmPerfLink24HrThreshRxFcsErrors,
        adGenEfmPerfLink24HrThreshRxCodingErrors
   }
   STATUS current
   DESCRIPTION
     "These objects provide support for the provisioning of
      24 hour thresholds."
   ::= { adGenEfmMibGroups 13}


-- ******************************************************************************************
-- Alarms
-- ******************************************************************************************
adGenEfmGroupDownClr   NOTIFICATION-TYPE
    OBJECTS         {
                    adTrapInformSeqNum,
                    sysName,
                    adGenSlotInfoIndex,
                    adGenPortTrapIdentifier,
                    ifIndex
                    }
    STATUS          current
    DESCRIPTION     "EFM Group Down - Cleared. All the links in the Group are
                     not down."

    --#TYPE         "Status - Alarm"
    --#SUMMARY      "EFM Group Down - Cleared"
    --#SUMMARY      "cleared at shelf: %s, slot: %d, interface %d"
    --#ARGUMENTS    {1,2,4}
    --#SEVERITY     "MAJOR"
    --#GENERIC      6
    --#CATEGORY     "Alarm Events"
    --#SOURCE_ID    "A"
    --#TIMEINDEX    0
    ::= {adGenEfmAlarms 2}

adGenEfmGroupDownAct   NOTIFICATION-TYPE
    OBJECTS         {
                    adTrapInformSeqNum,
                    sysName,
                    adGenSlotInfoIndex,
                    adGenPortTrapIdentifier,
                    ifIndex
                    }
    STATUS          current
    DESCRIPTION     "EFM Group Down - Active. All the links in the Group are
                     down."


    --#TYPE         "Status - Alarm"
    --#SUMMARY      "EFM Group Down - Active"
    --#SUMMARY      "detected at shelf: %s, slot: %d, interface %d"
    --#ARGUMENTS    {1,2,4}
    --#SEVERITY     "MAJOR"
    --#GENERIC      6
    --#CATEGORY     "Alarm Events"
    --#SOURCE_ID    "A"
    --#TIMEINDEX    0
    ::= {adGenEfmAlarms 3}

adGenEfmLinkDownClr   NOTIFICATION-TYPE
    OBJECTS         {
                    adTrapInformSeqNum,
                    sysName,
                    adGenSlotInfoIndex,
                    adGenPortTrapIdentifier,
                    ifIndex
                    }
    STATUS          current
    DESCRIPTION     "EFM Link Down - Cleared. TC-SYNC has been achieved for this
                     EFM Link."

    --#TYPE         "Status - Alarm"
    --#SUMMARY      "EFM Link Down - Cleared"
    --#SUMMARY      "cleared at shelf: %s, slot: %d, interface %d"
    --#ARGUMENTS    {1,2,4}
    --#SEVERITY     "MAJOR"
    --#GENERIC      6
    --#CATEGORY     "Alarm Events"
    --#SOURCE_ID    "A"
    --#TIMEINDEX    0
    ::= {adGenEfmAlarms 4}

adGenEfmLinkDownAct   NOTIFICATION-TYPE
    OBJECTS         {
                    adTrapInformSeqNum,
                    sysName,
                    adGenSlotInfoIndex,
                    adGenPortTrapIdentifier,
                    ifIndex
                    }
    STATUS          current
    DESCRIPTION     "EFM Link Down - Active. There is no TC-SYNC on this EFM
                     Link."

    --#TYPE         "Status - Alarm"
    --#SUMMARY      "EFM Link Down - Active"
    --#SUMMARY      "detected at shelf: %s, slot: %d, interface %d"
    --#ARGUMENTS    {1,2,4}
    --#SEVERITY     "MAJOR"
    --#GENERIC      6
    --#CATEGORY     "Alarm Events"
    --#SOURCE_ID    "A"
    --#TIMEINDEX    0
    ::= {adGenEfmAlarms 5}

adGenEfmGroupDownPartialClr   NOTIFICATION-TYPE
    OBJECTS         {
                    adTrapInformSeqNum,
                    sysName,
                    adGenSlotInfoIndex,
                    adGenPortTrapIdentifier,
                    ifIndex
                    }
    STATUS          current
    DESCRIPTION     "EFM Group Down Partial - Cleared. The number of active links
                     in the group are greater than or equal to the minimum
                     number of links provisioned for the group."

    --#TYPE         "Status - Alarm"
    --#SUMMARY      "EFM Group Down Partial - Cleared"
    --#SUMMARY      "cleared at shelf: %s, slot: %d, interface %d"
    --#ARGUMENTS    {1,2,4}
    --#SEVERITY     "MAJOR"
    --#GENERIC      6
    --#CATEGORY     "Alarm Events"
    --#SOURCE_ID    "A"
    --#TIMEINDEX    0
    ::= {adGenEfmAlarms 6}

adGenEfmGroupDownPartialAct   NOTIFICATION-TYPE
    OBJECTS         {
                    adTrapInformSeqNum,
                    sysName,
                    adGenSlotInfoIndex,
                    adGenPortTrapIdentifier,
                    ifIndex
                    }
    STATUS          current
    DESCRIPTION     "EFM Group Down Partial - Active. The number of active
                     links in this group are either down or less than the
                     minimum number of links provisioned for the group."

    --#TYPE         "Status - Alarm"
    --#SUMMARY      "EFM Group Down Partial - Active"
    --#SUMMARY      "detected at shelf: %s, slot: %d, interface %d"
    --#ARGUMENTS    {1,2,4}
    --#SEVERITY     "MAJOR"
    --#GENERIC      6
    --#CATEGORY     "Alarm Events"
    --#SOURCE_ID    "A"
    --#TIMEINDEX    0
    ::= {adGenEfmAlarms 7}

adGenEfmGroupDownstreamBandwidthClr   NOTIFICATION-TYPE
    OBJECTS         {
                    adTrapInformSeqNum,
                    sysName,
                    adGenSlotInfoIndex,
                    adGenPortTrapIdentifier,
                    ifIndex
                    }
    STATUS          current
    DESCRIPTION     "EFM Group Downstream Bandwidth - Cleared.
                     The cumulative downstream rate of all the links in the
                     group is less than the service rate for the group."

    --#TYPE         "Status - Alarm"
    --#SUMMARY      "EFM Group Downstream Bandwidth - Cleared"
    --#SUMMARY      "cleared at shelf: %s, slot: %d, interface %d"
    --#ARGUMENTS    {1,2,4}
    --#SEVERITY     "MINOR"
    --#GENERIC      6
    --#CATEGORY     "Alarm Events"
    --#SOURCE_ID    "A"
    --#TIMEINDEX    0
    ::= {adGenEfmAlarms 8}

adGenEfmGroupDownstreamBandwidthAct   NOTIFICATION-TYPE
    OBJECTS         {
                    adTrapInformSeqNum,
                    sysName,
                    adGenSlotInfoIndex,
                    adGenPortTrapIdentifier,
                    ifIndex
                    }
    STATUS          current
    DESCRIPTION     "EFM Group Downstream Bandwidth - Active.
                     The cumulative downstream rate of all the links in the
                     group is less than the service rate for the group."

    --#TYPE         "Status - Alarm"
    --#SUMMARY      "EFM Group Downstream Bandwidth - Active"
    --#SUMMARY      "detected at shelf: %s, slot: %d, interface %d"
    --#ARGUMENTS    {1,2,4}
    --#SEVERITY     "MINOR"
    --#GENERIC      6
    --#CATEGORY     "Alarm Events"
    --#SOURCE_ID    "A"
    --#TIMEINDEX    0
    ::= {adGenEfmAlarms 9}

adGenEfmGroupUpstreamBandwidthClr   NOTIFICATION-TYPE
    OBJECTS         {
                    adTrapInformSeqNum,
                    sysName,
                    adGenSlotInfoIndex,
                    adGenPortTrapIdentifier,
                    ifIndex
                    }
    STATUS          current
    DESCRIPTION     "EFM Group Upstream Bandwidth - Cleared.
                     The cumulative upstream rate of all the links in the
                     group is less than the service rate for the group."

    --#TYPE         "Status - Alarm"
    --#SUMMARY      "EFM Group Upstream Bandwidth - Cleared"
    --#SUMMARY      "cleared at shelf: %s, slot: %d, interface %d"
    --#ARGUMENTS    {1,2,4}
    --#SEVERITY     "MINOR"
    --#GENERIC      6
    --#CATEGORY     "Alarm Events"
    --#SOURCE_ID    "A"
    --#TIMEINDEX    0
    ::= {adGenEfmAlarms 10}

adGenEfmGroupUpstreamBandwidthAct   NOTIFICATION-TYPE
    OBJECTS         {
                    adTrapInformSeqNum,
                    sysName,
                    adGenSlotInfoIndex,
                    adGenPortTrapIdentifier,
                    ifIndex
                    }
    STATUS          current
    DESCRIPTION     "EFM Group Upstream Bandwidth - Active.
                     The cumulative upstream rate of all the links in the
                     group is less than the service rate for the group."

    --#TYPE         "Status - Alarm"
    --#SUMMARY      "EFM Group Upstream Bandwidth - Active"
    --#SUMMARY      "detected at shelf: %s, slot: %d, interface %d"
    --#ARGUMENTS    {1,2,4}
    --#SEVERITY     "MINOR"
    --#GENERIC      6
    --#CATEGORY     "Alarm Events"
    --#SOURCE_ID    "A"
    --#TIMEINDEX    0
    ::= {adGenEfmAlarms 11}

adGenEfmGroupDownstream4xRateViolationClr   NOTIFICATION-TYPE
    OBJECTS         {
                    adTrapInformSeqNum,
                    sysName,
                    adGenSlotInfoIndex,
                    adGenPortTrapIdentifier,
                    ifIndex
                    }
    STATUS          current
    DESCRIPTION     "EFM Group Downstream 4x Rate Violation - Cleared.
                     Links in the group are violating the 4x constraint."

    --#TYPE         "Status - Alarm"
    --#SUMMARY      "EFM Group Downstream 4x Rate Violation - Cleared"
    --#SUMMARY      "cleared at shelf: %s, slot: %d, interface %d"
    --#ARGUMENTS    {1,2,4}
    --#SEVERITY     "MINOR"
    --#GENERIC      6
    --#CATEGORY     "Alarm Events"
    --#SOURCE_ID    "A"
    --#TIMEINDEX    0
    ::= {adGenEfmAlarms 12}

adGenEfmGroupDownstream4xRateViolationAct   NOTIFICATION-TYPE
    OBJECTS         {
                    adTrapInformSeqNum,
                    sysName,
                    adGenSlotInfoIndex,
                    adGenPortTrapIdentifier,
                    ifIndex
                    }
    STATUS          current
    DESCRIPTION     "EFM Group Downstream 4x Rate Violation - Active.
                     Links in the group are violating the 4x constraint."

    --#TYPE         "Status - Alarm"
    --#SUMMARY      "EFM Group Downstream 4x Rate Violation - Active"
    --#SUMMARY      "detected at shelf: %s, slot: %d, interface %d"
    --#ARGUMENTS    {1,2,4}
    --#SEVERITY     "MINOR"
    --#GENERIC      6
    --#CATEGORY     "Alarm Events"
    --#SOURCE_ID    "A"
    --#TIMEINDEX    0
    ::= {adGenEfmAlarms 13}

adGenEfmGroupUpstream4xRateViolationClr   NOTIFICATION-TYPE
    OBJECTS         {
                    adTrapInformSeqNum,
                    sysName,
                    adGenSlotInfoIndex,
                    adGenPortTrapIdentifier,
                    ifIndex
                    }
    STATUS          current
    DESCRIPTION     "EFM Group Upstream 4x Rate Violation - Cleared.
                     Links in the group are violating the 4x constraint."

    --#TYPE         "Status - Alarm"
    --#SUMMARY      "EFM Group Upstream 4x Rate Violation - Cleared"
    --#SUMMARY      "cleared at shelf: %s, slot: %d, interface %d"
    --#ARGUMENTS    {1,2,4}
    --#SEVERITY     "MINOR"
    --#GENERIC      6
    --#CATEGORY     "Alarm Events"
    --#SOURCE_ID    "A"
    --#TIMEINDEX    0
    ::= {adGenEfmAlarms 14}

adGenEfmGroupUpstream4xRateViolationAct   NOTIFICATION-TYPE
    OBJECTS         {
                    adTrapInformSeqNum,
                    sysName,
                    adGenSlotInfoIndex,
                    adGenPortTrapIdentifier,
                    ifIndex
                    }
    STATUS          current
    DESCRIPTION     "EFM Group Upstream 4x Rate Violation - Active.
                     Links in the group are violating the 4x constraint."

    --#TYPE         "Status - Alarm"
    --#SUMMARY      "EFM Group Upstream 4x Rate Violation - Active"
    --#SUMMARY      "detected at shelf: %s, slot: %d, interface %d"
    --#ARGUMENTS    {1,2,4}
    --#SEVERITY     "MINOR"
    --#GENERIC      6
    --#CATEGORY     "Alarm Events"
    --#SOURCE_ID    "A"
    --#TIMEINDEX    0
    ::= {adGenEfmAlarms 15}

-- ******************************************************************************************
-- Threshold Alarms
-- ******************************************************************************************
adGenEfmGroup15MinRxBadFragmentsAct   NOTIFICATION-TYPE
    OBJECTS         {
                    adTrapInformSeqNum,
                    sysName,
                    adGenSlotInfoIndex,
                    adGenPortTrapIdentifier,
                    ifIndex
                    }
    STATUS          current
    DESCRIPTION
                    "EFM Group Rx Bad Fragments 15 Minute Threshold Crossed"
    --#TYPE         "Status - Alarm"
    --#SUMMARY      "EFM Group Rx Bad Fragments 15 Minute Threshold Crossed"
    --#SUMMARY      "detected at shelf: %s, slot: %d, interface %d"
    --#ARGUMENTS    {1,2,4}
    --#SEVERITY     "MAJOR"
    --#GENERIC      6
    --#CATEGORY     "Alarm Events"
    --#SOURCE_ID    "A"
    --#TIMEINDEX    0
    ::= {adGenEfmAlarms 20}

adGenEfmGroup15MinRxLostFragmentsAct   NOTIFICATION-TYPE
    OBJECTS         {
                    adTrapInformSeqNum,
                    sysName,
                    adGenSlotInfoIndex,
                    adGenPortTrapIdentifier,
                    ifIndex
                    }
    STATUS          current
    DESCRIPTION
                    "EFM Group Rx Lost Fragments 15 Minute Threshold Crossed"
    --#TYPE         "Status - Alarm"
    --#SUMMARY      "EFM Group Rx Lost Fragments 15 Minute Threshold Crossed"
    --#SUMMARY      "detected at shelf: %s, slot: %d, interface %d"
    --#ARGUMENTS    {1,2,4}
    --#SEVERITY     "MAJOR"
    --#GENERIC      6
    --#CATEGORY     "Alarm Events"
    --#SOURCE_ID    "A"
    --#TIMEINDEX    0
    ::= {adGenEfmAlarms 21}

adGenEfmGroup15MinRxLostStartsAct   NOTIFICATION-TYPE
    OBJECTS         {
                    adTrapInformSeqNum,
                    sysName,
                    adGenSlotInfoIndex,
                    adGenPortTrapIdentifier,
                    ifIndex
                    }
    STATUS          current
    DESCRIPTION
                    "EFM Group Rx Lost Starts 15 Minute Threshold Crossed"
    --#TYPE         "Status - Alarm"
    --#SUMMARY      "EFM Group Rx Lost Starts 15 Minute Threshold Crossed"
    --#SUMMARY      "detected at shelf: %s, slot: %d, interface %d"
    --#ARGUMENTS    {1,2,4}
    --#SEVERITY     "MAJOR"
    --#GENERIC      6
    --#CATEGORY     "Alarm Events"
    --#SOURCE_ID    "A"
    --#TIMEINDEX    0
    ::= {adGenEfmAlarms 22}

adGenEfmGroup15MinRxLostEndsAct   NOTIFICATION-TYPE
    OBJECTS         {
                    adTrapInformSeqNum,
                    sysName,
                    adGenSlotInfoIndex,
                    adGenPortTrapIdentifier,
                    ifIndex
                    }
    STATUS          current
    DESCRIPTION
                    "EFM Group Rx Lost Ends 15 Minute Threshold Crossed"
    --#TYPE         "Status - Alarm"
    --#SUMMARY      "EFM Group Rx Lost Ends 15 Minute Threshold Crossed"
    --#SUMMARY      "detected at shelf: %s, slot: %d, interface %d"
    --#ARGUMENTS    {1,2,4}
    --#SEVERITY     "MAJOR"
    --#GENERIC      6
    --#CATEGORY     "Alarm Events"
    --#SOURCE_ID    "A"
    --#TIMEINDEX    0
    ::= {adGenEfmAlarms 23}

adGenEfmGroup24HrRxBadFragmentsAct   NOTIFICATION-TYPE
    OBJECTS         {
                    adTrapInformSeqNum,
                    sysName,
                    adGenSlotInfoIndex,
                    adGenPortTrapIdentifier,
                    ifIndex
                    }
    STATUS          current
    DESCRIPTION
                    "EFM Group Rx Bad Fragments 24 Hour Threshold Crossed"
    --#TYPE         "Status - Alarm"
    --#SUMMARY      "EFM Group Rx Bad Fragments 24 Hour Threshold Crossed"
    --#SUMMARY      "detected at shelf: %s, slot: %d, interface %d"
    --#ARGUMENTS    {1,2,4}
    --#SEVERITY     "MAJOR"
    --#GENERIC      6
    --#CATEGORY     "Alarm Events"
    --#SOURCE_ID    "A"
    --#TIMEINDEX    0
    ::= {adGenEfmAlarms 24}

adGenEfmGroup24HrRxLostFragmentsAct   NOTIFICATION-TYPE
    OBJECTS         {
                    adTrapInformSeqNum,
                    sysName,
                    adGenSlotInfoIndex,
                    adGenPortTrapIdentifier,
                    ifIndex
                    }
    STATUS          current
    DESCRIPTION
                    "EFM Group Rx Lost Fragments 24 Hour Threshold Crossed"
    --#TYPE         "Status - Alarm"
    --#SUMMARY      "EFM Group Rx Lost Fragments 24 Hour Threshold Crossed"
    --#SUMMARY      "detected at shelf: %s, slot: %d, interface %d"
    --#ARGUMENTS    {1,2,4}
    --#SEVERITY     "MAJOR"
    --#GENERIC      6
    --#CATEGORY     "Alarm Events"
    --#SOURCE_ID    "A"
    --#TIMEINDEX    0
    ::= {adGenEfmAlarms 25}

adGenEfmGroup24HrRxLostStartsAct   NOTIFICATION-TYPE
    OBJECTS         {
                    adTrapInformSeqNum,
                    sysName,
                    adGenSlotInfoIndex,
                    adGenPortTrapIdentifier,
                    ifIndex
                    }
    STATUS          current
    DESCRIPTION
                    "EFM Group Rx Lost Starts 24 Hour Threshold Crossed"
    --#TYPE         "Status - Alarm"
    --#SUMMARY      "EFM Group Rx Lost Starts 24 Hour Threshold Crossed"
    --#SUMMARY      "detected at shelf: %s, slot: %d, interface %d"
    --#ARGUMENTS    {1,2,4}
    --#SEVERITY     "MAJOR"
    --#GENERIC      6
    --#CATEGORY     "Alarm Events"
    --#SOURCE_ID    "A"
    --#TIMEINDEX    0
    ::= {adGenEfmAlarms 26}

adGenEfmGroup24HrRxLostEndsAct   NOTIFICATION-TYPE
    OBJECTS         {
                    adTrapInformSeqNum,
                    sysName,
                    adGenSlotInfoIndex,
                    adGenPortTrapIdentifier,
                    ifIndex
                    }
    STATUS          current
    DESCRIPTION
                    "EFM Group Rx Lost Ends 24 Hour Threshold Crossed"
    --#TYPE         "Status - Alarm"
    --#SUMMARY      "EFM Group Rx Lost Ends 24 Hour Threshold Crossed"
    --#SUMMARY      "detected at shelf: %s, slot: %d, interface %d"
    --#ARGUMENTS    {1,2,4}
    --#SEVERITY     "MAJOR"
    --#GENERIC      6
    --#CATEGORY     "Alarm Events"
    --#SOURCE_ID    "A"
    --#TIMEINDEX    0
    ::= {adGenEfmAlarms 27}

adGenEfmLink15MinRxErroredFragmentsAct   NOTIFICATION-TYPE
    OBJECTS         {
                    adTrapInformSeqNum,
                    sysName,
                    adGenSlotInfoIndex,
                    adGenPortTrapIdentifier,
                    ifIndex
                    }
    STATUS          current
    DESCRIPTION
                    "EFM Link Rx Errored Fragments 15 Minute Threshold Crossed"
    --#TYPE         "Status - Alarm"
    --#SUMMARY      "EFM Link Rx Errored Fragments 15 Minute Threshold Crossed"
    --#SUMMARY      "detected at shelf: %s, slot: %d, interface %d"
    --#ARGUMENTS    {1,2,4}
    --#SEVERITY     "MAJOR"
    --#GENERIC      6
    --#CATEGORY     "Alarm Events"
    --#SOURCE_ID    "A"
    --#TIMEINDEX    0
    ::= {adGenEfmAlarms 28}

adGenEfmLink15MinRxSmallFragmentsAct   NOTIFICATION-TYPE
    OBJECTS         {
                    adTrapInformSeqNum,
                    sysName,
                    adGenSlotInfoIndex,
                    adGenPortTrapIdentifier,
                    ifIndex
                    }
    STATUS          current
    DESCRIPTION
                    "EFM Link Rx Small Fragments 15 Minute Threshold Crossed"
    --#TYPE         "Status - Alarm"
    --#SUMMARY      "EFM Link Rx Small Fragments 15 Minute Threshold Crossed"
    --#SUMMARY      "detected at shelf: %s, slot: %d, interface %d"
    --#ARGUMENTS    {1,2,4}
    --#SEVERITY     "MAJOR"
    --#GENERIC      6
    --#CATEGORY     "Alarm Events"
    --#SOURCE_ID    "A"
    --#TIMEINDEX    0
    ::= {adGenEfmAlarms 29}

adGenEfmLink15MinRxLargeFragmentsAct   NOTIFICATION-TYPE
    OBJECTS         {
                    adTrapInformSeqNum,
                    sysName,
                    adGenSlotInfoIndex,
                    adGenPortTrapIdentifier,
                    ifIndex
                    }
    STATUS          current
    DESCRIPTION
                    "EFM Link Rx Large Fragments 15 Minute Threshold Crossed"
    --#TYPE         "Status - Alarm"
    --#SUMMARY      "EFM Link Rx Large Fragments 15 Minute Threshold Crossed"
    --#SUMMARY      "detected at shelf: %s, slot: %d, interface %d"
    --#ARGUMENTS    {1,2,4}
    --#SEVERITY     "MAJOR"
    --#GENERIC      6
    --#CATEGORY     "Alarm Events"
    --#SOURCE_ID    "A"
    --#TIMEINDEX    0
    ::= {adGenEfmAlarms 30}

adGenEfmLink15MinRxDiscardedFragmentsAct   NOTIFICATION-TYPE
    OBJECTS         {
                    adTrapInformSeqNum,
                    sysName,
                    adGenSlotInfoIndex,
                    adGenPortTrapIdentifier,
                    ifIndex
                    }
    STATUS          current
    DESCRIPTION
                    "EFM Link Rx Discarded Fragments 15 Minute Threshold Crossed"
    --#TYPE         "Status - Alarm"
    --#SUMMARY      "EFM Link Rx Discarded Fragments 15 Minute Threshold Crossed"
    --#SUMMARY      "detected at shelf: %s, slot: %d, interface %d"
    --#ARGUMENTS    {1,2,4}
    --#SEVERITY     "MAJOR"
    --#GENERIC      6
    --#CATEGORY     "Alarm Events"
    --#SOURCE_ID    "A"
    --#TIMEINDEX    0
    ::= {adGenEfmAlarms 31}

adGenEfmLink15MinRxFcsErrorsAct   NOTIFICATION-TYPE
    OBJECTS         {
                    adTrapInformSeqNum,
                    sysName,
                    adGenSlotInfoIndex,
                    adGenPortTrapIdentifier,
                    ifIndex
                    }
    STATUS          current
    DESCRIPTION
                    "EFM Link Rx FCS Errors 15 Minute Threshold Crossed"
    --#TYPE         "Status - Alarm"
    --#SUMMARY      "EFM Link Rx FCS Errors 15 Minute Threshold Crossed"
    --#SUMMARY      "detected at shelf: %s, slot: %d, interface %d"
    --#ARGUMENTS    {1,2,4}
    --#SEVERITY     "MAJOR"
    --#GENERIC      6
    --#CATEGORY     "Alarm Events"
    --#SOURCE_ID    "A"
    --#TIMEINDEX    0
    ::= {adGenEfmAlarms 32}

adGenEfmLink15MinRxCodingErrorsAct   NOTIFICATION-TYPE
    OBJECTS         {
                    adTrapInformSeqNum,
                    sysName,
                    adGenSlotInfoIndex,
                    adGenPortTrapIdentifier,
                    ifIndex
                    }
    STATUS          current
    DESCRIPTION
                    "EFM Link Rx Coding Errors 15 Minute Threshold Crossed"
    --#TYPE         "Status - Alarm"
    --#SUMMARY      "EFM Link Rx Coding Errors 15 Minute Threshold Crossed"
    --#SUMMARY      "detected at shelf: %s, slot: %d, interface %d"
    --#ARGUMENTS    {1,2,4}
    --#SEVERITY     "MAJOR"
    --#GENERIC      6
    --#CATEGORY     "Alarm Events"
    --#SOURCE_ID    "A"
    --#TIMEINDEX    0
    ::= {adGenEfmAlarms 33}

adGenEfmLink24HrRxErroredFragmentsAct   NOTIFICATION-TYPE
    OBJECTS         {
                    adTrapInformSeqNum,
                    sysName,
                    adGenSlotInfoIndex,
                    adGenPortTrapIdentifier,
                    ifIndex
                    }
    STATUS          current
    DESCRIPTION
                    "EFM Link Rx Errored Fragments 24 Hour Threshold Crossed"
    --#TYPE         "Status - Alarm"
    --#SUMMARY      "EFM Link Rx Errored Fragments 24 Hour Threshold Crossed"
    --#SUMMARY      "detected at shelf: %s, slot: %d, interface %d"
    --#ARGUMENTS    {1,2,4}
    --#SEVERITY     "MAJOR"
    --#GENERIC      6
    --#CATEGORY     "Alarm Events"
    --#SOURCE_ID    "A"
    --#TIMEINDEX    0
    ::= {adGenEfmAlarms 34}

adGenEfmLink24HrRxSmallFragmentsAct   NOTIFICATION-TYPE
    OBJECTS         {
                    adTrapInformSeqNum,
                    sysName,
                    adGenSlotInfoIndex,
                    adGenPortTrapIdentifier,
                    ifIndex
                    }
    STATUS          current
    DESCRIPTION
                    "EFM Link Rx Small Fragments 24 Hour Threshold Crossed"
    --#TYPE         "Status - Alarm"
    --#SUMMARY      "EFM Link Rx Small Fragments 24 Hour Threshold Crossed"
    --#SUMMARY      "detected at shelf: %s, slot: %d, interface %d"
    --#ARGUMENTS    {1,2,4}
    --#SEVERITY     "MAJOR"
    --#GENERIC      6
    --#CATEGORY     "Alarm Events"
    --#SOURCE_ID    "A"
    --#TIMEINDEX    0
    ::= {adGenEfmAlarms 35}

adGenEfmLink24HrRxLargeFragmentsAct   NOTIFICATION-TYPE
    OBJECTS         {
                    adTrapInformSeqNum,
                    sysName,
                    adGenSlotInfoIndex,
                    adGenPortTrapIdentifier,
                    ifIndex
                    }
    STATUS          current
    DESCRIPTION
                    "EFM Link Rx Large Fragments 24 Hour Threshold Crossed"
    --#TYPE         "Status - Alarm"
    --#SUMMARY      "EFM Link Rx Large Fragments 24 Hour Threshold Crossed"
    --#SUMMARY      "detected at shelf: %s, slot: %d, interface %d"
    --#ARGUMENTS    {1,2,4}
    --#SEVERITY     "MAJOR"
    --#GENERIC      6
    --#CATEGORY     "Alarm Events"
    --#SOURCE_ID    "A"
    --#TIMEINDEX    0
    ::= {adGenEfmAlarms 36}

adGenEfmLink24HrRxDiscardedFragmentsAct   NOTIFICATION-TYPE
    OBJECTS         {
                    adTrapInformSeqNum,
                    sysName,
                    adGenSlotInfoIndex,
                    adGenPortTrapIdentifier,
                    ifIndex
                    }
    STATUS          current
    DESCRIPTION
                    "EFM Link Rx Discarded Fragments 24 Hour Threshold Crossed"
    --#TYPE         "Status - Alarm"
    --#SUMMARY      "EFM Link Rx Discarded Fragments 24 Hour Threshold Crossed"
    --#SUMMARY      "detected at shelf: %s, slot: %d, interface %d"
    --#ARGUMENTS    {1,2,4}
    --#SEVERITY     "MAJOR"
    --#GENERIC      6
    --#CATEGORY     "Alarm Events"
    --#SOURCE_ID    "A"
    --#TIMEINDEX    0
    ::= {adGenEfmAlarms 37}

adGenEfmLink24HrRxFcsErrorsAct   NOTIFICATION-TYPE
    OBJECTS         {
                    adTrapInformSeqNum,
                    sysName,
                    adGenSlotInfoIndex,
                    adGenPortTrapIdentifier,
                    ifIndex
                    }
    STATUS          current
    DESCRIPTION
                    "EFM Link Rx FCS Errors 24 Hour Threshold Crossed"
    --#TYPE         "Status - Alarm"
    --#SUMMARY      "EFM Link Rx FCS Errors 24 Hour Threshold Crossed"
    --#SUMMARY      "detected at shelf: %s, slot: %d, interface %d"
    --#ARGUMENTS    {1,2,4}
    --#SEVERITY     "MAJOR"
    --#GENERIC      6
    --#CATEGORY     "Alarm Events"
    --#SOURCE_ID    "A"
    --#TIMEINDEX    0
    ::= {adGenEfmAlarms 38}

adGenEfmLink24HrRxCodingErrorsAct   NOTIFICATION-TYPE
    OBJECTS         {
                    adTrapInformSeqNum,
                    sysName,
                    adGenSlotInfoIndex,
                    adGenPortTrapIdentifier,
                    ifIndex
                    }
    STATUS          current
    DESCRIPTION
                    "EFM Link Rx Coding Errors 24 Hour Threshold Crossed"
    --#TYPE         "Status - Alarm"
    --#SUMMARY      "EFM Link Rx Coding Errors 24 Hour Threshold Crossed"
    --#SUMMARY      "detected at shelf: %s, slot: %d, interface %d"
    --#ARGUMENTS    {1,2,4}
    --#SEVERITY     "MAJOR"
    --#GENERIC      6
    --#CATEGORY     "Alarm Events"
    --#SOURCE_ID    "A"
    --#TIMEINDEX    0
    ::= {adGenEfmAlarms 39}

-- ******************************************************************************************

END

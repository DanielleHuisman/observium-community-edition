ADTRAN-GEMINAX-MIB
-- TITLE:     The ADTRAN GEMINAX MIB
-- PRODUCT:   Multiple
-- VERSION:   0.1
-- DATE:      2010/06/04

-- This MIB defines the object identifiers (OIDs) for the Geminax Max ADSL DSP recovery feature.

-- HISTORY:
   -- Date       By  Descripition                                                Rev
   -- 2010/06/04 jeo First edition                                               (0.1). STATUS: PRELIMINARY

--*********************************************************************************************************
DEFINITIONS ::= BEGIN

    IMPORTS
	MODULE-IDENTITY,
    	OBJECT-TYPE
          	FROM SNMPv2-SMI
    	OBJECT-GROUP
        	FROM SNMPv2-CONF
        adGenSlotInfoIndex
            FROM ADTRAN-GENSLOT-MIB
    	adGenGeminax,
    	adGenGeminaxID
        	FROM ADTRAN-SHARED-XDSL-MIB
     ;

--*********************************************************************************************************
adGenGeminaxMIB MODULE-IDENTITY
       LAST-UPDATED "201006040000Z"
       ORGANIZATION "ADTRAN, Inc."
       CONTACT-INFO
         "Web: http://www.adtran.com
          E-mail: support@adtran.com"
       DESCRIPTION
            "This is the MIB module that describes
             Geminax recovery option settings"
       ::= { adGenGeminaxID 1 }

-- OBJECT IDENTIFIERS
   adGenGeminaxMax             OBJECT IDENTIFIER ::= { adGenGeminax 1 }

-- *************************************************************************
-- test
-- ************************************************************************
         adGenGeminaxDiagTable    OBJECT-TYPE
             SYNTAX          SEQUENCE OF AdGenGeminaxDiagEntry
             MAX-ACCESS      not-accessible
             STATUS          current
             DESCRIPTION
                "This table contains information on the Lantiq (Infineon)
                 GeminaxMax DSP. Each entry reflects a required
		 parameter or action required to perform either the SELT
		 or DELT diagnostic test. "
         ::= { adGenGeminaxMax 1 }


         adGenGeminaxDiagEntry   OBJECT-TYPE
             SYNTAX          AdGenGeminaxDiagEntry
             MAX-ACCESS      not-accessible
             STATUS          current
             DESCRIPTION     "This table contains configuration parameters for the GeminaxMax DSP.
                              The entries are used to configure the recovery option settings."
             INDEX           { adGenSlotInfoIndex }
         ::= { adGenGeminaxDiagTable 1 }

         AdGenGeminaxDiagEntry ::=
             SEQUENCE {
               adGenGeminaxErrorClassECF      INTEGER,
               adGenGeminaxErrorClassA        INTEGER,
               adGenGeminaxErrorClassB        INTEGER,
               adGenGeminaxErrorClassC        INTEGER,
               adGenGeminaxErrorClassD        INTEGER,
               adGenGeminaxErrorClassE        INTEGER
             }


         adGenGeminaxErrorClassECF OBJECT-TYPE
             SYNTAX      INTEGER {
			disabled(1),
			logOnly(2),
			softReset(3),
			hardReset(4)
	     }
             MAX-ACCESS  read-write
             STATUS      current
             DESCRIPTION
                 "Sets the action to be taken when a Class ECF error occurs. The following settings are allowed:
			disabled(1) - do nothing,
			logOnly(2) - log the event,
			softReset(3) - trigger a soft reset,
			hardReset(4) - trigger a hard reset"
         ::= { adGenGeminaxDiagEntry 1 }

        adGenGeminaxErrorClassA OBJECT-TYPE
             SYNTAX      INTEGER {
			disabled(1),
			logOnly(2),
			softReset(3),
			hardReset(4)
	     }
             MAX-ACCESS  read-write
             STATUS      current
             DESCRIPTION
                 "Sets the action to be taken when a Class A error occurs. The following settings are allowed:
			disabled(1) - do nothing,
			logOnly(2) - log the event,
			softReset(3) - trigger a soft reset,
			hardReset(4) - trigger a hard reset"
         ::= { adGenGeminaxDiagEntry 2 }

        adGenGeminaxErrorClassB OBJECT-TYPE
             SYNTAX      INTEGER {
			disabled(1),
			logOnly(2),
			softReset(3),
			hardReset(4)
	     }
             MAX-ACCESS  read-write
             STATUS      current
             DESCRIPTION
                 "Sets the action to be taken when a Class B error occurs. The following settings are allowed:
			disabled(1) - do nothing,
			logOnly(2) - log the event,
			softReset(3) - trigger a soft reset,
			hardReset(4) - trigger a hard reset"
         ::= { adGenGeminaxDiagEntry 3 }

        adGenGeminaxErrorClassC OBJECT-TYPE
             SYNTAX      INTEGER {
			disabled(1),
			logOnly(2),
			softReset(3),
			hardReset(4)
	     }
             MAX-ACCESS  read-write
             STATUS      current
             DESCRIPTION
                 "Sets the action to be taken when a Class C error occurs. The following settings are allowed:
			disabled(1) - do nothing,
			logOnly(2) - log the event,
			softReset(3) - trigger a soft reset,
			hardReset(4) - trigger a hard reset"
         ::= { adGenGeminaxDiagEntry 4 }

        adGenGeminaxErrorClassD OBJECT-TYPE
             SYNTAX      INTEGER {
			disabled(1),
			logOnly(2),
			softReset(3),
			hardReset(4)
	     }
             MAX-ACCESS  read-write
             STATUS      current
             DESCRIPTION
                 "Sets the action to be taken when a Class D error occurs. The following settings are allowed:
			disabled(1) - do nothing,
			logOnly(2) - log the event,
			softReset(3) - trigger a soft reset,
			hardReset(4) - trigger a hard reset"
         ::= { adGenGeminaxDiagEntry 5 }

         adGenGeminaxErrorClassE OBJECT-TYPE
             SYNTAX      INTEGER {
			disabled(1),
			logOnly(2),
			softReset(3),
			hardReset(4)
	     }
             MAX-ACCESS  read-write
             STATUS      current
             DESCRIPTION
                 "Sets the action to be taken when a Class E error occurs. The following settings are allowed:
			disabled(1) - do nothing,
			logOnly(2) - log the event,
			softReset(3) - trigger a soft reset,
			hardReset(4) - trigger a hard reset"
         ::= { adGenGeminaxDiagEntry 6 }



END

ADTRAN-GEN-ETH-IFC-MIB

-- TITLE:     The ADTRAN Generic Ethernet MIB
-- PRODUCT:   ADTRAN products featuring Ethernet ports
-- VERSION:   1.1
-- DATE:      04/23/2010
-- AUTHOR:    Bradley Collins
-- STATUS:    PRELIMINARY

-- This MIB contains information for configuring ethernet ports, including
-- PMs, Thresholds, Threshold crossing alarms, and speed/auto-negotiation

-- HISTORY:
-- 2009/02/19 bjc - STATUS: PRELIMINARY
-- 2009/02/23 bjc - Added tables to keep track of the PMs (current and inverval)
--                in addition to the thresholds
-- 2009/03/09 rajesh perumal - Added the OID for setting the speed/auto-negotiation of the Gig-E port.
-- 2009/03/31 bjc - Changed MIB name, file name, and OID names to be more
--                   accurate and ensure consistency
--                - Changed description to reflect expanded scope
--                - Eliminated MIB groups/conformance
--                - Replaced Gauge32 with Unsigned32 for Threshold items
--                - Replaced adGenPortTrapIdentifier with ifDescr in the traps
--                - Added SUMMARY and ARGUMENTS fields to traps
--                - Removed unnecessary adGenGigEthRstAllCurrentIntervals and
--                       adGenGigEthRstAllIntervals
--                - Added to the threshold table entry descriptions to explain
--                       further how the thresholds work
-- 2009/04/28 aed - Removed all references that specified gigabit ethernet.  This MIB should apply
--                       to any generic ethernet interface.  Added provisioning for duplex mode.
--                      Added status table for speed and duplex.  Added support for 64-bit PM counters.
-- 2009/05/12 aed - Added adGenEthIfcLinkUp and adGenEthIfcLinkDown traps
-- 2009/06/23 rp  - Added the 10-G enum for the OID adGenEthPortSpeed
-- 2009/08/26 aed - Changed adGenEthIfcLinkDown severity to MAJOR to match the firmware implementation.
-- 2009/09/03 jlb - Added EVC Advertisement provisioning and status.
-- 2010/04/23 gdo - Added adGenEthIfcLinkUpDownTrapEnable OID for enabling/disabling link down trap.
-- 2010/05/20 jlb - Added the following OIDs to adGenEth15MinThreshTable.
--                           adGenEth15MinThreshInUnicastPkts
--                           adGenEth15MinThreshInUnknownProtocols
--                           adGenEth15MinThreshInOctets
--                           adGenEth15MinThreshInPkts
--                           adGenEth15MinThreshInPkts64Octets
--                           adGenEth15MinThreshInPkts65to127Octets
--                           adGenEth15MinThreshInPkts128to255Octets
--                           adGenEth15MinThreshInPkts256to511Octets
--                           adGenEth15MinThreshInPkts512to1023Octets
--                           adGenEth15MinThreshInPkts1024toMaxOctets
--                           adGenEth15MinThreshOutErrors
--                           adGenEth15MinThreshOutDiscards
--                           adGenEth15MinThreshOutMulticastPkts
--                           adGenEth15MinThreshOutBroadcastPkts
--                           adGenEth15MinThreshOutUnicastPkts
--                           adGenEth15MinThreshOutOctets
--                           adGenEth15MinThreshOutPkts
--                           adGenEth15MinThreshES
--                           adGenEth15MinThreshLOSS
--                           adGenEth15MinThreshSEFS
--                           adGenEth15MinThreshSES
--                           adGenEth15MinThreshUAS
--                - Added the following threshold crossing alarms.
--                                       adGenEthSet15MinInUnicastPkts
--                                       adGenEthSet15MinInUnknownProtocols
--                                       adGenEthSet15MinInOctets
--                                       adGenEthSet15MinInPkts
--                                       adGenEthSet15MinInPkts64Octets
--                                       adGenEthSet15MinInPkts65to127Octets
--                                       adGenEthSet15MinInPkts128to255Octets
--                                       adGenEthSet15MinInPkts256to511Octets
--                                       adGenEthSet15MinInPkts512to1023Octets
--                                       adGenEthSet15MinInPkts1024toMaxOctets
--                                       adGenEthSet15MinOutErrors
--                                       adGenEthSet15MinOutDiscards
--                                       adGenEthSet15MinOutMulticastPkts
--                                       adGenEthSet15MinOutBroadcastPkts
--                                       adGenEthSet15MinOutUnicastPkts
--                                       adGenEthSet15MinOutOctets
--                                       adGenEthSet15MinOutPkts
--                                       adGenEthSet15MinES
--                                       adGenEthSet15MinLOSS
--                                       adGenEthSet15MinSEFS
--                                       adGenEthSet15MinSES
--                                       adGenEthSet15MinUAS
-- 2010/05/25 jlb - Corrected the name of adGenEthSet15MinInPkts1024toMaxOctets.  SMIC compiles.
-- 2010/08/30 Andria Dyess  Added autonegotiation status.  Added support for the
--                          rolling counters that are not supported in the IF-MIB
--                          and 5-minute averages.
-- 2010/09/24 bly - Changed adGenEth15MinThreshInOctets and adGenEth15MinThreshOutOctets
--                  from Unsigned32 to Unsigned64TC.
-- 2010/10/29 tgc - Added 6 provisioning variables to adGenEthProvTable for fixed speed and fixed
--                - duplex as well as auto-negotiation and advertisement for both copper and fiber.
--                - The 2 old speed and duplex variables are being deprecated. Added 4 status variables
--                - to adGenEthStatusTable: adGenEthCurrentAutoNegStatus, adGenEthCurrentInterfaceType,
--                - adGenEthInterfaceCuOrFiber, and adGenEthInterfaceFixedOrPluggable.
--          **** DO NOT ADD REVISION COMMENTS HERE ****
--
-- ******************************************************************************************
DEFINITIONS ::= BEGIN

IMPORTS
   MODULE-IDENTITY,
   OBJECT-TYPE,
   NOTIFICATION-TYPE,
   Unsigned32,
   Integer32,
   Gauge32,
   Counter32,
   Counter64
      FROM SNMPv2-SMI
   sysName
      FROM SNMPv2-MIB
   ifIndex,
   ifDescr,
   InterfaceIndex
      FROM IF-MIB
   adTrapInformSeqNum
      FROM ADTRAN-GENTRAPINFORM-MIB
   adGenSlotInfoIndex
      FROM ADTRAN-GENSLOT-MIB
   adGenEthIfc,
   adGenEthIfcID
      FROM ADTRAN-SHARED-CND-SYSTEM-MIB
   GenSystemInterfaceType
      FROM ADTRAN-SHARED-CND-SYSTEM-TC-MIB
   Unsigned64TC
      FROM APPLICATION-MIB
   TruthValue,
   DisplayString
      FROM SNMPv2-TC     -- [RFC2579]
   adTAeSCUTrapAlarmLevel
      FROM ADTRAN-TAeSCUEXT1-MIB
   ;

adGenEthMIB MODULE-IDENTITY
   LAST-UPDATED "202007210000Z"
   ORGANIZATION "Adtran, Inc."
   CONTACT-INFO
     "CND Tech Support
         Postal: ADTRAN, Inc.
                 901 Explorer Blvd.
                 Huntsville, AL  35806
                 Tel: +1 800 726-8663
                 Fax: +1 256 963 6217
                 E-mail: support@adtran.com"

   DESCRIPTION
      "This MIB contains information for configuring ethernet ports."

   REVISION "202007210000Z"
   DESCRIPTION "Added adGenEthPortBreakoutModeStatus."

   REVISION "202003260000Z"
   DESCRIPTION "Added adGenEthAlarmSlotIfcLinkDownSeverityLevel and adGenEthAlarmSlotLinkDownSeverityLevel."

   REVISION "201909030000Z"
   DESCRIPTION "Added adGenEthForwardErrorCorrection."

   REVISION "201904230000Z"
   DESCRIPTION "Added adGenEthPortBreakoutMode and adGenEthPortBreakoutModesSupported, update enum for adGenEthPortSpeed
                and adGenEthPortFixedSpeed."

   REVISION "201605260000Z"
   DESCRIPTION "Added adGenEthSpeedScanAlarm, adGenEthSpeedScanAlarmEnable, and adGenEthSpeedScanAlarmSeverityLevel"

   REVISION "201603070000Z"
   DESCRIPTION   "Added fixedSpeedScan(7) enumeration in adGenEthPortFixedSpeed"

   REVISION "201310250000Z"
   DESCRIPTION   "Added comments for Y-Cable Misconfiguation alarm."

   REVISION "201306140000Z"
   DESCRIPTION
          "Added adGenEthPerformanceCountersHCTable."

   REVISION "201303220000Z"
   DESCRIPTION
          "Moved AvgBitsPerSec and AvgPktsPerSec OIDs to the HC tables."

   REVISION "201302080000Z"
   DESCRIPTION
          "Added OIDS for PM with the following content:
                InAvgBitsPerSec, InAvgPktsPerSec,
                OutAvgBitsPerSec, OutAvgBitsPerSec,
                InPeakUtilization, InAvgUtilization,
                OutPeakUtilization, OutAvgUtilization
           to the following tables:
                adGenEth15MinCurrentTable
                adGenEth15MinIntervalTable
                adGenEth24HrCurrentTable
                adGenEth24HrIntervalTable

           Added these OIDs to adGenEthPerformanceCountersTable
                adGenEthInPeakUtilization, adGenEthInAvgUtilization
                adGenEthOutPeakUtilization, adGenEthOutAvgUtilization
                adGenEthDepthPacketsQueueN, for N = 0 through 7"

   REVISION "201209110000Z"
   DESCRIPTION "added adGenEthLastError"

   REVISION "201203140000Z"
   DESCRIPTION "added adGenEthAlarmStatus"

   REVISION "201202210000Z"
   DESCRIPTION "added adGenEthPortYCableCfgAlarmClear,
                      adGenEthPortYCableCfgAlarmSet"

   REVISION "201202130000Z"
   DESCRIPTION "added adGenEthIfcLOSSet,
                adGenEthIfcLOSClear,
                adGenEthIfcLOBSSet,
                adGenEthIfcLOBSClear,
                adGenEthIfcHIBERSet,
                adGenEthIfcHIBERClear,
                adGenEthIfcLocalFaultSet,
                adGenEthIfcLocalFaultClear,
                adGenEthIfcRemoteFaultSet,
                adGenEthIfcRemoteFaultClear"

   REVISION "201202020000Z"
   DESCRIPTION "added adGenEthPortYCableEnable"

   REVISION "201201110000Z"
   DESCRIPTION "Added adGenEth15MinCurrentHCOutLcv,
                           adGenEth15MinCurrentHCInLcv,
                                                         adGenEth15MinIntervalHCOutLcv,
                                                         adGenEth15MinIntervalHCInLcv,
                                                         adGenEth15MinIntervalHCValidData,
                                                         adGenEth24HrCurrentHCOutLcv,
                                                         adGenEth24HrCurrentHCInLcv,
                                                         adGenEth24HrIntervalHCOutLcv,
                                                         adGenEth24HrIntervalHCInLcv,
                                                         adGenEth24HrIntervalHCValidData,
                                                         adGenEth15MinThreshOutLcv,
                                                         adGenEth15MinThreshInLcv,
                                                         adGenEth24HrThreshOutLcv,
                                                         adGenEth24HrThreshInLcv,
                                                         adGenEthSet15MinOutLcvAlm,
                                                         adGenEthSet15MinInLcvAlm,
                                                         adGenEthSet24HrOutLcvAlm,
                                                         adGenEthSet24HrInLcvAlm"

   REVISION "201111281640Z"
   DESCRIPTION "Add OIDs to return the number of valid 15-minute and 24-hour performance intervals."

   REVISION "201110101346Z"
   DESCRIPTION "PJV - Add Missing PM OIDS"

   REVISION "201109150000Z"
   DESCRIPTION "Add 24-Hour egress queue counters. Added OIDS: 17-24 under adGenEth24HrCurrentEntry,
    9-16 under adGenEth24HrCurrentHCEntry, 18-25 under adGenEth24HrIntervalEntry,
    10-17 under adGenEth24HrIntervalHCEntry "

   REVISION "201104271959Z"
   DESCRIPTION "Add per-queue performance statistics and counters."

   REVISION "201004230000Z"
   DESCRIPTION "gdo - Added the adGenEthIfcLinkUpDownTrapEnable object."

   REVISION "200902190000Z"
   DESCRIPTION "Created"
::= { adGenEthIfcID 1 }


--==================================================================================================================

adGenEthIfcEvents                    OBJECT IDENTIFIER ::= {adGenEthIfc 0}
adGenEthIfcProvisioning              OBJECT IDENTIFIER ::= {adGenEthIfc 1}
adGenEthIfcStatus                    OBJECT IDENTIFIER ::= {adGenEthIfc 2}
adGenEthIfcPerformance               OBJECT IDENTIFIER ::= {adGenEthIfc 3}

--==================================================================================================================
-- Provisioning

   adGenEthProvTable OBJECT-TYPE
      SYNTAX  SEQUENCE OF AdGenEthProvEntry
      MAX-ACCESS  not-accessible
      STATUS  current
      DESCRIPTION
         "The Generic Ethernet provisioning table."
      ::= { adGenEthIfcProvisioning 1 }

   adGenEthProvEntry OBJECT-TYPE
      SYNTAX  AdGenEthProvEntry
      MAX-ACCESS  not-accessible
      STATUS  current
      DESCRIPTION
         "An entry in the Generic Ethernet provisioning table."
      INDEX   { ifIndex }
      ::= { adGenEthProvTable 1 }

   AdGenEthProvEntry  ::=
      SEQUENCE {
         adGenEthPortSpeed                   INTEGER,
         adGenEthPortDuplex                  INTEGER,
         adGenEthLinkUpDownTrapEnable        INTEGER,
         adGenEthPortFixedSpeed              INTEGER,
         adGenEthPortFixedDuplex             INTEGER,
         adGenEthAutoNegotiateCu             TruthValue,
         adGenEthAdvertisedSpeedAndDuplexCu  BITS,
         adGenEthAutoNegotiateFiber          TruthValue,
         adGenEthAdvertisedDuplexFiber       BITS,
         adGenEthPortYCableEnable            TruthValue,
         adGenEthSpeedScanAlarmEnable        TruthValue,
         adGenEthSpeedScanAlarmSeverityLevel INTEGER,
         adGenEthPortBreakoutMode            INTEGER,
         adGenEthPortBreakoutModesSupported  BITS,
         adGenEthForwardErrorCorrection      TruthValue,
         adGenEthPortBreakoutModeStatus      INTEGER,
      }


   adGenEthPortSpeed OBJECT-TYPE
          SYNTAX INTEGER {
                                auto(1),   -- shouldn't be used
                                speed10Mbps(2),
                                speed100Mbps(3),
                                speed1000Mbps(4),
                                speed2500Mbps(5),
                                speed10Gbps(6),
                                speedScan(7),
                                speed40Gbps(8),
                                speed100Gbps(9)
                         }
          MAX-ACCESS read-write
          STATUS deprecated
          DESCRIPTION
            "Provisions the speed for the selected ethernet port.
            Previously auto(1) was used to enable auto-negotiation,
            but that usage became outdated; therefore this
            OID's status has changed to deprecated. See
            adGenEthPortFixedSpeed,  adGenEthPortFixedDuplex,
            adGenEthAutoNegotiateCu and adGenEthAutoNegotiateFiber ."
    ::= { adGenEthProvEntry 1 }

   adGenEthPortDuplex OBJECT-TYPE
          SYNTAX INTEGER {
                                auto(1), -- shouldn't be used
                                halfDuplex(2),
                                fullDuplex(3)
                         }
          MAX-ACCESS read-write
          STATUS     deprecated
          DESCRIPTION
            "Provisions the duplex for the selected ethernet port.
            The use of auto(1) to enable auto-negotiation became outdated;
            therefore this OID's status has changed to deprecated. See
            adGenEthPortFixedSpeed,  adGenEthPortFixedDuplex,
            adGenEthAutoNegotiateCu and adGenEthAutoNegotiateFiber."
    ::= { adGenEthProvEntry 2 }

   adGenEthLinkUpDownTrapEnable  OBJECT-TYPE
          SYNTAX  INTEGER {
                                enabled(1),
                                disabled(2)
                          }
          MAX-ACCESS  read-write
          STATUS      current
          DESCRIPTION
            "Indicates whether adGenEthIfcLinkUp/LinkDown traps should
            be generated for this interface."
    ::= { adGenEthProvEntry 3 }

   adGenEthPortFixedSpeed OBJECT-TYPE
          SYNTAX INTEGER {
                                fixedSpeed10Mbps(2),
                                fixedSpeed100Mbps(3),
                                fixedSpeed1000Mbps(4),
                                fixedSpeed2500Mbps(5),
                                fixedSpeed10Gbps(6),
                                fixedSpeedScan(7),
                                fixedSpeed40Gbps(8),
                                fixedSpeed100Gbps(9)
                         }
          MAX-ACCESS read-write
          STATUS current
          DESCRIPTION
            "Provisions the speed for the selected ethernet port
             fixedSpeedScan(7) activates an Adtran-specific speed-scan algorithm to
             detect an appropriate fixed speed.
            (a) in all cases for Fiber and
            (b) for Copper when the autonegotiation OID,
                adGenEthAutoNegotiateCu, is set to false ."
    ::= { adGenEthProvEntry 4 }

   adGenEthPortFixedDuplex OBJECT-TYPE
          SYNTAX INTEGER {
                                fixedHalfDuplex(2),
                                fixedFullDuplex(3)
                         }
          MAX-ACCESS read-write
          STATUS current
          DESCRIPTION
            "Provisions the duplex for the selected ethernet port when the appropriate
            autonegotiation OID, adGenEthAutoNegotiateCu or adGenEthAutoNegotiateFiber,
            is set to false."
    ::= { adGenEthProvEntry 5 }

   adGenEthAutoNegotiateCu  OBJECT-TYPE
          SYNTAX TruthValue
          MAX-ACCESS read-write
          STATUS current
          DESCRIPTION
            "Enable or disable auto-negotiation. TruthValue of 1 is
            true/enable which implies that capabilities are advertised
            as selected (see adGenEthAdvertisedSpeedAndDuplexCu;
            note that adGenEthPortFixedSpeed and
            adGenEthPortFixedDuplex are ignored when these
            variables are used). TruthValue of 2 is false/disable which
            implies that speed and duplex are forced (so
            adGenEthPortFixedSpeed and adGenEthPortFixedDuplex are used)."
    ::= { adGenEthProvEntry 6 }

-- left room for { adGenEthProvEntry 7 }

   adGenEthAdvertisedSpeedAndDuplexCu OBJECT-TYPE
          SYNTAX BITS {
                                cuSpeed1000FullDuplex (0),
                                cuSpeed100FullDuplex (1),
                                cuSpeed100HalfDuplex (2),
                                cuSpeed10FullDuplex (3),
                                cuSpeed10HalfDuplex (4)
                      }
          MAX-ACCESS read-write
          STATUS current
          DESCRIPTION
            "If adGenEthAutoNegotiateCu = 2 (false), then speed and duplex are forced. If
            adGenEthAutoNegotiateCu = 1 (true), then auto-negotiation is enabled and
            capabilities are advertised as selected here. Set bits to 1 to advertise each capability
            and clear bits to 0 to NOT advertise each capability as appropriate."
    ::= { adGenEthProvEntry 8 }

   adGenEthAutoNegotiateFiber  OBJECT-TYPE
          SYNTAX TruthValue
          MAX-ACCESS read-write
          STATUS current
          DESCRIPTION
            "Enable or disable auto-negotiation. TruthValue of 1 is true/enable
            which implies that duplex capabilities are advertised as selected
            (see adGenEthAdvertisedDuplexFiber; note that
            adGenEthPortFixedDuplex is ignored when these variables are used).
            TruthValue of 2 is false/disable which implies that duplex is forced
            (so adGenEthPortFixedDuplex is used). In both cases adGenEthPortFixedSpeed
            is used to provision speed."
    ::= { adGenEthProvEntry 9 }

 -- left room for { adGenEthProvEntry 10 }

   adGenEthAdvertisedDuplexFiber  OBJECT-TYPE
          SYNTAX BITS {
                                fiberFullDuplex (0),
                                fiberHalfDuplex (1)
                      }
          MAX-ACCESS read-write
          STATUS current
          DESCRIPTION
            "If adGenEthAutoNegotiateFiber = 2 (false), then duplex is forced . If
            adGenEthAutoNegotiateFiber  = 1 (true), then auto-negotiation is enabled and
            capabilities are advertised as selected here. Set bits to 1 to advertise each capability
            and clear bits to 0 to NOT advertise each capability as appropriate."
    ::= { adGenEthProvEntry 11 }

   adGenEthPortYCableEnable  OBJECT-TYPE
          SYNTAX TruthValue
          MAX-ACCESS read-write
          STATUS current
          DESCRIPTION
            "Enable or disable Y-Cable.

            TruthValue of 1 is true/enable which implies that a Y-Cable is being
            used for this port.

            TruthValue of 2 is false/disable which implies that is NOT being
            used for this port."
    ::= { adGenEthProvEntry 12 }

   adGenEthSpeedScanAlarmEnable  OBJECT-TYPE
          SYNTAX TruthValue
          MAX-ACCESS read-write
          STATUS current
          DESCRIPTION
            "Enable or disable Speed Scan alarm.

            TruthValue of 1 is true/enable which implies that the Speed Scan alarm is enabled for this port.

            TruthValue of 2 is false/disable which implies that the Speed Scan alarm is disabled for this port."
          DEFVAL { true }
    ::= { adGenEthProvEntry 13 }

   adGenEthSpeedScanAlarmSeverityLevel          OBJECT-TYPE
          SYNTAX INTEGER {
                                info(2),
                                alert(3),
                                minor(4),
                                major(5),
                                critical(6)
                         }
          MAX-ACCESS                read-write
          STATUS                    current
          DESCRIPTION
            "Provision the severity level of Speed Scan alarm."
          DEFVAL { info }
    ::= {adGenEthProvEntry  14 }

   adGenEthPortBreakoutMode          OBJECT-TYPE
          SYNTAX INTEGER {
                                disable(1),
                                fourBy10Gig(2)
                         }
          MAX-ACCESS                read-write
          STATUS                    current
          DESCRIPTION
            "Provision the port breakout mode (if supported) by a given port.
             For 40Gbps interfaces which support breakout operation,
             1x40Gbps mode is implied by the disable(1) option. The results of
             a set operation can be retrieved from adGenEthPortBreakoutModeStatus.
             "
             DEFVAL { disable }
    ::= {adGenEthProvEntry  15 }

   adGenEthPortBreakoutModesSupported          OBJECT-TYPE
          SYNTAX BITS {
                                notSupported(0),
                                oneBy40Gig(1),
                                fourBy10Gig(2)
                      }

          MAX-ACCESS                read-only
          STATUS                    current
          DESCRIPTION
            "Indicates whether or not this port supports breakout operation where the
             lanes of the port are split into multiple logical ports. If the port
             doesn't support breakout mode then notSupported(0) should be set. In
             all other cases only the relevant bits should be set to indicate the
             available options, which are set using adGenEthPortBreakoutMode."

    ::= {adGenEthProvEntry  16 }

   adGenEthForwardErrorCorrection  OBJECT-TYPE
          SYNTAX  TruthValue
          MAX-ACCESS  read-write
          STATUS      current
          DESCRIPTION
            "Enable or disable FEC on this interface."
    ::= { adGenEthProvEntry 17 }

   adGenEthPortBreakoutModeStatus          OBJECT-TYPE
          SYNTAX INTEGER {
                                 success(0),
                                 breakoutNotSupported(-1),
                                 modeNotSupported(-2),
                                 portNotDisabled(-3),
                                 invalidPort(-4),
                                 internalError(-5),
                                 notDone(-6)
                         }
          MAX-ACCESS                read-only
          STATUS                    current
          DESCRIPTION
            "Reports the status of the last set operation to adGenEthPortBreakoutMode.
             The notDone status is returned while the operation is still in progress.
             Every status except notDone implies the operation is complete."
         DEFVAL { success }
    ::= {adGenEthProvEntry  18 }


--==================================================================================================================
-- EVC Advertisement Provisioning

   adGenEthProvEVCAdvertisementTable OBJECT-TYPE
      SYNTAX  SEQUENCE OF AdGenEthProvEVCAdvertisementEntry
      MAX-ACCESS  not-accessible
      STATUS  current
      DESCRIPTION
         "The EVC Advertisement provisioning table."
      ::= { adGenEthIfcProvisioning 2 }

   adGenEthProvEVCAdvertisementEntry OBJECT-TYPE
      SYNTAX  AdGenEthProvEVCAdvertisementEntry
      MAX-ACCESS  not-accessible
      STATUS  current
      DESCRIPTION
         "An entry in the EVC Advertisement provisioning table."
      INDEX   { ifIndex }
      ::= { adGenEthProvEVCAdvertisementTable 1 }

   AdGenEthProvEVCAdvertisementEntry  ::=
      SEQUENCE {
         adGenEthProvEVCAdvertisementState              INTEGER
      }


   adGenEthProvEVCAdvertisementState OBJECT-TYPE
      SYNTAX  INTEGER {
                disabled(1),
                enabled(2)
              }
      MAX-ACCESS  read-write
      STATUS  current
      DESCRIPTION
         "Used to enable/disable EVC Advertisement"
      ::= { adGenEthProvEVCAdvertisementEntry 1 }

--==================================================================================================================
-- Slot Alarm Provisioning

   adGenEthAlarmSlotProvTable OBJECT-TYPE
      SYNTAX  SEQUENCE OF AdGenEthAlarmSlotProvEntry
      MAX-ACCESS  not-accessible
      STATUS  current
      DESCRIPTION
         "The Ethernet Alarm Slot provisioning table."
      ::= { adGenEthIfcProvisioning 3 }


   adGenEthAlarmSlotProvEntry OBJECT-TYPE
      SYNTAX  AdGenEthAlarmSlotProvEntry
      MAX-ACCESS  not-accessible
      STATUS  current
      DESCRIPTION
         "An entry in the Ethernet Alarm Slot provisioning table."
      INDEX   { adGenSlotInfoIndex }
      ::= { adGenEthAlarmSlotProvTable 1 }

   AdGenEthAlarmSlotProvEntry  ::=
      SEQUENCE {
         adGenEthAlarmSlotIfcLinkDownSeverityLevel   INTEGER,
         adGenEthAlarmSlotLinkDownSeverityLevel      INTEGER
      }

   adGenEthAlarmSlotIfcLinkDownSeverityLevel          OBJECT-TYPE
          SYNTAX INTEGER {
                                info(2),
                                alert(3),
                                minor(4),
                                major(5),
                                critical(6)
                         }
          MAX-ACCESS                read-write
          STATUS                    current
          DESCRIPTION
            "Provision the severity level of Ifc Link Down alarm."
          DEFVAL { major }
    ::= {adGenEthAlarmSlotProvEntry  1 }

   adGenEthAlarmSlotLinkDownSeverityLevel          OBJECT-TYPE
          SYNTAX INTEGER {
                                info(2),
                                alert(3),
                                minor(4),
                                major(5),
                                critical(6)
                         }
          MAX-ACCESS                read-write
          STATUS                    current
          DESCRIPTION
            "Provision the severity level of RFC Link Down alarm."
          DEFVAL { major }
    ::= {adGenEthAlarmSlotProvEntry  2 }

--==================================================================================================================
-- Status

   adGenEthStatusTable OBJECT-TYPE
      SYNTAX  SEQUENCE OF AdGenEthStatusEntry
      MAX-ACCESS  not-accessible
      STATUS  current
      DESCRIPTION
         "The Ethernet status table."
      ::= { adGenEthIfcStatus 1 }

   adGenEthStatusEntry OBJECT-TYPE
      SYNTAX  AdGenEthStatusEntry
      MAX-ACCESS  not-accessible
      STATUS  current
      DESCRIPTION
         "An entry in the Ethernet status table."
      INDEX   { ifIndex }
      ::= { adGenEthStatusTable 1 }

   AdGenEthStatusEntry  ::=
      SEQUENCE {
         adGenEthCurrentSpeed               INTEGER,
         adGenEthCurrentDuplex              INTEGER,
         adGenEthCurrentAutoNeg             INTEGER,
         adGenEthCurrentAutoNegStatus       INTEGER,
         adGenEthCurrentInterfaceType       GenSystemInterfaceType,
         adGenEthInterfaceCuOrFiber         INTEGER,
         adGenEthInterfaceFixedOrPluggable  INTEGER,
         adGenEthValid15MinIntervals        INTEGER,
         adGenEthValid24HrIntervals         INTEGER,
         adGenEthAlarmStatus                BITS,
         adGenEthLastError                  DisplayString
      }

   adGenEthCurrentSpeed OBJECT-TYPE
      SYNTAX  INTEGER {
                unknown(1),
                speed10Mbps(2),
                speed100Mbps(3),
                speed1000Mbps(4),
                speed2500Mbps(5),
                speed10Gbps(6)
              }
      MAX-ACCESS  read-only
      STATUS  current
      DESCRIPTION
         "Returns the current speed for the selected ethernet port."
      ::= { adGenEthStatusEntry 1 }

   adGenEthCurrentDuplex OBJECT-TYPE
      SYNTAX  INTEGER {
                unknown(1),
                halfDuplex(2),
                fullDuplex(3)
              }
      MAX-ACCESS  read-only
      STATUS  current
      DESCRIPTION
         "Returns the current duplex mode for the selected ethernet port."
      ::= { adGenEthStatusEntry 2 }

   adGenEthCurrentAutoNeg       OBJECT-TYPE
      SYNTAX    INTEGER {
                  enable (1),
                  disable(2)
                }
       MAX-ACCESS                read-only
       STATUS                    current
       DESCRIPTION
           "Returns whether autonegotiation is currently enabled on the selected port."
       ::= { adGenEthStatusEntry 3 }

   adGenEthCurrentAutoNegStatus OBJECT-TYPE
      SYNTAX  INTEGER {
                notApplicable(1),
                incomplete(2),
                complete(3)
              }
      MAX-ACCESS  read-only
      STATUS  current
      DESCRIPTION
         "Returns the current auto-negotiation status for the selected ethernet port.
          notApplicable(1) - port provisioned to no auto-negotiation
          incomplete(2)    - port provisioned to auto-negotiation
                             but has not comleted auto-negotiation exchange with peer port.
          complete(3)      - port provisioned to auto-negotiation
                             and has completed auto-negotiation exchange with peer port."
      ::= { adGenEthStatusEntry 4 }

     adGenEthCurrentInterfaceType OBJECT-TYPE
      SYNTAX  GenSystemInterfaceType
      MAX-ACCESS  read-only
      STATUS  current
      DESCRIPTION
         "The initial purpose of this variable is to identify ethernet vs. gigabit ethernet
         interfaces. However it could be used to identify additional types later as
         GenSystemInterfaceType defines many types."
      ::= { adGenEthStatusEntry 5 }

   adGenEthInterfaceCuOrFiber OBJECT-TYPE
      SYNTAX  INTEGER {
                copper(1),
                fiber(2)
                }
      MAX-ACCESS  read-only
      STATUS  current
      DESCRIPTION
         "Returns the physical type, copper or fiber, of the ethernet interface."
      ::= { adGenEthStatusEntry  6}

   adGenEthInterfaceFixedOrPluggable OBJECT-TYPE
      SYNTAX  INTEGER {
                fixedPort(1),
                pluggablePort(2)
                }
      MAX-ACCESS  read-only
      STATUS  current
      DESCRIPTION
         "Returns the mechanical type, fixed or pluggable, of the ethernet
         interface/port. If pluggable, then see adGenPluggablePort.mi2."
      ::= { adGenEthStatusEntry  7}

   adGenEthValid15MinIntervals  OBJECT-TYPE
      SYNTAX            INTEGER (0..96)
      MAX-ACCESS        read-only
      STATUS            current
      DESCRIPTION
          "The number of valid 15-minute performance monitoring intervals for this interface.
           This value represents the maximum valid value of adGenEth15MinIntervalNumber in adGenEth15MinIntervalTable
           and the maximum valid value of adGenEth15MinIntervalHCNumber in adGenEth15MinIntervalHCTable."
      ::= { adGenEthStatusEntry 8 }

   adGenEthValid24HrIntervals  OBJECT-TYPE
      SYNTAX            INTEGER (0..7)
      MAX-ACCESS        read-only
      STATUS            current
      DESCRIPTION
          "The number of valid 24-hour performance monitoring intervals for this interface.
           This value represents the maximum valid value of adGenEth24HrIntervalNumber in adGenEth24HrIntervalTable
           and the maximum valid value of adGenEth24HrIntervalHCNumber in adGenEth24HrIntervalHCTable."
      ::= { adGenEthStatusEntry 9 }

   adGenEthAlarmStatus    OBJECT-TYPE
      SYNTAX BITS {
                   noAlarm(0),
                   lossOfSignal(1),
                   lossOfBlockSync(2),
                   highBERT(3),
                   localFault(4),
                   remoteFault(5)
                  }
      MAX-ACCESS read-only
      STATUS current
      DESCRIPTION
              "A bit-map representing the current ETH alarm status of the specified port.
              The bit positions are:
              0 - no alarm
              1 - LOS
              2 - LOBS
              3 - HIBER
              4 - LCLFLT
              5 - REMFLT"
      ::= { adGenEthStatusEntry 10 }

   adGenEthLastError    OBJECT-TYPE
      SYNTAX     DisplayString
      MAX-ACCESS read-only
      STATUS     current
      DESCRIPTION
              "Displays details of the latest error experienced by this particular entry."
      ::= { adGenEthStatusEntry 11 }

--==================================================================================================================
-- EVC Advertisement Status

   adGenEthStatEVCAdvertisementTable OBJECT-TYPE
      SYNTAX  SEQUENCE OF AdGenEthStatEVCAdvertisementEntry
      MAX-ACCESS  not-accessible
      STATUS  current
      DESCRIPTION
         "The EVC Advertisement status table."
      ::= { adGenEthIfcStatus 2 }

   adGenEthStatEVCAdvertisementEntry OBJECT-TYPE
      SYNTAX  AdGenEthStatEVCAdvertisementEntry
      MAX-ACCESS  not-accessible
      STATUS  current
      DESCRIPTION
         "An entry in the EVC Advertisement status table."
      INDEX   { ifIndex, adGenEthStatEVCAdvertisementVLANID }
      ::= { adGenEthStatEVCAdvertisementTable 1 }

   AdGenEthStatEVCAdvertisementEntry  ::=
      SEQUENCE {
                 adGenEthStatEVCAdvertisementVLANID                     Unsigned32,
                 adGenEthStatEVCAdvertisementStatus                     INTEGER
      }

   adGenEthStatEVCAdvertisementVLANID OBJECT-TYPE
      SYNTAX  Unsigned32 (0..4095)
      MAX-ACCESS  not-accessible
      STATUS  current
      DESCRIPTION
         "VLAN ID that is being advertised."
      ::= { adGenEthStatEVCAdvertisementEntry 1 }

   adGenEthStatEVCAdvertisementStatus OBJECT-TYPE
      SYNTAX  INTEGER
                          {
                                localAdvertisedOnly(1),
                                peerAdvertisedOnly(2),
                                localAndPeerAdvertised(3)
                          }
      MAX-ACCESS  read-only
      STATUS  current
      DESCRIPTION
         "The status of the VLAN ID on the selected interface.  Status definitions are as
                  follows:

                  localAdvertisedOnly(1)        - Only the local interface is provisioned with the specified VLAN.
                                                                          Traffic is not allowed to flow over the specified VLAN via this interface.
                  peerAdvertisedOnly(2)         - Only the peer's interface is provisioned with the specified VLAN
                                                                          Traffic is not allowed to flow over the specified VLAN via this interface.
                  localAndPeerAdvertised(3) - Both the local and the peer's interface is provisioned with the specified VLAN.
                                                                          Traffic is allowed to flow over the specified VLAN via this interface.
                 "
      ::= { adGenEthStatEVCAdvertisementEntry 2 }


--==================================================================================================================
   adGenEthPerformanceScalars  OBJECT IDENTIFIER ::= { adGenEthIfcPerformance 1 }

      adGenEthRstCurrentIntervals OBJECT-TYPE
         SYNTAX  INTEGER {
            rstAllCurrentIntervals(1)
         }
         MAX-ACCESS  read-write
         STATUS  current
         DESCRIPTION
            "Reset all performance monitoring data in the current interval on all Ethernet ports."
          ::= { adGenEthPerformanceScalars 1 }

      adGenEthRstAll OBJECT-TYPE
         SYNTAX  INTEGER {
            rstAllIntervals(1)
         }
         MAX-ACCESS  read-write
         STATUS  current
         DESCRIPTION
            "Reset all performance monitoring data on all Ethernet ports."
         ::= { adGenEthPerformanceScalars 2 }

--==================================================================================================================

   adGenEth15MinCurrentTable OBJECT-TYPE
      SYNTAX  SEQUENCE OF AdGenEth15MinCurrentEntry
      MAX-ACCESS  not-accessible
      STATUS  current
      DESCRIPTION
         "The Generic Ethernet 15Min current table."
      ::= { adGenEthIfcPerformance 2 }

   adGenEth15MinCurrentEntry OBJECT-TYPE
      SYNTAX  AdGenEth15MinCurrentEntry
      MAX-ACCESS  not-accessible
      STATUS  current
      DESCRIPTION
         "An entry in the Generic Ethernet 15Min current table."
      INDEX   { ifIndex }
      ::= { adGenEth15MinCurrentTable 1 }

   AdGenEth15MinCurrentEntry  ::=
      SEQUENCE {
         adGenEth15MinCurrentOutOctets
            Gauge32,
         adGenEth15MinCurrentOutPkts
            Gauge32,
         adGenEth15MinCurrentInOctets
            Gauge32,
         adGenEth15MinCurrentInPkts
            Gauge32,
         adGenEth15MinCurrentInGoodOctets
            Gauge32,
         adGenEth15MinCurrentInGoodPkts
            Gauge32,
         adGenEth15MinCurrentInErrors
            Gauge32,
         adGenEth15MinCurrentInDiscards
            Gauge32,
         adGenEth15MinCurrentInGiants
            Gauge32,
         adGenEth15MinCurrentInRunts
            Gauge32,
         adGenEth15MinCurrentInMulticastPkts
            Gauge32,
         adGenEth15MinCurrentInBroadcastPkts
            Gauge32,
         adGenEth15MinCurrentInUnicastPkts
            Gauge32,
         adGenEth15MinCurrentOutMulticastPkts
            Gauge32,
         adGenEth15MinCurrentOutBroadcastPkts
            Gauge32,
         adGenEth15MinCurrentOutUnicastPkts
            Gauge32,
         adGenEth15MinCurrentDroppedPktsQueue0
            Gauge32,
         adGenEth15MinCurrentDroppedPktsQueue1
            Gauge32,
         adGenEth15MinCurrentDroppedPktsQueue2
            Gauge32,
         adGenEth15MinCurrentDroppedPktsQueue3
            Gauge32,
         adGenEth15MinCurrentDroppedPktsQueue4
            Gauge32,
         adGenEth15MinCurrentDroppedPktsQueue5
            Gauge32,
         adGenEth15MinCurrentDroppedPktsQueue6
            Gauge32,
         adGenEth15MinCurrentDroppedPktsQueue7
            Gauge32,
         adGenEth15MinCurrentOutDiscards
            Gauge32,
         adGenEth15MinCurrentInCRCErrors
            Gauge32,
         adGenEth15MinCurrentInFrameErrors
            Gauge32,
         adGenEth15MinCurrentOutErrors
            Gauge32,

         adGenEth15MinCurrentInPeakUtilization
            Gauge32,
         adGenEth15MinCurrentInAvgUtilization
            Gauge32,
         adGenEth15MinCurrentOutPeakUtilization
            Gauge32,
         adGenEth15MinCurrentOutAvgUtilization
            Gauge32
       }

      adGenEth15MinCurrentOutOctets OBJECT-TYPE
         SYNTAX Gauge32
         MAX-ACCESS  read-only
         STATUS  current
         DESCRIPTION
            "The total number of octets transmitted on the interface
             during the current 15-minute interval, including framing characters."
         ::= { adGenEth15MinCurrentEntry 1 }

      adGenEth15MinCurrentOutPkts OBJECT-TYPE
         SYNTAX Gauge32
         MAX-ACCESS  read-only
         STATUS  current
         DESCRIPTION
            "The total number of packets transmitted on the interface
             during the current 15-minute interval."
         ::= { adGenEth15MinCurrentEntry 2 }

      adGenEth15MinCurrentInOctets OBJECT-TYPE
         SYNTAX Gauge32
         MAX-ACCESS  read-only
         STATUS  current
         DESCRIPTION
            "The total number of octets received on the interface
             during the current 15-minute interval, including framing characters."
         ::= { adGenEth15MinCurrentEntry 3 }

      adGenEth15MinCurrentInPkts OBJECT-TYPE
         SYNTAX Gauge32
         MAX-ACCESS  read-only
         STATUS  current
         DESCRIPTION
            "The total number of packets received on the interface
             during the current 15-minute interval."
         ::= { adGenEth15MinCurrentEntry 4 }

      adGenEth15MinCurrentInGoodOctets OBJECT-TYPE
         SYNTAX Gauge32
         MAX-ACCESS  read-only
         STATUS  current
         DESCRIPTION
            ""
         ::= { adGenEth15MinCurrentEntry 5 }

      adGenEth15MinCurrentInGoodPkts OBJECT-TYPE
         SYNTAX Gauge32
         MAX-ACCESS  read-only
         STATUS  current
         DESCRIPTION
            ""
         ::= { adGenEth15MinCurrentEntry 6 }

      adGenEth15MinCurrentInErrors OBJECT-TYPE
         SYNTAX Gauge32
         MAX-ACCESS  read-only
         STATUS  current
         DESCRIPTION
            "The number of inbound packets that contained errors
             during the current 15-minute interval."
         ::= { adGenEth15MinCurrentEntry 7 }

      adGenEth15MinCurrentInDiscards OBJECT-TYPE
         SYNTAX Gauge32
         MAX-ACCESS  read-only
         STATUS  current
         DESCRIPTION
            "The number of inbound packets which were chosen to be discarded
             during the current 15-minute interval even though no errors
             had been detected.  One reason for discarding such a packet
             could be congestion."
         ::= { adGenEth15MinCurrentEntry 8 }

      adGenEth15MinCurrentInGiants OBJECT-TYPE
         SYNTAX Gauge32
         MAX-ACCESS  read-only
         STATUS  current
         DESCRIPTION
            "The number of packets received during the current 15-minute
             interval which were larger than the maximum packet size."
         ::= { adGenEth15MinCurrentEntry 9 }

      adGenEth15MinCurrentInRunts OBJECT-TYPE
         SYNTAX Gauge32
         MAX-ACCESS  read-only
         STATUS  current
         DESCRIPTION
            "The number of packets received during the current 15-minute
             interval which were smaller than the minimum packet size."
         ::= { adGenEth15MinCurrentEntry 10 }

      adGenEth15MinCurrentInMulticastPkts OBJECT-TYPE
         SYNTAX Gauge32
         MAX-ACCESS  read-only
         STATUS  current
         DESCRIPTION
            "The total number of multicast packets received on this
              interface during the current 15-minute interval."
         ::= { adGenEth15MinCurrentEntry 11 }

      adGenEth15MinCurrentInBroadcastPkts OBJECT-TYPE
         SYNTAX Gauge32
         MAX-ACCESS  read-only
         STATUS  current
         DESCRIPTION
            "The total number of broadcast packets received on this
              interface during the current 15-minute interval."
         ::= { adGenEth15MinCurrentEntry 12 }

      adGenEth15MinCurrentInUnicastPkts OBJECT-TYPE
         SYNTAX Gauge32
         MAX-ACCESS  read-only
         STATUS  current
         DESCRIPTION
            "The total number of unicast packets received on this
              interface during the current 15-minute interval."
         ::= { adGenEth15MinCurrentEntry 13 }

      adGenEth15MinCurrentOutMulticastPkts OBJECT-TYPE
         SYNTAX Gauge32
         MAX-ACCESS  read-only
         STATUS  current
         DESCRIPTION
            "The total number of multicast packets transmitted on this
              interface during the current 15-minute interval."
         ::= { adGenEth15MinCurrentEntry 14 }

      adGenEth15MinCurrentOutBroadcastPkts OBJECT-TYPE
         SYNTAX Gauge32
         MAX-ACCESS  read-only
         STATUS  current
         DESCRIPTION
            "The total number of broadcast packets transmitted on this
              interface during the current 15-minute interval."
         ::= { adGenEth15MinCurrentEntry 15 }

      adGenEth15MinCurrentOutUnicastPkts OBJECT-TYPE
         SYNTAX Gauge32
         MAX-ACCESS  read-only
         STATUS  current
         DESCRIPTION
            "The total number of unicast packets transmitted on this
              interface during the current 15-minute interval."
         ::= { adGenEth15MinCurrentEntry 16 }

      adGenEth15MinCurrentDroppedPktsQueue0  OBJECT-TYPE
         SYNTAX Gauge32
         MAX-ACCESS  read-only
         STATUS  current
         DESCRIPTION
             "The number of dropped packets on queue 0
              during the current 15-minute interval."
         ::= { adGenEth15MinCurrentEntry 17 }

      adGenEth15MinCurrentDroppedPktsQueue1  OBJECT-TYPE
         SYNTAX Gauge32
         MAX-ACCESS  read-only
         STATUS  current
         DESCRIPTION
             "The number of dropped packets on queue 1
              during the current 15-minute interval."
         ::= { adGenEth15MinCurrentEntry 18 }

      adGenEth15MinCurrentDroppedPktsQueue2  OBJECT-TYPE
         SYNTAX Gauge32
         MAX-ACCESS  read-only
         STATUS  current
         DESCRIPTION
             "The number of dropped packets on queue 2
              during the current 15-minute interval."
         ::= { adGenEth15MinCurrentEntry 19 }

      adGenEth15MinCurrentDroppedPktsQueue3  OBJECT-TYPE
         SYNTAX Gauge32
         MAX-ACCESS  read-only
         STATUS  current
         DESCRIPTION
             "The number of dropped packets on queue 3
              during the current 15-minute interval."
         ::= { adGenEth15MinCurrentEntry 20 }

      adGenEth15MinCurrentDroppedPktsQueue4  OBJECT-TYPE
         SYNTAX Gauge32
         MAX-ACCESS  read-only
         STATUS  current
         DESCRIPTION
             "The number of dropped packets on queue 4
              during the current 15-minute interval."
         ::= { adGenEth15MinCurrentEntry 21 }

      adGenEth15MinCurrentDroppedPktsQueue5  OBJECT-TYPE
         SYNTAX Gauge32
         MAX-ACCESS  read-only
         STATUS  current
         DESCRIPTION
             "The number of dropped packets on queue 5
              during the current 15-minute interval."
         ::= { adGenEth15MinCurrentEntry 22 }

      adGenEth15MinCurrentDroppedPktsQueue6  OBJECT-TYPE
         SYNTAX Gauge32
         MAX-ACCESS  read-only
         STATUS  current
         DESCRIPTION
             "The number of dropped packets on queue 6
              during the current 15-minute interval."
         ::= { adGenEth15MinCurrentEntry 23 }

      adGenEth15MinCurrentDroppedPktsQueue7  OBJECT-TYPE
         SYNTAX Gauge32
         MAX-ACCESS  read-only
         STATUS  current
         DESCRIPTION
             "The number of dropped packets on queue 7
              during the current 15-minute interval."
         ::= { adGenEth15MinCurrentEntry 24 }

      adGenEth15MinCurrentOutDiscards OBJECT-TYPE
         SYNTAX Gauge32
         MAX-ACCESS  read-only
         STATUS  current
         DESCRIPTION
             "The total number of discarded packets transmitted on this
              interface during the current 15-minute interval."
         ::= { adGenEth15MinCurrentEntry 25 }

      adGenEth15MinCurrentInCRCErrors OBJECT-TYPE
         SYNTAX Gauge32
         MAX-ACCESS  read-only
         STATUS  current
         DESCRIPTION
             "The total number of packets with CRC errors received on this
              interface during the current 15-minute interval."
         ::= { adGenEth15MinCurrentEntry 26 }

      adGenEth15MinCurrentInFrameErrors OBJECT-TYPE
         SYNTAX Gauge32
         MAX-ACCESS  read-only
         STATUS  current
         DESCRIPTION
              "The total number of packets with frame errors received on this
               interface during the current 15-minute interval."
         ::= { adGenEth15MinCurrentEntry 27 }

      adGenEth15MinCurrentOutErrors OBJECT-TYPE
         SYNTAX Gauge32
         MAX-ACCESS  read-only
         STATUS  current
         DESCRIPTION
              "The total number of packets with errors transmitted on this
               interface during the current 15-minute interval."
         ::= { adGenEth15MinCurrentEntry 28 }

      adGenEth15MinCurrentInPeakUtilization OBJECT-TYPE
         SYNTAX  Gauge32
         MAX-ACCESS  read-only
         STATUS  current
         DESCRIPTION
             "The maximum usage of the ingress link (in whole percent)
              during the current 15-minute interval."
         ::= { adGenEth15MinCurrentEntry 29 }

      adGenEth15MinCurrentInAvgUtilization OBJECT-TYPE
         SYNTAX  Gauge32
         MAX-ACCESS  read-only
         STATUS  current
         DESCRIPTION
             "The average percent usage of the ingress link
              during the current 15-minute interval."
         ::= { adGenEth15MinCurrentEntry 30 }

      adGenEth15MinCurrentOutPeakUtilization OBJECT-TYPE
         SYNTAX  Gauge32
         MAX-ACCESS  read-only
         STATUS  current
         DESCRIPTION
             "The maximum usage of the egress link (in whole percent)
              during the current 15-minute interval."
         ::= { adGenEth15MinCurrentEntry 31 }

      adGenEth15MinCurrentOutAvgUtilization OBJECT-TYPE
         SYNTAX  Gauge32
         MAX-ACCESS  read-only
         STATUS  current
         DESCRIPTION
             "The average percent usage of the egress link
              during the current 15-minute interval."
         ::= { adGenEth15MinCurrentEntry 32 }


--==================================================================================================================


   adGenEth15MinCurrentHCTable OBJECT-TYPE
      SYNTAX  SEQUENCE OF AdGenEth15MinCurrentHCEntry
      MAX-ACCESS  not-accessible
      STATUS  current
      DESCRIPTION
         "The Generic Ethernet 15Min current high-capacity table."
      ::= { adGenEthIfcPerformance 3 }

   adGenEth15MinCurrentHCEntry OBJECT-TYPE
      SYNTAX  AdGenEth15MinCurrentHCEntry
      MAX-ACCESS  not-accessible
      STATUS  current
      DESCRIPTION
         "An entry in the Generic Ethernet 15Min current high-capacity table."
      INDEX   { ifIndex }
      ::= { adGenEth15MinCurrentHCTable 1 }

   AdGenEth15MinCurrentHCEntry  ::=
      SEQUENCE {
         adGenEth15MinCurrentHCOutOctets
            Counter64,
         adGenEth15MinCurrentHCInOctets
            Counter64,
         adGenEth15MinCurrentHCInMulticastPkts
            Counter64,
         adGenEth15MinCurrentHCInBroadcastPkts
            Counter64,
         adGenEth15MinCurrentHCInUnicastPkts
            Counter64,
         adGenEth15MinCurrentHCOutMulticastPkts
            Counter64,
         adGenEth15MinCurrentHCOutBroadcastPkts
            Counter64,
         adGenEth15MinCurrentHCOutUnicastPkts
            Counter64,
         adGenEth15MinCurrentHCTotalPktsQueue0
            Counter64,
         adGenEth15MinCurrentHCTotalPktsQueue1
            Counter64,
         adGenEth15MinCurrentHCTotalPktsQueue2
            Counter64,
         adGenEth15MinCurrentHCTotalPktsQueue3
            Counter64,
         adGenEth15MinCurrentHCTotalPktsQueue4
            Counter64,
         adGenEth15MinCurrentHCTotalPktsQueue5
            Counter64,
         adGenEth15MinCurrentHCTotalPktsQueue6
            Counter64,
         adGenEth15MinCurrentHCTotalPktsQueue7
            Counter64,
         adGenEth15MinCurrentHCOutLcv
            Counter64,
         adGenEth15MinCurrentHCInLcv
            Counter64,
         adGenEth15MinCurrentHCInAvgBitsPerSec
            Counter64,
         adGenEth15MinCurrentHCInAvgPktsPerSec
            Counter64,
         adGenEth15MinCurrentHCOutAvgBitsPerSec
            Counter64,
         adGenEth15MinCurrentHCOutAvgPktsPerSec
            Counter64
       }

      adGenEth15MinCurrentHCOutOctets OBJECT-TYPE
         SYNTAX Counter64
         MAX-ACCESS  read-only
         STATUS  current
         DESCRIPTION
            "The total number of octets transmitted on the interface
             during the current 15-minute interval, including framing characters.
             This object is a 64-bit version of adGenEth15MinCurrentOutOctets."
         ::= { adGenEth15MinCurrentHCEntry 1 }

      adGenEth15MinCurrentHCInOctets OBJECT-TYPE
         SYNTAX Counter64
         MAX-ACCESS  read-only
         STATUS  current
         DESCRIPTION
            "The total number of octets received on the interface
             during the current 15-minute interval, including framing characters.
             This object is a 64-bit version of adGenEth15MinCurrentInOctets."
         ::= { adGenEth15MinCurrentHCEntry 2 }

      adGenEth15MinCurrentHCInMulticastPkts OBJECT-TYPE
         SYNTAX Counter64
         MAX-ACCESS  read-only
         STATUS  current
         DESCRIPTION
            "The total number of multicast packets received on this
             interface during the current 15-minute interval.  This object
             is a 64-bit version of adGenEth15MinCurrentInMulticastPkts."
         ::= { adGenEth15MinCurrentHCEntry 3 }

      adGenEth15MinCurrentHCInBroadcastPkts OBJECT-TYPE
         SYNTAX Counter64
         MAX-ACCESS  read-only
         STATUS  current
         DESCRIPTION
            "The total number of broadcast packets received on this
             interface during the current 15-minute interval.  This object
             is a 64-bit version of adGenEth15MinCurrentInBroadcastPkts."
         ::= { adGenEth15MinCurrentHCEntry 4 }

      adGenEth15MinCurrentHCInUnicastPkts OBJECT-TYPE
         SYNTAX Counter64
         MAX-ACCESS  read-only
         STATUS  current
         DESCRIPTION
            "The total number of unicast packets received on this
             interface during the current 15-minute interval.  This object
             is a 64-bit version of adGenEth15MinCurrentInUnicastPkts."
         ::= { adGenEth15MinCurrentHCEntry 5 }

      adGenEth15MinCurrentHCOutMulticastPkts OBJECT-TYPE
         SYNTAX Counter64
         MAX-ACCESS  read-only
         STATUS  current
         DESCRIPTION
            "The total number of multicast packets transmitted on this
             interface during the current 15-minute interval.  This object
             is a 64-bit version of adGenEth15MinCurrentOutMulticastPkts."
         ::= { adGenEth15MinCurrentHCEntry 6 }

      adGenEth15MinCurrentHCOutBroadcastPkts OBJECT-TYPE
         SYNTAX Counter64
         MAX-ACCESS  read-only
         STATUS  current
         DESCRIPTION
            "The total number of broadcast packets transmitted on this
             interface during the current 15-minute interval.  This object
             is a 64-bit version of adGenEth15MinCurrentOutBroadcastPkts."
         ::= { adGenEth15MinCurrentHCEntry 7 }

      adGenEth15MinCurrentHCOutUnicastPkts OBJECT-TYPE
         SYNTAX Counter64
         MAX-ACCESS  read-only
         STATUS  current
         DESCRIPTION
            "The total number of unicast packets transmitted on this
             interface during the current 15-minute interval.  This object
             is a 64-bit version of adGenEth15MinCurrentOutUnicastPkts."
         ::= { adGenEth15MinCurrentHCEntry 8 }

      adGenEth15MinCurrentHCTotalPktsQueue0  OBJECT-TYPE
         SYNTAX  Counter64
         MAX-ACCESS  read-only
         STATUS current
         DESCRIPTION
             "The total number of packets transmitted on queue 0
              for this interface during the current 15-minute interval."
         ::= { adGenEth15MinCurrentHCEntry 9 }

      adGenEth15MinCurrentHCTotalPktsQueue1  OBJECT-TYPE
         SYNTAX  Counter64
         MAX-ACCESS  read-only
         STATUS current
         DESCRIPTION
             "The total number of packets transmitted on queue 1
              for this interface during the current 15-minute interval."
         ::= { adGenEth15MinCurrentHCEntry 10 }

      adGenEth15MinCurrentHCTotalPktsQueue2  OBJECT-TYPE
         SYNTAX  Counter64
         MAX-ACCESS  read-only
         STATUS current
         DESCRIPTION
             "The total number of packets transmitted on queue 2
              for this interface during the current 15-minute interval."
         ::= { adGenEth15MinCurrentHCEntry 11 }

      adGenEth15MinCurrentHCTotalPktsQueue3  OBJECT-TYPE
         SYNTAX  Counter64
         MAX-ACCESS  read-only
         STATUS current
         DESCRIPTION
             "The total number of packets transmitted on queue 3
              for this interface during the current 15-minute interval."
         ::= { adGenEth15MinCurrentHCEntry 12 }

      adGenEth15MinCurrentHCTotalPktsQueue4  OBJECT-TYPE
         SYNTAX  Counter64
         MAX-ACCESS  read-only
         STATUS current
         DESCRIPTION
             "The total number of packets transmitted on queue 4
              for this interface during the current 15-minute interval."
         ::= { adGenEth15MinCurrentHCEntry 13 }

      adGenEth15MinCurrentHCTotalPktsQueue5  OBJECT-TYPE
         SYNTAX  Counter64
         MAX-ACCESS  read-only
         STATUS current
         DESCRIPTION
             "The total number of packets transmitted on queue 5
              for this interface during the current 15-minute interval."
         ::= { adGenEth15MinCurrentHCEntry 14 }

      adGenEth15MinCurrentHCTotalPktsQueue6  OBJECT-TYPE
         SYNTAX  Counter64
         MAX-ACCESS  read-only
         STATUS current
         DESCRIPTION
             "The total number of packets transmitted on queue 6
              for this interface during the current 15-minute interval."
         ::= { adGenEth15MinCurrentHCEntry 15 }

      adGenEth15MinCurrentHCTotalPktsQueue7  OBJECT-TYPE
         SYNTAX  Counter64
         MAX-ACCESS  read-only
         STATUS current
         DESCRIPTION
             "The total number of packets transmitted on queue 7
              for this interface during the current 15-minute interval."
         ::= { adGenEth15MinCurrentHCEntry 16 }

      adGenEth15MinCurrentHCOutLcv OBJECT-TYPE
         SYNTAX Counter64
         MAX-ACCESS  read-only
         STATUS  current
         DESCRIPTION
            "The total number of line code violations
                                 that occurred on data received from system interface
                                 during the current 15-minute interval."
         ::= { adGenEth15MinCurrentHCEntry 17 }

      adGenEth15MinCurrentHCInLcv OBJECT-TYPE
         SYNTAX Counter64
         MAX-ACCESS  read-only
         STATUS  current
         DESCRIPTION
            "The total number of Line Code Violations
                                 that occurred on data received from line side
                                 during the current 15-minute interval."
         ::= { adGenEth15MinCurrentHCEntry 18 }

      adGenEth15MinCurrentHCInAvgBitsPerSec OBJECT-TYPE
         SYNTAX Counter64
         MAX-ACCESS  read-only
         STATUS  current
         DESCRIPTION
              "The average number of bits per second received
               on the interface during the current 15-minute interval."
         ::= { adGenEth15MinCurrentHCEntry 19 }

      adGenEth15MinCurrentHCInAvgPktsPerSec OBJECT-TYPE
         SYNTAX Counter64
         MAX-ACCESS  read-only
         STATUS  current
         DESCRIPTION
              "The average number of packets per second received
               on the interface during the current 15-minute interval."
         ::= { adGenEth15MinCurrentHCEntry 20 }

      adGenEth15MinCurrentHCOutAvgBitsPerSec OBJECT-TYPE
         SYNTAX Counter64
         MAX-ACCESS  read-only
         STATUS  current
         DESCRIPTION
              "The average number of bits per second sent
               on the interface during the current 15-minute interval."
         ::= { adGenEth15MinCurrentHCEntry 21 }

      adGenEth15MinCurrentHCOutAvgPktsPerSec OBJECT-TYPE
         SYNTAX Counter64
         MAX-ACCESS  read-only
         STATUS  current
         DESCRIPTION
              "The average number of packets per second sent
               on the interface during the current 15-minute interval."
         ::= { adGenEth15MinCurrentHCEntry 22 }

--==================================================================================================================

   adGenEth15MinIntervalTable OBJECT-TYPE
      SYNTAX  SEQUENCE OF AdGenEth15MinIntervalEntry
      MAX-ACCESS  not-accessible
      STATUS  current
      DESCRIPTION
         "The Ethernet 15Min interval table."
      ::= { adGenEthIfcPerformance 4 }

   adGenEth15MinIntervalEntry OBJECT-TYPE
      SYNTAX  AdGenEth15MinIntervalEntry
      MAX-ACCESS  not-accessible
      STATUS  current
      DESCRIPTION
         "An entry in the Ethernet 15Min interval table."
      INDEX   { ifIndex, adGenEth15MinIntervalNumber }
      ::= { adGenEth15MinIntervalTable 1 }

   AdGenEth15MinIntervalEntry  ::=
      SEQUENCE {
         adGenEth15MinIntervalNumber
            Integer32,
         adGenEth15MinIntervalOutOctets
            Gauge32,
         adGenEth15MinIntervalOutPkts
            Gauge32,
         adGenEth15MinIntervalInOctets
            Gauge32,
         adGenEth15MinIntervalInPkts
            Gauge32,
         adGenEth15MinIntervalInGoodOctets
            Gauge32,
         adGenEth15MinIntervalInGoodPkts
            Gauge32,
         adGenEth15MinIntervalInErrors
            Gauge32,
         adGenEth15MinIntervalInDiscards
            Gauge32,
         adGenEth15MinIntervalInGiants
            Gauge32,
         adGenEth15MinIntervalInRunts
            Gauge32,
         adGenEth15MinIntervalInMulticastPkts
            Gauge32,
         adGenEth15MinIntervalInBroadcastPkts
            Gauge32,
         adGenEth15MinIntervalInUnicastPkts
            Gauge32,
         adGenEth15MinIntervalOutMulticastPkts
            Gauge32,
         adGenEth15MinIntervalOutBroadcastPkts
            Gauge32,
         adGenEth15MinIntervalOutUnicastPkts
            Gauge32,
         adGenEth15MinIntervalDroppedPktsQueue0
            Gauge32,
         adGenEth15MinIntervalDroppedPktsQueue1
            Gauge32,
         adGenEth15MinIntervalDroppedPktsQueue2
            Gauge32,
         adGenEth15MinIntervalDroppedPktsQueue3
            Gauge32,
         adGenEth15MinIntervalDroppedPktsQueue4
            Gauge32,
         adGenEth15MinIntervalDroppedPktsQueue5
            Gauge32,
         adGenEth15MinIntervalDroppedPktsQueue6
            Gauge32,
         adGenEth15MinIntervalDroppedPktsQueue7
            Gauge32,
         adGenEth15MinIntervalOutDiscards
            Gauge32,
         adGenEth15MinIntervalInCRCErrors
            Gauge32,
         adGenEth15MinIntervalInFrameErrors
            Gauge32,
         adGenEth15MinIntervalOutErrors
            Gauge32,

         adGenEth15MinIntervalInPeakUtilization
            Gauge32,
         adGenEth15MinIntervalInAvgUtilization
            Gauge32,
         adGenEth15MinIntervalOutPeakUtilization
            Gauge32,
         adGenEth15MinIntervalOutAvgUtilization
            Gauge32
       }

      adGenEth15MinIntervalNumber OBJECT-TYPE
         SYNTAX  Integer32
         MAX-ACCESS  read-only
         STATUS  current
         DESCRIPTION
            "A number between 1 and 96, where 1 is the most
             recently completed 15 minute interval and 96 is
             the least recently completed 15 minutes interval
             (assuming that all 96 intervals are valid)."
         ::= { adGenEth15MinIntervalEntry 1 }

      adGenEth15MinIntervalOutOctets OBJECT-TYPE
         SYNTAX Gauge32
         MAX-ACCESS  read-only
         STATUS  current
         DESCRIPTION
            "The total number of octets transmitted on the interface
             during the selected 15-minute interval, including framing characters."
         ::= { adGenEth15MinIntervalEntry 2 }

      adGenEth15MinIntervalOutPkts OBJECT-TYPE
         SYNTAX Gauge32
         MAX-ACCESS  read-only
         STATUS  current
         DESCRIPTION
            "The total number of packets transmitted on the interface
             during the selected 15-minute interval."
         ::= { adGenEth15MinIntervalEntry 3 }

      adGenEth15MinIntervalInOctets OBJECT-TYPE
         SYNTAX Gauge32
         MAX-ACCESS  read-only
         STATUS  current
         DESCRIPTION
            "The total number of octets received on the interface during
             the selected 15-minute interval, including framing characters."
         ::= { adGenEth15MinIntervalEntry 4 }

      adGenEth15MinIntervalInPkts OBJECT-TYPE
         SYNTAX Gauge32
         MAX-ACCESS  read-only
         STATUS  current
         DESCRIPTION
            "The total number of packets received on the interface
             during the selected 15-minute interval."
         ::= { adGenEth15MinIntervalEntry 5 }

      adGenEth15MinIntervalInGoodOctets OBJECT-TYPE
         SYNTAX Gauge32
         MAX-ACCESS  read-only
         STATUS  current
         DESCRIPTION
            ""
         ::= { adGenEth15MinIntervalEntry 6 }

      adGenEth15MinIntervalInGoodPkts OBJECT-TYPE
         SYNTAX Gauge32
         MAX-ACCESS  read-only
         STATUS  current
         DESCRIPTION
            ""
         ::= { adGenEth15MinIntervalEntry 7 }

      adGenEth15MinIntervalInErrors OBJECT-TYPE
         SYNTAX Gauge32
         MAX-ACCESS  read-only
         STATUS  current
         DESCRIPTION
            "The number of inbound packets that contained errors
             during the selected 15-minute interval."
         ::= { adGenEth15MinIntervalEntry 8 }

      adGenEth15MinIntervalInDiscards OBJECT-TYPE
         SYNTAX Gauge32
         MAX-ACCESS  read-only
         STATUS  current
         DESCRIPTION
            "The number of inbound packets which were chosen to be discarded
             during the selected 15-minute interval even though no errors
             had been detected.  One reason for discarding such a packet
             could be congestion."
         ::= { adGenEth15MinIntervalEntry 9 }

      adGenEth15MinIntervalInGiants OBJECT-TYPE
         SYNTAX Gauge32
         MAX-ACCESS  read-only
         STATUS  current
         DESCRIPTION
            "The number of packets received during the selected 15-minute
             interval which were larger than the maximum packet size."
         ::= { adGenEth15MinIntervalEntry 10 }

      adGenEth15MinIntervalInRunts OBJECT-TYPE
         SYNTAX Gauge32
         MAX-ACCESS  read-only
         STATUS  current
         DESCRIPTION
            "The number of packets received during the selected 15-minute
             interval which were smaller than the minimum packet size."
         ::= { adGenEth15MinIntervalEntry 11 }

      adGenEth15MinIntervalInMulticastPkts OBJECT-TYPE
         SYNTAX Gauge32
         MAX-ACCESS  read-only
         STATUS  current
         DESCRIPTION
            "The total number of multicast packets received on this
              interface during the selected 15-minute interval."
         ::= { adGenEth15MinIntervalEntry 12 }

      adGenEth15MinIntervalInBroadcastPkts OBJECT-TYPE
         SYNTAX Gauge32
         MAX-ACCESS  read-only
         STATUS  current
         DESCRIPTION
            "The total number of broadcast packets received on this
              interface during the selected 15-minute interval."
         ::= { adGenEth15MinIntervalEntry 13 }

      adGenEth15MinIntervalInUnicastPkts OBJECT-TYPE
         SYNTAX Gauge32
         MAX-ACCESS  read-only
         STATUS  current
         DESCRIPTION
            "The total number of unicast packets received on this
              interface during the selected 15-minute interval."
         ::= { adGenEth15MinIntervalEntry 14 }

      adGenEth15MinIntervalOutMulticastPkts OBJECT-TYPE
         SYNTAX Gauge32
         MAX-ACCESS  read-only
         STATUS  current
         DESCRIPTION
            "The total number of multicast packets transmitted on this
              interface during the selected 15-minute interval."
         ::= { adGenEth15MinIntervalEntry 15 }

      adGenEth15MinIntervalOutBroadcastPkts OBJECT-TYPE
         SYNTAX Gauge32
         MAX-ACCESS  read-only
         STATUS  current
         DESCRIPTION
            "The total number of broadcast packets transmitted on this
              interface during the selected 15-minute interval."
         ::= { adGenEth15MinIntervalEntry 16 }

      adGenEth15MinIntervalOutUnicastPkts OBJECT-TYPE
         SYNTAX Gauge32
         MAX-ACCESS  read-only
         STATUS  current
         DESCRIPTION
            "The total number of unicast packets transmitted on this
              interface during the selected 15-minute interval."
         ::= { adGenEth15MinIntervalEntry 17 }

      adGenEth15MinIntervalDroppedPktsQueue0  OBJECT-TYPE
         SYNTAX  Gauge32
         MAX-ACCESS  read-only
         STATUS  current
         DESCRIPTION
             "The number of dropped packets for queue 0 on this
              interface during the selected 15-minute interval."
         ::= { adGenEth15MinIntervalEntry 18 }

      adGenEth15MinIntervalDroppedPktsQueue1  OBJECT-TYPE
         SYNTAX  Gauge32
         MAX-ACCESS  read-only
         STATUS  current
         DESCRIPTION
             "The number of dropped packets for queue 1 on this
              interface during the selected 15-minute interval."
         ::= { adGenEth15MinIntervalEntry 19 }

      adGenEth15MinIntervalDroppedPktsQueue2  OBJECT-TYPE
         SYNTAX  Gauge32
         MAX-ACCESS  read-only
         STATUS  current
         DESCRIPTION
             "The number of dropped packets for queue 2 on this
              interface during the selected 15-minute interval."
         ::= { adGenEth15MinIntervalEntry 20 }

      adGenEth15MinIntervalDroppedPktsQueue3  OBJECT-TYPE
         SYNTAX  Gauge32
         MAX-ACCESS  read-only
         STATUS  current
         DESCRIPTION
             "The number of dropped packets for queue 3 on this
              interface during the selected 15-minute interval."
         ::= { adGenEth15MinIntervalEntry 21 }

      adGenEth15MinIntervalDroppedPktsQueue4  OBJECT-TYPE
         SYNTAX  Gauge32
         MAX-ACCESS  read-only
         STATUS  current
         DESCRIPTION
             "The number of dropped packets for queue 4 on this
              interface during the selected 15-minute interval."
         ::= { adGenEth15MinIntervalEntry 22 }

      adGenEth15MinIntervalDroppedPktsQueue5  OBJECT-TYPE
         SYNTAX  Gauge32
         MAX-ACCESS  read-only
         STATUS  current
         DESCRIPTION
             "The number of dropped packets for queue 5 on this
              interface during the selected 15-minute interval."
         ::= { adGenEth15MinIntervalEntry 23 }

      adGenEth15MinIntervalDroppedPktsQueue6  OBJECT-TYPE
         SYNTAX  Gauge32
         MAX-ACCESS  read-only
         STATUS  current
         DESCRIPTION
             "The number of dropped packets for queue 6 on this
              interface during the selected 15-minute interval."
         ::= { adGenEth15MinIntervalEntry 24 }

      adGenEth15MinIntervalDroppedPktsQueue7  OBJECT-TYPE
         SYNTAX  Gauge32
         MAX-ACCESS  read-only
         STATUS  current
         DESCRIPTION
             "The number of dropped packets for queue 7 on this
              interface during the selected 15-minute interval."
         ::= { adGenEth15MinIntervalEntry 25 }

      adGenEth15MinIntervalOutDiscards OBJECT-TYPE
         SYNTAX Gauge32
         MAX-ACCESS  read-only
         STATUS  current
         DESCRIPTION
             "The total number of discarded packets transmitted on this
              interface during the selected 15-minute interval."
         ::= { adGenEth15MinIntervalEntry 26 }

      adGenEth15MinIntervalInCRCErrors OBJECT-TYPE
         SYNTAX Gauge32
         MAX-ACCESS  read-only
         STATUS  current
         DESCRIPTION
             "The total number of packets with CRC errors received on this
              interface during the selected 15-minute interval."
         ::= { adGenEth15MinIntervalEntry 27 }

      adGenEth15MinIntervalInFrameErrors OBJECT-TYPE
         SYNTAX Gauge32
         MAX-ACCESS  read-only
         STATUS  current
         DESCRIPTION
             "The total number of packets with frame errors received on this
              interface during the selected 15-minute interval."
         ::= { adGenEth15MinIntervalEntry 28 }

      adGenEth15MinIntervalOutErrors OBJECT-TYPE
         SYNTAX Gauge32
         MAX-ACCESS  read-only
         STATUS  current
         DESCRIPTION
             "The total number of packets with errors transmitted on this
              interface during the selected 15-minute interval."
         ::= { adGenEth15MinIntervalEntry 29 }

      adGenEth15MinIntervalInPeakUtilization OBJECT-TYPE
         SYNTAX  Gauge32
         MAX-ACCESS  read-only
         STATUS  current
         DESCRIPTION
             "The maximum usage of the ingress link (in whole percent)
              during the selected 15-minute interval."
         ::= { adGenEth15MinIntervalEntry 30 }

      adGenEth15MinIntervalInAvgUtilization OBJECT-TYPE
         SYNTAX  Gauge32
         MAX-ACCESS  read-only
         STATUS  current
         DESCRIPTION
             "The average percent usage of the ingress link
              during the selected 15-minute interval."
         ::= { adGenEth15MinIntervalEntry 31 }

      adGenEth15MinIntervalOutPeakUtilization OBJECT-TYPE
         SYNTAX  Gauge32
         MAX-ACCESS  read-only
         STATUS  current
         DESCRIPTION
             "The maximum usage of the egress link (in whole percent)
              during the selected 15-minute interval."
         ::= { adGenEth15MinIntervalEntry 32 }

      adGenEth15MinIntervalOutAvgUtilization OBJECT-TYPE
         SYNTAX  Gauge32
         MAX-ACCESS  read-only
         STATUS  current
         DESCRIPTION
             "The average percent usage of the egress link
              during the selected 15-minute interval."
         ::= { adGenEth15MinIntervalEntry 33 }


--==================================================================================================================


   adGenEth15MinIntervalHCTable OBJECT-TYPE
      SYNTAX  SEQUENCE OF AdGenEth15MinIntervalHCEntry
      MAX-ACCESS  not-accessible
      STATUS  current
      DESCRIPTION
         "The Ethernet 15Min interval high-capacity table."
      ::= { adGenEthIfcPerformance 5 }

   adGenEth15MinIntervalHCEntry OBJECT-TYPE
      SYNTAX  AdGenEth15MinIntervalHCEntry
      MAX-ACCESS  not-accessible
      STATUS  current
      DESCRIPTION
         "An entry in the Ethernet 15Min interval high-capacity table."
      INDEX   { ifIndex, adGenEth15MinIntervalHCNumber }
      ::= { adGenEth15MinIntervalHCTable 1 }

   AdGenEth15MinIntervalHCEntry  ::=
      SEQUENCE {
         adGenEth15MinIntervalHCNumber
            Integer32,
         adGenEth15MinIntervalHCOutOctets
            Counter64,
         adGenEth15MinIntervalHCInOctets
            Counter64,
         adGenEth15MinIntervalHCInMulticastPkts
            Counter64,
         adGenEth15MinIntervalHCInBroadcastPkts
            Counter64,
         adGenEth15MinIntervalHCInUnicastPkts
            Counter64,
         adGenEth15MinIntervalHCOutMulticastPkts
            Counter64,
         adGenEth15MinIntervalHCOutBroadcastPkts
            Counter64,
         adGenEth15MinIntervalHCOutUnicastPkts
            Counter64,
         adGenEth15MinIntervalHCTotalPktsQueue0
            Counter64,
         adGenEth15MinIntervalHCTotalPktsQueue1
            Counter64,
         adGenEth15MinIntervalHCTotalPktsQueue2
            Counter64,
         adGenEth15MinIntervalHCTotalPktsQueue3
            Counter64,
         adGenEth15MinIntervalHCTotalPktsQueue4
            Counter64,
         adGenEth15MinIntervalHCTotalPktsQueue5
            Counter64,
         adGenEth15MinIntervalHCTotalPktsQueue6
            Counter64,
         adGenEth15MinIntervalHCTotalPktsQueue7
            Counter64,
         adGenEth15MinIntervalHCOutLcv
            Counter64,
         adGenEth15MinIntervalHCInLcv
            Counter64,
         adGenEth15MinIntervalHCValidData
            TruthValue,
         adGenEth15MinIntervalHCInAvgBitsPerSec
            Counter64,
         adGenEth15MinIntervalHCInAvgPktsPerSec
            Counter64,
         adGenEth15MinIntervalHCOutAvgBitsPerSec
            Counter64,
         adGenEth15MinIntervalHCOutAvgPktsPerSec
            Counter64
       }

      adGenEth15MinIntervalHCNumber OBJECT-TYPE
         SYNTAX  Integer32
         MAX-ACCESS  read-only
         STATUS  current
         DESCRIPTION
            "A number between 1 and 96, where 1 is the most
             recently completed 15 minute interval and 96 is
             the least recently completed 15 minutes interval
             (assuming that all 96 intervals are valid)."
         ::= { adGenEth15MinIntervalHCEntry 1 }

      adGenEth15MinIntervalHCOutOctets OBJECT-TYPE
         SYNTAX Counter64
         MAX-ACCESS  read-only
         STATUS  current
         DESCRIPTION
            "The total number of octets transmitted on the interface
             during the selected 15-minute interval, including framing characters.
             This object is a 64-bit version of adGenEth15MinIntervalOutOctets."
         ::= { adGenEth15MinIntervalHCEntry 2 }

      adGenEth15MinIntervalHCInOctets OBJECT-TYPE
         SYNTAX Counter64
         MAX-ACCESS  read-only
         STATUS  current
         DESCRIPTION
            "The total number of octets received on the interface
             during the selected 15-minute interval, including framing characters.
             This object is a 64-bit version of adGenEth15MinIntervalInOctets."
         ::= { adGenEth15MinIntervalHCEntry 3 }

      adGenEth15MinIntervalHCInMulticastPkts OBJECT-TYPE
         SYNTAX Counter64
         MAX-ACCESS  read-only
         STATUS  current
         DESCRIPTION
            "The total number of multicast packets received on this
             interface during the selected 15-minute interval.  This object
             is a 64-bit version of adGenEth15MinIntervalInMulticastPkts."
         ::= { adGenEth15MinIntervalHCEntry 4 }

      adGenEth15MinIntervalHCInBroadcastPkts OBJECT-TYPE
         SYNTAX Counter64
         MAX-ACCESS  read-only
         STATUS  current
         DESCRIPTION
            "The total number of broadcast packets received on this
             interface during the selected 15-minute interval.  This object
             is a 64-bit version of adGenEth15MinIntervalInBroadcastPkts."
         ::= { adGenEth15MinIntervalHCEntry 5 }

      adGenEth15MinIntervalHCInUnicastPkts OBJECT-TYPE
         SYNTAX Counter64
         MAX-ACCESS  read-only
         STATUS  current
         DESCRIPTION
            "The total number of unicast packets received on this
             interface during the selected 15-minute interval.  This object
             is a 64-bit version of adGenEth15MinIntervalInUnicastPkts."
         ::= { adGenEth15MinIntervalHCEntry 6 }

      adGenEth15MinIntervalHCOutMulticastPkts OBJECT-TYPE
         SYNTAX Counter64
         MAX-ACCESS  read-only
         STATUS  current
         DESCRIPTION
            "The total number of multicast packets transmitted on this
             interface during the selected 15-minute interval.  This object
             is a 64-bit version of adGenEth15MinIntervalOutMulticastPkts."
         ::= { adGenEth15MinIntervalHCEntry 7 }

      adGenEth15MinIntervalHCOutBroadcastPkts OBJECT-TYPE
         SYNTAX Counter64
         MAX-ACCESS  read-only
         STATUS  current
         DESCRIPTION
            "The total number of broadcast packets transmitted on this
             interface during the selected 15-minute interval.  This object
             is a 64-bit version of adGenEth15MinIntervalOutBroadcastPkts."
         ::= { adGenEth15MinIntervalHCEntry 8 }

      adGenEth15MinIntervalHCOutUnicastPkts OBJECT-TYPE
         SYNTAX Counter64
         MAX-ACCESS  read-only
         STATUS  current
         DESCRIPTION
            "The total number of unicast packets transmitted on this
             interface during the selected 15-minute interval.  This object
             is a 64-bit version of adGenEth15MinIntervalOutUnicastPkts."
         ::= { adGenEth15MinIntervalHCEntry 9 }

      adGenEth15MinIntervalHCTotalPktsQueue0  OBJECT-TYPE
         SYNTAX Counter64
         MAX-ACCESS  read-only
         STATUS  current
         DESCRIPTION
            "The total number of packets transmitted on queue 0
             for this interface during the selected 15-minute interval."
         ::= { adGenEth15MinIntervalHCEntry 10 }

      adGenEth15MinIntervalHCTotalPktsQueue1  OBJECT-TYPE
         SYNTAX Counter64
         MAX-ACCESS  read-only
         STATUS  current
         DESCRIPTION
            "The total number of packets transmitted on queue 1
             for this interface during the selected 15-minute interval."
         ::= { adGenEth15MinIntervalHCEntry 11 }

      adGenEth15MinIntervalHCTotalPktsQueue2  OBJECT-TYPE
         SYNTAX Counter64
         MAX-ACCESS  read-only
         STATUS  current
         DESCRIPTION
            "The total number of packets transmitted on queue 2
             for this interface during the selected 15-minute interval."
         ::= { adGenEth15MinIntervalHCEntry 12 }

      adGenEth15MinIntervalHCTotalPktsQueue3  OBJECT-TYPE
         SYNTAX Counter64
         MAX-ACCESS  read-only
         STATUS  current
         DESCRIPTION
            "The total number of packets transmitted on queue 3
             for this interface during the selected 15-minute interval."
         ::= { adGenEth15MinIntervalHCEntry 13 }

      adGenEth15MinIntervalHCTotalPktsQueue4  OBJECT-TYPE
         SYNTAX Counter64
         MAX-ACCESS  read-only
         STATUS  current
         DESCRIPTION
            "The total number of packets transmitted on queue 4
             for this interface during the selected 15-minute interval."
         ::= { adGenEth15MinIntervalHCEntry 14 }

      adGenEth15MinIntervalHCTotalPktsQueue5  OBJECT-TYPE
         SYNTAX Counter64
         MAX-ACCESS  read-only
         STATUS  current
         DESCRIPTION
            "The total number of packets transmitted on queue 5
             for this interface during the selected 15-minute interval."
         ::= { adGenEth15MinIntervalHCEntry 15 }

      adGenEth15MinIntervalHCTotalPktsQueue6  OBJECT-TYPE
         SYNTAX Counter64
         MAX-ACCESS  read-only
         STATUS  current
         DESCRIPTION
            "The total number of packets transmitted on queue 6
             for this interface during the selected 15-minute interval."
         ::= { adGenEth15MinIntervalHCEntry 16 }

      adGenEth15MinIntervalHCTotalPktsQueue7  OBJECT-TYPE
         SYNTAX Counter64
         MAX-ACCESS  read-only
         STATUS  current
         DESCRIPTION
            "The total number of packets transmitted on queue 7
             for this interface during the selected 15-minute interval."
         ::= { adGenEth15MinIntervalHCEntry 17 }

      adGenEth15MinIntervalHCOutLcv OBJECT-TYPE
         SYNTAX Counter64
         MAX-ACCESS  read-only
         STATUS  current
         DESCRIPTION
            "The total number of line code violations
                                 that occurred on data received from system interface
             during the selected 15-minute interval."
         ::= { adGenEth15MinIntervalHCEntry 18 }

      adGenEth15MinIntervalHCInLcv OBJECT-TYPE
         SYNTAX Counter64
         MAX-ACCESS  read-only
         STATUS  current
         DESCRIPTION
            "The total number of line code violations
                                 that occurred on data received from line side
             during the selected 15-minute interval."
         ::= { adGenEth15MinIntervalHCEntry 19 }

                adGenEth15MinIntervalHCValidData OBJECT-TYPE
                        SYNTAX  TruthValue
                        MAX-ACCESS  read-only
                        STATUS  current
                        DESCRIPTION
                                "This variable indicates if the data for this
                                 15 minute interval is valid."
                        ::= { adGenEth15MinIntervalHCEntry 20 }

      adGenEth15MinIntervalHCInAvgBitsPerSec OBJECT-TYPE
         SYNTAX Counter64
         MAX-ACCESS  read-only
         STATUS  current
         DESCRIPTION
              "The average number of bits per second received
               on the interface during the selected 15-minute interval."
         ::= { adGenEth15MinIntervalHCEntry 21 }

      adGenEth15MinIntervalHCInAvgPktsPerSec OBJECT-TYPE
         SYNTAX Counter64
         MAX-ACCESS  read-only
         STATUS  current
         DESCRIPTION
              "The average number of packets per second received
               on the interface during the selected 15-minute interval."
         ::= { adGenEth15MinIntervalHCEntry 22 }

       adGenEth15MinIntervalHCOutAvgBitsPerSec OBJECT-TYPE
         SYNTAX Counter64
         MAX-ACCESS  read-only
         STATUS  current
         DESCRIPTION
              "The average number of bits per second sent
               on the interface during the selected 15-minute interval."
         ::= { adGenEth15MinIntervalHCEntry 23 }

      adGenEth15MinIntervalHCOutAvgPktsPerSec OBJECT-TYPE
         SYNTAX Counter64
         MAX-ACCESS  read-only
         STATUS  current
         DESCRIPTION
              "The average number of packets per second sent
               on the interface during the selected 15-minute interval."
         ::= { adGenEth15MinIntervalHCEntry 24 }

--==================================================================================================================

   adGenEth24HrCurrentTable OBJECT-TYPE
      SYNTAX  SEQUENCE OF AdGenEth24HrCurrentEntry
      MAX-ACCESS  not-accessible
      STATUS  current
      DESCRIPTION
         "The Generic Ethernet 24Hr current table."
      ::= { adGenEthIfcPerformance 6 }

   adGenEth24HrCurrentEntry OBJECT-TYPE
      SYNTAX  AdGenEth24HrCurrentEntry
      MAX-ACCESS  not-accessible
      STATUS  current
      DESCRIPTION
         "An entry in the Generic Ethernet 24Hr current table."
      INDEX   { ifIndex }
      ::= { adGenEth24HrCurrentTable 1 }

   AdGenEth24HrCurrentEntry  ::=
      SEQUENCE {
         adGenEth24HrCurrentOutOctets
            Gauge32,
         adGenEth24HrCurrentOutPkts
            Gauge32,
         adGenEth24HrCurrentInOctets
            Gauge32,
         adGenEth24HrCurrentInPkts
            Gauge32,
         adGenEth24HrCurrentInGoodOctets
            Gauge32,
         adGenEth24HrCurrentInGoodPkts
            Gauge32,
         adGenEth24HrCurrentInErrors
            Gauge32,
         adGenEth24HrCurrentInDiscards
            Gauge32,
         adGenEth24HrCurrentInGiants
            Gauge32,
         adGenEth24HrCurrentInRunts
            Gauge32,
         adGenEth24HrCurrentInMulticastPkts
            Gauge32,
         adGenEth24HrCurrentInBroadcastPkts
            Gauge32,
         adGenEth24HrCurrentInUnicastPkts
            Gauge32,
         adGenEth24HrCurrentOutMulticastPkts
            Gauge32,
         adGenEth24HrCurrentOutBroadcastPkts
            Gauge32,
         adGenEth24HrCurrentOutUnicastPkts
            Gauge32,
         adGenEth24HrCurrentDroppedPktsQueue0
            Gauge32,
         adGenEth24HrCurrentDroppedPktsQueue1
            Gauge32,
         adGenEth24HrCurrentDroppedPktsQueue2
            Gauge32,
         adGenEth24HrCurrentDroppedPktsQueue3
            Gauge32,
         adGenEth24HrCurrentDroppedPktsQueue4
            Gauge32,
         adGenEth24HrCurrentDroppedPktsQueue5
            Gauge32,
         adGenEth24HrCurrentDroppedPktsQueue6
            Gauge32,
         adGenEth24HrCurrentDroppedPktsQueue7
            Gauge32,
         adGenEth24HrCurrentOutDiscards
            Gauge32,
         adGenEth24HrCurrentInCRCErrors
            Gauge32,
         adGenEth24HrCurrentInFrameErrors
            Gauge32,
         adGenEth24HrCurrentOutErrors
            Gauge32,

         adGenEth24HrCurrentInPeakUtilization
            Gauge32,
         adGenEth24HrCurrentInAvgUtilization
            Gauge32,
         adGenEth24HrCurrentOutPeakUtilization
            Gauge32,
         adGenEth24HrCurrentOutAvgUtilization
            Gauge32
       }

      adGenEth24HrCurrentOutOctets OBJECT-TYPE
         SYNTAX Gauge32
         MAX-ACCESS  read-only
         STATUS  current
         DESCRIPTION
            "The total number of octets transmitted on the interface during
             the current 24-hour interval, including framing characters."
         ::= { adGenEth24HrCurrentEntry 1 }

      adGenEth24HrCurrentOutPkts OBJECT-TYPE
         SYNTAX Gauge32
         MAX-ACCESS  read-only
         STATUS  current
         DESCRIPTION
            "The total number of packets transmitted on the
             interface during the current 24-hour interval."
         ::= { adGenEth24HrCurrentEntry 2 }

      adGenEth24HrCurrentInOctets OBJECT-TYPE
         SYNTAX Gauge32
         MAX-ACCESS  read-only
         STATUS  current
         DESCRIPTION
            "The total number of octets received on the
             interface during the current 24-hour interval."
         ::= { adGenEth24HrCurrentEntry 3 }

      adGenEth24HrCurrentInPkts OBJECT-TYPE
         SYNTAX Gauge32
         MAX-ACCESS  read-only
         STATUS  current
         DESCRIPTION
            "The total number of packets received on the
             interface during the current 24-hour interval."
         ::= { adGenEth24HrCurrentEntry 4 }

      adGenEth24HrCurrentInGoodOctets OBJECT-TYPE
         SYNTAX Gauge32
         MAX-ACCESS  read-only
         STATUS  current
         DESCRIPTION
            ""
         ::= { adGenEth24HrCurrentEntry 5 }

      adGenEth24HrCurrentInGoodPkts OBJECT-TYPE
         SYNTAX Gauge32
         MAX-ACCESS  read-only
         STATUS  current
         DESCRIPTION
            ""
         ::= { adGenEth24HrCurrentEntry 6 }

      adGenEth24HrCurrentInErrors OBJECT-TYPE
         SYNTAX Gauge32
         MAX-ACCESS  read-only
         STATUS  current
         DESCRIPTION
            "The number of inbound packets that contained errors
             during the current 24-hour interval."
         ::= { adGenEth24HrCurrentEntry 7 }

      adGenEth24HrCurrentInDiscards OBJECT-TYPE
         SYNTAX Gauge32
         MAX-ACCESS  read-only
         STATUS  current
         DESCRIPTION
            "The number of inbound packets which were chosen to be discarded
             during the current 24-hour interval even though no errors had
             been detected.  One reason for discarding such a packet could
             be congestion."
         ::= { adGenEth24HrCurrentEntry 8 }

      adGenEth24HrCurrentInGiants OBJECT-TYPE
         SYNTAX Gauge32
         MAX-ACCESS  read-only
         STATUS  current
         DESCRIPTION
            "The number of packets received during the current 24-hour
             interval which were larger than the maximum packet size."
         ::= { adGenEth24HrCurrentEntry 9 }

      adGenEth24HrCurrentInRunts OBJECT-TYPE
         SYNTAX Gauge32
         MAX-ACCESS  read-only
         STATUS  current
         DESCRIPTION
            "The number of packets received during the current 24-hour
             interval which were smaller than the minimum packet size."
         ::= { adGenEth24HrCurrentEntry 10 }

      adGenEth24HrCurrentInMulticastPkts OBJECT-TYPE
         SYNTAX Gauge32
         MAX-ACCESS  read-only
         STATUS  current
         DESCRIPTION
            "The Gauge associated with the number of In Multicast Pkts
             enGaugeed by an interface in the current day."
         ::= { adGenEth24HrCurrentEntry 11 }

      adGenEth24HrCurrentInBroadcastPkts OBJECT-TYPE
         SYNTAX Gauge32
         MAX-ACCESS  read-only
         STATUS  current
         DESCRIPTION
            "The total number of broadcast packets received
             during the current 24-hour interval."
         ::= { adGenEth24HrCurrentEntry 12 }

      adGenEth24HrCurrentInUnicastPkts OBJECT-TYPE
         SYNTAX Gauge32
         MAX-ACCESS  read-only
         STATUS  current
         DESCRIPTION
            "The total number of unicast packets received
             during the current 24-hour interval."
         ::= { adGenEth24HrCurrentEntry 13 }

      adGenEth24HrCurrentOutMulticastPkts OBJECT-TYPE
         SYNTAX Gauge32
         MAX-ACCESS  read-only
         STATUS  current
         DESCRIPTION
            "The total number of multicast packets transmitted
             during the current 24-hour interval."
         ::= { adGenEth24HrCurrentEntry 14 }

      adGenEth24HrCurrentOutBroadcastPkts OBJECT-TYPE
         SYNTAX Gauge32
         MAX-ACCESS  read-only
         STATUS  current
         DESCRIPTION
            "The total number of broadcast packets transmitted
             during the current 24-hour interval."
         ::= { adGenEth24HrCurrentEntry 15 }

      adGenEth24HrCurrentOutUnicastPkts OBJECT-TYPE
         SYNTAX Gauge32
         MAX-ACCESS  read-only
         STATUS  current
         DESCRIPTION
            "The total number of unicast packets transmitted
             during the current 24-hour interval."
         ::= { adGenEth24HrCurrentEntry 16 }

     adGenEth24HrCurrentDroppedPktsQueue0  OBJECT-TYPE
         SYNTAX Gauge32
         MAX-ACCESS  read-only
         STATUS  current
         DESCRIPTION
             "The number of dropped packets on queue 0
              during the current 24-hour interval."
         ::= { adGenEth24HrCurrentEntry 17 }

      adGenEth24HrCurrentDroppedPktsQueue1  OBJECT-TYPE
         SYNTAX Gauge32
         MAX-ACCESS  read-only
         STATUS  current
         DESCRIPTION
             "The number of dropped packets on queue 1
              during the current 24-hour interval."
         ::= { adGenEth24HrCurrentEntry 18 }

      adGenEth24HrCurrentDroppedPktsQueue2  OBJECT-TYPE
         SYNTAX Gauge32
         MAX-ACCESS  read-only
         STATUS  current
         DESCRIPTION
             "The number of dropped packets on queue 2
              during the current 24-hour interval."
         ::= { adGenEth24HrCurrentEntry 19 }

      adGenEth24HrCurrentDroppedPktsQueue3  OBJECT-TYPE
         SYNTAX Gauge32
         MAX-ACCESS  read-only
         STATUS  current
         DESCRIPTION
             "The number of dropped packets on queue 3
              during the current 24-hour interval."
         ::= { adGenEth24HrCurrentEntry 20 }

      adGenEth24HrCurrentDroppedPktsQueue4  OBJECT-TYPE
         SYNTAX Gauge32
         MAX-ACCESS  read-only
         STATUS  current
         DESCRIPTION
             "The number of dropped packets on queue 4
              during the current 24-hour interval."
         ::= { adGenEth24HrCurrentEntry 21 }

      adGenEth24HrCurrentDroppedPktsQueue5  OBJECT-TYPE
         SYNTAX Gauge32
         MAX-ACCESS  read-only
         STATUS  current
         DESCRIPTION
             "The number of dropped packets on queue 5
              during the current 24-hour interval."
         ::= { adGenEth24HrCurrentEntry 22 }

      adGenEth24HrCurrentDroppedPktsQueue6  OBJECT-TYPE
         SYNTAX Gauge32
         MAX-ACCESS  read-only
         STATUS  current
         DESCRIPTION
             "The number of dropped packets on queue 6
              during the current 24-hour interval."
         ::= { adGenEth24HrCurrentEntry 23 }

      adGenEth24HrCurrentDroppedPktsQueue7  OBJECT-TYPE
         SYNTAX Gauge32
         MAX-ACCESS  read-only
         STATUS  current
         DESCRIPTION
             "The number of dropped packets on queue 7
              during the current 24-hour interval."
         ::= { adGenEth24HrCurrentEntry 24 }

      adGenEth24HrCurrentOutDiscards OBJECT-TYPE
         SYNTAX Gauge32
         MAX-ACCESS  read-only
         STATUS  current
         DESCRIPTION
             "The total number of discarded packets transmitted on this
              interface during the current 24-hour interval."
         ::= { adGenEth24HrCurrentEntry 25 }

      adGenEth24HrCurrentInCRCErrors OBJECT-TYPE
         SYNTAX Gauge32
         MAX-ACCESS  read-only
         STATUS  current
         DESCRIPTION
             "The total number of packets with CRC errors received on this
              interface during the current 24-hour interval."
         ::= { adGenEth24HrCurrentEntry 26 }

      adGenEth24HrCurrentInFrameErrors OBJECT-TYPE
         SYNTAX Gauge32
         MAX-ACCESS  read-only
         STATUS  current
         DESCRIPTION
             "The total number of packets with frame errors received on this
              interface during the current 24-hour interval."
         ::= { adGenEth24HrCurrentEntry 27 }

      adGenEth24HrCurrentOutErrors OBJECT-TYPE
         SYNTAX Gauge32
         MAX-ACCESS  read-only
         STATUS  current
         DESCRIPTION
             "The total number of packets with errors transmitted on this
              interface during the current 24-hour interval."
         ::= { adGenEth24HrCurrentEntry 28 }

      adGenEth24HrCurrentInPeakUtilization OBJECT-TYPE
         SYNTAX  Gauge32
         MAX-ACCESS  read-only
         STATUS  current
         DESCRIPTION
             "The maximum usage of the ingress link (in whole percent)
              during the current 24-hour interval."
         ::= { adGenEth24HrCurrentEntry 29 }

      adGenEth24HrCurrentInAvgUtilization OBJECT-TYPE
         SYNTAX  Gauge32
         MAX-ACCESS  read-only
         STATUS  current
         DESCRIPTION
             "The average percent usage of the ingress link
              during the current 24-hour interval."
         ::= { adGenEth24HrCurrentEntry 30 }

      adGenEth24HrCurrentOutPeakUtilization OBJECT-TYPE
         SYNTAX  Gauge32
         MAX-ACCESS  read-only
         STATUS  current
         DESCRIPTION
             "The maximum usage of the egress link (in whole percent)
              during the current 24-hour interval."
         ::= { adGenEth24HrCurrentEntry 31 }

      adGenEth24HrCurrentOutAvgUtilization OBJECT-TYPE
         SYNTAX  Gauge32
         MAX-ACCESS  read-only
         STATUS  current
         DESCRIPTION
             "The average percent usage of the egress link
              during the current 24-hour interval."
         ::= { adGenEth24HrCurrentEntry 32 }


--==================================================================================================================


   adGenEth24HrCurrentHCTable OBJECT-TYPE
      SYNTAX  SEQUENCE OF AdGenEth24HrCurrentHCEntry
      MAX-ACCESS  not-accessible
      STATUS  current
      DESCRIPTION
         "The Generic Ethernet 24Hr current high-capacity table."
      ::= { adGenEthIfcPerformance 7 }

   adGenEth24HrCurrentHCEntry OBJECT-TYPE
      SYNTAX  AdGenEth24HrCurrentHCEntry
      MAX-ACCESS  not-accessible
      STATUS  current
      DESCRIPTION
         "An entry in the Generic Ethernet 24Hr current high-capacity table."
      INDEX   { ifIndex }
      ::= { adGenEth24HrCurrentHCTable 1 }

   AdGenEth24HrCurrentHCEntry  ::=
      SEQUENCE {
         adGenEth24HrCurrentHCOutOctets
            Counter64,
         adGenEth24HrCurrentHCInOctets
            Counter64,
         adGenEth24HrCurrentHCInMulticastPkts
            Counter64,
         adGenEth24HrCurrentHCInBroadcastPkts
            Counter64,
         adGenEth24HrCurrentHCInUnicastPkts
            Counter64,
         adGenEth24HrCurrentHCOutMulticastPkts
            Counter64,
         adGenEth24HrCurrentHCOutBroadcastPkts
            Counter64,
         adGenEth24HrCurrentHCOutUnicastPkts
            Counter64,
         adGenEth24HrCurrentHCTotalPktsQueue0
            Counter64,
         adGenEth24HrCurrentHCTotalPktsQueue1
            Counter64,
         adGenEth24HrCurrentHCTotalPktsQueue2
            Counter64,
         adGenEth24HrCurrentHCTotalPktsQueue3
            Counter64,
         adGenEth24HrCurrentHCTotalPktsQueue4
            Counter64,
         adGenEth24HrCurrentHCTotalPktsQueue5
            Counter64,
         adGenEth24HrCurrentHCTotalPktsQueue6
            Counter64,
         adGenEth24HrCurrentHCTotalPktsQueue7
            Counter64,
         adGenEth24HrCurrentHCOutLcv
            Counter64,
         adGenEth24HrCurrentHCInLcv
            Counter64,
         adGenEth24HrCurrentHCInAvgBitsPerSec
            Counter64,
         adGenEth24HrCurrentHCInAvgPktsPerSec
            Counter64,
         adGenEth24HrCurrentHCOutAvgBitsPerSec
            Counter64,
         adGenEth24HrCurrentHCOutAvgPktsPerSec
            Counter64
       }

      adGenEth24HrCurrentHCOutOctets OBJECT-TYPE
         SYNTAX Counter64
         MAX-ACCESS  read-only
         STATUS  current
         DESCRIPTION
            "The total number of octets transmitted on the interface
             during the current 24-hour interval, including framing characters.
             This object is a 64-bit version of adGenEth24HrCurrentOutOctets."
         ::= { adGenEth24HrCurrentHCEntry 1 }

      adGenEth24HrCurrentHCInOctets OBJECT-TYPE
         SYNTAX Counter64
         MAX-ACCESS  read-only
         STATUS  current
         DESCRIPTION
            "The total number of octets received on the interface
             during the current 24-hour interval, including framing characters.
             This object is a 64-bit version of adGenEth24HrCurrentInOctets."
         ::= { adGenEth24HrCurrentHCEntry 2 }

      adGenEth24HrCurrentHCInMulticastPkts OBJECT-TYPE
         SYNTAX Counter64
         MAX-ACCESS  read-only
         STATUS  current
         DESCRIPTION
            "The total number of multicast packets received on this
             interface during the current 24-hour interval.  This object
             is a 64-bit version of adGenEth24HrCurrentInMulticastPkts."
         ::= { adGenEth24HrCurrentHCEntry 3 }

      adGenEth24HrCurrentHCInBroadcastPkts OBJECT-TYPE
         SYNTAX Counter64
         MAX-ACCESS  read-only
         STATUS  current
         DESCRIPTION
            "The total number of broadcast packets received on this
             interface during the current 24-hour interval.  This object
             is a 64-bit version of adGenEth24HrCurrentInBroadcastPkts."
         ::= { adGenEth24HrCurrentHCEntry 4 }

      adGenEth24HrCurrentHCInUnicastPkts OBJECT-TYPE
         SYNTAX Counter64
         MAX-ACCESS  read-only
         STATUS  current
         DESCRIPTION
            "The total number of unicast packets received on this
             interface during the current 24-hour interval.  This object
             is a 64-bit version of adGenEth24HrCurrentInUnicastPkts."
         ::= { adGenEth24HrCurrentHCEntry 5 }

      adGenEth24HrCurrentHCOutMulticastPkts OBJECT-TYPE
         SYNTAX Counter64
         MAX-ACCESS  read-only
         STATUS  current
         DESCRIPTION
            "The total number of multicast packets transmitted on this
             interface during the current 24-hour interval.  This object
             is a 64-bit version of adGenEth24HrCurrentOutMulticastPkts."
         ::= { adGenEth24HrCurrentHCEntry 6 }

      adGenEth24HrCurrentHCOutBroadcastPkts OBJECT-TYPE
         SYNTAX Counter64
         MAX-ACCESS  read-only
         STATUS  current
         DESCRIPTION
            "The total number of broadcast packets transmitted on this
             interface during the current 24-hour interval.  This object
             is a 64-bit version of adGenEth24HrCurrentOutBroadcastPkts."
         ::= { adGenEth24HrCurrentHCEntry 7 }

      adGenEth24HrCurrentHCOutUnicastPkts OBJECT-TYPE
         SYNTAX Counter64
         MAX-ACCESS  read-only
         STATUS  current
         DESCRIPTION
            "The total number of unicast packets transmitted on this
             interface during the current 24-hour interval.  This object
             is a 64-bit version of adGenEth24HrCurrentOutUnicastPkts."
         ::= { adGenEth24HrCurrentHCEntry 8 }

      adGenEth24HrCurrentHCTotalPktsQueue0  OBJECT-TYPE
         SYNTAX  Counter64
         MAX-ACCESS  read-only
         STATUS current
         DESCRIPTION
             "The total number of packets transmitted on queue 0
              for this interface during the current 24-hour interval."
         ::= { adGenEth24HrCurrentHCEntry 9 }

      adGenEth24HrCurrentHCTotalPktsQueue1  OBJECT-TYPE
         SYNTAX  Counter64
         MAX-ACCESS  read-only
         STATUS current
         DESCRIPTION
             "The total number of packets transmitted on queue 1
              for this interface during the current 24-hour interval."
         ::= { adGenEth24HrCurrentHCEntry 10 }

      adGenEth24HrCurrentHCTotalPktsQueue2  OBJECT-TYPE
         SYNTAX  Counter64
         MAX-ACCESS  read-only
         STATUS current
         DESCRIPTION
             "The total number of packets transmitted on queue 2
              for this interface during the current 24-hour interval."
         ::= { adGenEth24HrCurrentHCEntry 11 }

      adGenEth24HrCurrentHCTotalPktsQueue3  OBJECT-TYPE
         SYNTAX  Counter64
         MAX-ACCESS  read-only
         STATUS current
         DESCRIPTION
             "The total number of packets transmitted on queue 3
              for this interface during the current 24-hour interval."
         ::= { adGenEth24HrCurrentHCEntry 12 }

      adGenEth24HrCurrentHCTotalPktsQueue4  OBJECT-TYPE
         SYNTAX  Counter64
         MAX-ACCESS  read-only
         STATUS current
         DESCRIPTION
             "The total number of packets transmitted on queue 4
              for this interface during the current 24-hour interval."
         ::= { adGenEth24HrCurrentHCEntry 13 }

      adGenEth24HrCurrentHCTotalPktsQueue5  OBJECT-TYPE
         SYNTAX  Counter64
         MAX-ACCESS  read-only
         STATUS current
         DESCRIPTION
             "The total number of packets transmitted on queue 5
              for this interface during the current 24-hour interval."
         ::= { adGenEth24HrCurrentHCEntry 14 }

      adGenEth24HrCurrentHCTotalPktsQueue6  OBJECT-TYPE
         SYNTAX  Counter64
         MAX-ACCESS  read-only
         STATUS current
         DESCRIPTION
             "The total number of packets transmitted on queue 6
              for this interface during the current 24-hour interval."
         ::= { adGenEth24HrCurrentHCEntry 15 }

      adGenEth24HrCurrentHCTotalPktsQueue7  OBJECT-TYPE
         SYNTAX  Counter64
         MAX-ACCESS  read-only
         STATUS current
         DESCRIPTION
             "The total number of packets transmitted on queue 7
              for this interface during the current 24-hour interval."
         ::= { adGenEth24HrCurrentHCEntry 16 }

      adGenEth24HrCurrentHCOutLcv OBJECT-TYPE
         SYNTAX Counter64
         MAX-ACCESS  read-only
         STATUS  current
         DESCRIPTION
            "The total number of line code violations
                                 that occurred on data received from system interface
             during the current 24-hour interval."
         ::= { adGenEth24HrCurrentHCEntry 17 }

      adGenEth24HrCurrentHCInLcv OBJECT-TYPE
         SYNTAX Counter64
         MAX-ACCESS  read-only
         STATUS  current
         DESCRIPTION
            "The total number of line code violations
                                 that occurred on data received from line side
             during the current 24-hour interval."
         ::= { adGenEth24HrCurrentHCEntry 18 }

      adGenEth24HrCurrentHCInAvgBitsPerSec OBJECT-TYPE
         SYNTAX Counter64
         MAX-ACCESS  read-only
         STATUS  current
         DESCRIPTION
              "The average number of bits per second received
               on the interface during the current 24-hour interval."
         ::= { adGenEth24HrCurrentHCEntry 19 }

      adGenEth24HrCurrentHCInAvgPktsPerSec OBJECT-TYPE
         SYNTAX Counter64
         MAX-ACCESS  read-only
         STATUS  current
         DESCRIPTION
              "The average number of packets per second received
               on the interface during the current 24-hour interval."
         ::= { adGenEth24HrCurrentHCEntry 20 }

       adGenEth24HrCurrentHCOutAvgBitsPerSec OBJECT-TYPE
         SYNTAX Counter64
         MAX-ACCESS  read-only
         STATUS  current
         DESCRIPTION
              "The average number of bits per second sent
               on the interface during the current 24-hour interval."
         ::= { adGenEth24HrCurrentHCEntry 21 }

      adGenEth24HrCurrentHCOutAvgPktsPerSec OBJECT-TYPE
         SYNTAX Counter64
         MAX-ACCESS  read-only
         STATUS  current
         DESCRIPTION
              "The average number of packets per second sent
               on the interface during the current 24-hour interval."
         ::= { adGenEth24HrCurrentHCEntry 22 }

--==================================================================================================================

   adGenEth24HrIntervalTable OBJECT-TYPE
      SYNTAX  SEQUENCE OF AdGenEth24HrIntervalEntry
      MAX-ACCESS  not-accessible
      STATUS  current
      DESCRIPTION
         "The Generic Ethernet 24Hr interval table."
      ::= { adGenEthIfcPerformance 8 }

   adGenEth24HrIntervalEntry OBJECT-TYPE
      SYNTAX  AdGenEth24HrIntervalEntry
      MAX-ACCESS  not-accessible
      STATUS  current
      DESCRIPTION
         "An entry in the Generic Ethernet 24Hr interval table."
      INDEX   { ifIndex, adGenEth24HrIntervalNumber }
      ::= { adGenEth24HrIntervalTable 1 }

   AdGenEth24HrIntervalEntry  ::=
      SEQUENCE {
         adGenEth24HrIntervalNumber
            Integer32,
         adGenEth24HrIntervalOutOctets
            Gauge32,
         adGenEth24HrIntervalOutPkts
            Gauge32,
         adGenEth24HrIntervalInOctets
            Gauge32,
         adGenEth24HrIntervalInPkts
            Gauge32,
         adGenEth24HrIntervalInGoodOctets
            Gauge32,
         adGenEth24HrIntervalInGoodPkts
            Gauge32,
         adGenEth24HrIntervalInErrors
            Gauge32,
         adGenEth24HrIntervalInDiscards
            Gauge32,
         adGenEth24HrIntervalInGiants
            Gauge32,
         adGenEth24HrIntervalInRunts
            Gauge32,
         adGenEth24HrIntervalInMulticastPkts
            Gauge32,
         adGenEth24HrIntervalInBroadcastPkts
            Gauge32,
         adGenEth24HrIntervalInUnicastPkts
            Gauge32,
         adGenEth24HrIntervalOutMulticastPkts
            Gauge32,
         adGenEth24HrIntervalOutBroadcastPkts
            Gauge32,
         adGenEth24HrIntervalOutUnicastPkts
            Gauge32,
         adGenEth24HrIntervalDroppedPktsQueue0
            Gauge32,
         adGenEth24HrIntervalDroppedPktsQueue1
            Gauge32,
         adGenEth24HrIntervalDroppedPktsQueue2
            Gauge32,
         adGenEth24HrIntervalDroppedPktsQueue3
            Gauge32,
         adGenEth24HrIntervalDroppedPktsQueue4
            Gauge32,
         adGenEth24HrIntervalDroppedPktsQueue5
            Gauge32,
         adGenEth24HrIntervalDroppedPktsQueue6
            Gauge32,
         adGenEth24HrIntervalDroppedPktsQueue7
            Gauge32,
         adGenEth24HrIntervalOutDiscards
            Gauge32,
         adGenEth24HrIntervalInCRCErrors
            Gauge32,
         adGenEth24HrIntervalInFrameErrors
            Gauge32,
         adGenEth24HrIntervalOutErrors
            Gauge32,

         adGenEth24HrIntervalInPeakUtilization
            Gauge32,
         adGenEth24HrIntervalInAvgUtilization
            Gauge32,
         adGenEth24HrIntervalOutPeakUtilization
            Gauge32,
         adGenEth24HrIntervalOutAvgUtilization
            Gauge32
       }

      adGenEth24HrIntervalNumber OBJECT-TYPE
         SYNTAX  Integer32
         MAX-ACCESS  read-only
         STATUS  current
         DESCRIPTION
            "A number between 1 and 7, where 1 is the most recently
             completed day and 7 is the least recently completed
             day (assuming that all 7 days are valid)."
         ::= { adGenEth24HrIntervalEntry 1 }

      adGenEth24HrIntervalOutOctets OBJECT-TYPE
         SYNTAX Gauge32
         MAX-ACCESS  read-only
         STATUS  current
         DESCRIPTION
            "The total number of octets transmitted on the interface
             during the selected 24-hour interval, including framing characters."
         ::= { adGenEth24HrIntervalEntry 2 }

      adGenEth24HrIntervalOutPkts OBJECT-TYPE
         SYNTAX Gauge32
         MAX-ACCESS  read-only
         STATUS  current
         DESCRIPTION
            "The total number of packets transmitted on the
             interface during the selected 24-hour interval."
         ::= { adGenEth24HrIntervalEntry 3 }

      adGenEth24HrIntervalInOctets OBJECT-TYPE
         SYNTAX Gauge32
         MAX-ACCESS  read-only
         STATUS  current
         DESCRIPTION
            "The total number of octets received on the interface
             during the selected 24-hour interval, including framing characters."
         ::= { adGenEth24HrIntervalEntry 4 }

      adGenEth24HrIntervalInPkts OBJECT-TYPE
         SYNTAX Gauge32
         MAX-ACCESS  read-only
         STATUS  current
         DESCRIPTION
            "The total number of packets received on the
             interface during the selected 24-hour interval."
         ::= { adGenEth24HrIntervalEntry 5 }

      adGenEth24HrIntervalInGoodOctets OBJECT-TYPE
         SYNTAX Gauge32
         MAX-ACCESS  read-only
         STATUS  current
         DESCRIPTION
            ""
         ::= { adGenEth24HrIntervalEntry 6 }

      adGenEth24HrIntervalInGoodPkts OBJECT-TYPE
         SYNTAX Gauge32
         MAX-ACCESS  read-only
         STATUS  current
         DESCRIPTION
            ""
         ::= { adGenEth24HrIntervalEntry 7 }

      adGenEth24HrIntervalInErrors OBJECT-TYPE
         SYNTAX Gauge32
         MAX-ACCESS  read-only
         STATUS  current
         DESCRIPTION
            "The number of inbound packets that contained errors
             during the selected 24-hour interval."
         ::= { adGenEth24HrIntervalEntry 8 }

      adGenEth24HrIntervalInDiscards OBJECT-TYPE
         SYNTAX Gauge32
         MAX-ACCESS  read-only
         STATUS  current
         DESCRIPTION
            "The number of inbound packets which were chosen to be discarded
             during the selected 24-hour interval even though no errors had
             been detected.  One reason for discarding such a packet could
             be congestion."
         ::= { adGenEth24HrIntervalEntry 9 }

      adGenEth24HrIntervalInGiants OBJECT-TYPE
         SYNTAX Gauge32
         MAX-ACCESS  read-only
         STATUS  current
         DESCRIPTION
            "The number of packets received during the selected 24-hour
             interval which were larger than the maximum packet size."
         ::= { adGenEth24HrIntervalEntry 10 }

      adGenEth24HrIntervalInRunts OBJECT-TYPE
         SYNTAX Gauge32
         MAX-ACCESS  read-only
         STATUS  current
         DESCRIPTION
            "The number of packets received during the selected 24-hour
             interval which were smaller than the minimum packet size."
         ::= { adGenEth24HrIntervalEntry 11 }

      adGenEth24HrIntervalInMulticastPkts OBJECT-TYPE
         SYNTAX Gauge32
         MAX-ACCESS  read-only
         STATUS  current
         DESCRIPTION
            "The total number of multicast packets received on this
             interface during the selected 24-hour interval."
         ::= { adGenEth24HrIntervalEntry 12 }

      adGenEth24HrIntervalInBroadcastPkts OBJECT-TYPE
         SYNTAX Gauge32
         MAX-ACCESS  read-only
         STATUS  current
         DESCRIPTION
            "The total number of broadcast packets received on this
             interface during the selected 24-hour interval."
         ::= { adGenEth24HrIntervalEntry 13 }

      adGenEth24HrIntervalInUnicastPkts OBJECT-TYPE
         SYNTAX Gauge32
         MAX-ACCESS  read-only
         STATUS  current
         DESCRIPTION
            "The total number of unicast packets received on this
             interface during the selected 24-hour interval."
         ::= { adGenEth24HrIntervalEntry 14 }

      adGenEth24HrIntervalOutMulticastPkts OBJECT-TYPE
         SYNTAX Gauge32
         MAX-ACCESS  read-only
         STATUS  current
         DESCRIPTION
            "The total number of multicast packets transmitted on
             this interface during the selected 24-hour interval."
         ::= { adGenEth24HrIntervalEntry 15 }

      adGenEth24HrIntervalOutBroadcastPkts OBJECT-TYPE
         SYNTAX Gauge32
         MAX-ACCESS  read-only
         STATUS  current
         DESCRIPTION
            "The total number of broadcast packets transmitted on
             this interface during the selected 24-hour interval."
         ::= { adGenEth24HrIntervalEntry 16 }

      adGenEth24HrIntervalOutUnicastPkts OBJECT-TYPE
         SYNTAX Gauge32
         MAX-ACCESS  read-only
         STATUS  current
         DESCRIPTION
            "The total number of unicast packets transmitted on
             this interface during the selected 24-hour interval."
         ::= { adGenEth24HrIntervalEntry 17 }

      adGenEth24HrIntervalDroppedPktsQueue0  OBJECT-TYPE
         SYNTAX  Gauge32
         MAX-ACCESS  read-only
         STATUS  current
         DESCRIPTION
             "The number of dropped packets for queue 0 on this
              interface during the selected 24-hour interval."
         ::= { adGenEth24HrIntervalEntry 18 }

      adGenEth24HrIntervalDroppedPktsQueue1  OBJECT-TYPE
         SYNTAX  Gauge32
         MAX-ACCESS  read-only
         STATUS  current
         DESCRIPTION
             "The number of dropped packets for queue 1 on this
              interface during the selected 24-hour interval."
         ::= { adGenEth24HrIntervalEntry 19 }

      adGenEth24HrIntervalDroppedPktsQueue2  OBJECT-TYPE
         SYNTAX  Gauge32
         MAX-ACCESS  read-only
         STATUS  current
         DESCRIPTION
             "The number of dropped packets for queue 2 on this
              interface during the selected 24-hour interval."
         ::= { adGenEth24HrIntervalEntry 20 }

      adGenEth24HrIntervalDroppedPktsQueue3  OBJECT-TYPE
         SYNTAX  Gauge32
         MAX-ACCESS  read-only
         STATUS  current
         DESCRIPTION
             "The number of dropped packets for queue 3 on this
              interface during the selected 24-hour interval."
         ::= { adGenEth24HrIntervalEntry 21 }

      adGenEth24HrIntervalDroppedPktsQueue4  OBJECT-TYPE
         SYNTAX  Gauge32
         MAX-ACCESS  read-only
         STATUS  current
         DESCRIPTION
             "The number of dropped packets for queue 4 on this
              interface during the selected 24-hour interval."
         ::= { adGenEth24HrIntervalEntry 22 }

      adGenEth24HrIntervalDroppedPktsQueue5  OBJECT-TYPE
         SYNTAX  Gauge32
         MAX-ACCESS  read-only
         STATUS  current
         DESCRIPTION
             "The number of dropped packets for queue 5 on this
              interface during the selected 24-hour interval."
         ::= { adGenEth24HrIntervalEntry 23 }

      adGenEth24HrIntervalDroppedPktsQueue6  OBJECT-TYPE
         SYNTAX  Gauge32
         MAX-ACCESS  read-only
         STATUS  current
         DESCRIPTION
             "The number of dropped packets for queue 6 on this
              interface during the selected 24-hour interval."
         ::= { adGenEth24HrIntervalEntry 24 }

      adGenEth24HrIntervalDroppedPktsQueue7  OBJECT-TYPE
         SYNTAX  Gauge32
         MAX-ACCESS  read-only
         STATUS  current
         DESCRIPTION
             "The number of dropped packets for queue 7 on this
              interface during the selected 24-hour interval."
         ::= { adGenEth24HrIntervalEntry 25 }

      adGenEth24HrIntervalOutDiscards OBJECT-TYPE
         SYNTAX Gauge32
         MAX-ACCESS  read-only
         STATUS  current
         DESCRIPTION
             "The total number of discarded packets transmitted on this
              interface during the selected 24-hour interval."
         ::= { adGenEth24HrIntervalEntry 26 }

      adGenEth24HrIntervalInCRCErrors OBJECT-TYPE
         SYNTAX Gauge32
         MAX-ACCESS  read-only
         STATUS  current
         DESCRIPTION
             "The total number of packets with CRC errors received on this
              interface during the selected 24-hour interval."
         ::= { adGenEth24HrIntervalEntry 27 }

      adGenEth24HrIntervalInFrameErrors OBJECT-TYPE
         SYNTAX Gauge32
         MAX-ACCESS  read-only
         STATUS  current
         DESCRIPTION
             "The total number of packets with frame errors received on this
              interface during the selected 24-hour interval."
         ::= { adGenEth24HrIntervalEntry 28 }

      adGenEth24HrIntervalOutErrors OBJECT-TYPE
         SYNTAX Gauge32
         MAX-ACCESS  read-only
         STATUS  current
         DESCRIPTION
             "The total number of packets with errors transmitted on this
              interface during the selected 24-hour interval."
         ::= { adGenEth24HrIntervalEntry 29 }

      adGenEth24HrIntervalInPeakUtilization OBJECT-TYPE
         SYNTAX  Gauge32
         MAX-ACCESS  read-only
         STATUS  current
         DESCRIPTION
             "The maximum usage of the ingress link (in whole percent)
              during the selected 24-hour interval."
         ::= { adGenEth24HrIntervalEntry 30 }

      adGenEth24HrIntervalInAvgUtilization OBJECT-TYPE
         SYNTAX  Gauge32
         MAX-ACCESS  read-only
         STATUS  current
         DESCRIPTION
             "The average percent usage of the ingress link
              during the selected 24-hour interval."
         ::= { adGenEth24HrIntervalEntry 31 }

      adGenEth24HrIntervalOutPeakUtilization OBJECT-TYPE
         SYNTAX  Gauge32
         MAX-ACCESS  read-only
         STATUS  current
         DESCRIPTION
             "The maximum usage of the egress link (in whole percent)
              during the selected 24-hour interval."
         ::= { adGenEth24HrIntervalEntry 32 }

      adGenEth24HrIntervalOutAvgUtilization OBJECT-TYPE
         SYNTAX  Gauge32
         MAX-ACCESS  read-only
         STATUS  current
         DESCRIPTION
             "The average percent usage of the egress link
              during the selected 24-hour interval."
         ::= { adGenEth24HrIntervalEntry 33 }

--==================================================================================================================


   adGenEth24HrIntervalHCTable OBJECT-TYPE
      SYNTAX  SEQUENCE OF AdGenEth24HrIntervalHCEntry
      MAX-ACCESS  not-accessible
      STATUS  current
      DESCRIPTION
         "The Generic Ethernet 24Hr interval high-capacity table."
      ::= { adGenEthIfcPerformance 9 }

   adGenEth24HrIntervalHCEntry OBJECT-TYPE
      SYNTAX  AdGenEth24HrIntervalHCEntry
      MAX-ACCESS  not-accessible
      STATUS  current
      DESCRIPTION
         "An entry in the Generic Ethernet 24Hr interval hig-capacity table."
      INDEX   { ifIndex, adGenEth24HrIntervalHCNumber }
      ::= { adGenEth24HrIntervalHCTable 1 }

   AdGenEth24HrIntervalHCEntry  ::=
      SEQUENCE {
         adGenEth24HrIntervalHCNumber
            Integer32,
         adGenEth24HrIntervalHCOutOctets
            Counter64,
         adGenEth24HrIntervalHCInOctets
            Counter64,
         adGenEth24HrIntervalHCInMulticastPkts
            Counter64,
         adGenEth24HrIntervalHCInBroadcastPkts
            Counter64,
         adGenEth24HrIntervalHCInUnicastPkts
            Counter64,
         adGenEth24HrIntervalHCOutMulticastPkts
            Counter64,
         adGenEth24HrIntervalHCOutBroadcastPkts
            Counter64,
         adGenEth24HrIntervalHCOutUnicastPkts
            Counter64,
         adGenEth24HrIntervalHCTotalPktsQueue0
            Counter64,
         adGenEth24HrIntervalHCTotalPktsQueue1
            Counter64,
         adGenEth24HrIntervalHCTotalPktsQueue2
            Counter64,
         adGenEth24HrIntervalHCTotalPktsQueue3
            Counter64,
         adGenEth24HrIntervalHCTotalPktsQueue4
            Counter64,
         adGenEth24HrIntervalHCTotalPktsQueue5
            Counter64,
         adGenEth24HrIntervalHCTotalPktsQueue6
            Counter64,
         adGenEth24HrIntervalHCTotalPktsQueue7
            Counter64,
         adGenEth24HrIntervalHCOutLcv
            Counter64,
         adGenEth24HrIntervalHCInLcv
            Counter64,
         adGenEth24HrIntervalHCValidData
            TruthValue,
         adGenEth24HrIntervalHCInAvgBitsPerSec
            Counter64,
         adGenEth24HrIntervalHCInAvgPktsPerSec
            Counter64,
         adGenEth24HrIntervalHCOutAvgBitsPerSec
            Counter64,
         adGenEth24HrIntervalHCOutAvgPktsPerSec
            Counter64
       }

      adGenEth24HrIntervalHCNumber OBJECT-TYPE
         SYNTAX  Integer32
         MAX-ACCESS  read-only
         STATUS  current
         DESCRIPTION
            "A number between 1 and 7, where 1 is the most recently
             completed day and 7 is the least recently completed
             day (assuming that all 7 days are valid)."
         ::= { adGenEth24HrIntervalHCEntry 1 }

      adGenEth24HrIntervalHCOutOctets OBJECT-TYPE
         SYNTAX Counter64
         MAX-ACCESS  read-only
         STATUS  current
         DESCRIPTION
            "The total number of octets transmitted on the interface
             during the selected 24-hour interval, including framing characters.
             This object is a 64-bit version of adGenEth24HrIntervalOutOctets."
         ::= { adGenEth24HrIntervalHCEntry 2 }

      adGenEth24HrIntervalHCInOctets OBJECT-TYPE
         SYNTAX Counter64
         MAX-ACCESS  read-only
         STATUS  current
         DESCRIPTION
            "The total number of octets received on the interface
             during the selected 24-hour interval, including framing characters.
             This object is a 64-bit version of adGenEth24HrIntervalInOctets."
         ::= { adGenEth24HrIntervalHCEntry 3 }

      adGenEth24HrIntervalHCInMulticastPkts OBJECT-TYPE
         SYNTAX Counter64
         MAX-ACCESS  read-only
         STATUS  current
         DESCRIPTION
            "The total number of multicast packets received on this
             interface during the selected 24-hour interval.  This object
             is a 64-bit version of adGenEth24HrIntervalInMulticastPkts."
         ::= { adGenEth24HrIntervalHCEntry 4 }

      adGenEth24HrIntervalHCInBroadcastPkts OBJECT-TYPE
         SYNTAX Counter64
         MAX-ACCESS  read-only
         STATUS  current
         DESCRIPTION
            "The total number of broadcast packets received on this
             interface during the selected 24-hour interval.  This object
             is a 64-bit version of adGenEth24HrIntervalInBroadcastPkts."
         ::= { adGenEth24HrIntervalHCEntry 5 }

      adGenEth24HrIntervalHCInUnicastPkts OBJECT-TYPE
         SYNTAX Counter64
         MAX-ACCESS  read-only
         STATUS  current
         DESCRIPTION
            "The total number of unicast packets received on this
             interface during the selected 24-hour interval.  This object
             is a 64-bit version of adGenEth24HrIntervalInUnicastPkts."
         ::= { adGenEth24HrIntervalHCEntry 6 }

      adGenEth24HrIntervalHCOutMulticastPkts OBJECT-TYPE
         SYNTAX Counter64
         MAX-ACCESS  read-only
         STATUS  current
         DESCRIPTION
            "The total number of multicast packets transmitted on this
             interface during the selected 24-hour interval.  This object
             is a 64-bit version of adGenEth24HrIntervalOutMulticastPkts."
         ::= { adGenEth24HrIntervalHCEntry 7 }

      adGenEth24HrIntervalHCOutBroadcastPkts OBJECT-TYPE
         SYNTAX Counter64
         MAX-ACCESS  read-only
         STATUS  current
         DESCRIPTION
            "The total number of broadcast packets transmitted on this
             interface during the selected 24-hour interval.  This object
             is a 64-bit version of adGenEth24HrIntervalOutBroadcastPkts."
         ::= { adGenEth24HrIntervalHCEntry 8 }

      adGenEth24HrIntervalHCOutUnicastPkts OBJECT-TYPE
         SYNTAX Counter64
         MAX-ACCESS  read-only
         STATUS  current
         DESCRIPTION
            "The total number of unicast packets transmitted on this
             interface during the selected 24-hour interval.  This object
             is a 64-bit version of adGenEth24HrIntervalOutUnicastPkts."
         ::= { adGenEth24HrIntervalHCEntry 9 }

      adGenEth24HrIntervalHCTotalPktsQueue0  OBJECT-TYPE
         SYNTAX Counter64
         MAX-ACCESS  read-only
         STATUS  current
         DESCRIPTION
            "The total number of packets transmitted on queue 0
             for this interface during the selected 24-hour interval."
         ::= { adGenEth24HrIntervalHCEntry 10 }

      adGenEth24HrIntervalHCTotalPktsQueue1  OBJECT-TYPE
         SYNTAX Counter64
         MAX-ACCESS  read-only
         STATUS  current
         DESCRIPTION
            "The total number of packets transmitted on queue 1
             for this interface during the selected 24-hour interval."
         ::= { adGenEth24HrIntervalHCEntry 11 }

      adGenEth24HrIntervalHCTotalPktsQueue2  OBJECT-TYPE
         SYNTAX Counter64
         MAX-ACCESS  read-only
         STATUS  current
         DESCRIPTION
            "The total number of packets transmitted on queue 2
             for this interface during the selected 24-hour interval."
         ::= { adGenEth24HrIntervalHCEntry 12 }

      adGenEth24HrIntervalHCTotalPktsQueue3  OBJECT-TYPE
         SYNTAX Counter64
         MAX-ACCESS  read-only
         STATUS  current
         DESCRIPTION
            "The total number of packets transmitted on queue 3
             for this interface during the selected 24-hour interval."
         ::= { adGenEth24HrIntervalHCEntry 13 }

      adGenEth24HrIntervalHCTotalPktsQueue4  OBJECT-TYPE
         SYNTAX Counter64
         MAX-ACCESS  read-only
         STATUS  current
         DESCRIPTION
            "The total number of packets transmitted on queue 4
             for this interface during the selected 24-hour interval."
         ::= { adGenEth24HrIntervalHCEntry 14 }

      adGenEth24HrIntervalHCTotalPktsQueue5  OBJECT-TYPE
         SYNTAX Counter64
         MAX-ACCESS  read-only
         STATUS  current
         DESCRIPTION
            "The total number of packets transmitted on queue 5
             for this interface during the selected 24-hour interval."
         ::= { adGenEth24HrIntervalHCEntry 15 }

      adGenEth24HrIntervalHCTotalPktsQueue6  OBJECT-TYPE
         SYNTAX Counter64
         MAX-ACCESS  read-only
         STATUS  current
         DESCRIPTION
            "The total number of packets transmitted on queue 6
             for this interface during the selected 24-hour interval."
         ::= { adGenEth24HrIntervalHCEntry 16 }

      adGenEth24HrIntervalHCTotalPktsQueue7  OBJECT-TYPE
         SYNTAX Counter64
         MAX-ACCESS  read-only
         STATUS  current
         DESCRIPTION
            "The total number of packets transmitted on queue 7
             for this interface during the selected 24-hour interval."
         ::= { adGenEth24HrIntervalHCEntry 17 }

      adGenEth24HrIntervalHCOutLcv OBJECT-TYPE
         SYNTAX Counter64
         MAX-ACCESS  read-only
         STATUS  current
         DESCRIPTION
            "The total number of line code violations
                                 that occurred on data received from system interface
             during the selected 24-hour interval."
         ::= { adGenEth24HrIntervalHCEntry 18 }

      adGenEth24HrIntervalHCInLcv OBJECT-TYPE
         SYNTAX Counter64
         MAX-ACCESS  read-only
         STATUS  current
         DESCRIPTION
            "The total number of line code violations
                                 that occurred on data received from line side
             during the selected 24-hour interval."
         ::= { adGenEth24HrIntervalHCEntry 19 }

                adGenEth24HrIntervalHCValidData OBJECT-TYPE
                        SYNTAX  TruthValue
                        MAX-ACCESS  read-only
                        STATUS  current
                        DESCRIPTION
                                "This variable indicates if the data for this
                                 24 hour interval is valid."
                        ::= { adGenEth24HrIntervalHCEntry 20 }

      adGenEth24HrIntervalHCInAvgBitsPerSec OBJECT-TYPE
         SYNTAX Counter64
         MAX-ACCESS  read-only
         STATUS  current
         DESCRIPTION
              "The average number of bits per second received
               on the interface during the selected 24-hour interval."
         ::= { adGenEth24HrIntervalHCEntry 21 }

      adGenEth24HrIntervalHCInAvgPktsPerSec OBJECT-TYPE
         SYNTAX Counter64
         MAX-ACCESS  read-only
         STATUS  current
         DESCRIPTION
              "The average number of packets per second received
               on the interface during the selected 24-hour interval."
         ::= { adGenEth24HrIntervalHCEntry 22 }

      adGenEth24HrIntervalHCOutAvgBitsPerSec OBJECT-TYPE
         SYNTAX Counter64
         MAX-ACCESS  read-only
         STATUS  current
         DESCRIPTION
              "The average number of bits per second sent
               on the interface during the selected 24-hour interval."
         ::= { adGenEth24HrIntervalHCEntry 23 }

      adGenEth24HrIntervalHCOutAvgPktsPerSec OBJECT-TYPE
         SYNTAX Counter64
         MAX-ACCESS  read-only
         STATUS  current
         DESCRIPTION
              "The average number of packets per second sent
               on the interface during the selected 24-hour interval."
         ::= { adGenEth24HrIntervalHCEntry 24 }


--==================================================================================================================

   adGenEthPerfResetTable OBJECT-TYPE
      SYNTAX  SEQUENCE OF AdGenEthPerfResetEntry
      MAX-ACCESS  not-accessible
      STATUS  current
      DESCRIPTION
         "The Generic Ethernet Performance Reset table."
      ::= { adGenEthIfcPerformance 10 }

   adGenEthPerfResetEntry OBJECT-TYPE
      SYNTAX  AdGenEthPerfResetEntry
      MAX-ACCESS  not-accessible
      STATUS  current
      DESCRIPTION
         "An entry in the Generic Ethernet reset table."
      INDEX   { ifIndex }
      ::= { adGenEthPerfResetTable 1 }

   AdGenEthPerfResetEntry  ::=
      SEQUENCE {
         adGenEthPerfReset
            INTEGER
       }

   adGenEthPerfReset OBJECT-TYPE
      SYNTAX  INTEGER {
         ethPerfRst(1)
      }
      MAX-ACCESS  read-write
      STATUS  current
      DESCRIPTION
         "Reset all performance monitoring data for the selected
          Generic Ethernet port."
      ::= { adGenEthPerfResetEntry 1 }


--==================================================================================================================

   adGenEthPerfThresholds  OBJECT IDENTIFIER ::= { adGenEthIfcPerformance 11 }

   adGenEth15MinThreshTable OBJECT-TYPE
      SYNTAX  SEQUENCE OF AdGenEth15MinThreshEntry
      MAX-ACCESS  not-accessible
      STATUS  current
      DESCRIPTION
         "The Generic Ethernet 15 minute threshold table."
      ::= { adGenEthPerfThresholds 1 }

   adGenEth15MinThreshEntry OBJECT-TYPE
      SYNTAX  AdGenEth15MinThreshEntry
      MAX-ACCESS  not-accessible
      STATUS  current
      DESCRIPTION
         "An entry in the Generic Ethernet 15 minute threshold table."
      INDEX   { ifIndex }
      ::= { adGenEth15MinThreshTable 1 }

   AdGenEth15MinThreshEntry  ::=
      SEQUENCE {
         adGenEth15MinThreshInErrors
            Unsigned32,
         adGenEth15MinThreshInDiscards
            Unsigned32,
         adGenEth15MinThreshInGiants
            Unsigned32,
         adGenEth15MinThreshInRunts
            Unsigned32,
         adGenEth15MinThreshInMulticastPkts
            Unsigned32,
         adGenEth15MinThreshInBroadcastPkts
            Unsigned32,
         adGenEth15MinThreshInUnicastPkts
            Unsigned32,
         adGenEth15MinThreshInUnknownProtocols
            Unsigned32,
         adGenEth15MinThreshInOctets
            Unsigned64TC,
         adGenEth15MinThreshInPkts
            Unsigned32,
         adGenEth15MinThreshInPkts64Octets
            Unsigned32,
         adGenEth15MinThreshInPkts65to127Octets
            Unsigned32,
         adGenEth15MinThreshInPkts128to255Octets
            Unsigned32,
         adGenEth15MinThreshInPkts256to511Octets
            Unsigned32,
         adGenEth15MinThreshInPkts512to1023Octets
            Unsigned32,
         adGenEth15MinThreshInPkts1024toMaxOctets
            Unsigned32,
         adGenEth15MinThreshOutErrors
            Unsigned32,
         adGenEth15MinThreshOutDiscards
            Unsigned32,
         adGenEth15MinThreshOutMulticastPkts
            Unsigned32,
         adGenEth15MinThreshOutBroadcastPkts
            Unsigned32,
         adGenEth15MinThreshOutUnicastPkts
            Unsigned32,
         adGenEth15MinThreshOutOctets
            Unsigned64TC,
         adGenEth15MinThreshOutPkts
            Unsigned32,
         adGenEth15MinThreshES
            Unsigned32,
         adGenEth15MinThreshLOSS
            Unsigned32,
         adGenEth15MinThreshSEFS
            Unsigned32,
         adGenEth15MinThreshSES
            Unsigned32,
         adGenEth15MinThreshUAS
            Unsigned32,
         adGenEth15MinThreshOutLcv
                                Unsigned64TC,
         adGenEth15MinThreshInLcv
                                Unsigned64TC
       }

   adGenEth15MinThreshInErrors OBJECT-TYPE
      SYNTAX Unsigned32
      MAX-ACCESS  read-write
      STATUS  current
      DESCRIPTION
         "The 15 minute threshold associated with the number of input errors
          encountered by an interface in the current interval. If the
          statistic exceeds this threshold value in the current interval,
          a self-clearing alarm is raised."
      ::= { adGenEth15MinThreshEntry 1 }

   adGenEth15MinThreshInDiscards OBJECT-TYPE
      SYNTAX Unsigned32
      MAX-ACCESS  read-write
      STATUS  current
      DESCRIPTION
         "The 15 minute threshold associated with the number of input discards
          encountered by an interface in the current interval. If the
          statistic exceeds this threshold value in the current interval,
          a self-clearing alarm is raised."
      ::= { adGenEth15MinThreshEntry 2 }

   adGenEth15MinThreshInGiants OBJECT-TYPE
      SYNTAX Unsigned32
      MAX-ACCESS  read-write
      STATUS  current
      DESCRIPTION
         "The 15 minute threshold associated with the number of input giants
          encountered by an interface in the current interval. If the
          statistic exceeds this threshold value in the current interval,
          a self-clearing alarm is raised."
      ::= { adGenEth15MinThreshEntry 3 }

   adGenEth15MinThreshInRunts OBJECT-TYPE
      SYNTAX Unsigned32
      MAX-ACCESS  read-write
      STATUS  current
      DESCRIPTION
         "The 15 minute threshold associated with the number of input runts
          encountered by an interface in the current interval. If the
          statistic exceeds this threshold value in the current interval,
          a self-clearing alarm is raised."
      ::= { adGenEth15MinThreshEntry 4 }

   adGenEth15MinThreshInMulticastPkts OBJECT-TYPE
      SYNTAX Unsigned32
      MAX-ACCESS  read-write
      STATUS  current
      DESCRIPTION
         "The 15 minute threshold associated with the number of multicast
          packets received by an interface in the current interval. If the
          statistic exceeds this threshold value in the current interval,
          a self-clearing alarm is raised."
      ::= { adGenEth15MinThreshEntry 5 }

   adGenEth15MinThreshInBroadcastPkts OBJECT-TYPE
      SYNTAX Unsigned32
      MAX-ACCESS  read-write
      STATUS  current
      DESCRIPTION
         "The 15 minute threshold associated with the number of broadcast
          packets received by an interface in the current interval. If the
          statistic exceeds this threshold value in the current interval,
          a self-clearing alarm is raised."
      ::= { adGenEth15MinThreshEntry 6 }

   adGenEth15MinThreshInUnicastPkts OBJECT-TYPE
      SYNTAX Unsigned32
      MAX-ACCESS  read-write
      STATUS  current
      DESCRIPTION
         "The 15 minute threshold associated with the number of unicast
          packets received by an interface in the current interval. If the
          statistic exceeds this threshold value in the current interval,
          a self-clearing alarm is raised."
      ::= { adGenEth15MinThreshEntry 7 }

   adGenEth15MinThreshInUnknownProtocols OBJECT-TYPE
      SYNTAX Unsigned32
      MAX-ACCESS  read-write
      STATUS  current
      DESCRIPTION
         "The 15 minute threshold associated with the number of packets
          received by an interface in the current interval which were discarded.
                  due to an unknown or unsupported protocol.  If the
          statistic exceeds this threshold value in the current interval,
          a self-clearing alarm is raised."
      ::= { adGenEth15MinThreshEntry 8 }

   adGenEth15MinThreshInOctets OBJECT-TYPE
      SYNTAX Unsigned64TC
      MAX-ACCESS  read-write
      STATUS  current
      DESCRIPTION
         "The 15 minute threshold associated with the number of octets
          received by an interface in the current interval. If the
          statistic exceeds this threshold value in the current interval,
          a self-clearing alarm is raised."
      ::= { adGenEth15MinThreshEntry 9 }

   adGenEth15MinThreshInPkts OBJECT-TYPE
      SYNTAX Unsigned32
      MAX-ACCESS  read-write
      STATUS  current
      DESCRIPTION
         "The 15 minute threshold associated with the number of packets
          received by an interface in the current interval. If the
          statistic exceeds this threshold value in the current interval,
          a self-clearing alarm is raised."
      ::= { adGenEth15MinThreshEntry 10 }

   adGenEth15MinThreshInPkts64Octets OBJECT-TYPE
      SYNTAX Unsigned32
      MAX-ACCESS  read-write
      STATUS  current
      DESCRIPTION
         "The 15 minute threshold associated with the number of packets
          received by an interface in the current interval with a size of
          64 octets.

          If the statistic exceeds this threshold value in the current interval,
          a self-clearing alarm is raised."
      ::= { adGenEth15MinThreshEntry 11 }

   adGenEth15MinThreshInPkts65to127Octets OBJECT-TYPE
      SYNTAX Unsigned32
      MAX-ACCESS  read-write
      STATUS  current
      DESCRIPTION
         "The 15 minute threshold associated with the number of packets
          received by an interface in the current interval with a size between
          65 and 127 octets.

          If the statistic exceeds this threshold value in the current interval,
          a self-clearing alarm is raised."
      ::= { adGenEth15MinThreshEntry 12 }

   adGenEth15MinThreshInPkts128to255Octets OBJECT-TYPE
      SYNTAX Unsigned32
      MAX-ACCESS  read-write
      STATUS  current
      DESCRIPTION
         "The 15 minute threshold associated with the number of packets
          received by an interface in the current interval with a size between
          128 and 255 octets.

          If the statistic exceeds this threshold value in the current interval,
          a self-clearing alarm is raised."
      ::= { adGenEth15MinThreshEntry 13 }

   adGenEth15MinThreshInPkts256to511Octets OBJECT-TYPE
      SYNTAX Unsigned32
      MAX-ACCESS  read-write
      STATUS  current
      DESCRIPTION
         "The 15 minute threshold associated with the number of packets
          received by an interface in the current interval with a size between
          256 and 511 octets.

          If the statistic exceeds this threshold value in the current interval,
          a self-clearing alarm is raised."
      ::= { adGenEth15MinThreshEntry 14 }

   adGenEth15MinThreshInPkts512to1023Octets OBJECT-TYPE
      SYNTAX Unsigned32
      MAX-ACCESS  read-write
      STATUS  current
      DESCRIPTION
         "The 15 minute threshold associated with the number of packets
          received by an interface in the current interval with a size between
          512 and 1023 octets.

          If the statistic exceeds this threshold value in the current interval,
          a self-clearing alarm is raised."
      ::= { adGenEth15MinThreshEntry 15 }

   adGenEth15MinThreshInPkts1024toMaxOctets OBJECT-TYPE
      SYNTAX Unsigned32
      MAX-ACCESS  read-write
      STATUS  current
      DESCRIPTION
         "The 15 minute threshold associated with the number of packets
          received by an interface in the current interval with a size between
          1024 octets and the maximum packet size supported by the interface.

          If the statistic exceeds this threshold value in the current interval,
          a self-clearing alarm is raised."
      ::= { adGenEth15MinThreshEntry 16 }

   adGenEth15MinThreshOutErrors OBJECT-TYPE
      SYNTAX Unsigned32
      MAX-ACCESS  read-write
      STATUS  current
      DESCRIPTION
         "The 15 minute threshold associated with the number of input errors
          encountered by an interface in the current interval. If the
          statistic exceeds this threshold value in the current interval,
          a self-clearing alarm is raised."
      ::= { adGenEth15MinThreshEntry 17 }

   adGenEth15MinThreshOutDiscards OBJECT-TYPE
      SYNTAX Unsigned32
      MAX-ACCESS  read-write
      STATUS  current
      DESCRIPTION
         "The 15 minute threshold associated with the number of input discards
          encountered by an interface in the current interval. If the
          statistic exceeds this threshold value in the current interval,
          a self-clearing alarm is raised."
      ::= { adGenEth15MinThreshEntry 18 }

   adGenEth15MinThreshOutMulticastPkts OBJECT-TYPE
      SYNTAX Unsigned32
      MAX-ACCESS  read-write
      STATUS  current
      DESCRIPTION
         "The 15 minute threshold associated with the number of multicast
          packets transmitted by an interface in the current interval. If the
          statistic exceeds this threshold value in the current interval,
          a self-clearing alarm is raised."
      ::= { adGenEth15MinThreshEntry 19 }

   adGenEth15MinThreshOutBroadcastPkts OBJECT-TYPE
      SYNTAX Unsigned32
      MAX-ACCESS  read-write
      STATUS  current
      DESCRIPTION
         "The 15 minute threshold associated with the number of broadcast
          packets transmitted by an interface in the current interval. If the
          statistic exceeds this threshold value in the current interval,
          a self-clearing alarm is raised."
      ::= { adGenEth15MinThreshEntry 20 }

   adGenEth15MinThreshOutUnicastPkts OBJECT-TYPE
      SYNTAX Unsigned32
      MAX-ACCESS  read-write
      STATUS  current
      DESCRIPTION
         "The 15 minute threshold associated with the number of unicast
          packets transmitted by an interface in the current interval. If the
          statistic exceeds this threshold value in the current interval,
          a self-clearing alarm is raised."
      ::= { adGenEth15MinThreshEntry 21 }

   adGenEth15MinThreshOutOctets OBJECT-TYPE
      SYNTAX Unsigned64TC
      MAX-ACCESS  read-write
      STATUS  current
      DESCRIPTION
         "The 15 minute threshold associated with the number of octets
          transmitted by an interface in the current interval. If the
          statistic exceeds this threshold value in the current interval,
          a self-clearing alarm is raised."
      ::= { adGenEth15MinThreshEntry 22 }

   adGenEth15MinThreshOutPkts OBJECT-TYPE
      SYNTAX Unsigned32
      MAX-ACCESS  read-write
      STATUS  current
      DESCRIPTION
         "The 15 minute threshold associated with the number of packets
          transmitted by an interface in the current interval. If the
          statistic exceeds this threshold value in the current interval,
          a self-clearing alarm is raised."
      ::= { adGenEth15MinThreshEntry 23 }

   adGenEth15MinThreshES OBJECT-TYPE
      SYNTAX Unsigned32
      MAX-ACCESS  read-write
      STATUS  current
      DESCRIPTION
         "The 15 minute threshold associated with the number of errored
          seconds in the current interval. If the statistic exceeds this
          threshold value in the current interval a self-clearing alarm is raised.

                  An errored second(ES) is defined as the number of seconds
                  containing one or more frame errors OR one or more LOS defects."
      ::= { adGenEth15MinThreshEntry 24 }

   adGenEth15MinThreshLOSS OBJECT-TYPE
      SYNTAX Unsigned32
      MAX-ACCESS  read-write
      STATUS  current
      DESCRIPTION
         "The 15 minute threshold associated with the number of loss
          of signal seconds in the current interval. If the statistic exceeds this
          threshold value in the current interval a self-clearing alarm is raised.

                  An loss of signal second(LOSS) is defined as the number of seconds
                  containing one or more LOS defects."
      ::= { adGenEth15MinThreshEntry 25 }

   adGenEth15MinThreshSEFS OBJECT-TYPE
      SYNTAX Unsigned32
      MAX-ACCESS  read-write
      STATUS  current
      DESCRIPTION
         "The 15 minute threshold associated with the number of severely errored
          frame seconds in the current interval. If the statistic exceeds this
          threshold value in the current interval a self-clearing alarm is raised.

                  An severely errored frame second(SEFS) is defined as the number of seconds
                  containing severely errored frames.  Here, frames refer to MAC frames as
                  opposed to, say, 8B/10B words.  A 1-second interval is said to contain
                  severely errored frames if 1% or more of the frames received in that interval
                  contain errors."
      ::= { adGenEth15MinThreshEntry 26 }

   adGenEth15MinThreshSES OBJECT-TYPE
      SYNTAX Unsigned32
      MAX-ACCESS  read-write
      STATUS  current
      DESCRIPTION
         "The 15 minute threshold associated with the number of severely errored
          seconds in the current interval. If the statistic exceeds this
          threshold value in the current interval a self-clearing alarm is raised.

                  An severely errored second(ES) is defined as the number of seconds
                  containing severely frames OR one or more LOS defects."
      ::= { adGenEth15MinThreshEntry 27 }

   adGenEth15MinThreshUAS OBJECT-TYPE
      SYNTAX Unsigned32
      MAX-ACCESS  read-write
      STATUS  current
      DESCRIPTION
         "The 15 minute threshold associated with the number of unavailable
          seconds in the current interval. If the statistic exceeds this
          threshold value in the current interval a self-clearing alarm is raised.

                  An unavailable second(UAS) is defined as the number of seconds
                  that the interface is unavailable.  The interface transitions from
                  available to unavailable after 10 contiguous severely errored seconds."
      ::= { adGenEth15MinThreshEntry 28 }

   adGenEth15MinThreshOutLcv    OBJECT-TYPE
      SYNTAX Unsigned64TC
      MAX-ACCESS read-write
      STATUS current
      DESCRIPTION
                   "The 15 minute threshold associated with the number of line code violations
                         that occurred on data received from system interface in the current interval. If the
          statistic exceeds this threshold value in the current interval,
          a self-clearing alarm is raised."
      ::= { adGenEth15MinThreshEntry 29 }

        adGenEth15MinThreshInLcv    OBJECT-TYPE
      SYNTAX Unsigned64TC
      MAX-ACCESS read-write
      STATUS current
      DESCRIPTION
                   "The 15 minute threshold associated with the number of line code violations
                         that occurred on data received from line side in the current interval. If the
          statistic exceeds this threshold value in the current interval,
          a self-clearing alarm is raised."
      ::= { adGenEth15MinThreshEntry 30 }

--===================================================================

   adGenEth24HrThreshTable OBJECT-TYPE
      SYNTAX  SEQUENCE OF AdGenEth24HrThreshEntry
      MAX-ACCESS  not-accessible
      STATUS  current
      DESCRIPTION
         "The Generic Ethernet 24 hour threshold table."
      ::= { adGenEthPerfThresholds 2 }

   adGenEth24HrThreshEntry OBJECT-TYPE
      SYNTAX  AdGenEth24HrThreshEntry
      MAX-ACCESS  not-accessible
      STATUS  current
      DESCRIPTION
         "An entry in the Generic Ethernet 24 hour threshold table."
      INDEX   { ifIndex }
      ::= { adGenEth24HrThreshTable 1 }

   AdGenEth24HrThreshEntry  ::=
      SEQUENCE {
         adGenEth24HrThreshInErrors
            Unsigned32,
         adGenEth24HrThreshInDiscards
            Unsigned32,
         adGenEth24HrThreshInGiants
            Unsigned32,
         adGenEth24HrThreshInRunts
            Unsigned32,
         adGenEth24HrThreshInMulticastPkts
            Unsigned32,
         adGenEth24HrThreshInBroadcastPkts
            Unsigned32,
                        adGenEth24HrThreshOutLcv
                                Unsigned64TC,
         adGenEth24HrThreshInLcv
                                Unsigned64TC
       }

   adGenEth24HrThreshInErrors OBJECT-TYPE
      SYNTAX Unsigned32
      MAX-ACCESS  read-write
      STATUS  current
      DESCRIPTION
         "The 24 hour threshold associated with the number of errors
          received by an interface in the current interval. If the
          statistic exceeds this threshold value in the current interval,
          a self-clearing alarm is raised."
      ::= { adGenEth24HrThreshEntry 1 }

   adGenEth24HrThreshInDiscards OBJECT-TYPE
      SYNTAX Unsigned32
      MAX-ACCESS  read-write
      STATUS  current
      DESCRIPTION
         "The 24 hour threshold associated with the number of input discards
          encountered by an interface in the current interval. If the
          statistic exceeds this threshold value in the current interval,
          a self-clearing alarm is raised."
      ::= { adGenEth24HrThreshEntry 2 }

   adGenEth24HrThreshInGiants OBJECT-TYPE
      SYNTAX Unsigned32
      MAX-ACCESS  read-write
      STATUS  current
      DESCRIPTION
         "The 24 hour threshold associated with the number of giants
          received by an interface in the current interval. If the
          statistic exceeds this threshold value in the current interval,
          a self-clearing alarm is raised."
      ::= { adGenEth24HrThreshEntry 3 }

   adGenEth24HrThreshInRunts OBJECT-TYPE
      SYNTAX Unsigned32
      MAX-ACCESS  read-write
      STATUS  current
      DESCRIPTION
         "The 24 hour threshold associated with the number of runts
          received by an interface in the current interval. If the
          statistic exceeds this threshold value in the current interval,
          a self-clearing alarm is raised."
      ::= { adGenEth24HrThreshEntry 4 }

   adGenEth24HrThreshInMulticastPkts OBJECT-TYPE
      SYNTAX Unsigned32
      MAX-ACCESS  read-write
      STATUS  current
      DESCRIPTION
         "The 24 hour threshold associated with the number of multicast
          packets received by an interface in the current interval. If the
          statistic exceeds this threshold value in the current interval,
          a self-clearing alarm is raised."
      ::= { adGenEth24HrThreshEntry 5 }

   adGenEth24HrThreshInBroadcastPkts OBJECT-TYPE
      SYNTAX Unsigned32
      MAX-ACCESS  read-write
      STATUS  current
      DESCRIPTION
         "The 24 hour threshold associated with the number of broadcast
          packets received by an interface in the current interval. If the
          statistic exceeds this threshold value in the current interval,
          a self-clearing alarm is raised."
      ::= { adGenEth24HrThreshEntry 6 }

   adGenEth24HrThreshOutLcv    OBJECT-TYPE
      SYNTAX Unsigned64TC
      MAX-ACCESS read-write
      STATUS current
      DESCRIPTION
                   "The 24 hour threshold associated with the number of line code violations
          that occurred on data received from system interface in the current interval. If the
          statistic exceeds this threshold value in the current interval,
          a self-clearing alarm is raised."
      ::= { adGenEth24HrThreshEntry 7 }

        adGenEth24HrThreshInLcv    OBJECT-TYPE
      SYNTAX Unsigned64TC
      MAX-ACCESS read-write
      STATUS current
      DESCRIPTION
                   "The 24 hour threshold associated with the number of line code violations
          that occurred on data received from line side in the current interval. If the
          statistic exceeds this threshold value in the current interval,
          a self-clearing alarm is raised."
      ::= { adGenEth24HrThreshEntry 8 }

--==================================================================================================================

   adGenEthPerformanceCountersTable OBJECT-TYPE
      SYNTAX  SEQUENCE OF AdGenEthPerformanceCountersEntry
      MAX-ACCESS  not-accessible
      STATUS  current
      DESCRIPTION
         "This table contains rolling performance counters for ethernet ports.
          This table is intended to supplement the counters in the ifTable."
      ::= { adGenEthIfcPerformance 12 }

   adGenEthPerformanceCountersEntry     OBJECT-TYPE
      SYNTAX  AdGenEthPerformanceCountersEntry
      MAX-ACCESS  not-accessible
      STATUS  current
      DESCRIPTION
         "An entry in the Generic Ethernet performance counters table."
      INDEX   { ifIndex }
      ::= { adGenEthPerformanceCountersTable 1 }

   AdGenEthPerformanceCountersEntry  ::=
      SEQUENCE {
         adGenEthInPackets             Counter32,
         adGenEthOutPackets            Counter32,
         adGenEthInRunts               Counter32,
         adGenEthInGiants              Counter32,
         adGenEthInFrameErrors         Counter32,
         adGenEthInFCSErrors           Counter32,
         adGenEthInAvgPktsPerSec       Counter32,
         adGenEthOutAvgPktsPerSec      Counter32,
         adGenEthInAvgBitsPerSec       Counter32,
         adGenEthOutAvgBitsPerSec      Counter32,
         adGenEthTotalTxPacketsQueue0  Counter64,
         adGenEthTotalTxPacketsQueue1  Counter64,
         adGenEthTotalTxPacketsQueue2  Counter64,
         adGenEthTotalTxPacketsQueue3  Counter64,
         adGenEthTotalTxPacketsQueue4  Counter64,
         adGenEthTotalTxPacketsQueue5  Counter64,
         adGenEthTotalTxPacketsQueue6  Counter64,
         adGenEthTotalTxPacketsQueue7  Counter64,
         adGenEthDroppedPacketsQueue0  Counter32,
         adGenEthDroppedPacketsQueue1  Counter32,
         adGenEthDroppedPacketsQueue2  Counter32,
         adGenEthDroppedPacketsQueue3  Counter32,
         adGenEthDroppedPacketsQueue4  Counter32,
         adGenEthDroppedPacketsQueue5  Counter32,
         adGenEthDroppedPacketsQueue6  Counter32,
         adGenEthDroppedPacketsQueue7  Counter32,

         adGenEthInPeakUtilization     Gauge32,
         adGenEthInAvgUtilization      Gauge32,
         adGenEthOutPeakUtilization    Gauge32,
         adGenEthOutAvgUtilization     Gauge32,

         adGenEthDepthPacketsQueue0    Gauge32,
         adGenEthDepthPacketsQueue1    Gauge32,
         adGenEthDepthPacketsQueue2    Gauge32,
         adGenEthDepthPacketsQueue3    Gauge32,
         adGenEthDepthPacketsQueue4    Gauge32,
         adGenEthDepthPacketsQueue5    Gauge32,
         adGenEthDepthPacketsQueue6    Gauge32,
         adGenEthDepthPacketsQueue7    Gauge32,

         adGenEthHCInAvgPktsPerSec       Counter64,
         adGenEthHCOutAvgPktsPerSec      Counter64,
         adGenEthHCInAvgBitsPerSec       Counter64,
         adGenEthHCOutAvgBitsPerSec      Counter64
       }

   adGenEthInPackets    OBJECT-TYPE
      SYNTAX Counter32
      MAX-ACCESS  read-only
      STATUS  current
      DESCRIPTION
         "The total number of packets received on the interface."
      ::= { adGenEthPerformanceCountersEntry 1 }

   adGenEthOutPackets    OBJECT-TYPE
      SYNTAX Counter32
      MAX-ACCESS  read-only
      STATUS  current
      DESCRIPTION
         "The total number of packets transmitted on the interface."
      ::= { adGenEthPerformanceCountersEntry 2 }

   adGenEthInRunts    OBJECT-TYPE
      SYNTAX Counter32
      MAX-ACCESS  read-only
      STATUS  current
      DESCRIPTION
         "The total number of packets received on the interface
          which are smaller than the minimum packet size."
      ::= { adGenEthPerformanceCountersEntry 3 }

   adGenEthInGiants    OBJECT-TYPE
      SYNTAX Counter32
      MAX-ACCESS  read-only
      STATUS  current
      DESCRIPTION
         "The total number of packets received on the interface
          which are larger than the maximum packet size."
      ::= { adGenEthPerformanceCountersEntry 4 }

   adGenEthInFrameErrors    OBJECT-TYPE
      SYNTAX Counter32
      MAX-ACCESS  read-only
      STATUS  current
      DESCRIPTION
         "The total number of packets received on the interface
          that have frame errors."
      ::= { adGenEthPerformanceCountersEntry 5 }

   adGenEthInFCSErrors    OBJECT-TYPE
      SYNTAX Counter32
      MAX-ACCESS  read-only
      STATUS  current
      DESCRIPTION
         "The total number of packets received on the interface
          that have FCS errors."
      ::= { adGenEthPerformanceCountersEntry 6 }

   adGenEthInAvgPktsPerSec    OBJECT-TYPE
      SYNTAX Counter32
      MAX-ACCESS  read-only
      STATUS  current
      DESCRIPTION
         "The average number of packets per second received
          on the interface during the last 5 minutes."
      ::= { adGenEthPerformanceCountersEntry 7 }

   adGenEthOutAvgPktsPerSec    OBJECT-TYPE
      SYNTAX Counter32
      MAX-ACCESS  read-only
      STATUS  current
      DESCRIPTION
         "The average number of packets per second transmitted
          on the interface during the last 5 minutes."
      ::= { adGenEthPerformanceCountersEntry 8 }

   adGenEthInAvgBitsPerSec    OBJECT-TYPE
      SYNTAX Counter32
      MAX-ACCESS  read-only
      STATUS  current
      DESCRIPTION
         "The average number of bits per second received
          on the interface during the last 5 minutes."
      ::= { adGenEthPerformanceCountersEntry 9 }

   adGenEthOutAvgBitsPerSec    OBJECT-TYPE
      SYNTAX Counter32
      MAX-ACCESS  read-only
      STATUS  current
      DESCRIPTION
         "The average number of bits per second transmitted
          on the interface during the last 5 minutes."
      ::= { adGenEthPerformanceCountersEntry 10 }

    adGenEthTotalTxPacketsQueue0    OBJECT-TYPE
        SYNTAX  Counter64
        MAX-ACCESS  read-only
        STATUS  current
        DESCRIPTION
            "The total number of packets transmitted for queue 0."
        ::= { adGenEthPerformanceCountersEntry 11 }

    adGenEthTotalTxPacketsQueue1    OBJECT-TYPE
        SYNTAX  Counter64
        MAX-ACCESS  read-only
        STATUS  current
        DESCRIPTION
            "The total number of packets transmitted for queue 1."
        ::= { adGenEthPerformanceCountersEntry 12 }

    adGenEthTotalTxPacketsQueue2    OBJECT-TYPE
        SYNTAX  Counter64
        MAX-ACCESS  read-only
        STATUS  current
        DESCRIPTION
            "The total number of packets transmitted for queue 2."
        ::= { adGenEthPerformanceCountersEntry 13 }

    adGenEthTotalTxPacketsQueue3    OBJECT-TYPE
        SYNTAX  Counter64
        MAX-ACCESS  read-only
        STATUS  current
        DESCRIPTION
            "The total number of packets transmitted for queue 3."
        ::= { adGenEthPerformanceCountersEntry 14 }

    adGenEthTotalTxPacketsQueue4    OBJECT-TYPE
        SYNTAX  Counter64
        MAX-ACCESS  read-only
        STATUS  current
        DESCRIPTION
            "The total number of packets transmitted for queue 4."
        ::= { adGenEthPerformanceCountersEntry 15 }

    adGenEthTotalTxPacketsQueue5    OBJECT-TYPE
        SYNTAX  Counter64
        MAX-ACCESS  read-only
        STATUS  current
        DESCRIPTION
            "The total number of packets transmitted for queue 5."
        ::= { adGenEthPerformanceCountersEntry 16 }

    adGenEthTotalTxPacketsQueue6    OBJECT-TYPE
        SYNTAX  Counter64
        MAX-ACCESS  read-only
        STATUS  current
        DESCRIPTION
            "The total number of packets transmitted for queue 6."
        ::= { adGenEthPerformanceCountersEntry 17 }

    adGenEthTotalTxPacketsQueue7    OBJECT-TYPE
        SYNTAX  Counter64
        MAX-ACCESS  read-only
        STATUS  current
        DESCRIPTION
            "The total number of packets transmitted for queue 7."
        ::= { adGenEthPerformanceCountersEntry 18 }

    adGenEthDroppedPacketsQueue0    OBJECT-TYPE
        SYNTAX  Counter32
        MAX-ACCESS  read-only
        STATUS  current
        DESCRIPTION
            "The number of dropped packets for queue 0."
        ::= { adGenEthPerformanceCountersEntry 19 }

    adGenEthDroppedPacketsQueue1    OBJECT-TYPE
        SYNTAX  Counter32
        MAX-ACCESS  read-only
        STATUS  current
        DESCRIPTION
            "The number of dropped packets for queue 1."
        ::= { adGenEthPerformanceCountersEntry 20 }

    adGenEthDroppedPacketsQueue2    OBJECT-TYPE
        SYNTAX  Counter32
        MAX-ACCESS  read-only
        STATUS  current
        DESCRIPTION
            "The number of dropped packets for queue 2."
        ::= { adGenEthPerformanceCountersEntry 21 }

    adGenEthDroppedPacketsQueue3    OBJECT-TYPE
        SYNTAX  Counter32
        MAX-ACCESS  read-only
        STATUS  current
        DESCRIPTION
            "The number of dropped packets for queue 3."
        ::= { adGenEthPerformanceCountersEntry 22 }

    adGenEthDroppedPacketsQueue4    OBJECT-TYPE
        SYNTAX  Counter32
        MAX-ACCESS  read-only
        STATUS  current
        DESCRIPTION
            "The number of dropped packets for queue 4."
        ::= { adGenEthPerformanceCountersEntry 23 }

    adGenEthDroppedPacketsQueue5    OBJECT-TYPE
        SYNTAX  Counter32
        MAX-ACCESS  read-only
        STATUS  current
        DESCRIPTION
            "The number of dropped packets for queue 5."
        ::= { adGenEthPerformanceCountersEntry 24 }

    adGenEthDroppedPacketsQueue6    OBJECT-TYPE
        SYNTAX  Counter32
        MAX-ACCESS  read-only
        STATUS  current
        DESCRIPTION
            "The number of dropped packets for queue 6."
        ::= { adGenEthPerformanceCountersEntry 25 }

    adGenEthDroppedPacketsQueue7    OBJECT-TYPE
        SYNTAX  Counter32
        MAX-ACCESS  read-only
        STATUS  current
        DESCRIPTION
            "The number of dropped packets for queue 7."
        ::= { adGenEthPerformanceCountersEntry 26 }

    adGenEthInPeakUtilization       OBJECT-TYPE
        SYNTAX  Gauge32
        MAX-ACCESS  read-only
        STATUS  current
        DESCRIPTION
            "The maximum usage of the ingress link (in whole percent)."
        ::= { adGenEthPerformanceCountersEntry 27 }

    adGenEthInAvgUtilization        OBJECT-TYPE
        SYNTAX  Gauge32
        MAX-ACCESS  read-only
        STATUS  current
        DESCRIPTION
            "The percent of the ingress link in use over the last 5 minutes."
        ::= { adGenEthPerformanceCountersEntry 28 }

    adGenEthOutPeakUtilization      OBJECT-TYPE
        SYNTAX  Gauge32
        MAX-ACCESS  read-only
        STATUS  current
        DESCRIPTION
            "The maximum usage of the egress link (in whole percent)."
        ::= { adGenEthPerformanceCountersEntry 29 }

    adGenEthOutAvgUtilization       OBJECT-TYPE
        SYNTAX  Gauge32
        MAX-ACCESS  read-only
        STATUS  current
        DESCRIPTION
            "The percent of the egress link in use over the last 5 minutes."
        ::= { adGenEthPerformanceCountersEntry 30 }

    adGenEthDepthPacketsQueue0      OBJECT-TYPE
        SYNTAX  Gauge32
        MAX-ACCESS  read-only
        STATUS  current
        DESCRIPTION
            "The current depth of queue 0, in number of packets."
        ::= { adGenEthPerformanceCountersEntry 31 }

    adGenEthDepthPacketsQueue1      OBJECT-TYPE
        SYNTAX  Gauge32
        MAX-ACCESS  read-only
        STATUS  current
        DESCRIPTION
            "The current depth of queue 1, in number of packets."
        ::= { adGenEthPerformanceCountersEntry 32 }

    adGenEthDepthPacketsQueue2      OBJECT-TYPE
        SYNTAX  Gauge32
        MAX-ACCESS  read-only
        STATUS  current
        DESCRIPTION
            "The current depth of queue 2, in number of packets."
        ::= { adGenEthPerformanceCountersEntry 33 }

    adGenEthDepthPacketsQueue3      OBJECT-TYPE
        SYNTAX  Gauge32
        MAX-ACCESS  read-only
        STATUS  current
        DESCRIPTION
            "The current depth of queue 3, in number of packets."
        ::= { adGenEthPerformanceCountersEntry 34 }

    adGenEthDepthPacketsQueue4      OBJECT-TYPE
        SYNTAX  Gauge32
        MAX-ACCESS  read-only
        STATUS  current
        DESCRIPTION
            "The current depth of queue 4, in number of packets."
        ::= { adGenEthPerformanceCountersEntry 35 }

    adGenEthDepthPacketsQueue5      OBJECT-TYPE
        SYNTAX  Gauge32
        MAX-ACCESS  read-only
        STATUS  current
        DESCRIPTION
            "The current depth of queue 5, in number of packets."
        ::= { adGenEthPerformanceCountersEntry 36 }

    adGenEthDepthPacketsQueue6      OBJECT-TYPE
        SYNTAX  Gauge32
        MAX-ACCESS  read-only
        STATUS  current
        DESCRIPTION
            "The current depth of queue 6, in number of packets."
        ::= { adGenEthPerformanceCountersEntry 37 }

    adGenEthDepthPacketsQueue7      OBJECT-TYPE
        SYNTAX  Gauge32
        MAX-ACCESS  read-only
        STATUS  current
        DESCRIPTION
            "The current depth of queue 7, in number of packets."
        ::= { adGenEthPerformanceCountersEntry 38 }

   adGenEthHCInAvgPktsPerSec    OBJECT-TYPE
      SYNTAX Counter64
      MAX-ACCESS  read-only
      STATUS  current
      DESCRIPTION
         "The average number of packets per second received
          on the interface during the last 5 minutes."
      ::= { adGenEthPerformanceCountersEntry 39 }

   adGenEthHCOutAvgPktsPerSec    OBJECT-TYPE
      SYNTAX Counter64
      MAX-ACCESS  read-only
      STATUS  current
      DESCRIPTION
         "The average number of packets per second transmitted
          on the interface during the last 5 minutes."
      ::= { adGenEthPerformanceCountersEntry 40 }

   adGenEthHCInAvgBitsPerSec    OBJECT-TYPE
      SYNTAX Counter64
      MAX-ACCESS  read-only
      STATUS  current
      DESCRIPTION
         "The average number of bits per second received
          on the interface during the last 5 minutes."
      ::= { adGenEthPerformanceCountersEntry 41 }

   adGenEthHCOutAvgBitsPerSec    OBJECT-TYPE
      SYNTAX Counter64
      MAX-ACCESS  read-only
      STATUS  current
      DESCRIPTION
         "The average number of bits per second transmitted
          on the interface during the last 5 minutes."
      ::= { adGenEthPerformanceCountersEntry 42 }

 --================================================================================================================
-- Ethernet Performance Counters of 64bit
--==================================================================================================================

   adGenEthPerformanceCountersHCTable OBJECT-TYPE
      SYNTAX  SEQUENCE OF AdGenEthPerformanceCountersHCEntry
      MAX-ACCESS  not-accessible
      STATUS  current
      DESCRIPTION
         "This is a High-Capacity table contains rolling performance counters for ethernet ports.
          This table is intended to supplement the counters in the ifTable."
      ::= { adGenEthIfcPerformance 13 }

   adGenEthPerformanceCountersHCEntry     OBJECT-TYPE
      SYNTAX  AdGenEthPerformanceCountersHCEntry
      MAX-ACCESS  not-accessible
      STATUS  current
      DESCRIPTION
         "An entry in the Generic Ethernet performance counters High-Capacity table."
      INDEX   { ifIndex }
      ::= { adGenEthPerformanceCountersHCTable 1 }

   AdGenEthPerformanceCountersHCEntry  ::=
      SEQUENCE {
         adGenEthCounterHCInPackets             Counter64,
         adGenEthCounterHCOutPackets            Counter64,
         adGenEthCounterHCInBytes               Counter64,
         adGenEthCounterHCOutBytes              Counter64,
         adGenEthCounterHCInUnicasts            Counter64,
         adGenEthCounterHCOutUnicasts           Counter64,
         adGenEthCounterHCInBroadcasts          Counter64,
         adGenEthCounterHCOutBroadcasts         Counter64,
         adGenEthCounterHCInMulticasts          Counter64,
         adGenEthCounterHCOutMulticasts         Counter64,
         adGenEthCounterHCInErrors              Counter64,
         adGenEthCounterHCOutErrors             Counter64,
         adGenEthCounterHCInDiscards            Counter64,
         adGenEthCounterHCOutDiscards           Counter64,
         adGenEthCounterHCInLCVs                Counter64,
         adGenEthCounterHCOutLCVs               Counter64,
         adGenEthCounterHCInRunts               Counter64,
         adGenEthCounterHCInGiants              Counter64,
         adGenEthCounterHCInFrameErrors         Counter64,
         adGenEthCounterHCInCRCErrors           Counter64

         }

   adGenEthCounterHCInPackets    OBJECT-TYPE
      SYNTAX Counter64
      MAX-ACCESS  read-only
      STATUS  current
      DESCRIPTION
         "The total number of packets received on the interface. This object is the
         64-bit version of the adGenEthInPackets"
      ::= { adGenEthPerformanceCountersHCEntry 1 }

   adGenEthCounterHCOutPackets    OBJECT-TYPE
      SYNTAX Counter64
      MAX-ACCESS  read-only
      STATUS  current
      DESCRIPTION
         "The total number of packets transmitted on the interface.This object is the
         64-bit version of the adGenEthOutPackets"
      ::= { adGenEthPerformanceCountersHCEntry 2 }

   adGenEthCounterHCInBytes      OBJECT-TYPE
      SYNTAX Counter64
      MAX-ACCESS  read-only
      STATUS  current
      DESCRIPTION
         "The total number of Bytes received on the interface."
      ::= { adGenEthPerformanceCountersHCEntry 3 }

   adGenEthCounterHCOutBytes    OBJECT-TYPE
      SYNTAX Counter64
      MAX-ACCESS  read-only
      STATUS  current
      DESCRIPTION
         "The total number of Bytes transmitted on the interface."
      ::= { adGenEthPerformanceCountersHCEntry 4 }

   adGenEthCounterHCInUnicasts    OBJECT-TYPE
      SYNTAX Counter64
      MAX-ACCESS  read-only
      STATUS  current
      DESCRIPTION
         "The total number of Unicast packets received on the interface."
      ::= { adGenEthPerformanceCountersHCEntry 5 }

   adGenEthCounterHCOutUnicasts    OBJECT-TYPE
      SYNTAX Counter64
      MAX-ACCESS  read-only
      STATUS  current
      DESCRIPTION
         "The total number of Unicast packets transmitted on the interface."
      ::= { adGenEthPerformanceCountersHCEntry 6 }

   adGenEthCounterHCInBroadcasts    OBJECT-TYPE
      SYNTAX Counter64
      MAX-ACCESS  read-only
      STATUS  current
      DESCRIPTION
         "The total number of Broadcast packets received on the interface."
      ::= { adGenEthPerformanceCountersHCEntry 7 }

   adGenEthCounterHCOutBroadcasts    OBJECT-TYPE
      SYNTAX Counter64
      MAX-ACCESS  read-only
      STATUS  current
      DESCRIPTION
         "The total number of Broadcast packets transmitted on the interface."
      ::= { adGenEthPerformanceCountersHCEntry 8 }

   adGenEthCounterHCInMulticasts    OBJECT-TYPE
      SYNTAX Counter64
      MAX-ACCESS  read-only
      STATUS  current
      DESCRIPTION
         "The total number of Multicast packets received on the interface."
      ::= { adGenEthPerformanceCountersHCEntry 9 }

   adGenEthCounterHCOutMulticasts    OBJECT-TYPE
      SYNTAX Counter64
      MAX-ACCESS  read-only
      STATUS  current
      DESCRIPTION
         "The total number of Multicast packets transmitted on the interface."
      ::= { adGenEthPerformanceCountersHCEntry 10 }

   adGenEthCounterHCInErrors    OBJECT-TYPE
      SYNTAX Counter64
      MAX-ACCESS  read-only
      STATUS  current
      DESCRIPTION
         "The total number of packets with error received on the interface."
      ::= { adGenEthPerformanceCountersHCEntry 11 }

   adGenEthCounterHCOutErrors    OBJECT-TYPE
      SYNTAX Counter64
      MAX-ACCESS  read-only
      STATUS  current
      DESCRIPTION
         "The total number of packets with error transmitted on the interface."
      ::= { adGenEthPerformanceCountersHCEntry 12 }

   adGenEthCounterHCInDiscards    OBJECT-TYPE
      SYNTAX Counter64
      MAX-ACCESS  read-only
      STATUS  current
      DESCRIPTION
         "The total number of packets discarded on the interface."
      ::= { adGenEthPerformanceCountersHCEntry 13 }

   adGenEthCounterHCOutDiscards    OBJECT-TYPE
      SYNTAX Counter64
      MAX-ACCESS  read-only
      STATUS  current
      DESCRIPTION
         "The total number of packets discarded on the interface."
      ::= { adGenEthPerformanceCountersHCEntry 14 }

   adGenEthCounterHCInLCVs    OBJECT-TYPE
      SYNTAX Counter64
      MAX-ACCESS  read-only
      STATUS  current
      DESCRIPTION
         "The total number of Line code violations occured on the data received on the interface."
      ::= { adGenEthPerformanceCountersHCEntry 15 }

   adGenEthCounterHCOutLCVs    OBJECT-TYPE
      SYNTAX Counter64
      MAX-ACCESS  read-only
      STATUS  current
      DESCRIPTION
         "The total number of Line code violations occured on the data transmitted on the interface."
      ::= { adGenEthPerformanceCountersHCEntry 16 }

   adGenEthCounterHCInRunts    OBJECT-TYPE
      SYNTAX Counter64
      MAX-ACCESS  read-only
      STATUS  current
      DESCRIPTION
         "The total number of packets received on the interface which are smaller than the minimum packet size."
      ::= { adGenEthPerformanceCountersHCEntry 17 }

   adGenEthCounterHCInGiants    OBJECT-TYPE
      SYNTAX Counter64
      MAX-ACCESS  read-only
      STATUS  current
      DESCRIPTION
         "The total number of packets received on the interface which are larger than the maximum packet size."
      ::= { adGenEthPerformanceCountersHCEntry 18 }

   adGenEthCounterHCInFrameErrors    OBJECT-TYPE
      SYNTAX Counter64
      MAX-ACCESS  read-only
      STATUS  current
      DESCRIPTION
         "The total number of packets received on the interface that have frame errors"
      ::= { adGenEthPerformanceCountersHCEntry 19 }

   adGenEthCounterHCInCRCErrors    OBJECT-TYPE
      SYNTAX Counter64
      MAX-ACCESS  read-only
      STATUS  current
      DESCRIPTION
         "The total number of CRC errors received on the interface."
      ::= { adGenEthPerformanceCountersHCEntry 20 }

--==================================================================================================================
--==================================================================================================================
--==================================================================================================================

   adGenEthSet15MinInErrors NOTIFICATION-TYPE
      OBJECTS  {
         adTrapInformSeqNum,
         sysName,
         adGenSlotInfoIndex,
         ifDescr,
         ifIndex
      }
      STATUS  current
      DESCRIPTION
         "This trap indicates that the interface has crossed the 15 min In Errors Threshold"
         --#TYPE         "Status - Alarm"
         --#SUMMARY      "adGenEth 1: Ethernet In Errors 15 min Threshold Crossed."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 1 }

   adGenEthSet15MinInDiscards NOTIFICATION-TYPE
      OBJECTS  {
         adTrapInformSeqNum,
         sysName,
         adGenSlotInfoIndex,
         ifDescr,
         ifIndex
      }
      STATUS  current
      DESCRIPTION
         "This trap indicates that the interface has crossed the 15 min In Discard Threshold"
         --#TYPE         "Status - Alarm"
         --#SUMMARY      "adGenEth 2: Ethernet In Discards 15 min Threshold Crossed."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 2 }

   adGenEthSet15MinInGiants NOTIFICATION-TYPE
      OBJECTS  {
         adTrapInformSeqNum,
         sysName,
         adGenSlotInfoIndex,
         ifDescr,
         ifIndex
      }
      STATUS  current
      DESCRIPTION
         "This trap indicates that the interface has crossed the 15 min In Giants Threshold"
         --#TYPE         "Status - Alarm"
         --#SUMMARY      "adGenEth 3: Ethernet In Giants 15 min Threshold Crossed."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 3 }

   adGenEthSet15MinInRunts NOTIFICATION-TYPE
      OBJECTS  {
         adTrapInformSeqNum,
         sysName,
         adGenSlotInfoIndex,
         ifDescr,
         ifIndex
      }
      STATUS  current
      DESCRIPTION
         "This trap indicates that the interface has crossed the 15 min In Runts Threshold"
         --#TYPE         "Status - Alarm"
         --#SUMMARY      "adGenEth 4: Ethernet In Runts 15 min Threshold Crossed."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 4 }

   adGenEthSet15MinInMulticastPkts NOTIFICATION-TYPE
      OBJECTS  {
         adTrapInformSeqNum,
         sysName,
         adGenSlotInfoIndex,
         ifDescr,
         ifIndex
      }
      STATUS  current
      DESCRIPTION
         "This trap indicates that the interface has crossed the 15 min In Multicast Pkts Threshold"
         --#TYPE         "Status - Alarm"
         --#SUMMARY      "adGenEth 5: Ethernet In Multicast Pkts 15 min Threshold Crossed."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 5 }

   adGenEthSet15MinInBroadcastPkts NOTIFICATION-TYPE
      OBJECTS  {
         adTrapInformSeqNum,
         sysName,
         adGenSlotInfoIndex,
         ifDescr,
         ifIndex
      }
      STATUS  current
      DESCRIPTION
         "This trap indicates that the interface has crossed the 15 min In Broadcast Pkts Threshold"
         --#TYPE         "Status - Alarm"
         --#SUMMARY      "adGenEth 6: Ethernet In Broadcast Pkts 15 min Threshold Crossed."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 6 }


   adGenEthSet24HrInErrors NOTIFICATION-TYPE
      OBJECTS  {
         adTrapInformSeqNum,
         sysName,
         adGenSlotInfoIndex,
         ifDescr,
         ifIndex
      }
      STATUS  current
      DESCRIPTION
         "This trap indicates that the interface has crossed the 24 hour In Errors Threshold"
         --#TYPE         "Status - Alarm"
         --#SUMMARY      "adGenEth 7: Ethernet In Errors 24 hour Threshold Crossed."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 7 }

   adGenEthSet24HrInDiscards NOTIFICATION-TYPE
      OBJECTS  {
         adTrapInformSeqNum,
         sysName,
         adGenSlotInfoIndex,
         ifDescr,
         ifIndex
      }
      STATUS  current
      DESCRIPTION
         "This trap indicates that the interface has crossed the 24 hour In Discards Threshold"
         --#TYPE         "Status - Alarm"
         --#SUMMARY      "adGenEth 8: Ethernet In Discards 24 hour Threshold Crossed."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 8 }

   adGenEthSet24HrInGiants NOTIFICATION-TYPE
      OBJECTS  {
         adTrapInformSeqNum,
         sysName,
         adGenSlotInfoIndex,
         ifDescr,
         ifIndex
      }
      STATUS  current
      DESCRIPTION
         "This trap indicates that the interface has crossed the 24 hour In Giants Threshold"
         --#TYPE         "Status - Alarm"
         --#SUMMARY      "adGenEth 9: Ethernet In Giants 24 hour Threshold Crossed."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 9 }

   adGenEthSet24HrInRunts NOTIFICATION-TYPE
      OBJECTS  {
         adTrapInformSeqNum,
         sysName,
         adGenSlotInfoIndex,
         ifDescr,
         ifIndex
      }
      STATUS  current
      DESCRIPTION
         "This trap indicates that the interface has crossed the 24 hour In Runts Threshold"
         --#TYPE         "Status - Alarm"
         --#SUMMARY      "adGenEth 10: Ethernet In Runts 24 hour Threshold Crossed."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 10 }

   adGenEthSet24HrInMulticastPkts NOTIFICATION-TYPE
      OBJECTS  {
         adTrapInformSeqNum,
         sysName,
         adGenSlotInfoIndex,
         ifDescr,
         ifIndex
      }
      STATUS  current
      DESCRIPTION
         "This trap indicates that the interface has crossed the 24 hour In Multicast Pkts Threshold"
         --#TYPE         "Status - Alarm"
         --#SUMMARY      "adGenEth 11: Ethernet In Multicast Pkts 24 hour Threshold Crossed."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 11 }

   adGenEthSet24HrInBroadcastPkts NOTIFICATION-TYPE
      OBJECTS  {
         adTrapInformSeqNum,
         sysName,
         adGenSlotInfoIndex,
         ifDescr,
         ifIndex
      }
      STATUS  current
      DESCRIPTION
         "This trap indicates that the interface has crossed the 24 hour In Broadcast Pkts Threshold"
         --#TYPE         "Status - Alarm"
         --#SUMMARY      "adGenEth 12: Ethernet In Broadcast Pkts 24 hour Threshold Crossed."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 12 }

   adGenEthIfcLinkUp NOTIFICATION-TYPE
      OBJECTS  {
         adTrapInformSeqNum,
         sysName,
         adGenSlotInfoIndex,
         ifDescr,
         ifIndex
      }
      STATUS  current
      DESCRIPTION
         "This trap indicates that the ethernet link is up."
         --#TYPE         "Status - Alarm"
         --#SUMMARY      "adGenEth 14: Ethernet Link is Up."
         --#SUMMARY      "Detected at shelf: %s, slot: %d, interface %d"
         --#ARGUMENTS    {1,2,4}
         --#SEVERITY     MAJOR
         --#GENERIC      6
         --#CATEGORY     "Error Events"
         --#SOURCE_ID    "A"
         --#TIMEINDEX    0
      ::= { adGenEthIfcEvents 14 }

   adGenEthIfcLinkDown NOTIFICATION-TYPE
      OBJECTS  {
         adTrapInformSeqNum,
         sysName,
         adGenSlotInfoIndex,
         ifDescr,
         ifIndex
      }
      STATUS  current
      DESCRIPTION
         "This trap indicates that the ethernet link is down."
         --#TYPE         "Status - Alarm"
         --#SUMMARY      "adGenEth 15: Ethernet Link is Down."
         --#SUMMARY      "Detected at shelf: %s, slot: %d, interface %d"
         --#ARGUMENTS    {1,2,4}
         --#SEVERITY     MAJOR
         --#GENERIC      6
         --#CATEGORY     "Error Events"
         --#SOURCE_ID    "A"
         --#TIMEINDEX    0
      ::= { adGenEthIfcEvents 15 }

   adGenEthSet15MinInUnicastPkts NOTIFICATION-TYPE
      OBJECTS  {
         adTrapInformSeqNum,
         sysName,
         adGenSlotInfoIndex,
         ifDescr,
         ifIndex
      }
      STATUS  current
      DESCRIPTION
         "This trap indicates that the interface has crossed the 15 Minute In Unicast Pkts Threshold"
         --#TYPE         "Status - Alarm"
         --#SUMMARY      "adGenEth 12: Ethernet In Unicast Pkts 15 Minute Threshold Crossed."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 21 }

   adGenEthSet15MinInUnknownProtocols NOTIFICATION-TYPE
      OBJECTS  {
         adTrapInformSeqNum,
         sysName,
         adGenSlotInfoIndex,
         ifDescr,
         ifIndex
      }
      STATUS  current
      DESCRIPTION
         "This trap indicates that the interface has crossed the 15 Minute In Unknown Protocols Threshold"
         --#TYPE         "Status - Alarm"
         --#SUMMARY      "adGenEth 12: Ethernet In Unknown Protocols 15 Minute Threshold Crossed."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 22 }

   adGenEthSet15MinInOctets NOTIFICATION-TYPE
      OBJECTS  {
         adTrapInformSeqNum,
         sysName,
         adGenSlotInfoIndex,
         ifDescr,
         ifIndex
      }
      STATUS  current
      DESCRIPTION
         "This trap indicates that the interface has crossed the 15 Minute In Octets Threshold"
         --#TYPE         "Status - Alarm"
         --#SUMMARY      "adGenEth 12: Ethernet In Octets 15 Minute Threshold Crossed."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 23 }

   adGenEthSet15MinInPkts NOTIFICATION-TYPE
      OBJECTS  {
         adTrapInformSeqNum,
         sysName,
         adGenSlotInfoIndex,
         ifDescr,
         ifIndex
      }
      STATUS  current
      DESCRIPTION
         "This trap indicates that the interface has crossed the 15 Minute In Pkts Threshold"
         --#TYPE         "Status - Alarm"
         --#SUMMARY      "adGenEth 12: Ethernet In Pkts 15 Minute Threshold Crossed."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 24 }

   adGenEthSet15MinInPkts64Octets NOTIFICATION-TYPE
      OBJECTS  {
         adTrapInformSeqNum,
         sysName,
         adGenSlotInfoIndex,
         ifDescr,
         ifIndex
      }
      STATUS  current
      DESCRIPTION
         "This trap indicates that the interface has crossed the 15 Minute In Pkts 64 Octets Threshold"
         --#TYPE         "Status - Alarm"
         --#SUMMARY      "adGenEth 12: Ethernet In Pkts 64 Octets 15 Minute Threshold Crossed."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 25 }

   adGenEthSet15MinInPkts65to127Octets NOTIFICATION-TYPE
      OBJECTS  {
         adTrapInformSeqNum,
         sysName,
         adGenSlotInfoIndex,
         ifDescr,
         ifIndex
      }
      STATUS  current
      DESCRIPTION
         "This trap indicates that the interface has crossed the 15 Minute In Pkts 65 to 127 Octets Threshold"
         --#TYPE         "Status - Alarm"
         --#SUMMARY      "adGenEth 12: Ethernet In Pkts 65 to 127 Octets 15 Minute Threshold Crossed."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 27 }

   adGenEthSet15MinInPkts128to255Octets NOTIFICATION-TYPE
      OBJECTS  {
         adTrapInformSeqNum,
         sysName,
         adGenSlotInfoIndex,
         ifDescr,
         ifIndex
      }
      STATUS  current
      DESCRIPTION
         "This trap indicates that the interface has crossed the 15 Minute In Pkts 128 to 255 Octets Threshold"
         --#TYPE         "Status - Alarm"
         --#SUMMARY      "adGenEth 12: Ethernet In Pkts 128 to 255 Octets 15 Minute Threshold Crossed."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 28 }

   adGenEthSet15MinInPkts256to511Octets NOTIFICATION-TYPE
      OBJECTS  {
         adTrapInformSeqNum,
         sysName,
         adGenSlotInfoIndex,
         ifDescr,
         ifIndex
      }
      STATUS  current
      DESCRIPTION
         "This trap indicates that the interface has crossed the 15 Minute In Pkts 256 to 511 Octets Threshold"
         --#TYPE         "Status - Alarm"
         --#SUMMARY      "adGenEth 12: Ethernet In Pkts 256 to 511 Octets 15 Minute Threshold Crossed."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 29 }

   adGenEthSet15MinInPkts512to1023Octets NOTIFICATION-TYPE
      OBJECTS  {
         adTrapInformSeqNum,
         sysName,
         adGenSlotInfoIndex,
         ifDescr,
         ifIndex
      }
      STATUS  current
      DESCRIPTION
         "This trap indicates that the interface has crossed the 15 Minute In Pkts 512 to 1023 Octets Threshold"
         --#TYPE         "Status - Alarm"
         --#SUMMARY      "adGenEth 12: Ethernet In Pkts 512 to 1023 Octets 15 Minute Threshold Crossed."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 30 }

   adGenEthSet15MinInPkts1024toMaxOctets NOTIFICATION-TYPE
      OBJECTS  {
         adTrapInformSeqNum,
         sysName,
         adGenSlotInfoIndex,
         ifDescr,
         ifIndex
      }
      STATUS  current
      DESCRIPTION
         "This trap indicates that the interface has crossed the 15 Minute In Pkts 65 to Max Octets Threshold"
         --#TYPE         "Status - Alarm"
         --#SUMMARY      "adGenEth 12: Ethernet In Pkts 65 to Max Octets 15 Minute Threshold Crossed."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 31 }

   adGenEthSet15MinOutErrors NOTIFICATION-TYPE
      OBJECTS  {
         adTrapInformSeqNum,
         sysName,
         adGenSlotInfoIndex,
         ifDescr,
         ifIndex
      }
      STATUS  current
      DESCRIPTION
         "This trap indicates that the interface has crossed the 15 min Out Errors Threshold"
         --#TYPE         "Status - Alarm"
         --#SUMMARY      "adGenEth 1: Ethernet Out Errors 15 min Threshold Crossed."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 32 }

   adGenEthSet15MinOutDiscards NOTIFICATION-TYPE
      OBJECTS  {
         adTrapInformSeqNum,
         sysName,
         adGenSlotInfoIndex,
         ifDescr,
         ifIndex
      }
      STATUS  current
      DESCRIPTION
         "This trap indicates that the interface has crossed the 15 min Out Discard Threshold"
         --#TYPE         "Status - Alarm"
         --#SUMMARY      "adGenEth 2: Ethernet Out Discards 15 min Threshold Crossed."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 33 }

   adGenEthSet15MinOutMulticastPkts NOTIFICATION-TYPE
      OBJECTS  {
         adTrapInformSeqNum,
         sysName,
         adGenSlotInfoIndex,
         ifDescr,
         ifIndex
      }
      STATUS  current
      DESCRIPTION
         "This trap indicates that the interface has crossed the 15 min Out Multicast Pkts Threshold"
         --#TYPE         "Status - Alarm"
         --#SUMMARY      "adGenEth 5: Ethernet Out Multicast Pkts 15 min Threshold Crossed."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 34 }

   adGenEthSet15MinOutBroadcastPkts NOTIFICATION-TYPE
      OBJECTS  {
         adTrapInformSeqNum,
         sysName,
         adGenSlotInfoIndex,
         ifDescr,
         ifIndex
      }
      STATUS  current
      DESCRIPTION
         "This trap indicates that the interface has crossed the 15 min Out Broadcast Pkts Threshold"
         --#TYPE         "Status - Alarm"
         --#SUMMARY      "adGenEth 6: Ethernet Out Broadcast Pkts 15 min Threshold Crossed."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 35 }

   adGenEthSet15MinOutUnicastPkts NOTIFICATION-TYPE
      OBJECTS  {
         adTrapInformSeqNum,
         sysName,
         adGenSlotInfoIndex,
         ifDescr,
         ifIndex
      }
      STATUS  current
      DESCRIPTION
         "This trap indicates that the interface has crossed the 15 Minute Out Unicast Pkts Threshold"
         --#TYPE         "Status - Alarm"
         --#SUMMARY      "adGenEth 12: Ethernet Out Unicast Pkts 15 Minute Threshold Crossed."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 36 }

   adGenEthSet15MinOutOctets NOTIFICATION-TYPE
      OBJECTS  {
         adTrapInformSeqNum,
         sysName,
         adGenSlotInfoIndex,
         ifDescr,
         ifIndex
      }
      STATUS  current
      DESCRIPTION
         "This trap indicates that the interface has crossed the 15 Minute Out Octets Threshold"
         --#TYPE         "Status - Alarm"
         --#SUMMARY      "adGenEth 12: Ethernet Out Octets 15 Minute Threshold Crossed."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 37 }

   adGenEthSet15MinOutPkts NOTIFICATION-TYPE
      OBJECTS  {
         adTrapInformSeqNum,
         sysName,
         adGenSlotInfoIndex,
         ifDescr,
         ifIndex
      }
      STATUS  current
      DESCRIPTION
         "This trap indicates that the interface has crossed the 15 Minute Out Pkts Threshold"
         --#TYPE         "Status - Alarm"
         --#SUMMARY      "adGenEth 12: Ethernet Out Pkts 15 Minute Threshold Crossed."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 38 }

   adGenEthSet15MinES NOTIFICATION-TYPE
      OBJECTS  {
         adTrapInformSeqNum,
         sysName,
         adGenSlotInfoIndex,
         ifDescr,
         ifIndex
      }
      STATUS  current
      DESCRIPTION
         "This trap indicates that the interface has crossed the 15 Minute Errored Seconds Threshold"
         --#TYPE         "Status - Alarm"
         --#SUMMARY      "adGenEth 12: Ethernet Errored Seconds 15 Minute Threshold Crossed."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 39 }

   adGenEthSet15MinLOSS NOTIFICATION-TYPE
      OBJECTS  {
         adTrapInformSeqNum,
         sysName,
         adGenSlotInfoIndex,
         ifDescr,
         ifIndex
      }
      STATUS  current
      DESCRIPTION
         "This trap indicates that the interface has crossed the 15 Minute Loss of Signal Seconds Threshold"
         --#TYPE         "Status - Alarm"
         --#SUMMARY      "adGenEth 12: Ethernet Loss of Signal Seconds 15 Minute Threshold Crossed."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 40 }

   adGenEthSet15MinSEFS NOTIFICATION-TYPE
      OBJECTS  {
         adTrapInformSeqNum,
         sysName,
         adGenSlotInfoIndex,
         ifDescr,
         ifIndex
      }
      STATUS  current
      DESCRIPTION
         "This trap indicates that the interface has crossed the 15 Minute Severely Errored Frame Seconds Threshold"
         --#TYPE         "Status - Alarm"
         --#SUMMARY      "adGenEth 12: Ethernet Severely Errored Frame Seconds 15 Minute Threshold Crossed."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 41 }

   adGenEthSet15MinSES NOTIFICATION-TYPE
      OBJECTS  {
         adTrapInformSeqNum,
         sysName,
         adGenSlotInfoIndex,
         ifDescr,
         ifIndex
      }
      STATUS  current
      DESCRIPTION
         "This trap indicates that the interface has crossed the 15 Minute Severely Errored Seconds Threshold"
         --#TYPE         "Status - Alarm"
         --#SUMMARY      "adGenEth 12: Ethernet Severely Errored Seconds 15 Minute Threshold Crossed."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 42 }

   adGenEthSet15MinUAS NOTIFICATION-TYPE
      OBJECTS  {
         adTrapInformSeqNum,
         sysName,
         adGenSlotInfoIndex,
         ifDescr,
         ifIndex
      }
      STATUS  current
      DESCRIPTION
         "This trap indicates that the interface has crossed the 15 Minute Unavailable Seconds Threshold"
         --#TYPE         "Status - Alarm"
         --#SUMMARY      "adGenEth 12: Ethernet Unavailable Seconds 15 Minute Threshold Crossed."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 43 }

   adGenEthSet15MinOutLcvAlm    NOTIFICATION-TYPE
     OBJECTS       {
             adTrapInformSeqNum,
             sysName,
             adGenSlotInfoIndex,
             ifDescr,
             ifIndex,
             adGenEth15MinThreshOutLcv
             }
     STATUS current
     DESCRIPTION
             "This trap indicates that the interface has crossed the 15 minute Out Line Code Violation Threshold."
     --#TYPE      "Threshold Error - Ethernet Out line code violation 15 minute Threshold Crossed."
     --#SUMMARY   "adGenEth 44: 15-minute Ethernet Out Lcv Crossed"
     --#SUMMARY   "Detected at shelf: %s, slot: %d, interface %d"
     --#ARGUMENTS { 1, 2, 4 }
     --#SEVERITY  WARNING
     --#GENERIC   6
     --#CATEGORY  "Error Events"
     --#SOURCE_ID "A"
     --#TIMEINDEX 0
     ::= {adGenEthIfcEvents 44}

   adGenEthSet15MinInLcvAlm    NOTIFICATION-TYPE
     OBJECTS       {
             adTrapInformSeqNum,
             sysName,
             adGenSlotInfoIndex,
             ifDescr,
             ifIndex,
             adGenEth15MinThreshInLcv
             }
     STATUS current
     DESCRIPTION
             "This trap indicates that the interface has crossed the 15 minute In Line Code Violation Threshold."
     --#TYPE      "Threshold Error - Ethernet In line code violation 15 minute Threshold Crossed."
     --#SUMMARY   "adGenEth 45: 15-minute Ethernet In Lcv Crossed"
     --#SUMMARY   "Detected at shelf: %s, slot: %d, interface %d"
     --#ARGUMENTS { 1, 2, 4 }
     --#SEVERITY  WARNING
     --#GENERIC   6
     --#CATEGORY  "Error Events"
     --#SOURCE_ID "A"
     --#TIMEINDEX 0
     ::= {adGenEthIfcEvents 45}

   adGenEthSet24HrOutLcvAlm    NOTIFICATION-TYPE
      OBJECTS       {
             adTrapInformSeqNum,
             sysName,
             adGenSlotInfoIndex,
             ifDescr,
             ifIndex,
             adGenEth24HrThreshOutLcv
             }
     STATUS          current
     DESCRIPTION
             "This trap indicates that the interface has crossed the 24 hour Out Line Code Violation Threshold."
     --#TYPE      "Threshold Error - Ethernet Out line code violation 24 hour Threshold Crossed."
     --#SUMMARY   "adGenEth 46: 24-hour Ethernet Out Lcv Crossed"
     --#SUMMARY   "Detected at shelf: %s, slot: %d, interface %d"
     --#ARGUMENTS { 1, 2, 4 }
     --#SEVERITY  WARNING
     --#GENERIC   6
     --#CATEGORY  "Error Events"
     --#SOURCE_ID "A"
     --#TIMEINDEX 0
     ::= {adGenEthIfcEvents 46}

        adGenEthSet24HrInLcvAlm    NOTIFICATION-TYPE
     OBJECTS       {
             adTrapInformSeqNum,
             sysName,
             adGenSlotInfoIndex,
             ifDescr,
             ifIndex,
             adGenEth24HrThreshInLcv
             }
     STATUS          current
     DESCRIPTION
             "This trap indicates that the interface has crossed the 24 hour In Line Code Violation Threshold."
     --#TYPE      "Threshold Error - Ethernet In line code violation 24 hour Threshold Crossed."
     --#SUMMARY   "adGenEth 47: 24-hour Ethernet In Lcv Crossed"
     --#SUMMARY   "cleared at shelf: %s, Interface: %d %s"
     --#ARGUMENTS { 1, 2, 4 }
     --#SEVERITY  WARNING
     --#GENERIC   6
     --#CATEGORY  "Error Events"
     --#SOURCE_ID "A"
     --#TIMEINDEX 0
     ::= {adGenEthIfcEvents 47}

    adGenEthIfcLOSClear    NOTIFICATION-TYPE
      OBJECTS  {
         adTrapInformSeqNum,
         sysName,
         adGenSlotInfoIndex,
         ifDescr,
         ifIndex
      }
      STATUS  current
      DESCRIPTION
         "This trap indicates that the Loss of Signal (LOS) alarm is cleared."
         --#TYPE         "Status - Alarm"
         --#SUMMARY      "Loss Of Signal (LOS)."
         --#SUMMARY      "Cleared at shelf: %s, slot: %d, interface %d"
         --#ARGUMENTS    {1,2,4}
         --#SEVERITY     CRITICAL
         --#GENERIC      6
         --#CATEGORY     "Error Events"
         --#SOURCE_ID    "A"
         --#TIMEINDEX    0
      ::= { adGenEthIfcEvents 49 }

    adGenEthIfcLOSSet    NOTIFICATION-TYPE
      OBJECTS  {
         adTrapInformSeqNum,
         sysName,
         adGenSlotInfoIndex,
         ifDescr,
         ifIndex
      }
      STATUS  current
      DESCRIPTION
         "This trap indicates that the Loss of Signal (LOS) alarm is set."
         --#TYPE         "Status - Alarm"
         --#SUMMARY      "Loss Of Signal (LOS)."
         --#SUMMARY      "Detected at shelf: %s, slot: %d, interface %d"
         --#ARGUMENTS    {1,2,4}
         --#SEVERITY     CRITICAL
         --#GENERIC      6
         --#CATEGORY     "Error Events"
         --#SOURCE_ID    "A"
         --#TIMEINDEX    0
      ::= { adGenEthIfcEvents 50 }

    adGenEthIfcLOBSClear    NOTIFICATION-TYPE
      OBJECTS  {
         adTrapInformSeqNum,
         sysName,
         adGenSlotInfoIndex,
         ifDescr,
         ifIndex
      }
      STATUS  current
      DESCRIPTION
         "This trap indicates that the Loss of Block Synch (LOBS) alarm is cleared."
         --#TYPE         "Status - Alarm"
         --#SUMMARY      "Loss of Block Synch (LOBS)."
         --#SUMMARY      "Cleared at shelf: %s, slot: %d, interface %d"
         --#ARGUMENTS    {1,2,4}
         --#SEVERITY     CRITICAL
         --#GENERIC      6
         --#CATEGORY     "Error Events"
         --#SOURCE_ID    "A"
         --#TIMEINDEX    0
      ::= { adGenEthIfcEvents 51 }

    adGenEthIfcLOBSSet    NOTIFICATION-TYPE
      OBJECTS  {
         adTrapInformSeqNum,
         sysName,
         adGenSlotInfoIndex,
         ifDescr,
         ifIndex
      }
      STATUS  current
      DESCRIPTION
         "This trap indicates that Loss of Block Synch (LOBS) alarm is set."
         --#TYPE         "Status - Alarm"
         --#SUMMARY      "Loss of Block Synch (LOBS) Alarm."
         --#SUMMARY      "Detected at shelf: %s, slot: %d, interface %d"
         --#ARGUMENTS    {1,2,4}
         --#SEVERITY     CRITICAL
         --#GENERIC      6
         --#CATEGORY     "Error Events"
         --#SOURCE_ID    "A"
         --#TIMEINDEX    0
      ::= { adGenEthIfcEvents 52 }

    adGenEthIfcHIBERClear    NOTIFICATION-TYPE
      OBJECTS  {
         adTrapInformSeqNum,
         sysName,
         adGenSlotInfoIndex,
         ifDescr,
         ifIndex
      }
      STATUS  current
      DESCRIPTION
         "This trap indicates that the High BERT (HIBER) alarm is cleared."
         --#TYPE         "Status - Alarm"
         --#SUMMARY      "High BERT (HIBER)."
         --#SUMMARY      "Cleared at shelf: %s, slot: %d, interface %d"
         --#ARGUMENTS    {1,2,4}
         --#SEVERITY     CRITICAL
         --#GENERIC      6
         --#CATEGORY     "Error Events"
         --#SOURCE_ID    "A"
         --#TIMEINDEX    0
      ::= { adGenEthIfcEvents 53 }

    adGenEthIfcHIBERSet    NOTIFICATION-TYPE
      OBJECTS  {
         adTrapInformSeqNum,
         sysName,
         adGenSlotInfoIndex,
         ifDescr,
         ifIndex
      }
      STATUS  current
      DESCRIPTION
         "This trap indicates that High BERT (HIBER) alarm is set."
         --#TYPE         "Status - Alarm"
         --#SUMMARY      "High BERT (HIBER)."
         --#SUMMARY      "Detected at shelf: %s, slot: %d, interface %d"
         --#ARGUMENTS    {1,2,4}
         --#SEVERITY     CRITICAL
         --#GENERIC      6
         --#CATEGORY     "Error Events"
         --#SOURCE_ID    "A"
         --#TIMEINDEX    0
      ::= { adGenEthIfcEvents 54 }

    adGenEthIfcLocalFaultClear    NOTIFICATION-TYPE
      OBJECTS  {
         adTrapInformSeqNum,
         sysName,
         adGenSlotInfoIndex,
         ifDescr,
         ifIndex
      }
      STATUS  current
      DESCRIPTION
         "This trap indicates that the Local Fault Alarm (LCLFLT) alarm is cleared."
         --#TYPE         "Status - Alarm"
         --#SUMMARY      "Local Fault (LCLFLT) ."
         --#SUMMARY      "Cleared at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 55 }

    adGenEthIfcLocalFaultSet    NOTIFICATION-TYPE
      OBJECTS  {
         adTrapInformSeqNum,
         sysName,
         adGenSlotInfoIndex,
         ifDescr,
         ifIndex
      }
      STATUS  current
      DESCRIPTION
         "This trap indicates that Local Fault (LCLFLT) alarm is set."
         --#TYPE         "Status - Alarm"
         --#SUMMARY      "Local Fault (LCLFLT)."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 56 }

    adGenEthIfcRemoteFaultClear    NOTIFICATION-TYPE
      OBJECTS  {
         adTrapInformSeqNum,
         sysName,
         adGenSlotInfoIndex,
         ifDescr,
         ifIndex
      }
      STATUS  current
      DESCRIPTION
         "This trap indicates that the Remote Fault alarm (REMFLT) alarm is cleared."
         --#TYPE         "Status - Alarm"
         --#SUMMARY      "Remote Fault (REMFLT)."
         --#SUMMARY      "Cleared at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 57 }

    adGenEthIfcRemoteFaultSet    NOTIFICATION-TYPE
      OBJECTS  {
         adTrapInformSeqNum,
         sysName,
         adGenSlotInfoIndex,
         ifDescr,
         ifIndex
      }
      STATUS  current
      DESCRIPTION
         "This trap indicates that Remote Fault (REMFLT) alarm is set."
         --#TYPE         "Status - Alarm"
         --#SUMMARY      "Remote Fault (REMFLT)."
         --#SUMMARY      "Detected at shelf: %s, slot: %d, interface %d"
         --#ARGUMENTS    {1,2,4}
         --#SEVERITY     WARNING
         --#GENERIC      6
         --#CATEGORY     "Error Events"
         --#SOURCE_ID    "A"
         --#TIMEINDEX    0
      ::= { adGenEthIfcEvents 58 }

    adGenEthPortYCableCfgAlarmClear   NOTIFICATION-TYPE
         OBJECTS       {
                 adTrapInformSeqNum,
                 sysName,
                 adGenSlotInfoIndex,
                 ifDescr,
                 ifIndex
                 }
         STATUS          current
         DESCRIPTION
                 "This trap indicates that the y-cable misconfiguration alarm has been cleared."
         --#TYPE         "Status - Alarm"
         --#SUMMARY      "Y-Cable Misconfiguration"
         --#SUMMARY      "Cleared at shelf: %s, slot: %d, interface %d"
         --#ARGUMENTS    {1,2,4}
         --#SEVERITY     MAJOR
         --#GENERIC      6
         --#CATEGORY     "Error Events"
         --#SOURCE_ID    "A"
         --#TIMEINDEX    0
       ::= { adGenEthIfcEvents 59 }

    adGenEthPortYCableCfgAlarmSet   NOTIFICATION-TYPE
         OBJECTS       {
                 adTrapInformSeqNum,
                 sysName,
                 adGenSlotInfoIndex,
                 ifDescr,
                 ifIndex
                 }
         STATUS          current
         DESCRIPTION
                  "This trap indicates that the y-cable attribute has been enabled on an interface that does not meet the prerequisites."
         --#TYPE         "Status - Alarm"
         --#SUMMARY      "Y-Cable Misconfiguration"
         --#SUMMARY      "Detected at shelf: %s, slot: %d, interface %d"
         --#ARGUMENTS    {1,2,4}
         --#SEVERITY     MAJOR
         --#GENERIC      6
         --#CATEGORY     "Error Events"
         --#SOURCE_ID    "A"
         --#TIMEINDEX    0
        ::= { adGenEthIfcEvents 60 }

    adGenEthSpeedScanAlarm NOTIFICATION-TYPE
         OBJECTS  {
                 adTrapInformSeqNum,
                 sysName,
                 adGenSlotInfoIndex,
                 ifDescr,
                 ifIndex,
                 adTAeSCUTrapAlarmLevel
                 }
         STATUS  current
         DESCRIPTION
                  "This trap indicates that the ethernet link is in speed scan mode."
         --#TYPE         "Status - Alarm"
         --#SUMMARY      "adGenEth 61: Ethernet Link in speed scan mode."
         --#SUMMARY      "Detected at shelf: %s, slot: %d, interface %d"
         --#ARGUMENTS    {1,2,4}
         --#SEVERITY     Informational
         --#GENERIC      6
         --#CATEGORY     "Error Events"
         --#SOURCE_ID    "A"
         --#TIMEINDEX    0
        ::= { adGenEthIfcEvents 61 }

    adGenEthSpeedScanAlarmClear NOTIFICATION-TYPE
         OBJECTS  {
                 adTrapInformSeqNum,
                 sysName,
                 adGenSlotInfoIndex,
                 ifDescr,
                 ifIndex,
                 adTAeSCUTrapAlarmLevel
                 }
         STATUS  current
         DESCRIPTION
                  "This trap indicates that the ethernet link is out of speed scan mode."
         --#TYPE         "Status - Alarm"
         --#SUMMARY      "adGenEth 62: Ethernet Link in speed scan mode."
         --#SUMMARY      "Detected at shelf: %s, slot: %d, interface %d"
         --#ARGUMENTS    {1,2,4}
         --#SEVERITY     Informational
         --#GENERIC      6
         --#CATEGORY     "Error Events"
         --#SOURCE_ID    "A"
         --#TIMEINDEX    0
        ::= { adGenEthIfcEvents 62 }


END

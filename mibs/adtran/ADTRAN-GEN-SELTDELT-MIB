ADTRAN-GEN-SELTDELT-MIB
-- TITLE:     The ADTRAN SELT / DELT MIB
-- PRODUCT:   Multiple
-- VERSION:   0.1
-- DATE:      2008/07/17

-- This MIB defines the object identifiers (OIDs) for the SELT / DELT feature.

-- HISTORY:
   -- Date       By  Descripition                                                Rev
   -- 2009/01/07 och Update for a new OID (adGenSeltDeltEnumTestStatus) for EMS  (0.2). STATUS: PRELIMINARY
   -- 2008/07/17 och First edition                                               (0.1). STATUS: PRELIMINARY

--*********************************************************************************************************
DEFINITIONS ::= BEGIN

    IMPORTS
	MODULE-IDENTITY,
    	OBJECT-TYPE
          	FROM SNMPv2-SMI
    	OBJECT-GROUP
        	FROM SNMPv2-CONF
        adGenSlotInfoIndex
            FROM ADTRAN-GENSLOT-MIB
    	DisplayString
        	FROM SNMPv2-TC
    	adGenXdsl,
    	adGenXdslID
        	FROM ADTRAN-SHARED-XDSL-MIB
        InterfaceIndex
                FROM IF-MIB
     ;

--*********************************************************************************************************
adGenSeltDeltMIB MODULE-IDENTITY
       LAST-UPDATED "201312030000Z"
       ORGANIZATION "ADTRAN, Inc."
       CONTACT-INFO
         "Web: http://www.adtran.com
          E-mail: support@adtran.com"
       DESCRIPTION
            "This is the MIB module that describes
             SELT / DELT functionality."
             
        REVISION "201312030000Z"
        DESCRIPTION "Added adGenSeltDeltTestRemoteDevice and updated descriptions for
                     adGenSeltDeltTestPortNumber."

        REVISION "200807170000Z"
        DESCRIPTION "Created"
        
       ::= { adGenXdslID 1 }

-- OBJECT IDENTIFIERS
   adGenSeltDelt               OBJECT IDENTIFIER ::= { adGenXdsl  1 }
   adGenXdslMibConformance     OBJECT IDENTIFIER ::= { adGenXdsl 2 }
   adGenXdslMibGroups          OBJECT IDENTIFIER ::= { adGenXdslMibConformance 1 }

-- *************************************************************************
-- test
-- ************************************************************************
         adGenSeltDeltTable    OBJECT-TYPE
             SYNTAX          SEQUENCE OF AdGenSeltDeltEntry
             MAX-ACCESS      not-accessible
             STATUS          current
             DESCRIPTION
                "This table contains information on the XDSL generic
                 SELT / DELT feature. Each entry reflects a required
		 parameter or action required to perform either the SELT
		 or DELT diagnostic test. "
         ::= { adGenSeltDelt 1 }


         adGenSeltDeltEntry   OBJECT-TYPE
             SYNTAX          AdGenSeltDeltEntry
             MAX-ACCESS      not-accessible
             STATUS          current
             DESCRIPTION     "This table contains information on the SELT / DELT feature.
			      The entries are used for SELT / DELT support and operation."
             INDEX           { adGenSlotInfoIndex }
         ::= { adGenSeltDeltTable 1 }

         AdGenSeltDeltEntry ::=
             SEQUENCE {
             adGenSeltDeltTestPortNumber        INTEGER,
             adGenSeltDeltTestFilename          DisplayString,
             adGenSeltDeltStartSELTTest         INTEGER,
             adGenSeltDeltStartDELTTest         INTEGER,
             adGenSeltDeltStopTest              INTEGER,
             adGenSeltDeltCurrentTestStatus     DisplayString,
             adGenSeltDeltLastTestStatus        DisplayString,
             adGenSeltDeltRetrieveData          INTEGER,
	     adGenSeltDeltEnumTestStatus        INTEGER,
--G997 mib type
--             Loop diagnostics for future implementaion
--             adGenXdslineLoopDiagMode           INTEGER,
--             adGenXdslLineLoopDiagStatus        INTEGER,
             adGenSeltDeltTestRemoteDevice      InterfaceIndex

             }


         adGenSeltDeltTestPortNumber OBJECT-TYPE
             SYNTAX      INTEGER  (0..65535)
             MAX-ACCESS  read-write
             STATUS      current
             DESCRIPTION
                 "Selected port number for test operation.
		  The valid range is 0 up to the number of
                  ports on the card. This is functionally
                  equivalent to the port number of the
                  selected interface.
                  
                  Note:  adGenSeltDeltTestRemoteDevice should be
                         provisioned to 0, prior to the setting
                         of this value."
         ::= { adGenSeltDeltEntry 1 }

        adGenSeltDeltTestFilename OBJECT-TYPE
             SYNTAX      DisplayString
             MAX-ACCESS  read-write
             STATUS      current
             DESCRIPTION
                 "Name of the file to be transmitted via TFTP
                  containing all of the test data for the selected
                  interface."
         ::= { adGenSeltDeltEntry 2 }

        adGenSeltDeltStartSELTTest OBJECT-TYPE
             SYNTAX      INTEGER {
                         start(1)
             }
             MAX-ACCESS  read-write
             STATUS      current
             DESCRIPTION
                 "Used to initiate the SELT test for the xDSL port. When
                  the SELT test has completed the data file can be transferred
		  to a server via TFTP using adGenSeltDeltRetrieveData.
                  The TFTP address of the server will be specified by
                  adGenChassisTftpAddr. A get is meaningless and will
		  always return start(1).
	          Note: only one SELT or DELT test can be performed at a time."
         ::= { adGenSeltDeltEntry 3 }

        adGenSeltDeltStartDELTTest OBJECT-TYPE
             SYNTAX      INTEGER {
                         start(1)
             }
             MAX-ACCESS  read-write
             STATUS      current
             DESCRIPTION
                 "Used to initiate the DELT test for the xDSL port. When
                  the DELT test has completed the data file can be transferred
		  to a server via TFTP using adGenSeltDeltRetrieveData.
                  The TFTP address of the server will be specified by
                  adGenChassisTftpAddr. A get is meaningless and will
		  always return start(1).
	          Note: only one SELT or DELT test can be performed at a time."
         ::= { adGenSeltDeltEntry 4 }

        adGenSeltDeltStopTest OBJECT-TYPE
             SYNTAX      INTEGER {
                         stop(1)
             }
             MAX-ACCESS  read-write
             STATUS      current
             DESCRIPTION
                 "Used to terminate the currently active test.
                  A get is meaningless and will always return stop(1)."
         ::= { adGenSeltDeltEntry 5 }

         adGenSeltDeltCurrentTestStatus OBJECT-TYPE
             SYNTAX      DisplayString
             MAX-ACCESS  read-only
             STATUS      current
             DESCRIPTION
                 "Status of the currently active SELT or DELT test."
         ::= { adGenSeltDeltEntry 6 }

         adGenSeltDeltLastTestStatus OBJECT-TYPE
             SYNTAX      DisplayString
             MAX-ACCESS  read-only
             STATUS      current
             DESCRIPTION
                 "Status of the last attempted SELT or DELT test."
         ::= { adGenSeltDeltEntry 7 }

        adGenSeltDeltRetrieveData OBJECT-TYPE
             SYNTAX      INTEGER {
                         beginTransfer(1)
             }
             MAX-ACCESS  read-write
             STATUS      current
             DESCRIPTION
                 "Used to begin the transfer of the diagnostic data
                  to a remote server for evaluation.
                  A get is meaningless and always returns beginTransfer(1)."
         ::= { adGenSeltDeltEntry 8 }

        adGenSeltDeltEnumTestStatus OBJECT-TYPE
             SYNTAX      INTEGER {
                         idle(1),
                         active(2),
                         collectingData(3),
                         dataAvailable(4),
                         testFailed(5)
             }
             MAX-ACCESS  read-only
             STATUS      current
             DESCRIPTION
                 "Used to display the state of the current test in an
                  enumerated format.
                  The descriptions of the values are:
                  idle(1)           - Signifies the unit can accept an activation
                                      command. This response will only occur if no
                                      previous test has completed.
                  active(2)         - Signifies a SELT or DELT test is currently active.
                  collectingData(3) - Signifies the test is complete and the data is
                                      being retrieved from the datapump.
                  dataAvailable(4)  - Signifies the test is complete and the data is
                                      availble for the user to retrieve for evaluation.
                  testFailed(5)     - Signifies the SELT or DELT test failed.
                                      Use adGenSeltDeltLastTestStatus to determine the reason."
         ::= { adGenSeltDeltEntry 9 }

         adGenSeltDeltTestRemoteDevice OBJECT-TYPE
             SYNTAX      InterfaceIndex
             MAX-ACCESS  read-write
             STATUS      current
             DESCRIPTION
                 "The remote device index selected for test operation.
                  
                  NOTE:  adGenSeltDeltTestPortNumber should
                         be set to 0 prior to provisioning of this
                         remote device indexing"
         ::= { adGenSeltDeltEntry 10 }

-- *************************************************************************
-- adGenDeltResults
-- This section defines the response for retrieving DELT data
--
-- ************************************************************************
--          adGenDeltResults   OBJECT-TYPE
--              SYNTAX          AdGenDeltResults
--              MAX-ACCESS      not-accessible
--              STATUS          current
--              DESCRIPTION     "This table contains information on the SELT / DELT feature.
-- 			      The entries are used for retrieval DELT data parameters."
--              INDEX           { adGenSlotInfoIndex, adGenDeltSubcarrier }
--          ::= { adGenSeltDeltTable 2 }
--
--          adGenDeltResults ::=
--              SEQUENCE {
--              adGenDeltSubcarrier        	INTEGER,
--              adGenDeltUpstreamGroupSize        	INTEGER,
--              adGenDeltUpstreamHLINS             INTEGER,
--              adGenDeltUpstreamHLINReal          INTEGER,
--              adGenDeltUpstreamHLINImag          INTEGER,
--              adGenDeltUpstreamHLOG              INTEGER,
--              adGenDeltUpstreamQLN               INTEGER,
--              adGenDeltUpstreamSNR               INTEGER,
--              adGenDeltDownstreamGroupSize      	INTEGER,
--              adGenDeltDownstreamHLINS           INTEGER,
--               adGenDeltDownstreamHLINReal        INTEGER,
--              adGenDeltDownstreamHLINImag        INTEGER,
--              adGenDeltDownstreamHLOG            INTEGER,
--              adGenDeltDownstreamQLN             INTEGER,
--              adGenDeltDownstreamSNR             INTEGER,
--              }
--
--          adGenDeltSubcarrier OBJECT-TYPE
--              SYNTAX      INTEGER
--              MAX-ACCESS  read
--              STATUS      current
--              DESCRIPTION
--                  "Tone group value. For ADSL2 and ADSL2+ this contains the
-- 		  tone for the data presented. For VDSL this contains the
--                   tone group for the data presented."
--          ::= { adGenDeltResults 1 }
--
--          adGenDeltGroupSize OBJECT-TYPE
--              SYNTAX      INTEGER
--              MAX-ACCESS  read
--              STATUS      current
--              DESCRIPTION
--                  "This parameter contains the number of subcarriers per group
-- 	          used to report the DELT information. The valid values are
--                   1,2,3 and 8. For ADSLm the parameter is equal to one(1) and,
-- 	          for VDSL2, it is equal to the size of the subcarrier group
--                   used to compute the parameters."
--          ::= { adGenDeltResults 2 }
--
--          adGenDeltUpstreamHLINS OBJECT-TYPE
--             SYNTAX      INTEGER
--             MAX-ACCESS  read
--             STATUS      current
--             DESCRIPTION
--                 "This parameter is the scale factor to be applied to the
--		  upstream Hlin(f) values. It is represented as an unsigned
--                  interger in the range from 1 ro 2E16-1"
--         ::= { adGenDeltResults 3 }
--
--        adGenDeltUpstreamHLINReal OBJECT-TYPE
--             SYNTAX      INTEGER
--             MAX-ACCESS  read
--             STATUS      current
--             DESCRIPTION
--                 "This parameter is an array of real values in linear scale
--                  for upstream Hlin(f). This parameter is only valid after a
--                  successful loop diagnostic (DELT) procedure."
--         ::= { adGenDeltResults 4 }
--
--        adGenDeltUpstreamHLINImag OBJECT-TYPE
--             SYNTAX      INTEGER
--             MAX-ACCESS  read
--             STATUS      current
--             DESCRIPTION
--                 "This parameter is an array of imag values in linear scale
--                  for upstream Hlin(f). This parameter is only valid after a
--                  successful loop diagnostic (DELT) procedure."
--         ::= { adGenDeltResults 5 }
--
--        adGenDeltUpstreamHLOG OBJECT-TYPE
--             SYNTAX      INTEGER
--             MAX-ACCESS  read
--             STATUS      current
--             DESCRIPTION
--                 "This parameter is an array of real values in dB for
--		  upstream Hlog(f). This parameter is only valid after a
--                  successful loop diagnostic (DELT) procedure."
--         ::= { adGenDeltResults 6 }
--
--        adGenDeltUpstreamQLN OBJECT-TYPE
--             SYNTAX      INTEGER
--             MAX-ACCESS  read
--             STATUS      current
--             DESCRIPTION
--                 "This parameter is an array of real values in dBm/Hz for
--		  upstream QLN(f). This parameter is only valid after a
--                  successful loop diagnostic (DELT) procedure."
--         ::= { adGenDeltResults 7 }
--
--        adGenDeltUpstreamSNR OBJECT-TYPE
--             SYNTAX      INTEGER
--             MAX-ACCESS  read
--             STATUS      current
--             DESCRIPTION
--                 "This parameter is an array of real values in dB for
--		  upstream SNR(f). This parameter is only valid after a
--                  successful loop diagnostic (DELT) procedure."
--         ::= { adGenDeltResults 8 }
--
--         adGenDeltDownstreamHLINS OBJECT-TYPE
--             SYNTAX      INTEGER
--             MAX-ACCESS  read
--             STATUS      current
--             DESCRIPTION
--                 "This parameter is the scale factor to be applied to the
--		  Downstream Hlin(f) values. It is represented as an unsigned
--                  interger in the range from 1 ro 2E16-1"
--         ::= { adGenDeltResults 9 }
--
--        adGenDeltDownstreamHLINReal OBJECT-TYPE
--             SYNTAX      INTEGER
--             MAX-ACCESS  read
--             STATUS      current
--             DESCRIPTION
--                 "This parameter is an array of real values in linear scale
--                  for Downstream Hlin(f). This parameter is only valid after a
--                  successful loop diagnostic (DELT) procedure."
--         ::= { adGenDeltResults 10 }
--
--        adGenDeltDownstreamHLINImag OBJECT-TYPE
--             SYNTAX      INTEGER
--             MAX-ACCESS  read
--             STATUS      current
--             DESCRIPTION
--                 "This parameter is an array of imag values in linear scale
--                  for Downstream Hlin(f). This parameter is only valid after a
--                  successful loop diagnostic (DELT) procedure."
--         ::= { adGenDeltResults 11 }
--
--        adGenDeltDownstreamHLOG OBJECT-TYPE
--             SYNTAX      INTEGER
--             MAX-ACCESS  read
--             STATUS      current
--             DESCRIPTION
--                 "This parameter is an array of real values in dB for
--		  Downstream Hlog(f). This parameter is only valid after a
--                  successful loop diagnostic (DELT) procedure."
--         ::= { adGenDeltResults 12 }
--
--        adGenDeltDownstreamQLN OBJECT-TYPE
--             SYNTAX      INTEGER
--             MAX-ACCESS  read
--             STATUS      current
--             DESCRIPTION
--                 "This parameter is an array of real values in dBm/Hz for
--		  Downstream QLN(f). This parameter is only valid after a
--                  successful loop diagnostic (DELT) procedure."
--         ::= { adGenDeltResults 13 }
--
--        adGenDeltDownstreamSNR OBJECT-TYPE
--             SYNTAX      INTEGER
--             MAX-ACCESS  read
--             STATUS      current
--             DESCRIPTION
--                 "This parameter is an array of real values in dB for
--		  Downstream SNR(f). This parameter is only valid after a
--                  successful loop diagnostic (DELT) procedure."
--         ::= { adGenDeltResults 14 }
--
--
-- *************************************************************************
-- adGenDeltResults
-- This section defines the response for retrieving SELT data
--
-- ************************************************************************
--         adGenSeltResults   OBJECT-TYPE
--             SYNTAX          AdGenSeltResults
--             MAX-ACCESS      not-accessible
--             STATUS          current
--             DESCRIPTION     "This table contains information on the SELT / DELT feature.
--			      The entries are used for retrieval SELT data parameters."
--             INDEX           { adGenSlotInfoIndex }
--         ::= { adGenSeltDeltTable 3 }
--
--         adGenSeltResults ::=
--             SEQUENCE {
--             adGenSeltFDR                     	DisplayString,
--             adGenSeltICN                      	DisplayString,
--             }
--
--         adGenSeltFDR OBJECT-TYPE
--             SYNTAX      DisplayString
--             MAX-ACCESS  read
--             STATUS      current
--             DESCRIPTION
--                 "This parameter contains frequency domain reflectomerty (FDR) echo
--	          response of the loop as determined during the SELT line test."
--         ::= { adGenSeltResults 1 }
--
--         adGenSeltICN OBJECT-TYPE
--             SYNTAX      DisplayString
--             MAX-ACCESS  read
--             STATUS      current
--             DESCRIPTION
--                 "This parameter contains idle channel noise (ICN) response of the
--                  loop as determined during the SELT line test."
--         ::= { adGenSeltResults 2 }






   -- ************************************************************************
   -- MIB Groups
   -- ************************************************************************

   -- ============ Prov Group ================================================
   adGenXdslSeltDeltGroup OBJECT-GROUP
   OBJECTS
   {
             adGenSeltDeltTestPortNumber,
             adGenSeltDeltTestFilename,
             adGenSeltDeltStartSELTTest,
             adGenSeltDeltStartDELTTest,
             adGenSeltDeltStopTest,
             adGenSeltDeltCurrentTestStatus,
             adGenSeltDeltLastTestStatus,
             adGenSeltDeltRetrieveData,
	     adGenSeltDeltEnumTestStatus,
             adGenSeltDeltTestRemoteDevice
   }
   STATUS current
   DESCRIPTION
     "These objects provide support for xDSL SELT / DELT support and operation."
   ::= { adGenXdslMibGroups 1 }


END

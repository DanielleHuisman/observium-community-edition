ADTRAN-GEN-VLAN-MIB

    DEFINITIONS ::= BEGIN

    -- TITLE:     The ADTRAN VLAN MIB
    -- PRODUCT:   TA5000 SMs and AMs
    -- VERSION:   1.0
    -- DATE:      March 3, 2011

    -- This MIB Contains tables related to VLAN Memberships.

    IMPORTS
        MODULE-IDENTITY,
        OBJECT-TYPE,
        Integer32
            FROM SNMPv2-SMI

        adGenVlan,
        adGenVlanID
            FROM  ADTRAN-SHARED-CND-SYSTEM-MIB

        DisplayString
            FROM SNMPv2-TC

        adGenSlotInfoIndex
            FROM ADTRAN-GENSLOT-MIB;


-- *********************************************************************************************************

    adGenVlanModuleIdentity MODULE-IDENTITY
        LAST-UPDATED "201103070000Z"
        ORGANIZATION
            "ADTRAN, Inc."
        CONTACT-INFO
            "CND Tech Support
                Postal: ADTRAN, Inc.
                        901 Explorer Blvd.
                        Huntsville, AL  35806
                        Tel: +1 800 726-8663
                        Fax: +1 256 963 6217
                        E-mail: support@adtran.com"
        DESCRIPTION
            "Total Access 5000 Web GUI MIB"

        REVISION        "201103070000Z"
        DESCRIPTION     "Intial draft."

        ::= { adGenVlanID 1 }


    adGenVlanSlotTable     OBJECT-TYPE
        SYNTAX          SEQUENCE OF AdGenVlanSlotEntry
        MAX-ACCESS      not-accessible
        STATUS          current
        DESCRIPTION
            "This table provides information about VLANs for each slot."
        ::= { adGenVlan 1 }

    adGenVlanSlotEntry        OBJECT-TYPE
       SYNTAX      AdGenVlanSlotEntry
       MAX-ACCESS  not-accessible
       STATUS      current
       DESCRIPTION
            "An entry in the VLAN Slot table."
       INDEX { adGenSlotInfoIndex }
       ::= { adGenVlanSlotTable 1}

    AdGenVlanSlotEntry ::=
       SEQUENCE {
           adGenVlanCount                      Integer32,
           adGenVlanInterfaceList              DisplayString
       }

    adGenVlanCount     OBJECT-TYPE
       SYNTAX      Integer32
       MAX-ACCESS  read-only
       STATUS      current
       DESCRIPTION
            "A count of the number of entries in the Vlan Membership Table for this slot."
       ::= { adGenVlanSlotEntry 1 }

    adGenVlanInterfaceList     OBJECT-TYPE
        SYNTAX          DisplayString
        MAX-ACCESS      read-only
        STATUS          current
        DESCRIPTION
            "A comma-separated list of interface names associated with this slot.
             The order of interfaces in this list matches the order of the VLAN
             membership data in adGenVlanMemberships."
        ::= { adGenVlanSlotEntry 2 }

    adGenVlanDisplayTable OBJECT-TYPE
       SYNTAX      SEQUENCE OF AdGenVlanDisplayEntry
       MAX-ACCESS  not-accessible
       STATUS      current
       DESCRIPTION
           "This table provides information about VLAN memberships in the form of a
            single display string "
       ::= { adGenVlan 2 }

    adGenVlanDisplayEntry OBJECT-TYPE
       SYNTAX      AdGenVlanDisplayEntry
       MAX-ACCESS  not-accessible
       STATUS      current
       DESCRIPTION
           "Each entry in the Vlan Display Table represents memberships for a single VLAN."
       INDEX { adGenSlotInfoIndex, adGenVlanSTag }
       ::= { adGenVlanDisplayTable 1 }

    AdGenVlanDisplayEntry ::=
       SEQUENCE {
           adGenVlanSTag                         INTEGER,
           adGenVlanName                         DisplayString,
           adGenVlanDisplayText                  DisplayString
       }

    adGenVlanSTag      OBJECT-TYPE
        SYNTAX          INTEGER(1..4094)
        MAX-ACCESS      not-accessible
        STATUS          current
        DESCRIPTION     "The S-Tag associated with this VLAN."
        ::= { adGenVlanDisplayEntry 1}

    adGenVlanName      OBJECT-TYPE
        SYNTAX          DisplayString
        MAX-ACCESS      read-only
        STATUS          current
        DESCRIPTION     "The VLAN Name."
        ::= { adGenVlanDisplayEntry 2}

    adGenVlanDisplayText  OBJECT-TYPE
        SYNTAX          DisplayString
        MAX-ACCESS      read-only
        STATUS          current
        DESCRIPTION     "This string represents which interfaces belong to the given VLAN.
                         The string contains 2 ASCII characters for each interface.  The first of
                         the two characters is always a space.  The second character is one of the following:
                                'T' - Member of this VLAN, tunneled
                                '*' - Member of this VLAN, mac-Switched
                                '.' - Not a member of this VLAN.
                         The interfaces are reported in the order specified by adGenVlanInterfaceList."
        ::= { adGenVlanDisplayEntry 3}

END

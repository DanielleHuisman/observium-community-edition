ADTRAN-GENADSL2-LINE-MIB

    DEFINITIONS ::= BEGIN

    -- TITLE:     The ADTRAN TA Octal Adsl MIB 2
    -- PRODUCT:   ADTRAN ADSL Productsfor TOTAL ACCESS
    -- VERSION:   1.1
    -- DATE:      12/22/2011
    -- STATUS:    PRELIMINARY

    -- This MIB defines the SNMPv2 objects for object identifiers (OIDs)

    IMPORTS
        MODULE-IDENTITY,
        OBJECT-TYPE,
        enterprises,
        Gauge32,
        Counter32,
        Integer32,
        Unsigned32
            FROM SNMPv2-SMI
         OBJECT-GROUP
             FROM SNMPv2-CONF
        DisplayString
            FROM SNMPv2-TC
        SnmpAdminString
            FROM SNMP-FRAMEWORK-MIB
        ifIndex
            FROM IF-MIB
        adGenAdsl2,
        adGenAdsl2ID
            FROM ADTRAN-SHARED-ADSL2-MIB         -- v2 version
        ;


-- *********************************************************************************************************
  adGenAdslID MODULE-IDENTITY
         LAST-UPDATED "201201191500Z"
         ORGANIZATION "ADTRAN, Inc."
         CONTACT-INFO
           "CND Tech Support
            Postal: ADTRAN, Inc.
                    901 Explorer Blvd.
                    Huntsville, AL  35806
                    Tel: +1 800 726-8663
                    Fax: +1 256 963 6217
                    E-mail: support@adtran.com"

         DESCRIPTION
              "The is the MIB module that describes
               Octal Adsl SMIv2 objects."

         REVISION "201201191500Z"
         DESCRIPTION "SMD. Added ADSL Line up time OID."
         REVISION "201112220000Z"
         DESCRIPTION
              "Added adGenAdsl2Atuc1DayIntervalCorrectedBlks, adGenAdsl2Atuc1DayIntervalUncorrectedBlks, adGenAdsl2Atur1DayIntervalCorrectedBlks, adGenAdsl2Atur1DayIntervalUncorrectedBlks to fix CN-6026."
         REVISION "201110240000Z"
         DESCRIPTION "Created"
         ::= {  adGenAdsl2ID 1 }

-- ********************************************************************************************************
    -- OBJECT IDENTIFIERS

--  adtran                       OBJECT IDENTIFIER ::= { enterprises 664 }
--    adProducts                 OBJECT IDENTIFIER ::= { adtran 1 }


--    adMgmt           OBJECT IDENTIFIER ::= { adtran 2 }
          adGenAdsl2PM       OBJECT IDENTIFIER ::= { adGenAdsl2 1 }    -- used in ADTRAN-GenADSL2-MIB
          adGenAdsl2MibConformance     OBJECT IDENTIFIER ::= { adGenAdsl2 2 }
          adGenAdsl2MibGroups          OBJECT IDENTIFIER ::= { adGenAdsl2MibConformance 1 }
          adGenAdsl2Status      OBJECT IDENTIFIER ::= { adGenAdsl2 3 }
                    
-- ********************************************************************************************************


--
    -- ========= PM Group (adGenAdsl2Atuc1DayIntervalTable) =================
     adGenAdsl2Atuc1DayIntervalTable   OBJECT-TYPE
         SYNTAX          SEQUENCE OF AdGenAdsl2Atuc1DayIntervalEntry
         MAX-ACCESS      not-accessible
         STATUS          current
         DESCRIPTION
             "This table provides one row for each Atuc
             performance data collection 1 day interval.
             ADSL2 physical interfaces are
             those ifEntries where ifType is equal to adsl(94)."
     ::= { adGenAdsl2PM 1 }

         adGenAdsl2Atuc1DayIntervalEntry   OBJECT-TYPE
             SYNTAX          AdGenAdsl2Atuc1DayIntervalEntry
             MAX-ACCESS      not-accessible
             STATUS          current
             DESCRIPTION     "An entry in the adGenAdsl2Atuc1DayIntervalTable."
             INDEX           { ifIndex, adGenAdsl2Atuc1DayIntervalNumber }
         ::= { adGenAdsl2Atuc1DayIntervalTable 1 }

         AdGenAdsl2Atuc1DayIntervalEntry ::=
             SEQUENCE {
                 adGenAdsl2Atuc1DayIntervalNumber      Integer32,
                 adGenAdsl2Atuc1DayIntervalValidData     INTEGER,
                 adGenAdsl2Atuc1DayIntervalMoniSecs    Counter32,
                 adGenAdsl2Atuc1DayIntervalLofs        Counter32,
                 adGenAdsl2Atuc1DayIntervalLoss        Counter32,
                 adGenAdsl2Atuc1DayIntervalLols        Counter32,
                 adGenAdsl2Atuc1DayIntervalES          Counter32,
                 adGenAdsl2Atuc1DayIntervalInits       Counter32,
                 adGenAdsl2Atuc1DayIntervalCorrectedBlks Counter32,
                 adGenAdsl2Atuc1DayIntervalUncorrectedBlks Counter32,
                 adGenAdsl2Atuc1DayIntervalTxBlks Counter32,
                 adGenAdsl2Atuc1DayIntervalRxBlks Counter32
             }

         adGenAdsl2Atuc1DayIntervalNumber OBJECT-TYPE
             SYNTAX      Integer32(1..7)
             MAX-ACCESS  read-only
             STATUS      current
             DESCRIPTION
                 "Performance Data Interval number 1 is the
                 the most recent previous 1 day interval;
                 interval 7 is 7 Days ago.  Intervals 1..7 are
                 optional."
         ::= { adGenAdsl2Atuc1DayIntervalEntry 1 }

         adGenAdsl2Atuc1DayIntervalValidData OBJECT-TYPE
             SYNTAX      INTEGER {
                 valid (1),            -- no channels exist
                 notValid (2)          -- fast channel exists only
             }
             MAX-ACCESS read-only
             STATUS current
             DESCRIPTION
                 "This variable indicates if the data for this 1 Day
                 interval is valid."
         ::= { adGenAdsl2Atuc1DayIntervalEntry 2 }

         adGenAdsl2Atuc1DayIntervalMoniSecs OBJECT-TYPE
             SYNTAX      Counter32
             UNITS       "seconds"
             MAX-ACCESS  read-only
             STATUS      current
             DESCRIPTION
                 "Count of seconds in the 1 Day interval when there has
                 elasped or monitored."
         ::= { adGenAdsl2Atuc1DayIntervalEntry 3 }

         adGenAdsl2Atuc1DayIntervalLofs OBJECT-TYPE
             SYNTAX      Counter32
             UNITS       "seconds"
             MAX-ACCESS  read-only
             STATUS      current
             DESCRIPTION
                 "Count of seconds in the interval when there was Loss
                 of Framing."
         ::= { adGenAdsl2Atuc1DayIntervalEntry 4 }

         adGenAdsl2Atuc1DayIntervalLoss  OBJECT-TYPE
             SYNTAX      Counter32
             UNITS       "seconds"
             MAX-ACCESS  read-only
             STATUS      current
             DESCRIPTION
                 "Count of seconds in the 1 Day interval when there was Loss
                  of Signal."
         ::= { adGenAdsl2Atuc1DayIntervalEntry 5 }

         adGenAdsl2Atuc1DayIntervalLols  OBJECT-TYPE
             SYNTAX      Counter32
             UNITS       "seconds"
             MAX-ACCESS  read-only
             STATUS      current
             DESCRIPTION
                 "Count of seconds in the 1 Day interval when there was
                  Loss of Link."
         ::= { adGenAdsl2Atuc1DayIntervalEntry 6 }

         adGenAdsl2Atuc1DayIntervalES OBJECT-TYPE
             SYNTAX      Counter32
             UNITS       "seconds"
             MAX-ACCESS  read-only
             STATUS      current
             DESCRIPTION
                 "Count of Errored Seconds in the interval."
         ::= { adGenAdsl2Atuc1DayIntervalEntry 7 }

         adGenAdsl2Atuc1DayIntervalInits  OBJECT-TYPE
             SYNTAX      Counter32
             MAX-ACCESS  read-only
             STATUS      current
             DESCRIPTION
                 "Count of the line initialization attempts
                 during the 1 Day interval. Includes both successful
                 and failed attempts."
         ::= { adGenAdsl2Atuc1DayIntervalEntry 8 }

         adGenAdsl2Atuc1DayIntervalCorrectedBlks  OBJECT-TYPE
             SYNTAX      Counter32
             UNITS       "blocks"
             MAX-ACCESS  read-only
             STATUS      current
             DESCRIPTION
                 "Count of all blocks received with errors that were
                 corrected in the 1 Day interval."
         ::= { adGenAdsl2Atuc1DayIntervalEntry 9 }

         adGenAdsl2Atuc1DayIntervalUncorrectedBlks  OBJECT-TYPE
             SYNTAX      Counter32
             UNITS       "blocks"
             MAX-ACCESS  read-only
             STATUS      current
             DESCRIPTION
                 "Count of all blocks received with uncorrectable
                  errors in the 1 Day interval."
         ::= { adGenAdsl2Atuc1DayIntervalEntry 10 }
         
         adGenAdsl2Atuc1DayIntervalTxBlks  OBJECT-TYPE
             SYNTAX      Counter32
             UNITS       "blocks"
             MAX-ACCESS  read-only
             STATUS      current
             DESCRIPTION
                 "Count of all blocks transmitted
                  in the 1 Day interval."
         ::= { adGenAdsl2Atuc1DayIntervalEntry 11 }

         adGenAdsl2Atuc1DayIntervalRxBlks  OBJECT-TYPE
             SYNTAX      Counter32
             UNITS       "blocks"
             MAX-ACCESS  read-only
             STATUS      current
             DESCRIPTION
                 "Count of all blocks received
                  in the 1 Day interval."
         ::= { adGenAdsl2Atuc1DayIntervalEntry 12 }

         -- ========= PM Group (adGenAdsl2Atur1DayIntervalTable) =================
         adGenAdsl2Atur1DayIntervalTable   OBJECT-TYPE
             SYNTAX          SEQUENCE OF AdGenAdsl2Atur1DayIntervalEntry
             MAX-ACCESS      not-accessible
             STATUS          current
             DESCRIPTION
                 "This table provides one row for each Atur
                 performance data collection 1 Day interval.
                 ADSL2 physical interfaces are those
                 ifEntries where ifType is equal to Adsl(94)."
         ::= { adGenAdsl2PM 2 }

         adGenAdsl2Atur1DayIntervalEntry   OBJECT-TYPE
             SYNTAX          AdGenAdsl2Atur1DayIntervalEntry
             MAX-ACCESS      not-accessible
             STATUS          current
             DESCRIPTION     "An entry in the adGenAdsl2Atur1DayIntervalTable."
             INDEX           { ifIndex, adGenAdsl2Atur1DayIntervalNumber }
         ::= { adGenAdsl2Atur1DayIntervalTable 1 }
		 
         AdGenAdsl2Atur1DayIntervalEntry ::=
             SEQUENCE {
                 adGenAdsl2Atur1DayIntervalNumber      Integer32,
                 adGenAdsl2Atur1DayIntervalValidData     INTEGER,
                 adGenAdsl2Atur1DayIntervalMoniSecs    Counter32,
                 adGenAdsl2Atur1DayIntervalLofs        Counter32,
                 adGenAdsl2Atur1DayIntervalLoss        Counter32,
                 adGenAdsl2Atur1DayIntervalLprs        Counter32,
                 adGenAdsl2Atur1DayIntervalES          Counter32,
                 adGenAdsl2Atur1DayIntervalCorrectedBlks Counter32,
                 adGenAdsl2Atur1DayIntervalUncorrectedBlks Counter32,
                 adGenAdsl2Atur1DayIntervalTxBlks Counter32,
                 adGenAdsl2Atur1DayIntervalRxBlks Counter32
             }

         adGenAdsl2Atur1DayIntervalNumber OBJECT-TYPE
             SYNTAX      Integer32(1..7)
             MAX-ACCESS  read-only
             STATUS      current
             DESCRIPTION
                 "Performance Data Interval number 1 is the
                 the most recent previous 1 day interval;
                 interval 7 is 7 Days ago.  Intervals 1..7 are
                 optional."
         ::= { adGenAdsl2Atur1DayIntervalEntry 1 }

         adGenAdsl2Atur1DayIntervalValidData OBJECT-TYPE
             SYNTAX      INTEGER {
                 valid (1),
                 notValid (2)
             }
             MAX-ACCESS read-only
             STATUS current
             DESCRIPTION
                 "This variable indicates if the data for this 1 Day
                  interval is valid."
         ::= { adGenAdsl2Atur1DayIntervalEntry 2 }

         adGenAdsl2Atur1DayIntervalMoniSecs OBJECT-TYPE
             SYNTAX      Counter32
             UNITS       "seconds"
             MAX-ACCESS  read-only
             STATUS      current
             DESCRIPTION
                 "Count of seconds in the 1 Day interval when there has
                 elasped or monitored."
         ::= { adGenAdsl2Atur1DayIntervalEntry 3 }

         adGenAdsl2Atur1DayIntervalLofs OBJECT-TYPE
             SYNTAX      Counter32
             UNITS       "seconds"
             MAX-ACCESS  read-only
             STATUS      current
             DESCRIPTION
                 "Count of seconds in the 1 Day interval when there was
                 Loss of Framing."
         ::= { adGenAdsl2Atur1DayIntervalEntry 4 }

         adGenAdsl2Atur1DayIntervalLoss  OBJECT-TYPE
             SYNTAX      Counter32
             UNITS       "seconds"
             MAX-ACCESS  read-only
             STATUS      current
             DESCRIPTION
                 "Count of seconds in the 1 Day interval when there was
                 Loss of Signal."
         ::= { adGenAdsl2Atur1DayIntervalEntry 5 }

         adGenAdsl2Atur1DayIntervalLprs  OBJECT-TYPE
             SYNTAX      Counter32
             UNITS       "seconds"
             MAX-ACCESS  read-only
             STATUS      current
             DESCRIPTION
                 "Count of seconds in the 1 Day interval when there was
                 Loss of Power."
         ::= { adGenAdsl2Atur1DayIntervalEntry 6 }

         adGenAdsl2Atur1DayIntervalES OBJECT-TYPE
             SYNTAX      Counter32
             UNITS       "seconds"
             MAX-ACCESS  read-only
             STATUS      current
             DESCRIPTION
                 "Count of Errored Seconds in the 1 Day interval."
         ::= { adGenAdsl2Atur1DayIntervalEntry 7 }

         adGenAdsl2Atur1DayIntervalCorrectedBlks  OBJECT-TYPE
             SYNTAX      Counter32
             UNITS       "blocks"
             MAX-ACCESS  read-only
             STATUS      current
             DESCRIPTION
                 "Count of all blocks received with errors that were
                 corrected in the 1 Day interval."
         ::= { adGenAdsl2Atur1DayIntervalEntry 8 }

         adGenAdsl2Atur1DayIntervalUncorrectedBlks  OBJECT-TYPE
             SYNTAX      Counter32
             UNITS       "blocks"
             MAX-ACCESS  read-only
             STATUS      current
             DESCRIPTION
                 "Count of all blocks received with uncorrectable
                  errors in the 1 Day interval."
         ::= { adGenAdsl2Atur1DayIntervalEntry 9 }
         
         adGenAdsl2Atur1DayIntervalTxBlks  OBJECT-TYPE
             SYNTAX      Counter32
             UNITS       "blocks"
             MAX-ACCESS  read-only
             STATUS      current
             DESCRIPTION
                 "Count of all blocks transmitted
                  in the 1 Day interval."
         ::= { adGenAdsl2Atur1DayIntervalEntry 10 }

         adGenAdsl2Atur1DayIntervalRxBlks  OBJECT-TYPE
             SYNTAX      Counter32
             UNITS       "blocks"
             MAX-ACCESS  read-only
             STATUS      current
             DESCRIPTION
                 "Count of all blocks received
                  in the 1 Day interval."
         ::= { adGenAdsl2Atur1DayIntervalEntry 11 }
		 
		 -- ========= PM Group (adGenAdsl2AtucCurrentIntervalTable) =================
         adGenAdsl2AtucCurrentIntervalTable   OBJECT-TYPE
             SYNTAX          SEQUENCE OF AdGenAdsl2AtucCurrentIntervalEntry
             MAX-ACCESS      not-accessible
             STATUS          current
             DESCRIPTION
                 "This table provides one row for each Atuc
                 performance data collection current interval.
                 ADSL2 physical interfaces are those
                 ifEntries where ifType is equal to Adsl(94)."
         ::= { adGenAdsl2PM 3 }

         adGenAdsl2AtucCurrentIntervalEntry   OBJECT-TYPE
             SYNTAX          AdGenAdsl2AtucCurrentIntervalEntry
             MAX-ACCESS      not-accessible
             STATUS          current
             DESCRIPTION     "An entry in the adGenAdsl2AtucCurrentIntervalTable."
             INDEX           { ifIndex }
         ::= { adGenAdsl2AtucCurrentIntervalTable 1 }
		 
         AdGenAdsl2AtucCurrentIntervalEntry ::=
             SEQUENCE {
				 adGenAdsl2Atuc1DayCurrentIntervalTxBlks Counter32,
				 adGenAdsl2Atuc1DayCurrentIntervalRxBlks Counter32
             }
			 
		 adGenAdsl2Atuc1DayCurrentIntervalTxBlks  OBJECT-TYPE
             SYNTAX      Counter32
             UNITS       "blocks"
             MAX-ACCESS  read-only
             STATUS      current
             DESCRIPTION
                 "Count of all blocks received in the 
				  current 1 day interval."
         ::= { adGenAdsl2AtucCurrentIntervalEntry  1 }

         adGenAdsl2Atuc1DayCurrentIntervalRxBlks  OBJECT-TYPE
             SYNTAX      Counter32
             UNITS       "blocks"
             MAX-ACCESS  read-only
             STATUS      current
             DESCRIPTION
                 "Count of all blocks trasmitted in the 
				  current 1 day interval."
         ::= { adGenAdsl2AtucCurrentIntervalEntry  2 }
		 
		 -- ========= PM Group (adGenAdsl2AturCurrentIntervalTable) =================
         adGenAdsl2AturCurrentIntervalTable   OBJECT-TYPE
             SYNTAX          SEQUENCE OF AdGenAdsl2AturCurrentIntervalEntry
             MAX-ACCESS      not-accessible
             STATUS          current
             DESCRIPTION
                 "This table provides one row for each Atur
                 performance data collection current interval.
                 ADSL2 physical interfaces are those
                 ifEntries where ifType is equal to Adsl(94)."
         ::= { adGenAdsl2PM 4 }

         adGenAdsl2AturCurrentIntervalEntry   OBJECT-TYPE
             SYNTAX          AdGenAdsl2AturCurrentIntervalEntry
             MAX-ACCESS      not-accessible
             STATUS          current
             DESCRIPTION     "An entry in the adGenAdsl2AturCurrentIntervalTable."
             INDEX           { ifIndex }
         ::= { adGenAdsl2AturCurrentIntervalTable 1 }
		 
         AdGenAdsl2AturCurrentIntervalEntry ::=
             SEQUENCE {
				 adGenAdsl2Atur1DayCurrentIntervalTxBlks Counter32,
				 adGenAdsl2Atur1DayCurrentIntervalRxBlks Counter32
             }
             	 
		 adGenAdsl2Atur1DayCurrentIntervalTxBlks  OBJECT-TYPE
             SYNTAX      Counter32
             UNITS       "blocks"
             MAX-ACCESS  read-only
             STATUS      current
             DESCRIPTION
                 "Count of all blocks received in the 
				  current 1 day interval."
         ::= { adGenAdsl2AturCurrentIntervalEntry  1 }

         adGenAdsl2Atur1DayCurrentIntervalRxBlks  OBJECT-TYPE
             SYNTAX      Counter32
             UNITS       "blocks"
             MAX-ACCESS  read-only
             STATUS      current
             DESCRIPTION
                 "Count of all blocks trasmitted in the 
				  current 1 day interval."
         ::= { adGenAdsl2AturCurrentIntervalEntry  2 }

   -- ************************************************************************
   -- MIB Groups
   -- ************************************************************************
    -- ============ Prov Group ================================================

   -- ============ Status Group ===============================================
     adGenAdsl2LineTable OBJECT-TYPE
         SYNTAX          SEQUENCE OF AdGenAdsl2LineEntry
         MAX-ACCESS      not-accessible
         STATUS          current
         DESCRIPTION
             "This table includes common attributes describing
              both ends of the line.  It is required for all ADSL2
              physical interfaces.  ADSL2 physical interfaces are
              those ifEntries where ifType is equal to adsl(94)."
     ::= { adGenAdsl2Status 1 }
     
     adGenAdsl2LineEntry   OBJECT-TYPE
         SYNTAX          AdGenAdsl2LineEntry
         MAX-ACCESS      not-accessible
         STATUS          current
         DESCRIPTION     "An entry in the adGenAdsl2LineTable."
         INDEX           { ifIndex }
     ::= { adGenAdsl2LineTable 1 }
     
     AdGenAdsl2LineEntry ::=
         SEQUENCE {
             adGenAdsl2LineUpTime      Gauge32
         }
         
     adGenAdsl2LineUpTime  OBJECT-TYPE
         SYNTAX      Gauge32
         UNITS       "seconds"
         MAX-ACCESS  read-only
         STATUS      current
         DESCRIPTION
             "Indicates the amount of time the line has
              been in showtime."

     ::= { adGenAdsl2LineEntry 1 }
     
   -- ============ PM Group ==================================================
   adGenAdsl2PMGroup  OBJECT-GROUP
   OBJECTS
   {
                 adGenAdsl2Atuc1DayIntervalNumber,
                 adGenAdsl2Atuc1DayIntervalValidData,
                 adGenAdsl2Atuc1DayIntervalMoniSecs,
                 adGenAdsl2Atuc1DayIntervalLofs,
                 adGenAdsl2Atuc1DayIntervalLoss,
                 adGenAdsl2Atuc1DayIntervalLols,
                 adGenAdsl2Atuc1DayIntervalES,
                 adGenAdsl2Atuc1DayIntervalInits,
                 adGenAdsl2Atuc1DayIntervalCorrectedBlks,
                 adGenAdsl2Atuc1DayIntervalUncorrectedBlks,
				 adGenAdsl2Atuc1DayIntervalTxBlks,
				 adGenAdsl2Atuc1DayIntervalRxBlks,
				 adGenAdsl2Atuc1DayCurrentIntervalTxBlks,
                 adGenAdsl2Atuc1DayCurrentIntervalRxBlks,
                 adGenAdsl2Atur1DayIntervalNumber,
                 adGenAdsl2Atur1DayIntervalValidData,
                 adGenAdsl2Atur1DayIntervalMoniSecs,
                 adGenAdsl2Atur1DayIntervalLofs,
                 adGenAdsl2Atur1DayIntervalLoss,
                 adGenAdsl2Atur1DayIntervalLprs,
                 adGenAdsl2Atur1DayIntervalES,
                 adGenAdsl2Atur1DayIntervalCorrectedBlks,
                 adGenAdsl2Atur1DayIntervalUncorrectedBlks,
				 adGenAdsl2Atur1DayCurrentIntervalTxBlks,
                 adGenAdsl2Atur1DayCurrentIntervalRxBlks,
				 adGenAdsl2Atur1DayIntervalTxBlks,
				 adGenAdsl2Atur1DayIntervalRxBlks
   }
   STATUS current
   DESCRIPTION
     "These objects provide support for the reporting of the
      Adsl2 interface PM data."
   ::= { adGenAdsl2MibGroups 1}


   -- ============ Traps Group ================================================

   -- ============ Test Group ================================================


    END

ADTRAN-GENAUTOCONFIG-MIB

-- TITLE:     The ADTRAN Auto-Config MIB
-- PRODUCT:   ADTRAN products supporting Auto-Config
-- VERSION:   1.0
-- DATE:      10/13/2014
-- AUTHOR:    Byron Young
-- STATUS:    PRELIMINARY

-- This MIB defines the object identifiers (OIDs) for the ADTRAN Auto-Config MIB objects

-- ******************************************************************************************
DEFINITIONS ::= BEGIN

IMPORTS
   MODULE-IDENTITY,
   OBJECT-TYPE,
   NOTIFICATION-TYPE,
   Unsigned32
      FROM SNMPv2-SMI
   InetAddressIPv4,
   InetAddressIPv6
      FROM INET-ADDRESS-MIB
   sysName
      FROM SNMPv2-MIB
   TruthValue,
   DisplayString
      FROM SNMPv2-TC
   adTrapInformSeqNum
      FROM ADTRAN-GENTRAPINFORM-MIB
   adGenAutoConfig,
   adGenAutoConfigID
       FROM ADTRAN-SHARED-CND-SYSTEM-MIB
   adGenSlotProdPartNumber,
   adGenSlotProdSwVersion
      FROM ADTRAN-GENSLOT-MIB
   ;

adGenAutoConfigMIB MODULE-IDENTITY
   LAST-UPDATED "201410130000Z"
   ORGANIZATION "Adtran, Inc."
   CONTACT-INFO
     "CND Tech Support
         Postal: ADTRAN, Inc.
                 901 Explorer Blvd.
                 Huntsville, AL  35806
                 Tel: +1 800 726 8663
                 Fax: +1 256 963 6217
                 E-mail: support@adtran.com"
   DESCRIPTION
      "This MIB defines the objects for the Auto-Config MIB."

   REVISION "201410130000Z"
   DESCRIPTION "Created"

::= { adGenAutoConfigID 1 }

adGenAutoConfigEvents        OBJECT IDENTIFIER ::= {adGenAutoConfig 0}
adGenAutoConfigStatus        OBJECT IDENTIFIER ::= {adGenAutoConfig 1}
adGenAutoConfigProvisioning  OBJECT IDENTIFIER ::= {adGenAutoConfig 2}

   adGenAutoConfigEnabled OBJECT-TYPE
      SYNTAX       TruthValue
      MAX-ACCESS   read-only
      STATUS       current
      DESCRIPTION
        "The Auto-Config administrative state. When set to true, the
         Auto-Config feature is enabled on the network element."
       ::= {adGenAutoConfigStatus 1}

   adGenAutoConfigHostIPv4 OBJECT-TYPE
      SYNTAX      InetAddressIPv4
      MAX-ACCESS  read-only
      STATUS      current
      DESCRIPTION
          "The file server IPv4 address"
      ::= {adGenAutoConfigStatus 2}

   adGenAutoConfigHostIPv6 OBJECT-TYPE
      SYNTAX      InetAddressIPv6
      MAX-ACCESS  read-only
      STATUS      current
      DESCRIPTION
          "The file server IPv6 address"
      ::= {adGenAutoConfigStatus 3}

   adGenAutoConfigFilename OBJECT-TYPE
      SYNTAX      DisplayString
      MAX-ACCESS  read-only
      STATUS      current
      DESCRIPTION
         "The Auto-Config filename. This is the first file retrieved and
          parsed by the network element during the Auto-Config sequence.
          This file contains options and filenames that apply to the remainder
          of the Auto-Config sequence. This value provides the filename after
          any variable substitution is performed."
      ::= {adGenAutoConfigStatus 4}

   adGenAutoConfigGroupName OBJECT-TYPE
      SYNTAX      DisplayString
      MAX-ACCESS  read-only
      STATUS      current
      DESCRIPTION
         "The Auto-Config group name. The network element will substitute
          this value in filenames that contain a predefined keyword. This
          can be useful for customization purposes."
      ::= {adGenAutoConfigStatus 5}

   adGenAutoConfigTempConfigFilename OBJECT-TYPE
      SYNTAX      DisplayString
      MAX-ACCESS  read-only
      STATUS      current
      DESCRIPTION
         "The Auto-Config temporary configuration filename. This is a network
          element configuration file that can exist on the server for troubleshooting
          purposes. The network element will attempt to retrieve configuration files
          in the following order:
             1) temporary config
             2) unit config
             3) base config
          The network element learns this filename via the auto-config file.
          This value provides the filename after any variable substitution is
          performed."
      ::= {adGenAutoConfigStatus 6}

   adGenAutoConfigUnitConfigFilename OBJECT-TYPE
      SYNTAX      DisplayString
      MAX-ACCESS  read-only
      STATUS      current
      DESCRIPTION
         "The Auto-Config unit configuration filename. This is a network
          element configuration file that can exist on the server for normal
          operation. The network element will attempt to retrieve configuration
          files in the following order:
             1) temporary config
             2) unit config
             3) base config
          The network element learns this filename via the auto-config file.
          This value provides the filename after any variable substitution is
          performed."
      ::= {adGenAutoConfigStatus 7}

   adGenAutoConfigBaseConfigFilename OBJECT-TYPE
      SYNTAX      DisplayString
      MAX-ACCESS  read-only
      STATUS      current
      DESCRIPTION
         "The Auto-Config base configuration filename. This is a network
          element configuration file that can exist on the server to provide
          a common initial configuration for multiple network elements.
          The network element will attempt to retrieve configuration files in
          the following order:
             1) temporary config
             2) unit config
             3) base config
          The network element learns this filename via the auto-config file.
          This value provides the filename after any variable substitution is
          performed."
      ::= {adGenAutoConfigStatus 8}

   adGenAutoConfigFirmwareDefinitionFilename OBJECT-TYPE
      SYNTAX      DisplayString
      MAX-ACCESS  read-only
      STATUS      current
      DESCRIPTION
         "The Auto-Config firmware definition filename. This file lists
         firmware filename(s) that the network element should retrieve
         during the Auto-Config sequence. The network element learns this
         firmware definition filename via the auto-config file. This value
         provides the filename after any variable substitution is performed."
      ::= {adGenAutoConfigStatus 9}

   adGenAutoConfigRetryCount OBJECT-TYPE
      SYNTAX      Unsigned32 ( 0..10 )
      MAX-ACCESS  read-only
      STATUS      current
      DESCRIPTION
         "The Auto-Config retry count. When the network element attempts to
          retrieve a file from the server, it will restart the Auto-Config
          sequence if this maximum number of application-layer retries is
          exhausted."
      ::= {adGenAutoConfigStatus 10}

   adGenAutoConfigPollingInterval OBJECT-TYPE
      SYNTAX      Unsigned32 ( 0..2592000 )
      MAX-ACCESS  read-only
      STATUS      current
      DESCRIPTION
         "The Auto-Config polling interval in seconds. The network element will
          periodically restart the Auto-Config sequence on this interval. A value
          of zero disables the periodic restart of the sequence."
      ::= {adGenAutoConfigStatus 11}

   adGenAutoConfigProtocol OBJECT-TYPE
      SYNTAX      INTEGER { tftp(1), ftp(2), sftp(3) }
      MAX-ACCESS  read-only
      STATUS      current
      DESCRIPTION
         "The file transfer protocol that the network element uses to retrieve
         files from the server during the Auto-Config sequence."
      ::= {adGenAutoConfigStatus 12}

   adGenAutoConfigProtocolPortSFTP OBJECT-TYPE
      SYNTAX      Unsigned32 ( 1..65535 )
      MAX-ACCESS  read-only
      STATUS      current
      DESCRIPTION
         "The TCP port number that applies when the protocol is SFTP."
      ::= {adGenAutoConfigStatus 13}

   adGenAutoConfigLastFailureFilename OBJECT-TYPE
      SYNTAX      DisplayString
      MAX-ACCESS  read-only
      STATUS      current
      DESCRIPTION
         "If the network element encounters a problem that causes the Auto-Config
          sequence to fail, this value will provide the filename that relates to
          the failure. This value provides the filename after any variable
          substitution is performed."
      ::= {adGenAutoConfigStatus 14}

   adGenAutoConfigLastFailureReason OBJECT-TYPE
      SYNTAX      DisplayString
      MAX-ACCESS  read-only
      STATUS      current
      DESCRIPTION
         "If the network element encounters a problem that causes the Auto-Config
          sequence to fail, this value will provide a descriptive reason for the
          failure."
      ::= {adGenAutoConfigStatus 15}

   adGenAutoConfigCurrentStatus OBJECT-TYPE
      SYNTAX      DisplayString
      MAX-ACCESS  read-only
      STATUS      current
      DESCRIPTION
         "This value provides the current status of the Auto-Config subsystem."
      ::= {adGenAutoConfigStatus 16}

   adGenAutoConfigFailureAlmSeverity OBJECT-TYPE
      SYNTAX INTEGER {
         disabled(1),
         info(2),
         alert(3),
         minor(4),
         major(5),
         critical(6)
      }
      MAX-ACCESS read-only
      STATUS current
      DESCRIPTION
         "Alarm severity for the Auto-Config failure alarm."
      ::= {adGenAutoConfigStatus 17}

   adGenAutoConfigTimeoutAlmSeverity OBJECT-TYPE
      SYNTAX INTEGER {
         disabled(1),
         info(2),
         alert(3),
         minor(4),
         major(5),
         critical(6)
      }
      MAX-ACCESS read-only
      STATUS current
      DESCRIPTION
         "Alarm severity for the Auto-Config timeout alarm."
      ::= {adGenAutoConfigStatus 18}

   adGenAutoConfigRestart OBJECT-TYPE
      SYNTAX  INTEGER {
         restart(1)
      }
      MAX-ACCESS  read-write
      STATUS  current
      DESCRIPTION
        "When Auto-Config is enabled, this value can be set to cause the
         Auto-Config sequence to restart."
      ::= {adGenAutoConfigProvisioning 1}

   adGenAutoConfigFailureAlm NOTIFICATION-TYPE
      OBJECTS  {
         adTrapInformSeqNum,
         sysName,
         adGenAutoConfigFailureAlmSeverity,
         adGenSlotProdPartNumber,
         adGenSlotProdSwVersion,
         adGenAutoConfigHostIPv4,
         adGenAutoConfigHostIPv6,
         adGenAutoConfigFilename,
         adGenAutoConfigGroupName,
         adGenAutoConfigTempConfigFilename,
         adGenAutoConfigUnitConfigFilename,
         adGenAutoConfigBaseConfigFilename,
         adGenAutoConfigFirmwareDefinitionFilename,
         adGenAutoConfigLastFailureFilename,
         adGenAutoConfigLastFailureReason
      }
      STATUS  current
      DESCRIPTION
         "This notification indicates a failure in the Auto-Config sequence
          that may require user intervention to resolve. Possible reasons the
          network element may activate this alarm may include:
            1) A received file is rejected because it is corrupt
            2) A received file is rejected because it does not apply to the
               network element or does not meet minimum requirements
            3) A critical file does not exist on the file server"
         --#TYPE         "Status - Alarm"
         --#SUMMARY      "Auto-Config Failure"
         --#SEVERITY     MAJOR
         --#GENERIC      6
         --#CATEGORY     "Error Events"
         --#SOURCE_ID    "A"
         --#TIMEINDEX    0
      ::= {adGenAutoConfigEvents 1}

   adGenAutoConfigTimeoutAlm NOTIFICATION-TYPE
      OBJECTS  {
         adTrapInformSeqNum,
         sysName,
         adGenAutoConfigTimeoutAlmSeverity,
         adGenSlotProdPartNumber,
         adGenSlotProdSwVersion,
         adGenAutoConfigHostIPv4,
         adGenAutoConfigHostIPv6,
         adGenAutoConfigLastFailureFilename
      }
      STATUS  current
      DESCRIPTION
         "This notification indicates the network element has exhausted all of
          its application-layer retries when attempting to retrieve a file from
          the server during the Auto-Config sequence."
         --#TYPE         "Status - Alarm"
         --#SUMMARY      "Auto-Config Timeout"
         --#SEVERITY     WARNING
         --#GENERIC      6
         --#CATEGORY     "Informational Events"
         --#SOURCE_ID    "A"
         --#TIMEINDEX    0
      ::= {adGenAutoConfigEvents 2}

END

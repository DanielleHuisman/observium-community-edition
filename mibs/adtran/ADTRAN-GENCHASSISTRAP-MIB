ADTRAN-GENCHASSISTRAP-MIB   DEFINITIONS ::= BEGIN

     -- TITLE:       Generic chassis trap MIB
     -- PRODUCT:     All chassis type products
     -- VERSION:     1.0
     -- DATE:        00/06/26
     -- AUTHOR:      Theresa Chard
     -- SNMP:        SNMPv1
     -- MIB ARC:     adtran.adShared.adGenericShelves
     -- FILE:        genctrap.mib

     -- HISTORY:
        -- 06/26/00 tgc defined card removal and insertion traps
        -- 08/10/00 pnb insert all generic chassis traps
        --              clarify that link up/link down are mgmt links (AMCP)
        --              change link down cleared to link up
        --              removed blown fuse alarm clear - can't happen
        --              removed unknown card fuse blown - superfluous
        -- 09/28/00 pnb converted trap sequence number to object in genport.mib
        --              since all trap objects were allocated to gentrap.mib.
        --              This changed MO name from adGenChassisSeqNum to
        --              adTrapInformSeqNum
        -- 04/03/01 pnb Removed mgmtup/down link traps, and removed superfluous
        --              varbinds from others. Added prefix to all trap names.
        -- 04/06/01 pnb Removed 6th major alarm traps.
        -- 05/09/01 pnb Add service state traps
        -- 05/10/01 pnb Added comment about previously used OIDs.
        -- 05/10/01 pnb Changed all names to reduce size for HP OpenView limitations



     IMPORTS
           sysName
               FROM RFC1213-MIB
           TRAP-TYPE
               FROM RFC-1215
           adGenericShelves
               FROM ADTRAN-GENCHASSIS-MIB
           adGenSlotInfoIndex,
           adGenSlotAlarmStatus
               FROM ADTRAN-GENSLOT-MIB
           adGenPortTrapIdentifier
               FROM ADTRAN-GENPORT-MIB
           adTrapInformSeqNum
               FROM ADTRAN-GENTRAPINFORM-MIB
           ;

-- branch in MIB tree

--     adGenericShelves  OBJECT IDENTIFIER ::= { adShared 13 }


-- *******************************************************************************************************

-- ********************************************************************************************************

-- Generic Chassis Traps

        -- traps 00 and 01 were mgmtLinkUp and Down. obsolete.

        adCtrpCardInserted   TRAP-TYPE
                ENTERPRISE      adGenericShelves
                VARIABLES       {
                        adTrapInformSeqNum,
                        sysName,
                        adGenSlotInfoIndex
                        }
                DESCRIPTION
                        "A card has been inserted into the chassis"
        --#TYPE      "Warning - A card has been inserted into the chassis"
        --#SUMMARY   "GENCHASSIS 1001302: Card inserted into chassis;"
        --#SUMMARY   "detected at chassis: %s, slot: %d"
        --#ARGUMENTS { 1, 2 }
        --#SEVERITY  NORMAL
        --#GENERIC   6
        --#CATEGORY  "Configuration Events"
        --#SOURCE_ID "A"
        --#TIMEINDEX 0
        ::= 1001302


        adCtrpCardRemoved   TRAP-TYPE
                ENTERPRISE      adGenericShelves
                VARIABLES       {
                        adTrapInformSeqNum,
                        sysName,
                        adGenSlotInfoIndex
                        }
                DESCRIPTION
                        "A card has been removed from the chassis"
        --#TYPE      "Warning - A card has been removed from the chassis"
        --#SUMMARY   "GENCHASSIS 1001303: Card removed from chassis;"
        --#SUMMARY   "detected at chassis: %s, slot: %d"
        --#ARGUMENTS { 1, 2 }
        --#SEVERITY  WARNING
        --#GENERIC   6
        --#CATEGORY  "Configuration Events"
        --#SOURCE_ID "A"
        --#TIMEINDEX 0
        ::= 1001303

        adCtrpBlownFuse    TRAP-TYPE
                ENTERPRISE      adGenericShelves
                VARIABLES       {
                        adTrapInformSeqNum,
                        sysName,
                        adGenSlotInfoIndex
                        }
                DESCRIPTION
                        "Blown Fuse Alarm is active on module"
        --#TYPE      "Major - Blown Fuse Alarm is active on module"
        --#SUMMARY   "GENCHASSIS 1001305: Blown Fuse Alarm active;"
        --#SUMMARY   "detected at shelf: %s, slot: %d"
        --#ARGUMENTS { 1, 2 }
        --#SEVERITY  MAJOR
        --#GENERIC   6
        --#CATEGORY  "Error Events"
        --#SOURCE_ID "A"
        --#TIMEINDEX 0
        ::= 1001305

        -- trap 06 and 07 were 6th major alarm traps. obsolete.


        adCtrpRmtAlmClear    TRAP-TYPE
                ENTERPRISE      adGenericShelves
                VARIABLES       {
                        adTrapInformSeqNum,
                        sysName
                        }
                DESCRIPTION
                        "Remote Input Alarm clear"
        --#TYPE      "Major - Remote Input Alarm clear"
        --#SUMMARY   "GENCHASSIS 1001308: Remote Input Alarm cleared;"
        --#SUMMARY   "detected at shelf: %s"
        --#ARGUMENTS { 1 }
        --#SEVERITY  NORMAL
        --#GENERIC   6
        --#CATEGORY  "Error Events"
        --#SOURCE_ID "A"
        --#TIMEINDEX 0
        ::= 1001308

        adCtrpRmtAlm    TRAP-TYPE
                ENTERPRISE      adGenericShelves
                VARIABLES       {
                        adTrapInformSeqNum,
                        sysName
                        }
                DESCRIPTION
                        "Remote Input Alarm active"
        --#TYPE      "Major - Remote Input Alarm active"
        --#SUMMARY   "GENCHASSIS 1001309: Remote Input Alarm active;"
        --#SUMMARY   "detected at shelf: %s"
        --#ARGUMENTS { 1 }
        --#SEVERITY  MAJOR
        --#GENERIC   6
        --#CATEGORY  "Error Events"
        --#SOURCE_ID "A"
        --#TIMEINDEX 0
        ::= 1001309

        adCtrpExt1AlmClear    TRAP-TYPE
                ENTERPRISE      adGenericShelves
                VARIABLES       {
                        adTrapInformSeqNum,
                        sysName
                        }
                DESCRIPTION
                        "External Input #1 Alarm clear"
        --#TYPE      "Minor - External Input #1 Alarm clear"
        --#SUMMARY   "GENCHASSIS 1001310: External Input #1 Alarm cleared;"
        --#SUMMARY   "detected at shelf: %s"
        --#ARGUMENTS { 1 }
        --#SEVERITY  NORMAL
        --#GENERIC   6
        --#CATEGORY  "Error Events"
        --#SOURCE_ID "A"
        --#TIMEINDEX 0
        ::= 1001310

        adCtrpExt1Alm    TRAP-TYPE
                ENTERPRISE      adGenericShelves
                VARIABLES       {
                        adTrapInformSeqNum,
                        sysName
                        }
                DESCRIPTION
                        "External Input #1 Alarm active"
        --#TYPE      "Minor - External Input #1 Alarm active"
        --#SUMMARY   "GENCHASSIS 1001311: External Input #1 Alarm active;"
        --#SUMMARY   "detected at shelf: %s"
        --#ARGUMENTS { 1 }
        --#SEVERITY  MINOR
        --#GENERIC   6
        --#CATEGORY  "Error Events"
        --#SOURCE_ID "A"
        --#TIMEINDEX 0
        ::= 1001311

        adCtrpExt2AlmClear    TRAP-TYPE
                ENTERPRISE      adGenericShelves
                VARIABLES       {
                        adTrapInformSeqNum,
                        sysName
                        }
                DESCRIPTION
                        "External Input #2 Alarm clear"
        --#TYPE      "Warning - External Input #2 Alarm clear"
        --#SUMMARY   "GENCHASSIS 1001312: External Input #2 Alarm cleared;"
        --#SUMMARY   "detected at shelf: %s"
        --#ARGUMENTS { 1 }
        --#SEVERITY  NORMAL
        --#GENERIC   6
        --#CATEGORY  "Error Events"
        --#SOURCE_ID "A"
        --#TIMEINDEX 0
        ::= 1001312

        adCtrpExt2Alm    TRAP-TYPE
                ENTERPRISE      adGenericShelves
                VARIABLES       {
                        adTrapInformSeqNum,
                        sysName
                        }
                DESCRIPTION
                        "External Input #2 Alarm active"
        --#TYPE      "Warning - External Input #2 Alarm active"
        --#SUMMARY   "GENCHASSIS 1001313: External Input #2 Alarm active;"
        --#SUMMARY   "detected at shelf: %s"
        --#ARGUMENTS { 1 }
        --#SEVERITY  WARNING
        --#GENERIC   6
        --#CATEGORY  "Error Events"
        --#SOURCE_ID "A"
        --#TIMEINDEX 0
        ::= 1001313

        adCtrpBusApwrAlmClear    TRAP-TYPE
                ENTERPRISE      adGenericShelves
                VARIABLES       {
                        adTrapInformSeqNum,
                        sysName
                        }
                DESCRIPTION
                        "Bus A Power Failure Alarm clear"
        --#TYPE      "Minor - Bus A Power Failure Alarm clear"
        --#SUMMARY   "GENCHASSIS 1001314: Bus A Power Failure Alarm cleared;"
        --#SUMMARY   "detected at shelf: %s"
        --#ARGUMENTS { 1 }
        --#SEVERITY  NORMAL
        --#GENERIC   6
        --#CATEGORY  "Error Events"
        --#SOURCE_ID "A"
        --#TIMEINDEX 0
        ::= 1001314

        adCtrpBusApowerAlm    TRAP-TYPE
                ENTERPRISE      adGenericShelves
                VARIABLES       {
                        adTrapInformSeqNum,
                        sysName
                        }
                DESCRIPTION
                        "Bus A Power Failure Alarm active"
        --#TYPE      "Minor - Bus A Power Failure Alarm active"
        --#SUMMARY   "GENCHASSIS 1001315: Bus A Power Failure Alarm active;"
        --#SUMMARY   "detected at shelf: %s"
        --#ARGUMENTS { 1 }
        --#SEVERITY  MINOR
        --#GENERIC   6
        --#CATEGORY  "Error Events"
        --#SOURCE_ID "A"
        --#TIMEINDEX 0
        ::= 1001315

        adCtrpBusBpwrAlmClear    TRAP-TYPE
                ENTERPRISE      adGenericShelves
                VARIABLES       {
                        adTrapInformSeqNum,
                        sysName
                        }
                DESCRIPTION
                        "Bus B Power Failure Alarm clear"
        --#TYPE      "Minor - Bus B Power Failure Alarm clear"
        --#SUMMARY   "GENCHASSIS 1001316: Bus B Power Failure Alarm cleared;"
        --#SUMMARY   "detected at shelf: %s"
        --#ARGUMENTS { 1 }
        --#SEVERITY  NORMAL
        --#GENERIC   6
        --#CATEGORY  "Error Events"
        --#SOURCE_ID "A"
        --#TIMEINDEX 0
        ::= 1001316

        adCtrpBusBpowerAlm    TRAP-TYPE
                ENTERPRISE      adGenericShelves
                VARIABLES       {
                        adTrapInformSeqNum,
                        sysName
                        }
                DESCRIPTION
                        "Bus B Power Failure Alarm active"
        --#TYPE      "Minor - Bus B Power Failure Alarm active"
        --#SUMMARY   "GENCHASSIS 1001317: Bus B Power Failure Alarm active;"
        --#SUMMARY   "detected at shelf: %s"
        --#ARGUMENTS { 1 }
        --#SEVERITY  MINOR
        --#GENERIC   6
        --#CATEGORY  "Error Events"
        --#SOURCE_ID "A"
        --#TIMEINDEX 0
        ::= 1001317

        adCtrpInService   TRAP-TYPE
                ENTERPRISE      adGenericShelves
                VARIABLES       {
                        adTrapInformSeqNum,
                        sysName,
                        adGenSlotInfoIndex
                        }
                DESCRIPTION
                        "A card has entered the In-Service state"
        --#TYPE      "Minor - A card has entered the In-Service state"
        --#SUMMARY   "GENCHASSIS 1001318: Card is now In-Service; "
        --#SUMMARY   "detected at chassis: %s, slot: %d"
        --#ARGUMENTS { 1, 2 }
        --#SEVERITY  MINOR
        --#GENERIC   6
        --#CATEGORY  "Error Events"
        --#SOURCE_ID "A"
        --#TIMEINDEX 0
        ::= 1001318


        adCtrpOutOfService   TRAP-TYPE
                ENTERPRISE      adGenericShelves
                VARIABLES       {
                        adTrapInformSeqNum,
                        sysName,
                        adGenSlotInfoIndex
                        }
                DESCRIPTION
                        "A card has entered the Out-Of-Service state"
        --#TYPE      "Minor - A card has entered the Out-Of-Service state"
        --#SUMMARY   "GENCHASSIS 1001319: Card is now Out-Of-Service; "
        --#SUMMARY   "detected at chassis: %s, slot: %d"
        --#ARGUMENTS { 1, 2 }
        --#SEVERITY  MINOR
        --#GENERIC   6
        --#CATEGORY  "Error Events"
        --#SOURCE_ID "A"
        --#TIMEINDEX 0
        ::= 1001319


   END

ADTRAN-GENERIC-OTN-MIB

-- TITLE:     The ADTRAN OTN MIB
-- PRODUCT:   ADTRAN OTN Products
-- AUTHOR:    Jim Vance

-- This MIB defines the object identifiers (OIDs) for the
-- ADTRAN OTN MIB objects

-- Abbreviation Definitions as defined in ITU G.709
-- OTN    Optical Transport Network
-- OTU    Optical channel Transport Unit
-- OPU    Optical channel Payload Unit
-- ODU    Optical channel Data Unit

-- ******************************************************************************************
DEFINITIONS ::= BEGIN

--==================================================================================================================

IMPORTS
  MODULE-IDENTITY,
  Counter64,
  Counter32,
  NOTIFICATION-TYPE,
  OBJECT-TYPE,
  Unsigned32                FROM SNMPv2-SMI

  Unsigned64TC              FROM APPLICATION-MIB

  TEXTUAL-CONVENTION,
  RowStatus,
  TruthValue,
  DisplayString             FROM SNMPv2-TC

  sysName                   FROM SNMPv2-MIB

  adGenSlotInfoIndex        FROM ADTRAN-GENSLOT-MIB

  InterfaceIndex,
  ifDescr,
  ifIndex                   FROM IF-MIB

  adTrapInformSeqNum        FROM ADTRAN-GENTRAPINFORM-MIB

  adTAeSCUTrapAlarmLevel    FROM ADTRAN-TAeSCUEXT1-MIB

  adGenOtn,
  adGenOtnID                FROM ADTRAN-SHARED-CND-SYSTEM-MIB;

  -- Module Identifier
  adGenOtnIdentity MODULE-IDENTITY
       LAST-UPDATED "201410170000Z"
       ORGANIZATION "ADTRAN, Inc."
       CONTACT-INFO
              "        Technical Support Dept.
               Postal: ADTRAN, Inc.
                       901 Explorer Blvd.
                       Huntsville, AL 35806

                  Tel: +1 800 726-8663
                  Fax: +1 256 963 6217
               E-mail: support@adtran.com"
       DESCRIPTION
              "The MIB module that describes the generic OTN
               objects to manage cards with OTN interfaces."

       REVISION "201410170000Z"
       DESCRIPTION  "Added adGenOtnProtGroupWaitToRestoreRemainingTime to adGenOtnProtGroupEntry."

       REVISION "201409090000Z"
       DESCRIPTION "Added adGenOtnOduLoomfiClrAlm and adGenOtnOduLoomfiActAlm.
                    Added lossOfOpuMultiFrameIdentifier to adGenOtnSlotOduAlarmEnable and adGenOtnOduAlarmStatus."

       REVISION "201306100000Z"
       DESCRIPTION "Added adGenOtnOtuCounters and adGenOtnOduCounters."

       REVISION "201301080000Z"
       DESCRIPTION "Added adGenOtnOtuTraceAutoTxOperatorSpecEnable and adGenOtnOtuTraceTxOperatorSpecActual.
                    Updated descriptions for adGenOtnOtuTraceTxOperatorSpec and adGenOtnOtuTraceRxOperatorSpec.
                    Added a status of 'down' for protection group entities."

       REVISION "201212040000Z"
       DESCRIPTION "Added adGenOtnOduCsfClrAlm and adGenOtnOduCsfActAlm.
                    Added clientSignalFail to adGenOtnSlotOduAlarmEnable and adGenOtnOduAlarmStatus."

       REVISION "201210190000Z"
       DESCRIPTION "Added adGenOtnOdu2Odu3AutoPayloadType."

       REVISION "201208210000Z"
       DESCRIPTION "Added adGenOtnProtGroupOperStatus and adGenOtnProtGroupStatusString.
                    Added yCable to the list of protection group types."

       REVISION "201207190000Z"
       DESCRIPTION "Updated OIDs adGenOtnOtuMode, adGenOtnOtuSupportedModes,
                    adGenOtnOduMode and adGenOtnOduSupportedModes to support
                    Frame-mapped Generic Framing Procedure and Frame-mapped
                    Generic Framing Procedure Semi-transparent modes."

       REVISION "201203080000Z"
       DESCRIPTION  "Modified adGenOtnOduOciClrAlm and adGenOtnOduOciActAlm to
                     have a severity of Critical since they are service affecting."

       REVISION "201201170000Z"
       DESCRIPTION  "Modified adGenOtnOtuAlarmStatus and adGenOtnOduAlarmStatus to
                     include TIM with Consequence."

       REVISION "201112200000Z"
       DESCRIPTION  "Added adGenOtnPmInterfaceTable, adGenOtnPmSlotTable,
                           adGenOtnOtuPm15MinIntervalNeValidData,
									adGenOtnOtuPm15MinIntervalFeValidData,
							      adGenOtnOtuPm24HrIntervalNeValidData,
									adGenOtnOtuPm24HrIntervalFeValidData,
							      adGenOtnOduPm15MinIntervalNeValidData,
									adGenOtnOduPm15MinIntervalFeValidData,
							      adGenOtnOduPm24HrIntervalNeValidData,
									adGenOtnOduPm24HrIntervalFeValidData"

       REVISION "201112080000Z"
       DESCRIPTION  "Added adGenOtnProtGroupTable, adGenOtnProtGroupLastCreateErrorTable,
                     adGenOtnOtuFecType and adGenOtnOtuSupportedFecType."

      ::= { adGenOtnID 1 }

  -- OBJECT IDENTIFIERS
  adGenOtnProv                      OBJECT IDENTIFIER ::= { adGenOtn 1  }
  adGenOtnStatus                    OBJECT IDENTIFIER ::= { adGenOtn 2  }
  adGenOtnPmThres                   OBJECT IDENTIFIER ::= { adGenOtn 3  }
  adGenOtnPm                        OBJECT IDENTIFIER ::= { adGenOtn 4  }
  adGenOtnPmInterface     			OBJECT IDENTIFIER ::= { adGenOtn 5  }
  adGenOtnPmSlot          		 	OBJECT IDENTIFIER ::= { adGenOtn 6  }

  adGenOtnOtuAlms                   OBJECT IDENTIFIER ::= { adGenOtn 10  }
  adGenOtnOduAlms                   OBJECT IDENTIFIER ::= { adGenOtn 11  }
  adGenOtnOtuPmThres15MinAlms       OBJECT IDENTIFIER ::= { adGenOtn 12  }
  adGenOtnOtuPmThres24HrAlms        OBJECT IDENTIFIER ::= { adGenOtn 13  }
  adGenOtnOduPmThres15MinAlms       OBJECT IDENTIFIER ::= { adGenOtn 14  }
  adGenOtnOduPmThres24HrAlms        OBJECT IDENTIFIER ::= { adGenOtn 15  }

  adGenOtnOtuAlarms                OBJECT IDENTIFIER ::= { adGenOtnOtuAlms 0  }
  adGenOtnOduAlarms                OBJECT IDENTIFIER ::= { adGenOtnOduAlms 0  }
  adGenOtnOtuPmThres15MinAlarms    OBJECT IDENTIFIER ::= { adGenOtnOtuPmThres15MinAlms 0  }
  adGenOtnOtuPmThres24HrAlarms     OBJECT IDENTIFIER ::= { adGenOtnOtuPmThres24HrAlms 0  }
  adGenOtnOduPmThres15MinAlarms    OBJECT IDENTIFIER ::= { adGenOtnOduPmThres15MinAlms 0  }
  adGenOtnOduPmThres24HrAlarms     OBJECT IDENTIFIER ::= { adGenOtnOduPmThres24HrAlms 0  }


--==================================================================================================================
  AdGenOtnOduInterface ::= TEXTUAL-CONVENTION
      DISPLAY-HINT "1d 1d 1d 1d 1d 1d 1d 2d"
      STATUS       current
      DESCRIPTION "An octet string used to uniquely identify an ODU interface.  A value of zero indicates
                   that there isn't any encapsulation at that level.
                   The Octet string is defined as follows:
                   OCTET Position             Represented Num                   Range  Bandwidth
                   1                          Port Type                         0-1                 (0 = High Speed, 1 = Mid Speed)
                   2 (Most Significant Octet) Port Num                          1-n                 (n = num of ports on card)
                   3                          ODU4                              0-1    ~100  Gbps
                   4                          ODU3, ODU3e1, ODU3e2              0-2    ~40   Gbps
                   5                          ODU2, ODU2e, ODU2f, ODU1e, ODU1f  0-10   ~10   Gbps
                   6                          ODU1                              0-50   ~2.5  Gbps
                   7                          ODU0                              0-100  ~1.25 Gbps
                   8-9                        timeslot                          0-800  ~155  Mbps"
      SYNTAX       OCTET STRING (SIZE (9))


  OtnProtGrpInterface ::= TEXTUAL-CONVENTION
      DISPLAY-HINT "1d 1d 1d 1d 1d 1d 1d 1d 2d"
      STATUS       current
      DESCRIPTION "An octet string used to uniquely identify an interface for a protection group.  A value of zero indicates
                   that there isn't any encapsulation at that level.
                   The Octet string is defined as follows:
                   OCTET Position             Represented Num                   Range   Bandwidth
                   1 (Most Significant Octet) Slot Num                          1-m                (m = num of slots in shelf)
                   2                          Port Type                         0-1                (0 = High Speed, 1 = Mid Speed)
                   3                          Port Num                          1-n                (n = num of ports on card)
                   4                          ODU4                              0-1     ~100  Gbps
                   5                          ODU3, ODU3e1, ODU3e2              0-2     ~40   Gbps
                   6                          ODU2, ODU2e, ODU2f, ODU1e, ODU1f  0-10    ~10   Gbps
                   7                          ODU1                              0-50    ~2.5  Gbps
                   8                          ODU0                              0-100   ~1.25 Gbps
                   9-10                       timeslot                          0-800   ~155  Mbps"
      SYNTAX       OCTET STRING (SIZE (10))


   OtnPayloadTypes ::= TEXTUAL-CONVENTION
      STATUS      current
      DESCRIPTION "Possible payload types for muxponders."
      SYNTAX      INTEGER {
                           notApplicable(1),
                           otnPort(2),   -- OTN Port
                           odu4(3),      -- ~100Gbps
                           odu3(4),      -- ~40Gbps
                           odu3e1(5),    -- ~40Gbps
                           odu3e2(6),    -- ~40Gbps
                           odu2(7),      -- ~10Gbps
                           odu2e(8),     -- ~10Gbps
                           odu2f(9),     -- ~10Gbps
                           odu1e(10),    -- ~10Gbps
                           odu1f(11),    -- ~10Gbps
                           odu1(12),     -- ~2.5Gbps
                           odu0(13),     -- ~1.25Gbps
                           oduflex(14),  -- Variable between ~1.25Gbps and ~100Gbps
                           timeslot(15)  -- ~155Mbps
                          }

  -- /////////////////////////////////////////////////////////
  adGenOtnOtuProvTable OBJECT-TYPE
      SYNTAX  SEQUENCE OF AdGenOtnOtuProvEntry
      MAX-ACCESS  not-accessible
      STATUS  current
      DESCRIPTION
                 "OTU provisioning table."
      ::= { adGenOtnProv 1 }

  adGenOtnOtuProvEntry OBJECT-TYPE
      SYNTAX  AdGenOtnOtuProvEntry
      MAX-ACCESS  not-accessible
      STATUS  current
      DESCRIPTION
                 "Table Entry"
      INDEX   { ifIndex }
      ::= { adGenOtnOtuProvTable 1 }

  AdGenOtnOtuProvEntry ::=
      SEQUENCE {
                adGenOtnOtuLastError
                  DisplayString,
                adGenOtnOtuMode
                  INTEGER,
                adGenOtnOtuSupportedModes
                  BITS,
                adGenOtnOtuDegradeMonitor
                  INTEGER,
                adGenOtnOtuDegradeThres
                  INTEGER,
                adGenOtnOtuTraceTxSapi
                  DisplayString,
                adGenOtnOtuTraceTxDapi
                  DisplayString,
                adGenOtnOtuTraceTxOperatorSpec
                  DisplayString,
                adGenOtnOtuTraceRxSapi
                  DisplayString,
                adGenOtnOtuTraceRxDapi
                  DisplayString,
                adGenOtnOtuTraceRxOperatorSpec
                  DisplayString,
                adGenOtnOtuTraceExpectedSapi
                  DisplayString,
                adGenOtnOtuTraceExpectedDapi
                  DisplayString,
                adGenOtnOtuTraceAlarmControl
                  INTEGER,
                adGenOtnOtuTraceInsertAisEnable
                  TruthValue,
                adGenOtnOtuFecType
                  INTEGER,
                adGenOtnOtuSupportedFecType
                  BITS,
                adGenOtnOtuTraceAutoTxOperatorSpecEnable
                  TruthValue,
                adGenOtnOtuTraceTxOperatorSpecActual
                  DisplayString
               }

  adGenOtnOtuLastError    OBJECT-TYPE
      SYNTAX DisplayString
      MAX-ACCESS read-only
      STATUS current
      DESCRIPTION
              "This OID will return the error string for the last OTU provisioning error."
      ::= { adGenOtnOtuProvEntry 1 }

  adGenOtnOtuMode    OBJECT-TYPE
      SYNTAX INTEGER {
                      otu1(1),      -- ~2.5 Gbps
                      otu1e(2),     -- ~ 10 Gbps
                      otu1f(3),     -- ~ 10 Gbps
                      otu2(4),      -- ~ 10 Gbps
                      otu2e(5),     -- ~ 10 Gbps
                      otu2f(6),     -- ~ 10 Gbps
                      otu3(7),      -- ~ 40 Gbps
                      otu3e1(8),    -- ~ 40 Gbps
                      otu3e2(9),    -- ~ 40 Gbps
                      otu4(10),     -- ~100 Gbps
                      otu2gfpf(11), -- ~ 10 Gbps
                      otu2gfpfs(12) -- ~ 10 Gbps
                      }
      MAX-ACCESS read-write
      STATUS current
      DESCRIPTION
              "This OID will set the OTU to the specified mode."
      ::= { adGenOtnOtuProvEntry 2 }

  adGenOtnOtuSupportedModes    OBJECT-TYPE
      SYNTAX BITS {
                      otu1(0),      -- ~2.5 Gbps
                      otu1e(1),     -- ~ 10 Gbps
                      otu1f(2),     -- ~ 10 Gbps
                      otu2(3),      -- ~ 10 Gbps
                      otu2e(4),     -- ~ 10 Gbps
                      otu2f(5),     -- ~ 10 Gbps
                      otu3(6),      -- ~ 40 Gbps
                      otu3e1(7),    -- ~ 40 Gbps
                      otu3e2(8),    -- ~ 40 Gbps
                      otu4(9),      -- ~100 Gbps
                      otu2gfpf(10), -- ~ 10 Gbps
                      otu2gfpfs(11) -- ~ 10 Gbps
                      }
      MAX-ACCESS read-only
      STATUS current
      DESCRIPTION
              "This OID indicates the OTU modes that are supported for the indexed
              inteface.
              A value of 0 indicates the mode is not support.
              A value of 1 indicates the mode is support.
              The bit positions are:
               0 - OTU1
               1 - OTU1e
               2 - OTU2f
               3 - OTU2
               4 - OTU2e
               5 - OTU2f
               6 - OTU3
               7 - OTU3e1
               8 - OTU3e2
               9 - OTU4
              10 - OTU2gfpf
              11 - OTU2gfpfs"
      ::= { adGenOtnOtuProvEntry 3 }

  adGenOtnOtuDegradeMonitor    OBJECT-TYPE
      SYNTAX INTEGER (2..10)
      MAX-ACCESS read-write
      STATUS current
      DESCRIPTION
              "This OID indicates the OTU threshold value for the number of consecutive
              bad (1 second) intervals before raising the DEG-S alarm."
      ::= { adGenOtnOtuProvEntry 4 }

  adGenOtnOtuDegradeThres    OBJECT-TYPE
      SYNTAX INTEGER (1..100)
      MAX-ACCESS read-write
      STATUS current
      DESCRIPTION
              "This OID indicates the OTU threshold value for the percentage of errored blocks
              within a 1 second interval before raising the DEG-S alarm."
      ::= { adGenOtnOtuProvEntry 5 }

  adGenOtnOtuTraceTxSapi    OBJECT-TYPE
      SYNTAX DisplayString (SIZE (0..15))
      MAX-ACCESS read-write
      STATUS current
      DESCRIPTION
              "This OID will set the Trace Message Transmit SAPI(Source Access Point Identifier)
              field."
      ::= { adGenOtnOtuProvEntry 6 }

  adGenOtnOtuTraceTxDapi    OBJECT-TYPE
      SYNTAX DisplayString (SIZE (0..15))
      MAX-ACCESS read-write
      STATUS current
      DESCRIPTION
              "This OID will set the Trace Message Transmit DAPI(Destination Access Point Identifier)
              field."
      ::= { adGenOtnOtuProvEntry 7 }

  adGenOtnOtuTraceTxOperatorSpec    OBJECT-TYPE
      SYNTAX DisplayString (SIZE (0..32))
      MAX-ACCESS read-write
      STATUS current
      DESCRIPTION
              "This OID will set the user provisioned value of the Trace Message Transmit
              Operator Specific field.  When adGenOtnOtuTraceAutoTxOperatorSpecEnable is disabled,
              this string will be transmitted over the fiber."
      ::= { adGenOtnOtuProvEntry 8 }

  adGenOtnOtuTraceRxSapi    OBJECT-TYPE
      SYNTAX DisplayString (SIZE (0..15))
      MAX-ACCESS read-only
      STATUS current
      DESCRIPTION
              "This OID will return the Trace Message Receive SAPI(Source Access Point Identifier)
              field."
      ::= { adGenOtnOtuProvEntry 9 }

  adGenOtnOtuTraceRxDapi    OBJECT-TYPE
      SYNTAX DisplayString (SIZE (0..15))
      MAX-ACCESS read-only
      STATUS current
      DESCRIPTION
              "This OID will return the Trace Message Receive DAPI(Destination Access Point Identifier)
              field."
      ::= { adGenOtnOtuProvEntry 10 }

  adGenOtnOtuTraceRxOperatorSpec    OBJECT-TYPE
      SYNTAX DisplayString (SIZE (0..32))
      MAX-ACCESS read-only
      STATUS current
      DESCRIPTION
              "This OID will retrieve the Trace Message Receive Operator Specific field.
              If a '@' character is in the first byte, the management system should
              consider this field to have been Auto-Generated and therefore,
              can parse the information as defined in the description for
              adGenOtnOtuTraceAutoTxOperatorSpecEnable.  The parsed information
              can then be used for Network Topology Discovery and for display in a
              user friendly format."
      ::= { adGenOtnOtuProvEntry 11 }

  adGenOtnOtuTraceExpectedSapi    OBJECT-TYPE
      SYNTAX DisplayString (SIZE (0..15))
      MAX-ACCESS read-write
      STATUS current
      DESCRIPTION
              "This OID will set the Trace Message Expected SAPI(Source Access Point Identifier)
              field."
      ::= { adGenOtnOtuProvEntry 12 }

  adGenOtnOtuTraceExpectedDapi    OBJECT-TYPE
      SYNTAX DisplayString (SIZE (0..15))
      MAX-ACCESS read-write
      STATUS current
      DESCRIPTION
              "This OID will set the Trace Message Expected DAPI(Destination Access Point Identifier)
              field."
      ::= { adGenOtnOtuProvEntry 13 }

  adGenOtnOtuTraceAlarmControl    OBJECT-TYPE
      SYNTAX INTEGER {
                      disabled(1),  -- TIM alarm is disabled
                      sapiOnly(2),  -- Only a SAPI mismatch will cause a TIM alarm
                      dapiOnly(3),  -- Only a DAPI mismatch will cause a TIM alarm
                      either(4)     -- Either SAPI or DAPI mismatch will cause the TIM alarm
                      }
      MAX-ACCESS read-write
      STATUS current
      DESCRIPTION
              "This OID will control how the TIM(Trace Identifier Mismatch) alarm operates."
      ::= { adGenOtnOtuProvEntry 14 }

  adGenOtnOtuTraceInsertAisEnable    OBJECT-TYPE
      SYNTAX TruthValue
      MAX-ACCESS read-write
      STATUS current
      DESCRIPTION
              "This OID controls whether or not AIS is inserted downstream upon detection
              of the TIM."
      ::= { adGenOtnOtuProvEntry 15 }

  adGenOtnOtuFecType    OBJECT-TYPE
      SYNTAX INTEGER {
                      noFec(1),     -- No Forward Error Correction
                      gFec(2),      -- ITU-T G.709 Generic Forward Error Correction
                      eFec(3),      -- Enhanced Forward Error Correction
                      ufec(4)       -- Ultra-strong Forward Error Correction
                      }
      MAX-ACCESS read-write
      STATUS current
      DESCRIPTION
              "This OID controls the type Forward Error Correction to use for this OTU interface."
      ::= { adGenOtnOtuProvEntry 16 }

  adGenOtnOtuSupportedFecType    OBJECT-TYPE
      SYNTAX BITS {
                      noFec(0),     -- No Forward Error Correction
                      gFec(1),      -- ITU-T G.709 Generic Forward Error Correction
                      eFec(2),      -- Enhanced Forward Error Correction
                      ufec(3)       -- Ultra-strong Forward Error Correction
                      }
      MAX-ACCESS read-only
      STATUS current
      DESCRIPTION
              "This OID indicates the OTU FEC types that are supported for the indexed
              inteface.
              A value of 0 indicates the FEC type is not supported.
              A value of 1 indicates the FEC type is supported.
              The bit positions are:
               0 - no FEC
               1 - GFEC
               2 - EFEC
               3 - UFEC"
      ::= { adGenOtnOtuProvEntry 17 }

  adGenOtnOtuTraceAutoTxOperatorSpecEnable    OBJECT-TYPE
      SYNTAX TruthValue
      MAX-ACCESS read-write
      STATUS current
      DESCRIPTION
              "This OID controls whether or not the network element automatically generates
              the ASCII string for the Operator Specific Transmit Trace message.  The
              automatically generated string is used by the management system for network
              topology discovery.  Default value will be enable.
              The format for the automatically generated string is as follows:
              Byte(s)
              1       - '@'            -- This character is used to help determine if this is an
                                       -- auto-generated string.
              2-3     - '01'           -- Revision 01
              4-15    - '172028018100' -- Shelf IP Address 172.28.18.100
              16      - ' '            -- Space to help readability/parsing
              17-23   - '600010'       -- Local IF Index of the port
              24-32   - Null
              "
      ::= { adGenOtnOtuProvEntry 18 }

  adGenOtnOtuTraceTxOperatorSpecActual    OBJECT-TYPE
      SYNTAX DisplayString (SIZE (0..32))
      MAX-ACCESS read-only
      STATUS current
      DESCRIPTION
              "This OID will will return the ASCII string that is currently being
              transmitted over the fiber."
      ::= { adGenOtnOtuProvEntry 19 }


  -- /////////////////////////////////////////////////////////
  adGenOtnOduProvTable OBJECT-TYPE
      SYNTAX  SEQUENCE OF AdGenOtnOduProvEntry
      MAX-ACCESS  not-accessible
      STATUS  current
      DESCRIPTION
                 "OTN ODU Interface provisioning table.  In order
                 for this table to work as designed, the network
                 element would need to automatically create the
                 highest bandwidth ODU path when the OTU level is
                 created.  For example, if the OTN port is configured
                 for a OTU2 rate, then the corresponding ODU2 path
                 would automatically be created."
      ::= { adGenOtnProv 2 }

  adGenOtnOduProvEntry OBJECT-TYPE
      SYNTAX  AdGenOtnOduProvEntry
      MAX-ACCESS  not-accessible
      STATUS  current
      DESCRIPTION
                 "Table Entry"
      INDEX   { adGenSlotInfoIndex, adGenOtnOduIndex }
      ::= { adGenOtnOduProvTable 1 }

  AdGenOtnOduProvEntry ::=
      SEQUENCE {
                adGenOtnOduIndex
                  AdGenOtnOduInterface,
                adGenOtnOduLastError
                  DisplayString,
                adGenOtnOduAdminStatus
                  INTEGER,
                adGenOtnOduOperStatus
                  INTEGER,
                adGenOtnOduMode
                  INTEGER,
                adGenOtnOduSupportedModes
                  INTEGER,
                adGenOtnOduTimeslotBandwidth
                  INTEGER,
                adGenOtnOduRxPayloadLabel
                  INTEGER,
                adGenOtnOduTxPayloadLabel
                  INTEGER,
                adGenOtnOduProprietaryPayloadLabel
                  INTEGER,
                adGenOtnOduDegradeMonitor
                  INTEGER,
                adGenOtnOduDegradeThres
                  INTEGER,
                adGenOtnOduTraceTxSapi
                  DisplayString,
                adGenOtnOduTraceTxDapi
                  DisplayString,
                adGenOtnOduTraceTxOperatorSpec
                  DisplayString,
                adGenOtnOduTraceRxSapi
                  DisplayString,
                adGenOtnOduTraceRxDapi
                  DisplayString,
                adGenOtnOduTraceRxOperatorSpec
                  DisplayString,
                adGenOtnOduTraceExpectedSapi
                  DisplayString,
                adGenOtnOduTraceExpectedDapi
                  DisplayString,
                adGenOtnOduTraceAlarmControl
                  INTEGER,
                adGenOtnOduTraceInsertAisEnable
                  TruthValue,
                adGenOtnOduRowStatus
                  RowStatus,
                adGenOtnOdu2Odu3AutoPayloadType
                  INTEGER
               }

  adGenOtnOduIndex    OBJECT-TYPE
      SYNTAX AdGenOtnOduInterface
      MAX-ACCESS read-only
      STATUS current
      DESCRIPTION
              "This OID will return the ODU interface index."
      ::= { adGenOtnOduProvEntry 1 }

  adGenOtnOduLastError    OBJECT-TYPE
      SYNTAX DisplayString
      MAX-ACCESS read-only
      STATUS current
      DESCRIPTION
              "This OID will return the error string for the last ODU provisioning error
              for the specified ODU."
      ::= { adGenOtnOduProvEntry 2 }

  adGenOtnOduAdminStatus    OBJECT-TYPE
      SYNTAX INTEGER {
                      up(1),
                      down(2),
                      testing(3)
                     }
      MAX-ACCESS read-create
      STATUS current
      DESCRIPTION
              "The desired state of the ODU interface."
      ::= { adGenOtnOduProvEntry 3 }

  adGenOtnOduOperStatus    OBJECT-TYPE
      SYNTAX INTEGER {
                      up(1),
                      down(2),
                      testing(3)
                     }
      MAX-ACCESS read-only
      STATUS current
      DESCRIPTION
              "The current operational state of the ODU interface."
      ::= { adGenOtnOduProvEntry 4 }

  adGenOtnOduMode    OBJECT-TYPE
      SYNTAX INTEGER {
                      timeslot(1),  -- ~ 155 Mbps to 2.5 Gbps
                      oduFlex(2),   -- ~1.25 Gbps to 100 Gbps
                      odu0(3),      -- ~1.25 Gbps
                      odu1(4),      -- ~ 2.5 Gbps
                      odu1e(5),     -- ~  10 Gbps
                      odu1f(6),     -- ~  10 Gbps
                      odu2(7),      -- ~  10 Gbps
                      odu2e(8),     -- ~  10 Gbps
                      odu2f(9),     -- ~  10 Gbps
                      odu3(10),     -- ~  40 Gbps
                      odu3e1(11),   -- ~  40 Gbps
                      odu3e2(12),   -- ~  40 Gbps
                      odu4(13),     -- ~ 100 Gbps
                      odu2gfpf(14), -- ~  10 Gbps
                      odu2gfpfs(15) -- ~  10 Gbps
                     }
      MAX-ACCESS read-create
      STATUS current
      DESCRIPTION
              "This OID specifies the ODU mode."
      ::= { adGenOtnOduProvEntry 5 }

  adGenOtnOduSupportedModes    OBJECT-TYPE
      SYNTAX INTEGER {
                      timeslot(1),  -- ~ 155 Mbps to 2.5 Gbps
                      oduFlex(2),   -- ~1.25 Gbps to 100 Gbps
                      odu0(3),      -- ~1.25 Gbps
                      odu1(4),      -- ~ 2.5 Gbps
                      odu1e(5),     -- ~  10 Gbps
                      odu1f(6),     -- ~  10 Gbps
                      odu2(7),      -- ~  10 Gbps
                      odu2e(8),     -- ~  10 Gbps
                      odu2f(9),     -- ~  10 Gbps
                      odu3(10),     -- ~  40 Gbps
                      odu3e1(11),   -- ~  40 Gbps
                      odu3e2(12),   -- ~  40 Gbps
                      odu4(13),     -- ~ 100 Gbps
                      odu2gfpf(14), -- ~  10 Gbps
                      odu2gfpfs(15) -- ~  10 Gbps
                     }
      MAX-ACCESS read-only
      STATUS current
      DESCRIPTION
              "This OID specifies the ODU mode.
              A value of 0 indicates the mode is not support.
              A value of 1 indicates the mode is support.
              The bit positions are:
               0  - timeslots
               1  - ODUFlex
               2  - ODU0
               3  - ODU1
               4  - ODU1e
               5  - ODU2f
               6  - ODU2
               7  - ODU2e
               8  - ODU2f
               9  - ODU3
               10 - ODU3e1
               11 - ODU3e2
               12 - ODU4
               13 - ODU2gfpf
               14 - ODU2gfpfs"
      ::= { adGenOtnOduProvEntry 6 }

  adGenOtnOduTimeslotBandwidth    OBJECT-TYPE
      SYNTAX INTEGER (1..16)
      MAX-ACCESS read-create
      STATUS current
      DESCRIPTION
              "This OID will change the bandwidth of the indexed timeslot.  Measured
              in increments of 155Mbps."
      ::= { adGenOtnOduProvEntry 7 }

  adGenOtnOduRxPayloadLabel    OBJECT-TYPE
      SYNTAX INTEGER (0..255)
      MAX-ACCESS read-only
      STATUS current
      DESCRIPTION
              "This OID will return the Receive ODU Payload Label overhead byte.
              Byte defintions as defined in G.709 Table 15-8 are as follows:
              Hex Value       Definition
              00              Unassigned
              01              Experimental mapping
              02              Asynchronous CBR mapping
              03              Bit synchronous CBR mapping
              04              ATM mapping
              05              GFP mapping
              06              Virtual Concatenated signal
              07              1000BASE-X into OPU0 mapping
              08              FC-1200 into OPU2e mapping
              09              GFP mapping into Extended OPU2 payload
              0A              STM-1 mapping into ODU0
              0B              STM-4 mapping into ODU0
              0C              FC-100 mapping into ODU0
              0D              FC-200 mapping into ODU1
              0E              FC-400 mapping into ODUflex
              0F              FC-800 mapping into ODUflex
              10              Bit stream with octet timing mapping
              11              Bit stream without octet timing mapping
              20              ODU multiplex structure supporting ODTUjk
              21              ODU multiplex structure supporting ODTUk.ts
              55              Not available
              66              Not available
              80-8F           Reserved codes for proprietary
              FD              NULL test signal mapping
              FE              PRBS test signal mapping
              FF              Not available"
      ::= { adGenOtnOduProvEntry 8 }

  adGenOtnOduTxPayloadLabel    OBJECT-TYPE
      SYNTAX INTEGER (0..255)
      MAX-ACCESS read-only
      STATUS current
      DESCRIPTION
              "This OID will return the Transmit ODU Payload Label overhead byte.
              Byte defintions as defined in G.709 Table 15-8 are as follows:
              Hex Value       Definition
              00              Unassigned
              01              Experimental mapping
              02              Asynchronous CBR mapping
              03              Bit synchronous CBR mapping
              04              ATM mapping
              05              GFP mapping
              06              Virtual Concatenated signal
              07              1000BASE-X into OPU0 mapping
              08              FC-1200 into OPU2e mapping
              09              GFP mapping into Extended OPU2 payload
              0A              STM-1 mapping into ODU0
              0B              STM-4 mapping into ODU0
              0C              FC-100 mapping into ODU0
              0D              FC-200 mapping into ODU1
              0E              FC-400 mapping into ODUflex
              0F              FC-800 mapping into ODUflex
              10              Bit stream with octet timing mapping
              11              Bit stream without octet timing mapping
              20              ODU multiplex structure supporting ODTUjk
              21              ODU multiplex structure supporting ODTUk.ts
              55              Not available
              66              Not available
              80-8F           Reserved codes for proprietary
              FD              NULL test signal mapping
              FE              PRBS test signal mapping
              FF              Not available"
      ::= { adGenOtnOduProvEntry 9 }

  adGenOtnOduProprietaryPayloadLabel    OBJECT-TYPE
      SYNTAX INTEGER (128..143)    -- 0x80..0x8F
      MAX-ACCESS read-create
      STATUS current
      DESCRIPTION
              "This OID will set the proprietary payload label.  This payload label
              value will be used the for TX and expected payload label when carrying
              proprietary payload such as Timeslots.  This value must fall within the range
              of proprietarty payload label values as defined below (0x80-0x8F).
              Payload Label byte defintions as defined in G.709 Table 15-8 are as follows:
              Hex Value       Definition
              00              Unassigned
              01              Experimental mapping
              02              Asynchronous CBR mapping
              03              Bit synchronous CBR mapping
              04              ATM mapping
              05              GFP mapping
              06              Virtual Concatenated signal
              07              1000BASE-X into OPU0 mapping
              08              FC-1200 into OPU2e mapping
              09              GFP mapping into Extended OPU2 payload
              0A              STM-1 mapping into ODU0
              0B              STM-4 mapping into ODU0
              0C              FC-100 mapping into ODU0
              0D              FC-200 mapping into ODU1
              0E              FC-400 mapping into ODUflex
              0F              FC-800 mapping into ODUflex
              10              Bit stream with octet timing mapping
              11              Bit stream without octet timing mapping
              20              ODU multiplex structure supporting ODTUjk
              21              ODU multiplex structure supporting ODTUk.ts
              55              Not available
              66              Not available
              80-8F           Reserved codes for proprietary
              FD              NULL test signal mapping
              FE              PRBS test signal mapping
              FF              Not available"
      ::= { adGenOtnOduProvEntry 10 }

  adGenOtnOduDegradeMonitor    OBJECT-TYPE
      SYNTAX INTEGER (2..10)
      MAX-ACCESS read-create
      STATUS current
      DESCRIPTION
              "This OID indicates the ODU threshold value for the number of consecutive
              bad (1 second) intervals before declaring the interval bad."
      ::= { adGenOtnOduProvEntry 11 }

  adGenOtnOduDegradeThres    OBJECT-TYPE
      SYNTAX INTEGER (1..100)
      MAX-ACCESS read-create
      STATUS current
      DESCRIPTION
              "This OID indicates the ODU threshold value for the percentage of errored blocks
              within a 1 second interval before declaring the interval bad."
      ::= { adGenOtnOduProvEntry 12 }

  adGenOtnOduTraceTxSapi    OBJECT-TYPE
      SYNTAX DisplayString (SIZE (0..15))
      MAX-ACCESS read-create
      STATUS current
      DESCRIPTION
              "This OID will set the ODU Trace Message Transmit SAPI(Source Access Point Identifier)
              field."
      ::= { adGenOtnOduProvEntry 13 }

  adGenOtnOduTraceTxDapi    OBJECT-TYPE
      SYNTAX DisplayString (SIZE (0..15))
      MAX-ACCESS read-create
      STATUS current
      DESCRIPTION
              "This OID will set the ODU Trace Message Transmit DAPI(Destination Access Point Identifier)
              field."
      ::= { adGenOtnOduProvEntry 14 }

  adGenOtnOduTraceTxOperatorSpec    OBJECT-TYPE
      SYNTAX DisplayString (SIZE (0..32))
      MAX-ACCESS read-create
      STATUS current
      DESCRIPTION
              "This OID will set the ODU Trace Message Transmit Operator Specific field."
      ::= { adGenOtnOduProvEntry 15 }

  adGenOtnOduTraceRxSapi    OBJECT-TYPE
      SYNTAX DisplayString (SIZE (0..15))
      MAX-ACCESS read-only
      STATUS current
      DESCRIPTION
              "This OID will return the ODU Trace Message Receive SAPI(Source Access Point Identifier)
              field."
      ::= { adGenOtnOduProvEntry 16 }

  adGenOtnOduTraceRxDapi    OBJECT-TYPE
      SYNTAX DisplayString (SIZE (0..15))
      MAX-ACCESS read-only
      STATUS current
      DESCRIPTION
              "This OID will return the ODU Trace Message Receive DAPI(Destination Access Point Identifier)
              field."
      ::= { adGenOtnOduProvEntry 17 }

  adGenOtnOduTraceRxOperatorSpec    OBJECT-TYPE
      SYNTAX DisplayString (SIZE (0..32))
      MAX-ACCESS read-only
      STATUS current
      DESCRIPTION
              "This OID will set the ODU Trace Message Receive Operator Specific field."
      ::= { adGenOtnOduProvEntry 18 }

  adGenOtnOduTraceExpectedSapi    OBJECT-TYPE
      SYNTAX DisplayString (SIZE (0..15))
      MAX-ACCESS read-create
      STATUS current
      DESCRIPTION
              "This OID will set the ODU Trace Message Expected SAPI(Source Access Point Identifier)
              field."
      ::= { adGenOtnOduProvEntry 19 }

  adGenOtnOduTraceExpectedDapi    OBJECT-TYPE
      SYNTAX DisplayString (SIZE (0..15))
      MAX-ACCESS read-create
      STATUS current
      DESCRIPTION
              "This OID will set the ODU Trace Message Expected DAPI(Destination Access Point Identifier)
              field."
      ::= { adGenOtnOduProvEntry 20 }

  adGenOtnOduTraceAlarmControl    OBJECT-TYPE
      SYNTAX INTEGER {
                      disabled(1),  -- TIM alarm is disabled
                      sapiOnly(2),  -- Only a SAPI mismatch will cause a TIM alarm
                      dapiOnly(3),  -- Only a DAPI mismatch will cause a TIM alarm
                      either(4)     -- Either SAPI or DAPI mismatch will cause the TIM alarm
                      }
      MAX-ACCESS read-create
      STATUS current
      DESCRIPTION
              "This OID will control how the ODU TIM alarm operates."
      ::= { adGenOtnOduProvEntry 21 }

  adGenOtnOduTraceInsertAisEnable    OBJECT-TYPE
      SYNTAX TruthValue
      MAX-ACCESS read-create
      STATUS current
      DESCRIPTION
              "This OID controls whether or not AIS is inserted downstream upon detection
              of the ODU TIM."
      ::= { adGenOtnOduProvEntry 22 }

  adGenOtnOduRowStatus    OBJECT-TYPE
      SYNTAX RowStatus
      MAX-ACCESS read-create
      STATUS current
      DESCRIPTION
              "Used for creating/deleting ODUs."
      ::= { adGenOtnOduProvEntry 23 }

  adGenOtnOdu2Odu3AutoPayloadType    OBJECT-TYPE
      SYNTAX INTEGER {
                      unsupported(1),  -- Interface does not support this feature
                      enable(2),       -- Enable auto payload type
                      disable(3)       -- Disable auto payload type
                      }
      MAX-ACCESS read-create
      STATUS current
      DESCRIPTION
              "Enable/Disable auto payload type generation for ODU2 and
              ODU3 interfaces(All other ODU interfaces will return 'unsupported').
              When enabled, the network element will automatically chose between
              generating payload type 0x20 and 0x21 depending on whether it is receiving
              a payload type of 0x20 or 0x21.  This feature is used when the far end
              equipment only supports payload type 0x20 which indicates that it doesn't
              support ODU0s.  Default value will be enable."
      ::= { adGenOtnOduProvEntry 24 }

  -- /////////////////////////////////////////////////////////
  adGenOtnSlotProvTable OBJECT-TYPE
      SYNTAX  SEQUENCE OF AdGenOtnSlotProvEntry
      MAX-ACCESS  not-accessible
      STATUS  current
      DESCRIPTION
                 "OTN Slot table.  This table is used to handle any
                 provisioning at the slot level."
      ::= { adGenOtnProv 3 }

  adGenOtnSlotProvEntry OBJECT-TYPE
      SYNTAX  AdGenOtnSlotProvEntry
      MAX-ACCESS  not-accessible
      STATUS  current
      DESCRIPTION
                 "Table Entry"
      INDEX   { adGenSlotInfoIndex }
      ::= { adGenOtnSlotProvTable 1 }

  AdGenOtnSlotProvEntry ::=
      SEQUENCE {
                adGenOtnSlotOtuAlarmEnable
                  BITS,
                adGenOtnSlotOduAlarmEnable
                  BITS
               }

  adGenOtnSlotOtuAlarmEnable    OBJECT-TYPE
      SYNTAX BITS {
                   lossOfSignal(0),
                   lossOfFrame(1),
                   lossOfMultiFrame(2),
                   alarmIndicationSignal(3),
                   backwardDefectIndication(4),
                   traceIdentifierMismatch(5),
                   degradedSignal(6)
                  }
      MAX-ACCESS read-write
      STATUS current
      DESCRIPTION
              "This OID controls whether or not an OTU alarm is disabled.
              A value of 0 indicates the alarm is disabled.
              A value of 1 indicates the alarm is enabled.
              The bit positions are:
               0 - LOS
               1 - LOF-S
               2 - LOM-S
               3 - AIS-S
               4 - BDI-S
               5 - TIM-S
               6 - DEG-S"
      ::= { adGenOtnSlotProvEntry 1 }

  adGenOtnSlotOduAlarmEnable    OBJECT-TYPE
      SYNTAX BITS {
                   lossOfFrameAndMultiFrame(0),
                   backwardDefectIndication(1),
                   openConnectionIndication(2),
                   traceIdentifierMismatch(3),
                   degradedSignal(4),
                   payloadLabelMismatch(5),
                   lock(6),
                   alarmIndicationSignal(7),
                   multiplexStructureIdentifierMismatch(8),
                   clientSignalFail(9),
                   lossOfOpuMultiFrameIdentifier(10)
                  }
      MAX-ACCESS read-write
      STATUS current
      DESCRIPTION
              "This OID controls whether or not an ODU alarm is disabled.
              A value of 0 indicates the alarm is disabled.
              A value of 1 indicates the alarm is enabled.
              The bit positions are:
               0 - LOFLOM-P
               1 - BDI-P
               2 - OCI-P
               3 - TIM-P
               4 - DEG-P
               5 - PLM-P
               6 - LCK-P
               7 - AIS-P
               8 - MSIM-P
               9 - CSF-P
              10 - LOOMFI-P"
      ::= { adGenOtnSlotProvEntry 2 }


  -- /////////////////////////////////////////////////////////
  adGenOtnProtGroupTable OBJECT-TYPE
     SYNTAX  SEQUENCE OF AdGenOtnProtGroupEntry
     MAX-ACCESS  not-accessible
     STATUS  current
     DESCRIPTION
        "The OTN Protection Group table.  This table is used
        to create protection groups out of two OTN interfaces."
     ::= { adGenOtnProv 4 }

  adGenOtnProtGroupEntry OBJECT-TYPE
     SYNTAX  AdGenOtnProtGroupEntry
     MAX-ACCESS  not-accessible
     STATUS  current
     DESCRIPTION
        "An entry in the OTN Protection Group table."
     INDEX  { adGenSlotInfoIndex, IMPLIED adGenOtnProtGroupName }
     ::= { adGenOtnProtGroupTable 1 }

  AdGenOtnProtGroupEntry ::=
     SEQUENCE {
        adGenOtnProtGroupName
           DisplayString,
        adGenOtnProtGroupType
           INTEGER,
        adGenOtnProtGroupWorkingType
           OtnPayloadTypes,
        adGenOtnProtGroupWorkingInterface
           OtnProtGrpInterface,
        adGenOtnProtGroupProtectingType
           OtnPayloadTypes,
        adGenOtnProtGroupProtectingInterface
           OtnProtGrpInterface,
        adGenOtnProtGroupRowStatus
           RowStatus,
        adGenOtnProtGroupLastProvError
           DisplayString,
        adGenOtnProtGroupWorkIsOnline
           TruthValue,
        adGenOtnProtGroupSwitchCommands
           INTEGER,
        adGenOtnProtGroupWorkEntityStatus
           INTEGER,
        adGenOtnProtGroupProtectEntityStatus
           INTEGER,
        adGenOtnProtGroupRevertiveEnable
           TruthValue,
        adGenOtnProtGroupWaitToRestoreTime
           INTEGER,
        adGenOtnProtGroupOperStatus
           INTEGER,
        adGenOtnProtGroupStatusString
           DisplayString,
        adGenOtnProtGroupWaitToRestoreRemainingTime
           Unsigned32
     }

  adGenOtnProtGroupName OBJECT-TYPE
     SYNTAX DisplayString (SIZE (1..50))
     MAX-ACCESS not-accessible
     STATUS current
     DESCRIPTION
        "Protection Group name."
     ::= { adGenOtnProtGroupEntry 1 }

  adGenOtnProtGroupType OBJECT-TYPE
     SYNTAX INTEGER {
                      snci(1),  -- Subnetwork Connect protection with inherent monitoring (1+1 Line - unidirectional)
                      sncn(2),  -- Subnetwork Connect protection with non-intrusive monitoring (1+1 path switching)
                      yCable(3) -- The transmitter of the working and protect interfaces are connected via Y-Cable
                    }
     MAX-ACCESS read-create
     STATUS current
     DESCRIPTION
        "Protection Group type."
     ::= { adGenOtnProtGroupEntry 2 }

  adGenOtnProtGroupWorkingType OBJECT-TYPE
     SYNTAX OtnPayloadTypes
     MAX-ACCESS read-only
     STATUS current
     DESCRIPTION
        "This is used to indicate the payload type of the working
        entity."
     ::= { adGenOtnProtGroupEntry 3 }

  adGenOtnProtGroupWorkingInterface OBJECT-TYPE
     SYNTAX OtnProtGrpInterface
     MAX-ACCESS read-create
     STATUS current
     DESCRIPTION
        "The interface of the working entity."
     ::= { adGenOtnProtGroupEntry 4 }

  adGenOtnProtGroupProtectingType OBJECT-TYPE
     SYNTAX OtnPayloadTypes
     MAX-ACCESS read-create
     STATUS current
     DESCRIPTION
        "This is used to indicate the payload type of the protecting
        entity."
     ::= { adGenOtnProtGroupEntry 5 }

  adGenOtnProtGroupProtectingInterface OBJECT-TYPE
     SYNTAX OtnProtGrpInterface
     MAX-ACCESS read-create
     STATUS current
     DESCRIPTION
        "The interface of the protecting entity."
     ::= { adGenOtnProtGroupEntry 6 }

  adGenOtnProtGroupRowStatus OBJECT-TYPE
     SYNTAX RowStatus
     MAX-ACCESS read-create
     STATUS current
     DESCRIPTION
        "Protection Group Row Status."
     ::= { adGenOtnProtGroupEntry 7 }

  adGenOtnProtGroupLastProvError OBJECT-TYPE
      SYNTAX         DisplayString
      MAX-ACCESS     read-only
      STATUS         current
      DESCRIPTION
         "This string describes the last error experienced
          for this particular entry in the table."
     ::= { adGenOtnProtGroupEntry 8 }

  adGenOtnProtGroupWorkIsOnline OBJECT-TYPE
      SYNTAX         TruthValue
      MAX-ACCESS     read-only
      STATUS         current
      DESCRIPTION
         "Indicates whether or not the working-entity is online.  If not,
         the protect-entity is online."
     ::= { adGenOtnProtGroupEntry 9 }

  adGenOtnProtGroupSwitchCommands OBJECT-TYPE
      SYNTAX         INTEGER {
                              clear(1),                 -- Clear/Idle
                              manualSwitchToWork(2),    -- Manual Switch to Working-Entity
                              manualSwitchToProt(3),    -- Manual Switch to Protect-Entity
                              forceSwitchToWork(4),     -- Force Switch to Working-Entity
                              forceSwitchToProt(5),     -- Force Switch to Protect-Entity
                              lockout(6)                -- Lockout of Protection
                             }
      MAX-ACCESS     read-create
      STATUS         current
      DESCRIPTION
         "Protection Group Switch Commands."
     ::= { adGenOtnProtGroupEntry 10 }

  adGenOtnProtGroupWorkEntityStatus OBJECT-TYPE
      SYNTAX         INTEGER {
                              clear(1),           -- Signal is clear.  No faults.
                              signalFaulty(2),    -- Signal is faulty
                              signalDegraded(3),  -- Signal is degraded
                              down(4)             -- Administratively down
                             }
      MAX-ACCESS     read-only
      STATUS         current
      DESCRIPTION
         "Working Entity Signal Status."
     ::= { adGenOtnProtGroupEntry 11 }

  adGenOtnProtGroupProtectEntityStatus OBJECT-TYPE
      SYNTAX         INTEGER {
                              clear(1),           -- Signal is clear.  No faults.
                              signalFaulty(2),    -- Signal is faulty
                              signalDegraded(3),  -- Signal is degraded
                              down(4)             -- Administratively down
                             }
      MAX-ACCESS     read-only
      STATUS         current
      DESCRIPTION
         "Protect Entity Signal Status."
     ::= { adGenOtnProtGroupEntry 12 }

  adGenOtnProtGroupRevertiveEnable OBJECT-TYPE
     SYNTAX         TruthValue
     MAX-ACCESS     read-create
     STATUS         current
     DESCRIPTION
        "Enables/disables revertive switching for this protection group."
    ::= { adGenOtnProtGroupEntry 13 }

  adGenOtnProtGroupWaitToRestoreTime OBJECT-TYPE
     SYNTAX         INTEGER (1..20)
     MAX-ACCESS     read-create
     STATUS         current
     DESCRIPTION
        "Wait to restore time(in minutes)."
    ::= { adGenOtnProtGroupEntry 14 }

   adGenOtnProtGroupOperStatus OBJECT-TYPE
       SYNTAX      INTEGER {
                             up(1),
                             down(2)
                           }
       MAX-ACCESS  read-only
       STATUS      current
       DESCRIPTION
          "Operation Status of the Protection Group.  This operational status
          indicates whether or not the provisioning necessary for protection switching
          to function properly has been adequately provisioned.  It is not affected by
          by faults/degrades on the working or protecting interfaces.
          adGenOtnProtGroupStatusString is used to indicate why the operational status
          is 'down'."
      ::= { adGenOtnProtGroupEntry 15 }

   adGenOtnProtGroupStatusString OBJECT-TYPE
       SYNTAX         DisplayString
       MAX-ACCESS     read-only
       STATUS         current
       DESCRIPTION
          "The status string for the protection group.  Indicates
          why the protection group is down.  If protection group is up,
          then a blank string will be returned."
      ::= { adGenOtnProtGroupEntry 16 }

   adGenOtnProtGroupWaitToRestoreRemainingTime OBJECT-TYPE
       SYNTAX         Unsigned32(0..1200)
       UNITS          "seconds"
       MAX-ACCESS     read-only
       STATUS         current
       DESCRIPTION
          "The remaining time(in seconds) to restore the entity when wait to restore is enabled."
      ::= { adGenOtnProtGroupEntry 17 }

  -- /////////////////////////////////////////////////////////
  adGenOtnProtGroupLastCreateErrorTable OBJECT-TYPE
     SYNTAX  SEQUENCE OF AdGenOtnProtGroupLastCreateErrorEntry
     MAX-ACCESS  not-accessible
     STATUS  current
     DESCRIPTION
        "The OTN Protection Group Last Create Error table.
        This table is used to indicate the last error that occurred
        during creation of a protection group."
     ::= { adGenOtnProv 5 }

  adGenOtnProtGroupLastCreateErrorEntry OBJECT-TYPE
     SYNTAX  AdGenOtnProtGroupLastCreateErrorEntry
     MAX-ACCESS  not-accessible
     STATUS  current
     DESCRIPTION
        "An entry in the OTN Protection Group Last Create Error table."
     INDEX  { adGenSlotInfoIndex }
     ::= { adGenOtnProtGroupLastCreateErrorTable 1 }

  AdGenOtnProtGroupLastCreateErrorEntry ::=
     SEQUENCE {
        adGenOtnProtGroupLastCreateError
           DisplayString
     }

  adGenOtnProtGroupLastCreateError OBJECT-TYPE
     SYNTAX DisplayString
     MAX-ACCESS read-only
     STATUS current
     DESCRIPTION
        "The last error that occurred during the creation of a
        protection group."
     ::= { adGenOtnProtGroupLastCreateErrorEntry 1 }


  -- /////////////////////////////////////////////////////////
  adGenOtnOtuStatusTable OBJECT-TYPE
      SYNTAX  SEQUENCE OF AdGenOtnOtuStatusEntry
      MAX-ACCESS  not-accessible
      STATUS  current
      DESCRIPTION
                 "OTN OTU Interface status table."
      ::= { adGenOtnStatus 1 }

  adGenOtnOtuStatusEntry OBJECT-TYPE
      SYNTAX  AdGenOtnOtuStatusEntry
      MAX-ACCESS  not-accessible
      STATUS  current
      DESCRIPTION
                 "Table Entry"
      INDEX   { ifIndex }
      ::= { adGenOtnOtuStatusTable 1 }

  AdGenOtnOtuStatusEntry ::=
      SEQUENCE {
                adGenOtnOtuAlarmStatus
                  BITS
               }

  adGenOtnOtuAlarmStatus    OBJECT-TYPE
      SYNTAX BITS {
                   lossOfSignal(0),
                   lossOfFrame(1),
                   lossOfMultiFrame(2),
                   alarmIndicationSignal(3),
                   backwardDefectIndication(4),
                   traceIdentifierMismatch(5),
                   degradedSignal(6),
                   traceIdentifierMismatchWithConsequence(7)
                  }
      MAX-ACCESS read-only
      STATUS current
      DESCRIPTION
              "A bit-map representing the current alarm status of the specified
              OTU port.
              The bit positions are:
               0 - LOS
               1 - LOF-S
               2 - LOM-S
               3 - AIS-S
               4 - BDI-S
               5 - TIM-S
               6 - DEG-S
               7 - TIM-S with Consequence(AIS Insertion)"
      ::= { adGenOtnOtuStatusEntry 1 }


  -- /////////////////////////////////////////////////////////
  adGenOtnOduStatusTable OBJECT-TYPE
      SYNTAX  SEQUENCE OF AdGenOtnOduStatusEntry
      MAX-ACCESS  not-accessible
      STATUS  current
      DESCRIPTION
                 "OTN ODU Interface status table."
      ::= { adGenOtnStatus 2 }

  adGenOtnOduStatusEntry OBJECT-TYPE
      SYNTAX  AdGenOtnOduStatusEntry
      MAX-ACCESS  not-accessible
      STATUS  current
      DESCRIPTION
                 "Table Entry"
      INDEX   { adGenSlotInfoIndex, adGenOtnOduIndex }
      ::= { adGenOtnOduStatusTable 1 }

  AdGenOtnOduStatusEntry ::=
      SEQUENCE {
                adGenOtnOduAlarmStatus
                  BITS,
                adGenOtnOduStatus
                  BITS,
                adGenOtnOduProtGrpName
                  DisplayString
               }

  adGenOtnOduAlarmStatus    OBJECT-TYPE
      SYNTAX BITS {
                   lossOfFrameAndMultiFrame(0),
                   backwardDefectIndication(1),
                   openConnectionIndication(2),
                   traceIdentifierMismatch(3),
                   degradedSignal(4),
                   payloadLabelMismatch(5),
                   lock(6),
                   alarmIndicationSignal(7),
                   multiplexStructureIdentifierMismatch(8),
                   traceIdentifierMismatchWithConsequence(9),
                   clientSignalFail(10),
                   lossOfOpuMultiFrameIdentifier(11)
                  }
      MAX-ACCESS read-only
      STATUS current
      DESCRIPTION
              "A bit-map representing the current alarm status of the specified
              ODU path.
              The bit positions are:
               0  - LOFLOM-P
               1  - BDI-P
               2  - OCI-P
               3  - TIM-P
               4  - DEG-P
               5  - PLM-P
               6  - LCK-P
               7  - AIS-P
               8  - MSIM-P
               9  - TIM-P with Consequence(AIS Insertion)
               10 - CSF-P,
               11 - LOOMFI-P"
      ::= { adGenOtnOduStatusEntry 1 }

  adGenOtnOduStatus    OBJECT-TYPE
      SYNTAX BITS {
                   fault(0),
                   superordinateFault(1),
                   subordinateFault(2),
                   superordinateUnassigned(3),
                   subordinateInserviceOrMaintenance(4),
                   protected(5),
                   superordinateProtected(6),
                   subordinateProtected(7),
                   mapped(8),
                   superordinateMapped(9),
                   subordinateMapped(10),
                   crossconnected(11),
                   superordinateCrossConnected(12),
                   subordinateCrossConnected(13)
                  }
      MAX-ACCESS read-only
      STATUS current
      DESCRIPTION
              "ODU status.
              The bit positions are:
               0 - this interface is in fault
               1 - at least one superordinate interface or equipment is in fault
               2 - at least one subordinate interface is in fault
               3 - superordinate interface or equipment is unassigned
               4 - at least one subordinate interface is Inservice or Maintenance
               5 - protected - This interface is part of a protection group
               6 - at least one superordinate interface is part of a protection group
               7 - at least one subordinate interface is part of a protection group
               8 - mapped - This interface is part of at least one mapping
               9 - at least one superordinate interface is mapped
              10 - at least one subordinate interface is mapped
              11 - cross-connected - This interface is part of at least one cross-connect
              12 - at least one superordinate interface is cross-connected
              13 - at least one subordinate interface is cross-connected"
      ::= { adGenOtnOduStatusEntry 2 }

    adGenOtnOduProtGrpName OBJECT-TYPE
       SYNTAX DisplayString (SIZE (1..50))
       MAX-ACCESS read-only
       STATUS current
       DESCRIPTION
          "The name of the protection group for this ODU.  If this ODU is not part of a
          protection group, this field will be blank."
       ::= { adGenOtnOduStatusEntry 3 }

   -- /////////////////////////////////////////////////////////
   adGenOtnOduCrossConnectStatusTable OBJECT-TYPE
      SYNTAX  SEQUENCE OF AdGenOtnOduCrossConnectStatusEntry
      MAX-ACCESS  not-accessible
      STATUS  current
      DESCRIPTION
         "The OTN ODU Cross-Connect Status table."
      ::= { adGenOtnStatus 3 }

   adGenOtnOduCrossConnectStatusEntry OBJECT-TYPE
      SYNTAX  AdGenOtnOduCrossConnectStatusEntry
      MAX-ACCESS  not-accessible
      STATUS  current
      DESCRIPTION
         "An entry in the OTN ODU Cross-Connect Status table."
      INDEX  { adGenSlotInfoIndex, adGenOtnOduIndex, adGenOtnOduCrossConnectName }
      ::= { adGenOtnOduCrossConnectStatusTable 1 }

   AdGenOtnOduCrossConnectStatusEntry ::=
      SEQUENCE {
         adGenOtnOduCrossConnectName
            DisplayString,
         adGenOtnOduCrossConnectStatus
            INTEGER
      }

   adGenOtnOduCrossConnectName OBJECT-TYPE
      SYNTAX DisplayString (SIZE (1..50))
      MAX-ACCESS read-only
      STATUS current
      DESCRIPTION
         "Name of Cross-Connect."
      ::= { adGenOtnOduCrossConnectStatusEntry 1 }

   adGenOtnOduCrossConnectStatus OBJECT-TYPE
      SYNTAX INTEGER {
                      source(1),
                      destination(2),
                      sourceAndDestination(3)
                     }
      MAX-ACCESS read-only
      STATUS current
      DESCRIPTION
         "This OID indicates whether this ODU is defined as a source, destination or both for
         this cross-connect."
      ::= { adGenOtnOduCrossConnectStatusEntry 2 }


   -- /////////////////////////////////////////////////////////
   adGenOtnOduMappingStatusTable OBJECT-TYPE
      SYNTAX  SEQUENCE OF AdGenOtnOduMappingStatusEntry
      MAX-ACCESS  not-accessible
      STATUS  current
      DESCRIPTION
         "The OTN ODU Mapping Status table."
      ::= { adGenOtnStatus 4 }

   adGenOtnOduMappingStatusEntry OBJECT-TYPE
      SYNTAX  AdGenOtnOduMappingStatusEntry
      MAX-ACCESS  not-accessible
      STATUS  current
      DESCRIPTION
         "An entry in the OTN ODU Mapping Status table."
      INDEX  { adGenSlotInfoIndex, adGenOtnOduIndex, adGenOtnOduMappingName }
      ::= { adGenOtnOduMappingStatusTable 1 }

   AdGenOtnOduMappingStatusEntry ::=
      SEQUENCE {
         adGenOtnOduMappingName
            DisplayString,
         adGenOtnOduMappingStatus
            INTEGER
      }

   adGenOtnOduMappingName OBJECT-TYPE
      SYNTAX DisplayString (SIZE (1..50))
      MAX-ACCESS read-only
      STATUS current
      DESCRIPTION
         "Name of Mapping."
      ::= { adGenOtnOduMappingStatusEntry 1 }

   adGenOtnOduMappingStatus OBJECT-TYPE
      SYNTAX INTEGER {
                      source(1),
                      destination(2),
                      sourceAndDestination(3)
                     }
      MAX-ACCESS read-only
      STATUS current
      DESCRIPTION
         "This OID indicates whether this ODU is defined as a source, destination or both for
         this mapping."
      ::= { adGenOtnOduMappingStatusEntry 2 }


  -- /////////////////////////////////////////////////////////
  adGenOtnOtuPmThres15MinTable OBJECT-TYPE
      SYNTAX  SEQUENCE OF AdGenOtnOtuPmThres15MinEntry
      MAX-ACCESS  not-accessible
      STATUS  current
      DESCRIPTION
                 "OTU Performance Montitoring Threshold Provisioning 15-Minute table."
      ::= { adGenOtnPmThres 1 }

  adGenOtnOtuPmThres15MinEntry OBJECT-TYPE
      SYNTAX  AdGenOtnOtuPmThres15MinEntry
      MAX-ACCESS  not-accessible
      STATUS  current
      DESCRIPTION
                 "Table Entry"
      INDEX   { ifIndex }
      ::= { adGenOtnOtuPmThres15MinTable 1 }

  AdGenOtnOtuPmThres15MinEntry ::=
      SEQUENCE {
                adGenOtnOtuPmThres15MinNeEB
                  INTEGER,
                adGenOtnOtuPmThres15MinNeBBE
                  INTEGER,
                adGenOtnOtuPmThres15MinNeBBER
                  INTEGER,
                adGenOtnOtuPmThres15MinNeES
                  INTEGER,
                adGenOtnOtuPmThres15MinNeSES
                  INTEGER,
                adGenOtnOtuPmThres15MinNeESR
                  INTEGER,
                adGenOtnOtuPmThres15MinNeSESR
                  INTEGER,
                adGenOtnOtuPmThres15MinNeUAS
                  INTEGER,
                adGenOtnOtuPmThres15MinFeEB
                  INTEGER,
                adGenOtnOtuPmThres15MinFeBBE
                  INTEGER,
                adGenOtnOtuPmThres15MinFeBBER
                  INTEGER,
                adGenOtnOtuPmThres15MinFeES
                  INTEGER,
                adGenOtnOtuPmThres15MinFeSES
                  INTEGER,
                adGenOtnOtuPmThres15MinFeESR
                  INTEGER,
                adGenOtnOtuPmThres15MinFeSESR
                  INTEGER,
                adGenOtnOtuPmThres15MinFeUAS
                  INTEGER,
                adGenOtnOtuPmThres15MinFecCorrBits
                  Unsigned64TC,
                adGenOtnOtuPmThres15MinFecCorrOnes
                  Unsigned64TC,
                adGenOtnOtuPmThres15MinFecCorrZeros
                  Unsigned64TC,
                adGenOtnOtuPmThres15MinFecUnCorrBlks
                  Unsigned64TC,
                adGenOtnOtuPmThres15MinFecCorrBer
                  INTEGER
               }

  adGenOtnOtuPmThres15MinNeEB    OBJECT-TYPE
      SYNTAX INTEGER (0..700000)
      MAX-ACCESS read-write
      STATUS current
      DESCRIPTION
              "OTU Performance Monitoring Threshold for 15-Minute Near-End Errored Blocks.
              Threshold range can vary depending OTU Mode as follows:
              OTU4 - 0 to 700000
              OTU3 - 0 to 270000
              OTU2 - 0 to  70000
              OTU1 - 0 to  17500"
      ::= { adGenOtnOtuPmThres15MinEntry 1 }

  adGenOtnOtuPmThres15MinNeBBE    OBJECT-TYPE
      SYNTAX INTEGER (0..700000)
      MAX-ACCESS read-write
      STATUS current
      DESCRIPTION
              "OTU Performance Monitoring Threshold for 15-Minute Near-End Background Block Errors.
              Threshold range can vary depending OTU Mode as follows:
              OTU4 - 0 to 700000
              OTU3 - 0 to 270000
              OTU2 - 0 to  70000
              OTU1 - 0 to  17500"
      ::= { adGenOtnOtuPmThres15MinEntry 2 }

  adGenOtnOtuPmThres15MinNeBBER    OBJECT-TYPE
      SYNTAX INTEGER {
                      disable(1),           -- threshold disabled
                      oneExpMinusThree(2),  -- 1e-3,  10^-3
                      oneExpMinusFour(3),   -- 1e-4,  10^-4
                      oneExpMinusFive(4),   -- 1e-5,  10^-5
                      oneExpMinusSix(5),    -- 1e-6,  10^-6
                      oneExpMinusSeven(6),  -- 1e-7,  10^-7
                      oneExpMinusEight(7),  -- 1e-8,  10^-8
                      oneExpMinusNine(8),   -- 1e-9,  10^-9
                      oneExpMinusTen(9)     -- 1e-10, 10^-10
                     }
      MAX-ACCESS read-write
      STATUS current
      DESCRIPTION
              "OTU Performance Monitoring Threshold for 15-Minute Near-End Background Block Error Ratio."
      ::= { adGenOtnOtuPmThres15MinEntry 3 }

  adGenOtnOtuPmThres15MinNeES    OBJECT-TYPE
      SYNTAX INTEGER (0..900)
      MAX-ACCESS read-write
      STATUS current
      DESCRIPTION
              "OTU Performance Monitoring Threshold for 15-Minute Near-End Errored Seconds."
      ::= { adGenOtnOtuPmThres15MinEntry 4 }

  adGenOtnOtuPmThres15MinNeSES    OBJECT-TYPE
      SYNTAX INTEGER (0..900)
      MAX-ACCESS read-write
      STATUS current
      DESCRIPTION
              "OTU Performance Monitoring Threshold for 15-Minute Near-End Severely Errored Seconds."
      ::= { adGenOtnOtuPmThres15MinEntry 5 }

  adGenOtnOtuPmThres15MinNeESR    OBJECT-TYPE
      SYNTAX INTEGER (0..999)
      MAX-ACCESS read-write
      STATUS current
      DESCRIPTION
              "OTU Performance Monitoring Threshold for 15-Minute Near-End Errored Second Ratio.
              ESR is a decimal number between 0 and 0.999.  In order to not deal with a decimal number, the
              ESR value is multiplied by 1000 for this OID."
      ::= { adGenOtnOtuPmThres15MinEntry 6 }

  adGenOtnOtuPmThres15MinNeSESR    OBJECT-TYPE
      SYNTAX INTEGER (0..999)
      MAX-ACCESS read-write
      STATUS current
      DESCRIPTION
              "OTU Performance Monitoring Threshold for 15-Minute Near-End Severely Errored Second Ratio.
              SESR is a decimal number between 0 and 0.999.  In order to not deal with a decimal number, the
              SESR value is multiplied by 1000 for this OID."
      ::= { adGenOtnOtuPmThres15MinEntry 7 }

  adGenOtnOtuPmThres15MinNeUAS    OBJECT-TYPE
      SYNTAX INTEGER (0..900)
      MAX-ACCESS read-write
      STATUS current
      DESCRIPTION
              "OTU Performance Monitoring Threshold for 15-Minute Near-End Unavailable Seconds."
      ::= { adGenOtnOtuPmThres15MinEntry 8 }

  adGenOtnOtuPmThres15MinFeEB    OBJECT-TYPE
      SYNTAX INTEGER (0..700000)
      MAX-ACCESS read-write
      STATUS current
      DESCRIPTION
              "OTU Performance Monitoring Threshold for 15-Minute Far-End Errored Blocks.
              Threshold range can vary depending OTU Mode as follows:
              OTU4 - 0 to 700000
              OTU3 - 0 to 270000
              OTU2 - 0 to  70000
              OTU1 - 0 to  17500"
      ::= { adGenOtnOtuPmThres15MinEntry 9 }

  adGenOtnOtuPmThres15MinFeBBE    OBJECT-TYPE
      SYNTAX INTEGER (0..700000)
      MAX-ACCESS read-write
      STATUS current
      DESCRIPTION
              "OTU Performance Monitoring Threshold for 15-Minute Far-End Background Block Errors.
              Threshold range can vary depending OTU Mode as follows:
              OTU4 - 0 to 700000
              OTU3 - 0 to 270000
              OTU2 - 0 to  70000
              OTU1 - 0 to  17500"
      ::= { adGenOtnOtuPmThres15MinEntry 10 }

  adGenOtnOtuPmThres15MinFeBBER    OBJECT-TYPE
      SYNTAX INTEGER {
                      disable(1),           -- threshold disabled
                      oneExpMinusThree(2),  -- 1e-3,  10^-3
                      oneExpMinusFour(3),   -- 1e-4,  10^-4
                      oneExpMinusFive(4),   -- 1e-5,  10^-5
                      oneExpMinusSix(5),    -- 1e-6,  10^-6
                      oneExpMinusSeven(6),  -- 1e-7,  10^-7
                      oneExpMinusEight(7),  -- 1e-8,  10^-8
                      oneExpMinusNine(8),   -- 1e-9,  10^-9
                      oneExpMinusTen(9)     -- 1e-10, 10^-10
                     }
      MAX-ACCESS read-write
      STATUS current
      DESCRIPTION
              "OTU Performance Monitoring Threshold for 15-Minute Far-End Background Block Error Ratio."
      ::= { adGenOtnOtuPmThres15MinEntry 11 }

  adGenOtnOtuPmThres15MinFeES    OBJECT-TYPE
      SYNTAX INTEGER (0..900)
      MAX-ACCESS read-write
      STATUS current
      DESCRIPTION
              "OTU Performance Monitoring Threshold for 15-Minute Far-End Errored Seconds."
      ::= { adGenOtnOtuPmThres15MinEntry 12 }

  adGenOtnOtuPmThres15MinFeSES    OBJECT-TYPE
      SYNTAX INTEGER (0..900)
      MAX-ACCESS read-write
      STATUS current
      DESCRIPTION
              "OTU Performance Monitoring Threshold for 15-Minute Far-End Severely Errored Seconds."
      ::= { adGenOtnOtuPmThres15MinEntry 13 }

  adGenOtnOtuPmThres15MinFeESR    OBJECT-TYPE
      SYNTAX INTEGER (0..999)
      MAX-ACCESS read-write
      STATUS current
      DESCRIPTION
              "OTU Performance Monitoring Threshold for 15-Minute Far-End Errored Second Ratio.
              ESR is a decimal number between 0 and 0.999.  In order to not deal with a decimal number, the
              ESR value is multiplied by 1000 for this OID."
      ::= { adGenOtnOtuPmThres15MinEntry 14 }

  adGenOtnOtuPmThres15MinFeSESR    OBJECT-TYPE
      SYNTAX INTEGER (0..999)
      MAX-ACCESS read-write
      STATUS current
      DESCRIPTION
              "OTU Performance Monitoring Threshold for 15-Minute Far-End Severely Errored Second Ratio.
              SESR is a decimal number between 0 and 0.999.  In order to not deal with a decimal number, the
              SESR value is multiplied by 1000 for this OID."
      ::= { adGenOtnOtuPmThres15MinEntry 15 }

  adGenOtnOtuPmThres15MinFeUAS    OBJECT-TYPE
      SYNTAX INTEGER (0..900)
      MAX-ACCESS read-write
      STATUS current
      DESCRIPTION
              "OTU Performance Monitoring Threshold for 15-Minute Far-End Unavailable Seconds."
      ::= { adGenOtnOtuPmThres15MinEntry 16 }

  adGenOtnOtuPmThres15MinFecCorrBits    OBJECT-TYPE
      SYNTAX Unsigned64TC
      MAX-ACCESS read-write
      STATUS current
      DESCRIPTION
              "OTU Performance Monitoring Threshold for 15-Minute FEC (Forward Error Correction)
              Corrected Bits.
              Threshold range can vary depending OTU Mode as follows:
              OTU4 - 0 to 100000000000
              OTU3 - 0 to  40000000000
              OTU2 - 0 to  10000000000
              OTU1 - 0 to   2500000000"
      ::= { adGenOtnOtuPmThres15MinEntry 17 }

  adGenOtnOtuPmThres15MinFecCorrOnes    OBJECT-TYPE
      SYNTAX Unsigned64TC
      MAX-ACCESS read-write
      STATUS current
      DESCRIPTION
              "OTU Performance Monitoring Threshold for 15-Minute FEC (Forward Error Correction)
              Corrected Ones.
              Threshold range can vary depending OTU Mode as follows:
              OTU4 - 0 to 100000000000
              OTU3 - 0 to  40000000000
              OTU2 - 0 to  10000000000
              OTU1 - 0 to   2500000000"
      ::= { adGenOtnOtuPmThres15MinEntry 18 }

  adGenOtnOtuPmThres15MinFecCorrZeros    OBJECT-TYPE
      SYNTAX Unsigned64TC
      MAX-ACCESS read-write
      STATUS current
      DESCRIPTION
              "OTU Performance Monitoring Threshold for 15-Minute FEC (Forward Error Correction)
              Corrected Zeros.
              Threshold range can vary depending OTU Mode as follows:
              OTU4 - 0 to 100000000000
              OTU3 - 0 to  40000000000
              OTU2 - 0 to  10000000000
              OTU1 - 0 to   2500000000"
      ::= { adGenOtnOtuPmThres15MinEntry 19 }

  adGenOtnOtuPmThres15MinFecUnCorrBlks    OBJECT-TYPE
      SYNTAX Unsigned64TC
      MAX-ACCESS read-write
      STATUS current
      DESCRIPTION
              "OTU Performance Monitoring Threshold for 15-Minute FEC (Forward Error Correction)
              Uncorrected Blocks.
              Threshold range can vary depending OTU Mode as follows:
              OTU4 - 0 to 100000000000
              OTU3 - 0 to  40000000000
              OTU2 - 0 to  10000000000
              OTU1 - 0 to   2500000000"
      ::= { adGenOtnOtuPmThres15MinEntry 20 }

  adGenOtnOtuPmThres15MinFecCorrBer    OBJECT-TYPE
      SYNTAX INTEGER {
                      disable(1),           -- threshold disabled
                      oneExpMinusThree(2),  -- 1e-3,  10^-3
                      oneExpMinusFour(3),   -- 1e-4,  10^-4
                      oneExpMinusFive(4),   -- 1e-5,  10^-5
                      oneExpMinusSix(5),    -- 1e-6,  10^-6
                      oneExpMinusSeven(6),  -- 1e-7,  10^-7
                      oneExpMinusEight(7),  -- 1e-8,  10^-8
                      oneExpMinusNine(8),   -- 1e-9,  10^-9
                      oneExpMinusTen(9)     -- 1e-10, 10^-10
                     }
      MAX-ACCESS read-write
      STATUS current
      DESCRIPTION
              "OTU Performance Monitoring Threshold for 15-Minute FEC (Forward Error Correction)
              Corrected Bit Error Rate."
      ::= { adGenOtnOtuPmThres15MinEntry 21 }


  -- /////////////////////////////////////////////////////////
  adGenOtnOtuPmThres24HrTable OBJECT-TYPE
      SYNTAX  SEQUENCE OF AdGenOtnOtuPmThres24HrEntry
      MAX-ACCESS  not-accessible
      STATUS  current
      DESCRIPTION
                 "OTU Performance Montitoring Threshold Provisioning 24-Hour table."
      ::= { adGenOtnPmThres 2 }

  adGenOtnOtuPmThres24HrEntry OBJECT-TYPE
      SYNTAX  AdGenOtnOtuPmThres24HrEntry
      MAX-ACCESS  not-accessible
      STATUS  current
      DESCRIPTION
                 "Table Entry"
      INDEX   { ifIndex }
      ::= { adGenOtnOtuPmThres24HrTable 1 }

  AdGenOtnOtuPmThres24HrEntry ::=
      SEQUENCE {
                adGenOtnOtuPmThres24HrNeEB
                  INTEGER,
                adGenOtnOtuPmThres24HrNeBBE
                  INTEGER,
                adGenOtnOtuPmThres24HrNeBBER
                  INTEGER,
                adGenOtnOtuPmThres24HrNeES
                  INTEGER,
                adGenOtnOtuPmThres24HrNeSES
                  INTEGER,
                adGenOtnOtuPmThres24HrNeESR
                  INTEGER,
                adGenOtnOtuPmThres24HrNeSESR
                  INTEGER,
                adGenOtnOtuPmThres24HrNeUAS
                  INTEGER,
                adGenOtnOtuPmThres24HrFeEB
                  INTEGER,
                adGenOtnOtuPmThres24HrFeBBE
                  INTEGER,
                adGenOtnOtuPmThres24HrFeBBER
                  INTEGER,
                adGenOtnOtuPmThres24HrFeES
                  INTEGER,
                adGenOtnOtuPmThres24HrFeSES
                  INTEGER,
                adGenOtnOtuPmThres24HrFeESR
                  INTEGER,
                adGenOtnOtuPmThres24HrFeSESR
                  INTEGER,
                adGenOtnOtuPmThres24HrFeUAS
                  INTEGER,
                adGenOtnOtuPmThres24HrFecCorrBits
                  Unsigned64TC,
                adGenOtnOtuPmThres24HrFecCorrOnes
                  Unsigned64TC,
                adGenOtnOtuPmThres24HrFecCorrZeros
                  Unsigned64TC,
                adGenOtnOtuPmThres24HrFecUnCorrBlks
                  Unsigned64TC,
                adGenOtnOtuPmThres24HrFecCorrBer
                  INTEGER
               }

  adGenOtnOtuPmThres24HrNeEB    OBJECT-TYPE
      SYNTAX INTEGER (0..70000000)
      MAX-ACCESS read-write
      STATUS current
      DESCRIPTION
              "OTU Performance Monitoring Threshold for 24-Hour Near-End Errored Blocks.
              Threshold range can vary depending OTU Mode as follows:
              OTU4 - 0 to 70000000
              OTU3 - 0 to 28000000
              OTU2 - 0 to  7000000
              OTU1 - 0 to  1750000"
      ::= { adGenOtnOtuPmThres24HrEntry 1 }

  adGenOtnOtuPmThres24HrNeBBE    OBJECT-TYPE
      SYNTAX INTEGER (0..70000000)
      MAX-ACCESS read-write
      STATUS current
      DESCRIPTION
              "OTU Performance Monitoring Threshold for 24-Hour Near-End Background Block Errors.
              Threshold range can vary depending OTU Mode as follows:
              OTU4 - 0 to 70000000
              OTU3 - 0 to 28000000
              OTU2 - 0 to  7000000
              OTU1 - 0 to  1750000"
      ::= { adGenOtnOtuPmThres24HrEntry 2 }

  adGenOtnOtuPmThres24HrNeBBER    OBJECT-TYPE
      SYNTAX INTEGER {
                      disable(1),           -- threshold disabled
                      oneExpMinusThree(2),  -- 1e-3,  10^-3
                      oneExpMinusFour(3),   -- 1e-4,  10^-4
                      oneExpMinusFive(4),   -- 1e-5,  10^-5
                      oneExpMinusSix(5),    -- 1e-6,  10^-6
                      oneExpMinusSeven(6),  -- 1e-7,  10^-7
                      oneExpMinusEight(7),  -- 1e-8,  10^-8
                      oneExpMinusNine(8),   -- 1e-9,  10^-9
                      oneExpMinusTen(9)     -- 1e-10, 10^-10
                     }
      MAX-ACCESS read-write
      STATUS current
      DESCRIPTION
              "OTU Performance Monitoring Threshold for 24-Hour Near-End Background Block Error Ratio."
      ::= { adGenOtnOtuPmThres24HrEntry 3 }

  adGenOtnOtuPmThres24HrNeES    OBJECT-TYPE
      SYNTAX INTEGER (0..86400)
      MAX-ACCESS read-write
      STATUS current
      DESCRIPTION
              "OTU Performance Monitoring Threshold for 24-Hour Near-End Errored Seconds."
      ::= { adGenOtnOtuPmThres24HrEntry 4 }

  adGenOtnOtuPmThres24HrNeSES    OBJECT-TYPE
      SYNTAX INTEGER (0..86400)
      MAX-ACCESS read-write
      STATUS current
      DESCRIPTION
              "OTU Performance Monitoring Threshold for 24-Hour Near-End Severely Errored Seconds."
      ::= { adGenOtnOtuPmThres24HrEntry 5 }

  adGenOtnOtuPmThres24HrNeESR    OBJECT-TYPE
      SYNTAX INTEGER (0..999)
      MAX-ACCESS read-write
      STATUS current
      DESCRIPTION
              "OTU Performance Monitoring Threshold for 24-Hour Near-End Errored Second Ratio.
              ESR is a decimal number between 0 and 0.999.  In order to not deal with a decimal number, the
              ESR value is multiplied by 1000 for this OID."
      ::= { adGenOtnOtuPmThres24HrEntry 6 }

  adGenOtnOtuPmThres24HrNeSESR    OBJECT-TYPE
      SYNTAX INTEGER (0..999)
      MAX-ACCESS read-write
      STATUS current
      DESCRIPTION
              "OTU Performance Monitoring Threshold for 24-Hour Near-End Severely Errored Second Ratio.
              SESR is a decimal number between 0 and 0.999.  In order to not deal with a decimal number, the
              SESR value is multiplied by 1000 for this OID."
      ::= { adGenOtnOtuPmThres24HrEntry 7 }

  adGenOtnOtuPmThres24HrNeUAS    OBJECT-TYPE
      SYNTAX INTEGER (0..86400)
      MAX-ACCESS read-write
      STATUS current
      DESCRIPTION
              "OTU Performance Monitoring Threshold for 24-Hour Near-End Unavailable Seconds."
      ::= { adGenOtnOtuPmThres24HrEntry 8 }

  adGenOtnOtuPmThres24HrFeEB    OBJECT-TYPE
      SYNTAX INTEGER (0..70000000)
      MAX-ACCESS read-write
      STATUS current
      DESCRIPTION
              "OTU Performance Monitoring Threshold for 24-Hour Far-End Errored Blocks.
              Threshold range can vary depending OTU Mode as follows:
              OTU4 - 0 to 70000000
              OTU3 - 0 to 28000000
              OTU2 - 0 to  7000000
              OTU1 - 0 to  1750000"
      ::= { adGenOtnOtuPmThres24HrEntry 9 }

  adGenOtnOtuPmThres24HrFeBBE    OBJECT-TYPE
      SYNTAX INTEGER (0..70000000)
      MAX-ACCESS read-write
      STATUS current
      DESCRIPTION
              "OTU Performance Monitoring Threshold for 24-Hour Far-End Background Block Errors.
              Threshold range can vary depending OTU Mode as follows:
              OTU4 - 0 to 70000000
              OTU3 - 0 to 28000000
              OTU2 - 0 to  7000000
              OTU1 - 0 to  1750000"
      ::= { adGenOtnOtuPmThres24HrEntry 10 }

  adGenOtnOtuPmThres24HrFeBBER    OBJECT-TYPE
      SYNTAX  INTEGER {
                      disable(1),           -- threshold disabled
                      oneExpMinusThree(2),  -- 1e-3,  10^-3
                      oneExpMinusFour(3),   -- 1e-4,  10^-4
                      oneExpMinusFive(4),   -- 1e-5,  10^-5
                      oneExpMinusSix(5),    -- 1e-6,  10^-6
                      oneExpMinusSeven(6),  -- 1e-7,  10^-7
                      oneExpMinusEight(7),  -- 1e-8,  10^-8
                      oneExpMinusNine(8),   -- 1e-9,  10^-9
                      oneExpMinusTen(9)     -- 1e-10, 10^-10
                     }
      MAX-ACCESS read-write
      STATUS current
      DESCRIPTION
              "OTU Performance Monitoring Threshold for 24-Hour Far-End Background Block Error Ratio."
      ::= { adGenOtnOtuPmThres24HrEntry 11 }

  adGenOtnOtuPmThres24HrFeES    OBJECT-TYPE
      SYNTAX INTEGER (0..86400)
      MAX-ACCESS read-write
      STATUS current
      DESCRIPTION
              "OTU Performance Monitoring Threshold for 24-Hour Far-End Errored Seconds."
      ::= { adGenOtnOtuPmThres24HrEntry 12 }

  adGenOtnOtuPmThres24HrFeSES    OBJECT-TYPE
      SYNTAX INTEGER (0..86400)
      MAX-ACCESS read-write
      STATUS current
      DESCRIPTION
              "OTU Performance Monitoring Threshold for 24-Hour Far-End Severely Errored Seconds."
      ::= { adGenOtnOtuPmThres24HrEntry 13 }

  adGenOtnOtuPmThres24HrFeESR    OBJECT-TYPE
      SYNTAX INTEGER (0..999)
      MAX-ACCESS read-write
      STATUS current
      DESCRIPTION
              "OTU Performance Monitoring Threshold for 24-Hour Far-End Errored Second Ratio.
              ESR is a decimal number between 0 and 0.999.  In order to not deal with a decimal number, the
              ESR value is multiplied by 1000 for this OID."
      ::= { adGenOtnOtuPmThres24HrEntry 14 }

  adGenOtnOtuPmThres24HrFeSESR    OBJECT-TYPE
      SYNTAX INTEGER (0..999)
      MAX-ACCESS read-write
      STATUS current
      DESCRIPTION
              "OTU Performance Monitoring Threshold for 24-Hour Far-End Severely Errored Second Ratio.
              SESR is a decimal number between 0 and 0.999.  In order to not deal with a decimal number, the
              SESR value is multiplied by 1000 for this OID."
      ::= { adGenOtnOtuPmThres24HrEntry 15 }

  adGenOtnOtuPmThres24HrFeUAS    OBJECT-TYPE
      SYNTAX INTEGER (0..86400)
      MAX-ACCESS read-write
      STATUS current
      DESCRIPTION
              "OTU Performance Monitoring Threshold for 24-Hour Far-End Unavailable Seconds."
      ::= { adGenOtnOtuPmThres24HrEntry 16 }

  adGenOtnOtuPmThres24HrFecCorrBits    OBJECT-TYPE
      SYNTAX Unsigned64TC
      MAX-ACCESS read-write
      STATUS current
      DESCRIPTION
              "OTU Performance Monitoring Threshold for 24-Hour FEC (Forward Error Correction)
              Corrected Bits.
              Threshold range can vary depending OTU Mode as follows:
              OTU4 - 0 to 10000000000000
              OTU3 - 0 to  4000000000000
              OTU2 - 0 to  1000000000000
              OTU1 - 0 to   250000000000"
      ::= { adGenOtnOtuPmThres24HrEntry 17 }

  adGenOtnOtuPmThres24HrFecCorrOnes    OBJECT-TYPE
      SYNTAX Unsigned64TC
      MAX-ACCESS read-write
      STATUS current
      DESCRIPTION
              "OTU Performance Monitoring Threshold for 24-Hour FEC (Forward Error Correction)
              Corrected Ones.
              Threshold range can vary depending OTU Mode as follows:
              OTU4 - 0 to 10000000000000
              OTU3 - 0 to  4000000000000
              OTU2 - 0 to  1000000000000
              OTU1 - 0 to   250000000000"
      ::= { adGenOtnOtuPmThres24HrEntry 18 }

  adGenOtnOtuPmThres24HrFecCorrZeros    OBJECT-TYPE
      SYNTAX Unsigned64TC
      MAX-ACCESS read-write
      STATUS current
      DESCRIPTION
              "OTU Performance Monitoring Threshold for 24-Hour FEC (Forward Error Correction)
              Corrected Zeros.
              Threshold range can vary depending OTU Mode as follows:
              OTU4 - 0 to 10000000000000
              OTU3 - 0 to  4000000000000
              OTU2 - 0 to  1000000000000
              OTU1 - 0 to   250000000000"
      ::= { adGenOtnOtuPmThres24HrEntry 19 }

  adGenOtnOtuPmThres24HrFecUnCorrBlks    OBJECT-TYPE
      SYNTAX Unsigned64TC
      MAX-ACCESS read-write
      STATUS current
      DESCRIPTION
              "OTU Performance Monitoring Threshold for 24-Hour FEC (Forward Error Correction)
              Uncorrected Blocks.
              Threshold range can vary depending OTU Mode as follows:
              OTU4 - 0 to 10000000000000
              OTU3 - 0 to  4000000000000
              OTU2 - 0 to  1000000000000
              OTU1 - 0 to   250000000000"
      ::= { adGenOtnOtuPmThres24HrEntry 20 }

  adGenOtnOtuPmThres24HrFecCorrBer    OBJECT-TYPE
      SYNTAX INTEGER {
                      disable(1),           -- threshold disabled
                      oneExpMinusThree(2),  -- 1e-3,  10^-3
                      oneExpMinusFour(3),   -- 1e-4,  10^-4
                      oneExpMinusFive(4),   -- 1e-5,  10^-5
                      oneExpMinusSix(5),    -- 1e-6,  10^-6
                      oneExpMinusSeven(6),  -- 1e-7,  10^-7
                      oneExpMinusEight(7),  -- 1e-8,  10^-8
                      oneExpMinusNine(8),   -- 1e-9,  10^-9
                      oneExpMinusTen(9)     -- 1e-10, 10^-10
                     }
      MAX-ACCESS read-write
      STATUS current
      DESCRIPTION
              "OTU Performance Monitoring Threshold for 24-Hour FEC (Forward Error Correction)
              Corrected Bit Error Rate."
      ::= { adGenOtnOtuPmThres24HrEntry 21 }


  -- /////////////////////////////////////////////////////////
  adGenOtnOduPmThres15MinTable OBJECT-TYPE
      SYNTAX  SEQUENCE OF AdGenOtnOduPmThres15MinEntry
      MAX-ACCESS  not-accessible
      STATUS  current
      DESCRIPTION
                 "ODU Performance Montitoring Threshold Provisioning 15-Minute table."
      ::= { adGenOtnPmThres 3 }

  adGenOtnOduPmThres15MinEntry OBJECT-TYPE
      SYNTAX  AdGenOtnOduPmThres15MinEntry
      MAX-ACCESS  not-accessible
      STATUS  current
      DESCRIPTION
                 "Table Entry"
      INDEX   { adGenSlotInfoIndex, adGenOtnOduIndex }
      ::= { adGenOtnOduPmThres15MinTable 1 }

  AdGenOtnOduPmThres15MinEntry ::=
      SEQUENCE {
                adGenOtnOduPmThres15MinNeEB
                  INTEGER,
                adGenOtnOduPmThres15MinNeBBE
                  INTEGER,
                adGenOtnOduPmThres15MinNeBBER
                  INTEGER,
                adGenOtnOduPmThres15MinNeES
                  INTEGER,
                adGenOtnOduPmThres15MinNeSES
                  INTEGER,
                adGenOtnOduPmThres15MinNeESR
                  INTEGER,
                adGenOtnOduPmThres15MinNeSESR
                  INTEGER,
                adGenOtnOduPmThres15MinNeUAS
                  INTEGER,
                adGenOtnOduPmThres15MinFeEB
                  INTEGER,
                adGenOtnOduPmThres15MinFeBBE
                  INTEGER,
                adGenOtnOduPmThres15MinFeBBER
                  INTEGER,
                adGenOtnOduPmThres15MinFeES
                  INTEGER,
                adGenOtnOduPmThres15MinFeSES
                  INTEGER,
                adGenOtnOduPmThres15MinFeESR
                  INTEGER,
                adGenOtnOduPmThres15MinFeSESR
                  INTEGER,
                adGenOtnOduPmThres15MinFeUAS
                  INTEGER
               }

  adGenOtnOduPmThres15MinNeEB    OBJECT-TYPE
      SYNTAX INTEGER (0..700000)
      MAX-ACCESS read-write
      STATUS current
      DESCRIPTION
              "ODU Performance Monitoring Threshold for 15-Minute Near-End Errored Blocks.
              Threshold range can vary depending ODU Bandwidth Type as follows:
              ODU4 - 0 to 700000
              ODU3 - 0 to 280000
              ODU2 - 0 to  70000
              ODU1 - 0 to   1750
              ODU0 - 0 to    875"
      ::= { adGenOtnOduPmThres15MinEntry 1 }

  adGenOtnOduPmThres15MinNeBBE    OBJECT-TYPE
      SYNTAX INTEGER (0..700000)
      MAX-ACCESS read-write
      STATUS current
      DESCRIPTION
              "ODU Performance Monitoring Threshold for 15-Minute Near-End Background Block Errors.
              Threshold range can vary depending ODU Bandwidth Type as follows:
              ODU4 - 0 to 700000
              ODU3 - 0 to 280000
              ODU2 - 0 to  70000
              ODU1 - 0 to   1750
              ODU0 - 0 to    875"
      ::= { adGenOtnOduPmThres15MinEntry 2 }

  adGenOtnOduPmThres15MinNeBBER    OBJECT-TYPE
      SYNTAX INTEGER {
                      disable(1),           -- threshold disabled
                      oneExpMinusThree(2),  -- 1e-3,  10^-3
                      oneExpMinusFour(3),   -- 1e-4,  10^-4
                      oneExpMinusFive(4),   -- 1e-5,  10^-5
                      oneExpMinusSix(5),    -- 1e-6,  10^-6
                      oneExpMinusSeven(6),  -- 1e-7,  10^-7
                      oneExpMinusEight(7),  -- 1e-8,  10^-8
                      oneExpMinusNine(8),   -- 1e-9,  10^-9
                      oneExpMinusTen(9)     -- 1e-10, 10^-10
                     }
      MAX-ACCESS read-write
      STATUS current
      DESCRIPTION
              "ODU Performance Monitoring Threshold for 15-Minute Near-End Background Block Error Ratio."
      ::= { adGenOtnOduPmThres15MinEntry 3 }

  adGenOtnOduPmThres15MinNeES    OBJECT-TYPE
      SYNTAX INTEGER (0..900)
      MAX-ACCESS read-write
      STATUS current
      DESCRIPTION
              "ODU Performance Monitoring Threshold for 15-Minute Near-End Errored Seconds."
      ::= { adGenOtnOduPmThres15MinEntry 4 }

  adGenOtnOduPmThres15MinNeSES    OBJECT-TYPE
      SYNTAX INTEGER (0..900)
      MAX-ACCESS read-write
      STATUS current
      DESCRIPTION
              "ODU Performance Monitoring Threshold for 15-Minute Near-End Severely Errored Seconds."
      ::= { adGenOtnOduPmThres15MinEntry 5 }

  adGenOtnOduPmThres15MinNeESR    OBJECT-TYPE
      SYNTAX INTEGER (0..999)
      MAX-ACCESS read-write
      STATUS current
      DESCRIPTION
              "ODU Performance Monitoring Threshold for 15-Minute Near-End Severely Errored Second Ratio.
              ESR is a decimal number between 0 and 0.999.  In order to not deal with a decimal number, the
              ESR value is multiplied by 1000 for this OID."
      ::= { adGenOtnOduPmThres15MinEntry 6 }

  adGenOtnOduPmThres15MinNeSESR    OBJECT-TYPE
      SYNTAX INTEGER (0..999)
      MAX-ACCESS read-write
      STATUS current
      DESCRIPTION
              "ODU Performance Monitoring Threshold for 15-Minute Near-End Severely Errored Second Ratio.
              SESR is a decimal number between 0 and 0.999.  In order to not deal with a decimal number, the
              SESR value is multiplied by 1000 for this OID."
      ::= { adGenOtnOduPmThres15MinEntry 7 }

  adGenOtnOduPmThres15MinNeUAS    OBJECT-TYPE
      SYNTAX INTEGER (0..900)
      MAX-ACCESS read-write
      STATUS current
      DESCRIPTION
              "ODU Performance Monitoring Threshold for 15-Minute Near-End Unavailable Seconds."
      ::= { adGenOtnOduPmThres15MinEntry 8 }

  adGenOtnOduPmThres15MinFeEB    OBJECT-TYPE
      SYNTAX INTEGER (0..700000)
      MAX-ACCESS read-write
      STATUS current
      DESCRIPTION
              "ODU Performance Monitoring Threshold for 15-Minute Far-End Errored Blocks.
              Threshold range can vary depending ODU Bandwidth Type as follows:
              ODU4 - 0 to 700000
              ODU3 - 0 to 280000
              ODU2 - 0 to  70000
              ODU1 - 0 to   1750
              ODU0 - 0 to    875"
      ::= { adGenOtnOduPmThres15MinEntry 9 }

  adGenOtnOduPmThres15MinFeBBE    OBJECT-TYPE
      SYNTAX INTEGER (0..700000)
      MAX-ACCESS read-write
      STATUS current
      DESCRIPTION
              "ODU Performance Monitoring Threshold for 15-Minute Far-End Background Block Errors.
              Threshold range can vary depending ODU Bandwidth Type as follows:
              ODU4 - 0 to 700000
              ODU3 - 0 to 280000
              ODU2 - 0 to  70000
              ODU1 - 0 to   1750
              ODU0 - 0 to    875"
      ::= { adGenOtnOduPmThres15MinEntry 10 }

  adGenOtnOduPmThres15MinFeBBER    OBJECT-TYPE
      SYNTAX INTEGER {
                      disable(1),           -- threshold disabled
                      oneExpMinusThree(2),  -- 1e-3,  10^-3
                      oneExpMinusFour(3),   -- 1e-4,  10^-4
                      oneExpMinusFive(4),   -- 1e-5,  10^-5
                      oneExpMinusSix(5),    -- 1e-6,  10^-6
                      oneExpMinusSeven(6),  -- 1e-7,  10^-7
                      oneExpMinusEight(7),  -- 1e-8,  10^-8
                      oneExpMinusNine(8),   -- 1e-9,  10^-9
                      oneExpMinusTen(9)     -- 1e-10, 10^-10
                     }
      MAX-ACCESS read-write
      STATUS current
      DESCRIPTION
              "ODU Performance Monitoring Threshold for 15-Minute Far-End Background Block Error Ratio."
      ::= { adGenOtnOduPmThres15MinEntry 11 }

  adGenOtnOduPmThres15MinFeES    OBJECT-TYPE
      SYNTAX INTEGER (0..900)
      MAX-ACCESS read-write
      STATUS current
      DESCRIPTION
              "ODU Performance Monitoring Threshold for 15-Minute Far-End Errored Seconds."
      ::= { adGenOtnOduPmThres15MinEntry 12 }

  adGenOtnOduPmThres15MinFeSES    OBJECT-TYPE
      SYNTAX INTEGER (0..900)
      MAX-ACCESS read-write
      STATUS current
      DESCRIPTION
              "ODU Performance Monitoring Threshold for 15-Minute Far-End Severely Errored Seconds."
      ::= { adGenOtnOduPmThres15MinEntry 13 }

  adGenOtnOduPmThres15MinFeESR    OBJECT-TYPE
      SYNTAX INTEGER (0..999)
      MAX-ACCESS read-write
      STATUS current
      DESCRIPTION
              "ODU Performance Monitoring Threshold for 15-Minute Far-End Severely Errored Second Ratio.
              ESR is a decimal number between 0 and 0.999.  In order to not deal with a decimal number, the
              ESR value is multiplied by 1000 for this OID."
      ::= { adGenOtnOduPmThres15MinEntry 14 }

  adGenOtnOduPmThres15MinFeSESR    OBJECT-TYPE
      SYNTAX INTEGER (0..999)
      MAX-ACCESS read-write
      STATUS current
      DESCRIPTION
              "ODU Performance Monitoring Threshold for 15-Minute Far-End Severely Errored Second Ratio.
              SESR is a decimal number between 0 and 0.999.  In order to not deal with a decimal number, the
              SESR value is multiplied by 1000 for this OID."
      ::= { adGenOtnOduPmThres15MinEntry 15 }

  adGenOtnOduPmThres15MinFeUAS    OBJECT-TYPE
      SYNTAX INTEGER (0..900)
      MAX-ACCESS read-write
      STATUS current
      DESCRIPTION
              "ODU Performance Monitoring Threshold for 15-Minute Far-End Unavailable Seconds."
      ::= { adGenOtnOduPmThres15MinEntry 16 }


  -- /////////////////////////////////////////////////////////
  adGenOtnOduPmThres24HrTable OBJECT-TYPE
      SYNTAX  SEQUENCE OF AdGenOtnOduPmThres24HrEntry
      MAX-ACCESS  not-accessible
      STATUS  current
      DESCRIPTION
                 "ODU Performance Montitoring Threshold Provisioning 24-Hour table."
      ::= { adGenOtnPmThres 4 }

  adGenOtnOduPmThres24HrEntry OBJECT-TYPE
      SYNTAX  AdGenOtnOduPmThres24HrEntry
      MAX-ACCESS  not-accessible
      STATUS  current
      DESCRIPTION
                 "Table Entry"
      INDEX   { adGenSlotInfoIndex, adGenOtnOduIndex }
      ::= { adGenOtnOduPmThres24HrTable 1 }

  AdGenOtnOduPmThres24HrEntry ::=
      SEQUENCE {
                adGenOtnOduPmThres24HrNeEB
                  INTEGER,
                adGenOtnOduPmThres24HrNeBBE
                  INTEGER,
                adGenOtnOduPmThres24HrNeBBER
                  INTEGER,
                adGenOtnOduPmThres24HrNeES
                  INTEGER,
                adGenOtnOduPmThres24HrNeSES
                  INTEGER,
                adGenOtnOduPmThres24HrNeESR
                  INTEGER,
                adGenOtnOduPmThres24HrNeSESR
                  INTEGER,
                adGenOtnOduPmThres24HrNeUAS
                  INTEGER,
                adGenOtnOduPmThres24HrFeEB
                  INTEGER,
                adGenOtnOduPmThres24HrFeBBE
                  INTEGER,
                adGenOtnOduPmThres24HrFeBBER
                  INTEGER,
                adGenOtnOduPmThres24HrFeES
                  INTEGER,
                adGenOtnOduPmThres24HrFeSES
                  INTEGER,
                adGenOtnOduPmThres24HrFeESR
                  INTEGER,
                adGenOtnOduPmThres24HrFeSESR
                  INTEGER,
                adGenOtnOduPmThres24HrFeUAS
                  INTEGER
               }

  adGenOtnOduPmThres24HrNeEB    OBJECT-TYPE
      SYNTAX INTEGER (0..70000000)
      MAX-ACCESS read-write
      STATUS current
      DESCRIPTION
              "ODU Performance Monitoring Threshold for 15-Minute Near-End Errored Blocks.
              Threshold range can vary depending ODU Bandwidth Type as follows:
              ODU4 - 0 to 70000000
              ODU3 - 0 to 28000000
              ODU2 - 0 to  7000000
              ODU1 - 0 to   175000
              ODU0 - 0 to    87500"
      ::= { adGenOtnOduPmThres24HrEntry 1 }

  adGenOtnOduPmThres24HrNeBBE    OBJECT-TYPE
      SYNTAX INTEGER (0..70000000)
      MAX-ACCESS read-write
      STATUS current
      DESCRIPTION
              "ODU Performance Monitoring Threshold for 24-Hour Near-End Background Block Errors.
              Threshold range can vary depending ODU Bandwidth Type as follows:
              ODU4 - 0 to 70000000
              ODU3 - 0 to 28000000
              ODU2 - 0 to  7000000
              ODU1 - 0 to   175000
              ODU0 - 0 to    87500"
      ::= { adGenOtnOduPmThres24HrEntry 2 }

  adGenOtnOduPmThres24HrNeBBER    OBJECT-TYPE
      SYNTAX INTEGER {
                      disable(1),           -- threshold disabled
                      oneExpMinusThree(2),  -- 1e-3,  10^-3
                      oneExpMinusFour(3),   -- 1e-4,  10^-4
                      oneExpMinusFive(4),   -- 1e-5,  10^-5
                      oneExpMinusSix(5),    -- 1e-6,  10^-6
                      oneExpMinusSeven(6),  -- 1e-7,  10^-7
                      oneExpMinusEight(7),  -- 1e-8,  10^-8
                      oneExpMinusNine(8),   -- 1e-9,  10^-9
                      oneExpMinusTen(9)     -- 1e-10, 10^-10
                     }
      MAX-ACCESS read-write
      STATUS current
      DESCRIPTION
              "ODU Performance Monitoring Threshold for 24-Hour Near-End Background Block Error Ratio."
      ::= { adGenOtnOduPmThres24HrEntry 3 }

  adGenOtnOduPmThres24HrNeES    OBJECT-TYPE
      SYNTAX INTEGER (0..86400)
      MAX-ACCESS read-write
      STATUS current
      DESCRIPTION
              "ODU Performance Monitoring Threshold for 24-Hour Near-End Errored Seconds."
      ::= { adGenOtnOduPmThres24HrEntry 4 }

  adGenOtnOduPmThres24HrNeSES    OBJECT-TYPE
      SYNTAX INTEGER (0..86400)
      MAX-ACCESS read-write
      STATUS current
      DESCRIPTION
              "ODU Performance Monitoring Threshold for 24-Hour Near-End Severely Errored Seconds."
      ::= { adGenOtnOduPmThres24HrEntry 5 }

  adGenOtnOduPmThres24HrNeESR    OBJECT-TYPE
      SYNTAX INTEGER (0..999)
      MAX-ACCESS read-write
      STATUS current
      DESCRIPTION
              "ODU Performance Monitoring Threshold for 24-Hour Near-End Severely Errored Second Ratio.
              ESR is a decimal number between 0 and 0.999.  In order to not deal with a decimal number, the
              ESR value is multiplied by 1000 for this OID."
      ::= { adGenOtnOduPmThres24HrEntry 6 }

  adGenOtnOduPmThres24HrNeSESR    OBJECT-TYPE
      SYNTAX INTEGER (0..999)
      MAX-ACCESS read-write
      STATUS current
      DESCRIPTION
              "ODU Performance Monitoring Threshold for 24-Hour Near-End Severely Errored Second Ratio.
              SESR is a decimal number between 0 and 0.999.  In order to not deal with a decimal number, the
              SESR value is multiplied by 1000 for this OID."
      ::= { adGenOtnOduPmThres24HrEntry 7 }

  adGenOtnOduPmThres24HrNeUAS    OBJECT-TYPE
      SYNTAX INTEGER (0..86400)
      MAX-ACCESS read-write
      STATUS current
      DESCRIPTION
              "ODU Performance Monitoring Threshold for 24-Hour Near-End Unavailable Seconds."
      ::= { adGenOtnOduPmThres24HrEntry 8 }

  adGenOtnOduPmThres24HrFeEB    OBJECT-TYPE
      SYNTAX INTEGER (0..70000000)
      MAX-ACCESS read-write
      STATUS current
      DESCRIPTION
              "ODU Performance Monitoring Threshold for 24-Hour Far-End Errored Blocks.
              Threshold range can vary depending ODU Bandwidth Type as follows:
              ODU4 - 0 to 70000000
              ODU3 - 0 to 28000000
              ODU2 - 0 to  7000000
              ODU1 - 0 to   175000
              ODU0 - 0 to    87500"
      ::= { adGenOtnOduPmThres24HrEntry 9 }

  adGenOtnOduPmThres24HrFeBBE    OBJECT-TYPE
      SYNTAX INTEGER (0..70000000)
      MAX-ACCESS read-write
      STATUS current
      DESCRIPTION
              "ODU Performance Monitoring Threshold for 24-Hour Far-End Background Block Errors.
              Threshold range can vary depending ODU Bandwidth Type as follows:
              ODU4 - 0 to 70000000
              ODU3 - 0 to 28000000
              ODU2 - 0 to  7000000
              ODU1 - 0 to   175000
              ODU0 - 0 to    87500"
      ::= { adGenOtnOduPmThres24HrEntry 10 }

  adGenOtnOduPmThres24HrFeBBER    OBJECT-TYPE
      SYNTAX INTEGER {
                      disable(1),           -- threshold disabled
                      oneExpMinusThree(2),  -- 1e-3,  10^-3
                      oneExpMinusFour(3),   -- 1e-4,  10^-4
                      oneExpMinusFive(4),   -- 1e-5,  10^-5
                      oneExpMinusSix(5),    -- 1e-6,  10^-6
                      oneExpMinusSeven(6),  -- 1e-7,  10^-7
                      oneExpMinusEight(7),  -- 1e-8,  10^-8
                      oneExpMinusNine(8),   -- 1e-9,  10^-9
                      oneExpMinusTen(9)     -- 1e-10, 10^-10
                     }
      MAX-ACCESS read-write
      STATUS current
      DESCRIPTION
              "ODU Performance Monitoring Threshold for 24-Hour Far-End Background Block Error Ratio."
      ::= { adGenOtnOduPmThres24HrEntry 11 }

  adGenOtnOduPmThres24HrFeES    OBJECT-TYPE
      SYNTAX INTEGER (0..86400)
      MAX-ACCESS read-write
      STATUS current
      DESCRIPTION
              "ODU Performance Monitoring Threshold for 24-Hour Far-End Errored Seconds."
      ::= { adGenOtnOduPmThres24HrEntry 12 }

  adGenOtnOduPmThres24HrFeSES    OBJECT-TYPE
      SYNTAX INTEGER (0..86400)
      MAX-ACCESS read-write
      STATUS current
      DESCRIPTION
              "ODU Performance Monitoring Threshold for 24-Hour Far-End Severely Errored Seconds."
      ::= { adGenOtnOduPmThres24HrEntry 13 }

  adGenOtnOduPmThres24HrFeESR    OBJECT-TYPE
      SYNTAX INTEGER (0..999)
      MAX-ACCESS read-write
      STATUS current
      DESCRIPTION
              "ODU Performance Monitoring Threshold for 24-Hour Far-End Severely Errored Second Ratio.
              ESR is a decimal number between 0 and 0.999.  In order to not deal with a decimal number, the
              ESR value is multiplied by 1000 for this OID."
      ::= { adGenOtnOduPmThres24HrEntry 14 }

  adGenOtnOduPmThres24HrFeSESR    OBJECT-TYPE
      SYNTAX INTEGER (0..999)
      MAX-ACCESS read-write
      STATUS current
      DESCRIPTION
              "ODU Performance Monitoring Threshold for 24-Hour Far-End Severely Errored Second Ratio.
              SESR is a decimal number between 0 and 0.999.  In order to not deal with a decimal number, the
              SESR value is multiplied by 1000 for this OID."
      ::= { adGenOtnOduPmThres24HrEntry 15 }

  adGenOtnOduPmThres24HrFeUAS    OBJECT-TYPE
      SYNTAX INTEGER (0..86400)
      MAX-ACCESS read-write
      STATUS current
      DESCRIPTION
              "ODU Performance Monitoring Threshold for 24-Hour Far-End Unavailable Seconds."
      ::= { adGenOtnOduPmThres24HrEntry 16 }


  -- /////////////////////////////////////////////////////////
  adGenOtnOtuPm15MinCurrentTable OBJECT-TYPE
      SYNTAX  SEQUENCE OF AdGenOtnOtuPm15MinCurrentEntry
      MAX-ACCESS  not-accessible
      STATUS  current
      DESCRIPTION
                 "OTU Performance Montitoring 15-Minute Current table."
      ::= { adGenOtnPm 1 }

  adGenOtnOtuPm15MinCurrentEntry OBJECT-TYPE
      SYNTAX  AdGenOtnOtuPm15MinCurrentEntry
      MAX-ACCESS  not-accessible
      STATUS  current
      DESCRIPTION
                 "Table Entry"
      INDEX   { ifIndex }
      ::= { adGenOtnOtuPm15MinCurrentTable 1 }

  AdGenOtnOtuPm15MinCurrentEntry ::=
      SEQUENCE {
                adGenOtnOtuPm15MinCurrentNeEB
                  Counter32,
                adGenOtnOtuPm15MinCurrentNeBBE
                  Counter32,
                adGenOtnOtuPm15MinCurrentNeBBER
                  DisplayString,
                adGenOtnOtuPm15MinCurrentNeES
                  Counter32,
                adGenOtnOtuPm15MinCurrentNeSES
                  Counter32,
                adGenOtnOtuPm15MinCurrentNeESR
                  Counter32,
                adGenOtnOtuPm15MinCurrentNeSESR
                  Counter32,
                adGenOtnOtuPm15MinCurrentNeUAS
                  Counter32,
                adGenOtnOtuPm15MinCurrentFeEB
                  Counter32,
                adGenOtnOtuPm15MinCurrentFeBBE
                  Counter32,
                adGenOtnOtuPm15MinCurrentFeBBER
                  DisplayString,
                adGenOtnOtuPm15MinCurrentFeES
                  Counter32,
                adGenOtnOtuPm15MinCurrentFeSES
                  Counter32,
                adGenOtnOtuPm15MinCurrentFeESR
                  Counter32,
                adGenOtnOtuPm15MinCurrentFeSESR
                  Counter32,
                adGenOtnOtuPm15MinCurrentFeUAS
                  Counter32,
                adGenOtnOtuPm15MinCurrentFecCorrBits
                  Counter64,
                adGenOtnOtuPm15MinCurrentFecCorrOnes
                  Counter64,
                adGenOtnOtuPm15MinCurrentFecCorrZeros
                  Counter64,
                adGenOtnOtuPm15MinCurrentFecUnCorrBlks
                  Counter64,
                adGenOtnOtuPm15MinCurrentFecCorrBer
                  DisplayString
               }

  adGenOtnOtuPm15MinCurrentNeEB    OBJECT-TYPE
      SYNTAX Counter32
      MAX-ACCESS read-only
      STATUS current
      DESCRIPTION
              "OTU Performance Monitoring for 15-Minute Current Near-End Errored Blocks."
      ::= { adGenOtnOtuPm15MinCurrentEntry 1 }

  adGenOtnOtuPm15MinCurrentNeBBE    OBJECT-TYPE
      SYNTAX Counter32
      MAX-ACCESS read-only
      STATUS current
      DESCRIPTION
              "OTU Performance Monitoring for 15-Minute Current Near-End Background Block Errors."
      ::= { adGenOtnOtuPm15MinCurrentEntry 2 }

  adGenOtnOtuPm15MinCurrentNeBBER    OBJECT-TYPE
      SYNTAX DisplayString (SIZE (0..13))
      MAX-ACCESS read-only
      STATUS current
      DESCRIPTION
              "OTU Performance Monitoring for 15-Minute Current Near-End Background Block Error Ratio.
              The BBER decimal value between 0 and 1 calculated out to as many as 10 decimal place."
      ::= { adGenOtnOtuPm15MinCurrentEntry 3 }

  adGenOtnOtuPm15MinCurrentNeES    OBJECT-TYPE
      SYNTAX Counter32
      MAX-ACCESS read-only
      STATUS current
      DESCRIPTION
              "OTU Performance Monitoring for 15-Minute Current Near-End Errored Seconds."
      ::= { adGenOtnOtuPm15MinCurrentEntry 4 }

  adGenOtnOtuPm15MinCurrentNeSES    OBJECT-TYPE
      SYNTAX Counter32
      MAX-ACCESS read-only
      STATUS current
      DESCRIPTION
              "OTU Performance Monitoring for 15-Minute Current Near-End Severely Errored Seconds."
      ::= { adGenOtnOtuPm15MinCurrentEntry 5 }

  adGenOtnOtuPm15MinCurrentNeESR    OBJECT-TYPE
      SYNTAX Counter32
      MAX-ACCESS read-only
      STATUS current
      DESCRIPTION
              "OTU Performance Monitoring for 15-Minute Current Near-End Errored Second Ratio.
              ESR is a decimal number between 0 and 0.999.  In order to not deal with a decimal number, the
              SESR value is multiplied by 1000 for this OID."
      ::= { adGenOtnOtuPm15MinCurrentEntry 6 }

  adGenOtnOtuPm15MinCurrentNeSESR    OBJECT-TYPE
      SYNTAX Counter32
      MAX-ACCESS read-only
      STATUS current
      DESCRIPTION
              "OTU Performance Monitoring for 15-Minute Current Near-End Severely Errored Second Ratio.
              SESR is a decimal number between 0 and 0.999.  In order to not deal with a decimal number, the
              SESR value is multiplied by 1000 for this OID."
      ::= { adGenOtnOtuPm15MinCurrentEntry 7 }

  adGenOtnOtuPm15MinCurrentNeUAS    OBJECT-TYPE
      SYNTAX Counter32
      MAX-ACCESS read-only
      STATUS current
      DESCRIPTION
              "OTU Performance Monitoring for 15-Minute Current Near-End Unavailable Seconds."
      ::= { adGenOtnOtuPm15MinCurrentEntry 8 }

  adGenOtnOtuPm15MinCurrentFeEB    OBJECT-TYPE
      SYNTAX Counter32
      MAX-ACCESS read-only
      STATUS current
      DESCRIPTION
              "OTU Performance Monitoring for 15-Minute Current Far-End Errored Blocks."
      ::= { adGenOtnOtuPm15MinCurrentEntry 9 }

  adGenOtnOtuPm15MinCurrentFeBBE    OBJECT-TYPE
      SYNTAX Counter32
      MAX-ACCESS read-only
      STATUS current
      DESCRIPTION
              "OTU Performance Monitoring for 15-Minute Current Far-End Background Block Errors."
      ::= { adGenOtnOtuPm15MinCurrentEntry 10 }

  adGenOtnOtuPm15MinCurrentFeBBER    OBJECT-TYPE
      SYNTAX DisplayString (SIZE (0..13))
      MAX-ACCESS read-only
      STATUS current
      DESCRIPTION
              "OTU Performance Monitoring for 15-Minute Current Far-End Background Block Error Ratio.
              The BBER decimal value between 0 and 1 calculated out to as many as 10 decimal place."
      ::= { adGenOtnOtuPm15MinCurrentEntry 11 }

  adGenOtnOtuPm15MinCurrentFeES    OBJECT-TYPE
      SYNTAX Counter32
      MAX-ACCESS read-only
      STATUS current
      DESCRIPTION
              "OTU Performance Monitoring for 15-Minute Current Far-End Errored Seconds."
      ::= { adGenOtnOtuPm15MinCurrentEntry 12 }

  adGenOtnOtuPm15MinCurrentFeSES    OBJECT-TYPE
      SYNTAX Counter32
      MAX-ACCESS read-only
      STATUS current
      DESCRIPTION
              "OTU Performance Monitoring for 15-Minute Current Far-End Severely Errored Seconds."
      ::= { adGenOtnOtuPm15MinCurrentEntry 13 }

  adGenOtnOtuPm15MinCurrentFeESR    OBJECT-TYPE
      SYNTAX Counter32
      MAX-ACCESS read-only
      STATUS current
      DESCRIPTION
              "OTU Performance Monitoring for 15-Minute Current Far-End Severely Errored Second Ratio.
              ESR is a decimal number between 0 and 0.999.  In order to not deal with a decimal number, the
              ESR value is multiplied by 1000 for this OID."
      ::= { adGenOtnOtuPm15MinCurrentEntry 14 }

  adGenOtnOtuPm15MinCurrentFeSESR    OBJECT-TYPE
      SYNTAX Counter32
      MAX-ACCESS read-only
      STATUS current
      DESCRIPTION
              "OTU Performance Monitoring for 15-Minute Current Far-End Severely Errored Second Ratio.
              SESR is a decimal number between 0 and 0.999.  In order to not deal with a decimal number, the
              SESR value is multiplied by 1000 for this OID."
      ::= { adGenOtnOtuPm15MinCurrentEntry 15 }

  adGenOtnOtuPm15MinCurrentFeUAS    OBJECT-TYPE
      SYNTAX Counter32
      MAX-ACCESS read-only
      STATUS current
      DESCRIPTION
              "OTU Performance Monitoring for 15-Minute Current Far-End Unavailable Seconds."
      ::= { adGenOtnOtuPm15MinCurrentEntry 16 }

  adGenOtnOtuPm15MinCurrentFecCorrBits    OBJECT-TYPE
      SYNTAX Counter64
      MAX-ACCESS read-only
      STATUS current
      DESCRIPTION
              "OTU Performance Monitoring for 15-Minute Current FEC (Forward Error Correction)
              Corrected Bits."
      ::= { adGenOtnOtuPm15MinCurrentEntry 17 }

  adGenOtnOtuPm15MinCurrentFecCorrOnes    OBJECT-TYPE
      SYNTAX Counter64
      MAX-ACCESS read-only
      STATUS current
      DESCRIPTION
              "OTU Performance Monitoring for 15-Minute Current FEC (Forward Error Correction)
              Corrected Ones."
      ::= { adGenOtnOtuPm15MinCurrentEntry 18 }

  adGenOtnOtuPm15MinCurrentFecCorrZeros    OBJECT-TYPE
      SYNTAX Counter64
      MAX-ACCESS read-only
      STATUS current
      DESCRIPTION
              "OTU Performance Monitoring for 15-Minute Current FEC (Forward Error Correction)
              Corrected Zeros."
      ::= { adGenOtnOtuPm15MinCurrentEntry 19 }

  adGenOtnOtuPm15MinCurrentFecUnCorrBlks    OBJECT-TYPE
      SYNTAX Counter64
      MAX-ACCESS read-only
      STATUS current
      DESCRIPTION
              "OTU Performance Monitoring for 15-Minute Current FEC (Forward Error Correction)
              Uncorrected Blocks."
      ::= { adGenOtnOtuPm15MinCurrentEntry 20 }

  adGenOtnOtuPm15MinCurrentFecCorrBer    OBJECT-TYPE
      SYNTAX DisplayString (SIZE (0..13))
      MAX-ACCESS read-only
      STATUS current
      DESCRIPTION
              "OTU Performance Monitoring for 15-Minute Current FEC (Forward Error Correction)
              Corrected Bit Error Rate.  FEC-CORR-BER is a decimal value between 0 and 1 calculated
              out to as many as 10 decimal place."
      ::= { adGenOtnOtuPm15MinCurrentEntry 21 }


  -- /////////////////////////////////////////////////////////
  adGenOtnOtuPm15MinIntervalTable OBJECT-TYPE
      SYNTAX  SEQUENCE OF AdGenOtnOtuPm15MinIntervalEntry
      MAX-ACCESS  not-accessible
      STATUS  current
      DESCRIPTION
                 "OTU Performance Montitoring 15-Minute Interval table."
      ::= { adGenOtnPm 2 }

  adGenOtnOtuPm15MinIntervalEntry OBJECT-TYPE
      SYNTAX  AdGenOtnOtuPm15MinIntervalEntry
      MAX-ACCESS  not-accessible
      STATUS  current
      DESCRIPTION
                 "Table Entry"
      INDEX   { ifIndex, adGenOtnOtuPm15MinInterval }
      ::= { adGenOtnOtuPm15MinIntervalTable 1 }

  AdGenOtnOtuPm15MinIntervalEntry ::=
      SEQUENCE {
                adGenOtnOtuPm15MinInterval
                  INTEGER,
                adGenOtnOtuPm15MinIntervalNeEB
                  Counter32,
                adGenOtnOtuPm15MinIntervalNeBBE
                  Counter32,
                adGenOtnOtuPm15MinIntervalNeBBER
                  DisplayString,
                adGenOtnOtuPm15MinIntervalNeES
                  Counter32,
                adGenOtnOtuPm15MinIntervalNeSES
                  Counter32,
                adGenOtnOtuPm15MinIntervalNeESR
                  Counter32,
                adGenOtnOtuPm15MinIntervalNeSESR
                  Counter32,
                adGenOtnOtuPm15MinIntervalNeUAS
                  Counter32,
                adGenOtnOtuPm15MinIntervalFeEB
                  Counter32,
                adGenOtnOtuPm15MinIntervalFeBBE
                  Counter32,
                adGenOtnOtuPm15MinIntervalFeBBER
                  DisplayString,
                adGenOtnOtuPm15MinIntervalFeES
                  Counter32,
                adGenOtnOtuPm15MinIntervalFeSES
                  Counter32,
                adGenOtnOtuPm15MinIntervalFeESR
                  Counter32,
                adGenOtnOtuPm15MinIntervalFeSESR
                  Counter32,
                adGenOtnOtuPm15MinIntervalFeUAS
                  Counter32,
                adGenOtnOtuPm15MinIntervalFecCorrBits
                  Counter64,
                adGenOtnOtuPm15MinIntervalFecCorrOnes
                  Counter64,
                adGenOtnOtuPm15MinIntervalFecCorrZeros
                  Counter64,
                adGenOtnOtuPm15MinIntervalFecUnCorrBlks
                  Counter64,
                adGenOtnOtuPm15MinIntervalFecCorrBer
                  DisplayString,
					 adGenOtnOtuPm15MinIntervalNeValidData
						TruthValue,
					 adGenOtnOtuPm15MinIntervalFeValidData
						TruthValue
               }

  adGenOtnOtuPm15MinInterval    OBJECT-TYPE
      SYNTAX INTEGER (1..96)
      MAX-ACCESS read-only
      STATUS current
      DESCRIPTION
              "A number between 1 and 96, which identifies the interval for which the set
               of statistics is available. The interval identified by 1 is the most recently
               completed 15 minute interval, and the interval identified by N is the
               interval immediately preceding the one identified by N-1."
      ::= { adGenOtnOtuPm15MinIntervalEntry 1 }

  adGenOtnOtuPm15MinIntervalNeEB    OBJECT-TYPE
      SYNTAX Counter32
      MAX-ACCESS read-only
      STATUS current
      DESCRIPTION
              "OTU Performance Monitoring for 15-Minute Interval Near-End Errored Blocks."
      ::= { adGenOtnOtuPm15MinIntervalEntry 2 }

  adGenOtnOtuPm15MinIntervalNeBBE    OBJECT-TYPE
      SYNTAX Counter32
      MAX-ACCESS read-only
      STATUS current
      DESCRIPTION
              "OTU Performance Monitoring for 15-Minute Interval Near-End Background Block Errors."
      ::= { adGenOtnOtuPm15MinIntervalEntry 3 }

  adGenOtnOtuPm15MinIntervalNeBBER    OBJECT-TYPE
      SYNTAX DisplayString (SIZE (0..13))
      MAX-ACCESS read-only
      STATUS current
      DESCRIPTION
              "OTU Performance Monitoring for 15-Minute Interval Near-End Background Block Error Ratio.
              BBER is a decimal value between 0 and 1 calculated out to as many as 10 decimal place."
      ::= { adGenOtnOtuPm15MinIntervalEntry 4 }

  adGenOtnOtuPm15MinIntervalNeES    OBJECT-TYPE
      SYNTAX Counter32
      MAX-ACCESS read-only
      STATUS current
      DESCRIPTION
              "OTU Performance Monitoring for 15-Minute Interval Near-End Errored Seconds."
      ::= { adGenOtnOtuPm15MinIntervalEntry 5 }

  adGenOtnOtuPm15MinIntervalNeSES    OBJECT-TYPE
      SYNTAX Counter32
      MAX-ACCESS read-only
      STATUS current
      DESCRIPTION
              "OTU Performance Monitoring for 15-Minute Interval Near-End Severely Errored Seconds."
      ::= { adGenOtnOtuPm15MinIntervalEntry 6 }

  adGenOtnOtuPm15MinIntervalNeESR    OBJECT-TYPE
      SYNTAX Counter32
      MAX-ACCESS read-only
      STATUS current
      DESCRIPTION
              "OTU Performance Monitoring for 15-Minute Interval Near-End Errored Second Ratio.
              ESR is a decimal number between 0 and 0.999.  In order to not deal with a decimal number, the
              ESR value is multiplied by 1000 for this OID."
      ::= { adGenOtnOtuPm15MinIntervalEntry 7 }

  adGenOtnOtuPm15MinIntervalNeSESR    OBJECT-TYPE
      SYNTAX Counter32
      MAX-ACCESS read-only
      STATUS current
      DESCRIPTION
              "OTU Performance Monitoring for 15-Minute Interval Near-End Severely Errored Second Ratio.
              SESR is a decimal number between 0 and 0.99.  In order to not deal with a decimal number, the
              SESR value is multiplied by 100 for this OID."
      ::= { adGenOtnOtuPm15MinIntervalEntry 8 }

  adGenOtnOtuPm15MinIntervalNeUAS    OBJECT-TYPE
      SYNTAX Counter32
      MAX-ACCESS read-only
      STATUS current
      DESCRIPTION
              "OTU Performance Monitoring for 15-Minute Interval Near-End Unavailable Seconds."
      ::= { adGenOtnOtuPm15MinIntervalEntry 9 }

  adGenOtnOtuPm15MinIntervalFeEB    OBJECT-TYPE
      SYNTAX Counter32
      MAX-ACCESS read-only
      STATUS current
      DESCRIPTION
              "OTU Performance Monitoring for 15-Minute Interval Far-End Errored Blocks."
      ::= { adGenOtnOtuPm15MinIntervalEntry 10 }

  adGenOtnOtuPm15MinIntervalFeBBE    OBJECT-TYPE
      SYNTAX Counter32
      MAX-ACCESS read-only
      STATUS current
      DESCRIPTION
              "OTU Performance Monitoring for 15-Minute Interval Far-End Background Block Errors."
      ::= { adGenOtnOtuPm15MinIntervalEntry 11 }

  adGenOtnOtuPm15MinIntervalFeBBER    OBJECT-TYPE
      SYNTAX DisplayString (SIZE (0..13))
      MAX-ACCESS read-only
      STATUS current
      DESCRIPTION
              "OTU Performance Monitoring for 15-Minute Interval Far-End Background Block Error Ratio.
              BBER is a decimal value between 0 and 1 calculated out to as many as 10 decimal place."
      ::= { adGenOtnOtuPm15MinIntervalEntry 12 }

  adGenOtnOtuPm15MinIntervalFeES    OBJECT-TYPE
      SYNTAX Counter32
      MAX-ACCESS read-only
      STATUS current
      DESCRIPTION
              "OTU Performance Monitoring for 15-Minute Interval Far-End Errored Seconds."
      ::= { adGenOtnOtuPm15MinIntervalEntry 13 }

  adGenOtnOtuPm15MinIntervalFeSES    OBJECT-TYPE
      SYNTAX Counter32
      MAX-ACCESS read-only
      STATUS current
      DESCRIPTION
              "OTU Performance Monitoring for 15-Minute Interval Far-End Severely Errored Seconds."
      ::= { adGenOtnOtuPm15MinIntervalEntry 14 }

  adGenOtnOtuPm15MinIntervalFeESR    OBJECT-TYPE
      SYNTAX Counter32
      MAX-ACCESS read-only
      STATUS current
      DESCRIPTION
              "OTU Performance Monitoring for 15-Minute Interval Far-End Errored Second Ratio.
              ESR is a decimal number between 0 and 0.999.  In order to not deal with a decimal number, the
              ESR value is multiplied by 1000 for this OID."
      ::= { adGenOtnOtuPm15MinIntervalEntry 15 }

  adGenOtnOtuPm15MinIntervalFeSESR    OBJECT-TYPE
      SYNTAX Counter32
      MAX-ACCESS read-only
      STATUS current
      DESCRIPTION
              "OTU Performance Monitoring for 15-Minute Interval Far-End Severely Errored Second Ratio.
              SESR is a decimal number between 0 and 0.99.  In order to not deal with a decimal number, the
              SESR value is multiplied by 100 for this OID."
      ::= { adGenOtnOtuPm15MinIntervalEntry 16 }

  adGenOtnOtuPm15MinIntervalFeUAS    OBJECT-TYPE
      SYNTAX Counter32
      MAX-ACCESS read-only
      STATUS current
      DESCRIPTION
              "OTU Performance Monitoring for 15-Minute Interval Far-End Unavailable Seconds."
      ::= { adGenOtnOtuPm15MinIntervalEntry 17 }

  adGenOtnOtuPm15MinIntervalFecCorrBits    OBJECT-TYPE
      SYNTAX Counter64
      MAX-ACCESS read-only
      STATUS current
      DESCRIPTION
              "OTU Performance Monitoring for 15-Minute Interval FEC (Forward Error Correction)
              Corrected Bits."
      ::= { adGenOtnOtuPm15MinIntervalEntry 18 }

  adGenOtnOtuPm15MinIntervalFecCorrOnes    OBJECT-TYPE
      SYNTAX Counter64
      MAX-ACCESS read-only
      STATUS current
      DESCRIPTION
              "OTU Performance Monitoring for 15-Minute Interval FEC (Forward Error Correction)
              Corrected Ones."
      ::= { adGenOtnOtuPm15MinIntervalEntry 19 }

  adGenOtnOtuPm15MinIntervalFecCorrZeros    OBJECT-TYPE
      SYNTAX Counter64
      MAX-ACCESS read-only
      STATUS current
      DESCRIPTION
              "OTU Performance Monitoring for 15-Minute Interval FEC (Forward Error Correction)
              Corrected Zeros."
      ::= { adGenOtnOtuPm15MinIntervalEntry 20 }

  adGenOtnOtuPm15MinIntervalFecUnCorrBlks    OBJECT-TYPE
      SYNTAX Counter64
      MAX-ACCESS read-only
      STATUS current
      DESCRIPTION
              "OTU Performance Monitoring for 15-Minute Interval FEC (Forward Error Correction)
              Uncorrected Blocks."
      ::= { adGenOtnOtuPm15MinIntervalEntry 21 }

  adGenOtnOtuPm15MinIntervalFecCorrBer    OBJECT-TYPE
      SYNTAX DisplayString (SIZE (0..13))
      MAX-ACCESS read-only
      STATUS current
      DESCRIPTION
              "OTU Performance Monitoring for 15-Minute Interval FEC (Forward Error Correction)
              Corrected Bit Error Rate.  FEC-CORR-BER is a decimal value between 0 and 1 calculated
              out to as many as 10 decimal place."
      ::= { adGenOtnOtuPm15MinIntervalEntry 22 }

  adGenOtnOtuPm15MinIntervalNeValidData OBJECT-TYPE
		SYNTAX  TruthValue
		MAX-ACCESS  read-only
		STATUS  current
		DESCRIPTION
				  "This variable indicates if the data for this
				   near end 15 minute interval is valid."
			::= { adGenOtnOtuPm15MinIntervalEntry 23 }

  adGenOtnOtuPm15MinIntervalFeValidData OBJECT-TYPE
		SYNTAX  TruthValue
		MAX-ACCESS  read-only
		STATUS  current
		DESCRIPTION
				  "This variable indicates if the data for this
				   far end 15 minute interval is valid."
			::= { adGenOtnOtuPm15MinIntervalEntry 24 }


  -- /////////////////////////////////////////////////////////
  adGenOtnOtuPm24HrCurrentTable OBJECT-TYPE
      SYNTAX  SEQUENCE OF AdGenOtnOtuPm24HrCurrentEntry
      MAX-ACCESS  not-accessible
      STATUS  current
      DESCRIPTION
                 "OTU Performance Montitoring 24-Hour Current table."
      ::= { adGenOtnPm 3 }

  adGenOtnOtuPm24HrCurrentEntry OBJECT-TYPE
      SYNTAX  AdGenOtnOtuPm24HrCurrentEntry
      MAX-ACCESS  not-accessible
      STATUS  current
      DESCRIPTION
                 "Table Entry"
      INDEX   { ifIndex }
      ::= { adGenOtnOtuPm24HrCurrentTable 1 }

  AdGenOtnOtuPm24HrCurrentEntry ::=
      SEQUENCE {
                adGenOtnOtuPm24HrCurrentNeEB
                  Counter32,
                adGenOtnOtuPm24HrCurrentNeBBE
                  Counter32,
                adGenOtnOtuPm24HrCurrentNeBBER
                  DisplayString,
                adGenOtnOtuPm24HrCurrentNeES
                  Counter32,
                adGenOtnOtuPm24HrCurrentNeSES
                  Counter32,
                adGenOtnOtuPm24HrCurrentNeESR
                  Counter32,
                adGenOtnOtuPm24HrCurrentNeSESR
                  Counter32,
                adGenOtnOtuPm24HrCurrentNeUAS
                  Counter32,
                adGenOtnOtuPm24HrCurrentFeEB
                  Counter32,
                adGenOtnOtuPm24HrCurrentFeBBE
                  Counter32,
                adGenOtnOtuPm24HrCurrentFeBBER
                  DisplayString,
                adGenOtnOtuPm24HrCurrentFeES
                  Counter32,
                adGenOtnOtuPm24HrCurrentFeSES
                  Counter32,
                adGenOtnOtuPm24HrCurrentFeESR
                  Counter32,
                adGenOtnOtuPm24HrCurrentFeSESR
                  Counter32,
                adGenOtnOtuPm24HrCurrentFeUAS
                  Counter32,
                adGenOtnOtuPm24HrCurrentFecCorrBits
                  Counter64,
                adGenOtnOtuPm24HrCurrentFecCorrOnes
                  Counter64,
                adGenOtnOtuPm24HrCurrentFecCorrZeros
                  Counter64,
                adGenOtnOtuPm24HrCurrentFecUnCorrBlks
                  Counter64,
                adGenOtnOtuPm24HrCurrentFecCorrBer
                  DisplayString
               }

  adGenOtnOtuPm24HrCurrentNeEB    OBJECT-TYPE
      SYNTAX Counter32
      MAX-ACCESS read-only
      STATUS current
      DESCRIPTION
              "OTU Performance Monitoring for 24-Hour Current Near-End Errored Blocks."
      ::= { adGenOtnOtuPm24HrCurrentEntry 1 }

  adGenOtnOtuPm24HrCurrentNeBBE    OBJECT-TYPE
      SYNTAX Counter32
      MAX-ACCESS read-only
      STATUS current
      DESCRIPTION
              "OTU Performance Monitoring for 24-Hour Current Near-End Background Block Errors."
      ::= { adGenOtnOtuPm24HrCurrentEntry 2 }

  adGenOtnOtuPm24HrCurrentNeBBER    OBJECT-TYPE
      SYNTAX DisplayString (SIZE (0..13))
      MAX-ACCESS read-only
      STATUS current
      DESCRIPTION
              "OTU Performance Monitoring for 24-Hour Current Near-End Background Block Error Ratio.
              BBER is a decimal value between 0 and 1 calculated out to as many as 10 decimal place."
      ::= { adGenOtnOtuPm24HrCurrentEntry 3 }

  adGenOtnOtuPm24HrCurrentNeES    OBJECT-TYPE
      SYNTAX Counter32
      MAX-ACCESS read-only
      STATUS current
      DESCRIPTION
              "OTU Performance Monitoring for 24-Hour Current Near-End Errored Seconds."
      ::= { adGenOtnOtuPm24HrCurrentEntry 4 }

  adGenOtnOtuPm24HrCurrentNeSES    OBJECT-TYPE
      SYNTAX Counter32
      MAX-ACCESS read-only
      STATUS current
      DESCRIPTION
              "OTU Performance Monitoring for 24-Hour Current Near-End Severely Errored Seconds."
      ::= { adGenOtnOtuPm24HrCurrentEntry 5 }

  adGenOtnOtuPm24HrCurrentNeESR    OBJECT-TYPE
      SYNTAX Counter32
      MAX-ACCESS read-only
      STATUS current
      DESCRIPTION
              "OTU Performance Monitoring Threshold for 24-Hour Current Near-End Errored Second Ratio.
              ESR is a decimal number between 0 and 0.999.  In order to not deal with a decimal number, the
              ESR value is multiplied by 1000 for this OID."
      ::= { adGenOtnOtuPm24HrCurrentEntry 6 }

  adGenOtnOtuPm24HrCurrentNeSESR    OBJECT-TYPE
      SYNTAX Counter32
      MAX-ACCESS read-only
      STATUS current
      DESCRIPTION
              "OTU Performance Monitoring for 24-Hour Current Near-End Severely Errored Second Ratio.
              SESR is a decimal number between 0 and 0.99.  In order to not deal with a decimal number, the
              SESR value is multiplied by 100 for this OID."
      ::= { adGenOtnOtuPm24HrCurrentEntry 7 }

  adGenOtnOtuPm24HrCurrentNeUAS    OBJECT-TYPE
      SYNTAX Counter32
      MAX-ACCESS read-only
      STATUS current
      DESCRIPTION
              "OTU Performance Monitoring for 24-Hour Current Near-End Unavailable Seconds."
      ::= { adGenOtnOtuPm24HrCurrentEntry 8 }

  adGenOtnOtuPm24HrCurrentFeEB    OBJECT-TYPE
      SYNTAX Counter32
      MAX-ACCESS read-only
      STATUS current
      DESCRIPTION
              "OTU Performance Monitoring for 24-Hour Current Far-End Errored Blocks."
      ::= { adGenOtnOtuPm24HrCurrentEntry 9 }

  adGenOtnOtuPm24HrCurrentFeBBE    OBJECT-TYPE
      SYNTAX Counter32
      MAX-ACCESS read-only
      STATUS current
      DESCRIPTION
              "OTU Performance Monitoring for 24-Hour Current Far-End Background Block Errors."
      ::= { adGenOtnOtuPm24HrCurrentEntry 10 }

  adGenOtnOtuPm24HrCurrentFeBBER    OBJECT-TYPE
      SYNTAX DisplayString (SIZE (0..13))
      MAX-ACCESS read-only
      STATUS current
      DESCRIPTION
              "OTU Performance Monitoring for 24-Hour Current Far-End Background Block Error Ratio.
              BBER is a decimal value between 0 and 1 calculated out to as many as 10 decimal place."
      ::= { adGenOtnOtuPm24HrCurrentEntry 11 }

  adGenOtnOtuPm24HrCurrentFeES    OBJECT-TYPE
      SYNTAX Counter32
      MAX-ACCESS read-only
      STATUS current
      DESCRIPTION
              "OTU Performance Monitoring for 24-Hour Current Far-End Errored Seconds."
      ::= { adGenOtnOtuPm24HrCurrentEntry 12 }

  adGenOtnOtuPm24HrCurrentFeSES    OBJECT-TYPE
      SYNTAX Counter32
      MAX-ACCESS read-only
      STATUS current
      DESCRIPTION
              "OTU Performance Monitoring for 24-Hour Current Far-End Severely Errored Seconds."
      ::= { adGenOtnOtuPm24HrCurrentEntry 13 }

  adGenOtnOtuPm24HrCurrentFeESR    OBJECT-TYPE
      SYNTAX Counter32
      MAX-ACCESS read-only
      STATUS current
      DESCRIPTION
              "OTU Performance Monitoring Threshold for 24-Hour Current Far-End Errored Second Ratio.
              ESR is a decimal number between 0 and 0.999.  In order to not deal with a decimal number, the
              ESR value is multiplied by 1000 for this OID."
      ::= { adGenOtnOtuPm24HrCurrentEntry 14 }

  adGenOtnOtuPm24HrCurrentFeSESR    OBJECT-TYPE
      SYNTAX Counter32
      MAX-ACCESS read-only
      STATUS current
      DESCRIPTION
              "OTU Performance Monitoring for 24-Hour Current Far-End Severely Errored Second Ratio.
              SESR is a decimal number between 0 and 0.999.  In order to not deal with a decimal number, the
              SESR value is multiplied by 1000 for this OID."
      ::= { adGenOtnOtuPm24HrCurrentEntry 15 }

  adGenOtnOtuPm24HrCurrentFeUAS    OBJECT-TYPE
      SYNTAX Counter32
      MAX-ACCESS read-only
      STATUS current
      DESCRIPTION
              "OTU Performance Monitoring for 24-Hour Current Far-End Unavailable Seconds."
      ::= { adGenOtnOtuPm24HrCurrentEntry 16 }

  adGenOtnOtuPm24HrCurrentFecCorrBits    OBJECT-TYPE
      SYNTAX Counter64
      MAX-ACCESS read-only
      STATUS current
      DESCRIPTION
              "OTU Performance Monitoring for 24-Hour Current FEC (Forward Error Correction)
              Corrected Bits."
      ::= { adGenOtnOtuPm24HrCurrentEntry 17 }

  adGenOtnOtuPm24HrCurrentFecCorrOnes    OBJECT-TYPE
      SYNTAX Counter64
      MAX-ACCESS read-only
      STATUS current
      DESCRIPTION
              "OTU Performance Monitoring for 24-Hour Current FEC (Forward Error Correction)
              Corrected Ones."
      ::= { adGenOtnOtuPm24HrCurrentEntry 18 }

  adGenOtnOtuPm24HrCurrentFecCorrZeros    OBJECT-TYPE
      SYNTAX Counter64
      MAX-ACCESS read-only
      STATUS current
      DESCRIPTION
              "OTU Performance Monitoring for 24-Hour Current FEC (Forward Error Correction)
              Corrected Zeros."
      ::= { adGenOtnOtuPm24HrCurrentEntry 19 }

  adGenOtnOtuPm24HrCurrentFecUnCorrBlks    OBJECT-TYPE
      SYNTAX Counter64
      MAX-ACCESS read-only
      STATUS current
      DESCRIPTION
              "OTU Performance Monitoring for 24-Hour Current FEC (Forward Error Correction)
              Uncorrected Blocks."
      ::= { adGenOtnOtuPm24HrCurrentEntry 20 }

  adGenOtnOtuPm24HrCurrentFecCorrBer    OBJECT-TYPE
      SYNTAX DisplayString (SIZE (0..13))
      MAX-ACCESS read-only
      STATUS current
      DESCRIPTION
              "OTU Performance Monitoring for 24-Hour Current FEC (Forward Error Correction)
              Corrected Bit Error Ratio.  FEC-CORR-BER is a decimal value between 0 and 1 calculated
              out to as many as 10 decimal place."
      ::= { adGenOtnOtuPm24HrCurrentEntry 21 }


  -- /////////////////////////////////////////////////////////
  adGenOtnOtuPm24HrIntervalTable OBJECT-TYPE
      SYNTAX  SEQUENCE OF AdGenOtnOtuPm24HrIntervalEntry
      MAX-ACCESS  not-accessible
      STATUS  current
      DESCRIPTION
                 "OTU Performance Montitoring 24-Hour Interval table."
      ::= { adGenOtnPm 4 }

  adGenOtnOtuPm24HrIntervalEntry OBJECT-TYPE
      SYNTAX  AdGenOtnOtuPm24HrIntervalEntry
      MAX-ACCESS  not-accessible
      STATUS  current
      DESCRIPTION
                 "Table Entry"
      INDEX   { ifIndex, adGenOtnOtuPm24HrInterval }
      ::= { adGenOtnOtuPm24HrIntervalTable 1 }

  AdGenOtnOtuPm24HrIntervalEntry ::=
      SEQUENCE {
                adGenOtnOtuPm24HrInterval
                  INTEGER,
                adGenOtnOtuPm24HrIntervalNeEB
                  Counter32,
                adGenOtnOtuPm24HrIntervalNeBBE
                  Counter32,
                adGenOtnOtuPm24HrIntervalNeBBER
                  DisplayString,
                adGenOtnOtuPm24HrIntervalNeES
                  Counter32,
                adGenOtnOtuPm24HrIntervalNeSES
                  Counter32,
                adGenOtnOtuPm24HrIntervalNeESR
                  Counter32,
                adGenOtnOtuPm24HrIntervalNeSESR
                  Counter32,
                adGenOtnOtuPm24HrIntervalNeUAS
                  Counter32,
                adGenOtnOtuPm24HrIntervalFeEB
                  Counter32,
                adGenOtnOtuPm24HrIntervalFeBBE
                  Counter32,
                adGenOtnOtuPm24HrIntervalFeBBER
                  DisplayString,
                adGenOtnOtuPm24HrIntervalFeES
                  Counter32,
                adGenOtnOtuPm24HrIntervalFeSES
                  Counter32,
                adGenOtnOtuPm24HrIntervalFeESR
                  Counter32,
                adGenOtnOtuPm24HrIntervalFeSESR
                  Counter32,
                adGenOtnOtuPm24HrIntervalFeUAS
                  Counter32,
                adGenOtnOtuPm24HrIntervalFecCorrBits
                  Counter64,
                adGenOtnOtuPm24HrIntervalFecCorrOnes
                  Counter64,
                adGenOtnOtuPm24HrIntervalFecCorrZeros
                  Counter64,
                adGenOtnOtuPm24HrIntervalFecUnCorrBlks
                  Counter64,
                adGenOtnOtuPm24HrIntervalFecCorrBer
                  DisplayString,
					 adGenOtnOtuPm24HrIntervalNeValidData
						TruthValue,
					 adGenOtnOtuPm24HrIntervalFeValidData
						TruthValue
               }

  adGenOtnOtuPm24HrInterval    OBJECT-TYPE
      SYNTAX INTEGER (1..7)
      MAX-ACCESS read-only
      STATUS current
      DESCRIPTION
              "A number between 1 and 7, which identifies the daily interval for which
              the set of statistics is available.  The interval identified by 1 is the
              most recently completed 24 hour interval, and the interval identified by
              N is the interval immediately preceding the one identified by N-1."
      ::= { adGenOtnOtuPm24HrIntervalEntry 1 }

  adGenOtnOtuPm24HrIntervalNeEB    OBJECT-TYPE
      SYNTAX Counter32
      MAX-ACCESS read-only
      STATUS current
      DESCRIPTION
              "OTU Performance Monitoring for 24-Hour Interval Near-End Errored Blocks."
      ::= { adGenOtnOtuPm24HrIntervalEntry 2 }

  adGenOtnOtuPm24HrIntervalNeBBE    OBJECT-TYPE
      SYNTAX Counter32
      MAX-ACCESS read-only
      STATUS current
      DESCRIPTION
              "OTU Performance Monitoring for 24-Hour Interval Near-End Background Block Errors."
      ::= { adGenOtnOtuPm24HrIntervalEntry 3 }

  adGenOtnOtuPm24HrIntervalNeBBER    OBJECT-TYPE
      SYNTAX DisplayString (SIZE (0..13))
      MAX-ACCESS read-only
      STATUS current
      DESCRIPTION
              "OTU Performance Monitoring for 24-Hour Interval Near-End Background Block Error Ratio.
              BBER is a decimal value between 0 and 1 calculated out to as many as 10 decimal place."
      ::= { adGenOtnOtuPm24HrIntervalEntry 4 }

  adGenOtnOtuPm24HrIntervalNeES    OBJECT-TYPE
      SYNTAX Counter32
      MAX-ACCESS read-only
      STATUS current
      DESCRIPTION
              "OTU Performance Monitoring for 24-Hour Interval Near-End Errored Seconds."
      ::= { adGenOtnOtuPm24HrIntervalEntry 5 }

  adGenOtnOtuPm24HrIntervalNeSES    OBJECT-TYPE
      SYNTAX Counter32
      MAX-ACCESS read-only
      STATUS current
      DESCRIPTION
              "OTU Performance Monitoring for 24-Hour Interval Near-End Severely Errored Seconds."
      ::= { adGenOtnOtuPm24HrIntervalEntry 6 }

  adGenOtnOtuPm24HrIntervalNeESR    OBJECT-TYPE
      SYNTAX Counter32
      MAX-ACCESS read-only
      STATUS current
      DESCRIPTION
              "OTU Performance Monitoring Threshold for 24-Hour Interval Near-End Errored Second Ratio.
              ESR is a decimal number between 0 and 0.999.  In order to not deal with a decimal number, the
              ESR value is multiplied by 1000 for this OID."
      ::= { adGenOtnOtuPm24HrIntervalEntry 7 }

  adGenOtnOtuPm24HrIntervalNeSESR    OBJECT-TYPE
      SYNTAX Counter32
      MAX-ACCESS read-only
      STATUS current
      DESCRIPTION
              "OTU Performance Monitoring for 24-Hour Interval Near-End Severely Errored Second Ratio.
              SESR is a decimal number between 0 and 0.99.  In order to not deal with a decimal number, the
              SESR value is multiplied by 100 for this OID."
      ::= { adGenOtnOtuPm24HrIntervalEntry 8 }

  adGenOtnOtuPm24HrIntervalNeUAS    OBJECT-TYPE
      SYNTAX Counter32
      MAX-ACCESS read-only
      STATUS current
      DESCRIPTION
              "OTU Performance Monitoring for 24-Hour Interval Near-End Unavailable Seconds."
      ::= { adGenOtnOtuPm24HrIntervalEntry 9 }

  adGenOtnOtuPm24HrIntervalFeEB    OBJECT-TYPE
      SYNTAX Counter32
      MAX-ACCESS read-only
      STATUS current
      DESCRIPTION
              "OTU Performance Monitoring for 24-Hour Interval Far-End Errored Blocks."
      ::= { adGenOtnOtuPm24HrIntervalEntry 10 }

  adGenOtnOtuPm24HrIntervalFeBBE    OBJECT-TYPE
      SYNTAX Counter32
      MAX-ACCESS read-only
      STATUS current
      DESCRIPTION
              "OTU Performance Monitoring for 24-Hour Interval Far-End Background Block Errors."
      ::= { adGenOtnOtuPm24HrIntervalEntry 11 }

  adGenOtnOtuPm24HrIntervalFeBBER    OBJECT-TYPE
      SYNTAX DisplayString
      MAX-ACCESS read-only
      STATUS current
      DESCRIPTION
              "OTU Performance Monitoring for 24-Hour Interval Far-End Background Block Error Ratio.
              BBER is a decimal value between 0 and 1 calculated out to as many as 10 decimal place."
      ::= { adGenOtnOtuPm24HrIntervalEntry 12 }

  adGenOtnOtuPm24HrIntervalFeES    OBJECT-TYPE
      SYNTAX Counter32
      MAX-ACCESS read-only
      STATUS current
      DESCRIPTION
              "OTU Performance Monitoring for 24-Hour Interval Far-End Errored Seconds."
      ::= { adGenOtnOtuPm24HrIntervalEntry 13 }

  adGenOtnOtuPm24HrIntervalFeSES    OBJECT-TYPE
      SYNTAX Counter32
      MAX-ACCESS read-only
      STATUS current
      DESCRIPTION
              "OTU Performance Monitoring for 24-Hour Interval Far-End Severely Errored Seconds."
      ::= { adGenOtnOtuPm24HrIntervalEntry 14 }

  adGenOtnOtuPm24HrIntervalFeESR    OBJECT-TYPE
      SYNTAX Counter32
      MAX-ACCESS read-only
      STATUS current
      DESCRIPTION
              "OTU Performance Monitoring Threshold for 24-Hour Interval Far-End Errored Second Ratio.
              ESR is a decimal number between 0 and 0.999.  In order to not deal with a decimal number, the
              ESR value is multiplied by 1000 for this OID."
      ::= { adGenOtnOtuPm24HrIntervalEntry 15 }

  adGenOtnOtuPm24HrIntervalFeSESR    OBJECT-TYPE
      SYNTAX Counter32
      MAX-ACCESS read-only
      STATUS current
      DESCRIPTION
              "OTU Performance Monitoring for 24-Hour Interval Far-End Severely Errored Second Ratio.
              SESR is a decimal number between 0 and 0.99.  In order to not deal with a decimal number, the
              SESR value is multiplied by 100 for this OID."
      ::= { adGenOtnOtuPm24HrIntervalEntry 16 }

  adGenOtnOtuPm24HrIntervalFeUAS    OBJECT-TYPE
      SYNTAX Counter32
      MAX-ACCESS read-only
      STATUS current
      DESCRIPTION
              "OTU Performance Monitoring for 24-Hour Interval Far-End Unavailable Seconds."
      ::= { adGenOtnOtuPm24HrIntervalEntry 17 }

  adGenOtnOtuPm24HrIntervalFecCorrBits    OBJECT-TYPE
      SYNTAX Counter64
      MAX-ACCESS read-only
      STATUS current
      DESCRIPTION
              "OTU Performance Monitoring for 24-Hour Interval FEC (Forward Error Correction)
              Corrected Bits."
      ::= { adGenOtnOtuPm24HrIntervalEntry 18 }

  adGenOtnOtuPm24HrIntervalFecCorrOnes    OBJECT-TYPE
      SYNTAX Counter64
      MAX-ACCESS read-only
      STATUS current
      DESCRIPTION
              "OTU Performance Monitoring for 24-Hour Interval FEC (Forward Error Correction)
              Corrected Ones."
      ::= { adGenOtnOtuPm24HrIntervalEntry 19 }

  adGenOtnOtuPm24HrIntervalFecCorrZeros    OBJECT-TYPE
      SYNTAX Counter64
      MAX-ACCESS read-only
      STATUS current
      DESCRIPTION
              "OTU Performance Monitoring for 24-Hour Interval FEC (Forward Error Correction)
              Corrected Zeros."
      ::= { adGenOtnOtuPm24HrIntervalEntry 20 }

  adGenOtnOtuPm24HrIntervalFecUnCorrBlks    OBJECT-TYPE
      SYNTAX Counter64
      MAX-ACCESS read-only
      STATUS current
      DESCRIPTION
              "OTU Performance Monitoring for 24-Hour Interval FEC (Forward Error Correction)
              Uncorrected Blocks."
      ::= { adGenOtnOtuPm24HrIntervalEntry 21}

  adGenOtnOtuPm24HrIntervalFecCorrBer    OBJECT-TYPE
      SYNTAX DisplayString
      MAX-ACCESS read-only
      STATUS current
      DESCRIPTION
              "OTU Performance Monitoring for 24-Hour Interval FEC (Forward Error Correction)
              Corrected Bit Error Ratio.  FEC-CORR-BER is a decimal value between 0 and 1 calculated
              out to as many as 10 decimal place."
      ::= { adGenOtnOtuPm24HrIntervalEntry 22 }

  adGenOtnOtuPm24HrIntervalNeValidData OBJECT-TYPE
		SYNTAX  TruthValue
		MAX-ACCESS  read-only
		STATUS  current
		DESCRIPTION
				 "This variable indicates if the data for this
				  near end 24 hour interval is valid."
		::= { adGenOtnOtuPm24HrIntervalEntry 23 }

  adGenOtnOtuPm24HrIntervalFeValidData OBJECT-TYPE
		SYNTAX  TruthValue
		MAX-ACCESS  read-only
		STATUS  current
		DESCRIPTION
				 "This variable indicates if the data for this
				  far end 24 hour interval is valid."
		::= { adGenOtnOtuPm24HrIntervalEntry 24 }


  -- /////////////////////////////////////////////////////////
  adGenOtnOduPm15MinCurrentTable OBJECT-TYPE
      SYNTAX  SEQUENCE OF AdGenOtnOduPm15MinCurrentEntry
      MAX-ACCESS  not-accessible
      STATUS  current
      DESCRIPTION
                 "ODU Performance Montitoring 15-Minute Current table."
      ::= { adGenOtnPm 5 }

  adGenOtnOduPm15MinCurrentEntry OBJECT-TYPE
      SYNTAX  AdGenOtnOduPm15MinCurrentEntry
      MAX-ACCESS  not-accessible
      STATUS  current
      DESCRIPTION
                 "Table Entry"
      INDEX   { adGenSlotInfoIndex, adGenOtnOduIndex }
      ::= { adGenOtnOduPm15MinCurrentTable 1 }

  AdGenOtnOduPm15MinCurrentEntry ::=
      SEQUENCE {
                adGenOtnOduPm15MinCurrentNeEB
                  Counter32,
                adGenOtnOduPm15MinCurrentNeBBE
                  Counter32,
                adGenOtnOduPm15MinCurrentNeBBER
                  DisplayString,
                adGenOtnOduPm15MinCurrentNeES
                  Counter32,
                adGenOtnOduPm15MinCurrentNeSES
                  Counter32,
                adGenOtnOduPm15MinCurrentNeESR
                  Counter32,
                adGenOtnOduPm15MinCurrentNeSESR
                  Counter32,
                adGenOtnOduPm15MinCurrentNeUAS
                  Counter32,
                adGenOtnOduPm15MinCurrentFeEB
                  Counter32,
                adGenOtnOduPm15MinCurrentFeBBE
                  Counter32,
                adGenOtnOduPm15MinCurrentFeBBER
                  DisplayString,
                adGenOtnOduPm15MinCurrentFeES
                  Counter32,
                adGenOtnOduPm15MinCurrentFeSES
                  Counter32,
                adGenOtnOduPm15MinCurrentFeESR
                  Counter32,
                adGenOtnOduPm15MinCurrentFeSESR
                  Counter32,
                adGenOtnOduPm15MinCurrentFeUAS
                  Counter32
               }

  adGenOtnOduPm15MinCurrentNeEB    OBJECT-TYPE
      SYNTAX Counter32
      MAX-ACCESS read-only
      STATUS current
      DESCRIPTION
              "ODU Performance Monitoring for 15-Minute Current Near-End Errored Blocks."
      ::= { adGenOtnOduPm15MinCurrentEntry 1 }

  adGenOtnOduPm15MinCurrentNeBBE    OBJECT-TYPE
      SYNTAX Counter32
      MAX-ACCESS read-only
      STATUS current
      DESCRIPTION
              "ODU Performance Monitoring for 15-Minute Current Near-End Background Block Errors."
      ::= { adGenOtnOduPm15MinCurrentEntry 2 }

  adGenOtnOduPm15MinCurrentNeBBER    OBJECT-TYPE
      SYNTAX DisplayString (SIZE (0..13))
      MAX-ACCESS read-only
      STATUS current
      DESCRIPTION
              "ODU Performance Monitoring for 15-Minute Current Near-End Background Block Error Ratio.
              BBER is a decimal value between 0 and 1 calculated out to as many as 10 decimal place."
      ::= { adGenOtnOduPm15MinCurrentEntry 3 }

  adGenOtnOduPm15MinCurrentNeES    OBJECT-TYPE
      SYNTAX Counter32
      MAX-ACCESS read-only
      STATUS current
      DESCRIPTION
              "ODU Performance Monitoring for 15-Minute Current Near-End Errored Seconds."
      ::= { adGenOtnOduPm15MinCurrentEntry 4 }

  adGenOtnOduPm15MinCurrentNeSES    OBJECT-TYPE
      SYNTAX Counter32
      MAX-ACCESS read-only
      STATUS current
      DESCRIPTION
              "ODU Performance Monitoring for 15-Minute Current Near-End Severely Errored Seconds."
      ::= { adGenOtnOduPm15MinCurrentEntry 5 }

  adGenOtnOduPm15MinCurrentNeESR    OBJECT-TYPE
      SYNTAX Counter32
      MAX-ACCESS read-only
      STATUS current
      DESCRIPTION
              "ODU Performance Monitoring for 15-Minute Current Near-End Errored Second Ratio.
              ESR is a decimal number between 0 and 0.999.  In order to not deal with a decimal number, the
              ESR value is multiplied by 1000 for this OID."
      ::= { adGenOtnOduPm15MinCurrentEntry 6 }

  adGenOtnOduPm15MinCurrentNeSESR    OBJECT-TYPE
      SYNTAX Counter32
      MAX-ACCESS read-only
      STATUS current
      DESCRIPTION
              "ODU Performance Monitoring for 15-Minute Current Near-End Severely Errored Second Ratio.
              SESR is a decimal number between 0 and 0.99.  In order to not deal with a decimal number, the
              SESR value is multiplied by 100 for this OID."
      ::= { adGenOtnOduPm15MinCurrentEntry 7 }

  adGenOtnOduPm15MinCurrentNeUAS    OBJECT-TYPE
      SYNTAX Counter32
      MAX-ACCESS read-only
      STATUS current
      DESCRIPTION
              "ODU Performance Monitoring for 15-Minute Current Near-End Unavailable Seconds."
      ::= { adGenOtnOduPm15MinCurrentEntry 8 }

  adGenOtnOduPm15MinCurrentFeEB    OBJECT-TYPE
      SYNTAX Counter32
      MAX-ACCESS read-only
      STATUS current
      DESCRIPTION
              "ODU Performance Monitoring for 15-Minute Current Far-End Errored Blocks."
      ::= { adGenOtnOduPm15MinCurrentEntry 9 }

  adGenOtnOduPm15MinCurrentFeBBE    OBJECT-TYPE
      SYNTAX Counter32
      MAX-ACCESS read-only
      STATUS current
      DESCRIPTION
              "ODU Performance Monitoring for 15-Minute Current Far-End Background Block Errors."
      ::= { adGenOtnOduPm15MinCurrentEntry 10 }

  adGenOtnOduPm15MinCurrentFeBBER    OBJECT-TYPE
      SYNTAX DisplayString (SIZE (0..13))
      MAX-ACCESS read-only
      STATUS current
      DESCRIPTION
              "ODU Performance Monitoring for 15-Minute Current Far-End Background Block Error Ratio.
              BBER is a decimal value between 0 and 1 calculated out to as many as 10 decimal place."
      ::= { adGenOtnOduPm15MinCurrentEntry 11 }

  adGenOtnOduPm15MinCurrentFeES    OBJECT-TYPE
      SYNTAX Counter32
      MAX-ACCESS read-only
      STATUS current
      DESCRIPTION
              "ODU Performance Monitoring for 15-Minute Current Far-End Errored Seconds."
      ::= { adGenOtnOduPm15MinCurrentEntry 12 }

  adGenOtnOduPm15MinCurrentFeSES    OBJECT-TYPE
      SYNTAX Counter32
      MAX-ACCESS read-only
      STATUS current
      DESCRIPTION
              "ODU Performance Monitoring for 15-Minute Current Far-End Severely Errored Seconds."
      ::= { adGenOtnOduPm15MinCurrentEntry 13 }

  adGenOtnOduPm15MinCurrentFeESR    OBJECT-TYPE
      SYNTAX Counter32
      MAX-ACCESS read-only
      STATUS current
      DESCRIPTION
              "ODU Performance Monitoring for 15-Minute Current Far-End Errored Second Ratio.
              ESR is a decimal number between 0 and 0.999.  In order to not deal with a decimal number, the
              ESR value is multiplied by 1000 for this OID."
      ::= { adGenOtnOduPm15MinCurrentEntry 14 }

  adGenOtnOduPm15MinCurrentFeSESR    OBJECT-TYPE
      SYNTAX Counter32
      MAX-ACCESS read-only
      STATUS current
      DESCRIPTION
              "ODU Performance Monitoring for 15-Minute Current Far-End Severely Errored Second Ratio.
              SESR is a decimal number between 0 and 0.99.  In order to not deal with a decimal number, the
              SESR value is multiplied by 100 for this OID."
      ::= { adGenOtnOduPm15MinCurrentEntry 15 }

  adGenOtnOduPm15MinCurrentFeUAS    OBJECT-TYPE
      SYNTAX Counter32
      MAX-ACCESS read-only
      STATUS current
      DESCRIPTION
              "ODU Performance Monitoring for 15-Minute Current Far-End Unavailable Seconds."
      ::= { adGenOtnOduPm15MinCurrentEntry 16 }


  -- /////////////////////////////////////////////////////////
  adGenOtnOduPm15MinIntervalTable OBJECT-TYPE
      SYNTAX  SEQUENCE OF AdGenOtnOduPm15MinIntervalEntry
      MAX-ACCESS  not-accessible
      STATUS  current
      DESCRIPTION
                 "ODU Performance Montitoring 15-Minute Interval table."
      ::= { adGenOtnPm 6 }

  adGenOtnOduPm15MinIntervalEntry OBJECT-TYPE
      SYNTAX  AdGenOtnOduPm15MinIntervalEntry
      MAX-ACCESS  not-accessible
      STATUS  current
      DESCRIPTION
                 "Table Entry"
      INDEX   { adGenSlotInfoIndex, adGenOtnOduIndex, adGenOtnOduPm15MinInterval }
      ::= { adGenOtnOduPm15MinIntervalTable 1 }

  AdGenOtnOduPm15MinIntervalEntry ::=
      SEQUENCE {
                adGenOtnOduPm15MinInterval
                  INTEGER,
                adGenOtnOduPm15MinIntervalNeEB
                  Counter32,
                adGenOtnOduPm15MinIntervalNeBBE
                  Counter32,
                adGenOtnOduPm15MinIntervalNeBBER
                  DisplayString,
                adGenOtnOduPm15MinIntervalNeES
                  Counter32,
                adGenOtnOduPm15MinIntervalNeSES
                  Counter32,
                adGenOtnOduPm15MinIntervalNeESR
                  Counter32,
                adGenOtnOduPm15MinIntervalNeSESR
                  Counter32,
                adGenOtnOduPm15MinIntervalNeUAS
                  Counter32,
                adGenOtnOduPm15MinIntervalFeEB
                  Counter32,
                adGenOtnOduPm15MinIntervalFeBBE
                  Counter32,
                adGenOtnOduPm15MinIntervalFeBBER
                  DisplayString,
                adGenOtnOduPm15MinIntervalFeES
                  Counter32,
                adGenOtnOduPm15MinIntervalFeSES
                  Counter32,
                adGenOtnOduPm15MinIntervalFeESR
                  Counter32,
                adGenOtnOduPm15MinIntervalFeSESR
                  Counter32,
                adGenOtnOduPm15MinIntervalFeUAS
                  Counter32,
					 adGenOtnOduPm15MinIntervalNeValidData
						TruthValue,
					 adGenOtnOduPm15MinIntervalFeValidData
						TruthValue
               }

  adGenOtnOduPm15MinInterval    OBJECT-TYPE
      SYNTAX INTEGER (1..96)
      MAX-ACCESS read-only
      STATUS current
      DESCRIPTION
              "A number between 1 and 96, which identifies the interval for which the set
               of statistics is available. The interval identified by 1 is the most recently
               completed 15 minute interval, and the interval identified by N is the
               interval immediately preceding the one identified by N-1."
      ::= { adGenOtnOduPm15MinIntervalEntry 1 }

  adGenOtnOduPm15MinIntervalNeEB    OBJECT-TYPE
      SYNTAX Counter32
      MAX-ACCESS read-only
      STATUS current
      DESCRIPTION
              "ODU Performance Monitoring for 15-Minute Interval Near-End Errored Blocks."
      ::= { adGenOtnOduPm15MinIntervalEntry 2 }

  adGenOtnOduPm15MinIntervalNeBBE    OBJECT-TYPE
      SYNTAX Counter32
      MAX-ACCESS read-only
      STATUS current
      DESCRIPTION
              "ODU Performance Monitoring for 15-Minute Interval Near-End Background Block Errors."
      ::= { adGenOtnOduPm15MinIntervalEntry 3 }

  adGenOtnOduPm15MinIntervalNeBBER    OBJECT-TYPE
      SYNTAX DisplayString
      MAX-ACCESS read-only
      STATUS current
      DESCRIPTION
              "ODU Performance Monitoring for 15-Minute Interval Near-End Background Block Error Ratio.
              BBER is a decimal value between 0 and 1 calculated out to as many as 10 decimal place."
      ::= { adGenOtnOduPm15MinIntervalEntry 4 }

  adGenOtnOduPm15MinIntervalNeES    OBJECT-TYPE
      SYNTAX Counter32
      MAX-ACCESS read-only
      STATUS current
      DESCRIPTION
              "ODU Performance Monitoring for 15-Minute Interval Near-End Errored Seconds."
      ::= { adGenOtnOduPm15MinIntervalEntry 5 }

  adGenOtnOduPm15MinIntervalNeSES    OBJECT-TYPE
      SYNTAX Counter32
      MAX-ACCESS read-only
      STATUS current
      DESCRIPTION
              "ODU Performance Monitoring for 15-Minute Interval Near-End Severely Errored Seconds."
      ::= { adGenOtnOduPm15MinIntervalEntry 6 }

  adGenOtnOduPm15MinIntervalNeESR    OBJECT-TYPE
      SYNTAX Counter32
      MAX-ACCESS read-only
      STATUS current
      DESCRIPTION
              "ODU Performance Monitoring for 15-Minute Interval Near-End Errored Second Ratio.
              ESR is a decimal number between 0 and 0.999.  In order to not deal with a decimal number, the
              ESR value is multiplied by 1000 for this OID."
      ::= { adGenOtnOduPm15MinIntervalEntry 7 }

  adGenOtnOduPm15MinIntervalNeSESR    OBJECT-TYPE
      SYNTAX Counter32
      MAX-ACCESS read-only
      STATUS current
      DESCRIPTION
              "ODU Performance Monitoring for 15-Minute Interval Near-End Severely Errored Second Ratio.
              SESR is a decimal number between 0 and 0.99.  In order to not deal with a decimal number, the
              SESR value is multiplied by 100 for this OID."
      ::= { adGenOtnOduPm15MinIntervalEntry 8 }

  adGenOtnOduPm15MinIntervalNeUAS    OBJECT-TYPE
      SYNTAX Counter32
      MAX-ACCESS read-only
      STATUS current
      DESCRIPTION
              "ODU Performance Monitoring for 15-Minute Interval Near-End Unavailable Seconds."
      ::= { adGenOtnOduPm15MinIntervalEntry 9 }

  adGenOtnOduPm15MinIntervalFeEB    OBJECT-TYPE
      SYNTAX Counter32
      MAX-ACCESS read-only
      STATUS current
      DESCRIPTION
              "ODU Performance Monitoring for 15-Minute Interval Far-End Errored Blocks."
      ::= { adGenOtnOduPm15MinIntervalEntry 10 }

  adGenOtnOduPm15MinIntervalFeBBE    OBJECT-TYPE
      SYNTAX Counter32
      MAX-ACCESS read-only
      STATUS current
      DESCRIPTION
              "ODU Performance Monitoring for 15-Minute Interval Far-End Background Block Errors."
      ::= { adGenOtnOduPm15MinIntervalEntry 11 }

  adGenOtnOduPm15MinIntervalFeBBER    OBJECT-TYPE
      SYNTAX DisplayString (SIZE (0..13))
      MAX-ACCESS read-only
      STATUS current
      DESCRIPTION
              "ODU Performance Monitoring for 15-Minute Interval Far-End Background Block Error Ratio.
              BBER is a decimal value between 0 and 1 calculated out to as many as 10 decimal place."
      ::= { adGenOtnOduPm15MinIntervalEntry 12 }

  adGenOtnOduPm15MinIntervalFeES    OBJECT-TYPE
      SYNTAX Counter32
      MAX-ACCESS read-only
      STATUS current
      DESCRIPTION
              "ODU Performance Monitoring for 15-Minute Interval Far-End Errored Seconds."
      ::= { adGenOtnOduPm15MinIntervalEntry 13 }

  adGenOtnOduPm15MinIntervalFeSES    OBJECT-TYPE
      SYNTAX Counter32
      MAX-ACCESS read-only
      STATUS current
      DESCRIPTION
              "ODU Performance Monitoring for 15-Minute Interval Far-End Severely Errored Seconds."
      ::= { adGenOtnOduPm15MinIntervalEntry 14 }

  adGenOtnOduPm15MinIntervalFeESR    OBJECT-TYPE
      SYNTAX Counter32
      MAX-ACCESS read-only
      STATUS current
      DESCRIPTION
              "ODU Performance Monitoring for 15-Minute Interval Far-End Errored Second Ratio.
              ESR is a decimal number between 0 and 0.999.  In order to not deal with a decimal number, the
              ESR value is multiplied by 1000 for this OID."
      ::= { adGenOtnOduPm15MinIntervalEntry 15 }

  adGenOtnOduPm15MinIntervalFeSESR    OBJECT-TYPE
      SYNTAX Counter32
      MAX-ACCESS read-only
      STATUS current
      DESCRIPTION
              "ODU Performance Monitoring for 15-Minute Interval Far-End Severely Errored Second Ratio.
              SESR is a decimal number between 0 and 0.99.  In order to not deal with a decimal number, the
              SESR value is multiplied by 100 for this OID."
      ::= { adGenOtnOduPm15MinIntervalEntry 16 }

  adGenOtnOduPm15MinIntervalFeUAS    OBJECT-TYPE
      SYNTAX Counter32
      MAX-ACCESS read-only
      STATUS current
      DESCRIPTION
              "ODU Performance Monitoring for 15-Minute Interval Far-End Unavailable Seconds."
      ::= { adGenOtnOduPm15MinIntervalEntry 17 }

  adGenOtnOduPm15MinIntervalNeValidData OBJECT-TYPE
			SYNTAX  TruthValue
			MAX-ACCESS  read-only
			STATUS  current
			DESCRIPTION
				"This variable indicates if the data for this
				 near end 15 minute interval is valid."
			::= { adGenOtnOduPm15MinIntervalEntry 18 }

  adGenOtnOduPm15MinIntervalFeValidData OBJECT-TYPE
			SYNTAX  TruthValue
			MAX-ACCESS  read-only
			STATUS  current
			DESCRIPTION
				"This variable indicates if the data for this
				 far end 15 minute interval is valid."
			::= { adGenOtnOduPm15MinIntervalEntry 19 }


  -- /////////////////////////////////////////////////////////
  adGenOtnOduPm24HrCurrentTable OBJECT-TYPE
      SYNTAX  SEQUENCE OF AdGenOtnOduPm24HrCurrentEntry
      MAX-ACCESS  not-accessible
      STATUS  current
      DESCRIPTION
                 "ODU Performance Montitoring 24-Hour Current table."
      ::= { adGenOtnPm 7 }

  adGenOtnOduPm24HrCurrentEntry OBJECT-TYPE
      SYNTAX  AdGenOtnOduPm24HrCurrentEntry
      MAX-ACCESS  not-accessible
      STATUS  current
      DESCRIPTION
                 "Table Entry"
      INDEX   { adGenSlotInfoIndex, adGenOtnOduIndex }
      ::= { adGenOtnOduPm24HrCurrentTable 1 }

  AdGenOtnOduPm24HrCurrentEntry ::=
      SEQUENCE {
                adGenOtnOduPm24HrCurrentNeEB
                  Counter32,
                adGenOtnOduPm24HrCurrentNeBBE
                  Counter32,
                adGenOtnOduPm24HrCurrentNeBBER
                  DisplayString,
                adGenOtnOduPm24HrCurrentNeES
                  Counter32,
                adGenOtnOduPm24HrCurrentNeSES
                  Counter32,
                adGenOtnOduPm24HrCurrentNeESR
                  Counter32,
                adGenOtnOduPm24HrCurrentNeSESR
                  Counter32,
                adGenOtnOduPm24HrCurrentNeUAS
                  Counter32,
                adGenOtnOduPm24HrCurrentFeEB
                  Counter32,
                adGenOtnOduPm24HrCurrentFeBBE
                  Counter32,
                adGenOtnOduPm24HrCurrentFeBBER
                  DisplayString,
                adGenOtnOduPm24HrCurrentFeES
                  Counter32,
                adGenOtnOduPm24HrCurrentFeSES
                  Counter32,
                adGenOtnOduPm24HrCurrentFeESR
                  Counter32,
                adGenOtnOduPm24HrCurrentFeSESR
                  Counter32,
                adGenOtnOduPm24HrCurrentFeUAS
                  Counter32
               }

  adGenOtnOduPm24HrCurrentNeEB    OBJECT-TYPE
      SYNTAX Counter32
      MAX-ACCESS read-only
      STATUS current
      DESCRIPTION
              "ODU Performance Monitoring for 24-Hour Current Near-End Errored Blocks."
      ::= { adGenOtnOduPm24HrCurrentEntry 1 }

  adGenOtnOduPm24HrCurrentNeBBE    OBJECT-TYPE
      SYNTAX Counter32
      MAX-ACCESS read-only
      STATUS current
      DESCRIPTION
              "ODU Performance Monitoring for 24-Hour Current Near-End Background Block Errors."
      ::= { adGenOtnOduPm24HrCurrentEntry 2 }

  adGenOtnOduPm24HrCurrentNeBBER    OBJECT-TYPE
      SYNTAX DisplayString (SIZE (0..13))
      MAX-ACCESS read-only
      STATUS current
      DESCRIPTION
              "ODU Performance Monitoring for 24-Hour Current Near-End Background Block Error Ratio.
              BBER is a decimal value between 0 and 1 calculated out to as many as 10 decimal place."
      ::= { adGenOtnOduPm24HrCurrentEntry 3 }

  adGenOtnOduPm24HrCurrentNeES    OBJECT-TYPE
      SYNTAX Counter32
      MAX-ACCESS read-only
      STATUS current
      DESCRIPTION
              "ODU Performance Monitoring for 24-Hour Current Near-End Errored Seconds."
      ::= { adGenOtnOduPm24HrCurrentEntry 4 }

  adGenOtnOduPm24HrCurrentNeSES    OBJECT-TYPE
      SYNTAX Counter32
      MAX-ACCESS read-only
      STATUS current
      DESCRIPTION
              "ODU Performance Monitoring for 24-Hour Current Near-End Severely Errored Seconds."
      ::= { adGenOtnOduPm24HrCurrentEntry 5 }

  adGenOtnOduPm24HrCurrentNeESR    OBJECT-TYPE
      SYNTAX Counter32
      MAX-ACCESS read-only
      STATUS current
      DESCRIPTION
              "ODU Performance Monitoring for 24-Hour Current Near-End Errored Second Ratio.
              ESR is a decimal number between 0 and 0.999.  In order to not deal with a decimal number, the
              ESR value is multiplied by 1000 for this OID."
      ::= { adGenOtnOduPm24HrCurrentEntry 6 }

  adGenOtnOduPm24HrCurrentNeSESR    OBJECT-TYPE
      SYNTAX Counter32
      MAX-ACCESS read-only
      STATUS current
      DESCRIPTION
              "ODU Performance Monitoring for 24-Hour Current Near-End Severely Errored Second Ratio.
              SESR is a decimal number between 0 and 0.99.  In order to not deal with a decimal number, the
              SESR value is multiplied by 100 for this OID."
      ::= { adGenOtnOduPm24HrCurrentEntry 7 }

  adGenOtnOduPm24HrCurrentNeUAS    OBJECT-TYPE
      SYNTAX Counter32
      MAX-ACCESS read-only
      STATUS current
      DESCRIPTION
              "ODU Performance Monitoring for 24-Hour Current Near-End Unavailable Seconds."
      ::= { adGenOtnOduPm24HrCurrentEntry 8 }

  adGenOtnOduPm24HrCurrentFeEB    OBJECT-TYPE
      SYNTAX Counter32
      MAX-ACCESS read-only
      STATUS current
      DESCRIPTION
              "ODU Performance Monitoring for 24-Hour Current Far-End Errored Blocks."
      ::= { adGenOtnOduPm24HrCurrentEntry 9 }

  adGenOtnOduPm24HrCurrentFeBBE    OBJECT-TYPE
      SYNTAX Counter32
      MAX-ACCESS read-only
      STATUS current
      DESCRIPTION
              "ODU Performance Monitoring for 24-Hour Current Far-End Background Block Errors."
      ::= { adGenOtnOduPm24HrCurrentEntry 10 }

  adGenOtnOduPm24HrCurrentFeBBER    OBJECT-TYPE
      SYNTAX DisplayString (SIZE (0..13))
      MAX-ACCESS read-only
      STATUS current
      DESCRIPTION
              "ODU Performance Monitoring for 24-Hour Current Far-End Background Block Error Ratio.
              BBER is a decimal value between 0 and 1 calculated out to as many as 10 decimal place."
      ::= { adGenOtnOduPm24HrCurrentEntry 11 }

  adGenOtnOduPm24HrCurrentFeES    OBJECT-TYPE
      SYNTAX Counter32
      MAX-ACCESS read-only
      STATUS current
      DESCRIPTION
              "ODU Performance Monitoring for 24-Hour Current Far-End Errored Seconds."
      ::= { adGenOtnOduPm24HrCurrentEntry 12 }

  adGenOtnOduPm24HrCurrentFeSES    OBJECT-TYPE
      SYNTAX Counter32
      MAX-ACCESS read-only
      STATUS current
      DESCRIPTION
              "ODU Performance Monitoring for 24-Hour Current Far-End Severely Errored Seconds."
      ::= { adGenOtnOduPm24HrCurrentEntry 13 }

  adGenOtnOduPm24HrCurrentFeESR    OBJECT-TYPE
      SYNTAX Counter32
      MAX-ACCESS read-only
      STATUS current
      DESCRIPTION
              "ODU Performance Monitoring for 24-Hour Current Far-End Errored Second Ratio.
              ESR is a decimal number between 0 and 0.999.  In order to not deal with a decimal number, the
              ESR value is multiplied by 1000 for this OID."
      ::= { adGenOtnOduPm24HrCurrentEntry 14 }

  adGenOtnOduPm24HrCurrentFeSESR    OBJECT-TYPE
      SYNTAX Counter32
      MAX-ACCESS read-only
      STATUS current
      DESCRIPTION
              "ODU Performance Monitoring for 24-Hour Current Far-End Severely Errored Second Ratio.
              SESR is a decimal number between 0 and 0.99.  In order to not deal with a decimal number, the
              SESR value is multiplied by 100 for this OID."
      ::= { adGenOtnOduPm24HrCurrentEntry 15 }

  adGenOtnOduPm24HrCurrentFeUAS    OBJECT-TYPE
      SYNTAX Counter32
      MAX-ACCESS read-only
      STATUS current
      DESCRIPTION
              "ODU Performance Monitoring for 24-Hour Current Far-End Unavailable Seconds."
      ::= { adGenOtnOduPm24HrCurrentEntry 16 }


  -- /////////////////////////////////////////////////////////
  adGenOtnOduPm24HrIntervalTable OBJECT-TYPE
      SYNTAX  SEQUENCE OF AdGenOtnOduPm24HrIntervalEntry
      MAX-ACCESS  not-accessible
      STATUS  current
      DESCRIPTION
                 "ODU Performance Montitoring 24-Hour Interval table."
      ::= { adGenOtnPm 8 }

  adGenOtnOduPm24HrIntervalEntry OBJECT-TYPE
      SYNTAX  AdGenOtnOduPm24HrIntervalEntry
      MAX-ACCESS  not-accessible
      STATUS  current
      DESCRIPTION
                 "Table Entry"
      INDEX   { adGenSlotInfoIndex, adGenOtnOduIndex, adGenOtnOduPm24HrInterval }
      ::= { adGenOtnOduPm24HrIntervalTable 1 }

  AdGenOtnOduPm24HrIntervalEntry ::=
      SEQUENCE {
                adGenOtnOduPm24HrInterval
                  INTEGER,
                adGenOtnOduPm24HrIntervalNeEB
                  Counter32,
                adGenOtnOduPm24HrIntervalNeBBE
                  Counter32,
                adGenOtnOduPm24HrIntervalNeBBER
                  DisplayString,
                adGenOtnOduPm24HrIntervalNeES
                  Counter32,
                adGenOtnOduPm24HrIntervalNeSES
                  Counter32,
                adGenOtnOduPm24HrIntervalNeESR
                  Counter32,
                adGenOtnOduPm24HrIntervalNeSESR
                  Counter32,
                adGenOtnOduPm24HrIntervalNeUAS
                  Counter32,
                adGenOtnOduPm24HrIntervalFeEB
                  Counter32,
                adGenOtnOduPm24HrIntervalFeBBE
                  Counter32,
                adGenOtnOduPm24HrIntervalFeBBER
                  DisplayString,
                adGenOtnOduPm24HrIntervalFeES
                  Counter32,
                adGenOtnOduPm24HrIntervalFeSES
                  Counter32,
                adGenOtnOduPm24HrIntervalFeESR
                  Counter32,
                adGenOtnOduPm24HrIntervalFeSESR
                  Counter32,
                adGenOtnOduPm24HrIntervalFeUAS
                  Counter32,
					 adGenOtnOduPm24HrIntervalNeValidData
						TruthValue,
					 adGenOtnOduPm24HrIntervalFeValidData
						TruthValue
               }

  adGenOtnOduPm24HrInterval    OBJECT-TYPE
      SYNTAX INTEGER (1..7)
      MAX-ACCESS read-only
      STATUS current
      DESCRIPTION
              "A number between 1 and 7, which identifies the daily interval for which
              the set of statistics is available.  The interval identified by 1 is the
              most recently completed 24 hour interval, and the interval identified by
              N is the interval immediately preceding the one identified by N-1."
      ::= { adGenOtnOduPm24HrIntervalEntry 1 }

  adGenOtnOduPm24HrIntervalNeEB    OBJECT-TYPE
      SYNTAX Counter32
      MAX-ACCESS read-only
      STATUS current
      DESCRIPTION
              "ODU Performance Monitoring for 24-Hour Interval Near-End Errored Blocks."
      ::= { adGenOtnOduPm24HrIntervalEntry 2 }

  adGenOtnOduPm24HrIntervalNeBBE    OBJECT-TYPE
      SYNTAX Counter32
      MAX-ACCESS read-only
      STATUS current
      DESCRIPTION
              "ODU Performance Monitoring for 24-Hour Interval Near-End Background Block Errors."
      ::= { adGenOtnOduPm24HrIntervalEntry 3 }

  adGenOtnOduPm24HrIntervalNeBBER    OBJECT-TYPE
      SYNTAX DisplayString (SIZE (0..13))
      MAX-ACCESS read-only
      STATUS current
      DESCRIPTION
              "ODU Performance Monitoring for 24-Hour Interval Near-End Background Block Error Ratio.
              BBER is a decimal value between 0 and 1 calculated out to as many as 10 decimal place."
      ::= { adGenOtnOduPm24HrIntervalEntry 4 }

  adGenOtnOduPm24HrIntervalNeES    OBJECT-TYPE
      SYNTAX Counter32
      MAX-ACCESS read-only
      STATUS current
      DESCRIPTION
              "ODU Performance Monitoring for 24-Hour Interval Near-End Errored Seconds."
      ::= { adGenOtnOduPm24HrIntervalEntry 5 }

  adGenOtnOduPm24HrIntervalNeSES    OBJECT-TYPE
      SYNTAX Counter32
      MAX-ACCESS read-only
      STATUS current
      DESCRIPTION
              "ODU Performance Monitoring for 24-Hour Interval Near-End Severely Errored Seconds."
      ::= { adGenOtnOduPm24HrIntervalEntry 6 }

  adGenOtnOduPm24HrIntervalNeESR    OBJECT-TYPE
      SYNTAX Counter32
      MAX-ACCESS read-only
      STATUS current
      DESCRIPTION
              "ODU Performance Monitoring for 24-Hour Interval Near-End Errored Second Ratio.
              ESR is a decimal number between 0 and 0.999.  In order to not deal with a decimal number, the
              ESR value is multiplied by 1000 for this OID."
      ::= { adGenOtnOduPm24HrIntervalEntry 7 }

  adGenOtnOduPm24HrIntervalNeSESR    OBJECT-TYPE
      SYNTAX Counter32
      MAX-ACCESS read-only
      STATUS current
      DESCRIPTION
              "ODU Performance Monitoring for 24-Hour Interval Near-End Severely Errored Second Ratio.
              SESR is a decimal number between 0 and 0.99.  In order to not deal with a decimal number, the
              SESR value is multiplied by 100 for this OID."
      ::= { adGenOtnOduPm24HrIntervalEntry 8 }

  adGenOtnOduPm24HrIntervalNeUAS    OBJECT-TYPE
      SYNTAX Counter32
      MAX-ACCESS read-only
      STATUS current
      DESCRIPTION
              "ODU Performance Monitoring for 24-Hour Interval Near-End Unavailable Seconds."
      ::= { adGenOtnOduPm24HrIntervalEntry 9 }

  adGenOtnOduPm24HrIntervalFeEB    OBJECT-TYPE
      SYNTAX Counter32
      MAX-ACCESS read-only
      STATUS current
      DESCRIPTION
              "ODU Performance Monitoring for 24-Hour Interval Far-End Errored Blocks."
      ::= { adGenOtnOduPm24HrIntervalEntry 10 }

  adGenOtnOduPm24HrIntervalFeBBE    OBJECT-TYPE
      SYNTAX Counter32
      MAX-ACCESS read-only
      STATUS current
      DESCRIPTION
              "ODU Performance Monitoring for 24-Hour Interval Far-End Background Block Errors."
      ::= { adGenOtnOduPm24HrIntervalEntry 11 }

  adGenOtnOduPm24HrIntervalFeBBER    OBJECT-TYPE
      SYNTAX DisplayString (SIZE (0..13))
      MAX-ACCESS read-only
      STATUS current
      DESCRIPTION
              "ODU Performance Monitoring for 24-Hour Interval Far-End Background Block Error Ratio.
              BBER is a decimal value between 0 and 1 calculated out to as many as 10 decimal place."
      ::= { adGenOtnOduPm24HrIntervalEntry 12 }

  adGenOtnOduPm24HrIntervalFeES    OBJECT-TYPE
      SYNTAX Counter32
      MAX-ACCESS read-only
      STATUS current
      DESCRIPTION
              "ODU Performance Monitoring for 24-Hour Interval Far-End Errored Seconds."
      ::= { adGenOtnOduPm24HrIntervalEntry 13 }

  adGenOtnOduPm24HrIntervalFeSES    OBJECT-TYPE
      SYNTAX Counter32
      MAX-ACCESS read-only
      STATUS current
      DESCRIPTION
              "ODU Performance Monitoring for 24-Hour Interval Far-End Severely Errored Seconds."
      ::= { adGenOtnOduPm24HrIntervalEntry 14 }

  adGenOtnOduPm24HrIntervalFeESR    OBJECT-TYPE
      SYNTAX Counter32
      MAX-ACCESS read-only
      STATUS current
      DESCRIPTION
              "ODU Performance Monitoring for 24-Hour Interval Far-End Errored Second Ratio.
              ESR is a decimal number between 0 and 0.999.  In order to not deal with a decimal number, the
              ESR value is multiplied by 1000 for this OID."
      ::= { adGenOtnOduPm24HrIntervalEntry 15 }

  adGenOtnOduPm24HrIntervalFeSESR    OBJECT-TYPE
      SYNTAX Counter32
      MAX-ACCESS read-only
      STATUS current
      DESCRIPTION
              "ODU Performance Monitoring for 24-Hour Interval Far-End Severely Errored Second Ratio.
              SESR is a decimal number between 0 and 0.99.  In order to not deal with a decimal number, the
              SESR value is multiplied by 100 for this OID."
      ::= { adGenOtnOduPm24HrIntervalEntry 16 }

  adGenOtnOduPm24HrIntervalFeUAS    OBJECT-TYPE
      SYNTAX Counter32
      MAX-ACCESS read-only
      STATUS current
      DESCRIPTION
              "ODU Performance Monitoring for 24-Hour Interval Far-End Unavailable Seconds."
      ::= { adGenOtnOduPm24HrIntervalEntry 17 }

  adGenOtnOduPm24HrIntervalNeValidData OBJECT-TYPE
			SYNTAX  TruthValue
			MAX-ACCESS  read-only
			STATUS  current
			DESCRIPTION
				"This variable indicates if the data for this
				 near end 24 hour interval is valid."
			::= { adGenOtnOduPm24HrIntervalEntry 18 }

  adGenOtnOduPm24HrIntervalFeValidData OBJECT-TYPE
			SYNTAX  TruthValue
			MAX-ACCESS  read-only
			STATUS  current
			DESCRIPTION
				"This variable indicates if the data for this
				 far end 24 hour interval is valid."
			::= { adGenOtnOduPm24HrIntervalEntry 19 }

	-- /////////////////////////////////////////////////////////
	adGenOtnPmInterfaceTable OBJECT-TYPE
		SYNTAX  SEQUENCE OF AdGenOtnPmInterfaceEntry
		MAX-ACCESS  not-accessible
		STATUS  current
		DESCRIPTION
			"The Generic OTN PM interface table"
		::= { adGenOtnPmInterface 1 }

	adGenOtnPmInterfaceEntry OBJECT-TYPE
		SYNTAX  AdGenOtnPmInterfaceEntry
		MAX-ACCESS  not-accessible
		STATUS  current
		DESCRIPTION
			"An entry in the OTN PM interface table"
		INDEX   { ifIndex }
		::= { adGenOtnPmInterfaceTable 1 }

	AdGenOtnPmInterfaceEntry ::=
		SEQUENCE {
				adGenOtnPmInterface15MinValidIntervals 	INTEGER,
				adGenOtnPmInterface24HrValidIntervals  	INTEGER,
				adGenOtnPmInterfaceResetPM 	 				INTEGER
     }

	adGenOtnPmInterface15MinValidIntervals OBJECT-TYPE
		SYNTAX  INTEGER (0..96)
      MAX-ACCESS  read-only
      STATUS  current
      DESCRIPTION
			"It displays the number of completed quarter hourly (15-minute) bins per interface."
      ::= { adGenOtnPmInterfaceEntry 1 }

   adGenOtnPmInterface24HrValidIntervals OBJECT-TYPE
      SYNTAX  INTEGER (0..7)
      MAX-ACCESS  read-only
      STATUS  current
      DESCRIPTION
			"It displays the number of completed daily (24-hour) bins per interface."
      ::= { adGenOtnPmInterfaceEntry 2 }

	adGenOtnPmInterfaceResetPM OBJECT-TYPE
		SYNTAX  INTEGER {
                         reset(1)
                      }
      MAX-ACCESS  read-write
      STATUS  current
      DESCRIPTION
			"Reset all OTN PM counts per interface."
      ::= { adGenOtnPmInterfaceEntry 3 }


	-- /////////////////////////////////////////////////////////
	adGenOtnPmSlotTable OBJECT-TYPE
        SYNTAX  SEQUENCE OF AdGenOtnPmSlotEntry
        MAX-ACCESS  not-accessible
        STATUS  current
        DESCRIPTION
                   "The OTN PM Slot Table"
        ::= { adGenOtnPmSlot 1 }

   adGenOtnPmSlotEntry OBJECT-TYPE
        SYNTAX  AdGenOtnPmSlotEntry
        MAX-ACCESS  not-accessible
        STATUS  current
        DESCRIPTION
                   "An entry in the OTN PM Slot Table"
        INDEX   { adGenSlotInfoIndex }
        ::= { adGenOtnPmSlotTable 1 }

   AdGenOtnPmSlotEntry ::=
        SEQUENCE {
            adGenOtnPmResetAllPMData   INTEGER
        }

	adGenOtnPmResetAllPMData OBJECT-TYPE
		  SYNTAX INTEGER {
                         reset(1)
                       }
		  MAX-ACCESS  read-write
		  STATUS  current
		  DESCRIPTION
				"Reset all OTN PM counts per slot."
		  ::= { adGenOtnPmSlotEntry 1 }

-- ---------------------------------------------------------------------------------
-- The OTN OTU Running Counters Table

-- ---------------------------------------------------------------------------------

       adGenOtnOtuCountersTable OBJECT-TYPE
                SYNTAX  SEQUENCE OF AdGenOtnOtuCountersEntry
                MAX-ACCESS  not-accessible
                STATUS  current
                DESCRIPTION
                       "The OTN running counters table."
                ::= { adGenOtnPm 9 }

       adGenOtnOtuCountersEntry OBJECT-TYPE
                SYNTAX  AdGenOtnOtuCountersEntry
                MAX-ACCESS  not-accessible
                STATUS  current
                DESCRIPTION
                        "An entry in the OTN OTU Entry"
                INDEX   {ifIndex }
                ::= { adGenOtnOtuCountersTable 1 }

       AdGenOtnOtuCountersEntry ::=
                SEQUENCE {
                                adGenOtnOtuCounterNeEB              Counter64,
                                adGenOtnOtuCounterNeBBE             Counter64,
                                adGenOtnOtuCounterNeES              Counter64,
                                adGenOtnOtuCounterNeSES             Counter64,
                                adGenOtnOtuCounterNeUAS             Counter64,
                                adGenOtnOtuCounterFeEB              Counter64,
                                adGenOtnOtuCounterFeBBE             Counter64,
                                adGenOtnOtuCounterFeES              Counter64,
                                adGenOtnOtuCounterFeSES             Counter64,
                                adGenOtnOtuCounterFeUAS             Counter64,
                                adGenOtnOtuCounterFecCorrBits       Counter64,
                                adGenOtnOtuCounterFecUnCorrBlks     Counter64
     }

        adGenOtnOtuCounterNeEB OBJECT-TYPE
        SYNTAX  Counter64
        MAX-ACCESS  read-only
        STATUS  current
        DESCRIPTION
                "The counter associated with the number of Near End Errored blocks
                  encountered by an OTN OTU interface"
         ::= { adGenOtnOtuCountersEntry 1 }

        adGenOtnOtuCounterNeBBE OBJECT-TYPE
        SYNTAX  Counter64
        MAX-ACCESS  read-only
        STATUS  current
        DESCRIPTION
                "The counter associated with the number of Near End Background Block Errors
                  encountered by an OTN OTU interface"
         ::= { adGenOtnOtuCountersEntry 2 }

        adGenOtnOtuCounterNeES OBJECT-TYPE
        SYNTAX  Counter64
        MAX-ACCESS  read-only
        STATUS  current
        DESCRIPTION
               "The counter associated with the number of Near End  Errored Seconds
                 encountered by an OTN OTU interface"
         ::= { adGenOtnOtuCountersEntry 3 }

        adGenOtnOtuCounterNeSES OBJECT-TYPE
        SYNTAX  Counter64
        MAX-ACCESS  read-only
        STATUS  current
        DESCRIPTION
               "The counter associated with the number of Near End Severely Errored Seconds
                 encountered by an OTN OTU interface"
         ::= { adGenOtnOtuCountersEntry 4 }

        adGenOtnOtuCounterNeUAS OBJECT-TYPE
        SYNTAX  Counter64
        MAX-ACCESS  read-only
        STATUS  current
        DESCRIPTION
               "The counter associated with the number of Near End Unavailable Seconds encountered
                 by an OTN OTU interface"
         ::= { adGenOtnOtuCountersEntry 5 }

        adGenOtnOtuCounterFeEB OBJECT-TYPE
        SYNTAX  Counter64
        MAX-ACCESS  read-only
        STATUS  current
        DESCRIPTION
               "The counter associated with the number of Far End Errored blocks encountered
                 by an OTN OTU interface"
         ::= { adGenOtnOtuCountersEntry 6 }

        adGenOtnOtuCounterFeBBE OBJECT-TYPE
        SYNTAX  Counter64
        MAX-ACCESS  read-only
        STATUS  current
        DESCRIPTION
               "The counter associated with the number of Far End Background Block Errors encountered
                 by an OTN OTU interface"
         ::= { adGenOtnOtuCountersEntry 7 }

        adGenOtnOtuCounterFeES OBJECT-TYPE
        SYNTAX  Counter64
        MAX-ACCESS  read-only
        STATUS  current
        DESCRIPTION
               "The counter associated with the number of Far End  Errored Seconds encountered
                 by an OTN OTU interface"
         ::= { adGenOtnOtuCountersEntry 8 }

        adGenOtnOtuCounterFeSES OBJECT-TYPE
        SYNTAX  Counter64
        MAX-ACCESS  read-only
        STATUS  current
        DESCRIPTION
               "The counter associated with the number of Far End Severely Errored Seconds encountered
                by an OTN OTU interface"
         ::= { adGenOtnOtuCountersEntry 9 }

        adGenOtnOtuCounterFeUAS OBJECT-TYPE
        SYNTAX  Counter64
        MAX-ACCESS  read-only
        STATUS  current
        DESCRIPTION
               "The counter associated with the number of Far End Unavailable Seconds encountered
                by an OTN OTU interface"
         ::= { adGenOtnOtuCountersEntry 10 }

        adGenOtnOtuCounterFecCorrBits OBJECT-TYPE
        SYNTAX  Counter64
        MAX-ACCESS  read-only
        STATUS  current
        DESCRIPTION
               "The counter associated with the number of Far End Fec corrected Bits encountered
                 by an OTN OTU interface"
         ::= { adGenOtnOtuCountersEntry 11 }

        adGenOtnOtuCounterFecUnCorrBlks OBJECT-TYPE
        SYNTAX  Counter64
        MAX-ACCESS  read-only
        STATUS  current
        DESCRIPTION
               "The counter associated with the number of Far End Fec Uncorrected Blocks encountered
                 by an OTN OTU interface"
         ::= { adGenOtnOtuCountersEntry 12 }

-- ---------------------------------------------------------------------------------
-- The OTN ODU Running Counters Table

-- ---------------------------------------------------------------------------------
       adGenOtnOduCountersTable OBJECT-TYPE
                SYNTAX  SEQUENCE OF AdGenOtnOduCountersEntry
                MAX-ACCESS  not-accessible
                STATUS  current
                DESCRIPTION
                       "The OTN ODU running counters table."
                ::= { adGenOtnPm 10 }

        adGenOtnOduCountersEntry OBJECT-TYPE
                SYNTAX  AdGenOtnOduCountersEntry
                MAX-ACCESS  not-accessible
                STATUS  current
                DESCRIPTION
                        "An entry in the OTN ODU Running Counters Entry"
                INDEX   { adGenSlotInfoIndex, adGenOtnOduIndex }
                ::= { adGenOtnOduCountersTable 1 }

        AdGenOtnOduCountersEntry ::=
                SEQUENCE {
                                adGenOtnOduCounterNeEB    Counter64,
                                adGenOtnOduCounterNeBBE   Counter64,
                                adGenOtnOduCounterNeES    Counter64,
                                adGenOtnOduCounterNeSES   Counter64,
                                adGenOtnOduCounterNeUAS   Counter64,
                                adGenOtnOduCounterFeEB    Counter64,
                                adGenOtnOduCounterFeBBE   Counter64,
                                adGenOtnOduCounterFeES    Counter64,
                                adGenOtnOduCounterFeSES   Counter64,
                                adGenOtnOduCounterFeUAS   Counter64
     }

        adGenOtnOduCounterNeEB OBJECT-TYPE
        SYNTAX  Counter64
        MAX-ACCESS  read-only
        STATUS  current
        DESCRIPTION
               "The counter associated with the number of Near End Errored blocks encountered by
                 an OTN ODU interface"
         ::= { adGenOtnOduCountersEntry 1 }

        adGenOtnOduCounterNeBBE OBJECT-TYPE
        SYNTAX  Counter64
        MAX-ACCESS  read-only
        STATUS  current
        DESCRIPTION
               "The counter associated with the number of Near End Background Block Errors encountered
                 by an OTN ODU interface"
         ::= { adGenOtnOduCountersEntry 2 }

        adGenOtnOduCounterNeES OBJECT-TYPE
        SYNTAX  Counter64
        MAX-ACCESS  read-only
        STATUS  current
        DESCRIPTION
               "The counter associated with the number of Near End  Errored Seconds encountered
                 by an OTN ODU interface"
         ::= { adGenOtnOduCountersEntry 3 }

        adGenOtnOduCounterNeSES OBJECT-TYPE
        SYNTAX  Counter64
        MAX-ACCESS  read-only
        STATUS  current
        DESCRIPTION
               "The counter associated with the number of Near End Severely Errored Seconds encountered
                by an OTN OTU interface"
         ::= { adGenOtnOduCountersEntry 4 }

        adGenOtnOduCounterNeUAS OBJECT-TYPE
        SYNTAX  Counter64
        MAX-ACCESS  read-only
        STATUS  current
        DESCRIPTION
               "The counter associated with the number of Near End Unavailable Seconds encountered
                 by an OTN ODU interface"
         ::= { adGenOtnOduCountersEntry 5 }

        adGenOtnOduCounterFeEB OBJECT-TYPE
        SYNTAX  Counter64
        MAX-ACCESS  read-only
        STATUS  current
        DESCRIPTION
               "The counter associated with the number of Far End Errored blocks encountered
                 by an OTN ODU interface"
         ::= { adGenOtnOduCountersEntry 6 }

        adGenOtnOduCounterFeBBE OBJECT-TYPE
        SYNTAX  Counter64
        MAX-ACCESS  read-only
        STATUS  current
        DESCRIPTION
               "The counter associated with the number of Far End Background Block Errors encountered
                 by an OTN ODU interface"
         ::= { adGenOtnOduCountersEntry 7 }

        adGenOtnOduCounterFeES OBJECT-TYPE
        SYNTAX  Counter64
        MAX-ACCESS  read-only
        STATUS  current
        DESCRIPTION
               "The counter associated with the number of Far End  Errored Seconds encountered
                by an OTN ODU interface"
         ::= { adGenOtnOduCountersEntry 8 }

        adGenOtnOduCounterFeSES OBJECT-TYPE
        SYNTAX  Counter64
        MAX-ACCESS  read-only
        STATUS  current
        DESCRIPTION
               "The counter associated with the number of Far End Severely Errored Seconds
                 encountered by an OTN ODU interface"
         ::= { adGenOtnOduCountersEntry 9 }

        adGenOtnOduCounterFeUAS OBJECT-TYPE
        SYNTAX  Counter64
        MAX-ACCESS  read-only
        STATUS  current
        DESCRIPTION
                "The counter associated with the number of Far End Unavailable Seconds encountered
                  by an OTN ODU interface"
         ::= { adGenOtnOduCountersEntry 10 }


-- // OTU Alarms
  adGenOtnOtuLosClrAlm    NOTIFICATION-TYPE
     OBJECTS       {
             adTrapInformSeqNum,
             sysName,
             ifIndex,
             ifDescr,
             adTAeSCUTrapAlarmLevel
             }
     STATUS          current
     DESCRIPTION
             "Loss of Signal Alarm - Cleared"
     --#TYPE      "Critical - LOS"
     --#SUMMARY   "LOS Alarm - Cleared"
     --#SUMMARY   "cleared at shelf: %s, Interface: %d %s"
     --#ARGUMENTS { 1, 2, 3 }
     --#SEVERITY  CRITICAL
     --#GENERIC   6
     --#CATEGORY  "Error Events"
     --#SOURCE_ID "A"
     --#TIMEINDEX 0
     ::= {adGenOtnOtuAlarms 2}

  adGenOtnOtuLosActAlm    NOTIFICATION-TYPE
     OBJECTS       {
             adTrapInformSeqNum,
             sysName,
             ifIndex,
             ifDescr,
             adTAeSCUTrapAlarmLevel
             }
     STATUS          current
     DESCRIPTION
             "Loss of Signal Alarm - Active"
     --#TYPE      "Critical - LOS"
     --#SUMMARY   "LOS Alarm - Active"
     --#SUMMARY   "detected at shelf: %s, Interface: %d %s"
     --#ARGUMENTS { 1, 2, 3 }
     --#SEVERITY  CRITICAL
     --#GENERIC   6
     --#CATEGORY  "Error Events"
     --#SOURCE_ID "A"
     --#TIMEINDEX 0
     ::= {adGenOtnOtuAlarms 3}

-- //
  adGenOtnOtuLofClrAlm    NOTIFICATION-TYPE
     OBJECTS       {
             adTrapInformSeqNum,
             sysName,
             ifIndex,
             ifDescr,
             adTAeSCUTrapAlarmLevel
             }
     STATUS          current
     DESCRIPTION
             "Section Loss of Frame Alarm - Cleared"
     --#TYPE      "Critical - LOF-S"
     --#SUMMARY   "LOF-S Alarm - Cleared"
     --#SUMMARY   "cleared at shelf: %s, Interface: %d %s"
     --#ARGUMENTS { 1, 2, 3 }
     --#SEVERITY  CRITICAL
     --#GENERIC   6
     --#CATEGORY  "Error Events"
     --#SOURCE_ID "A"
     --#TIMEINDEX 0
     ::= {adGenOtnOtuAlarms 4}

  adGenOtnOtuLofActAlm    NOTIFICATION-TYPE
     OBJECTS       {
             adTrapInformSeqNum,
             sysName,
             ifIndex,
             ifDescr,
             adTAeSCUTrapAlarmLevel
             }
     STATUS          current
     DESCRIPTION
             "Section Loss of Frame Alarm - Active"
     --#TYPE      "Critical - LOF-S"
     --#SUMMARY   "LOF-S Alarm - Active"
     --#SUMMARY   "detected at shelf: %s, Interface: %d %s"
     --#ARGUMENTS { 1, 2, 3 }
     --#SEVERITY  CRITICAL
     --#GENERIC   6
     --#CATEGORY  "Error Events"
     --#SOURCE_ID "A"
     --#TIMEINDEX 0
     ::= {adGenOtnOtuAlarms 5}

-- //
  adGenOtnOtuLomClrAlm    NOTIFICATION-TYPE
     OBJECTS       {
             adTrapInformSeqNum,
             sysName,
             ifIndex,
             ifDescr,
             adTAeSCUTrapAlarmLevel
             }
     STATUS          current
     DESCRIPTION
             "Section Loss of Multiframe Alarm - Cleared"
     --#TYPE      "Critical - LOM-S"
     --#SUMMARY   "LOM-S Alarm - Cleared"
     --#SUMMARY   "cleared at shelf: %s, Interface: %d %s"
     --#ARGUMENTS { 1, 2, 3 }
     --#SEVERITY  CRITICAL
     --#GENERIC   6
     --#CATEGORY  "Error Events"
     --#SOURCE_ID "A"
     --#TIMEINDEX 0
     ::= {adGenOtnOtuAlarms 6}

  adGenOtnOtuLomActAlm    NOTIFICATION-TYPE
     OBJECTS       {
             adTrapInformSeqNum,
             sysName,
             ifIndex,
             ifDescr,
             adTAeSCUTrapAlarmLevel
             }
     STATUS          current
     DESCRIPTION
             "Section Loss of Multiframe Alarm - Active"
     --#TYPE      "Critical - LOM-S"
     --#SUMMARY   "LOM-S Alarm - Active"
     --#SUMMARY   "detected at shelf: %s, Interface: %d %s"
     --#ARGUMENTS { 1, 2, 3 }
     --#SEVERITY  CRITICAL
     --#GENERIC   6
     --#CATEGORY  "Error Events"
     --#SOURCE_ID "A"
     --#TIMEINDEX 0
     ::= {adGenOtnOtuAlarms 7}

-- //
  adGenOtnOtuAisClrAlm    NOTIFICATION-TYPE
     OBJECTS       {
             adTrapInformSeqNum,
             sysName,
             ifIndex,
             ifDescr,
             adTAeSCUTrapAlarmLevel
             }
     STATUS          current
     DESCRIPTION
             "Section Alarm Indication Signal Alarm - Cleared"
     --#TYPE      "Warning - AIS-S"
     --#SUMMARY   "AIS-S Alarm - Cleared"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuAlarms 8}

  adGenOtnOtuAisActAlm    NOTIFICATION-TYPE
     OBJECTS       {
             adTrapInformSeqNum,
             sysName,
             ifIndex,
             ifDescr,
             adTAeSCUTrapAlarmLevel
             }
     STATUS          current
     DESCRIPTION
             "Section Alarm Indication Signal Alarm - Active"
     --#TYPE      "Warning - AIS-S"
     --#SUMMARY   "AIS-S Alarm - Active"
     --#SUMMARY   "detected at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuAlarms 9}

-- //
  adGenOtnOtuBdiClrAlm    NOTIFICATION-TYPE
     OBJECTS       {
             adTrapInformSeqNum,
             sysName,
             ifIndex,
             ifDescr,
             adTAeSCUTrapAlarmLevel
             }
     STATUS          current
     DESCRIPTION
             "Section Backward Defect Indication Alarm - Cleared"
     --#TYPE      "Warning - BDI-S"
     --#SUMMARY   "BDI-S Alarm - Cleared"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuAlarms 10}

  adGenOtnOtuBdiActAlm    NOTIFICATION-TYPE
     OBJECTS       {
             adTrapInformSeqNum,
             sysName,
             ifIndex,
             ifDescr,
             adTAeSCUTrapAlarmLevel
             }
     STATUS          current
     DESCRIPTION
             "Section Backward Defect Indication Alarm - Active"
     --#TYPE      "Warning - BDI-S"
     --#SUMMARY   "BDI-S Alarm - Active"
     --#SUMMARY   "detected at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuAlarms 11}

-- //
  adGenOtnOtuTimClrAlm    NOTIFICATION-TYPE
     OBJECTS       {
             adTrapInformSeqNum,
             sysName,
             ifIndex,
             ifDescr,
             adTAeSCUTrapAlarmLevel
             }
     STATUS          current
     DESCRIPTION
             "Section Trace Identifier Mismatch Alarm - Cleared"
     --#TYPE      "Warning - TIM-S"
     --#SUMMARY   "TIM-S Alarm - Cleared"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuAlarms 12}

  adGenOtnOtuTimActAlm    NOTIFICATION-TYPE
     OBJECTS       {
             adTrapInformSeqNum,
             sysName,
             ifIndex,
             ifDescr,
             adTAeSCUTrapAlarmLevel
             }
     STATUS          current
     DESCRIPTION
             "Section Trace Identifier Mismatch Alarm - Active"
     --#TYPE      "Warning - TIM-S"
     --#SUMMARY   "TIM-S Alarm - Active"
     --#SUMMARY   "detected at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuAlarms 13}

-- //
  adGenOtnOtuDegClrAlm    NOTIFICATION-TYPE
     OBJECTS       {
             adTrapInformSeqNum,
             sysName,
             ifIndex,
             ifDescr,
             adTAeSCUTrapAlarmLevel
             }
     STATUS          current
     DESCRIPTION
             "Section Signal Degrade Alarm - Cleared"
     --#TYPE      "Critical - DEG-S"
     --#SUMMARY   "DEG-S Alarm - Cleared"
     --#SUMMARY   "cleared at shelf: %s, Interface: %d %s"
     --#ARGUMENTS { 1, 2, 3 }
     --#SEVERITY  CRITICAL
     --#GENERIC   6
     --#CATEGORY  "Error Events"
     --#SOURCE_ID "A"
     --#TIMEINDEX 0
     ::= {adGenOtnOtuAlarms 14}

  adGenOtnOtuDegActAlm    NOTIFICATION-TYPE
     OBJECTS       {
             adTrapInformSeqNum,
             sysName,
             ifIndex,
             ifDescr,
             adTAeSCUTrapAlarmLevel
             }
     STATUS          current
     DESCRIPTION
             "Section Signal Degrade Alarm - Active"
     --#TYPE      "Critical - DEG-S"
     --#SUMMARY   "DEG-S Alarm - Active"
     --#SUMMARY   "detected at shelf: %s, Interface: %d %s"
     --#ARGUMENTS { 1, 2, 3 }
     --#SEVERITY  CRITICAL
     --#GENERIC   6
     --#CATEGORY  "Error Events"
     --#SOURCE_ID "A"
     --#TIMEINDEX 0
     ::= {adGenOtnOtuAlarms 15}

-- // ODU Alarms

-- //
  adGenOtnOduLofLomClrAlm    NOTIFICATION-TYPE
     OBJECTS       {
             adTrapInformSeqNum,
             sysName,
             adGenSlotInfoIndex,
             adGenOtnOduIndex,
             adTAeSCUTrapAlarmLevel
             }
     STATUS          current
     DESCRIPTION
             "Path Loss of Frame and Multiframe Alarm - Cleared"
     --#TYPE      "Critical - LOFLOM-P"
     --#SUMMARY   "LOFLOM-P Alarm - Cleared"
     --#SUMMARY   "cleared at shelf: %s, Slot: %d Odu: %d"
     --#ARGUMENTS { 1, 2, 3 }
     --#SEVERITY  CRITICAL
     --#GENERIC   6
     --#CATEGORY  "Error Events"
     --#SOURCE_ID "A"
     --#TIMEINDEX 0
     ::= {adGenOtnOduAlarms 2}

  adGenOtnOduLofLomActAlm    NOTIFICATION-TYPE
     OBJECTS       {
             adTrapInformSeqNum,
             sysName,
             adGenSlotInfoIndex,
             adGenOtnOduIndex,
             adTAeSCUTrapAlarmLevel
             }
     STATUS          current
     DESCRIPTION
             "Path Loss of Frame and Multiframe Alarm - Active"
     --#TYPE      "Critical - LOFLOM-P"
     --#SUMMARY   "LOFLOM-P Alarm - Active"
     --#SUMMARY   "cleared at shelf: %s, Slot: %d Odu: %d"
     --#ARGUMENTS { 1, 2, 3 }
     --#SEVERITY  CRITICAL
     --#GENERIC   6
     --#CATEGORY  "Error Events"
     --#SOURCE_ID "A"
     --#TIMEINDEX 0
     ::= {adGenOtnOduAlarms 3}


  adGenOtnOduBdiClrAlm    NOTIFICATION-TYPE
     OBJECTS       {
             adTrapInformSeqNum,
             sysName,
             adGenSlotInfoIndex,
             adGenOtnOduIndex,
             adTAeSCUTrapAlarmLevel
             }
     STATUS          current
     DESCRIPTION
             "Path Backward Defect Indication Alarm - Cleared"
     --#TYPE      "Warning - BDI-P"
     --#SUMMARY   "BDI-P Alarm - Cleared"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduAlarms 4}

  adGenOtnOduBdiActAlm    NOTIFICATION-TYPE
     OBJECTS       {
             adTrapInformSeqNum,
             sysName,
             adGenSlotInfoIndex,
             adGenOtnOduIndex,
             adTAeSCUTrapAlarmLevel
             }
     STATUS          current
     DESCRIPTION
             "Path Backward Defect Indiction Alarm - Active"
     --#TYPE      "Warning - BDI-P"
     --#SUMMARY   "BDI-P Alarm - Active"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduAlarms 5}

-- //
  adGenOtnOduOciClrAlm    NOTIFICATION-TYPE
     OBJECTS       {
             adTrapInformSeqNum,
             sysName,
             adGenSlotInfoIndex,
             adGenOtnOduIndex,
             adTAeSCUTrapAlarmLevel
             }
     STATUS          current
     DESCRIPTION
             "Path Open Connection Indication Alarm - Cleared"
     --#TYPE      "Critical - OCI-P"
     --#SUMMARY   "OCI-P Alarm - Cleared"
     --#SUMMARY   "cleared at shelf: %s, Slot: %d Odu: %d"
     --#ARGUMENTS { 1, 2, 3 }
     --#SEVERITY  CRITICAL
     --#GENERIC   6
     --#CATEGORY  "Error Events"
     --#SOURCE_ID "A"
     --#TIMEINDEX 0
     ::= {adGenOtnOduAlarms 6}

  adGenOtnOduOciActAlm    NOTIFICATION-TYPE
     OBJECTS       {
             adTrapInformSeqNum,
             sysName,
             adGenSlotInfoIndex,
             adGenOtnOduIndex,
             adTAeSCUTrapAlarmLevel
             }
     STATUS          current
     DESCRIPTION
             "Path Open Connection Indiction Alarm - Active"
     --#TYPE      "Critical - OCI-P"
     --#SUMMARY   "OCI-P Alarm - Active"
     --#SUMMARY   "cleared at shelf: %s, Slot: %d Odu: %d"
     --#ARGUMENTS { 1, 2, 3 }
     --#SEVERITY  CRITICAL
     --#GENERIC   6
     --#CATEGORY  "Error Events"
     --#SOURCE_ID "A"
     --#TIMEINDEX 0
     ::= {adGenOtnOduAlarms 7}

-- //
  adGenOtnOduTimClrAlm    NOTIFICATION-TYPE
     OBJECTS       {
             adTrapInformSeqNum,
             sysName,
             adGenSlotInfoIndex,
             adGenOtnOduIndex,
             adTAeSCUTrapAlarmLevel
             }
     STATUS          current
     DESCRIPTION
             "Path Trace Identifier Mismatch Alarm - Cleared"
     --#TYPE      "Warning - TIM-P"
     --#SUMMARY   "TIM-P Alarm - Cleared"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduAlarms 8}

  adGenOtnOduTimActAlm    NOTIFICATION-TYPE
     OBJECTS       {
             adTrapInformSeqNum,
             sysName,
             adGenSlotInfoIndex,
             adGenOtnOduIndex,
             adTAeSCUTrapAlarmLevel
             }
     STATUS          current
     DESCRIPTION
             "Path Trace Identifier Mismatch Alarm - Active"
     --#TYPE      "Warning - TIM-P"
     --#SUMMARY   "TIM-P Alarm - Active"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduAlarms 9}

-- //
  adGenOtnOduDegClrAlm    NOTIFICATION-TYPE
     OBJECTS       {
             adTrapInformSeqNum,
             sysName,
             adGenSlotInfoIndex,
             adGenOtnOduIndex,
             adTAeSCUTrapAlarmLevel
             }
     STATUS          current
     DESCRIPTION
             "Path Signal Degrade Alarm - Cleared"
     --#TYPE      "Critical - DEG-P"
     --#SUMMARY   "DEG-P Alarm - Cleared"
     --#SUMMARY   "cleared at shelf: %s, Slot: %d Odu: %d"
     --#ARGUMENTS { 1, 2, 3 }
     --#SEVERITY  CRITICAL
     --#GENERIC   6
     --#CATEGORY  "Error Events"
     --#SOURCE_ID "A"
     --#TIMEINDEX 0
     ::= {adGenOtnOduAlarms 10}

  adGenOtnOduDegActAlm    NOTIFICATION-TYPE
     OBJECTS       {
             adTrapInformSeqNum,
             sysName,
             adGenSlotInfoIndex,
             adGenOtnOduIndex,
             adTAeSCUTrapAlarmLevel
             }
     STATUS          current
     DESCRIPTION
             "Path Signal Degrade Alarm - Active"
     --#TYPE      "Critical - DEG-P"
     --#SUMMARY   "DEG-P Alarm - Active"
     --#SUMMARY   "cleared at shelf: %s, Slot: %d Odu: %d"
     --#ARGUMENTS { 1, 2, 3 }
     --#SEVERITY  CRITICAL
     --#GENERIC   6
     --#CATEGORY  "Error Events"
     --#SOURCE_ID "A"
     --#TIMEINDEX 0
     ::= {adGenOtnOduAlarms 11}

-- //
  adGenOtnOduPlmClrAlm    NOTIFICATION-TYPE
     OBJECTS       {
             adTrapInformSeqNum,
             sysName,
             adGenSlotInfoIndex,
             adGenOtnOduIndex,
             adTAeSCUTrapAlarmLevel
             }
     STATUS          current
     DESCRIPTION
             "Path Payload Label Mismatch Alarm - Cleared"
     --#TYPE      "Critical - PLM-P"
     --#SUMMARY   "PLM-P Alarm - Cleared"
     --#SUMMARY   "cleared at shelf: %s, Slot: %d Odu: %d"
     --#ARGUMENTS { 1, 2, 3 }
     --#SEVERITY  CRITICAL
     --#GENERIC   6
     --#CATEGORY  "Error Events"
     --#SOURCE_ID "A"
     --#TIMEINDEX 0
     ::= {adGenOtnOduAlarms 12}

  adGenOtnOduPlmActAlm    NOTIFICATION-TYPE
     OBJECTS       {
             adTrapInformSeqNum,
             sysName,
             adGenSlotInfoIndex,
             adGenOtnOduIndex,
             adTAeSCUTrapAlarmLevel
             }
     STATUS          current
     DESCRIPTION
             "Path Payload Label Mismatch Alarm - Active"
     --#TYPE      "Critical - PLM-P"
     --#SUMMARY   "PLM-P Alarm - Active"
     --#SUMMARY   "cleared at shelf: %s, Slot: %d Odu: %d"
     --#ARGUMENTS { 1, 2, 3 }
     --#SEVERITY  CRITICAL
     --#GENERIC   6
     --#CATEGORY  "Error Events"
     --#SOURCE_ID "A"
     --#TIMEINDEX 0
     ::= {adGenOtnOduAlarms 13}

-- //
  adGenOtnOduLckClrAlm    NOTIFICATION-TYPE
     OBJECTS       {
             adTrapInformSeqNum,
             sysName,
             adGenSlotInfoIndex,
             adGenOtnOduIndex,
             adTAeSCUTrapAlarmLevel
             }
     STATUS          current
     DESCRIPTION
             "Path Locked Alarm - Cleared"
     --#TYPE      "Critical - LCK-P"
     --#SUMMARY   "LCK-P Alarm - Cleared"
     --#SUMMARY   "cleared at shelf: %s, Slot: %d Odu: %d"
     --#ARGUMENTS { 1, 2, 3 }
     --#SEVERITY  CRITICAL
     --#GENERIC   6
     --#CATEGORY  "Error Events"
     --#SOURCE_ID "A"
     --#TIMEINDEX 0
     ::= {adGenOtnOduAlarms 14}

  adGenOtnOduLckActAlm    NOTIFICATION-TYPE
     OBJECTS       {
             adTrapInformSeqNum,
             sysName,
             adGenSlotInfoIndex,
             adGenOtnOduIndex,
             adTAeSCUTrapAlarmLevel
             }
     STATUS          current
     DESCRIPTION
             "Path Locked Alarm - Active"
     --#TYPE      "Critical - LCK-P"
     --#SUMMARY   "LCK-P Alarm - Active"
     --#SUMMARY   "cleared at shelf: %s, Slot: %d Odu: %d"
     --#ARGUMENTS { 1, 2, 3 }
     --#SEVERITY  CRITICAL
     --#GENERIC   6
     --#CATEGORY  "Error Events"
     --#SOURCE_ID "A"
     --#TIMEINDEX 0
     ::= {adGenOtnOduAlarms 15}

-- //
  adGenOtnOduAisClrAlm    NOTIFICATION-TYPE
     OBJECTS       {
             adTrapInformSeqNum,
             sysName,
             adGenSlotInfoIndex,
             adGenOtnOduIndex,
             adTAeSCUTrapAlarmLevel
             }
     STATUS          current
     DESCRIPTION
             "Path Alarm Indication Signal Alarm - Cleared"
     --#TYPE      "Warning - AIS-P"
     --#SUMMARY   "AIS-P Alarm - Cleared"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduAlarms 16}

  adGenOtnOduAisActAlm    NOTIFICATION-TYPE
     OBJECTS       {
             adTrapInformSeqNum,
             sysName,
             adGenSlotInfoIndex,
             adGenOtnOduIndex,
             adTAeSCUTrapAlarmLevel
             }
     STATUS          current
     DESCRIPTION
             "Path Alarm Indication Signal Alarm - Active"
     --#TYPE      "Warning - AIS-P"
     --#SUMMARY   "AIS-P Alarm - Active"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduAlarms 17}

-- //
  adGenOtnOduMsimClrAlm    NOTIFICATION-TYPE
     OBJECTS       {
             adTrapInformSeqNum,
             sysName,
             adGenSlotInfoIndex,
             adGenOtnOduIndex,
             adTAeSCUTrapAlarmLevel
             }
     STATUS          current
     DESCRIPTION
             "Path Multiplex Structure Identifier Mismatch Alarm - Cleared"
     --#TYPE      "Warning - MISM-P"
     --#SUMMARY   "MISM-P Alarm - Cleared"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduAlarms 18}

  adGenOtnOduMsimActAlm    NOTIFICATION-TYPE
     OBJECTS       {
             adTrapInformSeqNum,
             sysName,
             adGenSlotInfoIndex,
             adGenOtnOduIndex,
             adTAeSCUTrapAlarmLevel
             }
     STATUS          current
     DESCRIPTION
             "Path Multiplex Structure Identifier Mismatch Alarm - Active"
     --#TYPE      "Warning - MISM-P"
     --#SUMMARY   "MISM-P Alarm - Active"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduAlarms 19}

-- //
  adGenOtnOduCsfClrAlm    NOTIFICATION-TYPE
     OBJECTS       {
             adTrapInformSeqNum,
             sysName,
             adGenSlotInfoIndex,
             adGenOtnOduIndex,
             adTAeSCUTrapAlarmLevel
             }
     STATUS          current
     DESCRIPTION
             "Path Client Signal Fail Alarm - Cleared"
     --#TYPE      "Warning - CSF-P"
     --#SUMMARY   "CSF-P Alarm - Cleared"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduAlarms 20}

  adGenOtnOduCsfActAlm    NOTIFICATION-TYPE
     OBJECTS       {
             adTrapInformSeqNum,
             sysName,
             adGenSlotInfoIndex,
             adGenOtnOduIndex,
             adTAeSCUTrapAlarmLevel
             }
     STATUS          current
     DESCRIPTION
             "Path Client Signal Fail Alarm - Active"
     --#TYPE      "Warning - CSF-P"
     --#SUMMARY   "CSF-P Alarm - Active"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduAlarms 21}

-- //
  adGenOtnOduLoomfiClrAlm    NOTIFICATION-TYPE
     OBJECTS       {
             adTrapInformSeqNum,
             sysName,
             adGenSlotInfoIndex,
             adGenOtnOduIndex,
             adTAeSCUTrapAlarmLevel
             }
     STATUS          current
     DESCRIPTION
             "Path Loss Of Opu Multi-Frame Identifier Alarm - Cleared"
     --#TYPE      "Critical - LOOMFI-P"
     --#SUMMARY   "LOOMFI-P Alarm - Cleared"
     --#SUMMARY   "cleared at shelf: %s, Slot: %d Odu: %d"
     --#ARGUMENTS { 1, 2, 3 }
     --#SEVERITY  CRITICAL
     --#GENERIC   6
     --#CATEGORY  "Error Events"
     --#SOURCE_ID "A"
     --#TIMEINDEX 0
     ::= {adGenOtnOduAlarms 22}

  adGenOtnOduLoomfiActAlm    NOTIFICATION-TYPE
     OBJECTS       {
             adTrapInformSeqNum,
             sysName,
             adGenSlotInfoIndex,
             adGenOtnOduIndex,
             adTAeSCUTrapAlarmLevel
             }
     STATUS          current
     DESCRIPTION
             "Path Loss Of Opu Multi-Frame Identifier Alarm - Active"
     --#TYPE      "Critical - LOOMFI-P"
     --#SUMMARY   "LOOMFI-P Alarm - Active"
     --#SUMMARY   "cleared at shelf: %s, Slot: %d Odu: %d"
     --#ARGUMENTS { 1, 2, 3 }
     --#SEVERITY  CRITICAL
     --#GENERIC   6
     --#CATEGORY  "Error Events"
     --#SOURCE_ID "A"
     --#TIMEINDEX 0
     ::= {adGenOtnOduAlarms 23}


-- // OTU PM Threshold 15-Minute Alarms
  adGenOtnOtuPmThres15MinNeEbAlm    NOTIFICATION-TYPE
     OBJECTS       {
             adTrapInformSeqNum,
             sysName,
             ifIndex,
             ifDescr,
             adTAeSCUTrapAlarmLevel
             }
     STATUS          current
     DESCRIPTION
             "15-minute Near-End OTU Errored Blocks (EB-S) Threshold Crossed"
     --#TYPE      "Threshold Error - 15-minute OTU Near-End EB"
     --#SUMMARY   "15-minute Near-End OTU EB Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres15MinAlarms 3}

-- //
  adGenOtnOtuPmThres15MinNeBbeAlm    NOTIFICATION-TYPE
     OBJECTS       {
             adTrapInformSeqNum,
             sysName,
             ifIndex,
             ifDescr,
             adTAeSCUTrapAlarmLevel
             }
     STATUS          current
     DESCRIPTION
             "15-minute Near-End OTU Backward Block Errors (BBE-S) Threshold Crossed"
     --#TYPE      "Threshold Error - 15-minute OTU Near-End BBE"
     --#SUMMARY   "15-minute Near-End OTU BBE Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres15MinAlarms 5}

-- //
  adGenOtnOtuPmThres15MinNeBberAlm    NOTIFICATION-TYPE
     OBJECTS       {
             adTrapInformSeqNum,
             sysName,
             ifIndex,
             ifDescr,
             adTAeSCUTrapAlarmLevel
             }
     STATUS          current
     DESCRIPTION
             "15-minute Near-End OTU Backward Block Error Ratio (BBER-S) Threshold Crossed"
     --#TYPE      "Threshold Error - 15-minute OTU Near-End BBER"
     --#SUMMARY   "15-minute Near-End OTU BBER Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres15MinAlarms 7}

-- //
  adGenOtnOtuPmThres15MinNeEsAlm    NOTIFICATION-TYPE
     OBJECTS       {
             adTrapInformSeqNum,
             sysName,
             ifIndex,
             ifDescr,
             adTAeSCUTrapAlarmLevel
             }
     STATUS          current
     DESCRIPTION
             "15-minute Near-End OTU Errored Seconds (ES-S) Threshold Crossed"
     --#TYPE      "Threshold Error - 15-minute OTU Near-End ES"
     --#SUMMARY   "15-minute Near-End OTU ES Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres15MinAlarms 9}

-- //
  adGenOtnOtuPmThres15MinNeSesAlm    NOTIFICATION-TYPE
     OBJECTS       {
             adTrapInformSeqNum,
             sysName,
             ifIndex,
             ifDescr,
             adTAeSCUTrapAlarmLevel
             }
     STATUS          current
     DESCRIPTION
             "15-minute Near-End OTU Severely Errored Seconds (SES-S) Threshold Crossed"
     --#TYPE      "Threshold Error - 15-minute OTU Near-End SES"
     --#SUMMARY   "15-minute Near-End OTU SES Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres15MinAlarms 11}

-- //
  adGenOtnOtuPmThres15MinNeEsrAlm    NOTIFICATION-TYPE
     OBJECTS       {
             adTrapInformSeqNum,
             sysName,
             ifIndex,
             ifDescr,
             adTAeSCUTrapAlarmLevel
             }
     STATUS          current
     DESCRIPTION
             "15-minute Near-End OTU Errored Second Ratio (ESR-S) Threshold Crossed"
     --#TYPE      "Threshold Error - 15-minute OTU Near-End ESR"
     --#SUMMARY   "15-minute Near-End OTU ESR Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres15MinAlarms 13}

-- //
  adGenOtnOtuPmThres15MinNeSesrAlm    NOTIFICATION-TYPE
     OBJECTS       {
             adTrapInformSeqNum,
             sysName,
             ifIndex,
             ifDescr,
             adTAeSCUTrapAlarmLevel
             }
     STATUS          current
     DESCRIPTION
             "15-minute Near-End OTU Severely Errored Second Ratio (SESR-S) Threshold Crossed"
     --#TYPE      "Threshold Error - 15-minute OTU Near-End SESR"
     --#SUMMARY   "15-minute Near-End OTU SESR Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres15MinAlarms 15}

-- //
  adGenOtnOtuPmThres15MinNeUasAlm    NOTIFICATION-TYPE
     OBJECTS       {
             adTrapInformSeqNum,
             sysName,
             ifIndex,
             ifDescr,
             adTAeSCUTrapAlarmLevel
             }
     STATUS          current
     DESCRIPTION
             "15-minute Near-End OTU Unavailable Seconds (UAS-S) Threshold Crossed"
     --#TYPE      "Threshold Error - 15-minute OTU Near-End UAS"
     --#SUMMARY   "15-minute Near-End OTU UAS Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres15MinAlarms 17}

-- //
  adGenOtnOtuPmThres15MinFeEbAlm    NOTIFICATION-TYPE
     OBJECTS       {
             adTrapInformSeqNum,
             sysName,
             ifIndex,
             ifDescr,
             adTAeSCUTrapAlarmLevel
             }
     STATUS          current
     DESCRIPTION
             "15-minute Far-End OTU Errored Blocks (EB-S) Threshold Crossed"
     --#TYPE      "Threshold Error - 15-minute OTU Far-End EB"
     --#SUMMARY   "15-minute Far-End OTU EB Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres15MinAlarms 19}

-- //
  adGenOtnOtuPmThres15MinFeBbeAlm    NOTIFICATION-TYPE
     OBJECTS       {
             adTrapInformSeqNum,
             sysName,
             ifIndex,
             ifDescr,
             adTAeSCUTrapAlarmLevel
             }
     STATUS          current
     DESCRIPTION
             "15-minute Far-End OTU Backward Block Errors (BBE-S) Threshold Crossed"
     --#TYPE      "Threshold Error - 15-minute OTU Far-End BBE"
     --#SUMMARY   "15-minute Far-End OTU BBE Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres15MinAlarms 21}

-- //
  adGenOtnOtuPmThres15MinFeBberAlm    NOTIFICATION-TYPE
     OBJECTS       {
             adTrapInformSeqNum,
             sysName,
             ifIndex,
             ifDescr,
             adTAeSCUTrapAlarmLevel
             }
     STATUS          current
     DESCRIPTION
             "15-minute Far-End OTU Backward Block Error Ratio (BBER-S) Threshold Crossed"
     --#TYPE      "Threshold Error - 15-minute OTU Far-End BBER"
     --#SUMMARY   "15-minute Far-End OTU BBER Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres15MinAlarms 23}

-- //
  adGenOtnOtuPmThres15MinFeEsAlm    NOTIFICATION-TYPE
     OBJECTS       {
             adTrapInformSeqNum,
             sysName,
             ifIndex,
             ifDescr,
             adTAeSCUTrapAlarmLevel
             }
     STATUS          current
     DESCRIPTION
             "15-minute Far-End OTU Errored Seconds (ES-S) Threshold Crossed"
     --#TYPE      "Threshold Error - 15-minute OTU Far-End ES"
     --#SUMMARY   "15-minute Far-End OTU ES Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres15MinAlarms 25}

-- //
  adGenOtnOtuPmThres15MinFeSesAlm    NOTIFICATION-TYPE
     OBJECTS       {
             adTrapInformSeqNum,
             sysName,
             ifIndex,
             ifDescr,
             adTAeSCUTrapAlarmLevel
             }
     STATUS          current
     DESCRIPTION
             "15-minute Far-End OTU Severely Errored Seconds (SES-S) Threshold Crossed"
     --#TYPE      "Threshold Error - 15-minute OTU Far-End SES"
     --#SUMMARY   "15-minute Far-End OTU SES Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres15MinAlarms 27}

-- //
  adGenOtnOtuPmThres15MinFeEsrAlm    NOTIFICATION-TYPE
     OBJECTS       {
             adTrapInformSeqNum,
             sysName,
             ifIndex,
             ifDescr,
             adTAeSCUTrapAlarmLevel
             }
     STATUS          current
     DESCRIPTION
             "15-minute Far-End OTU Errored Second Ratio (ESR-S) Threshold Crossed"
     --#TYPE      "Threshold Error - 15-minute OTU Far-End ESR"
     --#SUMMARY   "15-minute Far-End OTU ESR Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres15MinAlarms 29}

-- //
  adGenOtnOtuPmThres15MinFeSesrAlm    NOTIFICATION-TYPE
     OBJECTS       {
             adTrapInformSeqNum,
             sysName,
             ifIndex,
             ifDescr,
             adTAeSCUTrapAlarmLevel
             }
     STATUS          current
     DESCRIPTION
             "15-minute Far-End OTU Severely Errored Second Ratio (SESR-S) Threshold Crossed"
     --#TYPE      "Threshold Error - 15-minute OTU Far-End SESR"
     --#SUMMARY   "15-minute Far-End OTU SESR Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres15MinAlarms 31}

-- //
  adGenOtnOtuPmThres15MinFeUasAlm    NOTIFICATION-TYPE
     OBJECTS       {
             adTrapInformSeqNum,
             sysName,
             ifIndex,
             ifDescr,
             adTAeSCUTrapAlarmLevel
             }
     STATUS          current
     DESCRIPTION
             "15-minute Far-End OTU Unavailable Seconds (UAS-S) Threshold Crossed"
     --#TYPE      "Threshold Error - 15-minute OTU Far-End UAS"
     --#SUMMARY   "15-minute Far-End OTU UAS Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres15MinAlarms 33}

-- //
  adGenOtnOtuPmThres15MinFecCorrBitsAlm    NOTIFICATION-TYPE
     OBJECTS       {
             adTrapInformSeqNum,
             sysName,
             ifIndex,
             ifDescr,
             adTAeSCUTrapAlarmLevel
             }
     STATUS          current
     DESCRIPTION
             "15-minute OTU FEC Correct Bits (FEC-CORR-BITS-S) Threshold Crossed"
     --#TYPE      "Threshold Error - 15-minute OTU FEC-CORR-BITS"
     --#SUMMARY   "15-minute OTU FEC-CORR-BITS Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres15MinAlarms 35}

-- //
  adGenOtnOtuPmThres15MinFecCorrOnesAlm    NOTIFICATION-TYPE
     OBJECTS       {
             adTrapInformSeqNum,
             sysName,
             ifIndex,
             ifDescr,
             adTAeSCUTrapAlarmLevel
             }
     STATUS          current
     DESCRIPTION
             "15-minute OTU FEC Correct Ones (FEC-CORR-ONES-S) Threshold Crossed"
     --#TYPE      "Threshold Error - 15-minute OTU FEC-CORR-ONES"
     --#SUMMARY   "15-minute OTU FEC-CORR-ONES Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres15MinAlarms 37}

-- //
  adGenOtnOtuPmThres15MinFecCorrZerosAlm    NOTIFICATION-TYPE
     OBJECTS       {
             adTrapInformSeqNum,
             sysName,
             ifIndex,
             ifDescr,
             adTAeSCUTrapAlarmLevel
             }
     STATUS          current
     DESCRIPTION
             "15-minute OTU FEC Correct Zeros (FEC-CORR-ZEROS-S) Threshold Crossed"
     --#TYPE      "Threshold Error - 15-minute OTU FEC-CORR-ZEROS"
     --#SUMMARY   "15-minute OTU FEC-CORR-ZEROS Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres15MinAlarms 39}

-- //
  adGenOtnOtuPmThres15MinFecUncorrBlksAlm    NOTIFICATION-TYPE
     OBJECTS       {
             adTrapInformSeqNum,
             sysName,
             ifIndex,
             ifDescr,
             adTAeSCUTrapAlarmLevel
             }
     STATUS          current
     DESCRIPTION
             "15-minute OTU FEC Uncorrected Blocks (FEC-BLKS-S) Threshold Crossed"
     --#TYPE      "Threshold Error - 15-minute OTU FEC-BLKS-S"
     --#SUMMARY   "15-minute OTU FEC-BLKS-S Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres15MinAlarms 41}

-- //
  adGenOtnOtuPmThres15MinFecCorrBerAlm    NOTIFICATION-TYPE
     OBJECTS       {
             adTrapInformSeqNum,
             sysName,
             ifIndex,
             ifDescr,
             adTAeSCUTrapAlarmLevel
             }
     STATUS          current
     DESCRIPTION
             "15-minute OTU FEC Corrected Bit Error Rate (FEC-BER-S) Threshold Crossed"
     --#TYPE      "Threshold Error - 15-minute OTU FEC-BER-S"
     --#SUMMARY   "15-minute OTU FEC-BER-S Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres15MinAlarms 43}

-- // OTU PM Threshold 24-Hour Alarms
  adGenOtnOtuPmThres24HrNeEbAlm    NOTIFICATION-TYPE
     OBJECTS       {
             adTrapInformSeqNum,
             sysName,
             ifIndex,
             ifDescr,
             adTAeSCUTrapAlarmLevel
             }
     STATUS          current
     DESCRIPTION
             "24-hour Near-End OTU Errored Blocks (EB-S) Threshold Crossed"
     --#TYPE      "Threshold Error - 24-hour OTU Near-End EB"
     --#SUMMARY   "24-hour Near-End OTU EB Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres24HrAlarms 3}

-- //
  adGenOtnOtuPmThres24HrNeBbeAlm    NOTIFICATION-TYPE
     OBJECTS       {
             adTrapInformSeqNum,
             sysName,
             ifIndex,
             ifDescr,
             adTAeSCUTrapAlarmLevel
             }
     STATUS          current
     DESCRIPTION
             "24-hour Near-End OTU Backward Block Errors (BBE-S) Threshold Crossed"
     --#TYPE      "Threshold Error - 24-hour OTU Near-End BBE"
     --#SUMMARY   "24-hour Near-End OTU BBE Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres24HrAlarms 5}

-- //
  adGenOtnOtuPmThres24HrNeBberAlm    NOTIFICATION-TYPE
     OBJECTS       {
             adTrapInformSeqNum,
             sysName,
             ifIndex,
             ifDescr,
             adTAeSCUTrapAlarmLevel
             }
     STATUS          current
     DESCRIPTION
             "24-hour Near-End OTU Backward Block Error Ratio (BBER-S) Threshold Crossed"
     --#TYPE      "Threshold Error - 24-hour OTU Near-End BBER"
     --#SUMMARY   "24-hour Near-End OTU BBER Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres24HrAlarms 7}

-- //
  adGenOtnOtuPmThres24HrNeEsAlm    NOTIFICATION-TYPE
     OBJECTS       {
             adTrapInformSeqNum,
             sysName,
             ifIndex,
             ifDescr,
             adTAeSCUTrapAlarmLevel
             }
     STATUS          current
     DESCRIPTION
             "24-hour Near-End OTU Errored Seconds (ES-S) Threshold Crossed"
     --#TYPE      "Threshold Error - 24-hour OTU Near-End ES"
     --#SUMMARY   "24-hour Near-End OTU ES Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres24HrAlarms 9}

-- //
  adGenOtnOtuPmThres24HrNeSesAlm    NOTIFICATION-TYPE
     OBJECTS       {
             adTrapInformSeqNum,
             sysName,
             ifIndex,
             ifDescr,
             adTAeSCUTrapAlarmLevel
             }
     STATUS          current
     DESCRIPTION
             "24-hour Near-End OTU Severely Errored Seconds (SES-S) Threshold Crossed"
     --#TYPE      "Threshold Error - 24-hour OTU Near-End SES"
     --#SUMMARY   "24-hour Near-End OTU SES Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres24HrAlarms 11}

-- //
  adGenOtnOtuPmThres24HrNeEsrAlm    NOTIFICATION-TYPE
     OBJECTS       {
             adTrapInformSeqNum,
             sysName,
             ifIndex,
             ifDescr,
             adTAeSCUTrapAlarmLevel
             }
     STATUS          current
     DESCRIPTION
             "24-hour Near-End OTU Errored Second Ratio (ESR-S) Threshold Crossed"
     --#TYPE      "Threshold Error - 24-hour OTU Near-End ESR"
     --#SUMMARY   "24-hour Near-End OTU ESR Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres24HrAlarms 13}

-- //
  adGenOtnOtuPmThres24HrNeSesrAlm    NOTIFICATION-TYPE
     OBJECTS       {
             adTrapInformSeqNum,
             sysName,
             ifIndex,
             ifDescr,
             adTAeSCUTrapAlarmLevel
             }
     STATUS          current
     DESCRIPTION
             "24-hour Near-End OTU Severely Errored Second Ratio (SESR-S) Threshold Crossed"
     --#TYPE      "Threshold Error - 24-hour OTU Near-End SESR"
     --#SUMMARY   "24-hour Near-End OTU SESR Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres24HrAlarms 15}

-- //
  adGenOtnOtuPmThres24HrNeUasAlm    NOTIFICATION-TYPE
     OBJECTS       {
             adTrapInformSeqNum,
             sysName,
             ifIndex,
             ifDescr,
             adTAeSCUTrapAlarmLevel
             }
     STATUS          current
     DESCRIPTION
             "24-hour Near-End OTU Unavailable Seconds (UAS-S) Threshold Crossed"
     --#TYPE      "Threshold Error - 24-hour OTU Near-End UAS"
     --#SUMMARY   "24-hour Near-End OTU UAS Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres24HrAlarms 17}

-- //
  adGenOtnOtuPmThres24HrFeEbAlm    NOTIFICATION-TYPE
     OBJECTS       {
             adTrapInformSeqNum,
             sysName,
             ifIndex,
             ifDescr,
             adTAeSCUTrapAlarmLevel
             }
     STATUS          current
     DESCRIPTION
             "24-hour Far-End OTU Errored Blocks (EB-S) Threshold Crossed"
     --#TYPE      "Threshold Error - 24-hour OTU Far-End EB"
     --#SUMMARY   "24-hour Far-End OTU EB Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres24HrAlarms 19}

-- //
  adGenOtnOtuPmThres24HrFeBbeAlm    NOTIFICATION-TYPE
     OBJECTS       {
             adTrapInformSeqNum,
             sysName,
             ifIndex,
             ifDescr,
             adTAeSCUTrapAlarmLevel
             }
     STATUS          current
     DESCRIPTION
             "24-hour Far-End OTU Backward Block Errors (BBE-S) Threshold Crossed"
     --#TYPE      "Threshold Error - 24-hour OTU Far-End BBE"
     --#SUMMARY   "24-hour Far-End OTU BBE Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres24HrAlarms 21}

-- //
  adGenOtnOtuPmThres24HrFeBberAlm    NOTIFICATION-TYPE
     OBJECTS       {
             adTrapInformSeqNum,
             sysName,
             ifIndex,
             ifDescr,
             adTAeSCUTrapAlarmLevel
             }
     STATUS          current
     DESCRIPTION
             "24-hour Far-End OTU Backward Block Error Ratio (BBER-S) Threshold Crossed"
     --#TYPE      "Threshold Error - 24-hour OTU Far-End BBER"
     --#SUMMARY   "24-hour Far-End OTU BBER Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres24HrAlarms 23}

-- //
  adGenOtnOtuPmThres24HrFeEsAlm    NOTIFICATION-TYPE
     OBJECTS       {
             adTrapInformSeqNum,
             sysName,
             ifIndex,
             ifDescr,
             adTAeSCUTrapAlarmLevel
             }
     STATUS          current
     DESCRIPTION
             "24-hour Far-End OTU Errored Seconds (ES-S) Threshold Crossed"
     --#TYPE      "Threshold Error - 24-hour OTU Far-End ES"
     --#SUMMARY   "24-hour Far-End OTU ES Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres24HrAlarms 25}

-- //
  adGenOtnOtuPmThres24HrFeSesAlm    NOTIFICATION-TYPE
     OBJECTS       {
             adTrapInformSeqNum,
             sysName,
             ifIndex,
             ifDescr,
             adTAeSCUTrapAlarmLevel
             }
     STATUS          current
     DESCRIPTION
             "24-hour Far-End OTU Severely Errored Seconds (SES-S) Threshold Crossed"
     --#TYPE      "Threshold Error - 24-hour OTU Far-End SES"
     --#SUMMARY   "24-hour Far-End OTU SES Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres24HrAlarms 27}

-- //
  adGenOtnOtuPmThres24HrFeEsrAlm    NOTIFICATION-TYPE
     OBJECTS       {
             adTrapInformSeqNum,
             sysName,
             ifIndex,
             ifDescr,
             adTAeSCUTrapAlarmLevel
             }
     STATUS          current
     DESCRIPTION
             "24-hour Far-End OTU Errored Second Ratio (ESR-S) Threshold Crossed"
     --#TYPE      "Threshold Error - 24-hour OTU Far-End ESR"
     --#SUMMARY   "24-hour Far-End OTU ESR Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres24HrAlarms 29}

-- //
  adGenOtnOtuPmThres24HrFeSesrAlm    NOTIFICATION-TYPE
     OBJECTS       {
             adTrapInformSeqNum,
             sysName,
             ifIndex,
             ifDescr,
             adTAeSCUTrapAlarmLevel
             }
     STATUS          current
     DESCRIPTION
             "24-hour Far-End OTU Severely Errored Second Ratio (SESR-S) Threshold Crossed"
     --#TYPE      "Threshold Error - 24-hour OTU Far-End SESR"
     --#SUMMARY   "24-hour Far-End OTU SESR Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres24HrAlarms 31}

-- //
  adGenOtnOtuPmThres24HrFeUasAlm    NOTIFICATION-TYPE
     OBJECTS       {
             adTrapInformSeqNum,
             sysName,
             ifIndex,
             ifDescr,
             adTAeSCUTrapAlarmLevel
             }
     STATUS          current
     DESCRIPTION
             "24-hour Far-End OTU Unavailable Seconds (UAS-S) Threshold Crossed"
     --#TYPE      "Threshold Error - 24-hour OTU Far-End UAS"
     --#SUMMARY   "24-hour Far-End OTU UAS Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres24HrAlarms 33}

-- //
  adGenOtnOtuPmThres24HrFecCorrBitsAlm    NOTIFICATION-TYPE
     OBJECTS       {
             adTrapInformSeqNum,
             sysName,
             ifIndex,
             ifDescr,
             adTAeSCUTrapAlarmLevel
             }
     STATUS          current
     DESCRIPTION
             "24-hour OTU FEC Correct Bits (FEC-CORR-BITS-S) Threshold Crossed"
     --#TYPE      "Threshold Error - 24-hour OTU FEC-CORR-BITS"
     --#SUMMARY   "24-hour OTU FEC-CORR-BITS Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres24HrAlarms 35}

-- //
  adGenOtnOtuPmThres24HrFecCorrOnesAlm    NOTIFICATION-TYPE
     OBJECTS       {
             adTrapInformSeqNum,
             sysName,
             ifIndex,
             ifDescr,
             adTAeSCUTrapAlarmLevel
             }
     STATUS          current
     DESCRIPTION
             "24-hour OTU FEC Correct Ones (FEC-CORR-ONES-S) Threshold Crossed"
     --#TYPE      "Threshold Error - 24-hour OTU FEC-CORR-ONES"
     --#SUMMARY   "24-hour OTU FEC-CORR-ONES Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres24HrAlarms 37}

-- //
  adGenOtnOtuPmThres24HrFecCorrZerosAlm    NOTIFICATION-TYPE
     OBJECTS       {
             adTrapInformSeqNum,
             sysName,
             ifIndex,
             ifDescr,
             adTAeSCUTrapAlarmLevel
             }
     STATUS          current
     DESCRIPTION
             "24-hour OTU FEC Correct Zeros (FEC-CORR-ZEROS-S) Threshold Crossed"
     --#TYPE      "Threshold Error - 24-hour OTU FEC-CORR-ZEROS"
     --#SUMMARY   "24-hour OTU FEC-CORR-ZEROS Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres24HrAlarms 39}

-- //
  adGenOtnOtuPmThres24HrFecUncorrBlksAlm    NOTIFICATION-TYPE
     OBJECTS       {
             adTrapInformSeqNum,
             sysName,
             ifIndex,
             ifDescr,
             adTAeSCUTrapAlarmLevel
             }
     STATUS          current
     DESCRIPTION
             "24-hour OTU FEC Uncorrect Blocks (FEC-BLKS-S) Threshold Crossed"
     --#TYPE      "Threshold Error - 24-hour OTU FEC-BLKS-S"
     --#SUMMARY   "24-hour OTU FEC-BLKS-S Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres24HrAlarms 41}

-- //
  adGenOtnOtuPmThres24HrFecCorrBerAlm    NOTIFICATION-TYPE
     OBJECTS       {
             adTrapInformSeqNum,
             sysName,
             ifIndex,
             ifDescr,
             adTAeSCUTrapAlarmLevel
             }
     STATUS          current
     DESCRIPTION
             "24-hour OTU FEC Corrected Bit Error Rate (FEC-BER-S) Threshold Crossed"
     --#TYPE      "Threshold Error - 24-hour OTU FEC-BER-S"
     --#SUMMARY   "24-hour OTU FEC-BER-S Threshold Crossed"
     --#SUMMARY   "cleared at shelf: %s, Interface: %d %s"
     --#ARGUMENTS { 1, 2, 3 }
     --#SEVERITY  WARNING
     --#GENERIC   6
     --#CATEGORY  "Error Events"
     --#SOURCE_ID "A"
     --#TIMEINDEX 0
     ::= {adGenOtnOtuPmThres24HrAlarms 43}

-- // ODU PM Threshold 15-Minute Alarms
  adGenOtnOduPmThres15MinNeEbAlm    NOTIFICATION-TYPE
     OBJECTS       {
             adTrapInformSeqNum,
             sysName,
             adGenSlotInfoIndex,
             adGenOtnOduIndex,
             adTAeSCUTrapAlarmLevel
             }
     STATUS          current
     DESCRIPTION
             "15-minute Near-End OTU Errored Blocks (EB-P) Threshold Crossed"
     --#TYPE      "Threshold Error - 15-minute Near-End OTU EB"
     --#SUMMARY   "15-minute Near-End OTU EB Threshold Crossed"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduPmThres15MinAlarms 3}

-- //
  adGenOtnOduPmThres15MinNeBbeAlm    NOTIFICATION-TYPE
     OBJECTS       {
             adTrapInformSeqNum,
             sysName,
             adGenSlotInfoIndex,
             adGenOtnOduIndex,
             adTAeSCUTrapAlarmLevel
             }
     STATUS          current
     DESCRIPTION
             "15-minute Near-End OTU Backward Block Errors (BBE-P) Threshold Crossed"
     --#TYPE      "Threshold Error - 15-minute Near-End OTU BBE"
     --#SUMMARY   "15-minute Near-End OTU BBE Threshold Crossed"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduPmThres15MinAlarms 5}

-- //
  adGenOtnOduPmThres15MinNeBberAlm    NOTIFICATION-TYPE
     OBJECTS       {
             adTrapInformSeqNum,
             sysName,
             adGenSlotInfoIndex,
             adGenOtnOduIndex,
             adTAeSCUTrapAlarmLevel
             }
     STATUS          current
     DESCRIPTION
             "15-minute Near-End OTU Backward Block Error Ratio (BBER-P) Threshold Crossed"
     --#TYPE      "Threshold Error - 15-minute Near-End OTU BBER"
     --#SUMMARY   "15-minute Near-End OTU BBER Threshold Crossed"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduPmThres15MinAlarms 7}

-- //
  adGenOtnOduPmThres15MinNeEsAlm    NOTIFICATION-TYPE
     OBJECTS       {
             adTrapInformSeqNum,
             sysName,
             adGenSlotInfoIndex,
             adGenOtnOduIndex,
             adTAeSCUTrapAlarmLevel
             }
     STATUS          current
     DESCRIPTION
             "15-minute Near-End OTU Errored Seconds (ES-P) Threshold Crossed"
     --#TYPE      "Threshold Error - 15-minute Near-End OTU ES"
     --#SUMMARY   "15-minute Near-End OTU ES Threshold Crossed"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduPmThres15MinAlarms 9}

-- //
  adGenOtnOduPmThres15MinNeSesAlm    NOTIFICATION-TYPE
     OBJECTS       {
             adTrapInformSeqNum,
             sysName,
             adGenSlotInfoIndex,
             adGenOtnOduIndex,
             adTAeSCUTrapAlarmLevel
             }
     STATUS          current
     DESCRIPTION
             "15-minute Near-End OTU Severely Errored Seconds (SES-P) Threshold Crossed"
     --#TYPE      "Threshold Error - 15-minute Near-End OTU SES"
     --#SUMMARY   "15-minute Near-End OTU SES Threshold Crossed"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduPmThres15MinAlarms 11}

-- //
  adGenOtnOduPmThres15MinNeEsrAlm    NOTIFICATION-TYPE
     OBJECTS       {
             adTrapInformSeqNum,
             sysName,
             adGenSlotInfoIndex,
             adGenOtnOduIndex,
             adTAeSCUTrapAlarmLevel
             }
     STATUS          current
     DESCRIPTION
             "15-minute Near-End OTU Errored Second Ratio (ESR-P) Threshold Crossed"
     --#TYPE      "Threshold Error - 15-minute Near-End OTU ESR"
     --#SUMMARY   "15-minute Near-End OTU ESR Threshold Crossed"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduPmThres15MinAlarms 13}

-- //
  adGenOtnOduPmThres15MinNeSesrAlm    NOTIFICATION-TYPE
     OBJECTS       {
             adTrapInformSeqNum,
             sysName,
             adGenSlotInfoIndex,
             adGenOtnOduIndex,
             adTAeSCUTrapAlarmLevel
             }
     STATUS          current
     DESCRIPTION
             "15-minute Near-End OTU Severely Errored Second Ratio (SESR-P) Threshold Crossed"
     --#TYPE      "Threshold Error - 15-minute Near-End OTU SESR"
     --#SUMMARY   "15-minute Near-End OTU SESR Threshold Crossed"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduPmThres15MinAlarms 15}

-- //
  adGenOtnOduPmThres15MinNeUasAlm    NOTIFICATION-TYPE
     OBJECTS       {
             adTrapInformSeqNum,
             sysName,
             adGenSlotInfoIndex,
             adGenOtnOduIndex,
             adTAeSCUTrapAlarmLevel
             }
     STATUS          current
     DESCRIPTION
             "15-minute Near-End OTU Unavailable Seconds (UAS-P) Threshold Crossed"
     --#TYPE      "Threshold Error - 15-minute Near-End OTU UAS"
     --#SUMMARY   "15-minute Near-End OTU UAS Threshold Crossed"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduPmThres15MinAlarms 17}

-- //
  adGenOtnOduPmThres15MinFeEbAlm    NOTIFICATION-TYPE
     OBJECTS       {
             adTrapInformSeqNum,
             sysName,
             adGenSlotInfoIndex,
             adGenOtnOduIndex,
             adTAeSCUTrapAlarmLevel
             }
     STATUS          current
     DESCRIPTION
             "15-minute Far-End OTU Errored Blocks (EB-P) Threshold Crossed"
     --#TYPE      "Threshold Error - 15-minute Far-End OTU EB"
     --#SUMMARY   "15-minute Far-End OTU EB Threshold Crossed"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduPmThres15MinAlarms 19}

-- //
  adGenOtnOduPmThres15MinFeBbeAlm    NOTIFICATION-TYPE
     OBJECTS       {
             adTrapInformSeqNum,
             sysName,
             adGenSlotInfoIndex,
             adGenOtnOduIndex,
             adTAeSCUTrapAlarmLevel
             }
     STATUS          current
     DESCRIPTION
             "15-minute Far-End OTU Backward Block Errors (BBE-P) Threshold Crossed"
     --#TYPE      "Threshold Error - 15-minute Far-End OTU BBE"
     --#SUMMARY   "15-minute Far-End OTU BBE Threshold Crossed"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduPmThres15MinAlarms 21}

-- //
  adGenOtnOduPmThres15MinFeBberAlm    NOTIFICATION-TYPE
     OBJECTS       {
             adTrapInformSeqNum,
             sysName,
             adGenSlotInfoIndex,
             adGenOtnOduIndex,
             adTAeSCUTrapAlarmLevel
             }
     STATUS          current
     DESCRIPTION
             "15-minute Far-End OTU Backward Block Error Ratio (BBER-P) Threshold Crossed"
     --#TYPE      "Threshold Error - 15-minute Far-End OTU BBER"
     --#SUMMARY   "15-minute Far-End OTU BBER Threshold Crossed"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduPmThres15MinAlarms 23}

-- //
  adGenOtnOduPmThres15MinFeEsAlm    NOTIFICATION-TYPE
     OBJECTS       {
             adTrapInformSeqNum,
             sysName,
             adGenSlotInfoIndex,
             adGenOtnOduIndex,
             adTAeSCUTrapAlarmLevel
             }
     STATUS          current
     DESCRIPTION
             "15-minute Far-End OTU Errored Seconds (ES-P) Threshold Crossed"
     --#TYPE      "Threshold Error - 15-minute Far-End OTU ES"
     --#SUMMARY   "15-minute Far-End OTU ES Threshold Crossed"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduPmThres15MinAlarms 25}

-- //
  adGenOtnOduPmThres15MinFeSesAlm    NOTIFICATION-TYPE
     OBJECTS       {
             adTrapInformSeqNum,
             sysName,
             adGenSlotInfoIndex,
             adGenOtnOduIndex,
             adTAeSCUTrapAlarmLevel
             }
     STATUS          current
     DESCRIPTION
             "15-minute Far-End OTU Severely Errored Seconds (SES-P) Threshold Crossed"
     --#TYPE      "Threshold Error - 15-minute Far-End OTU SES"
     --#SUMMARY   "15-minute Far-End OTU SES Threshold Crossed"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduPmThres15MinAlarms 27}

-- //
  adGenOtnOduPmThres15MinFeEsrAlm    NOTIFICATION-TYPE
     OBJECTS       {
             adTrapInformSeqNum,
             sysName,
             adGenSlotInfoIndex,
             adGenOtnOduIndex,
             adTAeSCUTrapAlarmLevel
             }
     STATUS          current
     DESCRIPTION
             "15-minute Far-End OTU Errored Second Ratio (ESR-P) Threshold Crossed"
     --#TYPE      "Threshold Error - 15-minute Far-End OTU ESR"
     --#SUMMARY   "15-minute Far-End OTU ESR Threshold Crossed"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduPmThres15MinAlarms 29}

-- //
  adGenOtnOduPmThres15MinFeSesrAlm    NOTIFICATION-TYPE
     OBJECTS       {
             adTrapInformSeqNum,
             sysName,
             adGenSlotInfoIndex,
             adGenOtnOduIndex,
             adTAeSCUTrapAlarmLevel
             }
     STATUS          current
     DESCRIPTION
             "15-minute Far-End OTU Severely Errored Second Ratio (SESR-P) Threshold Crossed"
     --#TYPE      "Threshold Error - 15-minute Far-End OTU SESR"
     --#SUMMARY   "15-minute Far-End OTU SESR Threshold Crossed"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduPmThres15MinAlarms 31}

-- //
  adGenOtnOduPmThres15MinFeUasAlm    NOTIFICATION-TYPE
     OBJECTS       {
             adTrapInformSeqNum,
             sysName,
             adGenSlotInfoIndex,
             adGenOtnOduIndex,
             adTAeSCUTrapAlarmLevel
             }
     STATUS          current
     DESCRIPTION
             "15-minute Far-End OTU Unavailable Seconds (UAS-P) Threshold Crossed"
     --#TYPE      "Threshold Error - 15-minute Far-End OTU UAS"
     --#SUMMARY   "15-minute Far-End OTU UAS Threshold Crossed"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduPmThres15MinAlarms 33}

-- // ODU PM Threshold 24-Hour Alarms
  adGenOtnOduPmThres24HrNeEbAlm    NOTIFICATION-TYPE
     OBJECTS       {
             adTrapInformSeqNum,
             sysName,
             adGenSlotInfoIndex,
             adGenOtnOduIndex,
             adTAeSCUTrapAlarmLevel
             }
     STATUS          current
     DESCRIPTION
             "24-hour Near-End OTU Errored Blocks (EB-P) Threshold Crossed"
     --#TYPE      "Threshold Error - 24-hour Near-End OTU EB"
     --#SUMMARY   "24-hour Near-End OTU EB Threshold Crossed"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduPmThres24HrAlarms 3}

-- //
  adGenOtnOduPmThres24HrNeBbeAlm    NOTIFICATION-TYPE
     OBJECTS       {
             adTrapInformSeqNum,
             sysName,
             adGenSlotInfoIndex,
             adGenOtnOduIndex,
             adTAeSCUTrapAlarmLevel
             }
     STATUS          current
     DESCRIPTION
             "24-hour Near-End OTU Backward Block Errors (BBE-P) Threshold Crossed"
     --#TYPE      "Threshold Error - 24-hour Near-End OTU BBE"
     --#SUMMARY   "24-hour Near-End OTU BBE Threshold Crossed"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduPmThres24HrAlarms 5}

-- //
  adGenOtnOduPmThres24HrNeBberAlm    NOTIFICATION-TYPE
     OBJECTS       {
             adTrapInformSeqNum,
             sysName,
             adGenSlotInfoIndex,
             adGenOtnOduIndex,
             adTAeSCUTrapAlarmLevel
             }
     STATUS          current
     DESCRIPTION
             "24-hour Near-End OTU Backward Block Error Ratio (BBER-P) Threshold Crossed"
     --#TYPE      "Threshold Error - 24-hour Near-End OTU BBER"
     --#SUMMARY   "24-hour Near-End OTU BBER Threshold Crossed"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduPmThres24HrAlarms 7}

-- //
  adGenOtnOduPmThres24HrNeEsAlm    NOTIFICATION-TYPE
     OBJECTS       {
             adTrapInformSeqNum,
             sysName,
             adGenSlotInfoIndex,
             adGenOtnOduIndex,
             adTAeSCUTrapAlarmLevel
             }
     STATUS          current
     DESCRIPTION
             "24-hour Near-End OTU Errored Seconds (ES-P) Threshold Crossed"
     --#TYPE      "Threshold Error - 24-hour Near-End OTU ES"
     --#SUMMARY   "24-hour Near-End OTU ES Threshold Crossed"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduPmThres24HrAlarms 9}

-- //
  adGenOtnOduPmThres24HrNeSesAlm    NOTIFICATION-TYPE
     OBJECTS       {
             adTrapInformSeqNum,
             sysName,
             adGenSlotInfoIndex,
             adGenOtnOduIndex,
             adTAeSCUTrapAlarmLevel
             }
     STATUS          current
     DESCRIPTION
             "24-hour Near-End OTU Severely Errored Seconds (SES-P) Threshold Crossed"
     --#TYPE      "Threshold Error - 24-hour Near-End OTU SES"
     --#SUMMARY   "24-hour Near-End OTU SES Threshold Crossed"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduPmThres24HrAlarms 11}

-- //
  adGenOtnOduPmThres24HrNeEsrAlm    NOTIFICATION-TYPE
     OBJECTS       {
             adTrapInformSeqNum,
             sysName,
             adGenSlotInfoIndex,
             adGenOtnOduIndex,
             adTAeSCUTrapAlarmLevel
             }
     STATUS          current
     DESCRIPTION
             "24-hour Near-End OTU Errored Second Ratio (ESR-P) Threshold Crossed"
     --#TYPE      "Threshold Error - 24-hour Near-End OTU ESR"
     --#SUMMARY   "24-hour Near-End OTU SESESRThreshold Crossed"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduPmThres24HrAlarms 13}

-- //
  adGenOtnOduPmThres24HrNeSesrAlm    NOTIFICATION-TYPE
     OBJECTS       {
             adTrapInformSeqNum,
             sysName,
             adGenSlotInfoIndex,
             adGenOtnOduIndex,
             adTAeSCUTrapAlarmLevel
             }
     STATUS          current
     DESCRIPTION
             "24-hour Near-End OTU Severely Errored Second Ratio (SESR-P) Threshold Crossed"
     --#TYPE      "Threshold Error - 24-hour Near-End OTU SESR"
     --#SUMMARY   "24-hour Near-End OTU SESR Threshold Crossed"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduPmThres24HrAlarms 15}

-- //
  adGenOtnOduPmThres24HrNeUasAlm    NOTIFICATION-TYPE
     OBJECTS       {
             adTrapInformSeqNum,
             sysName,
             adGenSlotInfoIndex,
             adGenOtnOduIndex,
             adTAeSCUTrapAlarmLevel
             }
     STATUS          current
     DESCRIPTION
             "24-hour Near-End OTU Unavailable Seconds (UAS-P) Threshold Crossed"
     --#TYPE      "Threshold Error - 24-hour Near-End OTU UAS"
     --#SUMMARY   "24-hour Near-End OTU UAS Threshold Crossed"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduPmThres24HrAlarms 17}

-- //
  adGenOtnOduPmThres24HrFeEbAlm    NOTIFICATION-TYPE
     OBJECTS       {
             adTrapInformSeqNum,
             sysName,
             adGenSlotInfoIndex,
             adGenOtnOduIndex,
             adTAeSCUTrapAlarmLevel
             }
     STATUS          current
     DESCRIPTION
             "24-hour Far-End OTU Errored Blocks (EB-P) Threshold Crossed"
     --#TYPE      "Threshold Error - 24-hour Far-End OTU EB"
     --#SUMMARY   "24-hour Far-End OTU EB Threshold Crossed"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduPmThres24HrAlarms 19}

-- //
  adGenOtnOduPmThres24HrFeBbeAlm    NOTIFICATION-TYPE
     OBJECTS       {
             adTrapInformSeqNum,
             sysName,
             adGenSlotInfoIndex,
             adGenOtnOduIndex,
             adTAeSCUTrapAlarmLevel
             }
     STATUS          current
     DESCRIPTION
             "24-hour Far-End OTU Backward Block Errors (BBE-P) Threshold Crossed"
     --#TYPE      "Threshold Error - 24-hour Far-End OTU BBE"
     --#SUMMARY   "24-hour Far-End OTU BBE Threshold Crossed"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduPmThres24HrAlarms 21}

-- //
  adGenOtnOduPmThres24HrFeBberAlm    NOTIFICATION-TYPE
     OBJECTS       {
             adTrapInformSeqNum,
             sysName,
             adGenSlotInfoIndex,
             adGenOtnOduIndex,
             adTAeSCUTrapAlarmLevel
             }
     STATUS          current
     DESCRIPTION
             "24-hour Far-End OTU Backward Block Error Ratio (BBER-P) Threshold Crossed"
     --#TYPE      "Threshold Error - 24-hour Far-End OTU BBER"
     --#SUMMARY   "24-hour Far-End OTU BBER Threshold Crossed"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduPmThres24HrAlarms 23}

-- //
  adGenOtnOduPmThres24HrFeEsAlm    NOTIFICATION-TYPE
     OBJECTS       {
             adTrapInformSeqNum,
             sysName,
             adGenSlotInfoIndex,
             adGenOtnOduIndex,
             adTAeSCUTrapAlarmLevel
             }
     STATUS          current
     DESCRIPTION
             "24-hour Far-End OTU Errored Seconds (ES-P) Threshold Crossed"
     --#TYPE      "Threshold Error - 24-hour Far-End OTU ES"
     --#SUMMARY   "24-hour Far-End OTU ES Threshold Crossed"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduPmThres24HrAlarms 25}

-- //
  adGenOtnOduPmThres24HrFeSesAlm    NOTIFICATION-TYPE
     OBJECTS       {
             adTrapInformSeqNum,
             sysName,
             adGenSlotInfoIndex,
             adGenOtnOduIndex,
             adTAeSCUTrapAlarmLevel
             }
     STATUS          current
     DESCRIPTION
             "24-hour Far-End OTU Severely Errored Seconds (SES-P) Threshold Crossed"
     --#TYPE      "Threshold Error - 24-hour Far-End OTU SES"
     --#SUMMARY   "24-hour Far-End OTU SES Threshold Crossed"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduPmThres24HrAlarms 27}

-- //
  adGenOtnOduPmThres24HrFeEsrAlm    NOTIFICATION-TYPE
     OBJECTS       {
             adTrapInformSeqNum,
             sysName,
             adGenSlotInfoIndex,
             adGenOtnOduIndex,
             adTAeSCUTrapAlarmLevel
             }
     STATUS          current
     DESCRIPTION
             "24-hour Far-End OTU Errored Second Ratio (ESR-P) Threshold Crossed"
     --#TYPE      "Threshold Error - 24-hour Far-End OTU ESR"
     --#SUMMARY   "24-hour Far-End OTU ESR Threshold Crossed"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduPmThres24HrAlarms 29}

-- //
  adGenOtnOduPmThres24HrFeSesrAlm    NOTIFICATION-TYPE
     OBJECTS       {
             adTrapInformSeqNum,
             sysName,
             adGenSlotInfoIndex,
             adGenOtnOduIndex,
             adTAeSCUTrapAlarmLevel
             }
     STATUS          current
     DESCRIPTION
             "24-hour Far-End OTU Severely Errored Second Ratio (SESR-P) Threshold Crossed"
     --#TYPE      "Threshold Error - 24-hour Far-End OTU SESR"
     --#SUMMARY   "24-hour Far-End OTU SESR Threshold Crossed"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduPmThres24HrAlarms 31}

-- //
  adGenOtnOduPmThres24HrFeUasAlm    NOTIFICATION-TYPE
     OBJECTS       {
             adTrapInformSeqNum,
             sysName,
             adGenSlotInfoIndex,
             adGenOtnOduIndex,
             adTAeSCUTrapAlarmLevel
             }
     STATUS          current
     DESCRIPTION
             "24-hour Far-End OTU Unavailable Seconds (UAS-P) Threshold Crossed"
     --#TYPE      "Threshold Error - 24-hour Far-End OTU UAS"
     --#SUMMARY   "24-hour Far-End OTU UAS Threshold Crossed"
     --#SUMMARY   "cleared at shelf: %s, Slot: %d Odu: %d"
     --#ARGUMENTS { 1, 2, 3 }
     --#SEVERITY  WARNING
     --#GENERIC   6
     --#CATEGORY  "Error Events"
     --#SOURCE_ID "A"
     --#TIMEINDEX 0
     ::= {adGenOtnOduPmThres24HrAlarms 33}
END

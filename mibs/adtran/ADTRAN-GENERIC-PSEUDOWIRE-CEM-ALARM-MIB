ADTRAN-GENERIC-PSEUDOWIRE-CEM-ALARM-MIB  DEFINITIONS ::= BEGIN

   -- TITLE:      Total Access 5000 Pseudowire Circuit Emulation Alarm MIB
   -- PRODUCT:    1187500E1, 1187501G1, 1187502F1, 1188801G1, TBD.
   -- VERSION:    1.0
   -- DATE:       10/07/09 (yy/mm/dd)
   -- AUTHOR:     Shobana Rao <shobana.rao@adtran.com>
   -- SNMP:       SNMPv2
   -- MIB ARC:    adtran.adShared.adGenCndSystem.adGenPseudowireCEMMgmt.adGenPseudowireCEMAlarms

   -- DESCRIPTION:
         -- Created based upon genTa5kPseudowireAlarm.mi2
         -- to support TA5000 pseudowire circuit emulation alarms for the
         -- 1187500E1 (GPON OLT)
         -- 1187501G1 (GPON OLT)
         -- 1187502F1 (GPON OLT)
         -- 1188801G1 (32-Port E1 CEM)

   -- HISTORY: (yy/mm/dd)
         -- 10/07/09 - Created based upon the ADTRAN-GENERIC-TA5000-PSEUDOWIRE-ALARM-MIB.
         -- 02/28/11 - Changed the severity of Far End LOS and Far End LPS alarms to WARNING.
         -- "DO NOT MAKE HISTORY COMMENTS HERE!!!! Revision history now in REVISION/DESCRIPTION clauses below"

   -- NOTES:
         -- Created based upon the
         -- ADTRAN-GENERIC-TA5000-PSEUDOWIRE-ALARM-MIB to support TA5000 Pseudowire CEM alarms.
         -- Please consult product specific documentation and MIB's for
         -- further configuration details and considerations.
         --
         -- Far End Notifications are represented by the locally affected channel.

   IMPORTS
            MODULE-IDENTITY,
	    OBJECT-TYPE,
            NOTIFICATION-TYPE
               FROM SNMPv2-SMI

            adTrapInformSeqNum
               FROM ADTRAN-GENTRAPINFORM-MIB

            sysName
               FROM SNMPv2-MIB

            TruthValue
            	FROM SNMPv2-TC

            adGenSlotInfoIndex
               FROM ADTRAN-GENSLOT-MIB

            ifIndex
               FROM IF-MIB

            adGenPseudowireCEMAlarmsID, adGenPseudowireCEMEvents, adGenPseudowireCEMAlarmProv, adGenPseudowireCEMPhysicalPortIfIndex
               FROM ADTRAN-GENERIC-PSEUDOWIRE-CEM-MGMT-MIB;

-- Module ID ==================================================================

   adGenPseudowireCEMAlarmModuleIdentity         MODULE-IDENTITY
         LAST-UPDATED    "201811201700Z"
         ORGANIZATION
            "ADTRAN, Inc."
         CONTACT-INFO
            "CND Tech Support
                Postal: ADTRAN, Inc.
                        901 Explorer Blvd.
                        Huntsville, AL  35806
                        Tel: +1 800 726-8663
                        Fax: +1 256 963 6217
                        E-mail: support@adtran.com"
         DESCRIPTION
            "Total Access 5000 Pseudowire Circuit Emulation Alarm MIB"

         REVISION "201811201700Z"
            DESCRIPTION "Added the adGenPseudowireCEMPhysicalPortIfIndex varbind to the alarms."

         REVISION "201407011700Z"
            DESCRIPTION "Changed severity for the Far End LOS Alarm from WARNING to MAJOR"

         REVISION "201205181120Z"
            DESCRIPTION "Added provisioning OID for Far End LOS Alarm"

         ::= { adGenPseudowireCEMAlarmsID 1 }

-- OBJECT IDENTIFIERS - Pseudowire CEM Alarms =====================================

adGenPseudowireCEMAlarmFarEndLOSClear    NOTIFICATION-TYPE
   OBJECTS  {
                adTrapInformSeqNum,
                sysName,                   -- Shelf
                adGenSlotInfoIndex,        -- Slot
                ifIndex,
                adGenPseudowireCEMPhysicalPortIfIndex    -- T1/E1 Port
            }
    STATUS          current
    DESCRIPTION     "Indicates that the Pseudowire Far-End Loss Of Signal has been cleared."

    --#TYPE         "Status - Far End LOS Cleared"
    --#SUMMARY      "Pseudowire Far End LOS"
    --#SUMMARY      "Cleared at shelf: %s, slot: %d, interface %d"
    --#ARGUMENTS    {1,2,3}
    --#SEVERITY     MAJOR
    --#GENERIC      6
    --#CATEGORY     "Alarm Events"
    --#SOURCE_ID    "A"
    --#TIMEINDEX    0
    ::= {adGenPseudowireCEMEvents 1}

adGenPseudowireCEMAlarmFarEndLOSActive   NOTIFICATION-TYPE
   OBJECTS  {
                adTrapInformSeqNum,
                sysName,                    -- Shelf
                adGenSlotInfoIndex,         -- Slot
                ifIndex,
                adGenPseudowireCEMPhysicalPortIfIndex    -- T1/E1 Port
            }
    STATUS          current
    DESCRIPTION     "Indicates that the Pseudowire Far-End Loss Of Signal alarm active."

    --#TYPE         "Status - Far End LOS Active"
    --#SUMMARY      "Pseudowire Far End LOS"
    --#SUMMARY      "Activated at shelf: %s, slot: %d, interface %d"
    --#ARGUMENTS    {1,2,3}
    --#SEVERITY     MAJOR
    --#GENERIC      6
    --#CATEGORY     "Alarm Events"
    --#SOURCE_ID    "A"
    --#TIMEINDEX    0
    ::= {adGenPseudowireCEMEvents 2}

adGenPseudowireCEMAlarmNearEndLPSClear    NOTIFICATION-TYPE
   OBJECTS  {
               adTrapInformSeqNum,
               sysName,                     -- Shelf
               adGenSlotInfoIndex,          -- Slot
               ifIndex,
               adGenPseudowireCEMPhysicalPortIfIndex    -- T1/E1 Port
            }
    STATUS          current
    DESCRIPTION     "Indicates that the Pseudowire Near-End Loss of Packet State has been cleared."

    --#TYPE         "Status - Near End Loss of Packet State Cleared"
    --#SUMMARY      "Pseudowire Near End Loss of Packet State"
    --#SUMMARY      "Cleared at shelf: %s, slot: %d, interface %d"
    --#ARGUMENTS    {1,2,3}
    --#SEVERITY     MAJOR
    --#GENERIC      6
    --#CATEGORY     "Alarm Events"
    --#SOURCE_ID    "A"
    --#TIMEINDEX    0
    ::= {adGenPseudowireCEMEvents 3}

adGenPseudowireCEMAlarmNearEndLPSActive   NOTIFICATION-TYPE
   OBJECTS  {
               adTrapInformSeqNum,
               sysName,                      -- Shelf
               adGenSlotInfoIndex,           -- Slot
               ifIndex,
               adGenPseudowireCEMPhysicalPortIfIndex    -- T1/E1 Port
            }
    STATUS          current
    DESCRIPTION     "Indicates that the Pseudowire Near-End Loss of Packet State Alarm Active."

    --#TYPE         "Status - Near End Loss of Packet State Active"
    --#SUMMARY      "Pseudowire Near End Loss of Packet State"
    --#SUMMARY      "Activated at shelf: %s, slot: %d, interface %d"
    --#ARGUMENTS    {1,2,3}
    --#SEVERITY     MAJOR
    --#GENERIC      6
    --#CATEGORY     "Alarm Events"
    --#SOURCE_ID    "A"
    --#TIMEINDEX    0
    ::= {adGenPseudowireCEMEvents 4}

adGenPseudowireCEMAlarmFarEndLPSClear    NOTIFICATION-TYPE
   OBJECTS  {
               adTrapInformSeqNum,
               sysName,                      -- Shelf
               adGenSlotInfoIndex,           -- Slot
               ifIndex,
               adGenPseudowireCEMPhysicalPortIfIndex    -- T1/E1 Port
            }
    STATUS          current
    DESCRIPTION     "Indicates that the Pseudowire Far-End Loss of Packet State has been cleared."

    --#TYPE         "Status - Far End Loss of Packet State Cleared"
    --#SUMMARY      "Pseudowire Far End Loss of Packet State"
    --#SUMMARY      "Cleared at shelf: %s, slot: %d, interface %d"
    --#ARGUMENTS    {1,2,3}
    --#SEVERITY     WARNING
    --#GENERIC      6
    --#CATEGORY     "Alarm Events"
    --#SOURCE_ID    "A"
    --#TIMEINDEX    0
    ::= {adGenPseudowireCEMEvents 5}

adGenPseudowireCEMAlarmFarEndLPSActive   NOTIFICATION-TYPE
   OBJECTS  {
               adTrapInformSeqNum,
               sysName,                      -- Shelf
               adGenSlotInfoIndex,           -- Slot
               ifIndex,
               adGenPseudowireCEMPhysicalPortIfIndex    -- T1/E1 Port
            }
    STATUS          current
    DESCRIPTION     "Indicates that the Pseudowire Far-End Loss of Packet State Alarm Active."

    --#TYPE         "Status - Far End Loss of Packet State Active"
    --#SUMMARY      "Pseudowire Far End Loss of Packet State"
    --#SUMMARY      "Activated at shelf: %s, slot: %d, interface %d"
    --#ARGUMENTS    {1,2,3}
    --#SEVERITY     WARNING
    --#GENERIC      6
    --#CATEGORY     "Alarm Events"
    --#SOURCE_ID    "A"
    --#TIMEINDEX    0
    ::= {adGenPseudowireCEMEvents 6}

    -- Pseudowire CEM Alarm Provisioning Table
   adGenPseudowireCEMAlarmProvTable OBJECT-TYPE
         SYNTAX         SEQUENCE OF AdGenPseudowireCEMAlarmProvTableEntry
         MAX-ACCESS     not-accessible
         STATUS         current
         DESCRIPTION
            "Total Access 5000 Pseudowire CEM Alarm Provisioning Table."
         ::= { adGenPseudowireCEMAlarmProv 1 }

   adGenPseudowireCEMAlarmProvTableEntry OBJECT-TYPE
         SYNTAX         AdGenPseudowireCEMAlarmProvTableEntry
         MAX-ACCESS     not-accessible
         STATUS         current
         DESCRIPTION
            "Channel ifIndex - see specific product"
         INDEX   { ifIndex }
         ::= { adGenPseudowireCEMAlarmProvTable 1 }

   AdGenPseudowireCEMAlarmProvTableEntry ::=
         SEQUENCE {
            adGenPseudowireCEMFarEndLOSAlarmEnable	TruthValue
            }

   adGenPseudowireCEMFarEndLOSAlarmEnable OBJECT-TYPE
         SYNTAX         TruthValue
         MAX-ACCESS     read-create
         STATUS         current
         DESCRIPTION
            "Provisioning for Enable/Disable of Rx Far End LOS Alarm which is a port level alarm.
 				1 = True
 				2 = False"
         ::= { adGenPseudowireCEMAlarmProvTableEntry 1 }

END

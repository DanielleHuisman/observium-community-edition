ADTRAN-GENERIC-PSEUDOWIRE-CEM-COUNTERS-INFO-MIB  DEFINITIONS ::= BEGIN

   -- TITLE:      Total Access 5000 Pseudowire Circuit Emulation Counters Information MIB
   -- PRODUCT:    1187500E1, 1187501G1, 1187502F1, 1188801G1
   -- VERSION:    1.0
   -- DATE:       10/07/09 (yy/mm/dd)
   -- AUTHOR:     Shobana Rao <shobana.rao@adtran.com>
   -- SNMP:       SNMPv2
   -- MIB ARC:    adtran.adShared.adGenCndSystem.adGenPseudowireCEMMgmt.adGenPseudowireCEMPerfInfo

   -- DESCRIPTION:
         -- Created based upon genTa5kPseudowireCountersInfo.mi2 to support the
         -- 1187500E1 (GPON OLT)
         -- 1187501G1 (GPON OLT)
         -- 1187502F1 (GPON OLT)
         -- 1188801G1 (32-Port E1 CEM)

   -- HISTORY: (yy/mm/dd)
         -- 10/07/09 - Created based upon the ADTRAN-GENERIC-TA5000-PSEUDOWIRE-COUNTERS-INFO-MIB.

   -- NOTES:
         -- Created based upon the
         -- ADTRAN-GENERIC-TA5000-PSEUDOWIRE-COUNTERS-INFO-MIB
         -- to support TA5000 pseudowire circuit emulation counters.
         -- Please consult product specific documentation and MIB's for
         -- further configuration details and considerations.

   IMPORTS
            MODULE-IDENTITY,
            OBJECT-TYPE,
            Gauge32,
            Counter64
               FROM SNMPv2-SMI

            adGenPseudowireCEMPerfInfo, adGenPseudowireCEMPerfInfoID
               FROM ADTRAN-GENERIC-PSEUDOWIRE-CEM-MGMT-MIB

            ifIndex, InterfaceIndex
               FROM IF-MIB;

-- Module ID ==================================================================

   adGenPseudowireCEMPerfInfoModuleIdentity     MODULE-IDENTITY
         LAST-UPDATED    "201007090800Z"
         ORGANIZATION
            "ADTRAN, Inc."
         CONTACT-INFO
            "CND Tech Support
                Postal: ADTRAN, Inc.
                        901 Explorer Blvd.
                        Huntsville, AL  35806
                        Tel: +1 800 726-8663
                        Fax: +1 256 963 6217
                        E-mail: support@adtran.com"
         DESCRIPTION
            "Total Access 5000 Pseudowire Circuit Emulation Performance Information MIB"
         ::= { adGenPseudowireCEMPerfInfoID 1 }

-- OBJECT IDENTIFIERS - Pseudowire CEM Performance Table =========================

   -- Pseudowire CEM Current 15 Minute Performance Table
   adGenPseudowireCEMCurrent15MinPerfTable OBJECT-TYPE
         SYNTAX   SEQUENCE OF AdGenPseudowireCEMCurrent15MinPerfTableEntry
         MAX-ACCESS     not-accessible
         STATUS         current
         DESCRIPTION
            "Total Access 5000 Pseudowire CEM Performance Information Table - Current 15 Minute."
         ::= { adGenPseudowireCEMPerfInfo 1 }

   adGenPseudowireCEMCurrent15MinPerfTableEntry OBJECT-TYPE
         SYNTAX         AdGenPseudowireCEMCurrent15MinPerfTableEntry
         MAX-ACCESS     not-accessible
         STATUS         current
         DESCRIPTION
            "Channel ifIndex"
         INDEX   { ifIndex }
         ::= { adGenPseudowireCEMCurrent15MinPerfTable 1 }

   AdGenPseudowireCEMCurrent15MinPerfTableEntry ::=
         SEQUENCE {
            adGenPseudowireCEMCurrent15MinPacketsMissed             Gauge32,
            adGenPseudowireCEMCurrent15MinPacketsDropped            Gauge32,
            adGenPseudowireCEMCurrent15MinPacketsMalformed          Gauge32,
            adGenPseudowireCEMCurrent15MinFailureCount              Gauge32,
            adGenPseudowireCEMCurrent15MinTxPacketCount             Gauge32,
            adGenPseudowireCEMCurrent15MinRxPacketCount             Gauge32,
            adGenPseudowireCEMCurrent15MinTxByteCount               Counter64,
            adGenPseudowireCEMCurrent15MinRxByteCount               Counter64,
            adGenPseudowireCEMCurrent15MinJitterBufferUnderrun      Gauge32
         }

   adGenPseudowireCEMCurrent15MinPacketsMissed OBJECT-TYPE
         SYNTAX         Gauge32
         MAX-ACCESS     read-only
         STATUS         current
         DESCRIPTION
            "Packets missed for pseudowire channel.
             The number of packets determined to be missing based upon gaps in
             the sequence numbers of the received packets."
         ::= { adGenPseudowireCEMCurrent15MinPerfTableEntry 1 }

   adGenPseudowireCEMCurrent15MinPacketsDropped OBJECT-TYPE
         SYNTAX         Gauge32
         MAX-ACCESS     read-only
         STATUS         current
         DESCRIPTION
            "Packets dropped for pseudowire channel.
             The number of packets that were detected out of order,
             could not be reordered, or could not fit into the jitter
             buffer."
         ::= { adGenPseudowireCEMCurrent15MinPerfTableEntry 2 }

   adGenPseudowireCEMCurrent15MinPacketsMalformed OBJECT-TYPE
         SYNTAX         Gauge32
         MAX-ACCESS     read-only
         STATUS         current
         DESCRIPTION
            "Packets malformed for pseudowire channel.
             The number of malformed packets detected by a mismatch between the
             expected packet size (taking the value of the L bit into account)
             and the actual packets size inferred from the PSN and
             multiplexing layers."
         ::= { adGenPseudowireCEMCurrent15MinPerfTableEntry 3 }

   adGenPseudowireCEMCurrent15MinFailureCount OBJECT-TYPE
         SYNTAX         Gauge32
         MAX-ACCESS     read-only
         STATUS         current
         DESCRIPTION
            "Failure count for pseudowire channel.
             The number of instances that LOPS (loss of packet sync)
             is declared."
         ::= { adGenPseudowireCEMCurrent15MinPerfTableEntry 4 }

   adGenPseudowireCEMCurrent15MinTxPacketCount OBJECT-TYPE
         SYNTAX         Gauge32
         MAX-ACCESS     read-only
         STATUS         current
         DESCRIPTION
            "Transmit packet count for pseudowire channel."
         ::= { adGenPseudowireCEMCurrent15MinPerfTableEntry 5 }

   adGenPseudowireCEMCurrent15MinRxPacketCount OBJECT-TYPE
         SYNTAX         Gauge32
         MAX-ACCESS     read-only
         STATUS         current
         DESCRIPTION
            "Receive packet count for pseudowire channel."
         ::= { adGenPseudowireCEMCurrent15MinPerfTableEntry 6 }

   adGenPseudowireCEMCurrent15MinTxByteCount OBJECT-TYPE
         SYNTAX         Counter64
         MAX-ACCESS     read-only
         STATUS         current
         DESCRIPTION
            "Transmit byte count for pseudowire channel."
         ::= { adGenPseudowireCEMCurrent15MinPerfTableEntry 7 }

   adGenPseudowireCEMCurrent15MinRxByteCount OBJECT-TYPE
         SYNTAX         Counter64
         MAX-ACCESS     read-only
         STATUS         current
         DESCRIPTION
            "Receive byte count for pseudowire channel."
         ::= { adGenPseudowireCEMCurrent15MinPerfTableEntry 8 }

   adGenPseudowireCEMCurrent15MinJitterBufferUnderrun OBJECT-TYPE
         SYNTAX         Gauge32
         MAX-ACCESS     read-only
         STATUS         current
         DESCRIPTION
            "JitterBuffer underrun for pseudowire channel."
         ::= { adGenPseudowireCEMCurrent15MinPerfTableEntry 9 }

   -- Pseudowire CEM Current 24 Hour Performance Table
   adGenPseudowireCEMCurrent24HrPerfTable OBJECT-TYPE
         SYNTAX   SEQUENCE OF AdGenPseudowireCEMCurrent24HrPerfTableEntry
         MAX-ACCESS     not-accessible
         STATUS         current
         DESCRIPTION
            "Total Access 5000 Pseudowire CEM Performance Information Table - Current 24 Hour."
         ::= { adGenPseudowireCEMPerfInfo 2 }

   adGenPseudowireCEMCurrent24HrPerfTableEntry OBJECT-TYPE
         SYNTAX         AdGenPseudowireCEMCurrent24HrPerfTableEntry
         MAX-ACCESS     not-accessible
         STATUS         current
         DESCRIPTION
            "Channel ifIndex"
         INDEX   { ifIndex }
         ::= { adGenPseudowireCEMCurrent24HrPerfTable 1 }

   AdGenPseudowireCEMCurrent24HrPerfTableEntry ::=
         SEQUENCE {
            adGenPseudowireCEMCurrent24HrPacketsMissed              Gauge32,
            adGenPseudowireCEMCurrent24HrPacketsDropped             Gauge32,
            adGenPseudowireCEMCurrent24HrPacketsMalformed           Gauge32,
            adGenPseudowireCEMCurrent24HrFailureCount               Gauge32,
            adGenPseudowireCEMCurrent24HrTxPacketCount              Gauge32,
            adGenPseudowireCEMCurrent24HrRxPacketCount              Gauge32,
            adGenPseudowireCEMCurrent24HrTxByteCount                Counter64,
            adGenPseudowireCEMCurrent24HrRxByteCount                Counter64,
            adGenPseudowireCEMCurrent24HrJitterBufferUnderrun       Gauge32
         }

   adGenPseudowireCEMCurrent24HrPacketsMissed OBJECT-TYPE
         SYNTAX         Gauge32
         MAX-ACCESS     read-only
         STATUS         current
         DESCRIPTION
            "Packets missed for pseudowire channel.
             The number of packets determined to be missing based upon gaps in
             the sequence numbers of the received packets."
         ::= { adGenPseudowireCEMCurrent24HrPerfTableEntry 1 }

   adGenPseudowireCEMCurrent24HrPacketsDropped OBJECT-TYPE
         SYNTAX         Gauge32
         MAX-ACCESS     read-only
         STATUS         current
         DESCRIPTION
            "Packets dropped for pseudowire channel.
             The number of packets that were detected out of order,
             could not be reordered, or could not fit into the jitter
             buffer."
         ::= { adGenPseudowireCEMCurrent24HrPerfTableEntry 2 }

   adGenPseudowireCEMCurrent24HrPacketsMalformed OBJECT-TYPE
         SYNTAX         Gauge32
         MAX-ACCESS     read-only
         STATUS         current
         DESCRIPTION
            "Packets malformed for pseudowire channel.
             The number of malformed packets detected by a mismatch between the
             expected packet size (taking the value of the L bit into account)
             and the actual packets size inferred from the PSN and
             multiplexing layers."
         ::= { adGenPseudowireCEMCurrent24HrPerfTableEntry 3 }

   adGenPseudowireCEMCurrent24HrFailureCount OBJECT-TYPE
         SYNTAX         Gauge32
         MAX-ACCESS     read-only
         STATUS         current
         DESCRIPTION
            "Failure count for pseudowire channel.
             The number of instances that LOPS (loss of packet sync)
             is declared."
         ::= { adGenPseudowireCEMCurrent24HrPerfTableEntry 4 }

   adGenPseudowireCEMCurrent24HrTxPacketCount OBJECT-TYPE
         SYNTAX         Gauge32
         MAX-ACCESS     read-only
         STATUS         current
         DESCRIPTION
            "Transmit packet count for pseudowire channel."
         ::= { adGenPseudowireCEMCurrent24HrPerfTableEntry 5 }

   adGenPseudowireCEMCurrent24HrRxPacketCount OBJECT-TYPE
         SYNTAX         Gauge32
         MAX-ACCESS     read-only
         STATUS         current
         DESCRIPTION
            "Receive packet count for pseudowire channel."
         ::= { adGenPseudowireCEMCurrent24HrPerfTableEntry 6 }

   adGenPseudowireCEMCurrent24HrTxByteCount OBJECT-TYPE
         SYNTAX         Counter64
         MAX-ACCESS     read-only
         STATUS         current
         DESCRIPTION
            "Transmit byte count for pseudowire channel."
         ::= { adGenPseudowireCEMCurrent24HrPerfTableEntry 7 }

   adGenPseudowireCEMCurrent24HrRxByteCount OBJECT-TYPE
         SYNTAX         Counter64
         MAX-ACCESS     read-only
         STATUS         current
         DESCRIPTION
            "Receive byte count for pseudowire channel."
         ::= { adGenPseudowireCEMCurrent24HrPerfTableEntry 8 }

   adGenPseudowireCEMCurrent24HrJitterBufferUnderrun OBJECT-TYPE
         SYNTAX         Gauge32
         MAX-ACCESS     read-only
         STATUS         current
         DESCRIPTION
            "JitterBuffer underrun for pseudowire channel."
         ::= { adGenPseudowireCEMCurrent24HrPerfTableEntry 9 }

   -- Pseudowire CEM 15 Minute Interval Performance Table
   adGenPseudowireCEMInterval15MinPerfTable OBJECT-TYPE
         SYNTAX SEQUENCE OF AdGenPseudowireCEMInterval15MinPerfTableEntry
         MAX-ACCESS     not-accessible
         STATUS         current
         DESCRIPTION
            "Total Access 5000 Pseudowire CEM Performance Information Table - Interval 15 Minute."
         ::= { adGenPseudowireCEMPerfInfo 3 }

   adGenPseudowireCEMInterval15MinPerfTableEntry OBJECT-TYPE
         SYNTAX         AdGenPseudowireCEMInterval15MinPerfTableEntry
         MAX-ACCESS     not-accessible
         STATUS         current
         DESCRIPTION
            "Channel ifIndex"
         INDEX   { ifIndex,
                   adGenPseudowireCEMIntervalNumber15Min }
         ::= { adGenPseudowireCEMInterval15MinPerfTable 1 }

   AdGenPseudowireCEMInterval15MinPerfTableEntry ::=
         SEQUENCE {
            adGenPseudowireCEMIntervalNumber15Min                   INTEGER,
            adGenPseudowireCEMInterval15MinPacketsMissed            Gauge32,
            adGenPseudowireCEMInterval15MinPacketsDropped           Gauge32,
            adGenPseudowireCEMInterval15MinPacketsMalformed         Gauge32,
            adGenPseudowireCEMInterval15MinFailureCount             Gauge32,
            adGenPseudowireCEMInterval15MinTxPacketCount            Gauge32,
            adGenPseudowireCEMInterval15MinRxPacketCount            Gauge32,
            adGenPseudowireCEMInterval15MinTxByteCount              Counter64,
            adGenPseudowireCEMInterval15MinRxByteCount              Counter64,
            adGenPseudowireCEMInterval15MinJitterBufferUnderrun     Gauge32
         }

   adGenPseudowireCEMIntervalNumber15Min OBJECT-TYPE
         SYNTAX         INTEGER (1..96)
         MAX-ACCESS     read-only
         STATUS         current
         DESCRIPTION
            "A number between 1 and 96, where 1 is the most
             recently completed 15 minute interval and 96 is
             the least recently completed 15 minutes interval
             (assuming that all 96 intervals are valid)."
         ::= { adGenPseudowireCEMInterval15MinPerfTableEntry 1 }

   adGenPseudowireCEMInterval15MinPacketsMissed OBJECT-TYPE
         SYNTAX         Gauge32
         MAX-ACCESS     read-only
         STATUS         current
         DESCRIPTION
            "Packets missed for pseudowire channel.
             The number of packets determined to be missing based upon gaps in
             the sequence numbers of the received packets."
         ::= { adGenPseudowireCEMInterval15MinPerfTableEntry 2 }

   adGenPseudowireCEMInterval15MinPacketsDropped OBJECT-TYPE
         SYNTAX         Gauge32
         MAX-ACCESS     read-only
         STATUS         current
         DESCRIPTION
            "Packets dropped for pseudowire channel.
             The number of packets that were detected out of order,
             could not be reordered, or could not fit into the jitter
             buffer."
         ::= { adGenPseudowireCEMInterval15MinPerfTableEntry 3 }

   adGenPseudowireCEMInterval15MinPacketsMalformed OBJECT-TYPE
         SYNTAX         Gauge32
         MAX-ACCESS     read-only
         STATUS         current
         DESCRIPTION
            "Packets malformed for pseudowire channel.
             The number of malformed packets detected by a mismatch between the
             expected packet size (taking the value of the L bit into account)
             and the actual packets size inferred from the PSN and
             multiplexing layers."
         ::= { adGenPseudowireCEMInterval15MinPerfTableEntry 4 }

   adGenPseudowireCEMInterval15MinFailureCount OBJECT-TYPE
         SYNTAX         Gauge32
         MAX-ACCESS     read-only
         STATUS         current
         DESCRIPTION
            "Failure count for pseudowire channel.
             The number of instances that LOPS (loss of packet sync)
             is declared."
         ::= { adGenPseudowireCEMInterval15MinPerfTableEntry 5 }

   adGenPseudowireCEMInterval15MinTxPacketCount OBJECT-TYPE
         SYNTAX         Gauge32
         MAX-ACCESS     read-only
         STATUS         current
         DESCRIPTION
            "Transmit packet count for pseudowire channel."
         ::= { adGenPseudowireCEMInterval15MinPerfTableEntry 6 }

   adGenPseudowireCEMInterval15MinRxPacketCount OBJECT-TYPE
         SYNTAX         Gauge32
         MAX-ACCESS     read-only
         STATUS         current
         DESCRIPTION
            "Receive packet count for pseudowire channel."
         ::= { adGenPseudowireCEMInterval15MinPerfTableEntry 7 }

   adGenPseudowireCEMInterval15MinTxByteCount OBJECT-TYPE
         SYNTAX         Counter64
         MAX-ACCESS     read-only
         STATUS         current
         DESCRIPTION
            "Transmit byte count for pseudowire channel."
         ::= { adGenPseudowireCEMInterval15MinPerfTableEntry 8 }

   adGenPseudowireCEMInterval15MinRxByteCount OBJECT-TYPE
         SYNTAX         Counter64
         MAX-ACCESS     read-only
         STATUS         current
         DESCRIPTION
            "Receive byte count for pseudowire channel."
         ::= { adGenPseudowireCEMInterval15MinPerfTableEntry 9 }

   adGenPseudowireCEMInterval15MinJitterBufferUnderrun OBJECT-TYPE
         SYNTAX         Gauge32
         MAX-ACCESS     read-only
         STATUS         current
         DESCRIPTION
            "JitterBuffer underrun for pseudowire channel."
         ::= { adGenPseudowireCEMInterval15MinPerfTableEntry 10}

   -- Pseudowire CEM 24 Hour Interval Performance Table
   adGenPseudowireCEMInterval24HrPerfTable OBJECT-TYPE
         SYNTAX SEQUENCE OF AdGenPseudowireCEMInterval24HrPerfTableEntry
         MAX-ACCESS     not-accessible
         STATUS         current
         DESCRIPTION
            "Total Access 5000 PseudowireCEM Perf Information Table - Interval 24 Hour."
         ::= { adGenPseudowireCEMPerfInfo 4 }

   adGenPseudowireCEMInterval24HrPerfTableEntry OBJECT-TYPE
         SYNTAX         AdGenPseudowireCEMInterval24HrPerfTableEntry
         MAX-ACCESS     not-accessible
         STATUS         current
         DESCRIPTION
            "Channel ifIndex"
         INDEX   { ifIndex,
                   adGenPseudowireCEMIntervalNumber24Hr }
         ::= { adGenPseudowireCEMInterval24HrPerfTable 1 }

   AdGenPseudowireCEMInterval24HrPerfTableEntry ::=
         SEQUENCE {
            adGenPseudowireCEMIntervalNumber24Hr                    INTEGER,
            adGenPseudowireCEMInterval24HrPacketsMissed             Gauge32,
            adGenPseudowireCEMInterval24HrPacketsDropped            Gauge32,
            adGenPseudowireCEMInterval24HrPacketsMalformed          Gauge32,
            adGenPseudowireCEMInterval24HrFailureCount              Gauge32,
            adGenPseudowireCEMInterval24HrTxPacketCount             Gauge32,
            adGenPseudowireCEMInterval24HrRxPacketCount             Gauge32,
            adGenPseudowireCEMInterval24HrTxByteCount               Counter64,
            adGenPseudowireCEMInterval24HrRxByteCount               Counter64,
            adGenPseudowireCEMInterval24HrJitterBufferUnderrun      Gauge32
         }

   adGenPseudowireCEMIntervalNumber24Hr OBJECT-TYPE
         SYNTAX         INTEGER (1..7)
         MAX-ACCESS     read-only
         STATUS         current
         DESCRIPTION
            "A number between 1 and 7, where 1 is the most recently
             completed day and 7 is the least recently completed
             day (assuming that all 7 days are valid)."
         ::= { adGenPseudowireCEMInterval24HrPerfTableEntry 1 }

   adGenPseudowireCEMInterval24HrPacketsMissed OBJECT-TYPE
         SYNTAX         Gauge32
         MAX-ACCESS     read-only
         STATUS         current
         DESCRIPTION
            "Packets missed for pseudowire channel.
             The number of packets determined to be missing based upon gaps in
             the sequence numbers of the received packets."
         ::= { adGenPseudowireCEMInterval24HrPerfTableEntry 2 }

   adGenPseudowireCEMInterval24HrPacketsDropped OBJECT-TYPE
         SYNTAX         Gauge32
         MAX-ACCESS     read-only
         STATUS         current
         DESCRIPTION
            "Packets dropped for pseudowire channel.
             The number of packets that were detected out of order,
             could not be reordered, or could not fit into the jitter
             buffer."
         ::= { adGenPseudowireCEMInterval24HrPerfTableEntry 3 }

   adGenPseudowireCEMInterval24HrPacketsMalformed OBJECT-TYPE
         SYNTAX         Gauge32
         MAX-ACCESS     read-only
         STATUS         current
         DESCRIPTION
            "Packets malformed for pseudowire channel.
             The number of malformed packets detected by a mismatch between the
             expected packet size (taking the value of the L bit into account)
             and the actual packets size inferred from the PSN and
             multiplexing layers."
         ::= { adGenPseudowireCEMInterval24HrPerfTableEntry 4 }

   adGenPseudowireCEMInterval24HrFailureCount OBJECT-TYPE
         SYNTAX         Gauge32
         MAX-ACCESS     read-only
         STATUS         current
         DESCRIPTION
            "Failure count for pseudowire channel.
             The number of instances that LOPS (loss of packet sync)
             is declared."
         ::= { adGenPseudowireCEMInterval24HrPerfTableEntry 5 }

   adGenPseudowireCEMInterval24HrTxPacketCount OBJECT-TYPE
         SYNTAX         Gauge32
         MAX-ACCESS     read-only
         STATUS         current
         DESCRIPTION
            "Transmit packet count for pseudowire channel."
         ::= { adGenPseudowireCEMInterval24HrPerfTableEntry 6 }

   adGenPseudowireCEMInterval24HrRxPacketCount OBJECT-TYPE
         SYNTAX         Gauge32
         MAX-ACCESS     read-only
         STATUS         current
         DESCRIPTION
            "Receive packet count for pseudowire channel."
         ::= { adGenPseudowireCEMInterval24HrPerfTableEntry 7 }

   adGenPseudowireCEMInterval24HrTxByteCount OBJECT-TYPE
         SYNTAX         Counter64
         MAX-ACCESS     read-only
         STATUS         current
         DESCRIPTION
            "Transmit byte count for pseudowire channel."
         ::= { adGenPseudowireCEMInterval24HrPerfTableEntry 8 }

   adGenPseudowireCEMInterval24HrRxByteCount OBJECT-TYPE
         SYNTAX         Counter64
         MAX-ACCESS     read-only
         STATUS         current
         DESCRIPTION
            "Receive byte count for pseudowire channel."
         ::= { adGenPseudowireCEMInterval24HrPerfTableEntry 9 }

   adGenPseudowireCEMInterval24HrJitterBufferUnderrun OBJECT-TYPE
         SYNTAX         Gauge32
         MAX-ACCESS     read-only
         STATUS         current
         DESCRIPTION
            "JitterBuffer underrun for pseudowire channel."
         ::= { adGenPseudowireCEMInterval24HrPerfTableEntry 10}

END

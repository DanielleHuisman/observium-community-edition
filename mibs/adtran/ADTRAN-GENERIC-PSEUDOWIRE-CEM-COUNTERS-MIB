ADTRAN-GENERIC-PSEUDOWIRE-CEM-COUNTERS-MIB  DEFINITIONS ::= BEGIN

   -- TITLE:      Total Access 5000 Pseudowire Circuit Emulation Counters MIB
   -- PRODUCT:    1187500E1, 1187501G1, 1187502F1, 1188801G1
   -- VERSION:    1.0
   -- DATE:       10/07/09 (yy/mm/dd)
   -- AUTHOR:     Shobana Rao <shobana.rao@adtran.com>
   -- SNMP:       SNMPv2
   -- MIB ARC:    adtran.adShared.adGenCndSystem.adGenPseudowireCEMMgmt.adGenPseudowireCEMPerformance

   -- DESCRIPTION:
         -- Created based upon genTa5kPseudowireCounter.mi2 to support the
         -- 1187500E1 (GPON OLT)
         -- 1187501G1 (GPON OLT)
         -- 1187502F1 (GPON OLT)
         -- 1188801G1 (32-Port E1 CEM)

   -- HISTORY: (yy/mm/dd)
         -- 10/07/09 - Created based upon the ADTRAN-GENERIC-TA5000-PSEUDOWIRE-COUNTERS-MIB.

   -- NOTES:
         -- Created based upon the
         -- ADTRAN-GENERIC-TA5000-PSEUDOWIRE-COUNTERS-MIB
         -- to support TA5000 Pseudowire Circuit Emulation counters.
         -- Please consult product specific documentation and MIB's for
         -- further configuration details and considerations.

   IMPORTS
            OBJECT-TYPE,
            Integer32,
            MODULE-IDENTITY
               FROM SNMPv2-SMI

            DisplayString,
            TEXTUAL-CONVENTION
               FROM SNMPv2-TC

            adGenPseudowireCEMPerformance, adGenPseudowireCEMPerfID
               FROM ADTRAN-GENERIC-PSEUDOWIRE-CEM-MGMT-MIB

            ifIndex
               FROM IF-MIB;

-- Module ID ==================================================================

   adGenPseudowireCEMPerfModuleIdentity         MODULE-IDENTITY
         LAST-UPDATED    "201104280000Z"
         ORGANIZATION
            "ADTRAN, Inc."
         CONTACT-INFO
            "CND Tech Support
                Postal: ADTRAN, Inc.
                        901 Explorer Blvd.
                        Huntsville, AL  35806
                        Tel: +1 800 726-8663
                        Fax: +1 256 963 6217
                        E-mail: support@adtran.com"
         DESCRIPTION
            "Total Access 5000 Pseudowire Circuit Emulation Performance MIB"

         REVISION "201104280000Z"
         DESCRIPTION  "Replaced all read-create to read-only."

         ::= { adGenPseudowireCEMPerfID 1 }

-- OBJECT IDENTIFIERS =========================================================

   adGenPseudowireCEMPerfProv  OBJECT IDENTIFIER ::= {adGenPseudowireCEMPerformance 1}

-- OBJECT IDENTIFIERS - Pseudowire CEM Performance Provisioning Table ==============

   -- Pseudowire CEM Counters Provisioning Table
   adGenPseudowireCEMPerfProvTable OBJECT-TYPE
         SYNTAX         SEQUENCE OF AdGenPseudowireCEMPerfProvTableEntry
         MAX-ACCESS     not-accessible
         STATUS         current
         DESCRIPTION
            "Total Access 5000 Pseudowire Circuit Emulation Performance Provisioning Table."
         ::= { adGenPseudowireCEMPerfProv 1 }

   adGenPseudowireCEMPerfProvTableEntry OBJECT-TYPE
         SYNTAX         AdGenPseudowireCEMPerfProvTableEntry
         MAX-ACCESS     not-accessible
         STATUS         current
         DESCRIPTION
            "Device ifIndex"
         INDEX   { ifIndex }
         ::= { adGenPseudowireCEMPerfProvTable 1 }

   AdGenPseudowireCEMPerfProvTableEntry ::=
         SEQUENCE {
            adGenPseudowireCEMPerfErrorStr             DisplayString,
            adGenPseudowireCEMPerfClear15MinCounters   INTEGER,
            adGenPseudowireCEMPerfClear24HrCounters	   INTEGER
         }

   adGenPseudowireCEMPerfErrorStr OBJECT-TYPE
         SYNTAX         DisplayString
         MAX-ACCESS     read-only
         STATUS         current
         DESCRIPTION
            "The error string for SNMP query."
         ::= { adGenPseudowireCEMPerfProvTableEntry 1 }

   adGenPseudowireCEMPerfClear15MinCounters OBJECT-TYPE
         SYNTAX         INTEGER
		        {
				reset(1)
         	    }
         MAX-ACCESS     read-write
         STATUS         current
         DESCRIPTION
         "Clear 15 minute performance data on the selected pseudowire interface."
         ::= { adGenPseudowireCEMPerfProvTableEntry 2 }

   adGenPseudowireCEMPerfClear24HrCounters OBJECT-TYPE
         SYNTAX         INTEGER
				{
                reset(1)
         		}
         MAX-ACCESS     read-write
         STATUS         current
         DESCRIPTION
         "Clear 24 hour performance data on the selected pseudowire interface."
         ::= { adGenPseudowireCEMPerfProvTableEntry 3 }

END

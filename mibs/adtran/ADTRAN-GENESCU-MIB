ADTRAN-GENESCU-MIB

    DEFINITIONS ::= BEGIN

    -- TITLE:     The ADTRAN Generic Enhanced SCU MIB
    -- PRODUCTS:  3000 1181.018L1, 1500 L1
    -- VERSION:   1.0
    -- AUTHOR:   Phil Bergstresser
    -- DATE:      00/08/02

    -- This is a generic MIB for all versions of the Total Access System Controller
    --   Units that use the second generation RMD files and the generic chassis MIBs.
    -- The various SCU products define their level of support
    --   for the managed objects in this generic MIB in their own
    --   product specific MIBs.
    -- This MIB uses the GenericShelves MIBs for slot and port.
    --

    -- HISTORY:
       -- 00/08/02 pnb initial file
       -- 00/08/10 pnb add back in the MO for remote alarm status.
       --              transfer all traps to generic chassis traps MIB genctrap.
       -- 00/09/27 pnb remove Mfr Date MO inadvertantly copied from genh2tuc.
       -- 01/02/13 pnb change comments only about slot numbering conventions.
       -- 01/03/01 pnb add provisioning, status & test objects. Increase admin port
       --              baudrates to 115,200 bps.
       -- 01/03/02 pnb add chassis lamp test command, and CLLI & TIRKSID status
       -- 01/03/07 pnb correct name of rmtinStatus to eliminate accidental conflict
       --              with 017 SCU/NMI MIB. Network Manager problem if multiple chassis
       --              with different controllers are in use simultaneously with conflicting
       --              MIBs.
       -- 02/04/09   KABC Added adGenESCUadminSecurityEnable
       -- 02/24/2010 AP   Convert to SNMPv2 mi2.
       --


        IMPORTS
            Integer32, OBJECT-TYPE,
            MODULE-IDENTITY
                FROM SNMPv2-SMI
            DisplayString
                FROM SNMPv2-TC
            adShared
                FROM ADTRAN-MIB
            adGenSlotInfoIndex
                FROM ADTRAN-GENSLOT-MIB
        ;

        adGenESCUmg MODULE-IDENTITY
         LAST-UPDATED "201002241300Z"
         ORGANIZATION "Adtran, Inc."
         CONTACT-INFO
           "CND Tech Support
               Postal: ADTRAN, Inc.
                       901 Explorer Blvd.
                       Huntsville, AL  35806
                       Tel: +1 800 726-8663
                       Fax: +1 256 963 6217
                       E-mail: support@adtran.com"
         DESCRIPTION
            "This MIB defines the objects for the genescu MIB."
         REVISION "201002241300Z"
         DESCRIPTION "Converted from SNMPv1 genescu.mib file."
      ::= { adShared 17 }

    -- OBJECT IDENTIFIERS

      --adGenESCUmg            OBJECT IDENTIFIER ::= { adShared 17 }

    -- Slot numbering conventions for SNMP
        -- Slot numbers are assigned by chassis and SCU conventions and
        --   should be defined in the product specific MIBs for SCUs.
        -- However, a general rule is that the line card slots are numbered
        --   from 1 to N, then the muxes follow, and finally the SCU.
        -- Other chassis products may follow other conventions, such as the
        --   TA 1500 which has LIUs in place of muxes, and power supplies
        --   follow the SCU. The SNMP numbering does not signify ordering
        --   of cards in the chassis though.

        --
        -- Card configuration group
        --

        adGenESCUConfig  OBJECT IDENTIFIER ::= { adGenESCUmg 1 }




        --
        -- Card Provisioning group
        --

        adGenESCUProv OBJECT IDENTIFIER  ::= { adGenESCUmg 2 }

        adGenESCUProvTable OBJECT-TYPE
            SYNTAX      SEQUENCE OF AdGenESCUProvEntry
            MAX-ACCESS  not-accessible
            STATUS  current
            DESCRIPTION
                "The SCU Prov table."
           ::= { adGenESCUProv 1 }

        adGenESCUProvEntry OBJECT-TYPE
            SYNTAX  AdGenESCUProvEntry
            MAX-ACCESS  not-accessible
            STATUS  current
            DESCRIPTION
                "An entry in the SCU Provisioning table."
           INDEX   { adGenSlotInfoIndex }
           ::= { adGenESCUProvTable 1 }

        AdGenESCUProvEntry ::=
            SEQUENCE {
                adGenESCUadminPortRate
                    INTEGER,
                adGenESCUautoLogoff
                     INTEGER,
                adGenESCUautoLogoffTimer
                    Integer32,
                adGenESCUmoduleAutoProv
                    INTEGER,
                adGenESCUmuxAutoProv
                    INTEGER,
                adGenESCUrestoreFactoryDefaults
                    INTEGER,
                adGenESCUadminPortMode
                    INTEGER,
                adGenESCUcraftPortRate
                    INTEGER,
                adGenESCUadminSecurityEnable
                    INTEGER
            }

        adGenESCUadminPortRate OBJECT-TYPE
                SYNTAX  INTEGER {
                        baud9600 (1),
                        baud19200 (2),
                        baud38400 (3),
                        baud57600 (4),
                        baud115200 (5)
                        }
                MAX-ACCESS  read-write
                STATUS  current
                DESCRIPTION
                  "A Set changes the admin port baud rate to the set
                  value.  A Get retrieves the current baud rate."
                ::= { adGenESCUProvEntry 1 }

        adGenESCUautoLogoff OBJECT-TYPE
                SYNTAX  INTEGER {
                        disable (1),
                        enable (2)
                        }
                MAX-ACCESS  read-write
                STATUS  current
                DESCRIPTION
                  "Enables or disables the Terminal Auto-Logoff."
                ::= { adGenESCUProvEntry 2 }

        adGenESCUautoLogoffTimer OBJECT-TYPE
                SYNTAX  Integer32 (1..60)
                MAX-ACCESS  read-write
                STATUS  current
                DESCRIPTION
                  "Selects the Terminal Auto-Logoff time."
                ::= { adGenESCUProvEntry 3 }

        adGenESCUmoduleAutoProv OBJECT-TYPE
                SYNTAX  INTEGER {
                        disable (1),
                        enable (2)
                        }
                MAX-ACCESS  read-write
                STATUS  current
                DESCRIPTION
                  "Enables or disables Access Module Auto-Provisioning."
                ::= { adGenESCUProvEntry 4 }

        adGenESCUmuxAutoProv OBJECT-TYPE
                SYNTAX  INTEGER {
                        disable (1),
                        enable (2)
                        }
                MAX-ACCESS  read-write
                STATUS  current
                DESCRIPTION
                  "Enables or disables Mux Auto-Provisioning."
                ::= { adGenESCUProvEntry 5 }

        adGenESCUrestoreFactoryDefaults OBJECT-TYPE
                SYNTAX  INTEGER {
                        restoreFactoryDefaults(1)
                        }
                MAX-ACCESS  read-write
                STATUS  current
                DESCRIPTION
                  "A Set restores ALL provisioning to the factory defaults.
                   A get is meaningless and always returns a 1."
                ::= { adGenESCUProvEntry 6 }

        adGenESCUadminPortMode OBJECT-TYPE
                SYNTAX  INTEGER {
                        menus (1),
                        tl1 (2)
                        }
                MAX-ACCESS  read-write
                STATUS  current
                DESCRIPTION
                  "A Set changes the admin port mode for menus or TL1 access.
                   A Get retrieves the current mode."
                DEFVAL { menus }
                ::= { adGenESCUProvEntry 7 }

        adGenESCUcraftPortRate OBJECT-TYPE
                SYNTAX  INTEGER {
                        baud9600 (1),
                        baud19200 (2),
                        baud38400 (3),
                        baud57600 (4),
                        baud115200 (5)
                        }
                MAX-ACCESS  read-write
                STATUS  current
                DESCRIPTION
                  "A Set changes the craft port baud rate to the set
                   value.  A Get retrieves the current baud rate."
                DEFVAL { baud115200 }
                ::= { adGenESCUProvEntry 8 }

        adGenESCUadminSecurityEnable OBJECT-TYPE
                SYNTAX  INTEGER {
                        enabled(1),
                        disabled(2)
                        }
                MAX-ACCESS  read-write
                STATUS  current
                DESCRIPTION
                  "Require authentication."
                ::= { adGenESCUProvEntry 9 }

        --
        -- Card Status group
        --

        adGenESCUStatus  OBJECT IDENTIFIER    ::= { adGenESCUmg 3 }

        adGenESCUStatusTable OBJECT-TYPE
            SYNTAX  SEQUENCE OF AdGenESCUStatusEntry
            MAX-ACCESS  not-accessible
            STATUS  current
            DESCRIPTION
                "The SCU Status table."
            ::= { adGenESCUStatus 1 }

        adGenESCUStatusEntry OBJECT-TYPE
            SYNTAX  AdGenESCUStatusEntry
            MAX-ACCESS  not-accessible
            STATUS  current
            DESCRIPTION
                "An entry in the SCU Status table."
           INDEX   { adGenSlotInfoIndex }
           ::= { adGenESCUStatusTable 1 }

        AdGenESCUStatusEntry ::=
            SEQUENCE {
                adGenESCUacoStatus
                    INTEGER,
                adGenESCUacoinStatus
                    INTEGER,
                adGenESCUrmtinStatus
                    INTEGER,
                adGenESCUextin1Status
                    INTEGER,
                adGenESCUextin2Status
                    INTEGER,
                adGenESCUminus48PowerAStatus
                    INTEGER,
                adGenESCUminus48PowerBStatus
                    INTEGER,
                adGenESCUopenFuseStatus
                    INTEGER,
                adGenESCUCLLI
                    DisplayString,
                adGenESCUTIRKSID
                    Integer32
            }

        adGenESCUacoStatus OBJECT-TYPE
                SYNTAX  INTEGER {
                        off (1),
                        on (2)
                        }
                MAX-ACCESS  read-only
                STATUS  current
                DESCRIPTION
                  "Indicates whether or not the alarm cut-off is on."
                ::= { adGenESCUStatusEntry 1 }

        adGenESCUacoinStatus OBJECT-TYPE
                SYNTAX  INTEGER {
                        inactive (1),
                        active (2)
                        }
                MAX-ACCESS  read-only
                STATUS  current
                DESCRIPTION
                  "Indicates whether or not the alarm cut-off input
                  is active."
                ::= { adGenESCUStatusEntry 2 }

        adGenESCUrmtinStatus OBJECT-TYPE
                SYNTAX  INTEGER
                        {
                        inactive (1),
                        active (2)
                        }
                MAX-ACCESS  read-only
                STATUS  current
                DESCRIPTION
                  "Indicates whether or not the remote alarm input
                  is active."
                ::= { adGenESCUStatusEntry 3 }

        adGenESCUextin1Status OBJECT-TYPE
                SYNTAX  INTEGER {
                        inactive (1),
                        active (2)
                        }
                MAX-ACCESS  read-only
                STATUS  current
                DESCRIPTION
                  "Indicates whether or not the external alarm input #1
                  is active."
                ::= { adGenESCUStatusEntry 4 }

        adGenESCUextin2Status OBJECT-TYPE
                SYNTAX  INTEGER {
                        inactive (1),
                        active (2)
                        }
                MAX-ACCESS  read-only
                STATUS  current
                DESCRIPTION
                  "Indicates whether or not the external alarm input #2
                  is active."
                ::= { adGenESCUStatusEntry 5 }

        adGenESCUminus48PowerAStatus OBJECT-TYPE
                SYNTAX  INTEGER {
                        inactive (1),
                        active (2)
                        }
                MAX-ACCESS  read-only
                STATUS  current
                DESCRIPTION
                  "Indicates whether or not the minus 48V power supply
                   A is active."
                ::= { adGenESCUStatusEntry 6 }

        adGenESCUminus48PowerBStatus OBJECT-TYPE
                SYNTAX  INTEGER {
                        inactive (1),
                        active (2)
                        }
                MAX-ACCESS  read-only
                STATUS  current
                DESCRIPTION
                  "Indicates whether or not the minus 48V power supply
                   B is active."
                ::= { adGenESCUStatusEntry 7 }

        adGenESCUopenFuseStatus OBJECT-TYPE
                SYNTAX  INTEGER {
                        normal (1),
                        open (2)
                        }
                MAX-ACCESS  read-only
                STATUS  current
                DESCRIPTION
                  "Indicates whether one or more card fuses on this
                   chassis is open."
                ::= { adGenESCUStatusEntry 8 }

        adGenESCUCLLI OBJECT-TYPE
                SYNTAX  DisplayString (SIZE (0..20))
                MAX-ACCESS  read-only
                STATUS  current
                DESCRIPTION
                  "The Common Language Location Identifier of this chassis,
                   assigned at the craft port."
                ::= { adGenESCUStatusEntry 9 }

        adGenESCUTIRKSID OBJECT-TYPE
                SYNTAX  Integer32 (1..254)
                MAX-ACCESS  read-only
                STATUS  current
                DESCRIPTION
                  "The Trunk Information Record Keeping System unit number
                  assigned to this shelf, assigned at the craft port."
                ::= { adGenESCUStatusEntry 10 }


        --
        -- Card Test group
        --

        adGenESCUTest OBJECT IDENTIFIER   ::= { adGenESCUmg 4 }

        adGenESCUTestTable OBJECT-TYPE
            SYNTAX  SEQUENCE OF AdGenESCUTestEntry
            MAX-ACCESS  not-accessible
            STATUS  current
            DESCRIPTION
                "The SCU Test table."
           ::= { adGenESCUTest 1 }

        adGenESCUTestEntry OBJECT-TYPE
            SYNTAX  AdGenESCUTestEntry
            MAX-ACCESS  not-accessible
            STATUS  current
            DESCRIPTION
                "An entry in the SCU Test table."
           INDEX   { adGenSlotInfoIndex }
           ::= { adGenESCUTestTable 1 }

        AdGenESCUTestEntry ::=
            SEQUENCE {
                adGenESCUReset
                    INTEGER,
                adGenESCUselfTestResults
                    DisplayString,
                adGenESCUChassisLampTest
                    INTEGER
            }

        adGenESCUReset   OBJECT-TYPE
                SYNTAX  INTEGER {
                        reset(1)
                        }
                MAX-ACCESS  read-write
                STATUS  current
                DESCRIPTION
                  "A Set restarts the SCU and performs unit self-test.
                   A get always returns a 1."
                ::= { adGenESCUTestEntry 1 }

        adGenESCUselfTestResults OBJECT-TYPE
                SYNTAX  DisplayString
                MAX-ACCESS  read-only
                STATUS  current
                DESCRIPTION
                  "Contains the results of the self test performed on startup.
                   This can be from a commanded reset, or card insertion.
                   The text will read 'PASSED', or 'FAILED - xxxx' where
                   xxxx will be an explanation of the error(s) encountered.
                   See the documentation on the specific SCU or the enterprise
                   specific MIB for clarification of failures if encoded."
                ::= { adGenESCUTestEntry 2 }

        adGenESCUChassisLampTest   OBJECT-TYPE
                SYNTAX  INTEGER {
                        initiate(1)
                        }
                MAX-ACCESS  read-write
                STATUS  current
                DESCRIPTION
                  "A set causes the SCU to initiate a lamp test concurrently on
                   every card in the chassis, for a pre-determined duration.
                   A get always returns a 1."
                ::= { adGenESCUTestEntry 3 }



        END

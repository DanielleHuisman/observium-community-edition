ADTRAN-GENEZPROVISIONING-MIB

-- TITLE:     The ADTRAN EZ-Provisioning MIB
-- PRODUCT:   ADTRAN products supporting EZ-Provisioning
-- VERSION:   1.0
-- DATE:      5/05/2010
-- AUTHOR:    Byron Young
-- STATUS:    PRELIMINARY

-- This MIB defines the object identifiers (OIDs) for the
-- ADTRAN EZ-Provisioning MIB objects

-- HISTORY:
-- 05/11/2010 BLY Created
--
-- ******************************************************************************************
DEFINITIONS ::= BEGIN

IMPORTS
   MODULE-IDENTITY,
   OBJECT-TYPE,
   NOTIFICATION-TYPE,
   IpAddress,
   Unsigned32
      FROM SNMPv2-SMI
   sysName,
   sysLocation
      FROM SNMPv2-MIB
   RowStatus,
   TruthValue,
   DisplayString
      FROM SNMPv2-TC
   OBJECT-GROUP,
   NOTIFICATION-GROUP
      FROM SNMPv2-CONF
   adTrapInformSeqNum
      FROM ADTRAN-GENTRAPINFORM-MIB
   adGenSlotProdPartNumber,
   adGenSlotProdSwVersion
      FROM ADTRAN-GENSLOT-MIB
   adShared,
   adIdentityShared
       FROM ADTRAN-MIB
   adGenEZProv,
   adGenEZProvID
       FROM ADTRAN-SHARED-CND-SYSTEM-MIB
   AdGenTrapVersion
      FROM ADTRAN-SHARED-CND-SYSTEM-TC-MIB
   ;

adGenEZProvMIB MODULE-IDENTITY
   LAST-UPDATED "201004300000Z"
   ORGANIZATION "Adtran, Inc."
   CONTACT-INFO
     "CND Tech Support
         Postal: ADTRAN, Inc.
                 901 Explorer Blvd.
                 Huntsville, AL  35806
                 Tel: +1 800 726 8663
                 Fax: +1 256 963 6217
                 E-mail: support@adtran.com"
   DESCRIPTION
      "This MIB defines the objects for the EZ-Provisioning MIB."
   REVISION "201004300000Z"
   DESCRIPTION "Created"
::= { adGenEZProvID 1 }

adGenEZProvEvents    OBJECT IDENTIFIER ::= {adGenEZProv 0}
adGenEZProvStatus    OBJECT IDENTIFIER ::= {adGenEZProv 1}
adGenEZProvConfig    OBJECT IDENTIFIER ::= {adGenEZProv 2}
adGenEZProvHosts     OBJECT IDENTIFIER ::= {adGenEZProv 3}

   adGenEZProvIPAddress OBJECT-TYPE
      SYNTAX     IpAddress
      MAX-ACCESS  read-only
      STATUS  current
      DESCRIPTION
          "The management IP address of the device."
      ::= {adGenEZProvStatus 1}

   adGenEZProvSNMPReadCommunity OBJECT-TYPE
      SYNTAX DisplayString
      MAX-ACCESS  read-only
      STATUS  current
      DESCRIPTION
         "SNMP Read Community of the device."
      ::= {adGenEZProvStatus 2}

   adGenEZProvSNMPWriteCommunity OBJECT-TYPE
      SYNTAX DisplayString
      MAX-ACCESS  read-only
      STATUS  current
      DESCRIPTION
         "SNMP Write Community of the device."
      ::= {adGenEZProvStatus 3}

   adGenEZProvBootCodeVersion OBJECT-TYPE
      SYNTAX DisplayString
      MAX-ACCESS  read-only
      STATUS  current
      DESCRIPTION
         "Firmware version for the current boot code of the device."
      ::= {adGenEZProvStatus 4}

   adGenEZProvAppCodeVersion OBJECT-TYPE
      SYNTAX DisplayString
      MAX-ACCESS  read-only
      STATUS  current
      DESCRIPTION
         "Firmware version for the current app code of the device."
      ::= {adGenEZProvStatus 5}

   adGenEZProvConfigCrc32 OBJECT-TYPE
      SYNTAX Unsigned32
      MAX-ACCESS  read-only
      STATUS  current
      DESCRIPTION
         "This string provides the CRC-32 calculation of the configuration file
          of the device."
      ::= {adGenEZProvStatus 6}

   adGenEZProvStatusString OBJECT-TYPE
      SYNTAX DisplayString
      MAX-ACCESS  read-only
      STATUS  current
      DESCRIPTION
         "Current status of the EZ Provisioning process on the device."
      ::= {adGenEZProvStatus 7}

   adGenEZProvActiveHostIpAddress OBJECT-TYPE
      SYNTAX IpAddress
      MAX-ACCESS  read-write
      STATUS  current
      DESCRIPTION
         "The active EZ-Provisioning host for the device."
      ::= {adGenEZProvConfig 1}

   adGenEZProvBootCodeFilename OBJECT-TYPE
      SYNTAX DisplayString
      MAX-ACCESS  read-write
      STATUS  current
      DESCRIPTION
         "The boot code filename to be retrieved by the device."
      ::= {adGenEZProvConfig 2}

   adGenEZProvAppCodeFilename OBJECT-TYPE
      SYNTAX DisplayString
      MAX-ACCESS  read-write
      STATUS  current
      DESCRIPTION
         "The app code filename to be retrieved by the device."
      ::= {adGenEZProvConfig 3}

   adGenEZProvConfigFilename OBJECT-TYPE
      SYNTAX DisplayString
      MAX-ACCESS  read-write
      STATUS  current
      DESCRIPTION
         "The config filename to be retrieved by the device."
      ::= {adGenEZProvConfig 4}

   adGenEZProvEnabled OBJECT-TYPE
      SYNTAX       TruthValue
      MAX-ACCESS   read-write
      STATUS       current
      DESCRIPTION
        "The EZ-Provisioning administrative state."
       ::= {adGenEZProvConfig 5}

   adGenEZProvHostTable OBJECT-TYPE
       SYNTAX SEQUENCE OF AdGenEZProvHostEntry
       MAX-ACCESS  not-accessible
       STATUS  current
       DESCRIPTION
          "Table of EZ-Provisioning hosts."
       ::= {adGenEZProvHosts 1}

   adGenEZProvHostEntry OBJECT-TYPE
       SYNTAX  AdGenEZProvHostEntry
       MAX-ACCESS  not-accessible
       STATUS  current
       DESCRIPTION
               "Host table entry."
       INDEX   {adGenEZProvHostIP }
       ::= {adGenEZProvHostTable 1}

   AdGenEZProvHostEntry ::=
       SEQUENCE {
           adGenEZProvHostIP
               IpAddress,
           adGenEZProvHostTrapVersion
               AdGenTrapVersion,
           adGenEZProvHostRowStatus
               RowStatus
       }

   adGenEZProvHostIP OBJECT-TYPE
       SYNTAX      IpAddress
       MAX-ACCESS  not-accessible
       STATUS      current
       DESCRIPTION
          "IP address of host."
       ::= {adGenEZProvHostEntry 1}

   adGenEZProvHostTrapVersion OBJECT-TYPE
      SYNTAX       AdGenTrapVersion
      MAX-ACCESS   read-create
      STATUS       current
      DESCRIPTION
        "The trap version for this host."
       ::= {adGenEZProvHostEntry 2}

   adGenEZProvHostRowStatus OBJECT-TYPE
       SYNTAX      RowStatus
       MAX-ACCESS  read-create
       STATUS      current
       DESCRIPTION
          "The status of the row for this host.

           The writable columns in a row can not be changed if the row
           is active. All columns must have a valid value before a row
           can be activated."
       ::= {adGenEZProvHostEntry 3}

   adGenEZProvRequest NOTIFICATION-TYPE
      OBJECTS  {
         adTrapInformSeqNum,
         sysName,
         sysLocation,
         adGenEZProvSNMPReadCommunity,
         adGenEZProvSNMPWriteCommunity,
         adGenSlotProdPartNumber,
         adGenEZProvIPAddress,
         adGenEZProvBootCodeVersion,
         adGenEZProvAppCodeVersion,
         adGenEZProvConfigCrc32
      }
      STATUS  current
      DESCRIPTION
         "This trap serves as a file request to the EZ Provisioning host."
         --#TYPE         "Status - Alarm"
         --#SUMMARY      "EZProv 1: EZ Provisioning Request."
         --#SEVERITY     INFO
         --#GENERIC      6
         --#CATEGORY     "Error Events"
         --#SOURCE_ID    "A"
         --#TIMEINDEX    0
      ::= {adGenEZProvEvents 1}

   adGenEZProvFailure NOTIFICATION-TYPE
      OBJECTS  {
         adTrapInformSeqNum,
         sysName,
         sysLocation,
         adGenSlotProdPartNumber,
         adGenEZProvIPAddress,
         adGenEZProvStatusString
      }
      STATUS  current
      DESCRIPTION
         "This trap indicates a failure in the EZ-Provisioning sequence."
         --#TYPE         "Status - Alarm"
         --#SUMMARY      "EZProv 2: EZ Provisioning Failure."
         --#SEVERITY     MAJOR
         --#GENERIC      6
         --#CATEGORY     "Error Events"
         --#SOURCE_ID    "A"
         --#TIMEINDEX    0
      ::= {adGenEZProvEvents 2}

END

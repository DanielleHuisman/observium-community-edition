ADTRAN-GENHDSL-MIB

    DEFINITIONS ::= BEGIN

    -- ADTRAN Proprietary and Confidential
    --
    -- TITLE:     The ADTRAN Generic shared HDSL MIB
    -- PRODUCTS:  1181413Lx
    -- VERSION:   1.0
    -- AUTHOR:    Brian Slack
    -- DATE:      03/06/10
    --
    -- This MIB defines the shared management information for the 3rd gen or higher Single Port
    -- H4TUC access module for a Total Access 3000 shelf.

    --
    -- Contact Information:
    --                CND Tech Support
    --                Postal: ADTRAN, Inc.
    --                        901 Explorer Blvd.
    --                        Huntsville, AL  35806
    --                Tel:    +1 800 726-8663
    --                Fax:    +1 256 963 6217
    --                E-mail: support@adtran.com
    --
    -- HISTORY:
       -- 06/10/03 bcs First edition.
       -- 10/02/07 jlb Converted to SNMPv2

    IMPORTS
        adShared,
        adIdentityShared
            FROM ADTRAN-MIB
        MODULE-IDENTITY
            FROM SNMPv2-SMI
        ;

adHDSLIdentity MODULE-IDENTITY
   LAST-UPDATED "200710020000Z"
   ORGANIZATION "Adtran, Inc."
   CONTACT-INFO "http://www.adtran.com"
   DESCRIPTION
      "This MIB defines the objects for the HDSL MIB."
   REVISION "200710020000Z"
   DESCRIPTION "Created"
::= { adIdentityShared 51 }


    -- OBJECT IDENTIFIERS

    -- OBJECT IDENTIFIERS

        adGenHDSL               OBJECT IDENTIFIER ::= { adShared 51 }
        adGenHDSLID             OBJECT IDENTIFIER ::= { adHDSLIdentity 1 }

        END

ADTRAN-GENIGMPCACHE-MIB

-- TITLE:     The ADTRAN IGMP Cache MIB
-- PRODUCT:   Metro Ethernet Products
-- VERSION:   1.0
-- DATE:      03/02/09
-- AUTHOR:    Ron Zuckerman
-- STATUS:    PRELIMINARY

-- This MIB defines the object identifiers (OIDs) for the
-- ADTRAN GENIGMPCACHE MIB objects

-- HISTORY:
-- 03/02/09 rmz   STATUS: PRELIMINARY.
-- 03/04/09 rmz   STATUS: PRELIMINARY.
--                Fixed problems that were causing MIB2RMD to not generate any DIDs.
-- 03/06/09 rmz   STATUS: PRELIMINARY.
--                Renamed adGenIGMPCacheSlotPort to adGenIGMPCacheInterfaceDescription,
--                improved description, and added examples.
--                Improved description for adGenIGMPCacheIndex.
-- 03/09/09 jlb   SMIC verified.
-- 05/08/09 rmz   Added "NET 1" description for adGenIGMPCacheInterfaceDescription for AMs
-- *******************************************************************************************************
--    DO NOT MAKE HISTORY COMMENTS HERE!!!! Revision history now in REVISION/DESCRIPTION clauses below
-- *******************************************************************************************************
DEFINITIONS ::= BEGIN

IMPORTS

   adGenIGMPCache,
   adGenIGMPCacheID
      FROM ADTRAN-SHARED-CND-SYSTEM-MIB

   OBJECT-TYPE,
   MODULE-IDENTITY,
   Integer32,
   IpAddress,
   TimeTicks
      FROM SNMPv2-SMI

   DisplayString
      FROM SNMPv2-TC

   adGenSlotInfoIndex
      FROM ADTRAN-GENSLOT-MIB
   ;

adGenIGMPCacheMIB MODULE-IDENTITY
   LAST-UPDATED "201303050000Z"
   ORGANIZATION "Adtran, Inc."
   CONTACT-INFO "http://www.adtran.com"
   DESCRIPTION
      "This MIB defines the objects for the IGMP Cache MIB." 
      
   REVISION "201303050000Z"
   DESCRIPTION "Added adGenIGMPCacheMode."
   
   REVISION "201110310000Z"
   DESCRIPTION "Removed examples from adGenIGMPCacheInterfaceDescription and
                adGenIGMPCacheInterfaceName."
                
   REVISION "201110280000Z"
   DESCRIPTION "Added adGenIGMPCacheInterfaceName OID to adGenIGMPCacheTable."
   
   REVISION "200905080000Z"
   DESCRIPTION "Created"
::= { adGenIGMPCacheID 11 }

--==================================================================================================================

    adGenIGMPCacheTable OBJECT-TYPE
       SYNTAX      SEQUENCE OF AdGenIGMPCacheEntry
       MAX-ACCESS  not-accessible
       STATUS      current
       DESCRIPTION
         "The IGMP Cache Table provides status information on active
          multicast sessions in the system."
       ::= { adGenIGMPCache 1 }

   adGenIGMPCacheEntry OBJECT-TYPE
        SYNTAX      AdGenIGMPCacheEntry
        MAX-ACCESS  not-accessible
        STATUS      current
        DESCRIPTION
          "An entry in the IGMP Cache Table."
        INDEX       { adGenSlotInfoIndex, adGenIGMPCacheAddress, adGenIGMPCacheIndex }
        ::= { adGenIGMPCacheTable 1 }

   AdGenIGMPCacheEntry ::=
       SEQUENCE
       {
         adGenIGMPCacheAddress                  IpAddress,
         adGenIGMPCacheIndex                    Integer32,
         adGenIGMPCacheLastReporter             IpAddress,
         adGenIGMPCacheUpTime                   TimeTicks,
         adGenIGMPCacheExpiryTime               TimeTicks,
         adGenIGMPCacheInterfaceDescription     DisplayString,
         adGenIGMPCacheInterfaceName            DisplayString,
         adGenIGMPCacheMode                     INTEGER
       }

    adGenIGMPCacheAddress OBJECT-TYPE
        SYNTAX     IpAddress
        MAX-ACCESS not-accessible
        STATUS     current
        DESCRIPTION
          "The IP multicast group address for which this entry
           contains information."
        ::= { adGenIGMPCacheEntry 1 }

    adGenIGMPCacheIndex OBJECT-TYPE
        SYNTAX     Integer32
        MAX-ACCESS not-accessible
        STATUS     current
        DESCRIPTION
          "The IGMP network interface index for which this entry contains information
           for an IP multicast group address."
        ::= { adGenIGMPCacheEntry 2 }

    adGenIGMPCacheLastReporter OBJECT-TYPE
        SYNTAX     IpAddress
        MAX-ACCESS read-only
        STATUS     current
        DESCRIPTION
          "The IP address of the source of the last membership report
           received for this IP Multicast group address on this
           interface.  If no membership report has been received, this
           object has the value 0.0.0.0."
        ::= { adGenIGMPCacheEntry 3 }

    adGenIGMPCacheUpTime OBJECT-TYPE
        SYNTAX     TimeTicks
        MAX-ACCESS read-only
        STATUS     current
        DESCRIPTION
          "The time elapsed since this entry was created."
        ::= { adGenIGMPCacheEntry 4 }

    adGenIGMPCacheExpiryTime OBJECT-TYPE
        SYNTAX     TimeTicks
        MAX-ACCESS read-only
        STATUS     current
        DESCRIPTION
          "The minimum amount of time remaining before this entry will
           be aged out."
        ::= { adGenIGMPCacheEntry 5 }

    adGenIGMPCacheInterfaceDescription OBJECT-TYPE
        SYNTAX      DisplayString
        MAX-ACCESS  read-only
        STATUS      current
        DESCRIPTION
          "A text string describing the physical interface associated with this IGMP cache
           table entry."
        ::= { adGenIGMPCacheEntry 6 }

    adGenIGMPCacheInterfaceName OBJECT-TYPE
        SYNTAX      DisplayString
        MAX-ACCESS  read-only
        STATUS      current
        DESCRIPTION
          "A text string indicating the name of the interface associated with this IGMP cache
           table entry."
        ::= { adGenIGMPCacheEntry 7 }

    adGenIGMPCacheMode OBJECT-TYPE
         SYNTAX     INTEGER
                    {
                        v2              (1),
                        v3lite          (2),
                        v2Compatibility (3)
                    }

         MAX-ACCESS   read-only
         STATUS       current
         DESCRIPTION
           "The current IGMP operating mode for the for this IGMP cache table entry."
         ::= { adGenIGMPCacheEntry 8}    
        
END

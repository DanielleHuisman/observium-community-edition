ADTRAN-GENMEF-MIB

-- TITLE:     The ADTRAN MEF MIB
-- PRODUCT:   Metro Ethernet Products
-- VERSION:   1.0
-- DATE:      2/22/07
-- AUTHOR:    Joey Boyd
-- STATUS:    PRELIMINARY

-- This MIB defines the object identifier (OID) for the
-- ADTRAN GENMEF MIB objects

-- HISTORY:
-- 2007/02/22 jlb   STATUS: PRELIMINARY.
-- 2007/02/26 jlb   Added adGenMEFMapAssociatedEVC.  Placed genMEF into the adEoCu branch.
-- 2007/04/02 jlb   Changed the ifIndex support to use adGenMEFEVCIndex, adGenMEFMapIndex,
--		            and adGenMEFProfileIndex
-- 2007/04/10 jlb   Modified the MIB to be fully SNMPv2 compliant.
-- 2007/04/17 jlb   Changed the state variables to use RowStatus instead.  Changed the Create
--                  variables to return the next index.
-- 2007/04/18 jlb   Reordered the tables to group items that are similar.  Added the ability to
--                  to retrieve index values along with the aliases for linked items.
-- 2007/04/19 jlb   Removed adGenMEFPreDefinedMaps.  Added adGenMEFMapBroadcast, adGenMEFMapMulticast,
--                  adGenMEFMapUnicast, and adGenMEFMapL2CP.
-- 2007/04/23 jlb   Added adGenMEFEVCEthertype.
-- 2007/04/25 jlb   Added adGenMEFQueuesTable
-- 2007/04/26 jlb   Split adGenMEFQueuesTable into adGenMEF10100EthQueuesTable, adGenMEFGigEthQueuesTable,
--                  and adGenMEFBondGrpQueuesTable
-- 2007/05/03 jlb   Changed adGenMEFQueueWREDTimeConstant to use an enumerated integer list.
-- 2007/05/23 jlb   Added adGenMEFUNIMapsByAlias and adGenMEFUNIMapsByIndex.
--                  Changed adGenMEFEVCEthertype to read-write.
--                  Added adGenMEFEVCVLANIDPool.
-- 2007/06/07 jlb   Changed adGenMEFProfileEIR from a DisplayString to an INTEGER
-- 2007/08/06 jlb   Added commas to the enum for adGenMEFMapCoS fixing a compile error
-- 2007/09/04 jlb   Changed non enumerated INTEGERs to Integer32
-- 2007/10/02 jlb   Added CoS mapping for p-bit values
-- 2007/10/31 jlb   Added adGenMEFProfileDroppedPackets and changed the CONTACT-INFO.
-- 2008/09/09 Subbu Added UNI Anomalies and Traffic Management Performance Data
-- 2008/09/23 jsb   Reorganized/renamed Traffic Management Performance entries around Policers
-- 2008/10/29 jsb   Cleaning up varbind lists for policer thresholds changes
-- 2009/02/05 jlb   Added adGenMEFProfileCommittedInformationRate and adGenMEFProfileExcessInformationRate.
--                  Deprecated adGenMEFProfileCIR and adGenMEFProfileEIR.
-- 2009/02/05 jlb   Fixed the description for adGenMEFProfileExcessInformationRate.
-- 2009/03/05 sgs   Added adGenMEFQosUntagged.
-- 2009/11/12 jlb   Obsoleted adGenMEFEVCMapsByAlias.  Added adGenMEFEVCNumMaps.
-- 2010/02/03 jlb   Added adGenMEFMapMenCTag and adGenMEFMapMenCTagPri.  Added cTagOptionConflict(14) to adGenMEFMapStatus.
-- 2010/02/23 rpk   Added adGenMEFMapDSCPRange and deprecated adGenMEFMapDSCP
-- 2010/05/05 jb    Changed description for adGenMEFMapAssociatedEVCIndex
-- 2011/01/05 rpk   Added adGenMEFMapIpHost.

-- ******************************************************************************************
DEFINITIONS ::= BEGIN

IMPORTS
   OBJECT-TYPE,
   NOTIFICATION-TYPE,
   MODULE-IDENTITY,
   IpAddress,
   Unsigned32,
   Integer32,
   Gauge32,
   Counter64
      FROM SNMPv2-SMI
   Unsigned64TC
      FROM APPLICATION-MIB
   DisplayString,
   RowStatus
      FROM SNMPv2-TC
   sysName
      FROM SNMPv2-MIB
   OBJECT-GROUP,
   NOTIFICATION-GROUP
      FROM SNMPv2-CONF
   InterfaceIndex,
   ifIndex
      FROM IF-MIB
   adGenPortTrapIdentifier
      FROM ADTRAN-GENPORT-MIB
   adGenMEF,
   adGenMEFID
      FROM ADTRAN-SHARED-EOCU-MIB
   ;

adGenMEFMIB MODULE-IDENTITY
   LAST-UPDATED "201301140000Z"
   ORGANIZATION "Adtran, Inc."
   CONTACT-INFO
     "CND Tech Support
         Postal: ADTRAN, Inc.
                 901 Explorer Blvd.
                 Huntsville, AL  35806
                 Tel: +1 800 726-8663
                 Fax: +1 256 963 6217
                 E-mail: support@adtran.com"
   DESCRIPTION
      	"This MIB defines the objects for the MEF MIB."
   REVISION "201301140000Z"
   DESCRIPTION
		"Added 64 bit Gen Profile oids. As well as updated 32 bit descriptions."
   REVISION "201002030000Z"
   DESCRIPTION
		"Added adGenMEFMapMenCTag and adGenMEFMapMenCTagPri.
		 Added cTagOptionConflict(14) to adGenMEFMapStatus."

   REVISION "200704050000Z"
   DESCRIPTION
		"Created"
::= { adGenMEFID 1 }


--==================================================================================================================

adGenMEFEvents                      OBJECT IDENTIFIER ::= {adGenMEF 0}
adGenMEFProvisioning                OBJECT IDENTIFIER ::= {adGenMEF 1}

adGenMEFMibConformance              OBJECT IDENTIFIER ::= {adGenMEF 5 }
adGenMEFMibGroups                   OBJECT IDENTIFIER ::= {adGenMEFMibConformance 1 }

adGenMEFPerformance                 OBJECT IDENTIFIER ::= {adGenMEF 6}

--==================================================================================================================



--==================================================================================================================
--==================================================================================================================
--==================================================================================================================
adGenMEFProvisioningScalars	    OBJECT IDENTIFIER ::= {adGenMEFProvisioning 1}
      adGenMEFDeleteAll OBJECT-TYPE
         SYNTAX  INTEGER {
            deleteAllMaps(1)
         }
         MAX-ACCESS  read-write
         STATUS  current
         DESCRIPTION
            "Deletes ALL maps."
         ::= { adGenMEFProvisioningScalars 2 }

      adGenMEFEVCIndexNext OBJECT-TYPE
         SYNTAX         Integer32
         MAX-ACCESS     read-only
         STATUS         current
         DESCRIPTION
            "This object contains an appropriate value to
             be used for adGenMEFEVCIndex when creating
             entries in the adGenMEFEVCsTable.  The value
             0 indicates that no unassigned entries are
             available.  The default RowStatus for the newly
             created index is createAndWait."
         ::= { adGenMEFProvisioningScalars 3}

      adGenMEFMapIndexNext OBJECT-TYPE
         SYNTAX         Integer32
         MAX-ACCESS     read-only
         STATUS         current
         DESCRIPTION
            "This object contains an appropriate value to
             be used for adGenMEFMapIndex when creating
             entries in the adGenMEFMapsTable.  The value
             0 indicates that no unassigned entries are
             available.  The default RowStatus for the newly
             created index is createAndWait."
         ::= { adGenMEFProvisioningScalars 4}

      adGenMEFProfileIndexNext OBJECT-TYPE
         SYNTAX         Integer32
         MAX-ACCESS     read-only
         STATUS         current
         DESCRIPTION
            "This object contains an appropriate value to
             be used for adGenMEFProfileIndex when creating
             entries in the adGenMEFProfilesTable.  The value
             0 indicates that no unassigned entries are
             available.  The default RowStatus for the newly
             created index is createAndWait."
         ::= { adGenMEFProvisioningScalars 5}

      adGenMEFEVCEthertype OBJECT-TYPE
         SYNTAX         Integer32
         MAX-ACCESS  read-write
         STATUS  current
         DESCRIPTION
            "This variable specifies the ethertype used by the EVC.
             The default value is 0x8100."
         ::= { adGenMEFProvisioningScalars 6}
--==================================================================================================================

   adGenMEFEVCsTable OBJECT-TYPE
      SYNTAX  SEQUENCE OF AdGenMEFEVCsEntry
      MAX-ACCESS  not-accessible
      STATUS  current
      DESCRIPTION
         "The EVC provisioning table."
      ::= { adGenMEFProvisioning 2 }

   adGenMEFEVCsEntry OBJECT-TYPE
      SYNTAX  AdGenMEFEVCsEntry
      MAX-ACCESS  not-accessible
      STATUS  current
      DESCRIPTION
         "An entry in the EVC provisioning table."
      INDEX  { adGenMEFEVCIndex }
      ::= { adGenMEFEVCsTable 1 }

   AdGenMEFEVCsEntry ::=
      SEQUENCE {
	 adGenMEFEVCIndex
            Integer32,
         adGenMEFEVCRowStatus
            RowStatus,
         adGenMEFEVCAlias
            DisplayString,
         adGenMEFEVCStatus
	    INTEGER,
         adGenMEFEVCPort
	    InterfaceIndex,
         adGenMEFEVCCEVLANIDPreservation
	    INTEGER,
         adGenMEFEVCVLANID
            Integer32,
         adGenMEFEVCMapsByAlias
            DisplayString,
         adGenMEFEVCMapsByIndex
            DisplayString,
		 adGenMEFEVCNumMaps
			Unsigned32
      }

      adGenMEFEVCIndex OBJECT-TYPE
         SYNTAX  Integer32
         MAX-ACCESS  read-only
         STATUS  current
         DESCRIPTION
            "This variable is used as an index into the EVC table."
         ::= { adGenMEFEVCsEntry 1}

      adGenMEFEVCRowStatus OBJECT-TYPE
         SYNTAX  RowStatus
         MAX-ACCESS  read-create
         STATUS  current
         DESCRIPTION
           "This object is used to create
            a new row or modify or delete an
            existing row in this table."
         ::= { adGenMEFEVCsEntry 2}

      adGenMEFEVCAlias OBJECT-TYPE
         SYNTAX  DisplayString
         MAX-ACCESS  read-create
         STATUS  current
         DESCRIPTION
            "A user configurable alias for the EVC.  Upon creation of the EVC,
             the associated alias will default to a unique value."
         ::= { adGenMEFEVCsEntry 3}

      adGenMEFEVCStatus OBJECT-TYPE
         SYNTAX  INTEGER  {
            unknown(1),
            running(2),
            noMapsRunning(3),
            invalidEVCPort(4),
            invalidEVCVID(5),
            disabled(6),
            evcVIDNotAllowed(7),
	    duplicateEVC(8),
	    vlanMgmtConflict(9),
	    transparentEVCConflict(10)
	 }
         MAX-ACCESS  read-only
         STATUS  current
         DESCRIPTION
            "This variable provides the EVC status.  If the EVC status is running,
             then the EVC is applied.  If the EVC status is any other value, then
             the EVC is not applied."
         ::= { adGenMEFEVCsEntry 4}

      adGenMEFEVCPort OBJECT-TYPE
         SYNTAX  InterfaceIndex
         MAX-ACCESS  read-create
         STATUS  current
         DESCRIPTION
	    "This option provisions the physical port or bonding group for the
             selected EVC."
         ::= { adGenMEFEVCsEntry 5}

      adGenMEFEVCCEVLANIDPreservation OBJECT-TYPE
         SYNTAX  INTEGER  {
            disabled(1),
            enabled(2)
	 }
         MAX-ACCESS  read-create
         STATUS  current
         DESCRIPTION
            "This option provisions whether to preserve the CE VLAN tag
             received at the UNI port. Select enabled to push the EVC tag
             onto the CE tag for frames destined for this EVC. Select
             disabled to remove the CE VLAN tag and to add the EVC tag
             for the frames destined for this EVC."
         ::= { adGenMEFEVCsEntry 6}

      adGenMEFEVCVLANID OBJECT-TYPE
         SYNTAX  Integer32
         MAX-ACCESS  read-create
         STATUS  current
         DESCRIPTION
            "This variable specifies the outermost VLAN s-tag VID for
             frames on this EVC.  Selecting 0 to 4095 will apply a single
             VLAN s-tag (with this VID).  Selecting 4096 will force the
             EVC to be in transparent mode and no VLAN s-tag will be
             applied.  Selecting 4097 will leave the value unspecified."
         ::= { adGenMEFEVCsEntry 7}

      adGenMEFEVCMapsByAlias OBJECT-TYPE
         SYNTAX  DisplayString
         MAX-ACCESS  read-only
         STATUS  obsolete
         DESCRIPTION
            "This variable lists the maps that are connected to this EVC.
             The data is represented by a string that is a concatination of
             the map aliases specified by adGenMEFMapAlias.

			 THIS OBJECT HAS BEEN OBSOLETED."

         ::= { adGenMEFEVCsEntry 8}

      adGenMEFEVCMapsByIndex OBJECT-TYPE
         SYNTAX  DisplayString
         MAX-ACCESS  read-only
         STATUS  current
         DESCRIPTION
            "This variable lists the maps that are connected to this EVC.
             The data is represented by a string that is a concatination of
             the map indices specified by adGenMEFMapIndex."
         ::= { adGenMEFEVCsEntry 9}

      adGenMEFEVCNumMaps OBJECT-TYPE
         SYNTAX  Unsigned32
         MAX-ACCESS  read-only
         STATUS  current
         DESCRIPTION
            "This variable returns the number of maps that are connected to this EVC."
         ::= { adGenMEFEVCsEntry 10}

--==================================================================================================================

   adGenMEFMapsTable OBJECT-TYPE
      SYNTAX  SEQUENCE OF AdGenMEFMapsEntry
      MAX-ACCESS  not-accessible
      STATUS  current
      DESCRIPTION
         "The Map provisioning table."
      ::= { adGenMEFProvisioning 3 }

   adGenMEFMapsEntry OBJECT-TYPE
      SYNTAX  AdGenMEFMapsEntry
      MAX-ACCESS  not-accessible
      STATUS  current
      DESCRIPTION
         "An entry in the Map provisioning table."
      INDEX  { adGenMEFMapIndex }
      ::= { adGenMEFMapsTable 1 }

   AdGenMEFMapsEntry ::=
      SEQUENCE {
	 adGenMEFMapIndex
            Integer32,
         adGenMEFMapRowStatus
            RowStatus,
         adGenMEFMapAlias
            DisplayString,
         adGenMEFMapStatus
	    INTEGER,
         adGenMEFMapAssociatedEVCAlias
	    DisplayString,
         adGenMEFMapAssociatedEVCIndex
            Integer32,
         adGenMEFMapUNIPort
	    InterfaceIndex,
         adGenMEFMapCEVLANID
            Integer32,
         adGenMEFMapCEVLANPRI
	    DisplayString,
         adGenMEFMapDSCP
            Integer32,
         adGenMEFMapUntagged
	    INTEGER,
         adGenMEFMapCoS
	    INTEGER,
         adGenMEFMapAttachedProfileAlias
	    DisplayString,
         adGenMEFMapAttachedProfileIndex
            Integer32,
         adGenMEFMapBroadcast
            INTEGER,
         adGenMEFMapMulticast
            INTEGER,
         adGenMEFMapUnicast
            INTEGER,
         adGenMEFMapL2CP
            INTEGER,
	 adGenMEFMapMenCTag
	    INTEGER,
      	 adGenMEFMapMenCTagPri
	    INTEGER,
         adGenMEFMapDSCPRange
	    DisplayString,
	adGenMEFMapIpHost
	    OCTET STRING
	       }

      adGenMEFMapIndex OBJECT-TYPE
         SYNTAX  Integer32
         MAX-ACCESS  read-only
         STATUS  current
         DESCRIPTION
            "This variable is used as an index into the Map table."
         ::= { adGenMEFMapsEntry 1}

      adGenMEFMapRowStatus OBJECT-TYPE
         SYNTAX  RowStatus
         MAX-ACCESS  read-create
         STATUS  current
         DESCRIPTION
           "This object is used to create
            a new row or modify or delete an
            existing row in this table."
         ::= { adGenMEFMapsEntry 2}


      adGenMEFMapAlias OBJECT-TYPE
         SYNTAX  DisplayString
         MAX-ACCESS  read-create
         STATUS  current
         DESCRIPTION
            "A user configurable alias for the Map.  Upon creation of the Map,
             the associated alias will default to a unique value."
         ::= { adGenMEFMapsEntry 3}

      adGenMEFMapStatus OBJECT-TYPE
         SYNTAX  INTEGER  {
            unknown(1),
            running(2),
            noEVCconnected(3),
            evcNotRunning(4),
            invalidUNIport(5),
            disabled(6),
            duplicateMap(7),
	    vlanMGMTconflict(8),
	    tagOptionConflict(9),
	    excessUNIsPerEVC(10),
            uniPortEqualEVCPort(11),
            preserveConflict(12),
            resourcesUnavailable(13),
			cTagOptionConflict(14)
	 }
         MAX-ACCESS  read-only
         STATUS  current
         DESCRIPTION
            "This variable provides the Map status.  If the Map status is running,
             then the Map is applied.  If the Map status is any other value, then
             the Map is not applied."
         ::= { adGenMEFMapsEntry 4}

      adGenMEFMapAssociatedEVCAlias OBJECT-TYPE
         SYNTAX  DisplayString
         MAX-ACCESS  read-create
         STATUS  current
         DESCRIPTION
            "This option is used to configure the EVC, based on the EVC alias
	     (adGenMEFEVCAlias) that is associated with this Map."
         ::= { adGenMEFMapsEntry 5}

      adGenMEFMapAssociatedEVCIndex OBJECT-TYPE
         SYNTAX  Integer32
         MAX-ACCESS  read-create
         STATUS  current
         DESCRIPTION
            "A number greater than zero is used to configure the EVC, based on the EVC index
             (adGenMEFEVCIndex) that is associated with this Map.
             A -1 is used to connect discard the EVC that is associated with this Map.
             A zero means no EVC is associated with this map."
         ::= { adGenMEFMapsEntry 6}

      adGenMEFMapUNIPort OBJECT-TYPE
         SYNTAX  InterfaceIndex
         MAX-ACCESS  read-create
         STATUS  current
         DESCRIPTION
	    "This option provisions the physical port or bonding group at which
             the customer frame is received."
         ::= { adGenMEFMapsEntry 7}

      adGenMEFMapCEVLANID OBJECT-TYPE
         SYNTAX  Integer32
         MAX-ACCESS  read-create
         STATUS  current
         DESCRIPTION
            "This option specifies the VID of the outermost tag of the ingress
             (CE) frame at the UNI port. Selecting 0 to 4095 specifies the CE
             VLAN ID using the selected value. Selecting 4096 leaves the value
             unspecified."
         ::= { adGenMEFMapsEntry 8}

      adGenMEFMapCEVLANPRI OBJECT-TYPE
         SYNTAX  DisplayString
         MAX-ACCESS  read-create
         STATUS  current
         DESCRIPTION
            "This option is used to specify a list of allowable P-bit values
             of the outermost VLAN tag of the ingress (CE) frame as it is
             received on the UNI port.  This option is only valid if the
	     adGenMEFMapCEVLANID is specified.
             Example values:
                   Empty string = Unspecified
                   0,1,2        = P-bit values 0,1,2
                   0-2,5-7      = P-bit values 0,1,2,5,6,7"
         ::= { adGenMEFMapsEntry 9}

      adGenMEFMapDSCP OBJECT-TYPE
         SYNTAX  Integer32
         MAX-ACCESS  read-create
         STATUS  deprecated
         DESCRIPTION
            "This option is the specific DSCP value of the ingress frame at the UNI
             port.  This option is only valid if the adGenMEFMapCEVLANID
             is specified.  The DSCP value is specified by selecting 0 to 63.  64 is
             used for unspecified. 65 is used to specify a range has been configured
	     that cannot be represented by this OID."
         ::= { adGenMEFMapsEntry 10}

      adGenMEFMapUntagged OBJECT-TYPE
         SYNTAX  INTEGER  {
            disallow(1),
            allow(2)
	 }
         MAX-ACCESS  read-create
         STATUS  current
         DESCRIPTION
            "This option is only valid if the adGenMEFMapCEVLANID is
             specified.  It is used to control whether to allow untagged and
             priority tagged frames to ingress the UNI port in addition to frames
             tagged with the specified CE VLAN ID."
         ::= { adGenMEFMapsEntry 11}

      adGenMEFMapCoS OBJECT-TYPE
         SYNTAX  INTEGER  {
            explicit0(1),
            explicit1(2),
            explicit2(3),
            explicit3(4),
            explicit4(5),
            explicit5(6),
            explicit6(7),
            explicit7(8),
	    inheritFromCEVLANPbits(9)
	 }
         MAX-ACCESS  read-create
         STATUS  current
         DESCRIPTION
            "This option controls how the frames are classified for this Map.
             The CoS can be set explicitly or inherited from the CE VLAN P-bit
             value."
         ::= { adGenMEFMapsEntry 12}

      adGenMEFMapAttachedProfileAlias OBJECT-TYPE
         SYNTAX  DisplayString
         MAX-ACCESS  read-only
         STATUS  current
         DESCRIPTION
            "This variable shows the profile that is attached to this map.
	     The profile is represented by its alias given by adGenMEFProfileAlias."
         ::= { adGenMEFMapsEntry 13}

      adGenMEFMapAttachedProfileIndex OBJECT-TYPE
         SYNTAX  Integer32
         MAX-ACCESS  read-only
         STATUS  current
         DESCRIPTION
            "This variable shows the profile that is attached to this map.
             The profile is represented by its index given by adGenMEFProfileIndex."
         ::= { adGenMEFMapsEntry 14}

      adGenMEFMapBroadcast OBJECT-TYPE
         SYNTAX  INTEGER  {
            disallow(1),
            allow(2)
	 }
         MAX-ACCESS  read-create
         STATUS  current
         DESCRIPTION
             "This option is used to control whether to allow broadcast traffic
             to ingress the UNI port."
         ::= { adGenMEFMapsEntry 15}

      adGenMEFMapMulticast OBJECT-TYPE
         SYNTAX  INTEGER  {
            disallow(1),
            allow(2)
	 }
         MAX-ACCESS  read-create
         STATUS  current
         DESCRIPTION
             "This option is used to control whether to allow multicast traffic
             to ingress the UNI port."
         ::= { adGenMEFMapsEntry 16}

      adGenMEFMapUnicast OBJECT-TYPE
         SYNTAX  INTEGER  {
            disallow(1),
            allow(2)
	 }
         MAX-ACCESS  read-create
         STATUS  current
         DESCRIPTION
             "This option is used to control whether to allow unicast traffic
             to ingress the UNI port."
         ::= { adGenMEFMapsEntry 17}

      adGenMEFMapL2CP OBJECT-TYPE
         SYNTAX  INTEGER  {
            disallow(1),
            allow(2)
	 }
         MAX-ACCESS  read-create
         STATUS  current
         DESCRIPTION
             "This option is used to control whether to allow L2CP traffic
             to ingress the UNI port."
         ::= { adGenMEFMapsEntry 18}

   	  adGenMEFMapMenCTag OBJECT-TYPE
      	  SYNTAX  INTEGER(2..4095)
      	  MAX-ACCESS  read-create
          STATUS  current
          DESCRIPTION
         	"Specify the c-tag to be applied on traffic egressing the connected EVC.
			 A value of 4095 indicates that no c-tag is applied."
         ::= { adGenMEFMapsEntry 19}

      adGenMEFMapMenCTagPri OBJECT-TYPE
         SYNTAX  INTEGER  {
            explicit0(1),
            explicit1(2),
            explicit2(3),
            explicit3(4),
            explicit4(5),
            explicit5(6),
            explicit6(7),
            explicit7(8),
	    	inheritFromCEVLANPbits(9)
	 }
         MAX-ACCESS  read-create
         STATUS  current
         DESCRIPTION
            "This option controls how the frames are classified for this Map.
             The c-tag p-bits can be set explicitly or inherited from the CE VLAN P-bit
             value."
         ::= { adGenMEFMapsEntry 20}

       adGenMEFMapDSCPRange OBJECT-TYPE
         SYNTAX  DisplayString
         MAX-ACCESS  read-create
         STATUS  current
         DESCRIPTION
            "This option specifies a list of allowable DSCP values on the
             ingress frames at the UNI port. Each DSCP value can be from 0 to 63.
             Example values:
                   Empty string = Unspecified
                   0,1,2        = DSCP values 0,1,2
                   0-2,5-7      = DSCP values 0,1,2,5,6,7"
         ::= { adGenMEFMapsEntry 21}

       adGenMEFMapIpHost OBJECT-TYPE
    	 SYNTAX  OCTET STRING (SIZE (0..84))
    	 MAX-ACCESS  read-create
    	 STATUS  current
         DESCRIPTION
            "This option connects the evc-map to an existing IP-Host in the system.
             Setting the string to zero-length will clear the IP-Host connection.

	     To connect an IP-host, the octet string is formatted as follows:
	         Octets 0-3:	32-bit ifIndex of slot where IP-Host is located
		 Octets 4-n:	Ascii encoding of IP-Host name.  n can range from 5-83, allowing from 1 to 80 character IP-Host name.

	     Example:
		IP-Host 'ip' (i = 0x69, p = 0x70)
		on slot 2, where slot 2 has an ifIndex of 2,999,999 (0x002DC6BF)

		The value of this OID would be:
		00.2D.C6.BF.69.70
	     "
         ::= { adGenMEFMapsEntry 22 }



--==================================================================================================================

   adGenMEFProfilesTable OBJECT-TYPE
      SYNTAX  SEQUENCE OF AdGenMEFProfilesEntry
      MAX-ACCESS  not-accessible
      STATUS  current
      DESCRIPTION
         "The Profile provisioning table."
      ::= { adGenMEFProvisioning 4 }

   adGenMEFProfilesEntry OBJECT-TYPE
      SYNTAX  AdGenMEFProfilesEntry
      MAX-ACCESS  not-accessible
      STATUS  current
      DESCRIPTION
         "An entry in the Profile provisioning table."
      INDEX  { adGenMEFProfileIndex }
      ::= { adGenMEFProfilesTable 1 }

   AdGenMEFProfilesEntry ::=
      SEQUENCE {
	 adGenMEFProfileIndex
            Integer32,
         adGenMEFProfileRowStatus
            RowStatus,
         adGenMEFProfileAlias
            DisplayString,
         adGenMEFProfileStatus
	    INTEGER,
         adGenMEFProfileApp
	    INTEGER,
         adGenMEFProfileUNIPort
	    InterfaceIndex,
         adGenMEFProfileEVC
            Integer32,
	 adGenMEFProfileCoSValue
            DisplayString,
         adGenMEFProfileRateCoupling
	    INTEGER,
         adGenMEFProfileCIR
            Integer32,
         adGenMEFProfileCBS
            Integer32,
         adGenMEFProfileEIR
            Integer32,
	 adGenMEFProfileEBS
            Integer32,
	 adGenMEFProfileAddMap
	    DisplayString,
	 adGenMEFProfileRemoveMap
	    DisplayString,
         adGenMEFProfileMapsByAlias
	    DisplayString,
         adGenMEFProfileMapsByIndex
            DisplayString,
         adGenMEFProfileDroppedPackets
            Gauge32,
		 adGenMEFProfileCommittedInformationRate
			Integer32,
		 adGenMEFProfileExcessInformationRate
			Integer32
      }

      adGenMEFProfileIndex OBJECT-TYPE
         SYNTAX  Integer32
         MAX-ACCESS  read-only
         STATUS  current
         DESCRIPTION
            "This variable is used as an index into the Profiles table."
         ::= { adGenMEFProfilesEntry 1}

      adGenMEFProfileRowStatus OBJECT-TYPE
         SYNTAX  RowStatus
         MAX-ACCESS  read-create
         STATUS  current
         DESCRIPTION
           "This object is used to create
            a new row or modify or delete an
            existing row in this table."
         ::= { adGenMEFProfilesEntry 2}

      adGenMEFProfileAlias OBJECT-TYPE
         SYNTAX  DisplayString
         MAX-ACCESS  read-create
         STATUS  current
         DESCRIPTION
            "A user configurable alias for the Profile.  Upon creation of
             the Profile, the associated alias will default to a unique value."
         ::= { adGenMEFProfilesEntry 3}

      adGenMEFProfileStatus OBJECT-TYPE
         SYNTAX  INTEGER  {
            unknown(1),
            running(2),
            disabled(3),
            invalidUNIPort(4),
            invalidEVC(5),
            duplicateProfile(6),
            invalidRates(7),
            invalidApplication(8),
            invalidCoS(9),
            mapConflict(10)
	 }
         MAX-ACCESS  read-only
         STATUS  current
         DESCRIPTION
            "This variable provides the Profile status.  If the Profile status
             is running, then the Profile is applied.  If the Profile status
             is any other value, then the Profile is not applied."
         ::= { adGenMEFProfilesEntry 4}

      adGenMEFProfileApp OBJECT-TYPE
         SYNTAX  INTEGER  {
	    unspecified(1),
	    uniPort(2),
	    evc(3),
	    ceVLANCoS(4),
	    custom(5)
         }
         MAX-ACCESS  read-create
         STATUS  current
         DESCRIPTION
            "This variable provides the scope of the profile. For uniPort, the
             profile is applied to all maps of a specific UNI port.  For EVC, the
             profile is applied to all maps associated with a specific EVC. For
             ceVLANCoS, the profile is applied to a set of CoS values for a
             given EVC.  For custom, the profile is applied to all maps added to
	     the profile using adGenMEFProfileAddMap."
         ::= { adGenMEFProfilesEntry 5}

      adGenMEFProfileUNIPort OBJECT-TYPE
         SYNTAX  InterfaceIndex
         MAX-ACCESS  read-create
         STATUS  current
         DESCRIPTION
            "The variable is used if adGenMEFProfileApp is set
             to uniPort."
         ::= { adGenMEFProfilesEntry 6}

      adGenMEFProfileEVC OBJECT-TYPE
         SYNTAX  Integer32
         MAX-ACCESS  read-create
         STATUS  current
         DESCRIPTION
            "The variable is used if adGenMEFProfileApp is set
             to evc or ceVLANCoS.  The value is the adGenMEFEVCIndex of the EVC."
         ::= { adGenMEFProfilesEntry 7}

      adGenMEFProfileCoSValue OBJECT-TYPE
         SYNTAX  DisplayString
         MAX-ACCESS  read-create
         STATUS  current
         DESCRIPTION
            "The variable is used if adGenMEFProfileApp is set
             to ceVLANCoS.
             Example values:
                   Empty string = Unspecified
                   0,1,2        = P-bit values 0,1,2
                   0-2,5-7      = P-bit values 0,1,2,5,6,7"
         ::= { adGenMEFProfilesEntry 8}

      adGenMEFProfileRateCoupling OBJECT-TYPE
         SYNTAX  INTEGER  {
            disabled(1),
            enabled(2)
	 }
         MAX-ACCESS  read-create
         STATUS  current
         DESCRIPTION
            "This variable controls the relationship of the CIR to
             the EIR.  If enabled, the EIR value is additive to the CIR.
             If disabled, the EIR is inclusive of the CIR."
         ::= { adGenMEFProfilesEntry 9}

      adGenMEFProfileCIR OBJECT-TYPE
         SYNTAX  Integer32
         MAX-ACCESS  read-create
         STATUS  deprecated
         DESCRIPTION
            "This variable is used to configure the CIR (in kbps)."
         ::= { adGenMEFProfilesEntry 10}

      adGenMEFProfileCBS OBJECT-TYPE
         SYNTAX  Integer32
         MAX-ACCESS  read-create
         STATUS  current
         DESCRIPTION
            "This variable is used to configure the CBS (in bytes)."
         ::= { adGenMEFProfilesEntry 11}

      adGenMEFProfileEIR OBJECT-TYPE
         SYNTAX  Integer32
         MAX-ACCESS  read-create
         STATUS  deprecated
         DESCRIPTION
            "This variable is used to configure the EIR (in kbps).
            A null string is used to configure the EIR for no limit.
            The maximum CIR value is 100000."
         ::= { adGenMEFProfilesEntry 12}

      adGenMEFProfileEBS OBJECT-TYPE
         SYNTAX  Integer32
         MAX-ACCESS  read-create
         STATUS  current
         DESCRIPTION
            "This variable is used to configure the EBS (in bytes)."
         ::= { adGenMEFProfilesEntry 13}

      adGenMEFProfileAddMap OBJECT-TYPE
         SYNTAX  DisplayString
         MAX-ACCESS  read-create
         STATUS  current
         DESCRIPTION
            "This variable is used to add a map to the profile.  The map is
	     referenced by adGenMEFMapAlias.  This is only applicable when
	     adGenMEFProfileApp is set to custom(5)."
         ::= { adGenMEFProfilesEntry 14}

      adGenMEFProfileRemoveMap OBJECT-TYPE
         SYNTAX  DisplayString
         MAX-ACCESS  read-create
         STATUS  current
         DESCRIPTION
            "This variable is used to remove a map from the profile.  The map is
	     referenced by adGenMEFMapAlias.  This is only applicable when
	     adGenMEFProfileApp is set to custom(5)."
         ::= { adGenMEFProfilesEntry 15}

      adGenMEFProfileMapsByAlias OBJECT-TYPE
         SYNTAX  DisplayString
         MAX-ACCESS  read-only
         STATUS  current
         DESCRIPTION
            "This variable lists the maps that are connected to this profile.
             The data is represented by a string that is a concatination of
             the map aliases specified by adGenMEFMapAlias."
         ::= { adGenMEFProfilesEntry 16}

      adGenMEFProfileMapsByIndex OBJECT-TYPE
         SYNTAX  DisplayString
         MAX-ACCESS  read-only
         STATUS  current
         DESCRIPTION
            "This variable lists the maps that are connected to this profile.
             The data is represented by a string that is a concatination of
             the map indices specified by adGenMEFMapIndex."
         ::= { adGenMEFProfilesEntry 17}

      adGenMEFProfileDroppedPackets OBJECT-TYPE
         SYNTAX  Gauge32
         MAX-ACCESS  read-only
         STATUS  current
         DESCRIPTION
            "A count of the packets dropped due to this profile's bandwidth
             restriction (CIR + EIR)."
         ::= { adGenMEFProfilesEntry 18}

      adGenMEFProfileCommittedInformationRate OBJECT-TYPE
         SYNTAX  Integer32
         MAX-ACCESS  read-create
         STATUS  current
         DESCRIPTION
            "This variable is used to configure the CIR (in kbps)."
         ::= { adGenMEFProfilesEntry 19}

      adGenMEFProfileExcessInformationRate OBJECT-TYPE
         SYNTAX  Integer32
         MAX-ACCESS  read-create
         STATUS  current
         DESCRIPTION
            "This variable is used to configure the EIR (in kbps).
            A SET to a value of -1 is used to configure the EIR for no limit."
         ::= { adGenMEFProfilesEntry 20}

--==================================================================================================================
   adGenMEFQueueScalars                 OBJECT IDENTIFIER ::= { adGenMEFProvisioning 5 }

      adGenMEFQueueWREDTimeConstant OBJECT-TYPE
         SYNTAX  INTEGER  {
            approx2ms(1),
            approx4ms(2),
            approx8ms(3),
            approx16ms(4),
            approx32ms(5),
            approx62ms(6),
            approx125ms(7),
            approx250ms(8),
            approx500ms(9)
         }
         MAX-ACCESS  read-write
         STATUS  current
         DESCRIPTION
            "This variable is used to provision the WRED time
             constant for all queues."
         ::= { adGenMEFQueueScalars 1}

      adGenMEFQueueCoSMapForPri0 OBJECT-TYPE
         SYNTAX  Integer32
         MAX-ACCESS  read-write
         STATUS  current
         DESCRIPTION
            "This variable is used to provision the CoS queue that all
             traffic with a p-bit value of 0 gets mapped into.
             The valid range is 0 - 7 where 7 gets treated with the
             highest priority.  The default value is 1 per IEEE 802.1Q-2005"
         ::= { adGenMEFQueueScalars 2}

      adGenMEFQueueCoSMapForPri1 OBJECT-TYPE
         SYNTAX  Integer32
         MAX-ACCESS  read-write
         STATUS  current
         DESCRIPTION
            "This variable is used to provision the CoS queue that all
             traffic with a p-bit value of 1 gets mapped into.
             The valid range is 0 - 7 where 7 gets treated with the
             highest priority.  The default value is 0 per IEEE 802.1Q-2005"
         ::= { adGenMEFQueueScalars 3}

      adGenMEFQueueCoSMapForPri2 OBJECT-TYPE
         SYNTAX  Integer32
         MAX-ACCESS  read-write
         STATUS  current
         DESCRIPTION
            "This variable is used to provision the CoS queue that all
             traffic with a p-bit value of 2 gets mapped into.
             The valid range is 0 - 7 where 7 gets treated with the
             highest priority.  The default value is 2 per IEEE 802.1Q-2005"
         ::= { adGenMEFQueueScalars 4}

      adGenMEFQueueCoSMapForPri3 OBJECT-TYPE
         SYNTAX  Integer32
         MAX-ACCESS  read-write
         STATUS  current
         DESCRIPTION
            "This variable is used to provision the CoS queue that all
             traffic with a p-bit value of 3 gets mapped into.
             The valid range is 0 - 7 where 7 gets treated with the
             highest priority.  The default value is 3 per IEEE 802.1Q-2005"
         ::= { adGenMEFQueueScalars 5}

      adGenMEFQueueCoSMapForPri4 OBJECT-TYPE
         SYNTAX  Integer32
         MAX-ACCESS  read-write
         STATUS  current
         DESCRIPTION
            "This variable is used to provision the CoS queue that all
             traffic with a p-bit value of 4 gets mapped into.
             The valid range is 0 - 7 where 7 gets treated with the
             highest priority.  The default value is 4 per IEEE 802.1Q-2005"
         ::= { adGenMEFQueueScalars 6}

      adGenMEFQueueCoSMapForPri5 OBJECT-TYPE
         SYNTAX  Integer32
         MAX-ACCESS  read-write
         STATUS  current
         DESCRIPTION
            "This variable is used to provision the CoS queue that all
             traffic with a p-bit value of 5 gets mapped into.
             The valid range is 0 - 7 where 7 gets treated with the
             highest priority.  The default value is 5 per IEEE 802.1Q-2005"
         ::= { adGenMEFQueueScalars 7}

      adGenMEFQueueCoSMapForPri6 OBJECT-TYPE
         SYNTAX  Integer32
         MAX-ACCESS  read-write
         STATUS  current
         DESCRIPTION
            "This variable is used to provision the CoS queue that all
             traffic with a p-bit value of 6 gets mapped into.
             The valid range is 0 - 7 where 7 gets treated with the
             highest priority.  The default value is 6 per IEEE 802.1Q-2005"
         ::= { adGenMEFQueueScalars 8}

      adGenMEFQueueCoSMapForPri7 OBJECT-TYPE
         SYNTAX  Integer32
         MAX-ACCESS  read-write
         STATUS  current
         DESCRIPTION
            "This variable is used to provision the CoS queue that all
             traffic with a p-bit value of 7 gets mapped into.
             The valid range is 0 - 7 where 7 gets treated with the
             highest priority.  The default value is 7 per IEEE 802.1Q-2005"
         ::= { adGenMEFQueueScalars 9}

      adGenMEFQosUntagged OBJECT-TYPE
         SYNTAX  Integer32
         MAX-ACCESS  read-write
         STATUS  current
         DESCRIPTION
            "This variable is used to provision the MEN priority for
             untagged traffic.  The valid range is 0 - 7 where 7 gets
             treated with the highest priority.  The default value is
             0 per IEEE 802.1Q-2005"
         ::= { adGenMEFQueueScalars 10}

--==================================================================================================================
   adGenMEF10100EthQueuesTable OBJECT-TYPE
      SYNTAX  SEQUENCE OF AdGenMEF10100EthQueuesEntry
      MAX-ACCESS  not-accessible
      STATUS  current
      DESCRIPTION
         "The 10/100 Ethernet Queue provisioning table."
      ::= { adGenMEFProvisioning 6 }

   adGenMEF10100EthQueuesEntry OBJECT-TYPE
      SYNTAX  AdGenMEF10100EthQueuesEntry
      MAX-ACCESS  not-accessible
      STATUS  current
      DESCRIPTION
         "An entry in the 10/100 Ethernet Queue provisioning table."
      INDEX  { ifIndex, adGenMEF10100EthCoSIndex }
      ::= { adGenMEF10100EthQueuesTable 1 }

   AdGenMEF10100EthQueuesEntry ::=
      SEQUENCE {
         adGenMEF10100EthCoSIndex
            Integer32,
         adGenMEF10100EthQueueMaxDepth
            Integer32,
         adGenMEF10100EthQueueWREDState
            INTEGER,
         adGenMEF10100EthQueueWREDGreenMaxThresh
            Integer32,
         adGenMEF10100EthQueueWREDGreenMinThresh
            Integer32,
         adGenMEF10100EthQueueWREDGreenDropProb
            Integer32,
         adGenMEF10100EthQueueWREDYellowMaxThresh
            Integer32,
         adGenMEF10100EthQueueWREDYellowMinThresh
            Integer32,
         adGenMEF10100EthQueueWREDYellowDropProb
            Integer32
      }

      adGenMEF10100EthCoSIndex OBJECT-TYPE
         SYNTAX  Integer32
         MAX-ACCESS  read-only
         STATUS  current
         DESCRIPTION
            "This index represents the CoS value associated with
             the queue.  The value of the index is obtained by adding
             one(1) to the CoS value (e.g. CoS 0 = CoSIndex 1)."
         ::= { adGenMEF10100EthQueuesEntry 1}

      adGenMEF10100EthQueueMaxDepth OBJECT-TYPE
         SYNTAX  Integer32
         MAX-ACCESS  read-write
         STATUS  current
         DESCRIPTION
            "This variable is used to provision the maximum depth
             of the selected 10/100 Ethernet queue."
         ::= { adGenMEF10100EthQueuesEntry 2}

      adGenMEF10100EthQueueWREDState OBJECT-TYPE
         SYNTAX  INTEGER  {
            disabled(1),
            enabled(2)
	 }
         MAX-ACCESS  read-write
         STATUS  current
         DESCRIPTION
            "This variable is used to provision the WRED state
             of the selected 10/100 Ethernet queue."
         ::= { adGenMEF10100EthQueuesEntry 3}

      adGenMEF10100EthQueueWREDGreenMaxThresh OBJECT-TYPE
         SYNTAX  Integer32
         MAX-ACCESS  read-write
         STATUS  current
         DESCRIPTION
            "This variable is used to provision the WRED maximum green
             traffic threshold of the selected 10/100 Ethernet queue."
         ::= { adGenMEF10100EthQueuesEntry 4}

      adGenMEF10100EthQueueWREDGreenMinThresh OBJECT-TYPE
         SYNTAX  Integer32
         MAX-ACCESS  read-write
         STATUS  current
         DESCRIPTION
            "This variable is used to provision the WRED minimum green
             traffic threshold of the selected 10/100 Ethernet queue."
         ::= { adGenMEF10100EthQueuesEntry 5}

      adGenMEF10100EthQueueWREDGreenDropProb OBJECT-TYPE
         SYNTAX  Integer32
         MAX-ACCESS  read-write
         STATUS  current
         DESCRIPTION
            "This variable is used to provision the WRED drop probability of
             the green traffic in the selected 10/100 Ethernet queue."
         ::= { adGenMEF10100EthQueuesEntry 6}

      adGenMEF10100EthQueueWREDYellowMaxThresh OBJECT-TYPE
         SYNTAX  Integer32
         MAX-ACCESS  read-write
         STATUS  current
         DESCRIPTION
            "This variable is used to provision the WRED maximum yellow
             traffic threshold of the selected 10/100 Ethernet queue."
         ::= { adGenMEF10100EthQueuesEntry 7}

      adGenMEF10100EthQueueWREDYellowMinThresh OBJECT-TYPE
         SYNTAX  Integer32
         MAX-ACCESS  read-write
         STATUS  current
         DESCRIPTION
            "This variable is used to provision the WRED minimum yellow
             traffic threshold of the selected 10/100 Ethernet queue."
         ::= { adGenMEF10100EthQueuesEntry 8}

      adGenMEF10100EthQueueWREDYellowDropProb OBJECT-TYPE
         SYNTAX  Integer32
         MAX-ACCESS  read-write
         STATUS  current
         DESCRIPTION
            "This variable is used to provision the WRED drop probability of
             the yellow traffic in the selected 10/100 Ethernet queue."
         ::= { adGenMEF10100EthQueuesEntry 9}

--==================================================================================================================

   adGenMEFGigEthQueuesTable OBJECT-TYPE
      SYNTAX  SEQUENCE OF AdGenMEFGigEthQueuesEntry
      MAX-ACCESS  not-accessible
      STATUS  current
      DESCRIPTION
         "The Gigabit Ethernet Queue provisioning table."
      ::= { adGenMEFProvisioning 7 }

   adGenMEFGigEthQueuesEntry OBJECT-TYPE
      SYNTAX  AdGenMEFGigEthQueuesEntry
      MAX-ACCESS  not-accessible
      STATUS  current
      DESCRIPTION
         "An entry in the Gigabit Ethernet Queue provisioning table."
      INDEX  { ifIndex, adGenMEFGigEthCoSIndex }
      ::= { adGenMEFGigEthQueuesTable 1 }

   AdGenMEFGigEthQueuesEntry ::=
      SEQUENCE {
         adGenMEFGigEthCoSIndex
            Integer32,
         adGenMEFGigEthQueueMaxDepth
            Integer32,
         adGenMEFGigEthQueueWREDState
            INTEGER,
         adGenMEFGigEthQueueWREDGreenMaxThresh
            Integer32,
         adGenMEFGigEthQueueWREDGreenMinThresh
            Integer32,
         adGenMEFGigEthQueueWREDGreenDropProb
            Integer32,
         adGenMEFGigEthQueueWREDYellowMaxThresh
            Integer32,
         adGenMEFGigEthQueueWREDYellowMinThresh
            Integer32,
         adGenMEFGigEthQueueWREDYellowDropProb
            Integer32
      }

      adGenMEFGigEthCoSIndex OBJECT-TYPE
         SYNTAX  Integer32
         MAX-ACCESS  read-only
         STATUS  current
         DESCRIPTION
            "This index represents the CoS value associated with
             the queue.  The value of the index is obtained by adding
             one(1) to the CoS value (e.g. CoS 0 = CoSIndex 1)."
         ::= { adGenMEFGigEthQueuesEntry 1}

      adGenMEFGigEthQueueMaxDepth OBJECT-TYPE
         SYNTAX  Integer32
         MAX-ACCESS  read-write
         STATUS  current
         DESCRIPTION
            "This variable is used to provision the maximum depth
             of the selected Gigabit Ethernet queue."
         ::= { adGenMEFGigEthQueuesEntry 2}

      adGenMEFGigEthQueueWREDState OBJECT-TYPE
         SYNTAX  INTEGER  {
            disabled(1),
            enabled(2)
	 }
         MAX-ACCESS  read-write
         STATUS  current
         DESCRIPTION
            "This variable is used to provision the WRED state
             of the selected Gigabit Ethernet queue."
         ::= { adGenMEFGigEthQueuesEntry 3}

      adGenMEFGigEthQueueWREDGreenMaxThresh OBJECT-TYPE
         SYNTAX  Integer32
         MAX-ACCESS  read-write
         STATUS  current
         DESCRIPTION
            "This variable is used to provision the WRED maximum green
             traffic threshold of the selected Gigabit Ethernet queue."
         ::= { adGenMEFGigEthQueuesEntry 4}

      adGenMEFGigEthQueueWREDGreenMinThresh OBJECT-TYPE
         SYNTAX  Integer32
         MAX-ACCESS  read-write
         STATUS  current
         DESCRIPTION
            "This variable is used to provision the WRED minimum green
             traffic threshold of the selected Gigabit Ethernet queue."
         ::= { adGenMEFGigEthQueuesEntry 5}

      adGenMEFGigEthQueueWREDGreenDropProb OBJECT-TYPE
         SYNTAX  Integer32
         MAX-ACCESS  read-write
         STATUS  current
         DESCRIPTION
            "This variable is used to provision the WRED drop probability of
             the green traffic in the selected Gigabit Ethernet queue."
         ::= { adGenMEFGigEthQueuesEntry 6}

      adGenMEFGigEthQueueWREDYellowMaxThresh OBJECT-TYPE
         SYNTAX  Integer32
         MAX-ACCESS  read-write
         STATUS  current
         DESCRIPTION
            "This variable is used to provision the WRED maximum yellow
             traffic threshold of the selected Gigabit Ethernet queue."
         ::= { adGenMEFGigEthQueuesEntry 7}

      adGenMEFGigEthQueueWREDYellowMinThresh OBJECT-TYPE
         SYNTAX  Integer32
         MAX-ACCESS  read-write
         STATUS  current
         DESCRIPTION
            "This variable is used to provision the WRED minimum yellow
             traffic threshold of the selected Gigabit Ethernet queue."
         ::= { adGenMEFGigEthQueuesEntry 8}

      adGenMEFGigEthQueueWREDYellowDropProb OBJECT-TYPE
         SYNTAX  Integer32
         MAX-ACCESS  read-write
         STATUS  current
         DESCRIPTION
            "This variable is used to provision the WRED drop probability of
             the yellow traffic in the selected Gigabit Ethernet queue."
         ::= { adGenMEFGigEthQueuesEntry 9}

--==================================================================================================================

   adGenMEFBondGrpQueuesTable OBJECT-TYPE
      SYNTAX  SEQUENCE OF AdGenMEFBondGrpQueuesEntry
      MAX-ACCESS  not-accessible
      STATUS  current
      DESCRIPTION
         "The bonding group Queue provisioning table."
      ::= { adGenMEFProvisioning 8 }

   adGenMEFBondGrpQueuesEntry OBJECT-TYPE
      SYNTAX  AdGenMEFBondGrpQueuesEntry
      MAX-ACCESS  not-accessible
      STATUS  current
      DESCRIPTION
         "An entry in the bonding group Queue provisioning table."
      INDEX  { ifIndex, adGenMEFBondGrpCoSIndex }
      ::= { adGenMEFBondGrpQueuesTable 1 }

   AdGenMEFBondGrpQueuesEntry ::=
      SEQUENCE {
         adGenMEFBondGrpCoSIndex
            Integer32,
         adGenMEFBondGrpQueueMaxDepth
            Integer32,
         adGenMEFBondGrpQueueWREDState
            INTEGER,
         adGenMEFBondGrpQueueWREDGreenMaxThresh
            Integer32,
         adGenMEFBondGrpQueueWREDGreenMinThresh
            Integer32,
         adGenMEFBondGrpQueueWREDGreenDropProb
            Integer32,
         adGenMEFBondGrpQueueWREDYellowMaxThresh
            Integer32,
         adGenMEFBondGrpQueueWREDYellowMinThresh
            Integer32,
         adGenMEFBondGrpQueueWREDYellowDropProb
            Integer32
      }

      adGenMEFBondGrpCoSIndex OBJECT-TYPE
         SYNTAX  Integer32
         MAX-ACCESS  read-only
         STATUS  current
         DESCRIPTION
            "This index represents the CoS value associated with
             the queue.  The value of the index is obtained by adding
             one(1) to the CoS value (e.g. CoS 0 = CoSIndex 1)."
         ::= { adGenMEFBondGrpQueuesEntry 1}

      adGenMEFBondGrpQueueMaxDepth OBJECT-TYPE
         SYNTAX  Integer32
         MAX-ACCESS  read-write
         STATUS  current
         DESCRIPTION
            "This variable is used to provision the maximum depth
             of the selected bonding group queue."
         ::= { adGenMEFBondGrpQueuesEntry 2}

      adGenMEFBondGrpQueueWREDState OBJECT-TYPE
         SYNTAX  INTEGER  {
            disabled(1),
            enabled(2)
	 }
         MAX-ACCESS  read-write
         STATUS  current
         DESCRIPTION
            "This variable is used to provision the WRED state
             of the selected bonding group queue."
         ::= { adGenMEFBondGrpQueuesEntry 3}

      adGenMEFBondGrpQueueWREDGreenMaxThresh OBJECT-TYPE
         SYNTAX  Integer32
         MAX-ACCESS  read-write
         STATUS  current
         DESCRIPTION
            "This variable is used to provision the WRED maximum green
             traffic threshold of the selected bonding group queue."
         ::= { adGenMEFBondGrpQueuesEntry 4}

      adGenMEFBondGrpQueueWREDGreenMinThresh OBJECT-TYPE
         SYNTAX  Integer32
         MAX-ACCESS  read-write
         STATUS  current
         DESCRIPTION
            "This variable is used to provision the WRED minimum green
             traffic threshold of the selected bonding group queue."
         ::= { adGenMEFBondGrpQueuesEntry 5}

      adGenMEFBondGrpQueueWREDGreenDropProb OBJECT-TYPE
         SYNTAX  Integer32
         MAX-ACCESS  read-write
         STATUS  current
         DESCRIPTION
            "This variable is used to provision the WRED drop probability of
             the green traffic in the selected bonding group queue."
         ::= { adGenMEFBondGrpQueuesEntry 6}

      adGenMEFBondGrpQueueWREDYellowMaxThresh OBJECT-TYPE
         SYNTAX  Integer32
         MAX-ACCESS  read-write
         STATUS  current
         DESCRIPTION
            "This variable is used to provision the WRED maximum yellow
             traffic threshold of the selected bonding group queue."
         ::= { adGenMEFBondGrpQueuesEntry 7}

      adGenMEFBondGrpQueueWREDYellowMinThresh OBJECT-TYPE
         SYNTAX  Integer32
         MAX-ACCESS  read-write
         STATUS  current
         DESCRIPTION
            "This variable is used to provision the WRED minimum yellow
             traffic threshold of the selected bonding group queue."
         ::= { adGenMEFBondGrpQueuesEntry 8}

      adGenMEFBondGrpQueueWREDYellowDropProb OBJECT-TYPE
         SYNTAX  Integer32
         MAX-ACCESS  read-write
         STATUS  current
         DESCRIPTION
            "This variable is used to provision the WRED drop probability of
             the yellow traffic in the selected bonding group queue."
         ::= { adGenMEFBondGrpQueuesEntry 9}

--==================================================================================================================

   adGenMEFUNITable OBJECT-TYPE
      SYNTAX  SEQUENCE OF AdGenMEFUNIEntry
      MAX-ACCESS  not-accessible
      STATUS  current
      DESCRIPTION
         "The UNI provisioning table."
      ::= { adGenMEFProvisioning 9 }

   adGenMEFUNIEntry OBJECT-TYPE
      SYNTAX  AdGenMEFUNIEntry
      MAX-ACCESS  not-accessible
      STATUS  current
      DESCRIPTION
         "An entry in the UNI provisioning table."
      INDEX  { ifIndex }
      ::= { adGenMEFUNITable 1 }

   AdGenMEFUNIEntry ::=
      SEQUENCE {
         adGenMEFUNIMapsByAlias
            DisplayString,
         adGenMEFUNIMapsByIndex
            DisplayString
      }

      adGenMEFUNIMapsByAlias OBJECT-TYPE
         SYNTAX  DisplayString
         MAX-ACCESS  read-only
         STATUS  current
         DESCRIPTION
            "This variable lists the maps that are connected to this UNI.
             The data is represented by a string that is a concatination of
             the map aliases specified by adGenMEFMapAlias."
         ::= { adGenMEFUNIEntry 1}

      adGenMEFUNIMapsByIndex OBJECT-TYPE
         SYNTAX  DisplayString
         MAX-ACCESS  read-only
         STATUS  current
         DESCRIPTION
            "This variable lists the maps that are connected to this UNI.
             The data is represented by a string that is a concatination of
             the map indices specified by adGenMEFMapIndex."
         ::= { adGenMEFUNIEntry 2}


--==================================================================================================================

   adGenMEFMENTable OBJECT-TYPE
      SYNTAX  SEQUENCE OF AdGenMEFMENEntry
      MAX-ACCESS  not-accessible
      STATUS  current
      DESCRIPTION
         "The MEN provisioning table."
      ::= { adGenMEFProvisioning 10 }

   adGenMEFMENEntry OBJECT-TYPE
      SYNTAX  AdGenMEFMENEntry
      MAX-ACCESS  not-accessible
      STATUS  current
      DESCRIPTION
         "An entry in the MEN provisioning table."
      INDEX  { ifIndex }
      ::= { adGenMEFMENTable 1 }

   AdGenMEFMENEntry ::=
      SEQUENCE {
         adGenMEFMENVLANIDPool
            DisplayString
      }

      adGenMEFMENVLANIDPool OBJECT-TYPE
         SYNTAX  DisplayString
         MAX-ACCESS  read-only
         STATUS  current
         DESCRIPTION
            "This object is a text string listing the available VLAN IDs
             to use in EVC creation per MEN port.  If a restricted pool has been provisioned
             the string will return the VLANs separated by commas.  If no
             pool has been provisioned, the string will read All."
         ::= { adGenMEFMENEntry 1}

--==================================================================================================================
    adGenMEF10100EthAnomaliesPerformance OBJECT IDENTIFIER ::= { adGenMEFPerformance 1 }

   adGenMEF10100EthAnomalies15MinCurrentTable OBJECT-TYPE
      SYNTAX  SEQUENCE OF AdGenMEF10100EthAnomalies15MinCurrentEntry
      MAX-ACCESS  not-accessible
      STATUS  current
      DESCRIPTION
         "The 10/100 Ethernet MEF Anomalies 15Min current table."
      ::= { adGenMEF10100EthAnomaliesPerformance 1 }

   adGenMEF10100EthAnomalies15MinCurrentEntry OBJECT-TYPE
      SYNTAX  AdGenMEF10100EthAnomalies15MinCurrentEntry
      MAX-ACCESS  not-accessible
      STATUS  current
      DESCRIPTION
         "An entry in the 10/100 Ethernet MEF Anomalies 15Min current table."
      INDEX   { ifIndex }
      ::= { adGenMEF10100EthAnomalies15MinCurrentTable 1 }

   AdGenMEF10100EthAnomalies15MinCurrentEntry  ::=
      SEQUENCE {
         adGenMEF10100EthAnomalies15MinCurrentFramesWithInvalidCEVLANID
	    Gauge32
       }

      adGenMEF10100EthAnomalies15MinCurrentFramesWithInvalidCEVLANID OBJECT-TYPE
         SYNTAX Gauge32
         MAX-ACCESS  read-only
         STATUS  current
         DESCRIPTION
            "The counter associated with the number of received frames with
            invalid CE-VLAN id."
         ::= { adGenMEF10100EthAnomalies15MinCurrentEntry 1 }
--==================================================================================================================

   adGenMEF10100EthAnomalies15MinIntervalTable OBJECT-TYPE
      SYNTAX  SEQUENCE OF AdGenMEF10100EthAnomalies15MinIntervalEntry
      MAX-ACCESS  not-accessible
      STATUS  current
      DESCRIPTION
         "The 10/100 Ethernet MEF Anomalies 15Min interval table."
      ::= { adGenMEF10100EthAnomaliesPerformance 2 }

   adGenMEF10100EthAnomalies15MinIntervalEntry OBJECT-TYPE
      SYNTAX  AdGenMEF10100EthAnomalies15MinIntervalEntry
      MAX-ACCESS  not-accessible
      STATUS  current
      DESCRIPTION
         "An entry in the 10/100 Ethernet MEF Anomalies 15Min interval table."
      INDEX   { ifIndex, adGenMEF10100EthAnomalies15MinIntervalNumber }
      ::= { adGenMEF10100EthAnomalies15MinIntervalTable 1 }

   AdGenMEF10100EthAnomalies15MinIntervalEntry  ::=
      SEQUENCE {
         adGenMEF10100EthAnomalies15MinIntervalNumber
            Integer32,
         adGenMEF10100EthAnomalies15MinIntervalFramesWithInvalidCEVLANID
	    Gauge32
        }

      adGenMEF10100EthAnomalies15MinIntervalNumber OBJECT-TYPE
         SYNTAX  Integer32
         MAX-ACCESS  read-only
         STATUS  current
         DESCRIPTION
            "A number between 1 and 96, where 1 is the most
             recently completed 15 minute interval and 96 is
             the least recently completed 15 minutes interval
             (assuming that all 96 intervals are valid)."
         ::= { adGenMEF10100EthAnomalies15MinIntervalEntry 1 }

      adGenMEF10100EthAnomalies15MinIntervalFramesWithInvalidCEVLANID OBJECT-TYPE
         SYNTAX Gauge32
         MAX-ACCESS  read-only
         STATUS  current
         DESCRIPTION
            "The counter associated with the number of received frames with
            invalid CE-VLAN id."
         ::= { adGenMEF10100EthAnomalies15MinIntervalEntry 2 }


--==================================================================================================================

   adGenMEF10100EthAnomalies24HrCurrentTable OBJECT-TYPE
      SYNTAX  SEQUENCE OF AdGenMEF10100EthAnomalies24HrCurrentEntry
      MAX-ACCESS  not-accessible
      STATUS  current
      DESCRIPTION
         "The 10/100 Ethernet MEF Anomalies 24Hr current table."
      ::= { adGenMEF10100EthAnomaliesPerformance 3 }

   adGenMEF10100EthAnomalies24HrCurrentEntry OBJECT-TYPE
      SYNTAX  AdGenMEF10100EthAnomalies24HrCurrentEntry
      MAX-ACCESS  not-accessible
      STATUS  current
      DESCRIPTION
         "An entry in the 10/100 Ethernet MEF Anomalies 24Hr current table."
      INDEX   { ifIndex }
      ::= { adGenMEF10100EthAnomalies24HrCurrentTable 1 }

   AdGenMEF10100EthAnomalies24HrCurrentEntry  ::=
      SEQUENCE {
         adGenMEF10100EthAnomalies24HrCurrentFramesWithInvalidCEVLANID
	    Gauge32
        }

      adGenMEF10100EthAnomalies24HrCurrentFramesWithInvalidCEVLANID OBJECT-TYPE
         SYNTAX Gauge32
         MAX-ACCESS  read-only
         STATUS  current
         DESCRIPTION
            "The counter associated with the number of received frames with
            invalid CE-VLAN id."
         ::= { adGenMEF10100EthAnomalies24HrCurrentEntry 1 }

--==================================================================================================================

   adGenMEF10100EthAnomalies24HrIntervalTable OBJECT-TYPE
      SYNTAX  SEQUENCE OF AdGenMEF10100EthAnomalies24HrIntervalEntry
      MAX-ACCESS  not-accessible
      STATUS  current
      DESCRIPTION
         "The 10/100 Ethernet 24Hr interval table."
      ::= { adGenMEF10100EthAnomaliesPerformance 4 }

   adGenMEF10100EthAnomalies24HrIntervalEntry OBJECT-TYPE
      SYNTAX  AdGenMEF10100EthAnomalies24HrIntervalEntry
      MAX-ACCESS  not-accessible
      STATUS  current
      DESCRIPTION
         "An entry in the 10/100 Ethernet MEF Anomalies 24Hr interval table."
      INDEX   { ifIndex, adGenMEF10100EthAnomalies24HrIntervalNumber }
      ::= { adGenMEF10100EthAnomalies24HrIntervalTable 1 }

   AdGenMEF10100EthAnomalies24HrIntervalEntry  ::=
      SEQUENCE {
         adGenMEF10100EthAnomalies24HrIntervalNumber
            Integer32,
         adGenMEF10100EthAnomalies24HrIntervalFramesWithInvalidCEVLANID
	    Gauge32
        }

      adGenMEF10100EthAnomalies24HrIntervalNumber OBJECT-TYPE
         SYNTAX  Integer32
         MAX-ACCESS  read-only
         STATUS  current
         DESCRIPTION
            "A number between 1 and 7, where 1 is the most recently
             completed day and 7 is the least recently completed
             day (assuming that all 7 days are valid)."
         ::= { adGenMEF10100EthAnomalies24HrIntervalEntry 1 }

      adGenMEF10100EthAnomalies24HrIntervalFramesWithInvalidCEVLANID OBJECT-TYPE
         SYNTAX Gauge32
         MAX-ACCESS  read-only
         STATUS  current
         DESCRIPTION
            "The counter associated with the number of received frames with
            invalid CE-VLAN id in the selected day."
         ::= { adGenMEF10100EthAnomalies24HrIntervalEntry 2 }


--==================================================================================================================
    adGenMEFGigEthAnomaliesPerformance OBJECT IDENTIFIER ::= { adGenMEFPerformance 2 }

   adGenMEFGigEthAnomalies15MinCurrentTable OBJECT-TYPE
      SYNTAX  SEQUENCE OF AdGenMEFGigEthAnomalies15MinCurrentEntry
      MAX-ACCESS  not-accessible
      STATUS  current
      DESCRIPTION
         "The Gigabit Ethernet MEF Anomalies 15Min current table."
      ::= { adGenMEFGigEthAnomaliesPerformance 1 }

   adGenMEFGigEthAnomalies15MinCurrentEntry OBJECT-TYPE
      SYNTAX  AdGenMEFGigEthAnomalies15MinCurrentEntry
      MAX-ACCESS  not-accessible
      STATUS  current
      DESCRIPTION
         "An entry in the Gigabit Ethernet MEF Anomalies 15Min current table."
      INDEX   { ifIndex }
      ::= { adGenMEFGigEthAnomalies15MinCurrentTable 1 }

   AdGenMEFGigEthAnomalies15MinCurrentEntry  ::=
      SEQUENCE {
         adGenMEFGigEthAnomalies15MinCurrentFramesWithInvalidCEVLANID
	    Gauge32
       }

      adGenMEFGigEthAnomalies15MinCurrentFramesWithInvalidCEVLANID OBJECT-TYPE
         SYNTAX Gauge32
         MAX-ACCESS  read-only
         STATUS  current
         DESCRIPTION
            "The counter associated with the number of received frames with
            invalid CE-VLAN id."
         ::= { adGenMEFGigEthAnomalies15MinCurrentEntry 1 }

--==================================================================================================================

   adGenMEFGigEthAnomalies15MinIntervalTable OBJECT-TYPE
      SYNTAX  SEQUENCE OF AdGenMEFGigEthAnomalies15MinIntervalEntry
      MAX-ACCESS  not-accessible
      STATUS  current
      DESCRIPTION
         "The Gigabit Ethernet MEF Anomalies 15Min interval table."
      ::= { adGenMEFGigEthAnomaliesPerformance 2 }

   adGenMEFGigEthAnomalies15MinIntervalEntry OBJECT-TYPE
      SYNTAX  AdGenMEFGigEthAnomalies15MinIntervalEntry
      MAX-ACCESS  not-accessible
      STATUS  current
      DESCRIPTION
         "An entry in the Gigabit Ethernet MEF Anomalies 15Min interval table."
      INDEX   { ifIndex, adGenMEFGigEthAnomalies15MinIntervalNumber }
      ::= { adGenMEFGigEthAnomalies15MinIntervalTable 1 }

   AdGenMEFGigEthAnomalies15MinIntervalEntry  ::=
      SEQUENCE {
         adGenMEFGigEthAnomalies15MinIntervalNumber
            Integer32,
         adGenMEFGigEthAnomalies15MinIntervalFramesWithInvalidCEVLANID
	    Gauge32
        }

      adGenMEFGigEthAnomalies15MinIntervalNumber OBJECT-TYPE
         SYNTAX  Integer32
         MAX-ACCESS  read-only
         STATUS  current
         DESCRIPTION
            "A number between 1 and 96, where 1 is the most
             recently completed 15 minute interval and 96 is
             the least recently completed 15 minutes interval
             (assuming that all 96 intervals are valid)."
         ::= { adGenMEFGigEthAnomalies15MinIntervalEntry 1 }

      adGenMEFGigEthAnomalies15MinIntervalFramesWithInvalidCEVLANID OBJECT-TYPE
         SYNTAX Gauge32
         MAX-ACCESS  read-only
         STATUS  current
         DESCRIPTION
            "The counter associated with the number of received frames with
            invalid CE-VLAN id."
         ::= { adGenMEFGigEthAnomalies15MinIntervalEntry 2 }


--==================================================================================================================

   adGenMEFGigEthAnomalies24HrCurrentTable OBJECT-TYPE
      SYNTAX  SEQUENCE OF AdGenMEFGigEthAnomalies24HrCurrentEntry
      MAX-ACCESS  not-accessible
      STATUS  current
      DESCRIPTION
         "The Gigabit Ethernet MEF Anomalies 24Hr current table."
      ::= { adGenMEFGigEthAnomaliesPerformance 3 }

   adGenMEFGigEthAnomalies24HrCurrentEntry OBJECT-TYPE
      SYNTAX  AdGenMEFGigEthAnomalies24HrCurrentEntry
      MAX-ACCESS  not-accessible
      STATUS  current
      DESCRIPTION
         "An entry in the Gigabit Ethernet MEF Anomalies 24Hr current table."
      INDEX   { ifIndex }
      ::= { adGenMEFGigEthAnomalies24HrCurrentTable 1 }

   AdGenMEFGigEthAnomalies24HrCurrentEntry  ::=
      SEQUENCE {
         adGenMEFGigEthAnomalies24HrCurrentFramesWithInvalidCEVLANID
	    Gauge32
        }

      adGenMEFGigEthAnomalies24HrCurrentFramesWithInvalidCEVLANID OBJECT-TYPE
         SYNTAX Gauge32
         MAX-ACCESS  read-only
         STATUS  current
         DESCRIPTION
            "The counter associated with the number of received frames with
            invalid CE-VLAN id."
         ::= { adGenMEFGigEthAnomalies24HrCurrentEntry 1 }

--==================================================================================================================

   adGenMEFGigEthAnomalies24HrIntervalTable OBJECT-TYPE
      SYNTAX  SEQUENCE OF AdGenMEFGigEthAnomalies24HrIntervalEntry
      MAX-ACCESS  not-accessible
      STATUS  current
      DESCRIPTION
         "The Gigabit Ethernet 24Hr interval table."
      ::= { adGenMEFGigEthAnomaliesPerformance 4 }

   adGenMEFGigEthAnomalies24HrIntervalEntry OBJECT-TYPE
      SYNTAX  AdGenMEFGigEthAnomalies24HrIntervalEntry
      MAX-ACCESS  not-accessible
      STATUS  current
      DESCRIPTION
         "An entry in the Gigabit Ethernet MEF Anomalies 24Hr interval table."
      INDEX   { ifIndex, adGenMEFGigEthAnomalies24HrIntervalNumber }
      ::= { adGenMEFGigEthAnomalies24HrIntervalTable 1 }

   AdGenMEFGigEthAnomalies24HrIntervalEntry  ::=
      SEQUENCE {
         adGenMEFGigEthAnomalies24HrIntervalNumber
            Integer32,
         adGenMEFGigEthAnomalies24HrIntervalFramesWithInvalidCEVLANID
	    Gauge32
        }

      adGenMEFGigEthAnomalies24HrIntervalNumber OBJECT-TYPE
         SYNTAX  Integer32
         MAX-ACCESS  read-only
         STATUS  current
         DESCRIPTION
            "A number between 1 and 7, where 1 is the most recently
             completed day and 7 is the least recently completed
             day (assuming that all 7 days are valid)."
         ::= { adGenMEFGigEthAnomalies24HrIntervalEntry 1 }

      adGenMEFGigEthAnomalies24HrIntervalFramesWithInvalidCEVLANID OBJECT-TYPE
         SYNTAX Gauge32
         MAX-ACCESS  read-only
         STATUS  current
         DESCRIPTION
            "The counter associated with the number of received frames with
            invalid CE-VLAN id in the selected day."
         ::= { adGenMEFGigEthAnomalies24HrIntervalEntry 2 }

--==================================================================================================================
    adGenMEFPolicerPerformance OBJECT IDENTIFIER ::= { adGenMEFPerformance 3 }

    adGenMEFPolicerPerformanceScalars	OBJECT IDENTIFIER ::= { adGenMEFPolicerPerformance 1}

      adGenMEFPolicerRstCurrentIntervals OBJECT-TYPE
         SYNTAX  INTEGER {
            ethRstAllCurrentIntervals(1)
         }
         MAX-ACCESS  read-write
         STATUS  current
         DESCRIPTION
            "Reset current interval MEF Traffic Management PM data on ALL policers."
          ::= { adGenMEFPolicerPerformanceScalars 1 }

      adGenMEFPolicerRstAll OBJECT-TYPE
         SYNTAX  INTEGER {
            ethRstAll(1)
         }
         MAX-ACCESS  read-write
         STATUS  current
         DESCRIPTION
            "Reset MEF Traffic Management PM data on ALL policers."
         ::= { adGenMEFPolicerPerformanceScalars 2 }

    adGenMEFPolicer15MinCurrentTable OBJECT-TYPE
      SYNTAX  SEQUENCE OF AdGenMEFPolicer15MinCurrentEntry
      MAX-ACCESS  not-accessible
      STATUS  current
      DESCRIPTION
         "The MEF Traffic Management 15Min current table."
      ::= { adGenMEFPolicerPerformance 2 }

   adGenMEFPolicer15MinCurrentEntry OBJECT-TYPE
      SYNTAX  AdGenMEFPolicer15MinCurrentEntry
      MAX-ACCESS  not-accessible
      STATUS  current
      DESCRIPTION
         "An entry in MEF Traffic Management 15Min current table."
      INDEX   { adGenMEFProfileIndex }
      ::= { adGenMEFPolicer15MinCurrentTable 1 }

   AdGenMEFPolicer15MinCurrentEntry  ::=
      SEQUENCE {
         adGenMEFPolicer15MinCurrentIngressGreenFrames
    	    Gauge32,
         adGenMEFPolicer15MinCurrentIngressYellowFrames
	        Gauge32,
         adGenMEFPolicer15MinCurrentIngressRedFrames
	        Gauge32,
         adGenMEFPolicer15MinCurrentIngressGreenOctets
	        Gauge32,
         adGenMEFPolicer15MinCurrentIngressYellowOctets
	        Gauge32,
         adGenMEFPolicer15MinCurrentIngressRedOctets
         	Gauge32,
         adGenMEFPolicer15MinCurrentCongDiscardsIngressGreenFrames
                Gauge32,
         adGenMEFPolicer15MinCurrentCongDiscardsIngressGreenOctets
	        Gauge32,
         adGenMEFPolicer15MinCurrentCongDiscardsIngressYellowFrames
	        Gauge32,
         adGenMEFPolicer15MinCurrentCongDiscardsIngressYellowOctets
	        Gauge32,
         adGenMEFPolicer15MinCurrentHCIngressGreenFrames
    	        Counter64,
         adGenMEFPolicer15MinCurrentHCIngressYellowFrames
	        Counter64,
         adGenMEFPolicer15MinCurrentHCIngressRedFrames
	        Counter64,
         adGenMEFPolicer15MinCurrentHCIngressGreenOctets
	        Counter64,
         adGenMEFPolicer15MinCurrentHCIngressYellowOctets
	        Counter64,
         adGenMEFPolicer15MinCurrentHCIngressRedOctets
         	Counter64,
         adGenMEFPolicer15MinCurrentHCCongDiscardsIngressGreenFrames
                Counter64,
         adGenMEFPolicer15MinCurrentHCCongDiscardsIngressGreenOctets
	        Counter64,
         adGenMEFPolicer15MinCurrentHCCongDiscardsIngressYellowFrames
	        Counter64,
         adGenMEFPolicer15MinCurrentHCCongDiscardsIngressYellowOctets
	        Counter64
       }

      adGenMEFPolicer15MinCurrentIngressGreenFrames OBJECT-TYPE
         SYNTAX Gauge32
         MAX-ACCESS  read-only
         STATUS  current
         DESCRIPTION
            "The counter associated with the number frames coming out of the
            ingress policer which is marked green."
         ::= { adGenMEFPolicer15MinCurrentEntry 1 }

      adGenMEFPolicer15MinCurrentIngressYellowFrames OBJECT-TYPE
         SYNTAX Gauge32
         MAX-ACCESS  read-only
         STATUS  current
         DESCRIPTION
            "The counter associated with the number frames coming out of the
            ingress policer which is marked yellow."
         ::= { adGenMEFPolicer15MinCurrentEntry 2 }

      adGenMEFPolicer15MinCurrentIngressRedFrames OBJECT-TYPE
         SYNTAX Gauge32
         MAX-ACCESS  read-only
         STATUS  current
         DESCRIPTION
            "The counter associated with the number frames coming out of the
            ingress policer which is marked red (dropped)."
         ::= { adGenMEFPolicer15MinCurrentEntry 3 }

      adGenMEFPolicer15MinCurrentIngressGreenOctets OBJECT-TYPE
         SYNTAX Gauge32
         MAX-ACCESS  read-only
         STATUS  current
         DESCRIPTION
            "The counter associated with the number octets coming out of the
            ingress policer which is marked green."
         ::= { adGenMEFPolicer15MinCurrentEntry 4 }

      adGenMEFPolicer15MinCurrentIngressYellowOctets OBJECT-TYPE
         SYNTAX Gauge32
         MAX-ACCESS  read-only
         STATUS  current
         DESCRIPTION
            "The counter associated with the number octets coming out of the
            ingress policer which is marked yellow."
         ::= { adGenMEFPolicer15MinCurrentEntry 5 }

      adGenMEFPolicer15MinCurrentIngressRedOctets OBJECT-TYPE
         SYNTAX Gauge32
         MAX-ACCESS  read-only
         STATUS  current
         DESCRIPTION
            "The counter associated with the number octets coming out of the
            ingress policer which is marked red (dropped)."
         ::= { adGenMEFPolicer15MinCurrentEntry 6 }

      adGenMEFPolicer15MinCurrentCongDiscardsIngressGreenFrames OBJECT-TYPE
         SYNTAX Gauge32
         MAX-ACCESS  read-only
         STATUS  current
         DESCRIPTION
            "The counter associated with the number of green frames discarded due to
            congestion in the egress queue."
         ::= { adGenMEFPolicer15MinCurrentEntry 7 }

      adGenMEFPolicer15MinCurrentCongDiscardsIngressGreenOctets OBJECT-TYPE
         SYNTAX Gauge32
         MAX-ACCESS  read-only
         STATUS  current
         DESCRIPTION
            "The counter associated with the number of green octets discarded due to
            congestion in the egress queue"
         ::= { adGenMEFPolicer15MinCurrentEntry 8 }

      adGenMEFPolicer15MinCurrentCongDiscardsIngressYellowFrames OBJECT-TYPE
         SYNTAX Gauge32
         MAX-ACCESS  read-only
         STATUS  current
         DESCRIPTION
            "The counter associated with the number of yellow frames discarded due to
            congestion in the egress queue"
         ::= { adGenMEFPolicer15MinCurrentEntry 9 }

      adGenMEFPolicer15MinCurrentCongDiscardsIngressYellowOctets OBJECT-TYPE
         SYNTAX Gauge32
         MAX-ACCESS  read-only
         STATUS  current
         DESCRIPTION
            "The counter associated with the number of yellow octets discarded due to
            congestion in the egress queue"
         ::= { adGenMEFPolicer15MinCurrentEntry 10 }

adGenMEFPolicer15MinCurrentHCIngressGreenFrames OBJECT-TYPE
         SYNTAX Counter64
         MAX-ACCESS  read-only
         STATUS  current
         DESCRIPTION
            "The counter associated with the number frames coming out of the
            ingress policer which is marked green."
         ::= { adGenMEFPolicer15MinCurrentEntry 11 }

      adGenMEFPolicer15MinCurrentHCIngressYellowFrames OBJECT-TYPE
         SYNTAX Counter64
         MAX-ACCESS  read-only
         STATUS  current
         DESCRIPTION
            "The counter associated with the number frames coming out of the
            ingress policer which is marked yellow."
         ::= { adGenMEFPolicer15MinCurrentEntry 12 }

      adGenMEFPolicer15MinCurrentHCIngressRedFrames OBJECT-TYPE
         SYNTAX Counter64
         MAX-ACCESS  read-only
         STATUS  current
         DESCRIPTION
            "The counter associated with the number frames coming out of the
            ingress policer which is marked red (dropped)."
         ::= { adGenMEFPolicer15MinCurrentEntry 13 }

      adGenMEFPolicer15MinCurrentHCIngressGreenOctets OBJECT-TYPE
         SYNTAX Counter64
         MAX-ACCESS  read-only
         STATUS  current
         DESCRIPTION
            "The counter associated with the number octets coming out of the
            ingress policer which is marked green."
         ::= { adGenMEFPolicer15MinCurrentEntry 14 }

      adGenMEFPolicer15MinCurrentHCIngressYellowOctets OBJECT-TYPE
         SYNTAX Counter64
         MAX-ACCESS  read-only
         STATUS  current
         DESCRIPTION
            "The counter associated with the number octets coming out of the
            ingress policer which is marked yellow."
         ::= { adGenMEFPolicer15MinCurrentEntry 15 }

      adGenMEFPolicer15MinCurrentHCIngressRedOctets OBJECT-TYPE
         SYNTAX Counter64
         MAX-ACCESS  read-only
         STATUS  current
         DESCRIPTION
            "The counter associated with the number octets coming out of the
            ingress policer which is marked red (dropped)."
         ::= { adGenMEFPolicer15MinCurrentEntry 16 }

      adGenMEFPolicer15MinCurrentHCCongDiscardsIngressGreenFrames OBJECT-TYPE
         SYNTAX Counter64
         MAX-ACCESS  read-only
         STATUS  current
         DESCRIPTION
            "The counter associated with the number of green frames discarded due to
            congestion in the egress queue."
         ::= { adGenMEFPolicer15MinCurrentEntry 17 }

      adGenMEFPolicer15MinCurrentHCCongDiscardsIngressGreenOctets OBJECT-TYPE
         SYNTAX Counter64
         MAX-ACCESS  read-only
         STATUS  current
         DESCRIPTION
            "The counter associated with the number of green octets discarded due to
            congestion in the egress queue"
         ::= { adGenMEFPolicer15MinCurrentEntry 18 }

      adGenMEFPolicer15MinCurrentHCCongDiscardsIngressYellowFrames OBJECT-TYPE
         SYNTAX Counter64
         MAX-ACCESS  read-only
         STATUS  current
         DESCRIPTION
            "The counter associated with the number of yellow frames discarded due to
            congestion in the egress queue"
         ::= { adGenMEFPolicer15MinCurrentEntry 19 }

      adGenMEFPolicer15MinCurrentHCCongDiscardsIngressYellowOctets OBJECT-TYPE
         SYNTAX Counter64
         MAX-ACCESS  read-only
         STATUS  current
         DESCRIPTION
            "The counter associated with the number of yellow octets discarded due to
            congestion in the egress queue"
         ::= { adGenMEFPolicer15MinCurrentEntry 20 }
--==================================================================================================================

   adGenMEFPolicer15MinIntervalTable OBJECT-TYPE
      SYNTAX  SEQUENCE OF AdGenMEFPolicer15MinIntervalEntry
      MAX-ACCESS  not-accessible
      STATUS  current
      DESCRIPTION
         "The MEF Traffic Management 15Min interval table."
      ::= { adGenMEFPolicerPerformance 3 }

   adGenMEFPolicer15MinIntervalEntry OBJECT-TYPE
      SYNTAX  AdGenMEFPolicer15MinIntervalEntry
      MAX-ACCESS  not-accessible
      STATUS  current
      DESCRIPTION
         "An entry in Traffic Management 15Min interval table."
      INDEX   { adGenMEFProfileIndex, adGenMEFPolicer15MinIntervalNumber }
      ::= { adGenMEFPolicer15MinIntervalTable 1 }

   AdGenMEFPolicer15MinIntervalEntry  ::=
      SEQUENCE {
         adGenMEFPolicer15MinIntervalNumber
            Integer32,
         adGenMEFPolicer15MinIntervalIngressGreenFrames
    	    Gauge32,
         adGenMEFPolicer15MinIntervalIngressYellowFrames
	        Gauge32,
         adGenMEFPolicer15MinIntervalIngressRedFrames
	        Gauge32,
         adGenMEFPolicer15MinIntervalIngressGreenOctets
	        Gauge32,
         adGenMEFPolicer15MinIntervalIngressYellowOctets
	        Gauge32,
         adGenMEFPolicer15MinIntervalIngressRedOctets
	        Gauge32,
         adGenMEFPolicer15MinIntervalCongDiscardsIngressGreenFrames
                Gauge32,
         adGenMEFPolicer15MinIntervalCongDiscardsIngressGreenOctets
	        Gauge32,
         adGenMEFPolicer15MinIntervalCongDiscardsIngressYellowFrames
	        Gauge32,
         adGenMEFPolicer15MinIntervalCongDiscardsIngressYellowOctets
	        Gauge32,
	  adGenMEFPolicer15MinIntervalHCIngressGreenFrames
    	    Counter64,
         adGenMEFPolicer15MinIntervalHCIngressYellowFrames
	        Counter64,
         adGenMEFPolicer15MinIntervalHCIngressRedFrames
	        Counter64,
         adGenMEFPolicer15MinIntervalHCIngressGreenOctets
	        Counter64,
         adGenMEFPolicer15MinIntervalHCIngressYellowOctets
	        Counter64,
         adGenMEFPolicer15MinIntervalHCIngressRedOctets
	        Counter64,
         adGenMEFPolicer15MinIntervalHCCongDiscardsIngressGreenFrames
                Counter64,
         adGenMEFPolicer15MinIntervalHCCongDiscardsIngressGreenOctets
	        Counter64,
         adGenMEFPolicer15MinIntervalHCCongDiscardsIngressYellowFrames
	        Counter64,
         adGenMEFPolicer15MinIntervalHCCongDiscardsIngressYellowOctets
	        Counter64
       }

      adGenMEFPolicer15MinIntervalNumber OBJECT-TYPE
         SYNTAX Integer32
         MAX-ACCESS  read-only
         STATUS  current
         DESCRIPTION
            "A number between 1 and 96, where 1 is the most
             recently completed 15 minute interval and 96 is
             the least recently completed 15 minutes interval
             (assuming that all 96 intervals are valid)."
         ::= { adGenMEFPolicer15MinIntervalEntry 1 }

      adGenMEFPolicer15MinIntervalIngressGreenFrames OBJECT-TYPE
         SYNTAX Gauge32
         MAX-ACCESS  read-only
         STATUS  current
         DESCRIPTION
            "The counter associated with the number frames coming out of the
            ingress policer which is marked green in the selected interval."
         ::= { adGenMEFPolicer15MinIntervalEntry 2 }

      adGenMEFPolicer15MinIntervalIngressYellowFrames OBJECT-TYPE
         SYNTAX Gauge32
         MAX-ACCESS  read-only
         STATUS  current
         DESCRIPTION
            "The counter associated with the number frames coming out of the
            ingress policer which is marked yellow in the selected interval."
         ::= { adGenMEFPolicer15MinIntervalEntry 3 }

      adGenMEFPolicer15MinIntervalIngressRedFrames OBJECT-TYPE
         SYNTAX Gauge32
         MAX-ACCESS  read-only
         STATUS  current
         DESCRIPTION
            "The counter associated with the number frames coming out of the
            ingress policer which is marked red (dropped) in the selected interval."
         ::= { adGenMEFPolicer15MinIntervalEntry 4 }

      adGenMEFPolicer15MinIntervalIngressGreenOctets OBJECT-TYPE
         SYNTAX Gauge32
         MAX-ACCESS  read-only
         STATUS  current
         DESCRIPTION
            "The counter associated with the number octets coming out of the
            ingress policer which is marked green in the selected interval."
         ::= { adGenMEFPolicer15MinIntervalEntry 5 }

      adGenMEFPolicer15MinIntervalIngressYellowOctets OBJECT-TYPE
         SYNTAX Gauge32
         MAX-ACCESS  read-only
         STATUS  current
         DESCRIPTION
            "The counter associated with the number octets coming out of the
            ingress policer which is marked yellow in the selected interval."
         ::= { adGenMEFPolicer15MinIntervalEntry 6 }

      adGenMEFPolicer15MinIntervalIngressRedOctets OBJECT-TYPE
         SYNTAX Gauge32
         MAX-ACCESS  read-only
         STATUS  current
         DESCRIPTION
            "The counter associated with the number octets coming out of the
            ingress policer which is marked red (dropped) in the selected interval."
         ::= { adGenMEFPolicer15MinIntervalEntry 7 }

      adGenMEFPolicer15MinIntervalCongDiscardsIngressGreenFrames OBJECT-TYPE
         SYNTAX Gauge32
         MAX-ACCESS  read-only
         STATUS  current
         DESCRIPTION
            "The counter associated with the number of green frames discarded due to
            congestion in the egress queue in the selected interval."
         ::= { adGenMEFPolicer15MinIntervalEntry 8 }

      adGenMEFPolicer15MinIntervalCongDiscardsIngressGreenOctets OBJECT-TYPE
         SYNTAX Gauge32
         MAX-ACCESS  read-only
         STATUS  current
         DESCRIPTION
            "The counter associated with the number of green octets discarded due to
            congestion in the egress queue in the selected interval."
         ::= { adGenMEFPolicer15MinIntervalEntry 9 }

      adGenMEFPolicer15MinIntervalCongDiscardsIngressYellowFrames OBJECT-TYPE
         SYNTAX Gauge32
         MAX-ACCESS  read-only
         STATUS  current
         DESCRIPTION
            "The counter associated with the number of yellow frames discarded due to
            congestion in the egress queue in the selected interval."
         ::= { adGenMEFPolicer15MinIntervalEntry 10 }

      adGenMEFPolicer15MinIntervalCongDiscardsIngressYellowOctets OBJECT-TYPE
         SYNTAX Gauge32
         MAX-ACCESS  read-only
         STATUS  current
         DESCRIPTION
            "The counter associated with the number of yellow octets discarded due to
            congestion in the egress queue in the selected interval."
         ::= { adGenMEFPolicer15MinIntervalEntry 11 }

     adGenMEFPolicer15MinIntervalHCIngressGreenFrames OBJECT-TYPE
         SYNTAX Counter64
         MAX-ACCESS  read-only
         STATUS  current
         DESCRIPTION
            "The counter associated with the number frames coming out of the
            ingress policer which is marked green in the selected interval."
         ::= { adGenMEFPolicer15MinIntervalEntry 12 }

      adGenMEFPolicer15MinIntervalHCIngressYellowFrames OBJECT-TYPE
         SYNTAX Counter64
         MAX-ACCESS  read-only
         STATUS  current
         DESCRIPTION
            "The counter associated with the number frames coming out of the
            ingress policer which is marked yellow in the selected interval."
         ::= { adGenMEFPolicer15MinIntervalEntry 13 }

      adGenMEFPolicer15MinIntervalHCIngressRedFrames OBJECT-TYPE
         SYNTAX Counter64
         MAX-ACCESS  read-only
         STATUS  current
         DESCRIPTION
            "The counter associated with the number frames coming out of the
            ingress policer which is marked red (dropped) in the selected interval."
         ::= { adGenMEFPolicer15MinIntervalEntry 14 }

      adGenMEFPolicer15MinIntervalHCIngressGreenOctets OBJECT-TYPE
         SYNTAX Counter64
         MAX-ACCESS  read-only
         STATUS  current
         DESCRIPTION
            "The counter associated with the number octets coming out of the
            ingress policer which is marked green in the selected interval."
         ::= { adGenMEFPolicer15MinIntervalEntry 15 }

      adGenMEFPolicer15MinIntervalHCIngressYellowOctets OBJECT-TYPE
         SYNTAX Counter64
         MAX-ACCESS  read-only
         STATUS  current
         DESCRIPTION
            "The counter associated with the number octets coming out of the
            ingress policer which is marked yellow in the selected interval."
         ::= { adGenMEFPolicer15MinIntervalEntry 16 }

      adGenMEFPolicer15MinIntervalHCIngressRedOctets OBJECT-TYPE
         SYNTAX Counter64
         MAX-ACCESS  read-only
         STATUS  current
         DESCRIPTION
            "The counter associated with the number octets coming out of the
            ingress policer which is marked red (dropped) in the selected interval."
         ::= { adGenMEFPolicer15MinIntervalEntry 17 }

      adGenMEFPolicer15MinIntervalHCCongDiscardsIngressGreenFrames OBJECT-TYPE
         SYNTAX Counter64
         MAX-ACCESS  read-only
         STATUS  current
         DESCRIPTION
            "The counter associated with the number of green frames discarded due to
            congestion in the egress queue in the selected interval."
         ::= { adGenMEFPolicer15MinIntervalEntry 18 }

      adGenMEFPolicer15MinIntervalHCCongDiscardsIngressGreenOctets OBJECT-TYPE
         SYNTAX Counter64
         MAX-ACCESS  read-only
         STATUS  current
         DESCRIPTION
            "The counter associated with the number of green octets discarded due to
            congestion in the egress queue in the selected interval."
         ::= { adGenMEFPolicer15MinIntervalEntry 19 }

      adGenMEFPolicer15MinIntervalHCCongDiscardsIngressYellowFrames OBJECT-TYPE
         SYNTAX Counter64
         MAX-ACCESS  read-only
         STATUS  current
         DESCRIPTION
            "The counter associated with the number of yellow frames discarded due to
            congestion in the egress queue in the selected interval."
         ::= { adGenMEFPolicer15MinIntervalEntry 20 }

      adGenMEFPolicer15MinIntervalHCCongDiscardsIngressYellowOctets OBJECT-TYPE
         SYNTAX Counter64
         MAX-ACCESS  read-only
         STATUS  current
         DESCRIPTION
            "The counter associated with the number of yellow octets discarded due to
            congestion in the egress queue in the selected interval."
         ::= { adGenMEFPolicer15MinIntervalEntry 21 }
--==================================================================================================================

   adGenMEFPolicer24HrCurrentTable OBJECT-TYPE
      SYNTAX  SEQUENCE OF AdGenMEFPolicer24HrCurrentEntry
      MAX-ACCESS  not-accessible
      STATUS  current
      DESCRIPTION
         "The MEF Traffic Management 24Hr current table."
      ::= { adGenMEFPolicerPerformance 4 }

   adGenMEFPolicer24HrCurrentEntry OBJECT-TYPE
      SYNTAX  AdGenMEFPolicer24HrCurrentEntry
      MAX-ACCESS  not-accessible
      STATUS  current
      DESCRIPTION
         "An entry in MEF Traffic Management 24Hr current table."
      INDEX   { adGenMEFProfileIndex }
      ::= { adGenMEFPolicer24HrCurrentTable 1 }

   AdGenMEFPolicer24HrCurrentEntry  ::=
      SEQUENCE {
         adGenMEFPolicer24HrCurrentIngressGreenFrames
    	    Gauge32,
         adGenMEFPolicer24HrCurrentIngressYellowFrames
	        Gauge32,
         adGenMEFPolicer24HrCurrentIngressRedFrames
	        Gauge32,
         adGenMEFPolicer24HrCurrentIngressGreenOctets
	        Gauge32,
         adGenMEFPolicer24HrCurrentIngressYellowOctets
	        Gauge32,
         adGenMEFPolicer24HrCurrentIngressRedOctets
         	Gauge32,
         adGenMEFPolicer24HrCurrentCongDiscardsIngressGreenFrames
                Gauge32,
         adGenMEFPolicer24HrCurrentCongDiscardsIngressGreenOctets
	        Gauge32,
         adGenMEFPolicer24HrCurrentCongDiscardsIngressYellowFrames
	        Gauge32,
         adGenMEFPolicer24HrCurrentCongDiscardsIngressYellowOctets
	        Gauge32,
	  adGenMEFPolicer24HrCurrentHCIngressGreenFrames
    	    Counter64,
         adGenMEFPolicer24HrCurrentHCIngressYellowFrames
	        Counter64,
         adGenMEFPolicer24HrCurrentHCIngressRedFrames
	        Counter64,
         adGenMEFPolicer24HrCurrentHCIngressGreenOctets
	        Counter64,
         adGenMEFPolicer24HrCurrentHCIngressYellowOctets
	        Counter64,
         adGenMEFPolicer24HrCurrentHCIngressRedOctets
         	Counter64,
         adGenMEFPolicer24HrCurrentHCCongDiscardsIngressGreenFrames
                Counter64,
         adGenMEFPolicer24HrCurrentHCCongDiscardsIngressGreenOctets
	        Counter64,
         adGenMEFPolicer24HrCurrentHCCongDiscardsIngressYellowFrames
	        Counter64,
         adGenMEFPolicer24HrCurrentHCCongDiscardsIngressYellowOctets
	        Counter64
       }

      adGenMEFPolicer24HrCurrentIngressGreenFrames OBJECT-TYPE
         SYNTAX Gauge32
         MAX-ACCESS  read-only
         STATUS  current
         DESCRIPTION
            "The counter associated with the number frames coming out of the
            ingress policer which is marked green."
         ::= { adGenMEFPolicer24HrCurrentEntry 1 }

      adGenMEFPolicer24HrCurrentIngressYellowFrames OBJECT-TYPE
         SYNTAX Gauge32
         MAX-ACCESS  read-only
         STATUS  current
         DESCRIPTION
            "The counter associated with the number frames coming out of the
            ingress policer which is marked yellow."
         ::= { adGenMEFPolicer24HrCurrentEntry 2 }

      adGenMEFPolicer24HrCurrentIngressRedFrames OBJECT-TYPE
         SYNTAX Gauge32
         MAX-ACCESS  read-only
         STATUS  current
         DESCRIPTION
            "The counter associated with the number frames coming out of the
            ingress policer which is marked red (dropped)."
         ::= { adGenMEFPolicer24HrCurrentEntry 3 }

      adGenMEFPolicer24HrCurrentIngressGreenOctets OBJECT-TYPE
         SYNTAX Gauge32
         MAX-ACCESS  read-only
         STATUS  current
         DESCRIPTION
            "The counter associated with the number octets coming out of the
            ingress policer which is marked green."
         ::= { adGenMEFPolicer24HrCurrentEntry 4 }

      adGenMEFPolicer24HrCurrentIngressYellowOctets OBJECT-TYPE
         SYNTAX Gauge32
         MAX-ACCESS  read-only
         STATUS  current
         DESCRIPTION
            "The counter associated with the number octets coming out of the
            ingress policer which is marked yellow."
         ::= { adGenMEFPolicer24HrCurrentEntry 5 }

      adGenMEFPolicer24HrCurrentIngressRedOctets OBJECT-TYPE
         SYNTAX Gauge32
         MAX-ACCESS  read-only
         STATUS  current
         DESCRIPTION
            "The counter associated with the number octets coming out of the
            ingress policer which is marked red (dropped)."
         ::= { adGenMEFPolicer24HrCurrentEntry 6 }

      adGenMEFPolicer24HrCurrentCongDiscardsIngressGreenFrames OBJECT-TYPE
         SYNTAX Gauge32
         MAX-ACCESS  read-only
         STATUS  current
         DESCRIPTION
            "The counter associated with the number of green frames discarded due to
            congestion in the egress queue."
         ::= { adGenMEFPolicer24HrCurrentEntry 7 }

      adGenMEFPolicer24HrCurrentCongDiscardsIngressGreenOctets OBJECT-TYPE
         SYNTAX Gauge32
         MAX-ACCESS  read-only
         STATUS  current
         DESCRIPTION
            "The counter associated with the number of green octets discarded due to
            congestion in the egress queue."
         ::= { adGenMEFPolicer24HrCurrentEntry 8 }

      adGenMEFPolicer24HrCurrentCongDiscardsIngressYellowFrames OBJECT-TYPE
         SYNTAX Gauge32
         MAX-ACCESS  read-only
         STATUS  current
         DESCRIPTION
            "The counter associated with the number of yellow frames discarded due to
            congestion in the egress queue."
         ::= { adGenMEFPolicer24HrCurrentEntry 9 }

      adGenMEFPolicer24HrCurrentCongDiscardsIngressYellowOctets OBJECT-TYPE
         SYNTAX Gauge32
         MAX-ACCESS  read-only
         STATUS  current
         DESCRIPTION
            "The counter associated with the number of yellow octets discarded due to
            congestion in the egress queue."
         ::= { adGenMEFPolicer24HrCurrentEntry 10 }

adGenMEFPolicer24HrCurrentHCIngressGreenFrames OBJECT-TYPE
         SYNTAX Counter64
         MAX-ACCESS  read-only
         STATUS  current
         DESCRIPTION
            "The counter associated with the number frames coming out of the
            ingress policer which is marked green."
         ::= { adGenMEFPolicer24HrCurrentEntry 11 }

      adGenMEFPolicer24HrCurrentHCIngressYellowFrames OBJECT-TYPE
         SYNTAX Counter64
         MAX-ACCESS  read-only
         STATUS  current
         DESCRIPTION
            "The counter associated with the number frames coming out of the
            ingress policer which is marked yellow."
         ::= { adGenMEFPolicer24HrCurrentEntry 12 }

      adGenMEFPolicer24HrCurrentHCIngressRedFrames OBJECT-TYPE
         SYNTAX Counter64
         MAX-ACCESS  read-only
         STATUS  current
         DESCRIPTION
            "The counter associated with the number frames coming out of the
            ingress policer which is marked red (dropped)."
         ::= { adGenMEFPolicer24HrCurrentEntry 13 }

      adGenMEFPolicer24HrCurrentHCIngressGreenOctets OBJECT-TYPE
         SYNTAX Counter64
         MAX-ACCESS  read-only
         STATUS  current
         DESCRIPTION
            "The counter associated with the number octets coming out of the
            ingress policer which is marked green."
         ::= { adGenMEFPolicer24HrCurrentEntry 14 }

      adGenMEFPolicer24HrCurrentHCIngressYellowOctets OBJECT-TYPE
         SYNTAX Counter64
         MAX-ACCESS  read-only
         STATUS  current
         DESCRIPTION
            "The counter associated with the number octets coming out of the
            ingress policer which is marked yellow."
         ::= { adGenMEFPolicer24HrCurrentEntry 15 }

      adGenMEFPolicer24HrCurrentHCIngressRedOctets OBJECT-TYPE
         SYNTAX Counter64
         MAX-ACCESS  read-only
         STATUS  current
         DESCRIPTION
            "The counter associated with the number octets coming out of the
            ingress policer which is marked red (dropped)."
         ::= { adGenMEFPolicer24HrCurrentEntry 16 }

      adGenMEFPolicer24HrCurrentHCCongDiscardsIngressGreenFrames OBJECT-TYPE
         SYNTAX Counter64
         MAX-ACCESS  read-only
         STATUS  current
         DESCRIPTION
            "The counter associated with the number of green frames discarded due to
            congestion in the egress queue."
         ::= { adGenMEFPolicer24HrCurrentEntry 17 }

      adGenMEFPolicer24HrCurrentHCCongDiscardsIngressGreenOctets OBJECT-TYPE
         SYNTAX Counter64
         MAX-ACCESS  read-only
         STATUS  current
         DESCRIPTION
            "The counter associated with the number of green octets discarded due to
            congestion in the egress queue."
         ::= { adGenMEFPolicer24HrCurrentEntry 18 }

      adGenMEFPolicer24HrCurrentHCCongDiscardsIngressYellowFrames OBJECT-TYPE
         SYNTAX Counter64
         MAX-ACCESS  read-only
         STATUS  current
         DESCRIPTION
            "The counter associated with the number of yellow frames discarded due to
            congestion in the egress queue."
         ::= { adGenMEFPolicer24HrCurrentEntry 19 }

      adGenMEFPolicer24HrCurrentHCCongDiscardsIngressYellowOctets OBJECT-TYPE
         SYNTAX Counter64
         MAX-ACCESS  read-only
         STATUS  current
         DESCRIPTION
            "The counter associated with the number of yellow octets discarded due to
            congestion in the egress queue."
         ::= { adGenMEFPolicer24HrCurrentEntry 20 }
--==================================================================================================================

   adGenMEFPolicer24HrIntervalTable OBJECT-TYPE
      SYNTAX  SEQUENCE OF AdGenMEFPolicer24HrIntervalEntry
      MAX-ACCESS  not-accessible
      STATUS  current
      DESCRIPTION
         "The MEF Traffic Management 24Hr interval table."
      ::= { adGenMEFPolicerPerformance 5 }

   adGenMEFPolicer24HrIntervalEntry OBJECT-TYPE
      SYNTAX  AdGenMEFPolicer24HrIntervalEntry
      MAX-ACCESS  not-accessible
      STATUS  current
      DESCRIPTION
         "An entry in Traffic Management 24Hr interval table."
      INDEX   { adGenMEFProfileIndex, adGenMEFPolicer24HrIntervalNumber }
      ::= { adGenMEFPolicer24HrIntervalTable 1 }

   AdGenMEFPolicer24HrIntervalEntry  ::=
      SEQUENCE {
         adGenMEFPolicer24HrIntervalNumber
            Integer32,
         adGenMEFPolicer24HrIntervalIngressGreenFrames
    	    Gauge32,
         adGenMEFPolicer24HrIntervalIngressYellowFrames
	        Gauge32,
         adGenMEFPolicer24HrIntervalIngressRedFrames
	        Gauge32,
         adGenMEFPolicer24HrIntervalIngressGreenOctets
	        Gauge32,
         adGenMEFPolicer24HrIntervalIngressYellowOctets
	        Gauge32,
         adGenMEFPolicer24HrIntervalIngressRedOctets
	        Gauge32,
         adGenMEFPolicer24HrIntervalCongDiscardsIngressGreenFrames
                Gauge32,
         adGenMEFPolicer24HrIntervalCongDiscardsIngressGreenOctets
	        Gauge32,
         adGenMEFPolicer24HrIntervalCongDiscardsIngressYellowFrames
	        Gauge32,
         adGenMEFPolicer24HrIntervalCongDiscardsIngressYellowOctets
	        Gauge32,
         adGenMEFPolicer24HrIntervalHCIngressGreenFrames
    	    Counter64,
         adGenMEFPolicer24HrIntervalHCIngressYellowFrames
	        Counter64,
         adGenMEFPolicer24HrIntervalHCIngressRedFrames
	        Counter64,
         adGenMEFPolicer24HrIntervalHCIngressGreenOctets
	        Counter64,
         adGenMEFPolicer24HrIntervalHCIngressYellowOctets
	        Counter64,
         adGenMEFPolicer24HrIntervalHCIngressRedOctets
	        Counter64,
         adGenMEFPolicer24HrIntervalHCCongDiscardsIngressGreenFrames
                Counter64,
         adGenMEFPolicer24HrIntervalHCCongDiscardsIngressGreenOctets
	        Counter64,
         adGenMEFPolicer24HrIntervalHCCongDiscardsIngressYellowFrames
	        Counter64,
         adGenMEFPolicer24HrIntervalHCCongDiscardsIngressYellowOctets
	        Counter64
       }

      adGenMEFPolicer24HrIntervalNumber OBJECT-TYPE
         SYNTAX Integer32
         MAX-ACCESS  read-only
         STATUS  current
         DESCRIPTION
            "A number between 1 and 7, where 1 is the most recently
             completed day and 7 is the least recently completed
             day (assuming that all 7 days are valid)."
         ::= { adGenMEFPolicer24HrIntervalEntry 1 }

      adGenMEFPolicer24HrIntervalIngressGreenFrames OBJECT-TYPE
         SYNTAX Gauge32
         MAX-ACCESS  read-only
         STATUS  current
         DESCRIPTION
            "The counter associated with the number frames coming out of the
            ingress policer which is marked green in the selected interval."
         ::= { adGenMEFPolicer24HrIntervalEntry 2 }

      adGenMEFPolicer24HrIntervalIngressYellowFrames OBJECT-TYPE
         SYNTAX Gauge32
         MAX-ACCESS  read-only
         STATUS  current
         DESCRIPTION
            "The counter associated with the number frames coming out of the
            ingress policer which is marked yellow in the selected interval."
         ::= { adGenMEFPolicer24HrIntervalEntry 3 }

      adGenMEFPolicer24HrIntervalIngressRedFrames OBJECT-TYPE
         SYNTAX Gauge32
         MAX-ACCESS  read-only
         STATUS  current
         DESCRIPTION
            "The counter associated with the number frames coming out of the
            ingress policer which is marked red (dropped) in the selected interval."
         ::= { adGenMEFPolicer24HrIntervalEntry 4 }

      adGenMEFPolicer24HrIntervalIngressGreenOctets OBJECT-TYPE
         SYNTAX Gauge32
         MAX-ACCESS  read-only
         STATUS  current
         DESCRIPTION
            "The counter associated with the number octets coming out of the
            ingress policer which is marked green in the selected interval."
         ::= { adGenMEFPolicer24HrIntervalEntry 5 }

      adGenMEFPolicer24HrIntervalIngressYellowOctets OBJECT-TYPE
         SYNTAX Gauge32
         MAX-ACCESS  read-only
         STATUS  current
         DESCRIPTION
            "The counter associated with the number octets coming out of the
            ingress policer which is marked yellow in the selected interval."
         ::= { adGenMEFPolicer24HrIntervalEntry 6 }

      adGenMEFPolicer24HrIntervalIngressRedOctets OBJECT-TYPE
         SYNTAX Gauge32
         MAX-ACCESS  read-only
         STATUS  current
         DESCRIPTION
            "The counter associated with the number octets coming out of the
            ingress policer which is marked red (dropped) in the selected interval."
         ::= { adGenMEFPolicer24HrIntervalEntry 7 }

      adGenMEFPolicer24HrIntervalCongDiscardsIngressGreenFrames OBJECT-TYPE
         SYNTAX Gauge32
         MAX-ACCESS  read-only
         STATUS  current
         DESCRIPTION
            "The counter associated with the number of green frames discarded due to
            congestion in the egress queue in the selected interval."
         ::= { adGenMEFPolicer24HrIntervalEntry 8 }

      adGenMEFPolicer24HrIntervalCongDiscardsIngressGreenOctets OBJECT-TYPE
         SYNTAX Gauge32
         MAX-ACCESS  read-only
         STATUS  current
         DESCRIPTION
            "The counter associated with the number of green octets discarded due to
            congestion in the egress queue in the selected interval."
         ::= { adGenMEFPolicer24HrIntervalEntry 9 }

      adGenMEFPolicer24HrIntervalCongDiscardsIngressYellowFrames OBJECT-TYPE
         SYNTAX Gauge32
         MAX-ACCESS  read-only
         STATUS  current
         DESCRIPTION
            "The counter associated with the number of yellow frames discarded due to
            congestion in the egress queue in the selected interval."
         ::= { adGenMEFPolicer24HrIntervalEntry 10 }

      adGenMEFPolicer24HrIntervalCongDiscardsIngressYellowOctets OBJECT-TYPE
         SYNTAX Gauge32
         MAX-ACCESS  read-only
         STATUS  current
         DESCRIPTION
            "The counter associated with the number of yellow octets discarded due to
            congestion in the egress queue in the selected interval."
         ::= { adGenMEFPolicer24HrIntervalEntry 11 }

      adGenMEFPolicer24HrIntervalHCIngressGreenFrames OBJECT-TYPE
         SYNTAX Counter64
         MAX-ACCESS  read-only
         STATUS  current
         DESCRIPTION
            "The counter associated with the number frames coming out of the
            ingress policer which is marked green in the selected interval."
         ::= { adGenMEFPolicer24HrIntervalEntry 12 }

      adGenMEFPolicer24HrIntervalHCIngressYellowFrames OBJECT-TYPE
         SYNTAX Counter64
         MAX-ACCESS  read-only
         STATUS  current
         DESCRIPTION
            "The counter associated with the number frames coming out of the
            ingress policer which is marked yellow in the selected interval."
         ::= { adGenMEFPolicer24HrIntervalEntry 13 }

      adGenMEFPolicer24HrIntervalHCIngressRedFrames OBJECT-TYPE
         SYNTAX Counter64
         MAX-ACCESS  read-only
         STATUS  current
         DESCRIPTION
            "The counter associated with the number frames coming out of the
            ingress policer which is marked red (dropped) in the selected interval."
         ::= { adGenMEFPolicer24HrIntervalEntry 14 }

      adGenMEFPolicer24HrIntervalHCIngressGreenOctets OBJECT-TYPE
         SYNTAX Counter64
         MAX-ACCESS  read-only
         STATUS  current
         DESCRIPTION
            "The counter associated with the number octets coming out of the
            ingress policer which is marked green in the selected interval."
         ::= { adGenMEFPolicer24HrIntervalEntry 15 }

      adGenMEFPolicer24HrIntervalHCIngressYellowOctets OBJECT-TYPE
         SYNTAX Counter64
         MAX-ACCESS  read-only
         STATUS  current
         DESCRIPTION
            "The counter associated with the number octets coming out of the
            ingress policer which is marked yellow in the selected interval."
         ::= { adGenMEFPolicer24HrIntervalEntry 16 }

      adGenMEFPolicer24HrIntervalHCIngressRedOctets OBJECT-TYPE
         SYNTAX Counter64
         MAX-ACCESS  read-only
         STATUS  current
         DESCRIPTION
            "The counter associated with the number octets coming out of the
            ingress policer which is marked red (dropped) in the selected interval."
         ::= { adGenMEFPolicer24HrIntervalEntry 17 }

      adGenMEFPolicer24HrIntervalHCCongDiscardsIngressGreenFrames OBJECT-TYPE
         SYNTAX Counter64
         MAX-ACCESS  read-only
         STATUS  current
         DESCRIPTION
            "The counter associated with the number of green frames discarded due to
            congestion in the egress queue in the selected interval."
         ::= { adGenMEFPolicer24HrIntervalEntry 18 }

      adGenMEFPolicer24HrIntervalHCCongDiscardsIngressGreenOctets OBJECT-TYPE
         SYNTAX Counter64
         MAX-ACCESS  read-only
         STATUS  current
         DESCRIPTION
            "The counter associated with the number of green octets discarded due to
            congestion in the egress queue in the selected interval."
         ::= { adGenMEFPolicer24HrIntervalEntry 19 }

      adGenMEFPolicer24HrIntervalHCCongDiscardsIngressYellowFrames OBJECT-TYPE
         SYNTAX Counter64
         MAX-ACCESS  read-only
         STATUS  current
         DESCRIPTION
            "The counter associated with the number of yellow frames discarded due to
            congestion in the egress queue in the selected interval."
         ::= { adGenMEFPolicer24HrIntervalEntry 20 }

      adGenMEFPolicer24HrIntervalHCCongDiscardsIngressYellowOctets OBJECT-TYPE
         SYNTAX Counter64
         MAX-ACCESS  read-only
         STATUS  current
         DESCRIPTION
            "The counter associated with the number of yellow octets discarded due to
            congestion in the egress queue in the selected interval."
         ::= { adGenMEFPolicer24HrIntervalEntry 21 }
--==================================================================================================================

   adGenMEFPolicerPerfResetTable OBJECT-TYPE
      SYNTAX  SEQUENCE OF AdGenMEFPolicerPerfResetEntry
      MAX-ACCESS  not-accessible
      STATUS  current
      DESCRIPTION
         "The Policer Performance Reset table."
      ::= { adGenMEFPolicerPerformance 6 }

   adGenMEFPolicerPerfResetEntry OBJECT-TYPE
      SYNTAX  AdGenMEFPolicerPerfResetEntry
      MAX-ACCESS  not-accessible
      STATUS  current
      DESCRIPTION
         "An entry in the Policer Performance Reset table."
      INDEX   { adGenMEFProfileIndex }
      ::= { adGenMEFPolicerPerfResetTable 1 }

   AdGenMEFPolicerPerfResetEntry  ::=
      SEQUENCE {
         adGenMEFPolicerPerfReset
            INTEGER
       }

      adGenMEFPolicerPerfReset OBJECT-TYPE
         SYNTAX  INTEGER {
            policerPerfRst(1)
         }
         MAX-ACCESS  read-write
         STATUS  current
         DESCRIPTION
            "Resets all performance history for the selected policer."
         ::= { adGenMEFPolicerPerfResetEntry 1 }

--==================================================================================================================

   adGenMEF10100EthAnomaliesPerfThresholds  OBJECT IDENTIFIER ::= { adGenMEFPerformance 4 }

   adGenMEF10100EthAnomalies15MinThreshTable OBJECT-TYPE
      SYNTAX  SEQUENCE OF AdGenMEF10100EthAnomalies15MinThreshEntry
      MAX-ACCESS  not-accessible
      STATUS  current
      DESCRIPTION
         "The 10/100 Ethernet MEF Anomalies 15 minute threshold table."
      ::= { adGenMEF10100EthAnomaliesPerfThresholds 1 }

   adGenMEF10100EthAnomalies15MinThreshEntry OBJECT-TYPE
      SYNTAX  AdGenMEF10100EthAnomalies15MinThreshEntry
      MAX-ACCESS  not-accessible
      STATUS  current
      DESCRIPTION
         "An entry in the 10/100 Ethernet MEF Anomalies 15 minute threshold table."
      INDEX   { ifIndex }
      ::= { adGenMEF10100EthAnomalies15MinThreshTable 1 }

   AdGenMEF10100EthAnomalies15MinThreshEntry  ::=
      SEQUENCE {
         adGenMEF10100EthAnomalies15MinThreshFramesWithInvalidCEVLANID
            Gauge32
       }

      adGenMEF10100EthAnomalies15MinThreshFramesWithInvalidCEVLANID OBJECT-TYPE
         SYNTAX Gauge32
         MAX-ACCESS  read-write
         STATUS  current
         DESCRIPTION
            "The 15 minute threshold associated with the number of received frames with
            invalid CE-VLAN id."
         ::= { adGenMEF10100EthAnomalies15MinThreshEntry 1 }

--==================================================================================================================

   adGenMEF10100EthAnomalies24HrThreshTable OBJECT-TYPE
      SYNTAX  SEQUENCE OF AdGenMEF10100EthAnomalies24HrThreshEntry
      MAX-ACCESS  not-accessible
      STATUS  current
      DESCRIPTION
         "The 10/100 Ethernet MEF Anomalies 24 hour threshold table."
      ::= { adGenMEF10100EthAnomaliesPerfThresholds 2 }

   adGenMEF10100EthAnomalies24HrThreshEntry OBJECT-TYPE
      SYNTAX  AdGenMEF10100EthAnomalies24HrThreshEntry
      MAX-ACCESS  not-accessible
      STATUS  current
      DESCRIPTION
         "An entry in the 10/100 Ethernet MEF Anomalies 24 hour threshold table."
      INDEX   { ifIndex }
      ::= { adGenMEF10100EthAnomalies24HrThreshTable 1 }

   AdGenMEF10100EthAnomalies24HrThreshEntry  ::=
      SEQUENCE {
         adGenMEF10100EthAnomalies24HrThreshFramesWithInvalidCEVLANID
            Gauge32
       }

      adGenMEF10100EthAnomalies24HrThreshFramesWithInvalidCEVLANID OBJECT-TYPE
         SYNTAX Gauge32
         MAX-ACCESS  read-write
         STATUS  current
         DESCRIPTION
            "The 24 hour threshold associated with the number of received frames with
            invalid CE-VLAN id."
         ::= { adGenMEF10100EthAnomalies24HrThreshEntry 1 }

--==================================================================================================================

   adGenMEFGigEthAnomaliesPerfThresholds  OBJECT IDENTIFIER ::= { adGenMEFPerformance 5 }

   adGenMEFGigEthAnomalies15MinThreshTable OBJECT-TYPE
      SYNTAX  SEQUENCE OF AdGenMEFGigEthAnomalies15MinThreshEntry
      MAX-ACCESS  not-accessible
      STATUS  current
      DESCRIPTION
         "The Gigabit Ethernet MEF Anomalies 15 minute threshold table."
      ::= { adGenMEFGigEthAnomaliesPerfThresholds 1 }

   adGenMEFGigEthAnomalies15MinThreshEntry OBJECT-TYPE
      SYNTAX  AdGenMEFGigEthAnomalies15MinThreshEntry
      MAX-ACCESS  not-accessible
      STATUS  current
      DESCRIPTION
         "An entry in the Gigabit Ethernet MEF Anomalies 15 minute threshold table."
      INDEX   { ifIndex }
      ::= { adGenMEFGigEthAnomalies15MinThreshTable 1 }

   AdGenMEFGigEthAnomalies15MinThreshEntry  ::=
      SEQUENCE {
         adGenMEFGigEthAnomalies15MinThreshFramesWithInvalidCEVLANID
            Gauge32
       }

      adGenMEFGigEthAnomalies15MinThreshFramesWithInvalidCEVLANID OBJECT-TYPE
         SYNTAX Gauge32
         MAX-ACCESS  read-write
         STATUS  current
         DESCRIPTION
            "The 15 minute threshold associated with the number of received frames with
            invalid CE-VLAN id."
         ::= { adGenMEFGigEthAnomalies15MinThreshEntry 1 }

--==================================================================================================================

   adGenMEFGigEthAnomalies24HrThreshTable OBJECT-TYPE
      SYNTAX  SEQUENCE OF AdGenMEFGigEthAnomalies24HrThreshEntry
      MAX-ACCESS  not-accessible
      STATUS  current
      DESCRIPTION
         "The Gigabit Ethernet MEF Anomalies 24 hour threshold table."
      ::= { adGenMEFGigEthAnomaliesPerfThresholds 2 }

   adGenMEFGigEthAnomalies24HrThreshEntry OBJECT-TYPE
      SYNTAX  AdGenMEFGigEthAnomalies24HrThreshEntry
      MAX-ACCESS  not-accessible
      STATUS  current
      DESCRIPTION
         "An entry in the Gigabit Ethernet MEF Anomalies 24 hour threshold table."
      INDEX   { ifIndex }
      ::= { adGenMEFGigEthAnomalies24HrThreshTable 1 }

   AdGenMEFGigEthAnomalies24HrThreshEntry  ::=
      SEQUENCE {
         adGenMEFGigEthAnomalies24HrThreshFramesWithInvalidCEVLANID
            Gauge32
       }

      adGenMEFGigEthAnomalies24HrThreshFramesWithInvalidCEVLANID OBJECT-TYPE
         SYNTAX Gauge32
         MAX-ACCESS  read-write
         STATUS  current
         DESCRIPTION
            "The 24 hour threshold associated with the number of received frames with
            invalid CE-VLAN id."
         ::= { adGenMEFGigEthAnomalies24HrThreshEntry 1 }

--==================================================================================================================

   adGenMEFPolicerPerfThresholds  OBJECT IDENTIFIER ::= { adGenMEFPerformance 6 }

   adGenMEFPolicer15MinThreshTable OBJECT-TYPE
      SYNTAX  SEQUENCE OF AdGenMEFPolicer15MinThreshEntry
      MAX-ACCESS  not-accessible
      STATUS  current
      DESCRIPTION
         "The MEF Traffic Management 15 minute threshold table."
      ::= { adGenMEFPolicerPerfThresholds 1 }

   adGenMEFPolicer15MinThreshEntry OBJECT-TYPE
      SYNTAX  AdGenMEFPolicer15MinThreshEntry
      MAX-ACCESS  not-accessible
      STATUS  current
      DESCRIPTION
         "An entry in the MEF Traffic Management 15 minute threshold table."
      INDEX   { adGenMEFProfileIndex }
      ::= { adGenMEFPolicer15MinThreshTable 1 }

   AdGenMEFPolicer15MinThreshEntry  ::=
      SEQUENCE {
         adGenMEFPolicer15MinThresholdIngressGreenFrames
    	    Gauge32,
         adGenMEFPolicer15MinThresholdIngressYellowFrames
	        Gauge32,
         adGenMEFPolicer15MinThresholdIngressRedFrames
	        Gauge32,
         adGenMEFPolicer15MinThresholdCongDiscardsIngressGreenFrames
    	        Gauge32,
         adGenMEFPolicer15MinThresholdCongDiscardsIngressYellowFrames
	        Gauge32,
	  adGenMEFPolicer15MinThresholdHCIngressGreenFrames
    	    Unsigned64TC,
         adGenMEFPolicer15MinThresholdHCIngressYellowFrames
	        Unsigned64TC,
         adGenMEFPolicer15MinThresholdHCIngressRedFrames
	        Unsigned64TC,
         adGenMEFPolicer15MinThresholdHCCongDiscardsIngressGreenFrames
    	        Unsigned64TC,
         adGenMEFPolicer15MinThresholdHCCongDiscardsIngressYellowFrames
	        Unsigned64TC
       }

      adGenMEFPolicer15MinThresholdIngressGreenFrames OBJECT-TYPE
         SYNTAX Gauge32
         MAX-ACCESS  read-write
         STATUS  current
         DESCRIPTION
            "The 15 minute threshold associated with the number frames coming out of the
            ingress policer which is marked green.  A value of 0 will disable the Threshold.
            If the adGenMEFPolicer15MinThresholdHCIngressGreenFrames is set to a value greater
            than 2^32, then this oid will be forced to a 0."
         ::= { adGenMEFPolicer15MinThreshEntry 1 }

      adGenMEFPolicer15MinThresholdIngressYellowFrames OBJECT-TYPE
         SYNTAX Gauge32
         MAX-ACCESS  read-write
         STATUS  current
         DESCRIPTION
            "The 15 minute threshold associated with the number frames coming out of the
            ingress policer which is marked yellow.  A value of 0 will disable the Threshold.
            If the adGenMEFPolicer15MinThresholdHCIngressYellowFrames is set to a value greater
            than 2^32, then this oid will be forced to a 0."
         ::= { adGenMEFPolicer15MinThreshEntry 2 }

      adGenMEFPolicer15MinThresholdIngressRedFrames OBJECT-TYPE
         SYNTAX Gauge32
         MAX-ACCESS  read-write
         STATUS  current
         DESCRIPTION
            "The 15 minute threshold associated with the number frames coming out of the
            ingress policer which is marked red (dropped).  A value of 0 will disable the Threshold.
            If the adGenMEFPolicer15MinThresholdHCIngressRedFrames is set to a value greater
            than 2^32, then this oid will be forced to a 0."
         ::= { adGenMEFPolicer15MinThreshEntry 3 }

      adGenMEFPolicer15MinThresholdCongDiscardsIngressGreenFrames OBJECT-TYPE
         SYNTAX Gauge32
         MAX-ACCESS  read-write
         STATUS  current
         DESCRIPTION
            "The 15 minute threshold associated with the number of green frames discarded due to
            congestion in the egress queue.  A value of 0 will disable the Threshold.
            If the adGenMEFPolicer15MinThresholdHCCongDiscardsIngressGreenFrames is set to a value greater
            than 2^32, then this oid will be forced to a 0."
         ::= { adGenMEFPolicer15MinThreshEntry 4 }

      adGenMEFPolicer15MinThresholdCongDiscardsIngressYellowFrames OBJECT-TYPE
         SYNTAX Gauge32
         MAX-ACCESS  read-write
         STATUS  current
         DESCRIPTION
            "The 15 minute threshold associated with the number of yellow frames discarded due to
            congestion in the egress queue.  A value of 0 will disable the Threshold.
            If the adGenMEFPolicer15MinThresholdHCCongDiscardsIngressYellowFrames is set to a value greater
            than 2^32, then this oid will be forced to a 0."
         ::= { adGenMEFPolicer15MinThreshEntry 5 }

      adGenMEFPolicer15MinThresholdHCIngressGreenFrames OBJECT-TYPE
         SYNTAX Unsigned64TC
         MAX-ACCESS  read-write
         STATUS  current
         DESCRIPTION
            "The 15 minute threshold associated with the number frames coming out of the
            ingress policer which is marked green. A value of 0 will disable the Threshold.
            If this oid is set to a value greater
            than 2^32, then adGenMEFPolicer15MinThresholdIngressGreenFrames oid will be forced to a 0."
         ::= { adGenMEFPolicer15MinThreshEntry 6 }

      adGenMEFPolicer15MinThresholdHCIngressYellowFrames OBJECT-TYPE
         SYNTAX Unsigned64TC
         MAX-ACCESS  read-write
         STATUS  current
         DESCRIPTION
            "The 15 minute threshold associated with the number frames coming out of the
            ingress policer which is marked yellow.  A value of 0 will disable the Threshold.
            If this oid is set to a value greater
            than 2^32, then adGenMEFPolicer15MinThresholdIngressYellowFrames oid will be forced to a 0."
         ::= { adGenMEFPolicer15MinThreshEntry 7 }

      adGenMEFPolicer15MinThresholdHCIngressRedFrames OBJECT-TYPE
         SYNTAX Unsigned64TC
         MAX-ACCESS  read-write
         STATUS  current
         DESCRIPTION
            "The 15 minute threshold associated with the number frames coming out of the
            ingress policer which is marked red (dropped).  A value of 0 will disable the Threshold.
            If this oid is set to a value greater
            than 2^32, then adGenMEFPolicer15MinThresholdIngressRedFrames oid will be forced to a 0."
         ::= { adGenMEFPolicer15MinThreshEntry 8 }

      adGenMEFPolicer15MinThresholdHCCongDiscardsIngressGreenFrames OBJECT-TYPE
         SYNTAX Unsigned64TC
         MAX-ACCESS  read-write
         STATUS  current
         DESCRIPTION
            "The 15 minute threshold associated with the number of green frames discarded due to
            congestion in the egress queue.  A value of 0 will disable the Threshold.
            If this oid is set to a value greater
            than 2^32, then adGenMEFPolicer15MinThresholdCongDiscardsIngressGreenFrames oid will be forced to a 0."
         ::= { adGenMEFPolicer15MinThreshEntry 9 }

      adGenMEFPolicer15MinThresholdHCCongDiscardsIngressYellowFrames OBJECT-TYPE
         SYNTAX Unsigned64TC
         MAX-ACCESS  read-write
         STATUS  current
         DESCRIPTION
            "The 15 minute threshold associated with the number of yellow frames discarded due to
            congestion in the egress queue.  A value of 0 will disable the Threshold.
            If this oid is set to a value greater
            than 2^32, then adGenMEFPolicer15MinThresholdCongDiscardsIngressYellowFrames oid will be forced to a 0."
         ::= { adGenMEFPolicer15MinThreshEntry 10 }

--==================================================================================================================

   adGenMEFPolicer24HrThreshTable OBJECT-TYPE
      SYNTAX  SEQUENCE OF AdGenMEFPolicer24HrThreshEntry
      MAX-ACCESS  not-accessible
      STATUS  current
      DESCRIPTION
         "The MEF Traffic Management 24 hour threshold table."
      ::= { adGenMEFPolicerPerfThresholds 2 }

   adGenMEFPolicer24HrThreshEntry OBJECT-TYPE
      SYNTAX  AdGenMEFPolicer24HrThreshEntry
      MAX-ACCESS  not-accessible
      STATUS  current
      DESCRIPTION
         "An entry in the MEF Traffic Management 24 hour threshold table."
      INDEX   { adGenMEFProfileIndex }
      ::= { adGenMEFPolicer24HrThreshTable 1 }

   AdGenMEFPolicer24HrThreshEntry  ::=
      SEQUENCE {
         adGenMEFPolicer24HrThresholdIngressGreenFrames
    	    Gauge32,
         adGenMEFPolicer24HrThresholdIngressYellowFrames
	        Gauge32,
         adGenMEFPolicer24HrThresholdIngressRedFrames
	        Gauge32,
         adGenMEFPolicer24HrThresholdCongDiscardsIngressGreenFrames
    	        Gauge32,
         adGenMEFPolicer24HrThresholdCongDiscardsIngressYellowFrames
	        Gauge32,
	  adGenMEFPolicer24HrThresholdHCIngressGreenFrames
    	    Unsigned64TC,
         adGenMEFPolicer24HrThresholdHCIngressYellowFrames
	        Unsigned64TC,
         adGenMEFPolicer24HrThresholdHCIngressRedFrames
	        Unsigned64TC,
         adGenMEFPolicer24HrThresholdHCCongDiscardsIngressGreenFrames
    	        Unsigned64TC,
         adGenMEFPolicer24HrThresholdHCCongDiscardsIngressYellowFrames
	        Unsigned64TC
       }

      adGenMEFPolicer24HrThresholdIngressGreenFrames OBJECT-TYPE
         SYNTAX Gauge32
         MAX-ACCESS  read-write
         STATUS  current
         DESCRIPTION
            "The 24 hour threshold associated with the number frames coming out of the
            ingress policer which is marked green.  A value of 0 will disable the Threshold.
            If the adGenMEFPolicer24HrThresholdHCIngressGreenFrames is set to a value greater
            than 2^32, then this oid will be forced to a 0."
         ::= { adGenMEFPolicer24HrThreshEntry 1 }

      adGenMEFPolicer24HrThresholdIngressYellowFrames OBJECT-TYPE
         SYNTAX Gauge32
         MAX-ACCESS  read-write
         STATUS  current
         DESCRIPTION
            "The 24 hour threshold associated with the number frames coming out of the
            ingress policer which is marked yellow.  A value of 0 will disable the Threshold.
            If the adGenMEFPolicer24HrThresholdHCIngressYellowFrames is set to a value greater
            than 2^32, then this oid will be forced to a 0."
         ::= { adGenMEFPolicer24HrThreshEntry 2 }

      adGenMEFPolicer24HrThresholdIngressRedFrames OBJECT-TYPE
         SYNTAX Gauge32
         MAX-ACCESS  read-write
         STATUS  current
         DESCRIPTION
            "The 24 hour threshold associated with the number frames coming out of the
            ingress policer which is marked red (dropped).  A value of 0 will disable the Threshold.
            If the adGenMEFPolicer24HrThresholdHCIngressRedFrames is set to a value greater
            than 2^32, then this oid will be forced to a 0."
         ::= { adGenMEFPolicer24HrThreshEntry 3 }

      adGenMEFPolicer24HrThresholdCongDiscardsIngressGreenFrames OBJECT-TYPE
         SYNTAX Gauge32
         MAX-ACCESS  read-write
         STATUS  current
         DESCRIPTION
            "The 24 hour threshold associated with the number of green frames discarded due to
            congestion in the egress queue.  A value of 0 will disable the Threshold.
            If the adGenMEFPolicer24HrThresholdHCCongDiscardsIngressGreenFrames is set to a value greater
            than 2^32, then this oid will be forced to a 0."
         ::= { adGenMEFPolicer24HrThreshEntry 4 }

      adGenMEFPolicer24HrThresholdCongDiscardsIngressYellowFrames OBJECT-TYPE
         SYNTAX Gauge32
         MAX-ACCESS  read-write
         STATUS  current
         DESCRIPTION
            "The 24 hour threshold associated with the number of yellow frames discarded due to
            congestion in the egress queue.  A value of 0 will disable the Threshold.
            If the adGenMEFPolicer24HrThresholdHCCongDiscardsIngressYellowFrames is set to a value greater
            than 2^32, then this oid will be forced to a 0."
         ::= { adGenMEFPolicer24HrThreshEntry 5 }

      adGenMEFPolicer24HrThresholdHCIngressGreenFrames OBJECT-TYPE
         SYNTAX Unsigned64TC
         MAX-ACCESS  read-write
         STATUS  current
         DESCRIPTION
            "The 24 hour threshold associated with the number frames coming out of the
            ingress policer which is marked green.  A value of 0 will disable the Threshold.
            If this oid is set to a value greater
            than 2^32, then adGenMEFPolicer24HrThresholdIngressGreenFrames oid will be forced to a 0."
         ::= { adGenMEFPolicer24HrThreshEntry 6 }

      adGenMEFPolicer24HrThresholdHCIngressYellowFrames OBJECT-TYPE
         SYNTAX Unsigned64TC
         MAX-ACCESS  read-write
         STATUS  current
         DESCRIPTION
            "The 24 hour threshold associated with the number frames coming out of the
            ingress policer which is marked yellow.  A value of 0 will disable the Threshold.
            If this oid is set to a value greater
            than 2^32, then adGenMEFPolicer24HrThresholdIngressYellowFrames oid will be forced to a 0."
         ::= { adGenMEFPolicer24HrThreshEntry 7 }

      adGenMEFPolicer24HrThresholdHCIngressRedFrames OBJECT-TYPE
         SYNTAX Unsigned64TC
         MAX-ACCESS  read-write
         STATUS  current
         DESCRIPTION
            "The 24 hour threshold associated with the number frames coming out of the
            ingress policer which is marked red (dropped).  A value of 0 will disable the Threshold.
            If this oid is set to a value greater
            than 2^32, then adGenMEFPolicer24HrThresholdIngressRedFrames oid will be forced to a 0."
         ::= { adGenMEFPolicer24HrThreshEntry 8 }

      adGenMEFPolicer24HrThresholdHCCongDiscardsIngressGreenFrames OBJECT-TYPE
         SYNTAX Unsigned64TC
         MAX-ACCESS  read-write
         STATUS  current
         DESCRIPTION
            "The 24 hour threshold associated with the number of green frames discarded due to
            congestion in the egress queue.  A value of 0 will disable the Threshold.
            If this oid is set to a value greater
            than 2^32, then adGenMEFPolicer24HrThresholdCongDiscardsIngressGreenFrames oid will be forced to a 0."
         ::= { adGenMEFPolicer24HrThreshEntry 9 }

      adGenMEFPolicer24HrThresholdHCCongDiscardsIngressYellowFrames OBJECT-TYPE
         SYNTAX Unsigned64TC
         MAX-ACCESS  read-write
         STATUS  current
         DESCRIPTION
            "The 24 hour threshold associated with the number of yellow frames discarded due to
            congestion in the egress queue.  A value of 0 will disable the Threshold.
            If this oid is set to a value greater
            than 2^32, then adGenMEFPolicer24HrThresholdCongDiscardsIngressYellowFrames oid will be forced to a 0."
         ::= { adGenMEFPolicer24HrThreshEntry 10 }

--==================================================================================================================
-- ******************************************************************************************
-- Alarms
-- ******************************************************************************************

adGenMEFSet10100EthAnomalies15MinFramesWithInvalidCEVLANID NOTIFICATION-TYPE
   OBJECTS  {
      sysName,
      adGenPortTrapIdentifier,
      ifIndex
   }
   STATUS  current
   DESCRIPTION
      "This trap indicates that the Ethernet port has crossed the 15 min Frames with Invalid CE-VLAN ID Threshold"
      --#TYPE         "Status - Alarm"
      --#SUMMARY      "MEF 2: 10/100 Ethernet Frames with Invalid CE-VLAN ID 15 min Threshold Crossed."
      --#SEVERITY     WARNING
      --#GENERIC      6
      --#CATEGORY     "Error Events"
      --#SOURCE_ID    "A"
      --#TIMEINDEX    0
   ::= { adGenMEFEvents 1 }

adGenMEFSet10100EthAnomalies24HrFramesWithInvalidCEVLANID NOTIFICATION-TYPE
   OBJECTS  {
      sysName,
      adGenPortTrapIdentifier,
      ifIndex
   }
   STATUS  current
   DESCRIPTION
      "This trap indicates that the Ethernet port has crossed the 24 hour Frames with Invalid CE-VLAN ID Threshold"
      --#TYPE         "Status - Alarm"
      --#SUMMARY      "MEF 3: 10/100 Ethernet Frames with Invalid CE-VLAN ID 24 hr Threshold Crossed."
      --#SEVERITY     WARNING
      --#GENERIC      6
      --#CATEGORY     "Error Events"
      --#SOURCE_ID    "A"
      --#TIMEINDEX    0
   ::= { adGenMEFEvents 2 }

adGenMEFSetGigEthAnomalies15MinFramesWithInvalidCEVLANID NOTIFICATION-TYPE
   OBJECTS  {
      sysName,
      adGenPortTrapIdentifier,
      ifIndex
   }
   STATUS  current
   DESCRIPTION
      "This trap indicates that the Gigabit Ethernet port has crossed the 15 min Frames with Invalid CE-VLAN ID Threshold"
      --#TYPE         "Status - Alarm"
      --#SUMMARY      "MEF 4: Gigabit Ethernet Frames with Invalid CE-VLAN ID 15 min Threshold Crossed."
      --#SEVERITY     WARNING
      --#GENERIC      6
      --#CATEGORY     "Error Events"
      --#SOURCE_ID    "A"
      --#TIMEINDEX    0
   ::= { adGenMEFEvents 3 }

adGenMEFSetGigEthAnomalies24HrFramesWithInvalidCEVLANID NOTIFICATION-TYPE
   OBJECTS  {
      sysName,
      adGenPortTrapIdentifier,
      ifIndex
   }
   STATUS  current
   DESCRIPTION
      "This trap indicates that the Gigabit Ethernet port has crossed the 24 hour Frames with Invalid CE-VLAN ID Threshold"
      --#TYPE         "Status - Alarm"
      --#SUMMARY      "MEF 5: Gigabit Ethernet Frames with Invalid CE-VLAN ID 24 hour Threshold Crossed."
      --#SEVERITY     WARNING
      --#GENERIC      6
      --#CATEGORY     "Error Events"
      --#SOURCE_ID    "A"
      --#TIMEINDEX    0
   ::= { adGenMEFEvents 4 }

adGenMEFSetPolicer15MinIngressGreenFrames NOTIFICATION-TYPE
   OBJECTS  {
      sysName,
      adGenMEFProfileAlias,
      adGenMEFProfileIndex
   }
   STATUS  current
   DESCRIPTION
      "This trap indicates that the specified policer has crossed the 15 minute Ingress Green Frames Threshold"
      --#TYPE         "Status - Alarm"
      --#SUMMARY      "MEF 6: Ingress Green Frames 15 min Threshold Crossed."
      --#SEVERITY     WARNING
      --#GENERIC      6
      --#CATEGORY     "Error Events"
      --#SOURCE_ID    "A"
      --#TIMEINDEX    0
   ::= { adGenMEFEvents 5 }

adGenMEFSetPolicer15MinIngressYellowFrames NOTIFICATION-TYPE
   OBJECTS  {
      sysName,
      adGenMEFProfileAlias,
      adGenMEFProfileIndex
   }
   STATUS  current
   DESCRIPTION
      "This trap indicates that the specified policer has crossed the 15 minute Ingress Yellow Frames Threshold"
      --#TYPE         "Status - Alarm"
      --#SUMMARY      "MEF 6: Ingress Yellow Frames 15 min Threshold Crossed."
      --#SEVERITY     WARNING
      --#GENERIC      6
      --#CATEGORY     "Error Events"
      --#SOURCE_ID    "A"
      --#TIMEINDEX    0
   ::= { adGenMEFEvents 6 }

adGenMEFSetPolicer15MinIngressRedFrames NOTIFICATION-TYPE
   OBJECTS  {
      sysName,
      adGenMEFProfileAlias,
      adGenMEFProfileIndex
   }
   STATUS  current
   DESCRIPTION
      "This trap indicates that the specified policer has crossed the 15 minute Ingress Red Frames Threshold"
      --#TYPE         "Status - Alarm"
      --#SUMMARY      "MEF 6: Ingress Red Frames 15 min Threshold Crossed."
      --#SEVERITY     WARNING
      --#GENERIC      6
      --#CATEGORY     "Error Events"
      --#SOURCE_ID    "A"
      --#TIMEINDEX    0
   ::= { adGenMEFEvents 7 }

adGenMEFSetPolicer15MinCongDiscardsIngressGreenFrames NOTIFICATION-TYPE
   OBJECTS  {
      sysName,
      adGenMEFProfileAlias,
      adGenMEFProfileIndex
   }
   STATUS  current
   DESCRIPTION
      "This trap indicates that the specified policer has crossed the 15 minute Congestion Discards Ingress Green Frames Threshold"
      --#TYPE         "Status - Alarm"
      --#SUMMARY      "MEF 6: Congestion Discards Ingress Green Frames 15 min Threshold Crossed."
      --#SEVERITY     WARNING
      --#GENERIC      6
      --#CATEGORY     "Error Events"
      --#SOURCE_ID    "A"
      --#TIMEINDEX    0
   ::= { adGenMEFEvents 8 }

adGenMEFSetPolicer15MinCongDiscardsIngressYellowFrames NOTIFICATION-TYPE
   OBJECTS  {
      sysName,
      adGenMEFProfileAlias,
      adGenMEFProfileIndex
   }
   STATUS  current
   DESCRIPTION
      "This trap indicates that the specified policer has crossed the 15 minute Congestion Discards Ingress Yellow Frames Threshold"
      --#TYPE         "Status - Alarm"
      --#SUMMARY      "MEF 6: Congestion Discards Ingress Yellow Frames 15 min Threshold Crossed."
      --#SEVERITY     WARNING
      --#GENERIC      6
      --#CATEGORY     "Error Events"
      --#SOURCE_ID    "A"
      --#TIMEINDEX    0
   ::= { adGenMEFEvents 9 }

adGenMEFSetPolicer24HrIngressGreenFrames NOTIFICATION-TYPE
   OBJECTS  {
      sysName,
      adGenMEFProfileAlias,
      adGenMEFProfileIndex
   }
   STATUS  current
   DESCRIPTION
      "This trap indicates that the specified policer has crossed the 24 hour Ingress Green Frames Threshold"
      --#TYPE         "Status - Alarm"
      --#SUMMARY      "MEF 6: Ingress Green Frames 24 hour Threshold Crossed."
      --#SEVERITY     WARNING
      --#GENERIC      6
      --#CATEGORY     "Error Events"
      --#SOURCE_ID    "A"
      --#TIMEINDEX    0
   ::= { adGenMEFEvents 10 }

adGenMEFSetPolicer24HrIngressYellowFrames NOTIFICATION-TYPE
   OBJECTS  {
      sysName,
      adGenMEFProfileAlias,
      adGenMEFProfileIndex
   }
   STATUS  current
   DESCRIPTION
      "This trap indicates that the specified policer has crossed the 24 hour Ingress Yellow Frames Threshold"
      --#TYPE         "Status - Alarm"
      --#SUMMARY      "MEF 6: Ingress Yellow Frames 24 hour Threshold Crossed."
      --#SEVERITY     WARNING
      --#GENERIC      6
      --#CATEGORY     "Error Events"
      --#SOURCE_ID    "A"
      --#TIMEINDEX    0
   ::= { adGenMEFEvents 11 }

adGenMEFSetPolicer24HrIngressRedFrames NOTIFICATION-TYPE
   OBJECTS  {
      sysName,
      adGenMEFProfileAlias,
      adGenMEFProfileIndex
   }
   STATUS  current
   DESCRIPTION
      "This trap indicates that the specified policer has crossed the 24 hour Ingress Red Frames Threshold"
      --#TYPE         "Status - Alarm"
      --#SUMMARY      "MEF 6: Ingress Red Frames 24 hour Threshold Crossed."
      --#SEVERITY     WARNING
      --#GENERIC      6
      --#CATEGORY     "Error Events"
      --#SOURCE_ID    "A"
      --#TIMEINDEX    0
   ::= { adGenMEFEvents 12 }

adGenMEFSetPolicer24HrCongDiscardsIngressGreenFrames NOTIFICATION-TYPE
   OBJECTS  {
      sysName,
      adGenMEFProfileAlias,
      adGenMEFProfileIndex
   }
   STATUS  current
   DESCRIPTION
      "This trap indicates that the specified policer has crossed the 24 hour Congestion Discards Ingress Green Frames Threshold"
      --#TYPE         "Status - Alarm"
      --#SUMMARY      "MEF 6: Congestion Discards Ingress Green Frames 24 hour Threshold Crossed."
      --#SEVERITY     WARNING
      --#GENERIC      6
      --#CATEGORY     "Error Events"
      --#SOURCE_ID    "A"
      --#TIMEINDEX    0
   ::= { adGenMEFEvents 13 }

adGenMEFSetPolicer24HrCongDiscardsIngressYellowFrames NOTIFICATION-TYPE
   OBJECTS  {
      sysName,
      adGenMEFProfileAlias,
      adGenMEFProfileIndex
   }
   STATUS  current
   DESCRIPTION
      "This trap indicates that the specified policer has crossed the 24 hour Congestion Discards Ingress Yellow Frames Threshold"
      --#TYPE         "Status - Alarm"
      --#SUMMARY      "MEF 6: Congestion Discards Ingress Yellow Frames 24 hour Threshold Crossed."
      --#SEVERITY     WARNING
      --#GENERIC      6
      --#CATEGORY     "Error Events"
      --#SOURCE_ID    "A"
      --#TIMEINDEX    0
   ::= { adGenMEFEvents 14 }

--==================================================================================================================
-- ******************************************************************************************
-- MIB Groups
-- ******************************************************************************************
adGenMEFProvScalarGroup OBJECT-GROUP
   OBJECTS
   {
        adGenMEFDeleteAll,
        adGenMEFEVCIndexNext,
        adGenMEFMapIndexNext,
        adGenMEFProfileIndexNext,
        adGenMEFEVCEthertype
   }
   STATUS current
   DESCRIPTION
     "These objects provide support for the provisioning scalars."
   ::= { adGenMEFMibGroups 1 }

adGenMEFProvEVCGroup OBJECT-GROUP
   OBJECTS
   {
        adGenMEFEVCIndex,
        adGenMEFEVCRowStatus,
        adGenMEFEVCAlias,
        adGenMEFEVCStatus,
        adGenMEFEVCPort,
        adGenMEFEVCCEVLANIDPreservation,
        adGenMEFEVCVLANID,
        adGenMEFEVCMapsByIndex,
		adGenMEFEVCNumMaps
   }
   STATUS current
   DESCRIPTION
     "These objects provide support for the EVC provisioning."
   ::= { adGenMEFMibGroups 2 }

adGenMEFProvMapGroup OBJECT-GROUP
   OBJECTS
   {
        adGenMEFMapIndex,
        adGenMEFMapRowStatus,
        adGenMEFMapAlias,
        adGenMEFMapStatus,
        adGenMEFMapAssociatedEVCAlias,
        adGenMEFMapAssociatedEVCIndex,
        adGenMEFMapUNIPort,
        adGenMEFMapCEVLANID,
        adGenMEFMapCEVLANPRI,
        adGenMEFMapUntagged,
        adGenMEFMapCoS,
        adGenMEFMapAttachedProfileAlias,
        adGenMEFMapAttachedProfileIndex,
        adGenMEFMapBroadcast,
        adGenMEFMapMulticast,
        adGenMEFMapUnicast,
        adGenMEFMapL2CP,
	adGenMEFMapMenCTag,
      	adGenMEFMapMenCTagPri,
	adGenMEFMapDSCPRange,
	adGenMEFMapIpHost
   }
   STATUS current
   DESCRIPTION
     "These objects provide support for the map provisioning."
   ::= { adGenMEFMibGroups 3 }

adGenMEFProvProfileGroup OBJECT-GROUP
   OBJECTS
   {
        adGenMEFProfileIndex,
        adGenMEFProfileRowStatus,
        adGenMEFProfileAlias,
        adGenMEFProfileStatus,
        adGenMEFProfileApp,
        adGenMEFProfileUNIPort,
        adGenMEFProfileEVC,
        adGenMEFProfileCoSValue,
        adGenMEFProfileRateCoupling,
        adGenMEFProfileCBS,
        adGenMEFProfileEBS,
        adGenMEFProfileAddMap,
        adGenMEFProfileRemoveMap,
        adGenMEFProfileMapsByAlias,
        adGenMEFProfileMapsByIndex,
        adGenMEFProfileDroppedPackets,
		adGenMEFProfileCommittedInformationRate,
		adGenMEFProfileExcessInformationRate
   }
   STATUS current
   DESCRIPTION
     "These objects provide support for the profile provisioning."
   ::= { adGenMEFMibGroups 4 }

adGenMEFProv10100EthQueueGroup OBJECT-GROUP
   OBJECTS
   {
        adGenMEFQueueWREDTimeConstant,
        adGenMEF10100EthCoSIndex,
        adGenMEF10100EthQueueMaxDepth,
        adGenMEF10100EthQueueWREDState,
        adGenMEF10100EthQueueWREDGreenMaxThresh,
        adGenMEF10100EthQueueWREDGreenMinThresh,
        adGenMEF10100EthQueueWREDGreenDropProb,
        adGenMEF10100EthQueueWREDYellowMaxThresh,
        adGenMEF10100EthQueueWREDYellowMinThresh,
        adGenMEF10100EthQueueWREDYellowDropProb
   }
   STATUS current
   DESCRIPTION
     "These objects provide support for the 10/100 Ethernet queue provisioning."
   ::= { adGenMEFMibGroups 5 }

adGenMEFProvGigEthQueueGroup OBJECT-GROUP
   OBJECTS
   {
        adGenMEFQueueWREDTimeConstant,
        adGenMEFGigEthCoSIndex,
        adGenMEFGigEthQueueMaxDepth,
        adGenMEFGigEthQueueWREDState,
        adGenMEFGigEthQueueWREDGreenMaxThresh,
        adGenMEFGigEthQueueWREDGreenMinThresh,
        adGenMEFGigEthQueueWREDGreenDropProb,
        adGenMEFGigEthQueueWREDYellowMaxThresh,
        adGenMEFGigEthQueueWREDYellowMinThresh,
        adGenMEFGigEthQueueWREDYellowDropProb
   }
   STATUS current
   DESCRIPTION
     "These objects provide support for the Gigabit Ethernet queue provisioning."
   ::= { adGenMEFMibGroups 6 }

adGenMEFProvBondGrpQueueGroup OBJECT-GROUP
   OBJECTS
   {
        adGenMEFQueueWREDTimeConstant,
        adGenMEFBondGrpCoSIndex,
        adGenMEFBondGrpQueueMaxDepth,
        adGenMEFBondGrpQueueWREDState,
        adGenMEFBondGrpQueueWREDGreenMaxThresh,
        adGenMEFBondGrpQueueWREDGreenMinThresh,
        adGenMEFBondGrpQueueWREDGreenDropProb,
        adGenMEFBondGrpQueueWREDYellowMaxThresh,
        adGenMEFBondGrpQueueWREDYellowMinThresh,
        adGenMEFBondGrpQueueWREDYellowDropProb
   }
   STATUS current
   DESCRIPTION
     "These objects provide support for the bonding group queue provisioning."
   ::= { adGenMEFMibGroups 7 }

adGenMEFProvUNIGroup OBJECT-GROUP
   OBJECTS
   {
        adGenMEFUNIMapsByAlias,
        adGenMEFUNIMapsByIndex
   }
   STATUS current
   DESCRIPTION
     "These objects provide support for the UNI provisioning."
   ::= { adGenMEFMibGroups 8 }

adGenMEFProvMENGroup OBJECT-GROUP
   OBJECTS
   {
        adGenMEFMENVLANIDPool
   }
   STATUS current
   DESCRIPTION
     "These objects provide support for the MEN provisioning."
   ::= { adGenMEFMibGroups 9 }

adGenMEFProvQueueCoSMapGroup OBJECT-GROUP
   OBJECTS
   {
        adGenMEFQueueCoSMapForPri0,
        adGenMEFQueueCoSMapForPri1,
        adGenMEFQueueCoSMapForPri2,
        adGenMEFQueueCoSMapForPri3,
        adGenMEFQueueCoSMapForPri4,
        adGenMEFQueueCoSMapForPri5,
        adGenMEFQueueCoSMapForPri6,
        adGenMEFQueueCoSMapForPri7
   }
   STATUS current
   DESCRIPTION
     "These objects provide support for the CoS mapping."
   ::= { adGenMEFMibGroups 10 }

adGenMEFPolicerRstPerfGroup OBJECT-GROUP
   OBJECTS
   {
        adGenMEFPolicerRstCurrentIntervals,
        adGenMEFPolicerRstAll,
        adGenMEFPolicerPerfReset
   }
   STATUS current
   DESCRIPTION
     "These objects provide support for the Policer performance statistics resets."
   ::= { adGenMEFMibGroups 11 }

adGenMEFPolicerPerfGroup OBJECT-GROUP
   OBJECTS
   {
        adGenMEFPolicer15MinCurrentIngressGreenFrames,
        adGenMEFPolicer15MinCurrentIngressYellowFrames,
	    adGenMEFPolicer15MinCurrentIngressRedFrames,
	    adGenMEFPolicer15MinCurrentIngressGreenOctets,
	    adGenMEFPolicer15MinCurrentIngressYellowOctets,
	    adGenMEFPolicer15MinCurrentIngressRedOctets,
        adGenMEFPolicer15MinCurrentCongDiscardsIngressGreenFrames,
        adGenMEFPolicer15MinCurrentCongDiscardsIngressGreenOctets,
	    adGenMEFPolicer15MinCurrentCongDiscardsIngressYellowFrames,
	    adGenMEFPolicer15MinCurrentCongDiscardsIngressYellowOctets,
	  adGenMEFPolicer15MinCurrentHCIngressGreenFrames,
         adGenMEFPolicer15MinCurrentHCIngressYellowFrames,
         adGenMEFPolicer15MinCurrentHCIngressRedFrames,
         adGenMEFPolicer15MinCurrentHCIngressGreenOctets,
         adGenMEFPolicer15MinCurrentHCIngressYellowOctets,
         adGenMEFPolicer15MinCurrentHCIngressRedOctets,
         adGenMEFPolicer15MinCurrentHCCongDiscardsIngressGreenFrames,
         adGenMEFPolicer15MinCurrentHCCongDiscardsIngressGreenOctets,
         adGenMEFPolicer15MinCurrentHCCongDiscardsIngressYellowFrames,
         adGenMEFPolicer15MinCurrentHCCongDiscardsIngressYellowOctets,
	    adGenMEFPolicer15MinIntervalNumber,
        adGenMEFPolicer15MinIntervalIngressGreenFrames,
    	adGenMEFPolicer15MinIntervalIngressYellowFrames,
	    adGenMEFPolicer15MinIntervalIngressRedFrames,
	    adGenMEFPolicer15MinIntervalIngressGreenOctets,
	    adGenMEFPolicer15MinIntervalIngressYellowOctets,
	    adGenMEFPolicer15MinIntervalIngressRedOctets,
	    adGenMEFPolicer15MinIntervalCongDiscardsIngressGreenFrames,
        adGenMEFPolicer15MinIntervalCongDiscardsIngressGreenOctets,
	    adGenMEFPolicer15MinIntervalCongDiscardsIngressYellowFrames,
	    adGenMEFPolicer15MinIntervalCongDiscardsIngressYellowOctets,
        adGenMEFPolicer15MinIntervalHCIngressGreenFrames,
    	adGenMEFPolicer15MinIntervalHCIngressYellowFrames,
	    adGenMEFPolicer15MinIntervalHCIngressRedFrames,
	    adGenMEFPolicer15MinIntervalHCIngressGreenOctets,
	    adGenMEFPolicer15MinIntervalHCIngressYellowOctets,
	    adGenMEFPolicer15MinIntervalHCIngressRedOctets,
	    adGenMEFPolicer15MinIntervalHCCongDiscardsIngressGreenFrames,
        adGenMEFPolicer15MinIntervalHCCongDiscardsIngressGreenOctets,
	    adGenMEFPolicer15MinIntervalHCCongDiscardsIngressYellowFrames,
	    adGenMEFPolicer15MinIntervalHCCongDiscardsIngressYellowOctets,	    
	    adGenMEFPolicer24HrCurrentIngressGreenFrames,
    	adGenMEFPolicer24HrCurrentIngressYellowFrames,
	    adGenMEFPolicer24HrCurrentIngressRedFrames,
	    adGenMEFPolicer24HrCurrentIngressGreenOctets,
	    adGenMEFPolicer24HrCurrentIngressYellowOctets,
	    adGenMEFPolicer24HrCurrentIngressRedOctets,
        adGenMEFPolicer24HrCurrentCongDiscardsIngressGreenFrames,
        adGenMEFPolicer24HrCurrentCongDiscardsIngressGreenOctets,
	    adGenMEFPolicer24HrCurrentCongDiscardsIngressYellowFrames,
	    adGenMEFPolicer24HrCurrentCongDiscardsIngressYellowOctets,
	    adGenMEFPolicer24HrCurrentHCIngressGreenFrames,
    	adGenMEFPolicer24HrCurrentHCIngressYellowFrames,
	    adGenMEFPolicer24HrCurrentHCIngressRedFrames,
	    adGenMEFPolicer24HrCurrentHCIngressGreenOctets,
	    adGenMEFPolicer24HrCurrentHCIngressYellowOctets,
	    adGenMEFPolicer24HrCurrentHCIngressRedOctets,
        adGenMEFPolicer24HrCurrentHCCongDiscardsIngressGreenFrames,
        adGenMEFPolicer24HrCurrentHCCongDiscardsIngressGreenOctets,
	    adGenMEFPolicer24HrCurrentHCCongDiscardsIngressYellowFrames,
	    adGenMEFPolicer24HrCurrentHCCongDiscardsIngressYellowOctets,
	    adGenMEFPolicer24HrIntervalNumber,
        adGenMEFPolicer24HrIntervalIngressGreenFrames,
    	adGenMEFPolicer24HrIntervalIngressYellowFrames,
	    adGenMEFPolicer24HrIntervalIngressRedFrames,
	    adGenMEFPolicer24HrIntervalIngressGreenOctets,
	    adGenMEFPolicer24HrIntervalIngressYellowOctets,
	    adGenMEFPolicer24HrIntervalIngressRedOctets,
	    adGenMEFPolicer24HrIntervalCongDiscardsIngressGreenFrames,
        adGenMEFPolicer24HrIntervalCongDiscardsIngressGreenOctets,
	    adGenMEFPolicer24HrIntervalCongDiscardsIngressYellowFrames,
	    adGenMEFPolicer24HrIntervalCongDiscardsIngressYellowOctets,
           adGenMEFPolicer24HrIntervalHCIngressGreenFrames,
    	adGenMEFPolicer24HrIntervalHCIngressYellowFrames,
	    adGenMEFPolicer24HrIntervalHCIngressRedFrames,
	    adGenMEFPolicer24HrIntervalHCIngressGreenOctets,
	    adGenMEFPolicer24HrIntervalHCIngressYellowOctets,
	    adGenMEFPolicer24HrIntervalHCIngressRedOctets,
	    adGenMEFPolicer24HrIntervalHCCongDiscardsIngressGreenFrames,
        adGenMEFPolicer24HrIntervalHCCongDiscardsIngressGreenOctets,
	    adGenMEFPolicer24HrIntervalHCCongDiscardsIngressYellowFrames,
	    adGenMEFPolicer24HrIntervalHCCongDiscardsIngressYellowOctets

   }
   STATUS current
   DESCRIPTION
     "These objects provide support for the Policer performance statistics."
   ::= { adGenMEFMibGroups 12 }

adGenMEFEthPerfGroup OBJECT-GROUP
   OBJECTS
   {
        adGenMEF10100EthAnomalies15MinCurrentFramesWithInvalidCEVLANID,
        adGenMEF10100EthAnomalies15MinIntervalNumber,
        adGenMEF10100EthAnomalies15MinIntervalFramesWithInvalidCEVLANID,
        adGenMEF10100EthAnomalies24HrCurrentFramesWithInvalidCEVLANID,
        adGenMEF10100EthAnomalies24HrIntervalNumber,
        adGenMEF10100EthAnomalies24HrIntervalFramesWithInvalidCEVLANID
   }
   STATUS current
   DESCRIPTION
     "These objects provide support for additional Ethernet performance statistics."
   ::= { adGenMEFMibGroups 13 }

adGenMEFGigEthPerfGroup OBJECT-GROUP
   OBJECTS
   {
        adGenMEFGigEthAnomalies15MinCurrentFramesWithInvalidCEVLANID,
        adGenMEFGigEthAnomalies15MinIntervalNumber,
        adGenMEFGigEthAnomalies15MinIntervalFramesWithInvalidCEVLANID,
        adGenMEFGigEthAnomalies24HrCurrentFramesWithInvalidCEVLANID,
        adGenMEFGigEthAnomalies24HrIntervalNumber,
        adGenMEFGigEthAnomalies24HrIntervalFramesWithInvalidCEVLANID
   }
   STATUS current
   DESCRIPTION
     "These objects provide support for additional Gigabit Ethernet performance statistics."
   ::= { adGenMEFMibGroups 14 }

adGenMEFEthThreshGroup OBJECT-GROUP
   OBJECTS
   {
        adGenMEF10100EthAnomalies15MinThreshFramesWithInvalidCEVLANID,
        adGenMEF10100EthAnomalies24HrThreshFramesWithInvalidCEVLANID
   }
   STATUS current
   DESCRIPTION
     "These objects provide support for additional Ethernet thresholds."
   ::= { adGenMEFMibGroups 15 }

adGenMEFGigEthThreshGroup OBJECT-GROUP
   OBJECTS
   {
        adGenMEFGigEthAnomalies15MinThreshFramesWithInvalidCEVLANID,
        adGenMEFGigEthAnomalies24HrThreshFramesWithInvalidCEVLANID
   }
   STATUS current
   DESCRIPTION
     "These objects provide support for additional Gigabit Ethernet thresholds."
   ::= { adGenMEFMibGroups 16 }

adGenMEFPolicerThreshGroup OBJECT-GROUP
   OBJECTS
   {
        adGenMEFPolicer15MinThresholdIngressGreenFrames,
        adGenMEFPolicer15MinThresholdIngressYellowFrames,
	    adGenMEFPolicer15MinThresholdIngressRedFrames,
	    adGenMEFPolicer15MinThresholdCongDiscardsIngressGreenFrames,
        adGenMEFPolicer15MinThresholdCongDiscardsIngressYellowFrames,
        adGenMEFPolicer15MinThresholdHCIngressGreenFrames,
        adGenMEFPolicer15MinThresholdHCIngressYellowFrames,
	    adGenMEFPolicer15MinThresholdHCIngressRedFrames,
	    adGenMEFPolicer15MinThresholdHCCongDiscardsIngressGreenFrames,
        adGenMEFPolicer15MinThresholdHCCongDiscardsIngressYellowFrames,
	    adGenMEFPolicer24HrThresholdIngressGreenFrames,
    	adGenMEFPolicer24HrThresholdIngressYellowFrames,
	    adGenMEFPolicer24HrThresholdIngressRedFrames,
	    adGenMEFPolicer24HrThresholdCongDiscardsIngressGreenFrames,
        adGenMEFPolicer24HrThresholdCongDiscardsIngressYellowFrames,        
	    adGenMEFPolicer24HrThresholdHCIngressGreenFrames,
    	adGenMEFPolicer24HrThresholdHCIngressYellowFrames,
	    adGenMEFPolicer24HrThresholdHCIngressRedFrames,
	    adGenMEFPolicer24HrThresholdHCCongDiscardsIngressGreenFrames,
        adGenMEFPolicer24HrThresholdHCCongDiscardsIngressYellowFrames
   }
   STATUS current
   DESCRIPTION
     "These objects provide support for the Policer thresholds."
   ::= { adGenMEFMibGroups 17 }

adGenMEFEventGroup NOTIFICATION-GROUP
   NOTIFICATIONS
   {
        adGenMEFSet10100EthAnomalies15MinFramesWithInvalidCEVLANID,
        adGenMEFSet10100EthAnomalies24HrFramesWithInvalidCEVLANID,
        adGenMEFSetGigEthAnomalies15MinFramesWithInvalidCEVLANID,
        adGenMEFSetGigEthAnomalies24HrFramesWithInvalidCEVLANID,
        adGenMEFSetPolicer15MinIngressGreenFrames,
        adGenMEFSetPolicer15MinIngressYellowFrames,
        adGenMEFSetPolicer15MinIngressRedFrames,
        adGenMEFSetPolicer15MinCongDiscardsIngressGreenFrames,
        adGenMEFSetPolicer15MinCongDiscardsIngressYellowFrames,
        adGenMEFSetPolicer24HrIngressGreenFrames,
        adGenMEFSetPolicer24HrIngressYellowFrames,
        adGenMEFSetPolicer24HrIngressRedFrames,
        adGenMEFSetPolicer24HrCongDiscardsIngressGreenFrames,
        adGenMEFSetPolicer24HrCongDiscardsIngressYellowFrames
   }
   STATUS current
   DESCRIPTION
     "These objects provide support for events."
   ::= { adGenMEFMibGroups 18 }

adGenMEFDeprecatedGroup OBJECT-GROUP
   OBJECTS
   {
        adGenMEFProfileCIR,
        adGenMEFProfileEIR,
	adGenMEFMapDSCP
   }
   STATUS deprecated
   DESCRIPTION
     "These objects have been deprecated."
   ::= { adGenMEFMibGroups 19 }

adGenMEFObsoletedGroup OBJECT-GROUP
   OBJECTS
   {
        adGenMEFEVCMapsByAlias
   }
   STATUS obsolete
   DESCRIPTION
     "These objects have been obsoleted."
   ::= { adGenMEFMibGroups 20 }


END

ADTRAN-GENMEVC-MIB

-- TITLE:     The ADTRAN MEVC MIB
-- PRODUCT:   Metro Ethernet Products
-- VERSION:   1.0
-- DATE:      07/21/10
-- AUTHOR:    Anil Shah
-- STATUS:    PRELIMINARY

-- This MIB defines the object identifiers (OIDs) for the
-- ADTRAN GENMEVC MIB objects

-- HISTORY:
-- 2010/06/17 ams   STATUS: PRELIMINARY.
-- 2010/07/21 ams   Added a New table to report MEVC creation error.  Added MEVC name as
--                  a second index to report MEN Port creation error on MEVC.  Added a 
--                  new table to display number of MEVCs on SLOT.
-- 2011/02/16 ams   Added VLAN in use table.
--
-- *** DO NOT USE THIS FIELD. ***
-- ******************************************************************************************
DEFINITIONS ::= BEGIN

IMPORTS

   adGenMEVC,
   adGenMEVCID          FROM ADTRAN-SHARED-CND-SYSTEM-MIB

   OBJECT-TYPE,
   MODULE-IDENTITY,
   Integer32           FROM SNMPv2-SMI

   DisplayString,
   RowStatus,
   TimeStamp           FROM SNMPv2-TC

   ifIndex,
   InterfaceIndex      FROM IF-MIB

   adGenSlotInfoIndex  FROM ADTRAN-GENSLOT-MIB

   ;

adGenMEVCMIB MODULE-IDENTITY
   LAST-UPDATED "201501120000Z"
   ORGANIZATION "Adtran, Inc."
   CONTACT-INFO
     "CND Tech Support
         Postal: ADTRAN, Inc.
                 901 Explorer Blvd.
                 Huntsville, AL  35806
                 Tel: +1 800 726-8663
                 Fax: +1 256 963 6217
                 E-mail: support@adtran.com"
   DESCRIPTION
      "This MIB defines the objects for the MEVC MIB."

   REVISION "201501120000Z"
   DESCRIPTION "Added adGenMEVCIGMPImmediateLeave, adGenMEVCIGMPTimeoutInterval and adGenMEVCIGMPMode in the adGenMEVCTable
                Added a New adGenMEVCIGMPTable table."
      
   REVISION "201307030000Z"
   DESCRIPTION "Added a adGenMEVCEnhMenPortTable to replace adGenMEVCMenPortTable.
                This new table accepts interfaces from multiple slots to be added to MEVC."

   REVISION "201108260000Z"
   DESCRIPTION  "Added Management Entry to MEVC Table."
   REVISION "201102160000Z"
   DESCRIPTION "Created"

::= { adGenMEVCID 1 }

adGenMEVCEvents                      OBJECT IDENTIFIER ::= {adGenMEVC 0}
adGenMEVCProvisioning                OBJECT IDENTIFIER ::= {adGenMEVC 1}

--==================================================================================================================

   adGenMEVCTable OBJECT-TYPE
      SYNTAX  SEQUENCE OF AdGenMEVCEntry
      MAX-ACCESS  not-accessible
      STATUS  current
      DESCRIPTION
         "The MEVC provisioning table."
      ::= { adGenMEVCProvisioning 1 }

   adGenMEVCEntry OBJECT-TYPE
      SYNTAX  AdGenMEVCEntry
      MAX-ACCESS  not-accessible
      STATUS  current
      DESCRIPTION
         "An entry in the MEVC provisioning table.  MEVC entries
          are uniquely identified on Slot as well as by the MEvc 
          Name."
      INDEX  { adGenSlotInfoIndex, IMPLIED adGenMEVCName }
      ::= { adGenMEVCTable 1 }

   AdGenMEVCEntry ::=
      SEQUENCE {
         adGenMEVCName
            DisplayString,
         adGenMEVCRowStatus
            RowStatus,
         adGenMEVCOperStatus
            INTEGER,
         adGenMEVCStatus
            DisplayString,
         adGenMEVCSTagVID
            Integer32,
         adGenMEVCPreserveCEVlanId
        INTEGER,
         adGenMEVCMacSwitching
            INTEGER,
         adGenMEVCNumberOfInterfaces
            Integer32,
         adGenMEVCLastError
            DisplayString,
         adGenMevcManagement
            INTEGER,
         adGenMEVCIGMPImmediateLeave
            INTEGER,
         adGenMEVCIGMPTimeOutInterval
            INTEGER,
         adGenMEVCIGMPMode
            INTEGER
      }

      adGenMEVCName OBJECT-TYPE
         SYNTAX  DisplayString (SIZE (1..50))
         MAX-ACCESS  not-accessible
         STATUS  current
         DESCRIPTION
            "A user configurable name for the MEVC.  Upon creation of the MEVC,
             the associated name will default to a unique value."
         ::= { adGenMEVCEntry 1}

      adGenMEVCRowStatus OBJECT-TYPE
         SYNTAX  RowStatus
         MAX-ACCESS  read-create
         STATUS  current
         DESCRIPTION
           "This object is used to create a new row or modify or delete an
            existing row in the MEVC table."
         ::= { adGenMEVCEntry 2}

      adGenMEVCOperStatus OBJECT-TYPE
         SYNTAX INTEGER  {
            up(1),
            down(2)
         }
         MAX-ACCESS read-only
         STATUS current
         DESCRIPTION
            "Returns the current operational status of the MEVC."
         ::= { adGenMEVCEntry 3}

      adGenMEVCStatus OBJECT-TYPE
         SYNTAX  DisplayString
         MAX-ACCESS  read-only
         STATUS  current
         DESCRIPTION
            "This variable provides the MEVC status.  If there is no error, the MEVC
             status will be 'running'.  If there is an error and the MEVC cannot be
             applied, then adGenMEVCStatus will provide more details about the error."
         ::= { adGenMEVCEntry 4}

      adGenMEVCSTagVID OBJECT-TYPE
         SYNTAX  Integer32
         MAX-ACCESS  read-create
         STATUS  current
         DESCRIPTION
            "This variable specifies the outermost VLAN S-Tag VID for
             frames on this MEVC. No two entries in the MEVC Table may
             have the same S-Tag VID.
             S-Tag values 0 and 4095 are reserved and should not be used.
             Set the S-Tag to 4096 for untagged traffic and to 4097 for
             priority tagged traffic."
         ::= { adGenMEVCEntry 5}

      adGenMEVCPreserveCEVlanId OBJECT-TYPE
         SYNTAX  INTEGER  {
            disabled(1),
            enabled(2)
     }
         MAX-ACCESS  read-create
         STATUS  current
         DESCRIPTION
            "This option provisions whether to preserve the CE VLAN tag
             received at the UNI port. Select enabled to push the MEVC tag
             onto the CE tag for frames destined for this MEVC. Select
             disabled to remove the CE VLAN tag and to add the MEVC tag
             for the frames destined for this MEVC."
         ::= { adGenMEVCEntry 6}

      adGenMEVCMacSwitching OBJECT-TYPE
         SYNTAX INTEGER  {
            disabled(1),
            enabled(2)
         }
         MAX-ACCESS read-create
         STATUS current
         DESCRIPTION
            "This option provisions whether MAC Switching should be
             performed on this MEVC."
         ::= { adGenMEVCEntry 7}

      adGenMEVCNumberOfInterfaces OBJECT-TYPE
          SYNTAX Integer32
          MAX-ACCESS read-only
          STATUS current
          DESCRIPTION
             "Returns the number of interfaces connected to this MEVC."
          ::= {adGenMEVCEntry 8}

      adGenMEVCLastError OBJECT-TYPE
          SYNTAX         DisplayString
          MAX-ACCESS     read-only
          STATUS         current
          DESCRIPTION
             "This string describes the last error experienced
              for this particular entry in the table."
          ::= { adGenMEVCEntry 9 }

      adGenMevcManagement OBJECT-TYPE
         SYNTAX INTEGER  {
            disable(1),
            local(2),
            system(3)
         }
         MAX-ACCESS read-create
         STATUS current
         DESCRIPTION
            "This option provisions management vlan traffic
             switching setting. 
             Disable  - Only non-management Vlan traffic switching.
             Local    - Management Vlan traffic switched locally.
             System   - Management Vlan traffic switched through the system."
         ::= { adGenMEVCEntry 10 }
         
      adGenMEVCIGMPImmediateLeave OBJECT-TYPE
         SYNTAX  INTEGER  {
            disabled(1),
            enabled(2)
         }
         MAX-ACCESS  read-create
         STATUS  current
         DESCRIPTION
            "Enable/Disable immediate leave. "
         DEFVAL { disabled }
         ::= { adGenMEVCEntry 11 }
      
       adGenMEVCIGMPTimeOutInterval OBJECT-TYPE
         SYNTAX  INTEGER (1..65535)
         MAX-ACCESS  read-create
         STATUS  current
         DESCRIPTION
            "The IGMP group membership interval in units of seconds.
             If no IGMP join is received for a video group before this 
             interval expires, then the video group is removed for
             the host interface."
         DEFVAL { 260 }
         ::= { adGenMEVCEntry 12 }
         
       adGenMEVCIGMPMode OBJECT-TYPE
         SYNTAX   INTEGER
                  {
                      transparent(1),
                      snooping(2)
                  }
         MAX-ACCESS   read-create
         STATUS       current
         DESCRIPTION
            "The IGMP Mode associated with this MEVC ."
         DEFVAL { transparent }
         ::= { adGenMEVCEntry 13}
         
--==================================================================================================================

   adGenMEVCLookupTable OBJECT-TYPE
      SYNTAX  SEQUENCE OF AdGenMEVCLookupEntry
      MAX-ACCESS  not-accessible
      STATUS  current
      DESCRIPTION
         "The MEVC lookup table."
      ::= { adGenMEVCProvisioning 2 }

   adGenMEVCLookupEntry OBJECT-TYPE
      SYNTAX  AdGenMEVCLookupEntry
      MAX-ACCESS  not-accessible
      STATUS  current
      DESCRIPTION
         "An entry in the MEVC lookup table.  This table has one
          entry for each row in the adGenMEVCTable.  This table is
          used to find the MEVC name for a given SLOT and S-Tag 
          VLAN Id."
      INDEX  { adGenSlotInfoIndex, adGenMEVCLookupSTag }
      ::= { adGenMEVCLookupTable 1 }

   AdGenMEVCLookupEntry ::=
      SEQUENCE {
         adGenMEVCLookupSTag
            Integer32,
         adGenMEVCLookupName
            DisplayString
      }

      adGenMEVCLookupSTag OBJECT-TYPE
         SYNTAX  Integer32
         MAX-ACCESS  read-only
         STATUS  current
         DESCRIPTION
            "The S-Tag VLAN Id.
             S-Tag values 0, 1, and 4095 are reserved and should not be used.
             Set the S-Tag to 4096 for untagged traffic and to 4097 for
             priority tagged traffic."
         ::= { adGenMEVCLookupEntry 1}

      adGenMEVCLookupName OBJECT-TYPE
         SYNTAX  DisplayString
         MAX-ACCESS  read-only
         STATUS  current
         DESCRIPTION
            "Returns the MEVC name associated with the given S-Tag VID."
         ::= { adGenMEVCLookupEntry 2}

--==================================================================================================================
   adGenMEVCErrorTable OBJECT-TYPE
      SYNTAX  SEQUENCE OF AdGenMEVCErrorEntry
      MAX-ACCESS  not-accessible
      STATUS  current
      DESCRIPTION
         "The MEVC Creation Error table."
      ::= { adGenMEVCProvisioning 3 }

   adGenMEVCErrorEntry OBJECT-TYPE
      SYNTAX  AdGenMEVCErrorEntry
      MAX-ACCESS  not-accessible
      STATUS  current
      DESCRIPTION
         "An entry in the MEVC Creation Error table.
          The index, adGenSlotInfoIndex, identifies the SLOT."
      INDEX  { adGenSlotInfoIndex}
      ::= { adGenMEVCErrorTable 1 }

   AdGenMEVCErrorEntry ::=
      SEQUENCE {
         adGenMEVCError
            DisplayString
      }

      adGenMEVCError OBJECT-TYPE
         SYNTAX  DisplayString
         MAX-ACCESS  read-only
         STATUS  current
         DESCRIPTION
         "Returns information about the last error for the MEVC 
         create on SLOT. If row creation fails, this string 
         will provide details about why the row could not be created."
         ::= { adGenMEVCErrorEntry 1}

--==================================================================================================================

   adGenMEVCMenPortTable OBJECT-TYPE
      SYNTAX  SEQUENCE OF AdGenMEVCMenPortEntry
      MAX-ACCESS  not-accessible
      STATUS  deprecated
      DESCRIPTION
         "The MEVC MEN Port table.
         
          NOTE:  This table has been deprecated and replaced by
                 the adGenMEVCEnhMenPortTable.  The OIDs within
                 this table always assume slot and port identified
                 via ifIndex."
      ::= { adGenMEVCProvisioning 4 }

   adGenMEVCMenPortEntry OBJECT-TYPE
      SYNTAX  AdGenMEVCMenPortEntry
      MAX-ACCESS  not-accessible
      STATUS  deprecated
      DESCRIPTION
         "An entry in the MEVC MEN Port table.  This table can be
          used to add or remove MEN Port connections for an MEVC.
          The first index, ifIndex, identifies the MEN port.
          The second index, adGenProvisionedMEVCName, identifies the MEVC.
          
          NOTE:  This table has been deprecated and replaced by
                 the adGenMEVCEnhMenPortTable.  The OIDs within
                 this table always assume slot and port identified
                 via ifIndex."
      INDEX  { ifIndex, adGenProvisionedMEVCName   }
      ::= { adGenMEVCMenPortTable 1 }

   AdGenMEVCMenPortEntry ::=
      SEQUENCE {
         adGenProvisionedMEVCName
            OCTET STRING,
         adGenMEVCMenPortRowStatus
            RowStatus,
         adGenMEVCMenPortConnectionType
            INTEGER
      }

      adGenProvisionedMEVCName OBJECT-TYPE
         SYNTAX  OCTET STRING (SIZE (1..50))
         MAX-ACCESS  not-accessible
         STATUS  deprecated
         DESCRIPTION
            "A user configurable name for the MEVC.  Upon creation of the MEVC,
             the associated name will default to a unique value.
          
             NOTE:  This table has been deprecated and replaced by
                    the adGenMEVCEnhMenPortTable.  The OIDs within
                    this table always assume slot and port identified
                    via ifIndex."
         ::= { adGenMEVCMenPortEntry 1}

      adGenMEVCMenPortRowStatus OBJECT-TYPE
         SYNTAX  RowStatus
         MAX-ACCESS  read-create
         STATUS  deprecated
         DESCRIPTION
           "This object is used to create or destroy a MEN Port
            connection for an MEVC.
          
            NOTE:  This table has been deprecated and replaced by
                   the adGenMEVCEnhMenPortTable.  The OIDs within
                   this table always assume slot and port identified
                   via ifIndex."
         ::= { adGenMEVCMenPortEntry 2}

      adGenMEVCMenPortConnectionType OBJECT-TYPE
         SYNTAX INTEGER  {
            root(1),
            leaf(2)
     }
         MAX-ACCESS  read-create
         STATUS  deprecated
         DESCRIPTION
            "This option provisions whether the MEN port is a root
             or leaf of the given MEVC.
                       
             NOTE:  This table has been deprecated and replaced by
                    the adGenMEVCEnhMenPortTable.  The OIDs within
                    this table always assume slot and port identified
                    via ifIndex."          
         DEFVAL  { root }
         ::= { adGenMEVCMenPortEntry 3}

--==================================================================================================================

   adGenMEVCMenPortConnectionErrorTable OBJECT-TYPE
      SYNTAX  SEQUENCE OF AdGenMEVCMenPortConnectionErrorEntry
      MAX-ACCESS  not-accessible
      STATUS  current
      DESCRIPTION
         "The MEVC MEN Port Connection Error table."
      ::= { adGenMEVCProvisioning 5 }

   adGenMEVCMenPortConnectionErrorEntry OBJECT-TYPE
      SYNTAX  AdGenMEVCMenPortConnectionErrorEntry
      MAX-ACCESS  not-accessible
      STATUS  current
      DESCRIPTION
         "An entry in the MEVC MEN Port Connection Error table.
          The first index, adGenSlotInfoIndex, identifies the SLOT.
          The second index, adGenProvisionedMenPortMEVCName, identifies the MEVC"
      INDEX  { adGenSlotInfoIndex, adGenProvisionedMenPortMEVCName}
      ::= { adGenMEVCMenPortConnectionErrorTable 1 }

   AdGenMEVCMenPortConnectionErrorEntry ::=
      SEQUENCE {
         adGenProvisionedMenPortMEVCName
            OCTET STRING,
         adGenMEVCMenPortConnectionError
            DisplayString
      }

      adGenProvisionedMenPortMEVCName OBJECT-TYPE
         SYNTAX  OCTET STRING (SIZE (1..50))
         MAX-ACCESS  not-accessible
         STATUS  current
         DESCRIPTION
            "A user configured name for the MEVC."
         ::= { adGenMEVCMenPortConnectionErrorEntry 1}

      adGenMEVCMenPortConnectionError OBJECT-TYPE
         SYNTAX  DisplayString
         MAX-ACCESS  read-only
         STATUS  current
         DESCRIPTION
         "Returns information about the last error for the MEVC 
         MEN Port table on SLOT. If row creation fails, this string 
         will provide details about why the row could not be created."
         ::= { adGenMEVCMenPortConnectionErrorEntry 2}

--==================================================================================================================

   adGenMEVCMenPortProvisioningTable OBJECT-TYPE
      SYNTAX  SEQUENCE OF AdGenMEVCMenPortProvisioningEntry
      MAX-ACCESS  not-accessible
      STATUS  current
      DESCRIPTION
         "The MEVC MEN Port Provisioning table."
      ::= { adGenMEVCProvisioning 6 }

   adGenMEVCMenPortProvisioningEntry OBJECT-TYPE
      SYNTAX  AdGenMEVCMenPortProvisioningEntry
      MAX-ACCESS  not-accessible
      STATUS  current
      DESCRIPTION
         "An entry in the MEVC MEN Port Provisioning table.
         This table can be used to provision a MEN port.  The
         index for this table is the ifIndex of the MEN port."
      INDEX  { ifIndex }
      ::= { adGenMEVCMenPortProvisioningTable 1 }

   AdGenMEVCMenPortProvisioningEntry ::=
      SEQUENCE {
         adGenMEVCMenPortStagDei
            INTEGER
      }

      adGenMEVCMenPortStagDei OBJECT-TYPE
         SYNTAX INTEGER  {
            disabled (1),
            enabled (2)
         }
         MAX-ACCESS read-write
         STATUS current
         DESCRIPTION
            "This option provisions the marking of the DEI bit.
             When enabled, the bit functions as the Drop Eligible Indicator.
         When disabled, the bit functions as the Canonical Format Indicator."
         ::= { adGenMEVCMenPortProvisioningEntry 1 }

--==================================================================================================================

   adGenMEVCNumberOfMEVCsTable OBJECT-TYPE
      SYNTAX  SEQUENCE OF AdGenMEVCNumberOfMEVCsEntry
      MAX-ACCESS  not-accessible
      STATUS  current
      DESCRIPTION
         "The MEVC table to display number Of MEVCs associated with the Slot."
      ::= { adGenMEVCProvisioning 7 }

   adGenMEVCNumberOfMEVCsEntry OBJECT-TYPE
      SYNTAX  AdGenMEVCNumberOfMEVCsEntry
      MAX-ACCESS  not-accessible
      STATUS  current
      DESCRIPTION
         "An entry in the MEVC Number of MEVCs table.
          The index, adGenSlotInfoIndex, identifies the SLOT."
      INDEX  { adGenSlotInfoIndex }
      ::= { adGenMEVCNumberOfMEVCsTable 1 }

   AdGenMEVCNumberOfMEVCsEntry ::=
      SEQUENCE {
        adGenMEVCNumberOfMEVCs
            Integer32
      }

      adGenMEVCNumberOfMEVCs OBJECT-TYPE
         SYNTAX  Integer32
         MAX-ACCESS  read-only
         STATUS  current
         DESCRIPTION
            "This variable is used to display number of MEVCs associated 
             with the Slot."
         ::= { adGenMEVCNumberOfMEVCsEntry 1}

--==================================================================================================================

   adGenVLANInUseLookupTable OBJECT-TYPE
      SYNTAX  SEQUENCE OF AdGenVLANInUseLookupEntry
      MAX-ACCESS  not-accessible
      STATUS  current
      DESCRIPTION
         "The VLAN In Use lookup table."
      ::= { adGenMEVCProvisioning 8 }

   adGenVLANInUseLookupEntry OBJECT-TYPE
      SYNTAX  AdGenVLANInUseLookupEntry
      MAX-ACCESS  not-accessible
      STATUS  current
      DESCRIPTION
         "An entry in the VLAN In Use lookup table.  This table is use to 
         determine which VLANs are in use on specific SLOT."
      INDEX  { adGenSlotInfoIndex }
      ::= { adGenVLANInUseLookupTable 1 }

   AdGenVLANInUseLookupEntry ::=
      SEQUENCE {
         adGenVLANInUseLookupData
            OCTET STRING
      }

      adGenVLANInUseLookupData OBJECT-TYPE
         SYNTAX  OCTET STRING (SIZE(512))
         MAX-ACCESS  read-only
         STATUS  current
         DESCRIPTION
            "A binary string is returned, where each VLAN is represented 
            as a - bit, where 1 is in use, 0 is not in use. This applies 
            for all 4096 VLANs. Following is how VLANs are represented in
            Octet string:
            VLAN 0 - Octet byte 1, bit 7(MSB) 
            VLAN 1 - Octet byte 1, bit 6
            VLAN 2 - Octet byte 1, bit 5
            ....
            VLAN 7 - Octet byte 1, bit 0(LSB)
            VLAN 8 - Octet byte 2, bit 7(MSB)
            ....
            VLAN 4095 - Octet byte 512, bit 0(LSB)"
         ::= { adGenVLANInUseLookupEntry 1 }

--==================================================================================================================

   adGenMEVCEnhMenPortTable OBJECT-TYPE
      SYNTAX  SEQUENCE OF AdGenMEVCEnhMenPortEntry
      MAX-ACCESS  not-accessible
      STATUS  current
      DESCRIPTION
         "The MEVC MEN Port table."
      ::= { adGenMEVCProvisioning 9 }

   adGenMEVCEnhMenPortEntry OBJECT-TYPE
      SYNTAX  AdGenMEVCEnhMenPortEntry
      MAX-ACCESS  not-accessible
      STATUS  current
      DESCRIPTION
         "An entry in the MEVC MEN Port table.  This table can be
          used to add or remove MEN Port connections for an MEVC.
          The first index, identifies slot number associated with MEVC name.
          The second index, adGenMEVCMenPortIfIndex, identifies the MEN port.
          The third index, adGenProvMEVCName, identifies the MEVC"
      INDEX  { adGenSlotInfoIndex, adGenMEVCMenPortIfIndex, adGenProvMEVCName   }
      ::= { adGenMEVCEnhMenPortTable 1 }

   AdGenMEVCEnhMenPortEntry ::=
      SEQUENCE {
         adGenMEVCMenPortIfIndex
            InterfaceIndex,
         adGenProvMEVCName
            OCTET STRING,
         adGenMEVCEnhMenPortRowStatus
            RowStatus,
         adGenMEVCEnhMenPortConnectionType
            INTEGER
      }

      adGenMEVCMenPortIfIndex OBJECT-TYPE
         SYNTAX  InterfaceIndex
         MAX-ACCESS  not-accessible
         STATUS  current
         DESCRIPTION
           "This interface index of the MEN port to be connected to this EVC."
         ::= { adGenMEVCEnhMenPortEntry 1}

      adGenProvMEVCName OBJECT-TYPE
         SYNTAX  OCTET STRING (SIZE (1..50))
         MAX-ACCESS  not-accessible
         STATUS  current
         DESCRIPTION
            "A user configurable name for the MEVC.  Upon creation of the MEVC,
             the associated name will default to a unique value."
         ::= { adGenMEVCEnhMenPortEntry 2}

      adGenMEVCEnhMenPortRowStatus OBJECT-TYPE
         SYNTAX  RowStatus
         MAX-ACCESS  read-create
         STATUS  current
         DESCRIPTION
           "This object is used to create or destroy a MEN Port
            connection for an MEVC."
         ::= { adGenMEVCEnhMenPortEntry 3}

      adGenMEVCEnhMenPortConnectionType OBJECT-TYPE
         SYNTAX INTEGER  {
            root(1),
            leaf(2)
     }
         MAX-ACCESS  read-create
         STATUS  current
         DESCRIPTION
            "This option provisions whether the MEN port is a root
             or leaf of the given MEVC."
         DEFVAL  { root }
         ::= { adGenMEVCEnhMenPortEntry 4}
         
--==================================================================================================================
   adGenMEVCIGMPTable OBJECT-TYPE
      SYNTAX  SEQUENCE OF AdGenMEVCIGMPEntry
      MAX-ACCESS  not-accessible
      STATUS  current
      DESCRIPTION
        " The MEVC IGMP table."
      ::= { adGenMEVCProvisioning 10}

   adGenMEVCIGMPEntry OBJECT-TYPE
      SYNTAX  AdGenMEVCIGMPEntry
      MAX-ACCESS  not-accessible
      STATUS  current
      DESCRIPTION
         "An entry in the MEVC IGMP table. This table can be
          used to enable or disable the interface mode to either 
          of the igmp host or router . The first index, identifies 
          slot number associated with the mevc name.  The second index, 
          adGenMEVCIGMPInterfaceIndex, identifies the port. Third index,
          adGenMEVCName identifies the mevc name."
      INDEX  { adGenSlotInfoIndex, adGenMEVCIGMPInterfaceIndex, adGenMEVCIGMPEVCName }
      ::= { adGenMEVCIGMPTable 1 }


   AdGenMEVCIGMPEntry ::=
      SEQUENCE {
                  adGenMEVCIGMPInterfaceIndex   InterfaceIndex,
                  adGenMEVCIGMPEVCName          OCTET STRING,
                  adGenMEVCIGMPInterfaceMode    INTEGER,
                  adGenMEVCIGMPRowStatus        RowStatus,
                  adGenMEVCIGMPLastError        DisplayString
      }

      adGenMEVCIGMPInterfaceIndex OBJECT-TYPE
         SYNTAX  InterfaceIndex
         MAX-ACCESS  not-accessible
         STATUS  current
         DESCRIPTION
           "This interface index of the port on which IGMP mode is configured." 
         ::= { adGenMEVCIGMPEntry 1}

      adGenMEVCIGMPEVCName OBJECT-TYPE
         SYNTAX  OCTET STRING (SIZE (1..50))
         MAX-ACCESS  not-accessible
         STATUS  current
         DESCRIPTION
            "A user configurable name for the MEVC.  Upon creation of the MEVC,
             the associated name will default to a unique value."
         ::= { adGenMEVCIGMPEntry 2}
         
      adGenMEVCIGMPInterfaceMode OBJECT-TYPE
         SYNTAX INTEGER  {
            host(1),
            router(2)
         }  
         MAX-ACCESS read-create
         STATUS current
         DESCRIPTION
            "host -   RFC2236 host facing interface. Enable the interface act as IGMP host.
             router - RFC2236 Router facing interface. Enable the interface act as IGMP router."
         DEFVAL { host }
         ::= { adGenMEVCIGMPEntry 3}
              
      adGenMEVCIGMPRowStatus OBJECT-TYPE
         SYNTAX  RowStatus
         MAX-ACCESS  read-create
         STATUS  current
         DESCRIPTION
           "This object is used to create or modify or destroy a IGMP mode  
             on interface for an MEVC."
         ::= { adGenMEVCIGMPEntry 4}

      adGenMEVCIGMPLastError OBJECT-TYPE
          SYNTAX         DisplayString
          MAX-ACCESS     read-only
          STATUS         current
          DESCRIPTION
             "Returns information about the last error for the MEVC 
              IGMP table on slot. If row creation fails, this string 
              will provide details about why the row could not be created."
          ::= { adGenMEVCIGMPEntry 5 }

END

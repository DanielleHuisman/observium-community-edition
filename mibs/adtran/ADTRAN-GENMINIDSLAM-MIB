ADTRAN-GENMINIDSLAM-MIB

  DEFINITIONS ::= BEGIN

  -- TITLE:     Adtran Generic Mini-DSLAM MIB
  -- DATE:      Oct 23, 2007
  --
  -- REVISION HISTORY: Date           Comments
  --                   02/02/2005     gdo - Created.
  --                   02/02/2005     gdo - Modify module Identity clause.
  --                   08/04/2006     gdo - Add adGenBondingID OID.
  --                   10/23/2007     gdo - Rename adGenMiniDslam3gID to adTAMiniDslam3gID.

  -- This MIB defines the generic MIB for the Mini-DSLAM products.

  IMPORTS
      MODULE-IDENTITY
                        FROM SNMPv2-SMI
      adIdentityShared,
      adShared          FROM ADTRAN-MIB;

--*********************************************************************************************************
  adGENMINIDSLAMID MODULE-IDENTITY
         LAST-UPDATED "200710230800Z"
         ORGANIZATION "ADTRAN, Inc."
         CONTACT-INFO
           "CND Tech Support
            Postal: ADTRAN, Inc.
                    901 Explorer Blvd.
                    Huntsville, AL  35806
                    Tel: +1 800 726-8663
                    Fax: +1 256 963 6217
                    E-mail: support@adtran.com"
         DESCRIPTION
              "This MIB module describes the Adtran
               Generic Mini-DSLAM SMIv2 objects."
         ::= { adIdentityShared 61 }

--********************************************************************************************************
    -- OBJECT IDENTIFIERS

  adGenMiniDslam             OBJECT IDENTIFIER ::= { adShared 61 }

  -- Objects built specifically with 2nd generation Total Access Mini-DSLAMs in mind.
  adTAMiniDslam2g            OBJECT IDENTIFIER ::= { adGenMiniDslam 1 }
  adTAMiniDslam2gmg          OBJECT IDENTIFIER ::= { adTAMiniDslam2g 1 }

  -- Module Identity definitions
  -- adTAMINIDSLAMSYSTEMID   defined as { adGENMINIDSLAMID 2 } in ADTRAN-TAMINIDSLAMSYSTEM-MIB
  -- adTAMINIDSLAMSHELFID    defined as { adGENMINIDSLAMID 3 } in ADTRAN-TAMINIDSLAMSHELF-MIB

  -- From henceforth, all further child objects of adGENMINIDSLAMID MUST be defined below. - gdo
  adGenBondingID	 	     OBJECT IDENTIFIER ::= { adGENMINIDSLAMID 4 }
  adTAMiniDslam3gID         OBJECT IDENTIFIER ::= { adGENMINIDSLAMID 5 }
  END

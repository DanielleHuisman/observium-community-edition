ADTRAN-GENPOLICER-MIB

-- TITLE:     The ADTRAN POLICER MIB
-- PRODUCT:   Metro Ethernet Products
-- VERSION:   1.0
-- DATE:      09/16/10
-- AUTHOR:    Bhushan Parikh
-- STATUS:    PRELIMINARY

-- This MIB defines the object identifiers (OIDs) for the
-- ADTRAN GENPOLICER MIB objects

-- HISTORY:
-- 2010/09/16 bcp   STATUS: PRELIMINARY.
-- 2010/11/01 ams   STATUS: PRELIMINARY.
-- ******************************************************************************************
DEFINITIONS ::= BEGIN

IMPORTS

   adGenPolicer,
   adGenPolicerID           FROM ADTRAN-SHARED-CND-SYSTEM-MIB

   NOTIFICATION-TYPE,
   OBJECT-TYPE,
   MODULE-IDENTITY,
   Integer32                FROM SNMPv2-SMI

   DisplayString,
   RowStatus,
   TruthValue               FROM SNMPv2-TC

   InterfaceIndex,
   InterfaceIndexOrZero     FROM IF-MIB

   adGenSlotInfoIndex       FROM ADTRAN-GENSLOT-MIB

   sysName                  FROM SNMPv2-MIB

   adTrapInformSeqNum       FROM ADTRAN-GENTRAPINFORM-MIB

   ;

adGenPolicerMIB MODULE-IDENTITY
   LAST-UPDATED "201201300000Z"
   ORGANIZATION "Adtran, Inc."
   CONTACT-INFO
     "CND Tech Support
         Postal: ADTRAN, Inc.
                 901 Explorer Blvd.
                 Huntsville, AL  35806
                 Tel: +1 800 726-8663
                 Fax: +1 256 963 6217
                 E-mail: support@adtran.com"
   DESCRIPTION
      "This MIB defines the objects for the Policer MIB."

   REVISION "201201300000Z"
   DESCRIPTION "Added Threshold Alarms"

   REVISION "201009160000Z"
   DESCRIPTION "Created"
::= { adGenPolicerID 1 }

adGenPolicerEvents                      OBJECT IDENTIFIER ::= {adGenPolicer 0}
adGenPolicerProvisioning                OBJECT IDENTIFIER ::= {adGenPolicer 1}
adGenPolicerAlarm                       OBJECT IDENTIFIER ::= {adGenPolicer 100}
adGenPolicerAlarmEvents                 OBJECT IDENTIFIER ::= {adGenPolicerAlarm 0}

--==================================================================================================================

   adGenPolicerTable OBJECT-TYPE
      SYNTAX  SEQUENCE OF AdGenPolicerEntry
      MAX-ACCESS  not-accessible
      STATUS  current
      DESCRIPTION
         "The Policer provisioning table."
      ::= { adGenPolicerProvisioning 1 }

   adGenPolicerEntry OBJECT-TYPE
      SYNTAX  AdGenPolicerEntry
      MAX-ACCESS  not-accessible
      STATUS  current
      DESCRIPTION
         "An entry in the Policer provisioning table.  Policer entries
          are uniquely identified by Slot as well as by the Policer Name."
      INDEX  { adGenSlotInfoIndex, IMPLIED adGenPolicerName }
      ::= { adGenPolicerTable 1 }

   AdGenPolicerEntry ::=
      SEQUENCE {
         adGenPolicerName
            DisplayString,
         adGenPolicerRowStatus
            RowStatus,
         adGenPolicerStatus
            DisplayString,
         adGenPolicerOperStatus
            INTEGER,
         adGenPolicerCIR
            Integer32,
         adGenPolicerCBS
            Integer32,
         adGenPolicerEIR
            Integer32,
         adGenPolicerEIRNoLimit
            TruthValue,
         adGenPolicerEBS
            Integer32,
         adGenPolicerMode
            INTEGER,
         adGenPolicerUNIPort
            InterfaceIndexOrZero,
         adGenPolicerEVCName
            DisplayString,
         adGenPolicerMEVCName
            DisplayString,
         adGenPolicerCEVlanPriority
            DisplayString,
         adGenPolicerAddEvcMap
            DisplayString,
         adGenPolicerRemoveEvcMap
            DisplayString,
         adGenPolicerLastError
            DisplayString
      }

      adGenPolicerName OBJECT-TYPE
         SYNTAX  DisplayString (SIZE (1..50))
         MAX-ACCESS  not-accessible
         STATUS  current
         DESCRIPTION
            "A user configurable name for the Policer.  Upon creation of the
             Policer, the associated name will default to a unique value."
         ::= { adGenPolicerEntry 1 }

      adGenPolicerRowStatus OBJECT-TYPE
         SYNTAX  RowStatus
         MAX-ACCESS  read-create
         STATUS  current
         DESCRIPTION
           "This object is used to create a new row or modify or delete an
            existing row in the Policer table."
         ::= { adGenPolicerEntry 2 }

      adGenPolicerStatus OBJECT-TYPE
         SYNTAX  DisplayString
         MAX-ACCESS  read-only
         STATUS  current
         DESCRIPTION
            "This variable provides the Policer status.  If there is no error, the Policer
             status will be 'running'.  If there is an error and the Policer cannot be
             applied, then this variable will provide more details about the error."
         ::= { adGenPolicerEntry 3 }

      adGenPolicerOperStatus OBJECT-TYPE
         SYNTAX INTEGER  {
            up(1),
            down(2)
         }
         MAX-ACCESS read-only
         STATUS current
         DESCRIPTION
            "This variable provides the current operational status of the Policer."
         ::= { adGenPolicerEntry 4 }

      adGenPolicerCIR OBJECT-TYPE
         SYNTAX  Integer32
         MAX-ACCESS  read-create
         STATUS  current
         DESCRIPTION
            "This variable is used to configure the Committed Information Rate (CIR) for
             the policer. The CIR is the rate in kbps up to which service frames are
             delivered according to the service performance objectives."
         ::= { adGenPolicerEntry 5 }

      adGenPolicerCBS OBJECT-TYPE
         SYNTAX  Integer32
         MAX-ACCESS  read-create
         STATUS  current
         DESCRIPTION
            "This variable is used to configure the Committed Burst Size (CBS) for
             the policer. The CBS is the maximum available bytes for a burst of
             ingress traffic sent at the UNI speed while still conforming to the CIR."
         ::= { adGenPolicerEntry 6 }

      adGenPolicerEIR OBJECT-TYPE
         SYNTAX  Integer32
         MAX-ACCESS  read-create
         STATUS  current
         DESCRIPTION
            "This variable is used to configure the Excess Information Rate (EIR) for
             the policer. The EIR is the rate in kbps up to which service frames are
             delivered without any performance objectives."
         ::= { adGenPolicerEntry 7 }

      adGenPolicerEIRNoLimit OBJECT-TYPE
         SYNTAX         TruthValue
         MAX-ACCESS     read-create
         STATUS         current
         DESCRIPTION
           "A boolean indicating whether you want to configure EIR for no limit (max-bandwidth).
            If you configure value of EIR using adGenPolicerEIR, this should be set to FALSE."
         DEFVAL { false }
         ::= { adGenPolicerEntry 8 }

      adGenPolicerEBS OBJECT-TYPE
         SYNTAX  Integer32
         MAX-ACCESS  read-create
         STATUS  current
         DESCRIPTION
            "This variable is used to configure the Excess Burst Size (EBS) for
             the policer. TThe EBS is the maximum available bytes for a burst of
             ingress traffic sent at the UNI speed while still conforming to the EIR."
         ::= { adGenPolicerEntry 9 }

      adGenPolicerMode OBJECT-TYPE
         SYNTAX INTEGER {
            unspecified(1),
            perUNI(2),
            perInterface(3),
            perEVC(4),
            perMEVC(5),
            perEVCMap(6)
         }
         MAX-ACCESS  read-create
         STATUS  current
         DESCRIPTION
            "This variable provisions the type of the policer.
             * Use the unspecified option to remove currently selected per mode option.  Also this is
               a default value when per mode is not explicitly selected.
             * Use the perUNI option to apply the policer to all traffic on a particular UNI interface. 
             * Use the perEVC option to apply the policer to all traffic on a particular EVC.
             * Use the perEVCMap option to apply the policer to all traffic on a particular map.
               Multiple maps can be added to a single policer.
             * Use the perMEVC option to apply the policer to all traffic on a particular MEVC.
             * Use the perMEVC option with CE-VLAN-Pri <0-7> to apply the policer to a particular range
               of CE VLAN priority traffic within an MEVC.
             * Use the perInterface option to apply the policer to all traffic on a particular interface."
         ::= { adGenPolicerEntry 10 }

      adGenPolicerUNIPort OBJECT-TYPE
         SYNTAX  InterfaceIndexOrZero
         MAX-ACCESS  read-create
         STATUS  current
         DESCRIPTION
           "This variable is used if adGenPolicerMode is set to perUNI option.
            It specifies the interface index to apply the policer to a particular UNI."
         ::= { adGenPolicerEntry 11 }

      adGenPolicerEVCName OBJECT-TYPE
         SYNTAX  DisplayString
         MAX-ACCESS  read-create
         STATUS  current
         DESCRIPTION
           "This variable is used if adGenPolicerMode is set to perEVC option.
            It specifies the name of the EVC to apply the policer to a particular EVC."
         ::= { adGenPolicerEntry 12 }

      adGenPolicerMEVCName OBJECT-TYPE
         SYNTAX  DisplayString
         MAX-ACCESS  read-create
         STATUS  current
         DESCRIPTION
           "This variable is used if adGenPolicerMode is set to perMEVC option.
            It specifies the name of the MEVC to apply the policer to a particular MEVC."
         ::= { adGenPolicerEntry 13 }

      adGenPolicerCEVlanPriority OBJECT-TYPE
         SYNTAX  DisplayString
         MAX-ACCESS  read-create
         STATUS  current
         DESCRIPTION
           "This variable is used if adGenPolicerMode is set to perMEVC option and the policer
            is to be applied to a particular range of CE VLAN priority traffic within an MEVC.
            It specifies the value of the CE VLAN priority to apply to the policer.
            Example values:
                   Empty string = Unspecified
                   0,1,2        = P-bit values 0,1,2
                   0-2,5-7      = P-bit values 0,1,2,5,6,7"
         ::= { adGenPolicerEntry 14 }

      adGenPolicerAddEvcMap OBJECT-TYPE
         SYNTAX  DisplayString
         MAX-ACCESS  read-create
         STATUS  current
         DESCRIPTION
           "This variable is used if adGenPolicerMode is set to perEVCMap option. It is used
            to add a map to the policer. It specifies the EVC Map to apply the policer to all
            traffic on a particular map. Use adGenPolicerEVCMapLookupTable to list all
            configured Evc Maps."
         ::= { adGenPolicerEntry 15 }

      adGenPolicerRemoveEvcMap OBJECT-TYPE
         SYNTAX  DisplayString
         MAX-ACCESS  read-create
         STATUS  current
         DESCRIPTION
           "This variable is used if adGenPolicerMode is set to perEVCMap option. It is used
            to remove an EVC Map from the policer.  Use adGenPolicerEVCMapLookupTable to list all
            configured Evc Maps."
         ::= { adGenPolicerEntry 16 }

      adGenPolicerLastError OBJECT-TYPE
         SYNTAX         DisplayString
         MAX-ACCESS     read-only
         STATUS         current
         DESCRIPTION
           "This string describes the last error experienced
            for this particular entry in the table."
         ::= { adGenPolicerEntry 17 }

--==================================================================================================================

   adGenPolicerThresholds  OBJECT IDENTIFIER ::= { adGenPolicerProvisioning 2 }

   adGenPolicer15MinThresholdTable OBJECT-TYPE
      SYNTAX  SEQUENCE OF AdGenPolicer15MinThresholdEntry
      MAX-ACCESS  not-accessible
      STATUS  current
      DESCRIPTION
         "The Policer 15 minute threshold table."
      ::= { adGenPolicerThresholds 1 }

   adGenPolicer15MinThresholdEntry OBJECT-TYPE
      SYNTAX  AdGenPolicer15MinThresholdEntry
      MAX-ACCESS  not-accessible
      STATUS  current
      DESCRIPTION
         "An entry in the Policer 15 minute threshold table.  Each entry
          is uniquely identified by Slot as well as by the Policer Name."
      INDEX  { adGenSlotInfoIndex, adGenPolicerName }
      ::= { adGenPolicer15MinThresholdTable 1 }

   AdGenPolicer15MinThresholdEntry ::=
      SEQUENCE {
         adGenPolicer15MinThresholdDiscardsGreenFrames
            Integer32,
         adGenPolicer15MinThresholdTotalGreenFrames
            Integer32,
         adGenPolicer15MinThresholdDiscardsYellowFrames
            Integer32,
         adGenPolicer15MinThresholdTotalYellowFrames
            Integer32,
         adGenPolicer15MinThresholdTotalRedFrames
            Integer32
      }

      adGenPolicer15MinThresholdDiscardsGreenFrames OBJECT-TYPE
         SYNTAX  Integer32
         MAX-ACCESS  read-write
         STATUS  current
         DESCRIPTION
            "The 15 minute performance monitoring threshold associated with the
             number of green frames dropped due to congestion."
         ::= { adGenPolicer15MinThresholdEntry 1 }

      adGenPolicer15MinThresholdTotalGreenFrames OBJECT-TYPE
         SYNTAX  Integer32
         MAX-ACCESS  read-write
         STATUS  current
         DESCRIPTION
            "The 15 minute performance monitoring threshold associated with the
             number of all ingress frames colored green."
         ::= { adGenPolicer15MinThresholdEntry 2 }

      adGenPolicer15MinThresholdDiscardsYellowFrames OBJECT-TYPE
         SYNTAX  Integer32
         MAX-ACCESS  read-write
         STATUS  current
         DESCRIPTION
            "The 15 minute performance monitoring threshold associated with the
             number of yellow frames dropped due to congestion."
         ::= { adGenPolicer15MinThresholdEntry 3 }

      adGenPolicer15MinThresholdTotalYellowFrames OBJECT-TYPE
         SYNTAX  Integer32
         MAX-ACCESS  read-write
         STATUS  current
         DESCRIPTION
            "The 15 minute performance monitoring threshold associated with the
             number of all ingress frames colored yellow."
         ::= { adGenPolicer15MinThresholdEntry 4 }

      adGenPolicer15MinThresholdTotalRedFrames OBJECT-TYPE
         SYNTAX  Integer32
         MAX-ACCESS  read-write
         STATUS  current
         DESCRIPTION
            "The 15 minute performance monitoring threshold associated with the
             number of all ingress frames colored red."
         ::= { adGenPolicer15MinThresholdEntry 5 }

--==================================================================================================================

   adGenPolicer24HrThresholdTable OBJECT-TYPE
      SYNTAX  SEQUENCE OF AdGenPolicer24HrThresholdEntry
      MAX-ACCESS  not-accessible
      STATUS  current
      DESCRIPTION
         "The Policer 24 hour threshold table."
      ::= { adGenPolicerThresholds 2 }

   adGenPolicer24HrThresholdEntry OBJECT-TYPE
      SYNTAX  AdGenPolicer24HrThresholdEntry
      MAX-ACCESS  not-accessible
      STATUS  current
      DESCRIPTION
         "An entry in the Policer 24 hour threshold table.  Each entry
          is uniquely identified by Slot as well as by the Policer Name."
      INDEX  { adGenSlotInfoIndex, adGenPolicerName }
      ::= { adGenPolicer24HrThresholdTable 1 }

   AdGenPolicer24HrThresholdEntry ::=
      SEQUENCE {
         adGenPolicer24HrThresholdDiscardsGreenFrames
            Integer32,
         adGenPolicer24HrThresholdTotalGreenFrames
            Integer32,
         adGenPolicer24HrThresholdDiscardsYellowFrames
            Integer32,
         adGenPolicer24HrThresholdTotalYellowFrames
            Integer32,
         adGenPolicer24HrThresholdTotalRedFrames
            Integer32
      }

      adGenPolicer24HrThresholdDiscardsGreenFrames OBJECT-TYPE
         SYNTAX  Integer32
         MAX-ACCESS  read-write
         STATUS  current
         DESCRIPTION
            "The 24 hour performance monitoring threshold associated with the
             number of green frames dropped due to congestion."
         ::= { adGenPolicer24HrThresholdEntry 1 }

      adGenPolicer24HrThresholdTotalGreenFrames OBJECT-TYPE
         SYNTAX  Integer32
         MAX-ACCESS  read-write
         STATUS  current
         DESCRIPTION
            "The 24 hour performance monitoring threshold associated with the
             number of all ingress frames colored green."
         ::= { adGenPolicer24HrThresholdEntry 2 }

      adGenPolicer24HrThresholdDiscardsYellowFrames OBJECT-TYPE
         SYNTAX  Integer32
         MAX-ACCESS  read-write
         STATUS  current
         DESCRIPTION
            "The 24 hour performance monitoring threshold associated with the
             number of yellow frames dropped due to congestion."
         ::= { adGenPolicer24HrThresholdEntry 3 }

      adGenPolicer24HrThresholdTotalYellowFrames OBJECT-TYPE
         SYNTAX  Integer32
         MAX-ACCESS  read-write
         STATUS  current
         DESCRIPTION
            "The 24 hour performance monitoring threshold associated with the
             number of all ingress frames colored yellow."
         ::= { adGenPolicer24HrThresholdEntry 4 }

      adGenPolicer24HrThresholdTotalRedFrames OBJECT-TYPE
         SYNTAX  Integer32
         MAX-ACCESS  read-write
         STATUS  current
         DESCRIPTION
            "The 24 hour performance monitoring threshold associated with the
             number of all ingress frames colored red."
         ::= { adGenPolicer24HrThresholdEntry 5 }

--==================================================================================================================

   adGenPolicerErrorTable OBJECT-TYPE
      SYNTAX  SEQUENCE OF AdGenPolicerErrorEntry
      MAX-ACCESS  not-accessible
      STATUS  current
      DESCRIPTION
         "The Policer Creation Error table."
      ::= { adGenPolicerProvisioning 3 }

   adGenPolicerErrorEntry OBJECT-TYPE
      SYNTAX  AdGenPolicerErrorEntry
      MAX-ACCESS  not-accessible
      STATUS  current
      DESCRIPTION
         "An entry in the Policer Creation Error table.
          The index, adGenSlotInfoIndex, identifies the SLOT."
      INDEX  { adGenSlotInfoIndex }
      ::= { adGenPolicerErrorTable 1 }

   AdGenPolicerErrorEntry ::=
      SEQUENCE {
         adGenPolicerError
            DisplayString
      }

      adGenPolicerError OBJECT-TYPE
         SYNTAX  DisplayString
         MAX-ACCESS  read-only
         STATUS  current
         DESCRIPTION
           "Returns information about the last error for the Policer
            create on SLOT. If row creation fails, this string
            will provide details about why the row could not be created."
         ::= { adGenPolicerErrorEntry 1}

--==================================================================================================================

   adGenPolicerLookupTable OBJECT-TYPE
      SYNTAX  SEQUENCE OF AdGenPolicerLookupEntry
      MAX-ACCESS  not-accessible
      STATUS  current
      DESCRIPTION
         "The table to display Policer information associated with the Slot."
      ::= { adGenPolicerProvisioning 4 }

   adGenPolicerLookupEntry OBJECT-TYPE
      SYNTAX  AdGenPolicerLookupEntry
      MAX-ACCESS  not-accessible
      STATUS  current
      DESCRIPTION
         "An entry in the policer information table. Each entry in the table
          is uniquely indentified by Slot as well as by the Policer name."
      INDEX  { adGenSlotInfoIndex, adGenPolicerName }
      ::= { adGenPolicerLookupTable 1 }

   AdGenPolicerLookupEntry ::=
      SEQUENCE {
         adGenPolicerActualCIR
            Integer32,
         adGenPolicerActualCBS
            Integer32,
         adGenPolicerActualEIR
            Integer32,
         adGenPolicerActualEBS
            Integer32,
         adGenPolicerProvNumberOfEVCMaps
            Integer32,
         adGenPolicerQualifiedNumberOfEVCMaps
            Integer32
      }

      adGenPolicerActualCIR OBJECT-TYPE
         SYNTAX  Integer32
         MAX-ACCESS  read-only
         STATUS  current
         DESCRIPTION
            "This variable displays the actual Committed Information Rate (CIR) for
             the policer. The CIR is the rate in kbps up to which service frames are
             delivered according to the service performance objectives."
         ::= { adGenPolicerLookupEntry 1 }

      adGenPolicerActualCBS OBJECT-TYPE
         SYNTAX  Integer32
         MAX-ACCESS  read-only
         STATUS  current
         DESCRIPTION
            "This variable displays the actual Committed Burst Size (CBS) for
             the policer. The CBS is the maximum available bytes for a burst of
             ingress traffic sent at the UNI speed while still conforming to the CIR."
         ::= { adGenPolicerLookupEntry 2 }

      adGenPolicerActualEIR OBJECT-TYPE
         SYNTAX  Integer32
         MAX-ACCESS  read-only
         STATUS  current
         DESCRIPTION
            "This variable displays the actual Excess Information Rate (EIR) for
             the policer. The EIR is the rate in kbps up to which service frames are
             delivered without any performance objectives."
         ::= { adGenPolicerLookupEntry 3 }

      adGenPolicerActualEBS OBJECT-TYPE
         SYNTAX  Integer32
         MAX-ACCESS  read-only
         STATUS  current
         DESCRIPTION
            "This variable displays the actual Excess Burst Size (EBS) for
             the policer. The EBS is the maximum available bytes for a burst of
             ingress traffic sent at the UNI speed while still conforming to the EIR."
         ::= { adGenPolicerLookupEntry 4 }

      adGenPolicerProvNumberOfEVCMaps OBJECT-TYPE
         SYNTAX  Integer32
         MAX-ACCESS  read-only
         STATUS  current
         DESCRIPTION
            "This variable displays the count of Provisioned EVC maps that are connected to the policer."
         ::= { adGenPolicerLookupEntry 5 }

      adGenPolicerQualifiedNumberOfEVCMaps OBJECT-TYPE
         SYNTAX  Integer32
         MAX-ACCESS  read-only
         STATUS  current
         DESCRIPTION
            "This variable displays the count of Qualified EVC maps that are connected to the policer.
            The qualified Evc Maps are the Maps associated to MEVC,EVC, EVC Map, UNI or Interface
            based on adGenPolicerMode settings."
         ::= { adGenPolicerLookupEntry 6 }

--==================================================================================================================

   adGenPolicerEVCMapLookupTable OBJECT-TYPE
      SYNTAX  SEQUENCE OF AdGenPolicerEVCMapLookupEntry
      MAX-ACCESS  not-accessible
      STATUS  current
      DESCRIPTION
         "The lookup table to display Provisioned EVC Maps names associated with a policer."
      ::= { adGenPolicerProvisioning 5 }

   adGenPolicerEVCMapLookupEntry OBJECT-TYPE
      SYNTAX  AdGenPolicerEVCMapLookupEntry
      MAX-ACCESS  not-accessible
      STATUS  current
      DESCRIPTION
         "An entry in the policer EVC Map lookup table.
          The first index, adGenSlotInfoIndex, identifies the SLOT.
          The second index, adGenPolicerFixedLengthName, identifies the Policer.
          The third index, adGenPolicerEVCMapLookupIndex, identifies the associated
          Provisioned Evc Map index."
      INDEX  { adGenSlotInfoIndex, adGenPolicerFixedLengthName, adGenPolicerEVCMapLookupIndex }
      ::= { adGenPolicerEVCMapLookupTable 1 }

   AdGenPolicerEVCMapLookupEntry ::=
      SEQUENCE {
         adGenPolicerFixedLengthName
            OCTET STRING,
         adGenPolicerEVCMapLookupIndex
            Integer32,
         adGenPolicerEVCMapLookupName
            DisplayString
      }

      adGenPolicerFixedLengthName OBJECT-TYPE
         SYNTAX  OCTET STRING (SIZE (50))
         MAX-ACCESS  not-accessible
         STATUS  current
         DESCRIPTION
            "A user configured name for the Policer. This string matches
            adGenPolicerName from adGenPolicerTable, but it is padded at the
            end with 0x00 so that the table index has a fixed length of
            50 characters."
         ::= { adGenPolicerEVCMapLookupEntry 1}

      adGenPolicerEVCMapLookupIndex OBJECT-TYPE
         SYNTAX  Integer32
         MAX-ACCESS  not-accessible
         STATUS  current
         DESCRIPTION
            "This variable is used as an index into the EVC maps associated with the policer."
         ::= { adGenPolicerEVCMapLookupEntry 2}

      adGenPolicerEVCMapLookupName OBJECT-TYPE
         SYNTAX  DisplayString
         MAX-ACCESS  read-only
         STATUS  current
         DESCRIPTION
            "This variable list the EVC map name that is associated with the policer."
         ::= { adGenPolicerEVCMapLookupEntry 3}

--==================================================================================================================

   adGenPolicerQualifiedEVCMapLookupTable OBJECT-TYPE
      SYNTAX  SEQUENCE OF AdGenPolicerQualifiedEVCMapLookupEntry
      MAX-ACCESS  not-accessible
      STATUS  current
      DESCRIPTION
         "The lookup table to display Qualified EVC Maps names associated with a policer. The qualified
         Evc Maps are the Maps associated to MEVC,EVC, EVC Map, UNI or Interface based on adGenPolicerMode
         settings."
      ::= { adGenPolicerProvisioning 6 }

   adGenPolicerQualifiedEVCMapLookupEntry OBJECT-TYPE
      SYNTAX  AdGenPolicerQualifiedEVCMapLookupEntry
      MAX-ACCESS  not-accessible
      STATUS  current
      DESCRIPTION
         "An entry in the policer Qualified EVC Map lookup table.
          The first index, adGenSlotInfoIndex, identifies the SLOT.
          The second index, adGenPolicerFixedLengthName, identifies the Policer.
          The third index, adGenPolicerQualifiedEVCMapLookupIndex, identifies the associated
          Qualified Evc Map index."
      INDEX  { adGenSlotInfoIndex, adGenPolicerFixedLengthName, adGenPolicerQualifiedEVCMapLookupIndex }
      ::= { adGenPolicerQualifiedEVCMapLookupTable 1 }

   AdGenPolicerQualifiedEVCMapLookupEntry ::=
      SEQUENCE {
         adGenPolicerQualifiedEVCMapLookupIndex
            Integer32,
         adGenPolicerQualifiedEVCMapLookupName
            DisplayString,
         adGenPolicerQualifiedEVCMapLookupStatus
            INTEGER
      }

      adGenPolicerQualifiedEVCMapLookupIndex OBJECT-TYPE
         SYNTAX  Integer32
         MAX-ACCESS  not-accessible
         STATUS  current
         DESCRIPTION
            "This variable is used as an index into the Qualified EVC maps associated with the policer."
         ::= { adGenPolicerQualifiedEVCMapLookupEntry 1}

      adGenPolicerQualifiedEVCMapLookupName OBJECT-TYPE
         SYNTAX  DisplayString
         MAX-ACCESS  read-only
         STATUS  current
         DESCRIPTION
            "This variable list the Qualified EVC map name that is associated with the policer."
         ::= { adGenPolicerQualifiedEVCMapLookupEntry 2}

      adGenPolicerQualifiedEVCMapLookupStatus OBJECT-TYPE
         SYNTAX INTEGER {
            disabled (1),
            notApplied(2),
            applied(3)
         }
         MAX-ACCESS  read-only
         STATUS  current
         DESCRIPTION
            "This variable list the Qualified Evc Map Policed Status that is associated with the
             policer.
             * Evc Map policed Status of disabled indicates that the associated policer is not in the
               running state.
             * Evc Map policed status of notApplied indicates that traffic ingressing this Evc Map is
               subject to another, more qualified, policer's bandwidth profile. 
             * Evc Map policed status of applied indicates that all traffic ingressing this Evc Map is
               subject to this policer's bandwidth profile."
         ::= { adGenPolicerQualifiedEVCMapLookupEntry 3 }


--==================================================================================================================

   adGenPolicer15MinThresGreenTotalAlarm NOTIFICATION-TYPE
      OBJECTS  {
         adTrapInformSeqNum,
         sysName,
         adGenSlotInfoIndex,
         adGenPolicer15MinThresholdTotalGreenFrames
      }
      STATUS  current
      DESCRIPTION
         "This trap indicates that the Policer total green frames has crossed the 15 min green frames total Threshold"
         --#TYPE         "Status - Alarm"
         --#SUMMARY      "adGenPolicer 1: Total Green Frames 15 min Threshold Crossed."
         --#SUMMARY      "Detected at shelf: %s, slot: %d, policer %s"
         --#ARGUMENTS    {1,2,3}
         --#SEVERITY     WARNING
         --#GENERIC      6
         --#CATEGORY     "Error Events"
         --#SOURCE_ID    "A"
         --#TIMEINDEX    0
      ::= { adGenPolicerAlarmEvents 1 }


   adGenPolicer15MinThresYellowTotalAlarm NOTIFICATION-TYPE
      OBJECTS  {
         adTrapInformSeqNum,
         sysName,
         adGenSlotInfoIndex,
         adGenPolicer15MinThresholdTotalYellowFrames
      }
      STATUS  current
      DESCRIPTION
         "This trap indicates that the Policer total yellow frames has crossed the 15 min yellow total Threshold"
         --#TYPE         "Status - Alarm"
         --#SUMMARY      "adGenPolicer 3: Total Yellow Frames 15 min Threshold Crossed."
         --#SUMMARY      "Detected at shelf: %s, slot: %d, policer %s"
         --#ARGUMENTS    {1,2,3}
         --#SEVERITY     WARNING
         --#GENERIC      6
         --#CATEGORY     "Error Events"
         --#SOURCE_ID    "A"
         --#TIMEINDEX    0
      ::= { adGenPolicerAlarmEvents 3 }


   adGenPolicer15MinThresRedTotalAlarm NOTIFICATION-TYPE
      OBJECTS  {
         adTrapInformSeqNum,
         sysName,
         adGenSlotInfoIndex,
         adGenPolicer15MinThresholdTotalRedFrames
      }
      STATUS  current
      DESCRIPTION
         "This trap indicates that the Policer total red frames has crossed the 15 min red total Threshold"
         --#TYPE         "Status - Alarm"
         --#SUMMARY      "adGenPolicer 5: Total Red Frames 15 min Threshold Crossed."
         --#SUMMARY      "Detected at shelf: %s, slot: %d, policer %s"
         --#ARGUMENTS    {1,2,3}
         --#SEVERITY     WARNING
         --#GENERIC      6
         --#CATEGORY     "Error Events"
         --#SOURCE_ID    "A"
         --#TIMEINDEX    0
      ::= { adGenPolicerAlarmEvents 5 }


   adGenPolicer24HrThresGreenTotalAlarm NOTIFICATION-TYPE
      OBJECTS  {
         adTrapInformSeqNum,
         sysName,
         adGenSlotInfoIndex,
         adGenPolicer24HrThresholdTotalGreenFrames
      }
      STATUS  current
      DESCRIPTION
         "This trap indicates that the Policer total green frames has crossed the 24 hour green total Threshold"
         --#TYPE         "Status - Alarm"
         --#SUMMARY      "adGenPolicer 7: Total Green Frames 24 hour Threshold Crossed."
         --#SUMMARY      "Detected at shelf: %s, slot: %d, policer %s"
         --#ARGUMENTS    {1,2,3}
         --#SEVERITY     WARNING
         --#GENERIC      6
         --#CATEGORY     "Error Events"
         --#SOURCE_ID    "A"
         --#TIMEINDEX    0
      ::= { adGenPolicerAlarmEvents 7 }


   adGenPolicer24HrThresYellowTotalAlarm NOTIFICATION-TYPE
      OBJECTS  {
         adTrapInformSeqNum,
         sysName,
         adGenSlotInfoIndex,
         adGenPolicer24HrThresholdTotalYellowFrames
      }
      STATUS  current
      DESCRIPTION
         "This trap indicates that the Policer total yellow frames has crossed the 24 hour yellow total Threshold"
         --#TYPE         "Status - Alarm"
         --#SUMMARY      "adGenPolicer 9: Total Yellow Frames 24 hour Threshold Crossed."
         --#SUMMARY      "Detected at shelf: %s, slot: %d, policer %s"
         --#ARGUMENTS    {1,2,3}
         --#SEVERITY     WARNING
         --#GENERIC      6
         --#CATEGORY     "Error Events"
         --#SOURCE_ID    "A"
         --#TIMEINDEX    0
      ::= { adGenPolicerAlarmEvents 9 }


   adGenPolicer24HrThresRedTotalAlarm NOTIFICATION-TYPE
      OBJECTS  {
         adTrapInformSeqNum,
         sysName,
         adGenSlotInfoIndex,
         adGenPolicer24HrThresholdTotalRedFrames
      }
      STATUS  current
      DESCRIPTION
         "This trap indicates that the Policer total red frames has crossed the 24 hour red total Threshold"
         --#TYPE         "Status - Alarm"
         --#SUMMARY      "adGenPolicer 11: Total Red Frames 24 hour Threshold Crossed."
         --#SUMMARY      "Detected at shelf: %s, slot: %d, policer %s"
         --#ARGUMENTS    {1,2,3}
         --#SEVERITY     WARNING
         --#GENERIC      6
         --#CATEGORY     "Error Events"
         --#SOURCE_ID    "A"
         --#TIMEINDEX    0
      ::= { adGenPolicerAlarmEvents 11 }

END

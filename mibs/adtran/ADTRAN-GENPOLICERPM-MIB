ADTRAN-GENPOLICERPM-MIB

-- TITLE:     The ADTRAN POLICER PM MIB
-- PRODUCT:   Metro Ethernet Products
-- VERSION:   1.0
-- DATE:      11/11/2010
-- AUTHOR:    Danmin Wu
-- STATUS:    PRELIMINARY

-- This MIB defines the object identifiers (OIDs) for the
-- ADTRAN GENPOLICER PM MIB objects

-- HISTORY:
-- 2010/11/11 dmw   STATUS: PRELIMINARY.
-- ******************************************************************************************
DEFINITIONS ::= BEGIN

IMPORTS

   adGenPolicer,
   adGenPolicerID
									FROM ADTRAN-SHARED-CND-SYSTEM-MIB

	adGenPolicerName,
   adGenPolicerFixedLengthName
	                        FROM ADTRAN-GENPOLICER-MIB

   OBJECT-TYPE,
   MODULE-IDENTITY,
   Integer32,
	Counter64
									FROM SNMPv2-SMI

   TruthValue
									FROM SNMPv2-TC

   adGenSlotInfoIndex
									FROM ADTRAN-GENSLOT-MIB
   ;

adGenPolicerPMMIB MODULE-IDENTITY
   LAST-UPDATED "201011030000Z"
   ORGANIZATION "Adtran, Inc."
   CONTACT-INFO
     "CND Tech Support
         Postal: ADTRAN, Inc.
                 901 Explorer Blvd.
                 Huntsville, AL  35806
                 Tel: +1 800 726-8663
                 Fax: +1 256 963 6217
                 E-mail: support@adtran.com"
   DESCRIPTION
      "This MIB defines the objects for the Policer PM MIB."
   REVISION "201011030000Z"
   DESCRIPTION "Created"
::= { adGenPolicerID 2 }

adGenPolicerPerformance                 OBJECT IDENTIFIER ::= {adGenPolicer 2}


--==================================================================================================================
-- Policer PM current 15-Minute interval parameters

  adGenPolicerPM15MinCurrentTable OBJECT-TYPE
      SYNTAX  SEQUENCE OF AdGenPolicerPM15MinCurrentEntry
      MAX-ACCESS  not-accessible
      STATUS  current
      DESCRIPTION
         "The Generic Policer PM 15-Minute current table."
      ::= { adGenPolicerPerformance 1 }

  adGenPolicerPM15MinCurrentEntry OBJECT-TYPE
      SYNTAX  AdGenPolicerPM15MinCurrentEntry
      MAX-ACCESS  not-accessible
      STATUS  current
      DESCRIPTION
         "An entry in the Generic Policer PM 15-Minute current table.
			 Policer PM entries are uniquely identified by the Slot and the Policer Name.
			 adGenSlotInfoIndex, identifies the SLOT;
			 adGenPolicerFixedLengthName, identifies the Policer;"
      INDEX  { adGenSlotInfoIndex, adGenPolicerName }
      ::= { adGenPolicerPM15MinCurrentTable 1 }

  AdGenPolicerPM15MinCurrentEntry  ::=
      SEQUENCE {
         adGenPolicerPM15MinCurrentIngressGreenFrames
            Counter64,
         adGenPolicerPM15MinCurrentIngressYellowFrames
            Counter64,
         adGenPolicerPM15MinCurrentIngressRedFrames
            Counter64
		}

  adGenPolicerPM15MinCurrentIngressGreenFrames OBJECT-TYPE
         SYNTAX Counter64
         MAX-ACCESS  read-only
         STATUS  current
         DESCRIPTION
            "The total numbers of Green Frames received on the Policer
             during the current 15-Minute interval"
         ::= { adGenPolicerPM15MinCurrentEntry 1 }

  adGenPolicerPM15MinCurrentIngressYellowFrames OBJECT-TYPE
         SYNTAX Counter64
         MAX-ACCESS  read-only
         STATUS  current
         DESCRIPTION
            "The total numbers of Yellow Frames received on the Policer
             during the current 15-Minute interval"
         ::= { adGenPolicerPM15MinCurrentEntry 2 }

  adGenPolicerPM15MinCurrentIngressRedFrames OBJECT-TYPE
         SYNTAX Counter64
         MAX-ACCESS  read-only
         STATUS  current
         DESCRIPTION
            "The total numbers of Red Frames received on the Policer
             during the current 15-Minute interval"
         ::= { adGenPolicerPM15MinCurrentEntry 3 }

--==================================================================================================================
-- Policer PM 1-96 15-Minute interval parameters

   adGenPolicerPM15MinIntervalTable OBJECT-TYPE
      SYNTAX  SEQUENCE OF AdGenPolicerPM15MinIntervalEntry
      MAX-ACCESS  not-accessible
      STATUS  current
      DESCRIPTION
         "The Policer PM 15-Minute interval table."
      ::= { adGenPolicerPerformance 2 }

   adGenPolicerPM15MinIntervalEntry OBJECT-TYPE
      SYNTAX  AdGenPolicerPM15MinIntervalEntry
      MAX-ACCESS  not-accessible
      STATUS  current
      DESCRIPTION
         "An entry in the Policer PM 15-Minute interval table.
				adGenSlotInfoIndex, identifies the SLOT;
				adGenPolicerFixedLengthName, identifies the Policer;
				adGenPolicerPM15MinIntervalNumber, identifies the 15-Minute interval; "
      INDEX   { adGenSlotInfoIndex, adGenPolicerFixedLengthName, adGenPolicerPM15MinIntervalNumber }
      ::= { adGenPolicerPM15MinIntervalTable 1 }

  AdGenPolicerPM15MinIntervalEntry  ::=
      SEQUENCE {
         adGenPolicerPM15MinIntervalNumber
            Integer32,
         adGenPolicerPM15MinIntervalIngressGreenFrames
            Counter64,
         adGenPolicerPM15MinIntervalIngressYellowFrames
            Counter64,
         adGenPolicerPM15MinIntervalIngressRedFrames
            Counter64,
			adGenPolicerPM15MinIntervalValidData
				TruthValue

		}

  adGenPolicerPM15MinIntervalNumber OBJECT-TYPE
         SYNTAX  Integer32
         MAX-ACCESS  read-only
         STATUS  current
         DESCRIPTION
            "A number between 1 and 96, where 1 is the most
             recently completed 15-Minute interval and 96 is
             the least recently completed 15-Minute interval
             (assuming that all 96 intervals are valid)."
         ::= { adGenPolicerPM15MinIntervalEntry 1 }

  adGenPolicerPM15MinIntervalIngressGreenFrames OBJECT-TYPE
         SYNTAX Counter64
         MAX-ACCESS  read-only
         STATUS  current
         DESCRIPTION
            "The total number of Green Frames received on the Policer
             during the selected 15-Minute interval"
         ::= { adGenPolicerPM15MinIntervalEntry 2 }

  adGenPolicerPM15MinIntervalIngressYellowFrames OBJECT-TYPE
         SYNTAX Counter64
         MAX-ACCESS  read-only
         STATUS  current
         DESCRIPTION
            "The total number of Yellow Frames received on the Policer
             during the selected 15-Minute interval"
         ::= { adGenPolicerPM15MinIntervalEntry 3 }

  adGenPolicerPM15MinIntervalIngressRedFrames OBJECT-TYPE
         SYNTAX Counter64
         MAX-ACCESS  read-only
         STATUS  current
         DESCRIPTION
            "The total number of Red Frames received on the Policer
             during the selected 15-Minute interval"
         ::= { adGenPolicerPM15MinIntervalEntry 4 }

  adGenPolicerPM15MinIntervalValidData OBJECT-TYPE
          SYNTAX TruthValue
          MAX-ACCESS read-only
          STATUS current
          DESCRIPTION
                 "This variable indicates if the data for this 15-minute
                 interval is valid."
          ::= { adGenPolicerPM15MinIntervalEntry 5 }

--==================================================================================================================
-- Policer PM current 24-Hour interval parameters

   adGenPolicerPM24HrCurrentTable OBJECT-TYPE
      SYNTAX  SEQUENCE OF AdGenPolicerPM24HrCurrentEntry
      MAX-ACCESS  not-accessible
      STATUS  current
      DESCRIPTION
         "The Generic Policer PM 24-Hour current table."
      ::= { adGenPolicerPerformance 3 }

   adGenPolicerPM24HrCurrentEntry OBJECT-TYPE
      SYNTAX  AdGenPolicerPM24HrCurrentEntry
      MAX-ACCESS  not-accessible
      STATUS  current
      DESCRIPTION
         "An entry in the Generic Policer PM 24-Hour current table.
			 adGenSlotInfoIndex, identifies the SLOT;
			 adGenPolicerFixedLengthName, identifies the Policer;"
      INDEX   { adGenSlotInfoIndex, adGenPolicerName }
      ::= { adGenPolicerPM24HrCurrentTable 1 }

   AdGenPolicerPM24HrCurrentEntry  ::=
      SEQUENCE {
         adGenPolicerPM24HrCurrentIngressGreenFrames
            Counter64,
         adGenPolicerPM24hrCurrentIngressYellowFrames
            Counter64,
         adGenPolicerPM24HrCurrentIngressRedFrames
            Counter64
		}

    adGenPolicerPM24HrCurrentIngressGreenFrames OBJECT-TYPE
         SYNTAX Counter64
         MAX-ACCESS  read-only
         STATUS  current
         DESCRIPTION
            "The total numbers of Green Frames received on the Policer
             during the current 24-Hour interval"
         ::= { adGenPolicerPM24HrCurrentEntry 1 }

   adGenPolicerPM24hrCurrentIngressYellowFrames OBJECT-TYPE
         SYNTAX Counter64
         MAX-ACCESS  read-only
         STATUS  current
         DESCRIPTION
            "The total numbers of Yellow Frames received on the Policer
             during the current 24-Hour interval"
         ::= { adGenPolicerPM24HrCurrentEntry 2 }

   adGenPolicerPM24HrCurrentIngressRedFrames OBJECT-TYPE
         SYNTAX Counter64
         MAX-ACCESS  read-only
         STATUS  current
         DESCRIPTION
            "The total numbers of Red Frames received on the Policer
             during the current 24-Hour interval"
         ::= { adGenPolicerPM24HrCurrentEntry 3 }

--==================================================================================================================
-- Policer PM 1-7 24-Hour interval parameters

   adGenPolicerPM24HrIntervalTable OBJECT-TYPE
      SYNTAX  SEQUENCE OF AdGenPolicerPM24HrIntervalEntry
      MAX-ACCESS  not-accessible
      STATUS  current
      DESCRIPTION
         "The Generic Policer PM 24-Hour interval table."
      ::= { adGenPolicerPerformance 4 }

   adGenPolicerPM24HrIntervalEntry OBJECT-TYPE
      SYNTAX  AdGenPolicerPM24HrIntervalEntry
      MAX-ACCESS  not-accessible
      STATUS  current
      DESCRIPTION
         "An entry in the Generic Policer PM 24-Hour interval table."
      INDEX   { adGenSlotInfoIndex, adGenPolicerFixedLengthName, adGenPolicerPM24HrIntervalNumber }
      ::= { adGenPolicerPM24HrIntervalTable 1 }

   AdGenPolicerPM24HrIntervalEntry  ::=
      SEQUENCE {
         adGenPolicerPM24HrIntervalNumber
            Integer32,
         adGenPolicerPM24HrIntervalIngressGreenFrames
            Counter64,
         adGenPolicerPM24HrIntervalIngressYellowFrames
            Counter64,
         adGenPolicerPM24HrIntervalIngressRedFrames
            Counter64,
			adGenPolicerPM24HrIntervalValidData
				TruthValue
		}

	adGenPolicerPM24HrIntervalNumber OBJECT-TYPE
         SYNTAX  Integer32
         MAX-ACCESS  read-only
         STATUS  current
         DESCRIPTION
            "A number between 1 and 7, where 1 is the most recently
             completed day and 7 is the least recently completed
             day (assuming that all 7 days are valid)."
         ::= { adGenPolicerPM24HrIntervalEntry 1 }
			
   adGenPolicerPM24HrIntervalIngressGreenFrames OBJECT-TYPE
         SYNTAX Counter64
         MAX-ACCESS  read-only
         STATUS  current
         DESCRIPTION
            "The total number of Green Frames received on the Policer
             during the selected 24-Hour interval"
         ::= { adGenPolicerPM24HrIntervalEntry 2 }

  adGenPolicerPM24HrIntervalIngressYellowFrames OBJECT-TYPE
         SYNTAX Counter64
         MAX-ACCESS  read-only
         STATUS  current
         DESCRIPTION
            "The total number of Yellow Frames received on the Policer
             during the selected 24-Hour interval"
         ::= { adGenPolicerPM24HrIntervalEntry 3 }

  adGenPolicerPM24HrIntervalIngressRedFrames OBJECT-TYPE
         SYNTAX Counter64
         MAX-ACCESS  read-only
         STATUS  current
         DESCRIPTION
            "The total number of Red Frames received on the Policer
             during the selected 24-Hour interval"
         ::= { adGenPolicerPM24HrIntervalEntry 4 }

  adGenPolicerPM24HrIntervalValidData OBJECT-TYPE
          SYNTAX TruthValue
          MAX-ACCESS read-only
          STATUS current
          DESCRIPTION
                 "This variable indicates if the data for this 24-hour
                 interval is valid."
          ::= { adGenPolicerPM24HrIntervalEntry 5 }

--==================================================================================================================
-- Policer PM parameters per slot index

   adGenPolicerPMSlotTable OBJECT-TYPE
      SYNTAX  SEQUENCE OF AdGenPolicerPMSlotEntry
      MAX-ACCESS  not-accessible
      STATUS  current
      DESCRIPTION
         "The Generic Policer PM Reset table per slot."
      ::= { adGenPolicerPerformance 5 }

   adGenPolicerPMSlotEntry OBJECT-TYPE
      SYNTAX  AdGenPolicerPMSlotEntry
      MAX-ACCESS  not-accessible
      STATUS  current
      DESCRIPTION
         "An entry in the Generic Policer PM table per slot."
      INDEX   { adGenSlotInfoIndex }
      ::= { adGenPolicerPMSlotTable 1 }

   AdGenPolicerPMSlotEntry  ::=
      SEQUENCE {
         adGenPolicerPMResetSlot
            INTEGER
       }

   adGenPolicerPMResetSlot OBJECT-TYPE
      SYNTAX  INTEGER {
         reset(1)
      }
      MAX-ACCESS  read-write
      STATUS  current
      DESCRIPTION
         "Reset all PM data for the selected
          Policer per slot."
      ::= { adGenPolicerPMSlotEntry 1 }

--==================================================================================================================
-- Policer PM parameters per slot index and policer name

   adGenPolicerPMPerPolicerTable OBJECT-TYPE
      SYNTAX  SEQUENCE OF AdGenPolicerPMPerPolicerEntry
      MAX-ACCESS  not-accessible
      STATUS  current
      DESCRIPTION
         "The Generic Policer PM table per slot and policer name."
      ::= { adGenPolicerPerformance 6 }

   adGenPolicerPMPerPolicerEntry OBJECT-TYPE
      SYNTAX  AdGenPolicerPMPerPolicerEntry
      MAX-ACCESS  not-accessible
      STATUS  current
      DESCRIPTION
         "An entry in the Generic Policer PM reset table per slot and policer name."
      INDEX   { adGenSlotInfoIndex, adGenPolicerName }
      ::= { adGenPolicerPMPerPolicerTable 1 }

   AdGenPolicerPMPerPolicerEntry  ::=
      SEQUENCE {
         adGenPolicerPMResetPolicer
            INTEGER,
			adGenPolicerPMPerPolicer15MinValidIntervals
			   INTEGER,
			adGenPolicerPMPerPolicer24HrValidIntervals
			   INTEGER
       }

   adGenPolicerPMResetPolicer OBJECT-TYPE
      SYNTAX  INTEGER {
         reset(1)
      }
      MAX-ACCESS  read-write
      STATUS  current
      DESCRIPTION
         "Reset all PM data for the selected
          Policer per slot and policer name."
      ::= { adGenPolicerPMPerPolicerEntry 1 }

  adGenPolicerPMPerPolicer15MinValidIntervals OBJECT-TYPE
          SYNTAX  INTEGER (0..96)
          MAX-ACCESS  read-only
          STATUS  current
          DESCRIPTION
                 "The number of previous intervals for
                 which data was collected.  The value will be
                 96 unless the interface was brought online within
                 the last 24 hours, in which case the value will be
                 the number of complete 15-minute intervals since
					  the interface has been online.  In
                 the case where the agent is a proxy, it is
                 possible that some intervals are unavailable.  In
                 this case, this interval is the maximum interval
                 number for which data is available."
          ::= { adGenPolicerPMPerPolicerEntry 2 }

  adGenPolicerPMPerPolicer24HrValidIntervals OBJECT-TYPE
          SYNTAX  INTEGER (0..7)
          MAX-ACCESS  read-only
          STATUS  current
          DESCRIPTION
                 "The number of previous intervals for
                 which data was collected.  The value will be
                 7 unless the interface was brought online within
                 the last 7 days, in which case the value will be
                 the number of complete 24-hour intervals since
					  the interface has been online.  In
                 the case where the agent is a proxy, it is
                 possible that some intervals are unavailable.  In
                 this case, this interval is the maximum interval
                 number for which data is available."
          ::= { adGenPolicerPMPerPolicerEntry 3 }

END

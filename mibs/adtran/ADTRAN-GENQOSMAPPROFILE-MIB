ADTRAN-GENQOSMAPPROFILE-MIB

-- TITLE:     The ADTRAN Qos Map Profile
-- PRODUCT:   Egress Based Switching Elements
-- VERSION:   1.0
-- DATE:      04/09/2012
-- AUTHOR:    Patrick Viafore
-- STATUS:    PRELIMINARY

-- This MIB defines the object identifier (OID) for the
-- ADTRAN QoS Map Profile MIB

-- ******************************************************************************************
DEFINITIONS ::= BEGIN

IMPORTS
   adShared,
   adIdentityShared
      FROM ADTRAN-MIB
   OBJECT-TYPE,
   NOTIFICATION-TYPE,
   MODULE-IDENTITY,
   Unsigned32
      FROM SNMPv2-SMI
   DisplayString,
   RowStatus
      FROM SNMPv2-TC
   OBJECT-GROUP
      FROM SNMPv2-CONF
      ;

adGenQosMapProfileMIB MODULE-IDENTITY
   LAST-UPDATED "201205170000Z"
   ORGANIZATION "Adtran, Inc."
   CONTACT-INFO
     "CND Tech Support
         Postal: ADTRAN, Inc.
                 901 Explorer Blvd.
                 Huntsville, AL  35806
                 Tel: +1 800 726-8663
                 Fax: +1 256 963 6217
                 E-mail: support@adtran.com"
   DESCRIPTION
      "This MIB defines the objects for the QoS Map Profile."

   REVISION "201205170000Z"
   DESCRIPTION "Added adGenQosMapProfileStatus,
                      adGenQosMapProfileMaxAllowedProfiles,
                      adGenQosMapProfileCurrentProfileCount,
                      adGenQosMapProfileLastInsertStatus"

   REVISION "201204090451Z"
   DESCRIPTION "Created"
::= { adIdentityShared 83 }


--==================================================================================================================

adGenQosMapProfileProvisioning              OBJECT IDENTIFIER ::= {adGenQosMapProfile 1}
adGenQosMapProfileStatus                    OBJECT IDENTIFIER ::= {adGenQosMapProfile 2}

--==================================================================================================================


-- ******************************************************************************************
--  QosMapProfile Provisionng Table
-- ******************************************************************************************
   adGenQosMapProfileProvisioningTable OBJECT-TYPE
      SYNTAX  SEQUENCE OF AdGenQosMapProfileProvisioningEntry
      MAX-ACCESS  not-accessible
      STATUS  current
      DESCRIPTION
         "The Qos Map profile table,
         indexed by name of the profile.  Each profile will have a unique name."
      ::= { adGenQosMapProfileProvisioning 1 }


   adGenQosMapProfileProvisioningEntry OBJECT-TYPE
      SYNTAX  AdGenQosMapProfileProvisioningEntry
      MAX-ACCESS  not-accessible
      STATUS  current
      DESCRIPTION
         "A Qos Map Profile entry in the QosMapProfile Provisioning table."
      INDEX  { IMPLIED adGenQosMapProfileName }
      ::= { adGenQosMapProfileProvisioningTable 1 }


   AdGenQosMapProfileProvisioningEntry ::=
      SEQUENCE {
        adGenQosMapProfileName
              DisplayString,
        adGenQosMapProfileClassification
              OCTET STRING,
        adGenQosMapProfileRowStatus
              RowStatus,
        adGenQosMapProfileDescription
              DisplayString
      }


    adGenQosMapProfileName OBJECT-TYPE
      SYNTAX  DisplayString (SIZE (1..80))
      MAX-ACCESS  not-accessible
      STATUS  current
      DESCRIPTION
         "A user configurable name for the QoS Map Profile.  Upon creation of the Qos Map Profile,
          the associated name will default to a unique value."
      ::= { adGenQosMapProfileProvisioningEntry 1}


    adGenQosMapProfileClassification OBJECT-TYPE
      SYNTAX  OCTET STRING
      MAX-ACCESS  read-create
      STATUS  current
      DESCRIPTION
         "A variable length string indicating how traffic is classified into queues.
         Message format:  1 byte for message type, followed by variable length
         depending on message.

         The profile defaults to using a p-bit to queue mapping where each p-bit
         is mapped into a queue with the same value.  Ex: P-Bit 0 -> Queue 0

         Currently supported message types :

             p-bit to queue mapping : 0x00
                 Data: 8 bytes - one byte, read left to right for each p-bit (0-7),
                       each representing which queue they map to

                 Example: Byte:    1  2  3  4  5  6  7  8  9
                          P-Bit:      0  1  2  3  4  5  6  7
                          Msg: 0x 00 01 01 02 02 04 05 06 07
                          0x00 is message type byte indicating p-bit mapping
                          p-bit 0 and 1 go into queue 1, p-bit 2 and 3 go into queue 2,
                          p-bit 4 into queue 4, p-bit 5 into queue 5,
                          p-bit 6 into queue 6, and p-bit 7 into queue 7."
      ::= { adGenQosMapProfileProvisioningEntry 2}


   adGenQosMapProfileRowStatus OBJECT-TYPE
      SYNTAX  RowStatus
      MAX-ACCESS  read-create
      STATUS  current
      DESCRIPTION
        "This object is used to create a new row or modify or delete an
         existing row in the QoS Map Profile Table"
      ::= { adGenQosMapProfileProvisioningEntry 3}


   adGenQosMapProfileDescription OBJECT-TYPE
      SYNTAX  DisplayString (SIZE (1..80))
      MAX-ACCESS  read-create
      STATUS  current
      DESCRIPTION
        "This object is provided so that the user can describe a particular QoS Map Profile
         by any means desired"
      ::= { adGenQosMapProfileProvisioningEntry 4}

-- ******************************************************************************************
--  QosMapProfile Status Table
-- ******************************************************************************************
   adGenQosMapProfileLastInsertStatus OBJECT-TYPE
      SYNTAX  DisplayString
      MAX-ACCESS  read-only
      STATUS  current
      DESCRIPTION
         "Returns information about the last status when inserting a QoS Map Profile.
          If creation fails, the string will provide details about why the row could
          not be created.  An empty string will be returned if the last insert was
          successful."
      ::= { adGenQosMapProfileStatus 1 }


   adGenQosMapProfileMaxAllowedProfiles OBJECT-TYPE
      SYNTAX  Unsigned32
      MAX-ACCESS  read-only
      STATUS  current
      DESCRIPTION
         "Returns the maximum number of QoS Map Profiles that are allowed to be created on
         the system.  Attempting to add more than this number will result in a failure.
         After a failed insert, adGenQosMapProfileLastInsertStatus will return an error
         detailing the reason for the failure."
      ::= { adGenQosMapProfileStatus 2 }

  adGenQosMapProfileCurrentProfileCount OBJECT-TYPE
      SYNTAX  Unsigned32
      MAX-ACCESS  read-only
      STATUS  current
      DESCRIPTION
         "Returns the current number of QoS Map Profiles provisioned on the system."
      ::= { adGenQosMapProfileStatus 3 }

 adGenQosMapProfile          OBJECT IDENTIFIER ::= { adShared 83 }

END

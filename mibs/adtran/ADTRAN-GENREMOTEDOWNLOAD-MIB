ADTRAN-GENREMOTEDOWNLOAD-MIB

-- TITLE:     The ADTRAN Generic Remote Download MIB
-- PRODUCT:   ADTRAN products supporting file downloads to remote devices
-- VERSION:   1.0
-- DATE:      08/30/2010
-- AUTHOR:    Joey Boyd
-- STATUS:    PRELIMINARY

-- HISTORY:
-- 2010/08/30 jlb - STATUS: PRELIMINARY


-- ******************************************************************************************
DEFINITIONS ::= BEGIN

IMPORTS
   MODULE-IDENTITY,
   OBJECT-TYPE
      FROM SNMPv2-SMI
   ifIndex
      FROM IF-MIB
   DisplayString
      FROM SNMPv2-TC
   adGenRemoteDownload,
   adGenRemoteDownloadID
      FROM ADTRAN-SHARED-CND-SYSTEM-MIB
   ;

adGenRemoteDownloadMIB MODULE-IDENTITY
   LAST-UPDATED "201008300000Z"
   ORGANIZATION "Adtran, Inc."
   CONTACT-INFO
     "CND Tech Support
         Postal: ADTRAN, Inc.
                 901 Explorer Blvd.
                 Huntsville, AL  35806
                 Tel: +1 800 726-8663
                 Fax: +1 256 963 6217
                 E-mail: support@adtran.com"
   DESCRIPTION
      "This MIB contains OIDs for downloading files to remote devices."

::= { adGenRemoteDownloadID 1 }


--==================================================================================================================

adGenRemoteDownloadProvisioning              OBJECT IDENTIFIER ::= {adGenRemoteDownload 1}
adGenRemoteDownloadStatus                    OBJECT IDENTIFIER ::= {adGenRemoteDownload 2}

--==================================================================================================================
-- Provisioning

   adGenRemoteDownloadProvTable OBJECT-TYPE
      SYNTAX  SEQUENCE OF AdGenRemoteDownloadProvEntry
      MAX-ACCESS  not-accessible
      STATUS  current
      DESCRIPTION
         "The Remote Download Provisioning Table"
      ::= { adGenRemoteDownloadProvisioning 1 }

   adGenRemoteDownloadProvEntry OBJECT-TYPE
      SYNTAX  AdGenRemoteDownloadProvEntry
      MAX-ACCESS  not-accessible
      STATUS  current
      DESCRIPTION
         "An entry in the Remote Download Provisioning Table.  Each OID is indexed
	  using the Extended ifIndex that specifies the appropriate remote device connected to
	  a selected interface."
      INDEX   { ifIndex }
      ::= { adGenRemoteDownloadProvTable 1 }

   AdGenRemoteDownloadProvEntry  ::=
      SEQUENCE
      {
         adGenRemoteDownloadFilename		DisplayString,
         adGenRemoteDownloadInitiate            INTEGER,
	 adGenRemoteDownloadReboot		INTEGER
      }


   adGenRemoteDownloadFilename OBJECT-TYPE
      SYNTAX  DisplayString
      MAX-ACCESS  read-write
      STATUS  current
      DESCRIPTION
         "Sets the filename to be transferred to the selected remote device."
      ::= { adGenRemoteDownloadProvEntry 1 }

   adGenRemoteDownloadInitiate OBJECT-TYPE
      SYNTAX  INTEGER
	      {
               	initiate(1)
              }
      MAX-ACCESS  read-write
      STATUS  current
      DESCRIPTION
         "Initiates the transfer of the provisioned file to the selected remote device.
	  If the initiation cannot take place, a generic error will be returned and
	  adGenRemoteDownloadStatusString will be populated with the cause."
      ::= { adGenRemoteDownloadProvEntry 2 }

   adGenRemoteDownloadReboot OBJECT-TYPE
      SYNTAX  INTEGER
	      {
               	reboot(1)
              }
      MAX-ACCESS  read-write
      STATUS  current
      DESCRIPTION
         "Reboots the selected device(s)"
      ::= { adGenRemoteDownloadProvEntry 3 }

--==================================================================================================================
-- Status

   adGenRemoteDownloadStatusTable OBJECT-TYPE
      SYNTAX  SEQUENCE OF AdGenRemoteDownloadStatusEntry
      MAX-ACCESS  not-accessible
      STATUS  current
      DESCRIPTION
         "The Remote Device Status Table."
      ::= { adGenRemoteDownloadStatus 1 }

   adGenRemoteDownloadStatusEntry OBJECT-TYPE
      SYNTAX  AdGenRemoteDownloadStatusEntry
      MAX-ACCESS  not-accessible
      STATUS  current
      DESCRIPTION
         "An entry in the Remote Download Status Table.  Each OID is indexed
	  using the Extended ifIndex that specifies the appropriate remote device connected to
	  a selected interface."
      INDEX   { ifIndex }
      ::= { adGenRemoteDownloadStatusTable 1 }

   AdGenRemoteDownloadStatusEntry  ::=
      SEQUENCE {
	 adGenRemoteDownloadStatusSummary	INTEGER,
         adGenRemoteDownloadStatusString	DisplayString
      }

   adGenRemoteDownloadStatusSummary OBJECT-TYPE
      SYNTAX  INTEGER
	      {
		idle(1),
		inProgress(2),
		error(3),
		success(4)
	      }

      MAX-ACCESS  read-only
      STATUS  current
      DESCRIPTION
         "Returns a general summary of the file download.  Further details can be obtained via adGenRemoteDownloadStatusString."
      ::= { adGenRemoteDownloadStatusEntry 1 }

   adGenRemoteDownloadStatusString OBJECT-TYPE
      SYNTAX  DisplayString
      MAX-ACCESS  read-only
      STATUS  current
      DESCRIPTION
         "Returns the current status of the download including errors encountered during initiation."
      ::= { adGenRemoteDownloadStatusEntry 2 }



END

ADTRAN-GENSIP-MIB

-- TITLE:     The ADTRAN Generic SIP MIB
-- PRODUCT:   TA5000, TA1100, TA1200, TA3xx
-- VERSION:   1.0
-- DATE:      10/06/09
-- AUTHOR:    Jason Brock, Peter Kerr, and Peter Som de Cerff
-- STATUS:    PRELIMINARY

-- This MIB defines the object identifiers (OIDs) for the
-- ADTRAN GENSIP entities.

-- "DO NOT MAKE HISTORY COMMENTS HERE!!!! Revision history now in REVISION/DESCRIPTION clauses below"

-- *****************************************************************************
DEFINITIONS ::= BEGIN

IMPORTS

   adGenSip,
   adGenSipID
      FROM ADTRAN-SHARED-CND-SYSTEM-MIB

   OBJECT-TYPE,
   MODULE-IDENTITY,
   Integer32,
   Unsigned32
      FROM SNMPv2-SMI

   DisplayString,
   RowStatus,
   TruthValue
      FROM SNMPv2-TC

   ifIndex
      FROM IF-MIB

   AdGenVoipTrunkName,
   AdGenVoipUserNumber
      FROM ADTRAN-GENVOIP-MIB
   ;

adGenSipIdentity MODULE-IDENTITY
   LAST-UPDATED "201804110000Z"
   ORGANIZATION "Adtran, Inc."
   CONTACT-INFO
     "CND Tech Support
         Postal: ADTRAN, Inc.
                 901 Explorer Blvd.
                 Huntsville, AL  35806
                 Tel: +1 800 726-8663
                 Fax: +1 256 963 6217
                 E-mail: support@adtran.com"
   DESCRIPTION
      "This MIB defines the objects for SIP management."

   REVISION "201804110000Z"
   DESCRIPTION "Added support for adGenSipTrunkGrammarAddressScheme."
   REVISION "201105040000Z"
   DESCRIPTION "Added support to force/clear registration and report registration
                status with the voice gateway."
   REVISION "201012220000Z"
   DESCRIPTION "Added support for setting trunk SIP msg DSCP value and RTP msg DSCP
                values, adGenSipTrunkSipDscp, adGenSipTrunkRtpDscp"
   REVISION "200910060000Z"
   DESCRIPTION "Created"
::= { adGenSipID 1 }

--==============================================================================
-- PROVISIONING
--==============================================================================

adGenSipProvisioning                OBJECT IDENTIFIER ::= {adGenSip 1}

-- *****************************************************************************
-- Groups in Voip Provisioning
-- *****************************************************************************

adGenSipTrunkProv             OBJECT IDENTIFIER  ::= { adGenSipProvisioning 1 }
adGenSipIdentityProv          OBJECT IDENTIFIER  ::= { adGenSipProvisioning 2 }


--******************************************************************************
-- This table is for SIP trunk provisioning.
--******************************************************************************

adGenSipTrunkProvCurrentNumber OBJECT-TYPE
   SYNTAX      Integer32
   MAX-ACCESS  read-only
   STATUS      current
   DESCRIPTION
     "Current number of SIP trunks defined."
   ::= { adGenSipTrunkProv 1 }

adGenSipTrunkProvLastCreateError OBJECT-TYPE
   SYNTAX      DisplayString
   MAX-ACCESS  read-only
   STATUS      current
   DESCRIPTION
     "The reason for the last error that occured while attempting to create
      an entry in the SIP trunk provisioning table (adGenSipTrunkProvTable)."
   ::= { adGenSipTrunkProv 2 }

adGenSipTrunkProvTable OBJECT-TYPE
   SYNTAX      SEQUENCE OF AdGenSipTrunkProvEntry
   MAX-ACCESS  not-accessible
   STATUS      current
   DESCRIPTION
     "This table supports provisioning of SIP trunk parameters for the SIP
      engine. Used in conjunction with adGenVoipTrunkProvTable."
   ::= { adGenSipTrunkProv 3 }

adGenSipTrunkProvEntry OBJECT-TYPE
   SYNTAX      AdGenSipTrunkProvEntry
   MAX-ACCESS  not-accessible
   STATUS      current
   DESCRIPTION
     "An entry in the adGenSipTrunkProvTable."
   INDEX { adGenSipTrunkEntryIndex }
   ::= { adGenSipTrunkProvTable 1 }

AdGenSipTrunkProvEntry ::=
   SEQUENCE
   {
      adGenSipTrunkEntryIndex                      AdGenVoipTrunkName,
      adGenSipTrunkRowStatus                       RowStatus,
      adGenSipTrunkLastErrorString                 DisplayString,

      adGenSipTrunkSipProxyPrimary                 DisplayString,
      adGenSipTrunkSipProxyPrimaryUdp              Integer32,
      adGenSipTrunkSipProxySecondary               DisplayString,
      adGenSipTrunkSipProxySecondaryUdp            Integer32,

      adGenSipTrunkSipOutboundProxyPrimary         DisplayString,
      adGenSipTrunkSipOutboundProxyPrimaryUdp      Integer32,
      adGenSipTrunkSipOutboundProxySecondary       DisplayString,
      adGenSipTrunkSipOutboundProxySecondaryUdp    Integer32,

      adGenSipTrunkSipDomain                       DisplayString,
      adGenSipTrunkSipTrustDomain                  TruthValue,
      adGenSipTrunkSipTrustDomainPAssertedIdReq    TruthValue,

      adGenSipTrunkSipAuthenticate                 TruthValue,

      adGenSipTrunkSipDialStringSource             INTEGER,

      adGenSipTrunkSipKeepAliveMethod              INTEGER,
      adGenSipTrunkSipKeepAliveInterval            Integer32,

      adGenSipTrunkTimerRegFailRetry               Integer32,
      adGenSipTrunkTimerRollover                   Integer32,

      adGenSipTrunkPrivacy                         TruthValue,

      adGenSipTrunkGrammarRequestUriResolve        TruthValue,
      adGenSipTrunkGrammarRequestUriHost           INTEGER,
      adGenSipTrunkGrammarFromHost                 INTEGER,
      adGenSipTrunkGrammarFromUser                 INTEGER,
      adGenSipTrunkGrammarPAssertedIdHost          INTEGER,
      adGenSipTrunkGrammarToHost                   INTEGER,
      adGenSipTrunkGrammarAlertInfoUrl             DisplayString,
      adGenSipTrunkGrammarSupported100Rel          TruthValue,
      adGenSipTrunkGrammarProxyRequirePrivacy      TruthValue,
      adGenSipTrunkGrammarRequire100rel            TruthValue,
      adGenSipTrunkGrammarUserAgent                DisplayString,
      adGenSipTrunkGrammarSdpHold                  INTEGER,

      adGenSipTrunkSipRegistrarPrimary             DisplayString,
      adGenSipTrunkSipRegistrarPrimaryUdp          Integer32,
      adGenSipTrunkSipRegistrarSecondary           DisplayString,
      adGenSipTrunkSipRegistrarSecondaryUdp        Integer32,

      adGenSipTrunkSipRegistrarThresholdType       INTEGER,
      adGenSipTrunkSipRegistrarThresholdValue      Integer32,
      adGenSipTrunkSipRegistrarMaxConcurrentReg    Integer32,
      adGenSipTrunkSipRegistrarExpireTime          Integer32,
      adGenSipTrunkSipRegistrarRequireExpires      TruthValue,
      adGenSipTrunkSipDscp						   Integer32,
      adGenSipTrunkRtpDscp                         Integer32,
      adGenSipTrunkGrammarAddressScheme            INTEGER
    }

adGenSipTrunkEntryIndex OBJECT-TYPE
   SYNTAX      AdGenVoipTrunkName
   MAX-ACCESS  not-accessible
   STATUS      current
   DESCRIPTION
     "The name of the SIP trunk. OIDs from adGenVoipTrunkProvTable are addressed
      using the same index string."
   ::= { adGenSipTrunkProvEntry 1 }

adGenSipTrunkRowStatus OBJECT-TYPE
   SYNTAX       RowStatus
   MAX-ACCESS   read-create
   STATUS       current
   DESCRIPTION
     "This object is used to create a new row or modify or delete an existing
      row in this table."
   ::= { adGenSipTrunkProvEntry 2 }

adGenSipTrunkLastErrorString OBJECT-TYPE
   SYNTAX       DisplayString
   MAX-ACCESS   read-only
   STATUS       current
   DESCRIPTION
     "The reason for the last error that occured while attempting to create an
      entry in the SIP Trunk Prov Table."
   ::= { adGenSipTrunkProvEntry 3 }

adGenSipTrunkSipProxyPrimary OBJECT-TYPE
   SYNTAX      DisplayString
   MAX-ACCESS  read-create
   STATUS      current
   DESCRIPTION
     "The primary SIP proxy server's IP address or host name."
   ::= { adGenSipTrunkProvEntry 4 }

adGenSipTrunkSipProxyPrimaryUdp OBJECT-TYPE
   SYNTAX      Integer32 (0..65535)
   MAX-ACCESS  read-create
   STATUS      current
   DESCRIPTION
     "The primary SIP proxy server's UDP port."
   ::= { adGenSipTrunkProvEntry 5 }

adGenSipTrunkSipProxySecondary OBJECT-TYPE
   SYNTAX      DisplayString
   MAX-ACCESS  read-create
   STATUS      current
   DESCRIPTION
     "The secondary SIP proxy server's IP address or host name."
   ::= { adGenSipTrunkProvEntry 6 }

adGenSipTrunkSipProxySecondaryUdp OBJECT-TYPE
   SYNTAX      Integer32 (0..65535)
   MAX-ACCESS  read-create
   STATUS      current
   DESCRIPTION
     "The secondary SIP proxy server's UDP port."
   ::= { adGenSipTrunkProvEntry 7 }

adGenSipTrunkSipOutboundProxyPrimary OBJECT-TYPE
   SYNTAX      DisplayString
   MAX-ACCESS  read-create
   STATUS      current
   DESCRIPTION
     "The primary SIP outbound proxy server's IP address or host name."
   ::= { adGenSipTrunkProvEntry 8 }

adGenSipTrunkSipOutboundProxyPrimaryUdp OBJECT-TYPE
   SYNTAX      Integer32 (0..65535)
   MAX-ACCESS  read-create
   STATUS      current
   DESCRIPTION
     "The primary SIP outbound proxy server's UDP port."
   ::= { adGenSipTrunkProvEntry 9 }

adGenSipTrunkSipOutboundProxySecondary OBJECT-TYPE
   SYNTAX      DisplayString
   MAX-ACCESS  read-create
   STATUS      current
   DESCRIPTION
     "The secondary SIP outbound proxy server's IP address or host name."
   ::= { adGenSipTrunkProvEntry 10 }

adGenSipTrunkSipOutboundProxySecondaryUdp OBJECT-TYPE
   SYNTAX      Integer32 (0..65535)
   MAX-ACCESS  read-create
   STATUS      current
   DESCRIPTION
     "The secondary SIP outbound proxy server's UDP port."
   ::= { adGenSipTrunkProvEntry 11 }

adGenSipTrunkSipDomain OBJECT-TYPE
   SYNTAX      DisplayString (SIZE(1..80))
   MAX-ACCESS  read-create
   STATUS      current
   DESCRIPTION
     "Configure the assigned domain name for host messages. The domain is an
      unique identifier for the SIP users on the trunk."
   ::= { adGenSipTrunkProvEntry 12 }

adGenSipTrunkSipTrustDomain OBJECT-TYPE
   SYNTAX      TruthValue
   MAX-ACCESS  read-create
   STATUS      current
   DESCRIPTION
     "Set to add security measures for users' identity and privacy by connecting
      the trunk to a trusted domain. The system supports RFC 3323 and RFC 3325."
   ::= { adGenSipTrunkProvEntry 13 }

adGenSipTrunkSipTrustDomainPAssertedIdReq OBJECT-TYPE
   SYNTAX      TruthValue
   MAX-ACCESS  read-create
   STATUS      current
   DESCRIPTION
     "Set to Require the use of P-Asserted-Identity SIP privacy for this trusted
      domain"
   ::= { adGenSipTrunkProvEntry 14 }

adGenSipTrunkSipAuthenticate OBJECT-TYPE
   SYNTAX      TruthValue
   MAX-ACCESS  read-create
   STATUS      current
   DESCRIPTION
     "Set to enable SIP server authentication."
   ::= { adGenSipTrunkProvEntry 15 }

adGenSipTrunkSipDialStringSource OBJECT-TYPE
   SYNTAX      INTEGER {
                  requestUri(1),
                  to(2)
                  }
   MAX-ACCESS  read-create
   STATUS      current
   DESCRIPTION
     "Use to specify the dial-string source for the SIP server.
         1 = requestUri    Specifies the Request-URI user field as the
                           dial-string source.
         2 = to            Specifies the To header as the dial-string source."
   ::= { adGenSipTrunkProvEntry 16 }

adGenSipTrunkSipKeepAliveMethod OBJECT-TYPE
   SYNTAX      INTEGER {
                  none(1),
                  info(2),
                  options(3)
                  }
   MAX-ACCESS  read-create
   STATUS      current
   DESCRIPTION
     "The keep-alive method to use for SIP registrar connections."
   ::= { adGenSipTrunkProvEntry 17 }

adGenSipTrunkSipKeepAliveInterval OBJECT-TYPE
   SYNTAX       Integer32 (30..3600)
   MAX-ACCESS   read-create
   STATUS       current
   DESCRIPTION
     "The interval between keep alive messages."
   ::= { adGenSipTrunkProvEntry 18 }

adGenSipTrunkTimerRegFailRetry OBJECT-TYPE
   SYNTAX      Integer32 (10..604800)
   MAX-ACCESS  read-create
   STATUS      current
   DESCRIPTION
     "Used to configure the time (in seconds) that will elapse before a SIP
      endpoint will retry registration with the SIP server after a registration
      failure has occurred."
   ::= { adGenSipTrunkProvEntry 19 }

adGenSipTrunkTimerRollover OBJECT-TYPE
   SYNTAX      Integer32 (1..32)
   MAX-ACCESS  read-create
   STATUS      current
   DESCRIPTION
     "Sets the SIP 'timer B' value for Invite transactions originating from a
     SIP trunk. If there is no response after the timer expires, the SIP trunk
     will attempt to send Invite messages to the highest priority backup SIP
     server. As long as the SIP trunk does not receive a response, it will
     continue this cycle until it has attempted to contact all the SIP servers."
   ::= { adGenSipTrunkProvEntry 20 }

adGenSipTrunkPrivacy OBJECT-TYPE
   SYNTAX      TruthValue
   MAX-ACCESS  read-create
   STATUS      current
   DESCRIPTION
     "Specify outbound calls to include privacy headers (when configured) and
      inbound calls to be filtered on privacy settings."
   ::= { adGenSipTrunkProvEntry 21 }

adGenSipTrunkGrammarRequestUriResolve OBJECT-TYPE
   SYNTAX      TruthValue
   MAX-ACCESS  read-create
   STATUS      current
   DESCRIPTION
     "Enables the local unit to resolve the domain before resolving the request
      uniform resource identifier (URI)"
   ::= { adGenSipTrunkProvEntry 22 }

adGenSipTrunkGrammarRequestUriHost OBJECT-TYPE
   SYNTAX      INTEGER {
                  sipOutboundProxy(1),
                  sipProxy(2),
                  domain(3)
                  }
   MAX-ACCESS  read-create
   STATUS      current
   DESCRIPTION
     "Used to format the Request uniform resource identifier (URI) for SIP
      messages."
   ::= { adGenSipTrunkProvEntry 23 }

adGenSipTrunkGrammarFromHost OBJECT-TYPE
   SYNTAX      INTEGER {
                  outboundProxy(1),
                  proxy(2),
                  domain(3),
                  local(4)
                  }
   MAX-ACCESS  read-create
   STATUS      current
   DESCRIPTION
     "Specifies the Host field formatting for the From header."
   ::= { adGenSipTrunkProvEntry 24 }

adGenSipTrunkGrammarFromUser OBJECT-TYPE
   SYNTAX      INTEGER {
                  domestic(1),
                  international(2)
                  }
   MAX-ACCESS  read-create
   STATUS      current
   DESCRIPTION
     "Specifies the User field formatting for the From header."
   ::= { adGenSipTrunkProvEntry 25 }

adGenSipTrunkGrammarPAssertedIdHost OBJECT-TYPE
   SYNTAX      INTEGER {
                  outboundProxy(1),
                  proxy(2),
                  domain(3),
                  local(4)
                  }
   MAX-ACCESS  read-create
   STATUS      current
   DESCRIPTION
     "Set to configure the P-Asserted Identity header host format for the SIP
      trunk."
   ::= { adGenSipTrunkProvEntry 26 }

adGenSipTrunkGrammarToHost OBJECT-TYPE
   SYNTAX      INTEGER {
                  server(1),
                  domain(2)
                  }
   MAX-ACCESS  read-create
   STATUS      current
   DESCRIPTION
     "Used to configure the To header host format of SIP trunk messages."
   ::= { adGenSipTrunkProvEntry 27 }

adGenSipTrunkGrammarAlertInfoUrl OBJECT-TYPE
   SYNTAX      DisplayString
   MAX-ACCESS  read-create
   STATUS      current
   DESCRIPTION
     "Specifies the Alert-Info HyperText Transfer Protocol (HTTP) universal
      resource locator (URL) header format."
   ::= { adGenSipTrunkProvEntry 28 }

adGenSipTrunkGrammarSupported100Rel OBJECT-TYPE
   SYNTAX      TruthValue
   MAX-ACCESS  read-create
   STATUS      current
   DESCRIPTION
     "Set to include 100rel in the supported header of the SIP trunk message."
   ::= { adGenSipTrunkProvEntry 29 }

adGenSipTrunkGrammarProxyRequirePrivacy OBJECT-TYPE
   SYNTAX      TruthValue
   MAX-ACCESS  read-create
   STATUS      current
   DESCRIPTION
     "Used to add privacy to Proxy-Require header format for the SIP trunk."
   ::= { adGenSipTrunkProvEntry 30 }

adGenSipTrunkGrammarRequire100rel OBJECT-TYPE
   SYNTAX      TruthValue
   MAX-ACCESS  read-create
   STATUS      current
   DESCRIPTION
     "This object is used to add 100rel to the Require header of a SIP
      provisional response, thereby enabling or disabling the sending of
      reliable provisional responses to clients that support 100rel.  Reliable
      provisional responses will always be sent to clients that require 100rel
      even if this is set to disabled."
   ::= { adGenSipTrunkProvEntry 31 }

adGenSipTrunkGrammarUserAgent OBJECT-TYPE
   SYNTAX      DisplayString (SIZE(1..128))
   MAX-ACCESS  read-create
   STATUS      current
   DESCRIPTION
     "Uses to configure the user agent header format in SIP messages.  To
      prevent the insertion of a user agent field in SIP messages set this
      object to an emptry string."
   ::= { adGenSipTrunkProvEntry 32 }

adGenSipTrunkGrammarSdpHold OBJECT-TYPE
   SYNTAX      INTEGER {
                  rfc2543(1),
                  rfc3264(2)
                  }
   MAX-ACCESS  read-create
   STATUS      current
   DESCRIPTION
     "Used to specify which RFC to use for formatting hold messages in SDP
      announcements."
   ::= { adGenSipTrunkProvEntry 33 }

adGenSipTrunkSipRegistrarPrimary OBJECT-TYPE
   SYNTAX      DisplayString
   MAX-ACCESS  read-create
   STATUS      current
   DESCRIPTION
     "The primary SIP Registrar server's IP address or host name."
   ::= { adGenSipTrunkProvEntry 34 }

adGenSipTrunkSipRegistrarPrimaryUdp OBJECT-TYPE
   SYNTAX      Integer32 (0..65535)
   MAX-ACCESS  read-create
   STATUS      current
   DESCRIPTION
     "The primary SIP Registrar server's UDP port."
   ::= { adGenSipTrunkProvEntry 35 }

adGenSipTrunkSipRegistrarSecondary OBJECT-TYPE
   SYNTAX      DisplayString
   MAX-ACCESS  read-create
   STATUS      current
   DESCRIPTION
     "The secondary SIP Registrar server's IP address or host name."
   ::= { adGenSipTrunkProvEntry 36 }

adGenSipTrunkSipRegistrarSecondaryUdp OBJECT-TYPE
   SYNTAX      Integer32 (0..65535)
   MAX-ACCESS  read-create
   STATUS      current
   DESCRIPTION
     "The secondary SIP Registrar server's UDP port."
   ::= { adGenSipTrunkProvEntry 37 }

adGenSipTrunkSipRegistrarThresholdType OBJECT-TYPE
   SYNTAX      INTEGER {
                  percentage(1),
                  absolute(2)
                  }
   MAX-ACCESS  read-create
   STATUS      current
   DESCRIPTION
     "Used to configure when the Session Initiation Protocol (SIP) trunk
      registration will be renewed.
         1 = percentage    Configures the threshold time as a percentage of the
                           returned valid registration time.
         2 = absolute      Configures an absolute threshold time in seconds."
   ::= { adGenSipTrunkProvEntry 38 }

adGenSipTrunkSipRegistrarThresholdValue OBJECT-TYPE
   SYNTAX      Integer32 (1..604800)
   MAX-ACCESS  read-create
   STATUS      current
   DESCRIPTION
     "Used to configure when the Session Initiation Protocol (SIP) trunk
      registration will be renewed.
         Valid range is 30 to 604800 seconds when SipRegistrarThresholdType is
         set to absolute, or 1 to 90 percent when set to percent."
   ::= { adGenSipTrunkProvEntry 39 }

adGenSipTrunkSipRegistrarMaxConcurrentReg OBJECT-TYPE
   SYNTAX      Integer32 (1..32)
   MAX-ACCESS  read-create
   STATUS      current
   DESCRIPTION
     "Used to control the maximum number of simultaneous registrations that are
      allowed. This value can be adjusted to help eliminate congestion caused by
      too many concurrent registrations."
   ::= { adGenSipTrunkProvEntry 40 }

adGenSipTrunkSipRegistrarExpireTime OBJECT-TYPE
   SYNTAX      Integer32 (0..2147483647)
   MAX-ACCESS  read-create
   STATUS      current
   DESCRIPTION
     "Used to define the Session Initiation Protocol (SIP) expiration time for
      registration."
   ::= { adGenSipTrunkProvEntry 41 }

adGenSipTrunkSipRegistrarRequireExpires OBJECT-TYPE
   SYNTAX      TruthValue
   MAX-ACCESS  read-create
   STATUS      current
   DESCRIPTION
     "When enabled, a response to a register must contain an expires header or
     the response will be considered a failure. When disabled, a successful
     response does not require an expires header."
   ::= { adGenSipTrunkProvEntry 42 }

adGenSipTrunkSipDscp OBJECT-TYPE
   SYNTAX      Integer32 (0..63)
   MAX-ACCESS  read-create
   STATUS      current
   DESCRIPTION
     "Used to set the Differentiated Services Code Point in the IP header for
     the SIP protocol messages. Valid values defined in RFC2474."
   ::= { adGenSipTrunkProvEntry 43 }

adGenSipTrunkRtpDscp OBJECT-TYPE
   SYNTAX      Integer32 (0..63)
   MAX-ACCESS  read-create
   STATUS      current
   DESCRIPTION
     "Used to set the Differentiated Services Code Point in the IP header for
     the RTP protocol messages. Valid values defined in RFC2474."
   ::= { adGenSipTrunkProvEntry 44 }

adGenSipTrunkGrammarAddressScheme OBJECT-TYPE
   SYNTAX      INTEGER {
                  sipUri(1),
                  telUri(2)
                  }
   MAX-ACCESS  read-create
   STATUS      current
   DESCRIPTION
     "Used to provision the protocol scheme used in the uniform resource identier (URI) for SIP messages."
   DEFVAL      { sipUri }
   ::= { adGenSipTrunkProvEntry 45 }

--==============================================================================

--******************************************************************************
-- This table is for SIP identity provisioning.
--******************************************************************************

adGenSipIdentityProvCurrentNumber OBJECT-TYPE
   SYNTAX      Integer32
   MAX-ACCESS  read-only
   STATUS      current
   DESCRIPTION
     "Current number of SIP identities defined. Note that this is the total for
      the system. To find the number of identities per user, use the
      adGenVoipUserNumIdentities OID from the adGenVoipUserProvTable table. To
      find the number of identies on a specific trunk, walk the table with the
      trunk index fixed."
   ::= { adGenSipIdentityProv 1 }

adGenSipIdentityProvLastCreateError OBJECT-TYPE
   SYNTAX      DisplayString
   MAX-ACCESS  read-only
   STATUS      current
   DESCRIPTION
     "The reason for the last error that occured while attempting to create
      an entry in the SIP identity provisioning table
      (adGenSipIdentityProvTable)."
   ::= { adGenSipIdentityProv 2 }

adGenSipIdentityProvTable OBJECT-TYPE
   SYNTAX      SEQUENCE OF AdGenSipIdentityProvEntry
   MAX-ACCESS  not-accessible
   STATUS      current
   DESCRIPTION
     "This table supports provisioning of the SIP identity parameters for a SIP
      user. It is indexed by the trunk and identity. It is attached to a
      specific user through an entry in the table.
      All entries except the user are optional. However, no entries can be
      changed at any time other than the row's creation. To change provisioning
      of an existing identity, destroy the row and recreate."
   ::= { adGenSipIdentityProv 3 }

adGenSipIdentityProvEntry OBJECT-TYPE
   SYNTAX      AdGenSipIdentityProvEntry
   MAX-ACCESS  not-accessible
   STATUS      current
   DESCRIPTION
     "An entry in the adGenSipIdentityProvTable."
   INDEX { adGenSipIdentityUserIndex,
           adGenSipIdentityTrunkIndex,
           IMPLIED adGenSipIdentityEntryIndex }
   ::= { adGenSipIdentityProvTable 1 }

AdGenSipIdentityProvEntry ::=
   SEQUENCE
   {
      adGenSipIdentityUserIndex                    AdGenVoipUserNumber,
      adGenSipIdentityTrunkIndex                   AdGenVoipTrunkName,
      adGenSipIdentityEntryIndex                   DisplayString,
      adGenSipIdentityRowStatus                    RowStatus,
      adGenSipIdentityLastErrorString              DisplayString,

      adGenSipIdentityRegister                     TruthValue,
      adGenSipIdentityAuthName                     DisplayString,
      adGenSipIdentityPassword                     DisplayString
   }

adGenSipIdentityUserIndex OBJECT-TYPE
   SYNTAX      AdGenVoipUserNumber
   MAX-ACCESS  not-accessible
   STATUS      current
   DESCRIPTION
     "The name of the VoIP user to which this identity is applied. (The same as
      the index from adGenVoipUserProvTable.)"
   ::= { adGenSipIdentityProvEntry 1 }

adGenSipIdentityTrunkIndex OBJECT-TYPE
   SYNTAX      AdGenVoipTrunkName
   MAX-ACCESS  not-accessible
   STATUS      current
   DESCRIPTION
     "The name of the SIP trunk to which this identity is applied. (The same as
      the index from adGenSipTrunkProvTable.)"
   ::= { adGenSipIdentityProvEntry 2 }

adGenSipIdentityEntryIndex OBJECT-TYPE
   SYNTAX      DisplayString (SIZE(1..80))
   MAX-ACCESS  not-accessible
   STATUS      current
   DESCRIPTION
     "A string identifying the user on the SIP server. It may not contain any
      of the following characters: `@^[]{}\|:<>? <space> <quotation mark>."
   ::= { adGenSipIdentityProvEntry 3 }

adGenSipIdentityRowStatus OBJECT-TYPE
   SYNTAX      RowStatus
   MAX-ACCESS  read-create
   STATUS      current
   DESCRIPTION
     "This object is used to create a new row or modify or delete an existing
      row in this table."
   ::= { adGenSipIdentityProvEntry 4 }

adGenSipIdentityLastErrorString OBJECT-TYPE
   SYNTAX      DisplayString
   MAX-ACCESS  read-only
   STATUS      current
   DESCRIPTION
     "The reason for the last error that occured while attempting to create an
      entry in the SIP Identity Table."
   ::= { adGenSipIdentityProvEntry 5 }

adGenSipIdentityRegister OBJECT-TYPE
   SYNTAX      TruthValue
   MAX-ACCESS  read-create
   STATUS      current
   DESCRIPTION
     "Set to true to allow the user to register with the SIP server."
   ::= { adGenSipIdentityProvEntry 6 }

adGenSipIdentityAuthName OBJECT-TYPE
   SYNTAX      DisplayString (SIZE(1..80))
   MAX-ACCESS  read-create
   STATUS      current
   DESCRIPTION
     "The user's Authorization Name"
   ::= { adGenSipIdentityProvEntry 7 }

adGenSipIdentityPassword OBJECT-TYPE
   SYNTAX      DisplayString (SIZE(1..80))
   MAX-ACCESS  read-create
   STATUS      current
   DESCRIPTION
     "The User's password"
   ::= { adGenSipIdentityProvEntry 8 }

--==============================================================================
-- Management actions
--==============================================================================

adGenSipMgmnt                OBJECT IDENTIFIER ::= {adGenSip 2}

-- *****************************************************************************
-- Groups in management actions
-- *****************************************************************************

adGenSipMgmntActions             OBJECT IDENTIFIER  ::= { adGenSipMgmnt 1 }

--******************************************************************************
-- This table is for SIP management.
--******************************************************************************

adGenSipMgmntTable OBJECT-TYPE
   SYNTAX      SEQUENCE OF AdGenSipMgmntEntry
   MAX-ACCESS  not-accessible
   STATUS      current
   DESCRIPTION
     "This table supports actions for maintenance."
   ::= { adGenSipMgmntActions 1 }

adGenSipMgmntEntry OBJECT-TYPE
   SYNTAX      AdGenSipMgmntEntry
   MAX-ACCESS  not-accessible
   STATUS      current
   DESCRIPTION
     "An entry in the adGenSipMgmntTable."
   INDEX {ifIndex,  -- This is the device-level index.
   		  adGenSipMgmntTrunkIndex,
   		  IMPLIED adGenSipMgmntIdentityIndex }
   ::= { adGenSipMgmntTable 1 }

AdGenSipMgmntEntry ::=
   SEQUENCE
   {
      adGenSipMgmntTrunkIndex                 AdGenVoipTrunkName,
      adGenSipMgmntIdentityIndex              DisplayString,

      adGenSipMgmntForceReg                   INTEGER,
      adGenSipMgmntClearReg                   INTEGER
   }

adGenSipMgmntTrunkIndex OBJECT-TYPE
   SYNTAX      AdGenVoipTrunkName
   MAX-ACCESS  not-accessible
   STATUS      current
   DESCRIPTION
     "The name of the SIP trunk to which this identity is applied. (The same as
      the index from adGenSipTrunkProvTable.)"
   ::= { adGenSipMgmntEntry 1 }

adGenSipMgmntIdentityIndex OBJECT-TYPE
   SYNTAX      DisplayString (SIZE(1..80))
   MAX-ACCESS  not-accessible
   STATUS      current
   DESCRIPTION
     "A string identifying the user on the SIP server. It may not contain any
      of the following characters: `@^[]{}\|:<>? <space> <quotation mark>."
   ::= { adGenSipMgmntEntry 2 }

adGenSipMgmntForceReg OBJECT-TYPE
   SYNTAX     	INTEGER	{
                    force(1)
                    }
   MAX-ACCESS  read-write
   STATUS      current
   DESCRIPTION
     "Write any value to this object to force SIP identity to send a
      registration message to the gateway provider. Reads always return 1"
   ::= { adGenSipMgmntEntry 3 }

adGenSipMgmntClearReg OBJECT-TYPE
   SYNTAX     	INTEGER {
                    clear(1)
                    }
   MAX-ACCESS  read-write
   STATUS      current
   DESCRIPTION
     "Write any value to this object to clear registration of a SIP identity
      with the gateway provider. Reads always return 1"
   ::= { adGenSipMgmntEntry 4 }

--==============================================================================
-- Status
--==============================================================================

adGenSipStatus                OBJECT IDENTIFIER ::= {adGenSip 3}

-- *****************************************************************************
-- Groups in Voip Provisioning
-- *****************************************************************************

adGenSipStatusRegistration             OBJECT IDENTIFIER  ::= { adGenSipStatus 1 }

--******************************************************************************
-- This table is for SIP user registration status.
--******************************************************************************
adGenSipStatusRegistrationTable OBJECT-TYPE
   SYNTAX      SEQUENCE OF AdGenSipStatusRegistrationEntry
   MAX-ACCESS  not-accessible
   STATUS      current
   DESCRIPTION
     "This table supports user registration status with the voice gateway provider."
   ::= { adGenSipStatusRegistration 1 }

adGenSipStatusRegistrationEntry OBJECT-TYPE
   SYNTAX      AdGenSipStatusRegistrationEntry
   MAX-ACCESS  not-accessible
   STATUS      current
   DESCRIPTION
     "An entry in the adGenSipStatusRegistrationTable."
   INDEX {ifIndex,  -- This is the device-level index.
   		  adGenSipRegistrationTrunkIndex,
   		  IMPLIED adGenSipRegistrationIdentityIndex }
   ::= { adGenSipStatusRegistrationTable 1 }

AdGenSipStatusRegistrationEntry ::=
   SEQUENCE
   {
      adGenSipRegistrationTrunkIndex               AdGenVoipTrunkName,
      adGenSipRegistrationIdentityIndex            DisplayString,

      adGenSipStatusRegistrationStatus             INTEGER,
      adGenSipStatusRegistrationGrant              Unsigned32,
      adGenSipStatusRegistrationExpires            Unsigned32,
      adGenSipStatusRegistrationSuccess            Unsigned32,
      adGenSipStatusRegistrationFail               Unsigned32,
      adGenSipStatusRegistrationRequests           Unsigned32,
      adGenSipStatusRegistrationChallenges         Unsigned32,
      adGenSipStatusRegistrationRollovers          Unsigned32
   }

adGenSipRegistrationTrunkIndex OBJECT-TYPE
   SYNTAX      AdGenVoipTrunkName
   MAX-ACCESS  not-accessible
   STATUS      current
   DESCRIPTION
     "The name of the SIP trunk to which this identity is applied. (The same as
      the index from adGenSipTrunkProvTable.)"
   ::= { adGenSipStatusRegistrationEntry 1 }

adGenSipRegistrationIdentityIndex OBJECT-TYPE
   SYNTAX      DisplayString (SIZE(1..80))
   MAX-ACCESS  not-accessible
   STATUS      current
   DESCRIPTION
     "A string identifying the user on the SIP server. It may not contain any
      of the following characters: `@^[]{}\|:<>? <space> <quotation mark>."
   ::= { adGenSipStatusRegistrationEntry 2 }

adGenSipStatusRegistrationStatus OBJECT-TYPE
   SYNTAX      INTEGER {
                  yes(1),
                  no(2)
                  }
   MAX-ACCESS  read-only
   STATUS      current
   DESCRIPTION
     "A value showing the SIP identities registration status with the
     gateway provider.
         1 = Yes, the SIP identity is registered.
         2 = No, the SIP identity is NOT registered."
   ::= { adGenSipStatusRegistrationEntry 3 }

adGenSipStatusRegistrationGrant OBJECT-TYPE
   SYNTAX      Unsigned32
   MAX-ACCESS  read-only
   STATUS      current
   DESCRIPTION
     "A value representing the periodic time in seconds that a registration
     is valid."
   ::= { adGenSipStatusRegistrationEntry 4 }

adGenSipStatusRegistrationExpires OBJECT-TYPE
   SYNTAX      Unsigned32
   MAX-ACCESS  read-only
   STATUS      current
   DESCRIPTION
     "A value representing the time in seconds remaining that a registration
     is valid."
   ::= { adGenSipStatusRegistrationEntry 5 }

adGenSipStatusRegistrationSuccess OBJECT-TYPE
   SYNTAX      Unsigned32
   MAX-ACCESS  read-only
   STATUS      current
   DESCRIPTION
     "A counter of the number of successfull registrations."
   ::= { adGenSipStatusRegistrationEntry 6 }

adGenSipStatusRegistrationFail OBJECT-TYPE
   SYNTAX      Unsigned32
   MAX-ACCESS  read-only
   STATUS      current
   DESCRIPTION
     "A counter of the number of failed registrations."
   ::= { adGenSipStatusRegistrationEntry 7 }

adGenSipStatusRegistrationRequests OBJECT-TYPE
   SYNTAX      Unsigned32
   MAX-ACCESS  read-only
   STATUS      current
   DESCRIPTION
     "A counter of the number of registration requests."
   ::= { adGenSipStatusRegistrationEntry 8 }

adGenSipStatusRegistrationChallenges OBJECT-TYPE
   SYNTAX      Unsigned32
   MAX-ACCESS  read-only
   STATUS      current
   DESCRIPTION
     "A counter of the number of registration challenges."
   ::= { adGenSipStatusRegistrationEntry 9 }

adGenSipStatusRegistrationRollovers OBJECT-TYPE
   SYNTAX      Unsigned32
   MAX-ACCESS  read-only
   STATUS      current
   DESCRIPTION
     "A counter of the number of registration rollovers from
     primary to secondary gateway."
   ::= { adGenSipStatusRegistrationEntry 10 }
END

ADTRAN-GENSLOT2-MIB   DEFINITIONS ::= BEGIN

     -- TITLE:       Generic chassis slot MIB extension
     -- PRODUCT:     All chassis type products
     -- VERSION:     1.0
     -- DATE:        2007/05/18
     -- AUTHOR:      Arthur Poleon
     -- SNMP:        SNMPv1
     -- MIB ARC:     adtran.adShared.adGenericShelves.adGenSlot

     -- HISTORY:
     --

     IMPORTS

          OBJECT-TYPE, MODULE-IDENTITY
               FROM SNMPv2-SMI
          DisplayString
               FROM SNMPv2-TC
          adGenSlotInfoIndex,  adGenSlot
               FROM ADTRAN-GENSLOT-MIB;


    adGenSlot2 MODULE-IDENTITY
        LAST-UPDATED "200809250000Z"
        ORGANIZATION "ADTRAN, Inc."
        CONTACT-INFO
               "        Technical Support Dept.
                Postal: ADTRAN, Inc.
                        901 Explorer Blvd.
                        Huntsville, AL 35806

                   Tel: +1 800 726-8663
                   Fax: +1 256 963 6217
                E-mail: support@adtran.com"
        DESCRIPTION
               "The MIB module that describes the generic objects
               used to mananage individual cards in a shelf/bank
               developed by ADTRAN, Inc."
       ::= { adGenSlot 5 }

    -- This MIB is a extension of the GenSlot.mib.
    --
    --


    -- This group contains information common for most all Adtran
    --  products. It is a slot addressable copy of the multi-scoped
    --  ADTRAN-MIB. It augments the slot info table.
    --

   adGenSlot2ProdTable OBJECT-TYPE
       SYNTAX  SEQUENCE OF AdGenSlot2ProdEntry
       MAX-ACCESS  not-accessible
       STATUS  current
       DESCRIPTION
               "Table of slots additional product information available for boards."
       ::= { adGenSlot 6 }

   adGenSlot2ProdEntry OBJECT-TYPE
       SYNTAX  AdGenSlot2ProdEntry
       MAX-ACCESS  not-accessible
       STATUS  current
       DESCRIPTION
               ""
       INDEX   { adGenSlotInfoIndex }
       ::= { adGenSlot2ProdTable 1 }

   AdGenSlot2ProdEntry ::=
       SEQUENCE {
           adGenSlotProdHwRevision
               DisplayString
       }


    adGenSlotProdHwRevision  OBJECT-TYPE
        SYNTAX  DisplayString
        MAX-ACCESS  read-only
        STATUS  current
        DESCRIPTION
            "The Adtran Product hardware revision."
        ::= { adGenSlot2ProdEntry 1 }



    END

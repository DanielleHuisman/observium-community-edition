ADTRAN-GENSUBTENDEDHOST-MIB

-- TITLE:     The ADTRAN Generic Subtended Host MIB
-- PRODUCT:   Products that subtend a managed device
-- VERSION:   1.0
-- DATE:      03/09/09
-- AUTHOR:    Joey Boyd
-- STATUS:    PRELIMINARY

-- This MIB defines the object identifiers (OIDs) for the
-- ADTRAN GENSUBTENDEDHOST MIB objects

-- HISTORY:
-- 03/09/09 jlb   STATUS: PRELIMINARY.
-- 03/10/09 jlb   Changed adGenSubHostProvCtrlPushdown to adGenSubHostProvIfMode.
-- 03/25/09 jlb   Reordered the enums for adGenSubHostProvIfMode.  SMIC verified.
-- 04/06/09 jlb   Added adGenSubHostProvMgmtIpAssignMode, adGenSubHostProvMgmtSync,
--                adGenSubHostStatIpAddress, and adGenSubHostStatGateway.
--                SMIC verified.
-- 04/08/09 jlb   Added adGenSubHostStatProvSync.  SMIC verified.
-- 04/10/09 jlb   Swapped the enumerations in adGenSubHostProvMgmtIpAssignMode.
-- 04/14/09 jlb   Changed the enumerations of adGenSubHostProvIfMode from uplink(1), downlink(2),
--				  none(3) to listener(1), sender(2), disabled(3).  SMIC verified.
-- 05/05/10 bly   Added the following, SMIC verified: adGenSubHostProvMgmtSnmpSysLocation, 
--                adGenSubHostProvMgmtEzProvHostOneIpAddress, adGenSubHostProvMgmtEzProvHostOneTrapVersion,
--                adGenSubHostProvMgmtEzProvHostTwoIpAddress, adGenSubHostProvMgmtEzProvHostTwoTrapVersion,
--                adGenSubHostProvMgmtEzProvEnabled 
-- 07/23/10 sgs   Added adGenSubHostStatIpSubnetMask; SMIC verified

-- ******************************************************************************************
DEFINITIONS ::= BEGIN

IMPORTS

   adGenSubtendedHost,
   adGenSubtendedHostID
      FROM ADTRAN-SHARED-CND-SYSTEM-MIB
   OBJECT-TYPE,
   MODULE-IDENTITY,
   NOTIFICATION-TYPE,
   Integer32,
   IpAddress
      FROM SNMPv2-SMI
   sysName
      FROM SNMPv2-MIB
   DisplayString,
   MacAddress,
   TruthValue
      FROM SNMPv2-TC
   InetAddressIPv4,
   InetAddressIPv6,
   InetAddressPrefixLength
      FROM INET-ADDRESS-MIB
   AdGenTrapVersion
      FROM ADTRAN-SHARED-CND-SYSTEM-TC-MIB
   ifDescr,
   ifIndex,
   InterfaceIndex
      FROM IF-MIB
   adTrapInformSeqNum
      FROM ADTRAN-GENTRAPINFORM-MIB
   adGenSlotInfoIndex
      FROM ADTRAN-GENSLOT-MIB
   ;

adGenSubtendedHostMIB MODULE-IDENTITY
   LAST-UPDATED "201508210000Z"
   ORGANIZATION "Adtran, Inc."
   CONTACT-INFO
     "CND Tech Support
         Postal: ADTRAN, Inc.
                 901 Explorer Blvd.
                 Huntsville, AL  35806
                 Tel: +1 800 726-8663
                 Fax: +1 256 963 6217
                 E-mail: support@adtran.com"
   DESCRIPTION
      "This MIB defines the objects for the Subtended Host MIB."

   REVISION "201508210000Z"
   DESCRIPTION "Added new OID to adGenSubHostProvMgmtTable
      adGenSubHostProvMgmtLastErrorString."	

   REVISION "201505270000Z"
   DESCRIPTION "Corrected the structure of the NE discovery
      notification (adGenSubHostProvIfAutoDiscoveryAlm) to
      be SMIv1 conformant."

   REVISION "201503060000Z"
   DESCRIPTION "Added new items for Auto-Discovery and Auto-Config:
      adGenSubHostProvIfAutoDiscoveryMode,
      adGenSubHostProvIfAutoDiscoveryAck,
      adGenSubHostProvIfAutoDiscoveryAlm,
      adGenSubHostProvMgmtAutoConfigMode,
      adGenSubHostProvMgmtAutoConfigFilename,
      adGenSubHostProvMgmtAutoConfigGroupName,
      adGenSubHostProvMgmtAutoConfigHostIpv4,
      adGenSubHostProvMgmtAutoConfigHostIpv6,
      adGenSubHostStatAutoConfigMode,
      adGenSubHostStatAutoConfigFilename,
      adGenSubHostStatAutoConfigGroupName,
      adGenSubHostStatAutoConfigHostIpv4,
      adGenSubHostStatAutoConfigHostIpv6"

   REVISION "201405160000Z"
   DESCRIPTION "Added the following OIDs for IPv6 address management:
       adGenSubHostProvMgmtIpv6AddressLinkLocal,
       adGenSubHostProvMgmtIpv6Address,
       adGenSubHostProvMgmtIpv6AddressPrefixLength,
       adGenSubHostProvMgmtIpv6AddressEui64,
       adGenSubHostStatIpv6AddressLinkLocal,
       adGenSubHostStatIpv6Address,
       adGenSubHostStatIpv6AddressPrefixLength,
       adGenSubHostStatIpv6AddressEui64"

   REVISION "200903090000Z"
   DESCRIPTION "Created"

::= { adGenSubtendedHostID 1 }

adGenSubtendedHostProvisioning                OBJECT IDENTIFIER ::= {adGenSubtendedHost 1}
adGenSubtendedHostStatus                      OBJECT IDENTIFIER ::= {adGenSubtendedHost 2}
adGenSubtendedHostNotificationsPrefix         OBJECT IDENTIFIER ::= {adGenSubtendedHost 3}
adGenSubtendedHostNotifications               OBJECT IDENTIFIER ::= {adGenSubtendedHostNotificationsPrefix 0}

--==================================================================================================================
-- PROVISIONING
--==================================================================================================================

adGenSubHostProvMgmtTable OBJECT-TYPE
   SYNTAX      SEQUENCE OF AdGenSubHostProvMgmtEntry
   MAX-ACCESS  not-accessible
   STATUS      current
   DESCRIPTION
     "This table supports provisioning of inband management
	  interface on a subtended host. These entries will be
      proxied for by the device subtending the host."
   ::= { adGenSubtendedHostProvisioning 1 }

adGenSubHostProvMgmtEntry OBJECT-TYPE
   SYNTAX      AdGenSubHostProvMgmtEntry
   MAX-ACCESS  not-accessible
   STATUS      current
   DESCRIPTION
     "An entry in the adGenSubHostProvMgmtTable."
   INDEX { ifIndex }
   ::= { adGenSubHostProvMgmtTable 1 }

AdGenSubHostProvMgmtEntry ::=
   SEQUENCE
   {
      adGenSubHostProvMgmtIpAddress           IpAddress,
      adGenSubHostProvMgmtIpSubnetMask        IpAddress,
      adGenSubHostProvMgmtIpGateway           IpAddress,
      adGenSubHostProvMgmtIpVlan              Integer32,
      adGenSubHostProvMgmtTftpServer          IpAddress,
      adGenSubHostProvMgmtSnmpWriteCommunity  DisplayString,
      adGenSubHostProvMgmtSnmpReadCommunity   DisplayString,
      adGenSubHostProvMgmtSysName             DisplayString,
      adGenSubHostProvMgmtPriority            Integer32,
      adGenSubHostProvMgmtIpAssignMode        INTEGER,
      adGenSubHostProvMgmtSync                INTEGER,
      adGenSubHostProvMgmtSnmpSysLocation     DisplayString,
      adGenSubHostProvMgmtEzProvHostOneIpAddress      IpAddress,
      adGenSubHostProvMgmtEzProvHostOneTrapVersion    AdGenTrapVersion,
      adGenSubHostProvMgmtEzProvHostTwoIpAddress      IpAddress,
      adGenSubHostProvMgmtEzProvHostTwoTrapVersion    AdGenTrapVersion,
      adGenSubHostProvMgmtEzProvEnabled               TruthValue,
      adGenSubHostProvMgmtIpv6AddressPrefixLength     InetAddressPrefixLength,
      adGenSubHostProvMgmtIpv6AddressEui64            TruthValue,
      adGenSubHostProvMgmtIpv6Address                 InetAddressIPv6,
      adGenSubHostProvMgmtIpv6AddressLinkLocal        InetAddressIPv6,
      adGenSubHostProvMgmtAutoConfigMode              TruthValue,
      adGenSubHostProvMgmtAutoConfigFilename          DisplayString,
      adGenSubHostProvMgmtAutoConfigGroupName         DisplayString,
      adGenSubHostProvMgmtAutoConfigHostIpv4          InetAddressIPv4,
      adGenSubHostProvMgmtAutoConfigHostIpv6          InetAddressIPv6,
      adGenSubHostProvMgmtLastErrorString             DisplayString
   }

adGenSubHostProvMgmtIpAddress OBJECT-TYPE
   SYNTAX      	IpAddress
   MAX-ACCESS   read-write
   STATUS       current
   DESCRIPTION
     "The management IP address of the subtended host."
	 ::= { adGenSubHostProvMgmtEntry 1 }

adGenSubHostProvMgmtIpSubnetMask OBJECT-TYPE
   SYNTAX      	IpAddress
   MAX-ACCESS   read-write
   STATUS       current
   DESCRIPTION
     "The management subnet mask of the subtended host."
	 ::= { adGenSubHostProvMgmtEntry 2 }

adGenSubHostProvMgmtIpGateway OBJECT-TYPE
   SYNTAX      	IpAddress
   MAX-ACCESS   read-write
   STATUS       current
   DESCRIPTION
     "The management default gateway of the subtended host."
	 ::= { adGenSubHostProvMgmtEntry 3 }

adGenSubHostProvMgmtIpVlan OBJECT-TYPE
   SYNTAX      	Integer32
   MAX-ACCESS   read-write
   STATUS       current
   DESCRIPTION
     "The management VLAN of the subtended host."
	 ::= { adGenSubHostProvMgmtEntry 4 }

adGenSubHostProvMgmtTftpServer OBJECT-TYPE
   SYNTAX      	IpAddress
   MAX-ACCESS   read-write
   STATUS       current
   DESCRIPTION
     "The TFTP server address used by the subtended host."
	 ::= { adGenSubHostProvMgmtEntry 5 }

adGenSubHostProvMgmtSnmpWriteCommunity OBJECT-TYPE
   SYNTAX       DisplayString
   MAX-ACCESS   read-write
   STATUS       current
   DESCRIPTION
     "The read-write SNMP community string used
      by the subtended host."
         ::= { adGenSubHostProvMgmtEntry 6 }

adGenSubHostProvMgmtSnmpReadCommunity OBJECT-TYPE
   SYNTAX       DisplayString
   MAX-ACCESS   read-write
   STATUS       current
   DESCRIPTION
     "The read-only SNMP community string used
      by the subtended host."
         ::= { adGenSubHostProvMgmtEntry 7 }

adGenSubHostProvMgmtSysName OBJECT-TYPE
   SYNTAX       DisplayString
   MAX-ACCESS   read-write
   STATUS       current
   DESCRIPTION
     "The System Name (TID) used by the subtended host."
    ::= { adGenSubHostProvMgmtEntry 8 }

adGenSubHostProvMgmtPriority OBJECT-TYPE
   SYNTAX      	Integer32
   MAX-ACCESS   read-write
   STATUS       current
   DESCRIPTION
     "The priority of the management VLAN of the subtended host."
    ::= { adGenSubHostProvMgmtEntry 9 }

adGenSubHostProvMgmtIpAssignMode OBJECT-TYPE
   SYNTAX      	INTEGER
				{
					dynamic(1),
					static(2)
				}
   MAX-ACCESS   read-write
   STATUS       current
   DESCRIPTION
     "The method by which IP addresses are assigned to the subtended host.
	  Static IP addresses are provisioned through this MIB.  Dynamic IP addresses
	  are provisioned via DHCP or a similar protocol."
    ::= { adGenSubHostProvMgmtEntry 10 }

adGenSubHostProvMgmtSync OBJECT-TYPE
   SYNTAX      	INTEGER
				{
					resync(1),
					reset(2)
				}
   MAX-ACCESS   read-write
   STATUS       current
   DESCRIPTION
     "A SET to resync(1) forces management provisioning to be sent to the
	  subtended host.  A SET to reset(2) defaults the management on the
	  subtended host."
    ::= { adGenSubHostProvMgmtEntry 11 }

adGenSubHostProvMgmtSnmpSysLocation OBJECT-TYPE
   SYNTAX        DisplayString
   MAX-ACCESS    read-write
   STATUS        current
   DESCRIPTION
     "The SNMP SysLocation string used by the subtended host."
    ::= { adGenSubHostProvMgmtEntry 12 }

adGenSubHostProvMgmtEzProvHostOneIpAddress OBJECT-TYPE
   SYNTAX      	IpAddress
   MAX-ACCESS   read-write
   STATUS       current
   DESCRIPTION
     "The EZ-Provisioning trap host IP address of the subtended host."
    ::= { adGenSubHostProvMgmtEntry 13 }

adGenSubHostProvMgmtEzProvHostOneTrapVersion OBJECT-TYPE
   SYNTAX       AdGenTrapVersion
   MAX-ACCESS   read-write
   STATUS       current
   DESCRIPTION
     "The EZ-Provisioning trap version of the subtended host."
    ::= { adGenSubHostProvMgmtEntry 14 }

adGenSubHostProvMgmtEzProvHostTwoIpAddress OBJECT-TYPE
   SYNTAX      	IpAddress
   MAX-ACCESS   read-write
   STATUS       current
   DESCRIPTION
     "The EZ-Provisioning trap host IP address of the subtended host."
    ::= { adGenSubHostProvMgmtEntry 15 }

adGenSubHostProvMgmtEzProvHostTwoTrapVersion OBJECT-TYPE
   SYNTAX       AdGenTrapVersion
   MAX-ACCESS   read-write
   STATUS       current
   DESCRIPTION
     "The EZ-Provisioning trap version of the subtended host."
    ::= { adGenSubHostProvMgmtEntry 16 }

adGenSubHostProvMgmtEzProvEnabled OBJECT-TYPE
   SYNTAX       TruthValue
   MAX-ACCESS   read-write
   STATUS       current
   DESCRIPTION
     "The EZ-Provisioning administrative state of the subtended host."
    ::= { adGenSubHostProvMgmtEntry 17 }

adGenSubHostProvMgmtIpv6AddressPrefixLength OBJECT-TYPE
   SYNTAX        InetAddressPrefixLength
   MAX-ACCESS    read-write
   STATUS        current
   DESCRIPTION
     "The provisioned IPv6 unicast address prefix length."
    ::= { adGenSubHostProvMgmtEntry 18 }

adGenSubHostProvMgmtIpv6AddressEui64 OBJECT-TYPE
   SYNTAX       TruthValue
   MAX-ACCESS   read-write
   STATUS       current
   DESCRIPTION
     "When true, then the operational IPv6 unicast address is a combination
      of the provisioned prefix and an EUI-64 formatted Interface ID."
    ::= { adGenSubHostProvMgmtEntry 19 }

adGenSubHostProvMgmtIpv6Address OBJECT-TYPE
   SYNTAX        InetAddressIPv6
   MAX-ACCESS    read-write
   STATUS        current
   DESCRIPTION
     "The provisioned IPv6 unicast address or address prefix.
      If EUI-64 is false, then the operational unicast address equals
      this value. If EUI-64 is true, then the operational unicast address
      is derived from this value (high-order bits) and the Interface ID
      (low-order bits) in combination with the prefix length."
    ::= { adGenSubHostProvMgmtEntry 20 }

adGenSubHostProvMgmtIpv6AddressLinkLocal OBJECT-TYPE
   SYNTAX        InetAddressIPv6
   MAX-ACCESS    read-write
   STATUS        current
   DESCRIPTION
     "The provisioned IPv6 link-local address prefix.
      The prefix length is implicitly 10 bits."
    ::= { adGenSubHostProvMgmtEntry 21 }

adGenSubHostProvMgmtAutoConfigMode OBJECT-TYPE
   SYNTAX       TruthValue
   MAX-ACCESS   read-write
   STATUS       current
   DESCRIPTION
     "Auto-Config mode.  When set to True, the Auto-Config feature is
      enabled on the subtended host.  When set to False, the Auto-Config
      feature is disabled on the subtended host."
   DEFVAL { false }
    ::= { adGenSubHostProvMgmtEntry 22 }

adGenSubHostProvMgmtAutoConfigFilename OBJECT-TYPE
   SYNTAX        DisplayString
   MAX-ACCESS    read-write
   STATUS        current
   DESCRIPTION
     "Auto-Config filename.  This filename is used by the subtended host
      during the Auto-Config sequence to retrieve configuration and firmware."
   DEFVAL { "" }
    ::= { adGenSubHostProvMgmtEntry 23 }

adGenSubHostProvMgmtAutoConfigGroupName OBJECT-TYPE
   SYNTAX        DisplayString
   MAX-ACCESS    read-write
   STATUS        current
   DESCRIPTION
     "Auto-Config group name.  This group name may be used by the subtended
      host to configure filenames to retrieve from the file server."
   DEFVAL { "" }
    ::= { adGenSubHostProvMgmtEntry 24 }

adGenSubHostProvMgmtAutoConfigHostIpv4 OBJECT-TYPE
   SYNTAX        InetAddressIPv4
   MAX-ACCESS    read-write
   STATUS        current
   DESCRIPTION
     "Auto-Config file server IPv4 address"
    ::= { adGenSubHostProvMgmtEntry 25 }

adGenSubHostProvMgmtAutoConfigHostIpv6 OBJECT-TYPE
   SYNTAX        InetAddressIPv6
   MAX-ACCESS    read-write
   STATUS        current
   DESCRIPTION
     "Auto-Config file server IPv6 address"
    ::= { adGenSubHostProvMgmtEntry 26 }

adGenSubHostProvMgmtLastErrorString OBJECT-TYPE
   SYNTAX        DisplayString
   MAX-ACCESS    read-only
   STATUS        current
   DESCRIPTION
     "The last error reported during subtended host provisioning."
   DEFVAL { "" }
    ::= { adGenSubHostProvMgmtEntry 27 }

--==================================================================================================================

adGenSubHostProvIfTable OBJECT-TYPE
   SYNTAX      SEQUENCE OF AdGenSubHostProvIfEntry
   MAX-ACCESS  not-accessible
   STATUS      current
   DESCRIPTION
     "This table supports provisioning items for configuring the
	  interface used for subtending."

   ::= { adGenSubtendedHostProvisioning 2 }

adGenSubHostProvIfEntry OBJECT-TYPE
   SYNTAX      AdGenSubHostProvIfEntry
   MAX-ACCESS  not-accessible
   STATUS      current
   DESCRIPTION
     "An entry in the adGenSubHostProvIfTable."
   INDEX { ifIndex }
   ::= { adGenSubHostProvIfTable 1 }

AdGenSubHostProvIfEntry ::=
   SEQUENCE
   {
      adGenSubHostProvIfMode     		INTEGER,
      adGenSubHostProvIfAutoDiscoveryMode       TruthValue,
      adGenSubHostProvIfAutoDiscoveryAck        TruthValue
   }

adGenSubHostProvIfMode OBJECT-TYPE
   SYNTAX      	INTEGER
				{
					disabled(1),
					listener(2),
					sender(3)
				}
   MAX-ACCESS   read-write
   STATUS       current
   DESCRIPTION
     "The provisioning item controls the subtending abilities of the
	  interface.  A listener can receive provisioning.  A sender can
	  transmit provisioning.  If disabled is selected, neither function will
	  be performed."
    ::= { adGenSubHostProvIfEntry 1 }

adGenSubHostProvIfAutoDiscoveryMode OBJECT-TYPE
   SYNTAX       TruthValue
   MAX-ACCESS   read-write
   STATUS       current
   DESCRIPTION
     "Auto-Discover mode. When set to true, the system will send a notification
     (adGenSubHostProvIfAutoDiscoveryAlm) to prompt the EMS to automatically discover
     the NE. The system will retransmit the trap periodically until the EMS acknowledges
     the notification by setting adGenSubHostProvIfAutoDiscoveryAck to true."
   DEFVAL { false }
    ::= { adGenSubHostProvIfEntry 2 }

adGenSubHostProvIfAutoDiscoveryAck OBJECT-TYPE
   SYNTAX       TruthValue
   MAX-ACCESS   read-write
   STATUS       current
   DESCRIPTION
     "Auto-Discover acknowledgement. The NE sets this value to false when it activates
     the Auto-Discovery alarm (adGenSubHostProvIfAutoDiscoveryAlm). The EMS should set this value
     to true to acknowledge the notification."
   DEFVAL { false }
    ::= { adGenSubHostProvIfEntry 3 }

--==================================================================================================================
-- STATUS
--==================================================================================================================
adGenSubHostStatTable OBJECT-TYPE
   SYNTAX      SEQUENCE OF AdGenSubHostStatEntry
   MAX-ACCESS  not-accessible
   STATUS      current
   DESCRIPTION
     "This table supports status items related to the
	  subtended host.  These items are proxied for by
	  the device subtending the host."
   ::= { adGenSubtendedHostStatus 1 }

adGenSubHostStatEntry OBJECT-TYPE
   SYNTAX      AdGenSubHostStatEntry
   MAX-ACCESS  not-accessible
   STATUS      current
   DESCRIPTION
     "An entry in the adGenSubHostStatTable."
   INDEX { ifIndex }
   ::= { adGenSubHostStatTable 1 }

AdGenSubHostStatEntry ::=
   SEQUENCE
   {
      adGenSubHostStatMacAddress                        MacAddress,
      adGenSubHostStatIpAddress                         IpAddress,
      adGenSubHostStatGateway                           IpAddress,
      adGenSubHostStatProvSync  		        DisplayString,
      adGenSubHostStatIpSubnetMask                      IpAddress,
      adGenSubHostStatIpv6AddressPrefixLength           InetAddressPrefixLength,
      adGenSubHostStatIpv6AddressEui64                  TruthValue,
      adGenSubHostStatIpv6Address                       InetAddressIPv6,
      adGenSubHostStatIpv6AddressLinkLocal              InetAddressIPv6,
      adGenSubHostStatAutoConfigMode                    TruthValue,
      adGenSubHostStatAutoConfigFilename                DisplayString,
      adGenSubHostStatAutoConfigGroupName               DisplayString,
      adGenSubHostStatAutoConfigHostIpv4                InetAddressIPv4,
      adGenSubHostStatAutoConfigHostIpv6                InetAddressIPv6
   }

adGenSubHostStatMacAddress OBJECT-TYPE
   SYNTAX       MacAddress
   MAX-ACCESS   read-only
   STATUS       current
   DESCRIPTION
     "The MAC address associated with the management interface on the
	  subtended host."
    ::= { adGenSubHostStatEntry 1 }

adGenSubHostStatIpAddress OBJECT-TYPE
   SYNTAX      	IpAddress
   MAX-ACCESS   read-only
   STATUS       current
   DESCRIPTION
     "The management IP address of the subtended host."
	 ::= { adGenSubHostStatEntry 2 }

adGenSubHostStatGateway OBJECT-TYPE
   SYNTAX      	IpAddress
   MAX-ACCESS   read-only
   STATUS       current
   DESCRIPTION
     "The management default gateway of the subtended host."
	 ::= { adGenSubHostStatEntry 3 }

adGenSubHostStatProvSync OBJECT-TYPE
   SYNTAX      	DisplayString
   MAX-ACCESS   read-only
   STATUS       current
   DESCRIPTION
     "A text string describing the current status of the provisioning
	  sync with the subtended host.  This string may be used to indicate a failure in the
	  protocol being used to send the provisioning to the subtended host."
	 ::= { adGenSubHostStatEntry 4 } 
	 
adGenSubHostStatIpSubnetMask OBJECT-TYPE
   SYNTAX      	IpAddress
   MAX-ACCESS   read-only
   STATUS       current
   DESCRIPTION
     "The management subnet mask of the subtended host."
	 ::= { adGenSubHostStatEntry 5 }

adGenSubHostStatIpv6AddressPrefixLength OBJECT-TYPE
   SYNTAX       InetAddressPrefixLength
   MAX-ACCESS   read-only
   STATUS       current
   DESCRIPTION
     "The provisioned IPv6 unicast address prefix length."
    ::= { adGenSubHostStatEntry 6 }

adGenSubHostStatIpv6AddressEui64 OBJECT-TYPE
   SYNTAX       TruthValue
   MAX-ACCESS   read-only
   STATUS       current
   DESCRIPTION
     "When true, then the operational IPv6 unicast address is a combination
      of the provisioned prefix and an EUI-64 formatted Interface ID."
    ::= { adGenSubHostStatEntry 7 }

adGenSubHostStatIpv6Address OBJECT-TYPE
   SYNTAX       InetAddressIPv6
   MAX-ACCESS   read-only
   STATUS       current
   DESCRIPTION
       "The provisioned IPv6 unicast address or address prefix.
        If EUI-64 is false, then the operational unicast address equals
        this value. If EUI-64 is true, then the operational unicast address
        is derived from this value (high-order bits) and the Interface ID
        (low-order bits) in combination with the prefix length."
    ::= { adGenSubHostStatEntry 8 }

adGenSubHostStatIpv6AddressLinkLocal OBJECT-TYPE
   SYNTAX       InetAddressIPv6
   MAX-ACCESS   read-only
   STATUS       current
   DESCRIPTION
     "The provisioned IPv6 link-local address prefix.
      The prefix length is implicitly 10 bits."
    ::= { adGenSubHostStatEntry 9 }

adGenSubHostStatAutoConfigMode OBJECT-TYPE
   SYNTAX       TruthValue
   MAX-ACCESS   read-only
   STATUS       current
   DESCRIPTION
     "Auto-Config mode.  When set to True, the Auto-Config feature is
      enabled on the subtended host.  When set to False, the Auto-Config
      feature is disabled on the subtended host."
    ::= { adGenSubHostStatEntry 10 }

adGenSubHostStatAutoConfigFilename OBJECT-TYPE
   SYNTAX        DisplayString
   MAX-ACCESS    read-only
   STATUS        current
   DESCRIPTION
     "Auto-Config filename.  This filename is used by the subtended host
      during the Auto-Config sequence to retrieve configuration and firmware."
    ::= { adGenSubHostStatEntry 11 }

adGenSubHostStatAutoConfigGroupName OBJECT-TYPE
   SYNTAX        DisplayString
   MAX-ACCESS    read-only
   STATUS        current
   DESCRIPTION
     "Auto-Config group name.  This group name may be used by the subtended
      host to configure filenames to retrieve from the file server."
    ::= { adGenSubHostStatEntry 12 }

adGenSubHostStatAutoConfigHostIpv4 OBJECT-TYPE
   SYNTAX        InetAddressIPv4
   MAX-ACCESS    read-only
   STATUS        current
   DESCRIPTION
     "Auto-Config file server IPv4 address"
    ::= { adGenSubHostStatEntry 13 }

adGenSubHostStatAutoConfigHostIpv6 OBJECT-TYPE
   SYNTAX        InetAddressIPv6
   MAX-ACCESS    read-only
   STATUS        current
   DESCRIPTION
     "Auto-Config file server IPv6 address"
    ::= { adGenSubHostStatEntry 14 }

--==================================================================================================================
adGenSubHostStatFarEndTable OBJECT-TYPE
   SYNTAX      SEQUENCE OF AdGenSubHostStatFarEndEntry
   MAX-ACCESS  not-accessible
   STATUS      current
   DESCRIPTION
     "This table supports status items that are queried on the
	  subtended host.  These items are used to identify the
	  device subtending the host."
   ::= { adGenSubtendedHostStatus 2 }

adGenSubHostStatFarEndEntry OBJECT-TYPE
   SYNTAX      AdGenSubHostStatFarEndEntry
   MAX-ACCESS  not-accessible
   STATUS      current
   DESCRIPTION
     "An entry in the adGenSubHostStatFarEndTable."
   INDEX { ifIndex }
   ::= { adGenSubHostStatFarEndTable 1 }

AdGenSubHostStatFarEndEntry ::=
   SEQUENCE
   {
      adGenSubHostStatFarEndIfIndex       InterfaceIndex,
      adGenSubHostStatFarEndIpAddress     IpAddress,
      adGenSubHostStatFarEndSysName       DisplayString
   }

adGenSubHostStatFarEndIfIndex OBJECT-TYPE
   SYNTAX       InterfaceIndex
   MAX-ACCESS   read-only
   STATUS       current
   DESCRIPTION
     "The ifIndex associated with the bonded group connected to this subtended host."
    ::= { adGenSubHostStatFarEndEntry 1 }

adGenSubHostStatFarEndIpAddress OBJECT-TYPE
   SYNTAX       IpAddress
   MAX-ACCESS   read-only
   STATUS       current
   DESCRIPTION
     "The IP address associated with the system connected to this subtended host."
    ::= { adGenSubHostStatFarEndEntry 2 }

adGenSubHostStatFarEndSysName OBJECT-TYPE
   SYNTAX       DisplayString
   MAX-ACCESS   read-only
   STATUS       current
   DESCRIPTION
     "The System Name (TID) associated with the system connected to this subtended host."
    ::= { adGenSubHostStatFarEndEntry 3 }

--==================================================================================================================
-- NOTIFICATIONS
--==================================================================================================================

adGenSubHostProvIfAutoDiscoveryAlm NOTIFICATION-TYPE
    OBJECTS         {
                    adTrapInformSeqNum,
                    sysName,
                    adGenSlotInfoIndex,
                    ifDescr,
                    ifIndex
                    }
    STATUS          current
    DESCRIPTION
                    "NE Discovery"
    --#TYPE         "Info - NE Discovery
    --#SUMMARY      "NE Discovery "
    --#SUMMARY      "detected at shelf: %s, slot: %d and customer: %s"
    --#ARGUMENTS    {1,2,3}
    --#SEVERITY     "INFORMATIONAL"
    --#GENERIC      6
    --#CATEGORY     "Info Events"
    --#SOURCE_ID    "A"
    --#TIMEINDEX    0
    ::= {adGenSubtendedHostNotifications 1}

END

ADTRAN-GENSYSTEM-MIB   DEFINITIONS ::= BEGIN

     -- TITLE:       Generic System MIB
     -- PRODUCT:     All types of products
     -- VERSION:     1.2
     -- DATE:        2007/10/03
     -- AUTHOR:      Shaik Abdulla
     -- SNMP:        SNMPv2
     -- MIB ARC:     adtran.adShared.adGenSystem
     -- HISTORY:
       -- 2007/10/03  SA - created
       -- 2008/04/30  TGC - added adGenSystemFeatureSupportByteMap
       -- 2008/05/01  JLB - conversion from v1 to v2
       -- 2008/05/02  TGC - modified description of adGenSystemFeatureSupportByteMap
       --                   and added initial list of Feature IDs provided by Tim Cox,
       --                   current Systems Feature Admin
       -- 2008/05/22  TGC - added Feature IDs for Redundancy Mode Prov v2 and
       --                   LACP Mode Prov at the request of A.Dyess and T.Cox; also
       --                   added a few comments to the Feature IDs to help with future usage
       -- 2008/10/15  TWC - added Feature ID for NTP
       -- 2008/10/24  RJF - Reserve a block of IDs (10..19), indicating support for new version (1..9) query oid.
       -- 2008/10/27  RJF - Ver 1.1: Initial cut of version-indexed System FeatureID table.
       --                   Also restructure FeatureID description table.
       --                   Also Add FeatureIDs for SystemControlledReboot brx and adTaSntpGMTtimeZoneString oid.
       -- 2008/11/04  RJF - Ver 1.2: Add new adGenSystemProductMgGrp branch for future extension
       --                   Move adGenSystemFeatureSupportVersionTable to the new adGenSystemProductMgGrp brx.
       -- 2008/11/08  CRH - Added Feature ID for EFM OAM Remote Loopback for the TA5k SM platform
       -- 2008/12/03  OCH - Added Feature ID for ATM Bonding for the TA5k ADSL2+ Combo and ADSL2+ 32 port cards
       -- 2008/12/18  DCC - Added Feature IDs for BSM Flows and PPP, added rev 2. of Ethernet OAM (CFM)
       -- 2008/12/24  DCC - Added Feature ID for IMA
       -- 2009/01/12  JLB - Added Feature ID for MAC Aging
       -- 2009/01/16  PSK - Added Feature ID for TA5k Universal termination support
       -- 2009/01/22  JLB - Added Feature ID for Egress Queue
       -- 2009/01/27  OCH - Added Feature ID for SELT/DELT
       -- 2009/02/05  JLB - Added Feature ID for New GenMEF OID support
       -- 2009/03/26  AED - Added Feature IDs for Centralized EVCs and the new Pluggable MIB
       -- 2009/06/03  SS  - Added Feature IDs for Etherflow component
       -- 2009/08/17  GLF - Added new Revision to PPP for MLPPP support
       -- 2009/09/28  GLF - Added Feature ID for AINS (Auto In Service)
       -- 2009/10/05  CJW - Added Feature IDs for PWE3 Provisioning
       -- 2009/10/06  srao - Added Feature ID for TSCAN FDL
       -- 2009/10/23  srao - Added Feature ID for PWE3 H4TUC Provisioning
       -- 2009/11/06  CRH - Added Feature ID for Extended Reach TSCAN
       -- 2009/12/09  JDD - Added Feature ID for PWE3 Timing Mode Provisioning
       -- 2009/12/17  TGC - Added Feature ID for GR909 tests on behalf of Seetha S.
       -- 2009/12/17  PK  - Added Feature ID for SIP
       -- 2010/02/02  JLB - Added Feature ID for Double Tagging.
       -- 2010/02/23  JLB - Added Feature ID for Configurable Memory Threshold and Alarm
       -- 2010/02/23  RPK - Added Feature ID for GenMEF DSCP Range OID
       -- 2010/05/05  BLY - Added Feature ID for EZ-Provisioning
       -- 2010/05/24  JLB - Added Feature ID for genIP support of MEN priority inherit.
       -- 2010/07/22  WFE - Added Feature ID for Remote Power-Shedding.
       -- 2010/08/05  SGS - Added Feature IDs for Registration ID based ONT activation.
       -- 2010/08/09  PAL - Added Feature IDs for OSP VLAN discovery and VG ActiveEthernet support.
       -- 2010/08/10  DCC - Added Feature ID to indicate that EVPL Cross Connects can no longer be used with PPP groups.
       -- 2010/08/16  RAB - Added Feature IDs for Downstream Vdsl power backoff support.
       -- 2010/08/27  PAL - Added Feature IDs for authenticated Etherflow EFM-Groups, frame relay, and IP host version 2.
       -- 2010/10/05  RAB - Added Feature IDs for ANFP cal value support.
       -- 2010/10/27  RP  - Added Feature ID for Node Information Advertisement
       -- 2010/10/29 MM - Added Feature ID for 1024 max depth support on Unchannelized DS3 (1187260G1)
       -- 2010/11/02  XL  - Added Feature ID for Subscriber MAC OID support
       -- 2011/01/19 RPK - Added Feature ID for TWAMP Reflector Version 1
       -- 2011/01/31  MAS - Added Feature IDs support for setting trunk SIP msg DSCP value and RTP msg DSCP value.
       -- 2011/02/03 TAS - Added two Feature IDs, one for SM IGMP support and another for AM IGMP support
       -- 2011/02/18 TAS - Added Feature ID for policer actual statistics support
       -- 2011/03/08 PAL - Revision history now in REVISION/DESCRIPTION clauses below
       -- 2011/03/16 CRH - Added feature ID for legacy OSP provisioning mode
       -- 2011/03/17 TKR - Added feature ID for tx and rx EFM group percent utilization
       -- *******************************************************************************************************
       --    DO NOT MAKE HISTORY COMMENTS HERE!!!! Revision history now in REVISION/DESCRIPTION clauses below
       -- *******************************************************************************************************

     IMPORTS

          OBJECT-TYPE,
          MODULE-IDENTITY,
          Integer32
               FROM SNMPv2-SMI
          OBJECT-GROUP
            FROM SNMPv2-CONF
          DisplayString
               FROM SNMPv2-TC
          adShared
               FROM ADTRAN-MIB
          adGenSlotInfoIndex
               FROM ADTRAN-GENSLOT-MIB
          adGenSystemProduct,
          adGenSystemProductMg,
          adGenSystemProductID
               FROM ADTRAN-SHARED-CND-SYSTEM-MIB
          ;

adGenSystemsMIB MODULE-IDENTITY
   LAST-UPDATED "202205310000Z"
   ORGANIZATION "Adtran, Inc."
   CONTACT-INFO
     "CND Tech Support
         Postal: ADTRAN, Inc.
                 901 Explorer Blvd.
                 Huntsville, AL  35806
                 Tel: +1 800 726-8663
                 Fax: +1 256 963 6217
                 E-mail: support@adtran.com"
   DESCRIPTION
      "This MIB defines the objects for the GenSystems MIB."

   REVISION "202205310000Z"
   DESCRIPTION "Added Feature ID 226 for GAL Ethernet discarded frames counter"
   
   REVISION "202203300000Z"
   DESCRIPTION "Added Feature ID 225 for higher speeds (2.5G, 5G, 10G) on the ONT Ethernet interface"

   REVISION "202203290000Z"
   DESCRIPTION "Added Feature ID 224 for Upstream FEC rolling counters"

   REVISION "202203110000Z"
   DESCRIPTION "Added Feature ID 223 for configurable ONT Dying Gasp alarm severities."

   REVISION "202202230000Z"
   DESCRIPTION "Added Feature ID 222 for ONT reporting temp/bias current/voltage data."

   REVISION "202201070000Z"
   DESCRIPTION "Added Feature ID 221 for 85 vrms ring voltage support.
                Added Feature ID 220 for the Voice Timeouts Connected feature."

   REVISION "202107060000Z"
   DESCRIPTION "Support for Signed x.509 SSL Certificates"

   REVISION "202012010000Z"
   DESCRIPTION "Added Feature ID 218 for configurable SIP Registrar thresholds."

   REVISION "202005110000Z"
   DESCRIPTION "Added Feature ID 215 and 216 support for configurable EFM Group and VDSL2 alarm severities."

   REVISION "202004130000Z"
   DESCRIPTION "Added Feature ID 214 support for configurable ONT, Pluggable and Ethernet link down alarm severities."

   REVISION "201910090000Z"
   DESCRIPTION "Added Feature ID 213 Warmline feature for Voip Users"

   REVISION "201907310000Z"
   DESCRIPTION "Added Feature ID 212 support for Voice User SIP Trunk Manual Selection"

   REVISION "201904040000Z"
   DESCRIPTION "Added Feature ID 211 support for Default SIP Trunk"

   REVISION "201903210000Z"
   DESCRIPTION "Added Feature ID 210 support for FXS Pulse Digit Detection enable/disable"

   REVISION "201801090000Z"
   DESCRIPTION "Added Feature ID 209 support for VDSL Uplink NTR timing source"

   REVISION "201808290000Z"
   DESCRIPTION "Added Feature ID 208 support for EFM-Group downlink"

   REVISION "201807160000Z"
   DESCRIPTION "Added Feature ID 207 support for interop with the Huawei softswitch"

   REVISION "201804020000Z"
   DESCRIPTION "Added Feature ID 206 support for SNMP access the description for POTS ports"

   REVISION "201802220000Z"
   DESCRIPTION "Added Feature ID 205 Support for Rate Adaptation (SRA) Auto Config Mode"

   REVISION "201801260000Z"
   DESCRIPTION "Added Feature ID 204 Support for Gpon Slot level Protection for PON Redundancy"

   REVISION "201801170000Z"
   DESCRIPTION "Added Feature ID 203 Hotline feature for Voip Users"

   REVISION "201710160000Z"
   DESCRIPTION "Added Feature ID 202 Scheduled Fxs Line Tests Enable, Scheduled Fxs Load Coil Tests Enable, and Scheduled Fxs Line Tests Start Time"

   REVISION "201710120000Z"
   DESCRIPTION "Added Feature ID 201 SVX"

   REVISION "201709230000Z"
   DESCRIPTION "Added Feature ID 200 DLV"

   REVISION "201708100000Z"
   DESCRIPTION "Added Feature ID 199 Voice User Revserse Lookup Table"

   REVISION "201708100000Z"
   DESCRIPTION "Added Feature ID 198 Support of DMT EFM Group Uplink"

   REVISION "201706060000Z"
   DESCRIPTION "Added Feature ID 197 Support of slot based vectoring fallback command and status SNMP OIDS."

   REVISION "201704140000Z"
   DESCRIPTION "Added Feature ID 196 Support of returning slot uptime in seconds."

   REVISION "201612070000Z"
   DESCRIPTION "Added Feature ID 195 Support of FXS Jitter-Buffer configuration."

   REVISION "201611280000Z"
   DESCRIPTION "Added Feature ID 194 Support of SCM SCR reboot mode."

   REVISION "201610100000Z"
   DESCRIPTION "Added Feature ID 193 Support for RADIUS server sequence[0-4] and RADIUS names."

   REVISION "201609150000Z"
   DESCRIPTION "Added Feature ID 192 Support for Forcing the Message-Waiting Indicator either off or on with the ability to
                detect the state of the Indicator."

   REVISION "201606130000Z"
   DESCRIPTION "Added Feature ID 191 Support of SCM IPV6 server address."

   REVISION "201604010000Z"
   DESCRIPTION "Added Feature ID 190 for support of Message-Waiting Indication using neon lamps."

   REVISION "201603160000Z"
   DESCRIPTION "Added Feature ID 189 for support of CPU rate limiting alarm enable and severity provisioning."

   REVISION "201602220000Z"
   DESCRIPTION "Added Feature ID 188 for replacing ONT 32-bit Ethernet PM counters with 64-bit counters; all
                associated Counter32 adGenPmStats OIDs are replaced with Counter64 adGenPmStats OIDs."

   REVISION "201601040000Z"
   DESCRIPTION "Added Feature ID 187 for reporting PON wavelength and technology as well as new ONT activation"

   REVISION "201510290000Z"
   DESCRIPTION "Added Feature ID 184, 185, 186 for SNMP trap host provisioning in genTrap"

   REVISION "201510070000Z"
   DESCRIPTION "Added Feature ID 183 for warble tone generation on FXS ports."

   REVISION "201510060000Z"
   DESCRIPTION "Added Feature ID 182 for supporting single MAC clearing"

   REVISION "201509300000Z"
   DESCRIPTION "Added Feature ID 180 and 181 for quiet line noise (QLN) and  channel transfer
                function (HLOG) for VDSL"

   REVISION "201508120000Z"
   DESCRIPTION "Added Feature ID 178 and 179 for Downstrem SNR and memory split ratio for VDSL"

   REVISION "201508050000Z"
   DESCRIPTION "Added Feature ID 177 for resetting PON upstream and downstream BIP counters for GPON OLT"

   REVISION "201505070000Z"
   DESCRIPTION "Added Feature ID 176 for Domain Name and DNS in IP Host for GPON/AE OLT"

   REVISION "201503190000Z"
   DESCRIPTION "Added Feature ID 175 for VDSL link-down alarm severity provisioning on GPON OLT"

   REVISION "201502230000Z"
   DESCRIPTION "Added Feature ID 174 ONT Software Image "

   REVISION "201501220000Z"
   DESCRIPTION "Added Feature ID 173 AM Frequency Masking on VDSL Products"

   REVISION "201501060000Z"
   DESCRIPTION "Added Feature ID 172 for ONT Invalid SN alarms"

   REVISION "201412170000Z"
   DESCRIPTION "Added new OIDs to display Pseudowire Detailed Operational Status"

   REVISION "201412150000Z"
   DESCRIPTION "Added Feature ID 170 for Link State Awareness alarm"

   REVISION "201412100000Z"
   DESCRIPTION "Added Feature ID 169 for deferring the activation and commit of ONT software image
                after a software download"

   REVISION "201412090000Z"
   DESCRIPTION "Added Feature ID 166 for Evc-map Match DA, 167 for ERPS V2 Ladders and
                168 for ERPS MIB Provisioning"

   REVISION "201412050000Z"
   DESCRIPTION "Added Feature ID 165 for upstream Forward Error Correction (FEC) for 4th Gen GPON OLT"

   REVISION "201410310000Z"
   DESCRIPTION "Added Feature ID 164 for new OID to retrieve bulk voice users"

   REVISION "201410150000Z"
   DESCRIPTION "Added Feature ID 163 for new OID to read AMIO Part Number and Description"

   REVISION "201410130000Z"
   DESCRIPTION "Added Feature ID 162 for Auto-Config"

   REVISION "201409300000Z"
   DESCRIPTION "Added Feature ID 161 for adding support for SIP Dialing Profile Description.
                Deprecating adGenVoipDialingProfileProvExt replaced by adGenVoipDialingProfileCommonProv"

   REVISION "201409220000Z"
   DESCRIPTION "Added Feature ID 158 for Auto-Config subtended-host provisioning, and Feature ID 159 for Auto-Discovery of subtended-host"

   REVISION "201409150000Z"
   DESCRIPTION "Added Feature ID 160 for Match non-IP traffic support."

   REVISION "201406270000Z"
   DESCRIPTION "Added Feature ID 156 for 128 ONT support and Feature ID 157 for DSCP support on GPON OLT."

   REVISION "201406250000Z"
   DESCRIPTION "Updated Vectoring Feature ID 133 to revision 2 for new fallback mode support."

   REVISION "201406210000Z"
   DESCRIPTION "Added Feature ID 155 for CPOTS Ring Trip Mute Interval"

   REVISION "201406200000Z"
   DESCRIPTION "Added Feature ID 154 for bulk-data-export path support"

   REVISION "201406160000Z"
   DESCRIPTION "Added Feature ID 153 for Forwarding Group Limited"

   REVISION "201406100000Z"
   DESCRIPTION "Added Feature ID 152 for NTP broadcast client support"

   REVISION "201405160000Z"
   DESCRIPTION "Added Feature ID 151 for IPv6 support on subtended hosts"

   REVISION "201405130000Z"
   DESCRIPTION "Added Feature ID 150 for downstream min-rate"

   REVISION "201405080000Z"
   DESCRIPTION "Added Feature ID 149 to Send specified number of OAM Loopback requests"

   REVISION "201404220000Z"
   DESCRIPTION "Added Feature ID 148 for multicast CAC"

   REVISION "201404020000Z"
   DESCRIPTION "Added Feature ID 147 for centralized voice profiles"

   REVISION "201403140000Z"
   DESCRIPTION "Incremented revision for SIP over OMCI"

   REVISION "201403060000Z"
   DESCRIPTION "Added Feature ID 146 for 85 vrms ring voltage support
                   Added Feature ID 145 for setting FXS impedance by loop length"

   REVISION "201402180000Z"
   DESCRIPTION "Added Feature ID 144 for MGCP over OMCI"

   REVISION "201402070000Z"
   DESCRIPTION "Added Feature ID 143 for PonLos alarm"

   REVISION "201401300000Z"
   DESCRIPTION "Added Feature ID 142 for Cross Slot LAG"

   REVISION "201401060000Z"
   DESCRIPTION "Added Feature ID 141 for SELT/DELT Remote Device Support"

   REVISION "201312120000Z"
   DESCRIPTION "Added Feature ID 140 for EFM Peer Bonding (GPON)
                Added Feature ID 139 for ONT Rx/Tx Power
                Added Feature ID 138 for resource allocation mode"

   REVISION "201311080000Z"
   DESCRIPTION "Added Feature ID 137 for match source MAC address (aka MAC OUI)"

   REVISION "201310170000Z"
   DESCRIPTION "Added Feature ID 135 for Per Uni System Policer and 136 for Per Uni LAG Policer"

   REVISION "201310090000Z"
   DESCRIPTION "Added Feature ID 134 for Option 82 Suboption 9"

   REVISION "201310070000Z"
   DESCRIPTION "Added Feature IDs 130-133 for G.INP Downstream, G.INP Upstream, SRA and Vectoring Support"

   REVISION "201310040000Z"
   DESCRIPTION "Added Feature ID 128 for System Uni and 129 for LAG Uni"

   REVISION "201309130000Z"
   DESCRIPTION "Added Feature ID 127 for Radius Relay"

   REVISION "201309040000Z"
   DESCRIPTION "Added Feature ID 126 for SIP over OMCI Provisioning"

   REVISION "201308260000Z"
   DESCRIPTION "Added Feature ID 121 for Flex Ports, 122 for ERPSv2, 123 for Optical Carrier, 124 for Optical DCM and 125 for Optical Amplifier"

   REVISION "201307180000Z"
   DESCRIPTION "Added Feature ID 120 for Downstream P-Bit Classification Provisioning"

   REVISION "201306110000Z"
   DESCRIPTION "Added Feature ID 117 for Radius Authentication Provisioning, 118 for Radius Authentication Stats and Feature ID 119 for 802.1x Authentication"

   REVISION "201305020000Z"
   DESCRIPTION "Added Feature ID 116"

   REVISION "201304100000Z"
   DESCRIPTION "Updated Feature ID 95 version to 2 to show upper freqency limit increased to 40 MHz"

   REVISION "201303110000Z"
   DESCRIPTION "Added Feature IDs 114-115"

   REVISION "201302210000Z"
   DESCRIPTION "Added Feature IDs 109-113.  Added revision 2 for features 66 and 67 for IGMPv3 Lite"

   REVISION "201301160000Z"
   DESCRIPTION "Added Feature ID 108"

   REVISION "201211080000Z"
   DESCRIPTION "Updated Feature ID 47 version to 3 to show support for new dial plans, spre codes, and external
   line codes tables that support dialing profiles."

   REVISION "201211060000Z"
   DESCRIPTION "Added Feature ID 106 for upstream PON oversubscription and
                Feature ID 107 for fixed/assured shaper rate provisioning"

   REVISION "201210080000Z"
   DESCRIPTION "Added Feature ID 105 for downstream PON oversubscription"

   REVISION "201210040000Z"
   DESCRIPTION "Updated the revision of Feature ID 30 to indicate a change in initiation of DELT testing.
                The DELT test can know be initiated when the port is provisioned for ADSL2-multimode."

   REVISION "201209050000Z"
   DESCRIPTION "Updated description on Feature ID 103"

   REVISION "201208230000Z"
   DESCRIPTION "Added Feature IDs 103 and 104"

   REVISION "201208090000Z"
   DESCRIPTION "Added Feature IDs 102 - SHDSL Circuit Topology"

   REVISION "201207310000Z"
   DESCRIPTION "Added Feature IDs 101 - Support for RG ONT Virtual Ethernet Interface"

   REVISION "201207230000Z"
   DESCRIPTION "Added Feature IDs 99 and 100"

   REVISION "201205220825Z"
   DESCRIPTION "Bumped pseudowire revisions to 2, this means that the genPseudowireCEM* MIBS are now the preferred pseudowire MIBS."

   REVISION "201205030000Z"
   DESCRIPTION "Added Feature ID 98 for TR-177 IPv6 support"

   REVISION "201204300000Z"
   DESCRIPTION "Added Feature ID 97 Per Service / Per Uni Shaping"

   REVISION "201204200000Z"
   DESCRIPTION "Added Feature ID 96 for per service upstream shaper"

   REVISION "201204170000Z"
   DESCRIPTION "Added Feature ID 95 for Video Return Path"

   REVISION "201203060000Z"
   DESCRIPTION "Added Feature ID 94 for Ethernet Loopbacks"

   REVISION "201202060000Z"
   DESCRIPTION "Added Feature ID 93 for Gen PM support"

   REVISION "201110190000Z"
   DESCRIPTION "Corrected Revision for feature ID 54"

   REVISION "201109200000Z"
   DESCRIPTION "Added feature IDs 91-92"

   REVISION "201108290000Z"
   DESCRIPTION "Added feature ID 90"

   REVISION "201108220000Z"
   DESCRIPTION "Added feature ID 89"

   REVISION "201106220000Z"
   DESCRIPTION "Added feature ID 88"

   REVISION "201105090000Z"
   DESCRIPTION "Added feature ID 87"

   REVISION "201104180000Z"
   DESCRIPTION "Added feature ID 86"

   REVISION "201104140000Z"
   DESCRIPTION "Added feature IDs 83-85"

   REVISION "201104120000Z"
   DESCRIPTION "Added feature ID 82 for Octal GE UNI"

   REVISION "201104111551Z"
   DESCRIPTION "Added feature ID 81 for SHDSL ANFP"


   REVISION "201104071902Z"
   DESCRIPTION "Added feature ID 80 for provisionable number of CoS queues"

   REVISION "201103281500Z"
   DESCRIPTION "Added feature ID 79 for Bad Splice Detect 15 minute intervals"

   REVISION "201103241423Z"
   DESCRIPTION "Added feature ID 78 for Extended SHDSL Rates"

   REVISION "201103241100Z"
   DESCRIPTION "Added feature ID 77 for EthernetDslamFlowShaper OperStatus Support (RowStatus now means AdminStatus) "

   REVISION "201103240000Z"
   DESCRIPTION "Added feature ID 76 for DS1 test patterns"

   REVISION "201103210000Z"
   DESCRIPTION "Added new Revision for the registration ID feature(54) for the new registration mode"

   REVISION "201103080000Z"
   DESCRIPTION "Added feature IDs 69-73 for new GPON and ActiveEthernet features"

   REVISION "200705010000Z"
   DESCRIPTION "Created"
::= { adGenSystemProductID 1 }


--==================================================================================================================
    --
    -- This MIB contains OIDs to manage the common system level features across all the adtran products
    -- and the list of Feature IDs.  Please complete entries below as fully as possible.
    --
--==================================================================================================================
    --  Feature IDs

      -- FeatureID:          0
      --   Revision:         0
      --   Description:      TWAMP Reflector
      --   Assoc MIB(s):
      --   OID Branch(es):
      --   Platform:
      --   Date/Developer:
      --   SysRel/Version:

      -- FeatureID:          0
      --   Revision:         1
      --   Description:      TWAMP Reflector - Enhanced Status and Configurable UDP Port Range
      --   Assoc MIB(s):     adGenTwampReflector.mi2
      --   OID Branch(es):
      --   Platform:         NVCore Products
      --   Date/Developer:   01/19/2011 RPK
      --   SysRel/Version:   CE3.0

      -- FeatureID:          1
      --   Revision:         0
      --   Description:      TWAMP Initiator
      --   Assoc MIB(s):
      --   OID Branch(es):
      --   Platform:
      --   Date/Developer:
      --   SysRel/Version:

      -- FeatureID:          2
      --   Revision:         0
      --   Description:      802.1ag CFM
      --   Assoc MIB(s):
      --   OID Branch(es):
      --   Platform:
      --   Date/Developer:
      --   SysRel/Version:
      --   Revision:         2
      --   Description:      802.1ag CFM - MEPs on AMs and Link State Awareness available
      --   Assoc MIB(s):     genEthCfm.mi2
      --   OID Branch(es):   adGenEthCfmMepEntry
      --   Platform:         TA5k (SM and BSM AMs)
      --   Date/Developer:   12/17/2008, DCox
      --   SysRel/Version:   TA5k 04.05

      -- FeatureID:          3
      --   Revision:         0
      --   Description:      EZ Bridge Modify
      --   Assoc MIB(s):
      --   OID Branch(es):
      --   Platform:         TA5k (primarily for SM and also for EFM cards)
      --   Date/Developer:
      --   SysRel/Version:

      -- FeatureID:          4
      --   Revision:         0
      --   Description:      Constellation
      --   Assoc MIB(s):
      --   OID Branch(es):
      --   Platform:         TA5k SHDSL
      --   Date/Developer:
      --   SysRel/Version:

      -- FeatureID:          5
      --   Revision:         0
      --   Description:      ANFP
      --   Assoc MIB(s):
      --   OID Branch(es):
      --   Platform:         TA5k SHDSL
      --   Date/Developer:
      --   SysRel/Version:

      -- FeatureID:          6
      --   Revision:         0
      --   Description:      PM Reset
      --   Assoc MIB(s):
      --   OID Branch(es):
      --   Platform:
      --   Date/Developer:
      --   SysRel/Version:

      -- FeatureID:          7
      --   Revision:         0
      --   Description:      Single DS3 Bert Unf (Unf => unframed)
      --   Assoc MIB(s):
      --   OID Branch(es):
      --   Platform:
      --   Date/Developer:
      --   SysRel/Version:

      -- FeatureID:          8
      --   Revision:         0
      --   Description:      Redundancy Mode Prov v2 (SM to mean NOT the original upstream & downstream chaining)
      --   Assoc MIB(s):
      --   OID Branch(es):
      --   Platform:         TA5k SM
      --   Date/Developer:
      --   SysRel/Version:

      -- FeatureID:          9
      --   Revision:         0
      --   Description:      LACP Mode Prov
      --   Assoc MIB(s):
      --   OID Branch(es):
      --   Platform:         TA5k SM
      --   Date/Developer:
      --   SysRel/Version:

      -- FeatureID:          10
      --   Revision:         0
      --   Description:      NTP (Network Time Protocol)
      --   Assoc MIB(s):
      --   OID Branch(es):
      --   Platform:
      --   Date/Developer:
      --   SysRel/Version:

      -- FeatureID:          11
      --   Revision:         1
      --   Description:      adGenSystemFeatureSupportVersionQuery (version-indexed, version 1)
      --   Assoc MIB(s):     genSystems.mi2
      --   OID Branch(es):   adGenSystemProductEntry
      --   Platform:         Common Controller Platform (TA5K, OPTI, TA3K, OSP, PCU)
      --   Date/Developer:   10/27/2008, RJFlory
      --   SysRel/Version:   TA5K 04.01, D00.22

      -- FeatureID:          12
      --   Revision:         1
      --   Description:      adGenSystemFeatureSupportVersionQuery (version-indexed, version 2)
      --   Assoc MIB(s):     genSystems.mi2
      --   OID Branch(es):   adGenSystemProductEntry
      --   Platform:         Common Controller Platform (TA5K, OPTI, TA3K, OSP, PCU)
      --   Date/Developer:   10/27/2008, RJFlory
      --   SysRel/Version:   TA5K 04.01, D00.22

      -- FeatureID:          13
      --   Revision:         1
      --   Description:      adGenSystemFeatureSupportVersionQuery (version-indexed, version 3)
      --   Assoc MIB(s):     genSystems.mi2
      --   OID Branch(es):   adGenSystemProductEntry
      --   Platform:         *Reserved*
      --   Date/Developer:   *Reserved*
      --   SysRel/Version:   *Reserved*

      -- FeatureID:          14
      --   Revision:         1
      --   Description:      adGenSystemFeatureSupportVersionQuery (version-indexed, version 4)
      --   Assoc MIB(s):     genSystems.mi2
      --   OID Branch(es):   adGenSystemProductEntry
      --   Platform:         *Reserved*
      --   Date/Developer:   *Reserved*
      --   SysRel/Version:   *Reserved*

      -- FeatureID:          15
      --   Revision:         1
      --   Description:      adGenSystemFeatureSupportVersionQuery (version-indexed, version 5)
      --   Assoc MIB(s):     genSystems.mi2
      --   OID Branch(es):   adGenSystemProductEntry
      --   Platform:         *Reserved*
      --   Date/Developer:   *Reserved*
      --   SysRel/Version:   *Reserved*

      -- FeatureID:          16
      --   Revision:         1
      --   Description:      adGenSystemFeatureSupportVersionQuery (version-indexed, version 6)
      --   Assoc MIB(s):     genSystems.mi2
      --   OID Branch(es):   adGenSystemProductEntry
      --   Platform:         *Reserved*
      --   Date/Developer:   *Reserved*
      --   SysRel/Version:   *Reserved*

      -- FeatureID:          17
      --   Revision:         1
      --   Description:      adGenSystemFeatureSupportVersionQuery (version-indexed, version 7)
      --   Assoc MIB(s):     genSystems.mi2
      --   OID Branch(es):   adGenSystemProductEntry
      --   Platform:         Common Controller Platform (TA5K, OPTI, TA3K, OSP, PCU)
      --   Date/Developer:   *Reserved*
      --   SysRel/Version:   *Reserved*

      -- FeatureID:          18
      --   Revision:         1
      --   Description:      adGenSystemFeatureSupportVersionQuery (version-indexed, version 8)
      --   Assoc MIB(s):     genSystems.mi2
      --   OID Branch(es):   adGenSystemProductEntry
      --   Platform:         *Reserved*
      --   Date/Developer:   *Reserved*
      --   SysRel/Version:   *Reserved*

      -- FeatureID:          19
      --   Revision:         1
      --   Description:      adGenSystemFeatureSupportVersionQuery (version-indexed, version 9)
      --   Assoc MIB(s):     genSystems.mi2
      --   OID Branch(es):   adGenSystemProductEntry
      --   Platform:         *Reserved*
      --   Date/Developer:   *Reserved*
      --   SysRel/Version:   *Reserved*

      -- FeatureID:          20
      --   Revision:         1
      --   Description:      SystemControlledReboot (SCR)
      --   Assoc MIB(s):     adTASysCtrlProduct.mib
      --   OID Branch(es):   adTaSysCtrlReboot
      --   Platform:         Common Controller Platform (TA5K, OPTI, TA3K, OSP, PCU)
      --   Date/Developer:   10/27/2008, RJFlory
      --   SysRel/Version:   TA5K 04.01, D00.22

      -- FeatureID:          21
      --   Revision:         1
      --   Description:      Added single adTaSntpGMTtimeZoneString oid
      --   Assoc MIB(s):     adTASysCtrlProduct.mib
      --   OID Branch(es):   adTaSntp
      --   Platform:         Common Controller Platform (TA5K, OPTI, TA3K, OSP, PCU)
      --   Date/Developer:   10/23/2008, BPoleon
      --   SysRel/Version:   TA5K 04.01, D00.22

      -- FeatureID:          22
      --   Revision:         1
      --   Description:      EFM OAM Remote Loopback
      --   Assoc MIB(s):     genEfm.mi2
      --   OID Branch(es):   adGenEfmTestEntry
      --   Platform:         TA5k SM
      --   Date/Developer:   11/10/2008 CHodges
      --   SysRel/Version:   TA5k 04.01

      -- FeatureID:          23
      --   Revision:         1
      --   Description:      ATM Bonding supported
      --   Assoc MIB(s):     genBonding.mi2
      --   OID Branch(es):
      --   Platform:         TA5k All ADSL2+ cards (1187100L1, 1187100L2, 1187101E1, 1188101E1, etc.)
      --   Date/Developer:   12/3/2008 CHall
      --   SysRel/Version:   TA5K 04.02

      -- FeatureID:          24
      --   Revision:         1
      --   Description:      Business Service Migration (BSM) Application Flow, rev. 1
      --   Assoc MIB(s):     genEthernetDslamFlow.mi2
      --   OID Branch(es):   adGenEthernetDslamFlowEntry
      --   Platform:         TA5k Multi-service AMs (1187220G1, 1187803G1)
      --   Date/Developer:   12/16/2008 DCox
      --   SysRel/Version:   TA5k 04.05

      -- FeatureID:          25
      --   Revision:         1
      --   Description:      PPP support - no multilink
      --   Assoc MIB(s):     genPPP.mi2
      --   OID Branch(es):
      --   Platform:         TA5k SMs and Multi-service AMs (1187220G1, 1187803G1)
      --   Date/Developer:   12/16/2008 DCox
      --   SysRel/Version:   TA5k 04.05

      -- FeatureID:          25
      --   Revision:         2
      --   Description:      MLPPP support - multilink
      --   Assoc MIB(s):     genPPP.mi2
      --   OID Branch(es):
      --   Platform:         TA5k SMs and Multi-service AMs (1187220G1, 1187803G1)
      --   Date/Developer:   08/17/2009 Gfernandez
      --   SysRel/Version:   TA5k SR5.1

      -- FeatureID:          26
      --   Revision:         1
      --   Description:      IMA support
      --   Assoc MIB(s):     genIma.mi2
      --   OID Branch(es):
      --   Platform:         TA5k SMs and Multi-service AMs (1187220G1, 1187803G1)
      --   Date/Developer:   12/19/2008 DCox
      --   SysRel/Version:   TA5k 04.05

      -- FeatureID:          27
      --   Revision:         1
      --   Description:      MAC Aging
      --   Assoc MIB(s):     genMAC.mi2
      --   OID Branch(es):
      --   Platform:         NetVanta 8xx NCTEs
      --   Date/Developer:   01/12/2009 JBoyd
      --   SysRel/Version:   SR4.1.1 B02.xx

      -- FeatureID:          28
      --   Revision:         1
      --   Description:      "TA5000 Universal" analog termination support
      --   Assoc MIB(s):     adTA1500qFXOMLT.mib
      --   OID Branch(es):
      --   Platform:         TA1500 Quad CPOTS (1180407L1)
      --   Date/Developer:   1/12/2009 pkerr
      --   SysRel/Version:   TA1500 LIU T24

      -- FeatureID:          29
      --   Revision:         1
      --   Description:      Egress Queue
      --   Assoc MIB(s):     genEgressQueue.mi2
      --   OID Branch(es):
      --   Platform:         TA5000 and NCTEs
      --   Date/Developer:   1/22/2009 JBoyd
      --   SysRel/Version:   SR4.1.1

      -- FeatureID:          30
      --   Revision:         1
      --   Description:      SELT and DELT supported
      --   Assoc MIB(s):     adXdsl.mi2; adgenSeltDelt.mi2
      --   OID Branch(es):
      --   Platform:         TA5k All cards that support SELT and DELT operation (i.e. 1187100L1, 1187100L2, 1187101E1, 1188101E1, 1187120L1, 1187121L1)
      --   Date/Developer:   01/27/2009 CHall
      --   SysRel/Version:   TA5K 04.03

      -- FeatureID:          30
      --   Revision:         2
      --   Description:      The DELT test can know be initiated when the port is provisioned for ADSL2-multimode.
      --   Assoc MIB(s):     adXdsl.mi2; adgenSeltDelt.mi2
      --   OID Branch(es):
      --   Platform:         TA5k All cards that support SELT and DELT operation (i.e. 1187100L1, 1187100L2, 1187101E1, 1188101E1, 1187120L1, 1187121L1)
      --   Date/Developer:   10/4/2012 CHall
      --   SysRel/Version:   TA5K 7.0

      -- FeatureID:          31
      --   Revision:         1
      --   Description:      New GenMEF OID support for CIR and EIR
      --   Assoc MIB(s):     genMEF.mi2
      --   OID Branch(es):
      --   Platform:         NetVanta 8xx
      --   Date/Developer:   02/05/2009 JBoyd
      --   SysRel/Version:   SR4.1.1

      -- FeatureID:          32
      --   Revision:         1
      --   Description:      Support for Centralized EVC Provisioning
      --   Assoc MIB(s):     genEVC.mi2
      --   OID Branch(es):
      --   Platform:         TA5000 and OSPs
      --   Date/Developer:   Andria Dyess, Daniel Barnes
      --   SysRel/Version:   TA5k SR4.8, OSP2.5

      -- FeatureID:          33
      --   Revision:         1
      --   Description:      New common MIB for gathering information from pluggable devices (SFPs, XFPs)
      --   Assoc MIB(s):     GenPluggablePort.mi2
      --   OID Branch(es):
      --   Platform:         TA5000
      --   Date/Developer:   Andria Dyess, Jackie Zoucha
      --   SysRel/Version:   TA5k SR4.8

      -- FeatureID:          34
      --   Revision:         1 (Support for threshold provisioning and threshold-crossing alarms only)
      --   Description:      New common MIB for ethernet physical interfaces
      --   Assoc MIB(s):     GenEthIfc.mi2
      --   OID Branch(es):
      --   Platform:         TA5000
      --   Date/Developer:   Andria Dyess
      --   SysRel/Version:   TA5k SR4.8

      -- FeatureID:          35
      --   Revision:         1 (Etherflow component)
      --   Description:      Etherflow capabilities between different Versions  (GPON OLT card)
      --   Assoc MIB(s):     genEthernetDslamFlow.mi2
      --   OID Branch(es):
      --   Platform:         TA5000
      --   Date/Developer:   03/06/2009 Seetha Subramanian
      --   SysRel/Version:   TA5k SR5.0

      -- FeatureID:          36
      --   Revision:         1 (Etherflow component)
      --   Description:      Etherflow capabilities between different Versions (VDSL card)
      --   Assoc MIB(s):     genEthernetDslamFlow.mi2
      --   OID Branch(es):
      --   Platform:         TA5000
      --   Date/Developer:   03/06/2009 Seetha Subramanian
      --   SysRel/Version:   TA5k SR5.0

      -- FeatureID:          37
      --   Revision:         1 (New GPON POTS subscriber provisioning fields on the DS1 VG)
      --   Description:      New PON, ONT, and ONT Port OIDs for provisioning GPON subscribers on the DS1 VG
      --   Assoc MIB(s):     ds1VgProv.mi2, adTa5kTr08.mi2
      --   OID Branch(es):
      --   Platform:         TA5000
      --   Date/Developer:   06/30/2009 Jeremy Duncan
      --   SysRel/Version:   TA5k SR5.0

      -- FeatureID:          38
      --   Revision:         1
      --   Description:      Auto In Service Feature
      --   Assoc MIB(s):     genIf.mi2
      --   OID Branch(es):
      --   Platform:         TA5000
      --   Date/Developer:   09/28/2009 Gilbert Fernandez
      --   SysRel/Version:   TA5k SR5.1

      -- FeatureID:          39
      --   Revision:         1
      --   Description:      Pseudowire Circuit ID Provisioning
      --   Assoc MIB(s):     Pseudowire.mi2, genTa5kPseudowireMgmt.mi2
      --   OID Branch(es):
      --   Platform:         TA5000 32-Port Voice Gateway (1187800L1),
      --                            32-Port PWE3          (1187801L1),
      --                            8-Port DS1            (1187300L1),
      --                            8-Port HDSL4          (1187310L1)
      --   Date/Developer:   10/05/2009 Carl White
      --   SysRel/Version:   TA5k SR5.1

      -- FeatureID:          39
      --   Revision:         2
      --   Description:      New Pseudowire Circuit ID Provisioning using a new set of MIBS
      --   Assoc MIB(s):     genPseudowireCEMMgmt.mi2
      --   OID Branch(es):
      --   Platform:         TA5000 32-Port Voice Gateway (1187800L1),
      --                            32-Port PWE3          (1187801L1),
      --                            8-Port DS1            (1187300L1),
      --                            8-Port HDSL4          (1187310L1),
      --                            32-Port E1-CEM        (1188801G1)
      --   Date/Developer:   05/23/2012 Tim Myers
      --   SysRel/Version:   TA5k SR7.0

      -- FeatureID:          40
      --   Revision:         1
      --   Description:      Pseudowire Packet Payload Provisioning
      --   Assoc MIB(s):     Pseudowire.mi2, genTa5kPseudowireMgmt.mi2
      --   OID Branch(es):
      --   Platform:         TA5000 32-Port Voice Gateway (1187800L1),
      --                            32-Port PWE3          (1187801L1),
      --                            8-Port DS1            (1187300L1),
      --                            8-Port HDSL4          (1187310L1)
      --   Date/Developer:   10/05/2009 Carl White
      --   SysRel/Version:   TA5k SR5.1

      -- FeatureID:          40
      --   Revision:         2
      --   Description:      New Pseudowire Packet Payload Provisioning using a new set of MIBS
      --   Assoc MIB(s):     genPseudowireCEMMgmt.mi2
      --   OID Branch(es):
      --   Platform:         TA5000 32-Port Voice Gateway (1187800L1),
      --                            32-Port PWE3          (1187801L1),
      --                            8-Port DS1            (1187300L1),
      --                            8-Port HDSL4          (1187310L1),
      --                            32-Port E1-CEM        (1188801G1)
      --   Date/Developer:   05/23/2012 Tim Myers
      --   SysRel/Version:   TA5k SR7.0

      -- FeatureID:          41
      --   Revision:         1
      --   Description:      Pseudowire Advanced Provisioning
      --   Assoc MIB(s):     genTa5kPseudowireMgmt.mi2
      --   OID Branch(es):
      --   Platform:         TA5000 32-Port Voice Gateway (1187800L1),
      --                            32-Port PWE3          (1187801L1)
      --   Date/Developer:   10/05/2009 Carl White
      --   SysRel/Version:   TA5k SR5.1

      -- FeatureID:          41
      --   Revision:         2
      --   Description:      New Pseudowire Advanced Provisioning using a new set of MIBS
      --   Assoc MIB(s):     genPseudowireCEMMgmt.mi2
      --   OID Branch(es):
      --   Platform:         TA5000 32-Port Voice Gateway (1187800L1),
      --                            32-Port PWE3          (1187801L1),
      --                            32-Port E1-CEM        (1188801G1)
      --   Date/Developer:   05/23/2012 Tim Myers
      --   SysRel/Version:   TA5k SR7.0

      -- FeatureID:          42
      --   Revision:         1
      --   Description:      TSCAN FDL
      --   Assoc MIB(s):     genDslProxy.mi2, gentscan.mi2, geneshdsl.mi2
      --   OID Branch(es):
      --   Platform:         TA5000 DS1 EFM, Ch.DS3 EFM and PIVOT cards (1187220G1, 1187803G1)
      --   Date/Developer:   10/06/2009 Shobana Rao
      --   SysRel/Version:   TA5k SR5.1

      -- FeatureID:          43
      --   Revision:         1
      --   Description:      Pseudowire H4TUC Provisioning
      --   Assoc MIB(s):     genh4tuc.mib
      --   OID Branch(es):
      --   Platform:         TA5000 8-Port HDSL4 (1187310L1)
      --   Date/Developer:   10/23/2009 Shobana Rao
      --   SysRel/Version:   TA5k SR5.1

      -- FeatureID:          44
      --   Revision:         1
      --   Description:      Extended Reach TSCAN
      --   Assoc MIB(s):     gentscan.mi2
      --   OID Branch(es):
      --   Platform:         TA5000 SHDSL / NV83x / TA1448S-CE
      --   Date/Developer:   11/6/2009 Chris Hodges
      --   SysRel/Version:   TA5k SR5.1 / CERT 1.0

      -- FeatureID:          45
      --   Revision:         1
      --   Description:      Pseudowire Timing Mode Provisioning
      --   Assoc MIB(s):     genTa5kPseudowireMgmt.mi2
      --   OID Branch(es):
      --   Platform:         TA5000 32-Port Voice Gateway (1187800L1),
      --                            32-Port PWE3          (1187801L1)
      --   Date/Developer:   12/9/2009 Jeremy Duncan
      --   SysRel/Version:   TA5k SR5.1

      -- FeatureID:          45
      --   Revision:         2
      --   Description:      New Pseudowire Timing Mode Provisioning using a new MIB
      --   Assoc MIB(s):     adGenPacketTiming.mi2
      --   OID Branch(es):
      --   Platform:         TA5000 32-Port Voice Gateway (1187800L1),
      --                            32-Port PWE3          (1187801L1),
      --                            32-Port E1-CEM        (1188801G1)
      --   Date/Developer:   05/23/2012 Tim Myers
      --   SysRel/Version:   TA5k SR7.0

      -- FeatureID:          46
      --   Revision:         1 (POTS GR909 Test)
      --   Description:      Execute and report GR909 tests, results
      --   Assoc MIB(s):     GenGr909.mi2
      --   OID Branch(es):
      --   Platform:         TA5000
      --   Date/Developer:   approx. 12/15/2009 per S.Pandey and P.Kerr (recorded by T.Chard)
      --   SysRel/Version:   TA5k SR5.1

      -- FeatureID:          47
      --   Revision:         1
      --   Description:      SIP
      --   Assoc MIB(s):     genVoIP.mi2 and genSIP.mi2
      --   OID Branch(es):
      --   Platform:         TA5000 POTS products
      --   Date/Developer:   12/16/2009 Peter Kerr
      --   SysRel/Version:   TA5k SR5.1

      -- FeatureID:          47
      --   Revision:         2
      --   Description:      SIP DSCP and RTP DSCP support.
      --   Assoc MIB(s):     genVoIP.mi2 and genSIP.mi2
      --   OID Branch(es):
      --   Platform:         TA5000 POTS products
      --   Date/Developer:   01/31/2011 Mike Schroer
      --   SysRel/Version:   TA5k SR6.0

      -- FeatureID:          47
      --   Revision:         3
      --   Description:      Dialing Profiles support.
      --   Assoc MIB(s):     genVoIP.mi2
      --   OID Branch(es):
      --   Platform:         TA5000 POTS products
      --   Date/Developer:   11/05/2012 Tim Myers
      --   SysRel/Version:   TA5k SR7.2

      -- FeatureID:          48
      --   Revision:         1
      --   Description:      Double Tagging Support
      --   Assoc MIB(s):     genMEF.mi2
      --   OID Branch(es):
      --   Platform:         NetVanta 8xx
      --   Date/Developer:   2/2/2010 Joey Boyd
      --   SysRel/Version:   TA5k SR5.1

      -- FeatureID:          49
      --   Revision:         1
      --   Description:      Configurable Memory Threshold and Alarm
      --   Assoc MIB(s):     genProcesses.mi2
      --   OID Branch(es):
      --   Platform:         NetVanta 8xx
      --   Date/Developer:   2/23/2010 Joey Boyd
      --   SysRel/Version:   TA5k SR5.1

      -- FeatureID:          50
      --   Revision:         1
      --   Description:      DSCP Range in GenMEF
      --   Assoc MIB(s):     genMEF.mi2
      --   OID Branch(es):
      --   Platform:         NetVanta 8xx
      --   Date/Developer:   2/23/2010 Rick King
      --   SysRel/Version:   TA5k SR5.1

      -- FeatureID:          51
      --   Revision:         1
      --   Description:      EZ-Provisioning
      --   Assoc MIB(s):     genEZProvisioning.mi2, genSubtendedHost.mi2, genEfmNtu.mi2
      --   OID Branch(es):
      --   Platform:         TA5K, NetVanta 8xx and 8xxx
      --   Date/Developer:   5/05/2010 Byron Young
      --   SysRel/Version:   TA5K SR 5.7, CE 2.0

      -- FeatureID:          52
      --   Revision:         1
      --   Description:      genIP support of MEN priority inherit
      --   Assoc MIB(s):     genIP.mi2
      --   OID Branch(es):
      --   Platform:         OSP
      --   Date/Developer:   5/24/2010 Joey Boyd
      --   SysRel/Version:   OSP 3.2

      -- FeatureID:          53
      --   Revision:         1
      --   Description:      Remote Power-Shedding
      --   Assoc MIB(s):     adTaSysCtrlProduct.mi2
      --   OID Branch(es):
      --   Platform:         TA5K, FTTC
      --   Date/Developer:   07/22/2010 Forrest Evans
      --   SysRel/Version:   TA5K SR5.5, FTTC SR1.0

      -- FeatureID:          54
      --   Revision:         1
      --   Description:      Registration ID based ONT activation
      --   Assoc MIB(s):     adgenGpon.mi2
      --   OID Branch(es):
      --   Platform:         TA5K
      --   Date/Developer:   08/05/2010 Seetha Subramanian
      --   SysRel/Version:   TA5K SR5.5

      -- FeatureID:          54
      --   Revision:         2
      --   Description:      Fix the registration-id cannot be pre-privisioned issue.
      --   Assoc MIB(s):     adgenGpon.mi2
      --   OID Branch(es):
      --   Platform:         TA5K
      --   Date/Developer:   11/23/2010 Seetha Subramanian
      --   SysRel/Version:   TA5K SR5.5.3

      -- FeatureID:          54
      --   Revision:         3
      --   Description:      Add a new Registration ID based ONT activation mode with serial number unlock
      --   Assoc MIB(s):     adgenGpon.mi2
      --   OID Branch(es):
      --   Platform:         TA5K
      --   Date/Developer:   03/21/2011 Xiaoying Lou
      --   SysRel/Version:   TA5K SR6.0.1

      -- FeatureID:          55
      --   Revision:         1
      --   Description:      OSP VLAN Discovery
      --   Assoc MIB(s):
      --   OID Branch(es):
      --   Platform:         OSP
      --   Date/Developer:   08/09/2010 Peter Loveman
      --   SysRel/Version:   OSP SR4.0

      -- FeatureID:          56
      --   Revision:         1
      --   Description:      Voice Gateway ActiveEthenet ONT support
      --   Assoc MIB(s):
      --   OID Branch(es):
      --   Platform:         TA5K
      --   Date/Developer:   08/09/2010 Peter Loveman
      --   SysRel/Version:   TA5K SR5.5

      -- FeatureID:          57
      --   Revision:         1
      --   Description:      EVPL Cross Connects no longer supported with PPP groups
      --   Assoc MIB(s):     genEthernet.mi2
      --   OID Branch(es):
      --   Platform:         TA5k SMs and MLPPP AMs (1187220G1, 1187803G2)
      --   Date/Developer:   08/10/2010 Dennis Cox
      --   SysRel/Version:   TA5k SR6.0

      -- FeatureID:          58
      --   Revision:         1
      --   Description:      VDSL2 products Downstream Power Back Off support
      --   Assoc MIB(s):     adGenVdsl2.mi2
      --   OID Branch(es):
      --   Platform:         OSP VDSL2 DSLAMs and TA5k 32 port VDSL2 access modules
      --   Date/Developer:   8/19/2010 Robert Barrett
      --   SysRel/Version:   OSP SR3.1.3, OSP SR4.0

      -- FeatureID:          59
      --   Revision:         1
      --   Description:      Support for authenticated Etherflow EFM-Groups
      --   Assoc MIB(s):     genEthernetDslamFlow.mi2
      --   OID Branch(es):
      --   Platform:         OSP VDSL2 DSLAMs and TA5K VDSL2 access modules
      --   Date/Developer:   08/27/2010 Ben Kelley
      --   SysRel/Version:   OSP RS4.0

      -- FeatureID:          60
      --   Revision:         1
      --   Description:      Frame Relay support
      --   Assoc MIB(s):     genFrameRelay.mi2
      --   OID Branch(es):
      --   Platform:         TA5k SMs and Multi-service AMs (1187220G3, 1187803G3)
      --   Date/Developer:   08/26/2010 Gfernandez
      --   SysRel/Version:   TA5k SR5.7

      -- FeatureID:          61
      --   Revision:         2
      --   Description:      IP Host Support.  Version 2 is for connect table support.
      --   Assoc MIB(s):     genIpHost.mi2
      --   OID Branch(es):
      --   Platform:         TA5k AMs
      --   Date/Developer:   08/26/2010 Seetha Subramanian
      --   SysRel/Version:   TA5k SR5.5.1

      -- FeatureID:          62
      --   Revision:         1
      --   Description:      ANFP cal value support
      --   Assoc MIB(s):     adGenVdsl2.mi2
      --   OID Branch(es):
      --   Platform:         OSP VDSL2 DSLAMs and TA5k 32 port VDSL2 access modules
      --   Date/Developer:   10/05/2010
      --   SysRel/Version:   OSP SR3.2.1

      -- FeatureID:          63
      --   Revision:         1
      --   Description:      Node Information Advertisement support.
      --   Assoc MIB(s):     adTa5kTreeNetworking.mi2
      --   OID Branch(es):
      --   Platform:         TA5k SMs
      --   Date/Developer:   10/27/2010 Rajesh Perumal
      --   SysRel/Version:   TA5k SR5.7


      -- FeatureID: 64
      --   Revision: 1
      --   Description: 1024 max depth support for Unchan DS3 (1187260G1)
      --   Assoc MIB(s): genEgressQueue.mi2
      --   OID Branch(es):
      --   Platform: Unchannelized DS3 on TA5K
      --   Date/Developer: 10/29/2010 Munaf Musani
      --   SysRel/Version: SR6.0

      -- FeatureID:          65
      --   Revision:         1
      --   Description:      Subscriber MAC Table Support.
      --   Assoc MIB(s):     adGenMiniDslam3gMacTable.mi2
      --   OID Branch(es):
      --   Platform:         TA5k AMs
      --   Date/Developer:   11/02/2010
      --   SysRel/Version:   TA5k SR6.0

      -- FeatureID:          66
      --   Revision:         1
      --   Description:      IGMP support for SMs.
      --   Assoc MIB(s):     genIGMP.mi2
      --   OID Branch(es):
      --   Platform:         TA5k SMs
      --   Date/Developer:   02/03/2011
      --   SysRel/Version:   TA5k SR6.0

      -- FeatureID:          66
      --   Revision:         2
      --   Description:      Support for IGMP V3 Lite
      --   Assoc MIB(s):     genEVC.mi2
      --   Platform:         TA5K
      --   Date/Developer:   02/04/2013 Grant Patten
      --   SysRel/Version:   SR7.3

      -- FeatureID:          67
      --   Revision:         1
      --   Description:      IGMP support for AMs.
      --   Assoc MIB(s):     genIGMP.mi2
      --   OID Branch(es):
      --   Platform:         TA5k AMs
      --   Date/Developer:   02/03/2011
      --   SysRel/Version:   TA5k SR6.0

      -- FeatureID:          67
      --   Revision:         2
      --   Description:      Support for IGMP V3 Lite
      --   Assoc MIB(s):     genEVC.mi2
      --   Platform:         TA5K
      --   Date/Developer:   02/04/2013 Grant Patten
      --   SysRel/Version:   SR7.3

      -- FeatureID:          68
      --   Revision:         1
      --   Description:      Policer actual statistics support.
      --   Assoc MIB(s):     genEthernetDslamFlow.mi2
      --   OID Branch(es):
      --   Platform:         TA5k AMs
      --   Date/Developer:   02/18/2011
      --   SysRel/Version:   TA5k SR6.0

      -- FeatureID:          69
      --   Revision:         1
      --   Description:      ONT config file download support.
      --   Assoc MIB(s):     adGenGpon.mi2
      --   OID Branch(es):
      --   Platform:         TA5k GPON and ActiveEthernet OLTs
      --   Date/Developer:   03/04/2011
      --   SysRel/Version:   TA5k SR6.0

      -- FeatureID:          70
      --   Revision:         1
      --   Description:      GPON RSSI support.
      --   Assoc MIB(s):     adGenGpon.mi2
      --   OID Branch(es):
      --   Platform:         TA5k GPON OLT
      --   Date/Developer:   03/04/2011
      --   SysRel/Version:   TA5k SR6.0

      -- FeatureID:          71
      --   Revision:         1
      --   Description:      Enhanced ONT statistics (Eth port status and counters).
      --   Assoc MIB(s):     genEthIfc.mi2
      --   OID Branch(es):
      --   Platform:         TA5k GPON and ActiveEthernet OLTs
      --   Date/Developer:   03/04/2011
      --   SysRel/Version:   TA5k SR6.0

      -- FeatureID:          72
      --   Revision:         1
      --   Description:      ONT TR08 support and per FXS configuration GR303 or TR08.
      --   Assoc MIB(s):     adta5kpots.mi2
      --   OID Branch(es):
      --   Platform:         TA5k GPON and ActiveEthernet OLTs
      --   Date/Developer:   03/04/2011
      --   SysRel/Version:   TA5k SR6.0

      -- FeatureID:          73
      --   Revision:         1
      --   Description:      Tagged multicast at subscriber interface.
      --   Assoc MIB(s):     genEthernetDslamFlow.mi2
      --   Platform:         TA5k GPON and ActiveEthernet OLTs
      --   Date/Developer:   03/04/2011
      --   SysRel/Version:   TA5k SR6.0

      -- FeatureID:          74
      --   Revision:         1
      --   Description:      OSP Client running in legacy provisioning mode
      --   Assoc MIB(s):
      --   Platform:         OSP DSLAMs
      --   Date/Developer:   03/16/2011 Chris Hodges
      --   SysRel/Version:   OSP SR4.0

      -- FeatureID:          75
      --   Revision:         1
      --   Description:      EFM group tx and rx average percent utlization statistics.
      --   Assoc MIB(s):     genefm.mi2
      --   Platform:         Ta5k SHDSL AM's
      --   Date/Developer:   03/17/2011 Tim Rothenberger
      --   SysRel/Version:   Ta5k SR6.0

      -- FeatureID:          76
      --   Revision:         1
      --   Description:      Add DS1 test patterns (2-in-8 and 3-in-24)
      --   Assoc MIB(s):     genDS1Test.mi2
      --   Platform:         Ta5k AM's
      --   Date/Developer:   03/24/2011 Keith Baird
      --   SysRel/Version:   Ta5k SR6.0

      -- FeatureID:          77
      --   Revision:         1
      --   Description:      Ethernet Flow Shaper RowStatus OID now means AdminStatus; OperStatus OID is functional
      --   Assoc MIB(s):     genEthernetDslamFlow.mi2
      --   Platform:         TA5K and OSP EthernetDslamFlow Implementers
      --   Date/Developer:   03/22/2011 Ben Kelley
      --   SysRel/Version:   TA5k SR6.0

      -- FeatureID:          78
      --   Revision:         1
      --   Description:      Extended SHDSL Rate Support
      --   Assoc MIB(s):     geneshdsl.mi2
      --   Platform:         NV83x, TA1448S-CE, TA5k SHDSL AMs w/MLT
      --   Date/Developer:   03/24/2011 Joey Boyd
      --   SysRel/Version:   Future CE release beyond 3.2; Future SR release beyond 6.0

      -- FeatureID:          79
      --   Revision:         1
      --   Description:      Bad Splice Detect 15 minute intervals
      --   Assoc MIB(s):     geneshdsl.mi2
      --   Platform:         NV83x, TA1448S-CE, TA5k SHDSL AMs w/MLT
      --   Date/Developer:   03/28/2011 Joey Boyd
      --   SysRel/Version:   Future CE release beyond 3.2; Future SR release beyond 6.0

      -- FeatureID:          80
      --   Revision:         1
      --   Description:      Provisionable number of CoS queues
      --   Assoc MIB(s):     genEgressQueue.mi2
      --   Platform:         TA5000
      --   Date/Developer:   04/07/2011 AED
      --   SysRel/Version:   TA5K SR6.0

      -- FeatureID:          81
      --   Revision:         1
      --   Description:      Feature ID for SHDSL ANFP support
      --   Assoc MIB(s):     geneshsdsl.mi2
      --   Platform:         NV83x, TA1448S-CE, TA5k SHDSL AMs w/MLT
      --   Date/Developer:   04/04/2011 Robert Barrett
      --   SysRel/Version:   TA5k SR6.0. Future CE release beyond 3.2

      -- FeatureID:          82
      --   Revision:         1
      --   Description:      OctalGE UNI
      --   Assoc MIB(s):     genEthernetDslamFlow.mi2
      --   Platform:         TA5000
      --   Date/Developer:   04/12/2011 SPM
      --   SysRel/Version:   TA5K SR6.0

      -- FeatureID:          83
      --   Revision:         1
      --   Description:      Expanded SHDSL PM
      --   Assoc MIB(s):     geneshdsl.mi2
      --   Platform:         NV83x, TA1448S-CE, TA5k SHDSL AMs w/MLT
      --   Date/Developer:   04/13/2011 Joey Boyd
      --   SysRel/Version:   Future CE release beyond 3.2; Future SR release beyond 6.0

      -- FeatureID:          84
      --   Revision:         1
      --   Description:      ONT RF port status and thresholding support.
      --   Assoc MIB(s):     adGenGpon.mi2
      --   Platform:         TA5k GPON OLTs
      --   Date/Developer:   04/13/2011 Jackson Pan
      --   SysRel/Version:   TA5K SR6.0

      -- FeatureID:          84
      --   Revision:         1
      --   Description:      ONT RF port status and thresholding support.
      --   Assoc MIB(s):     adGenGpon.mi2
      --   Platform:         TA5k GPON OLTs
      --   Date/Developer:   04/13/2011 Jackson Pan
      --   SysRel/Version:   TA5K SR6.0

      -- FeatureID:          85
      --   Revision:         1
      --   Description:      Encoded sub-interface index from VPI/VCI for ATM interfaces.
      --   Assoc MIB(s):     genEthernetDslamFlow.mi2
      --   Platform:         TA5k SM, ADSL, VDSL
      --   Date/Developer:   04/14/2011 Ben Kelley
      --   SysRel/Version:   TA5K SR6.0

      -- FeatureID:          86
      --   Revision:         1
      --   Description:      EFM Link Status String support
      --   Assoc MIB(s):     genefmext.mi2
      --   Platform:         NV8xx, TA5k EoX AMs
      --   Date/Developer:   04/18/2011 Chris Hodges
      --   SysRel/Version:   Future CE release beyond 3.2; SR 6.0

      -- FeatureID:          87
      --   Revision:         1
      --   Description:      Ethercraft support
      --   Assoc MIB(s):     adTaSysCtrlProduct.mi2
      --   Platform:         TA5K, OSP
      --   Date/Developer:   05/09/2011 Forrest Evans
      --   SysRel/Version:   SR 6.0

      -- FeatureID:          88
      --   Revision:         1
      --   Description:      ONT Upstream Shaping
      --   Assoc MIB(s):     genEthernetDslamFlow.mi2
      --   Platform:         TA5K
      --   Date/Developer:   06/22/2011 Patrick Viafore
      --   SysRel/Version:   SR 6.0

      -- FeatureID:          89
      --   Revision:         1
      --   Description:      BBDLC Shaper Improvements
      --   Assoc MIB(s):     genEthernetDslamFlow.mi2
      --   Platform:         TA5K
      --   Date/Developer:   08/17/2011 Peter Loveman
      --   SysRel/Version:   SR 6.0

      -- FeatureID:          90
      --   Revision:         1
      --   Description:      Identify EFM Link/EFM Group ifIndex offset. Version 1->(1000/2000), Version 2->(10000/40000)
      --   Assoc MIB(s):     All EFM Link/EFM Group
      --   Platform:         TA5K
      --   Date/Developer:   08/29/2011 Sean Dowell
      --   SysRel/Version:   SR 6.0

      -- FeatureID:          91
      --   Revision:         1
      --   Description:      VDSL2 Tx Line Rates and Previous Tx Line Rates
      --   Assoc MIB(s):     adGenVdsl2.mi2
      --   Platform:         TA5K VDSL Cards
      --   Date/Developer:   09/19/2011 Craye Hall
      --   SysRel/Version:   SR 6.x

      -- FeatureID:          92
      --   Revision:         1
      --   Description:      Remote ID support
      --   Assoc MIB(s):     genEthernetDslamFlow.mi2
      --   Platform:         TA5K
      --   Date/Developer:   09/20/2011 Tim Scott
      --   SysRel/Version:   SR 6.0.1

      -- FeatureID:          93
      --   Revision:         1
      --   Description:      Gen PM support
      --   Assoc MIB(s):     adGenPm.mi2
      --   Platform:         TA5K
      --   Date/Developer:   02/06/2012 Sean Dowell
      --   SysRel/Version:   SR 6.2

      -- FeatureID:          94
      --   Revision:         1
      --   Description:      Ethernet Loopbacks
      --   Assoc MIB(s):     genEthLbk.mi2
      --   Platform:         TA5K
      --   Date/Developer:   03/01/2012 Joey Boyd
      --   SysRel/Version:   CE 5.0

      -- FeatureID:          95
      --   Revision:         1
      --   Description:      Video Return Path
      --   Assoc MIB(s):     adGenGpon.mi2
      --   Platform:         TA5K
      --   Date/Developer:   04/17/2012 Massimo Galliano
      --   SysRel/Version:   SR 6.2

      -- FeatureID:          95
      --   Revision:         2
      --   Description:      Video Return Path Updated VRP frequency Limit
      --   Assoc MIB(s):     adGenGpon.mi2
      --   Platform:         TA5K
      --   Date/Developer:   04/10/2013 Massimo Galliano
      --   SysRel/Version:   SR 7.3

      -- FeatureID:          96
      --   Revision:         1
      --   Description:      Per service upstream shaper
      --   Assoc MIB(s):     genEthernetDslamFlow.mi2
      --   Platform:         TA5K
      --   Date/Developer:   04/20/2012 Massimo Galliano
      --   SysRel/Version:   SR 6.3

      -- FeatureID:          97
      --   Revision:         1
      --   Description:      Per Service / Per Uni Shaping
      --   Assoc MIB(s):     genQosMapProfile.mi2
      --   Platform:         TA5K SMs, Active Ethernet AMs, Active Ethernet Pizza Box, GPON AMs
      --   Date/Developer:   04/24/2012 Patrick Viafore
      --   SysRel/Version:   SR 7.0

      -- FeatureID:          98
      --   Revision:         1
      --   Description:      TR-177 IPv6 support
      --   Assoc MIB(s):     genEthernetDslamFlow.mi2
      --   Platform:         TA5K and OSP
      --   Date/Developer:   05/03/2012 Tim Scott
      --   SysRel/Version:   SR 7.0

      -- FeatureID:          99
      --   Revision:         1
      --   Description:      SHDSL Repeater Powering
      --   Assoc MIB(s):     geneshdsl.mi2
      --   Platform:         TA5K and NCTE
      --   Date/Developer:   07/11/2012 Joey Boyd
      --   SysRel/Version:   Post-PSI3 CE and SR

      -- FeatureID:         100
      --   Revision:         1
      --   Description:      Queue Cos mode
      --   Assoc MIB(s):     genEgressQueue.mi2
      --   Platform:         TA5K and NetVanta
      --   Date/Developer:   07/18/2012 Seetha Subramanian
      --   SysRel/Version:   SR 7.0

      -- FeatureID:         101
      --   Revision:         1
      --   Description:      Virtual Ethernet Interface
      --   Assoc MIB(s):     adGenGpon.mi2
      --   Platform:         TA5K
      --   Date/Developer:   07/31/2012 Massimo Galliano
      --   SysRel/Version:   Post-PSI3

      -- FeatureID:          102
      --   Revision:         1
      --   Description:      SHDSL Circuit Topology
      --   Assoc MIB(s):     geneshdsl.mi2
      --   Platform:         TA5K and NCTE
      --   Date/Developer:   07/31/2012 Joey Boyd
      --   SysRel/Version:   Post-PSI3 CE and SR

      -- FeatureID:          103
      --   Revision:         1
      --   Description:      Extended Remote ifIndices to support up to 255 ONTs per PON and up to 15 PONs per OLT.
      --                     Also indicates support for adGenGponOltMaxOntsPerPon and adGenGponOltNumPons in
      --                     adGenGpon.mi2
      --   Assoc MIB(s):     All GPON
      --   Platform:         TA5K Quad OLT, Future GPON Pizza Box
      --   Date/Developer:   09/05/2012 Ron Zuckerman
      --   SysRel/Version:   Post-PSI4

      -- FeatureID:          104
      --   Revision:         2
      --   Description:      FXO Interface
      --   Assoc MIB(s):     genFXO.mi2
      --   Platform:         TA5K
      --   Date/Developer:   08/23/2012 Peter Kerr
      --   SysRel/Version:   SR6.3.1 and SR7.0

      -- FeatureID:          105
      --   Revision:         1
      --   Description:      PON Downstream oversubscription
      --   Assoc MIB(s):     adGenGpon.mi2
      --   Platform:         TA5K
      --   Date/Developer:   10/08/2012 Tim Scott
      --   SysRel/Version:   SR7.1

      -- FeatureID:          106
      --   Revision:         1
      --   Description:      PON Upstream oversubscription
      --   Assoc MIB(s):     adGenGpon.mi2
      --   Platform:         TA5K
      --   Date/Developer:   11/01/2012 Tim Scott
      --   SysRel/Version:   SR7.1

      -- FeatureID:          107
      --   Revision:         1
      --   Description:      Fixed and assured shaper rate provisioning
      --   Assoc MIB(s):     genEthernetDslamFlow.mi2
      --   Platform:         TA5K
      --   Date/Developer:   11/01/2012 Tim Scott
      --   SysRel/Version:   SR7.1

      -- FeatureID:          108
      --   Revision:         1
      --   Description:      Support of 2^64 counters and threshold for genMEF policer counts
      --   Assoc MIB(s):     genMEF.mi2
      --   Platform:         NV
      --   Date/Developer:   01/16/2013 Andy Ruble
      --   SysRel/Version:   CE 5.2.2

      -- FeatureID:          109
      --   Revision:         1
      --   Description:      Support of TR069
      --   Assoc MIB(s):     adGenAcsServerProfile.mi2, adGenGpon.mi2
      --   Platform:         TA5K
      --   Date/Developer:   02/06/2013 Massimo Galliano
      --   SysRel/Version:   SR7.3

      -- FeatureID:          110
      --   Revision:         1
      --   Description:      Support of Whole Home DVR
      --   Assoc MIB(s):     adGenGpon.mi2
      --   Platform:         TA5K
      --   Date/Developer:   02/06/2013 Massimo Galliano
      --   SysRel/Version:   SR7.3

      -- FeatureID:          111
      --   Revision:         1
      --   Description:      Support for Dynamic Counters provisioning/status
      --   Assoc MIB(s):     genDynamicCounters.mi2
      --   Platform:         TA5K
      --   Date/Developer:   02/11/2013 - Jackie Zoucha
      --   SysRel/Version:   SR7.3

      -- FeatureID:          112
      --   Revision:         1
      --   Description:      Netvanta  Shaper
      --   Assoc MIB(s):     ADTRAN-GENSHAPER-MIB
      --   OID Branch(es):
      --   Platform:         NetVanta 8xx and 8xxx
      --   Date/Developer:   Byron Young
      --   SysRel/Version:   CE5.2.3

      -- FeatureID:          112
      --   Revision:         2
      --   Description:      Netvanta  Shaper Burst Size
      --   Assoc MIB(s):     ADTRAN-GENSHAPER-MIB
      --   OID Branch(es):
      --   Platform:         NetVanta 8xx and 8xxx
      --   Date/Developer:   Byron Young
      --   SysRel/Version:   CE5.2.3

      -- FeatureID:          113
      --   Revision:         1
      --   Description:      Support IGMP Forking
      --   Assoc MIB(s):     genEthernetDslamFlow.mi2
      --   Platform:         TA5K/OSP
      --   Date/Developer:   02/19/2013 Team Anostos
      --   SysRel/Version:   SR7.3

      -- FeatureID:          114
      --   Revision:         1
      --   Description:      Support for p-bit remapping
      --   Assoc MIB(s):     adTa5kPbitRemapping.mi2
      --   Platform:         TA5K SM
      --   Date/Developer:   02/28/2013 Andria Dyess
      --   SysRel/Version:   SR7.3

      -- FeatureID:          115
      --   Revision:         1
      --   Description:      PTM Fallback Supported
      --   Assoc MIB(s):     adGenVdsl2.mi2
      --   Platform:         3rdGen OSP
      --   Date/Developer:   03/08/2013 DSL Driver Team
      --   SysRel/Version:   OSP SR5.2

      -- FeatureID:          116
      --   Revision:         1
      --   Description:      IGMP Authentication Disable Supported
      --   Assoc MIB(s):     genIGMP.mi2
      --   Platform:         TA5K
      --   Date/Developer:   05/02/2013 GPON Team
      --   SysRel/Version:   PSI-7

      -- FeatureID:          117
      --   Revision:         1
      --   Description:      Radius Authentication Provisioning
      --   Assoc MIB(s):     genRadiusAuth.mi2
      --   Platform:         TA5K
      --   Date/Developer:   06/11/2013 Anostos Team
      --   SysRel/Version:   PSI-8

      -- FeatureID:          118
      --   Revision:         1
      --   Description:      Radius Authentication Stats
      --   Assoc MIB(s):     genRadiusAuth.mi2
      --   Platform:         TA5K
      --   Date/Developer:   06/11/2013 Anostos Team
      --   SysRel/Version:   PSI-8

      -- FeatureID:          119
      --   Revision:         1
      --   Description:      802.1x Authentication
      --   Assoc MIB(s):   ieee8021x.mib
      --   Platform:         TA5K
      --   Date/Developer:   06/11/2013 Anostos Team
      --   SysRel/Version:   PSI-8

      -- FeatureID:          120
      --   Revision:         1
      --   Description:      Downstream P-Bit classification
      --   Assoc MIB(s):     genEthernetDslamFlow.mi2
      --   Platform:         TA5K
      --   Date/Developer:   07/18/2013 Eagles Team
      --   SysRel/Version:   PSI-8

      -- FeatureID:          121
      --   Revision:         1
      --   Description:      Flex Ports
      --   Assoc MIB(s):     genMuxponder.mi2, genMEVC.mi2
      --   Platform:         TA5K/ONE
      --   Date/Developer:   08/26/2013 Anil Shah
      --   SysRel/Version:   PSI-8

      -- FeatureID:          122
      --   Revision:         1
      --   Description:      ERPSv2
      --   Assoc MIB(s):     ADTRAN-ERPS-MIB.mi2
      --   Platform:         TA5K/ONE
      --   Date/Developer:   08/26/2013 Bruce Bender
      --   SysRel/Version:   PSI-8

      -- FeatureID:          123
      --   Revision:         1
      --   Description:      Optical Carrier support
      --   Assoc MIB(s):     genOpticalCarrier.mi2, gensubslot.mi2
      --   Platform:         TA5K/ONE
      --   Date/Developer:   08/26/2013 James Chen
      --   SysRel/Version:   PSI-8

      -- FeatureID:          124
      --   Revision:         1
      --   Description:      Optical DCM support
      --   Assoc MIB(s):     genOpticalDCM.mi2
      --   Platform:         TA5K/ONE
      --   Date/Developer:   08/26/2013 James Chen
      --   SysRel/Version:   PSI-8

      -- FeatureID:          125
      --   Revision:         1
      --   Description:      Optical Amplifier support
      --   Assoc MIB(s):     genOpticalAmplifier.mi2
      --   Platform:         TA5K/ONE
      --   Date/Developer:   08/26/2013 James Chen
      --   SysRel/Version:   PSI-8

      -- FeatureID:          126
      --   Revision:         2
      --   Description:      SIP over OMCI
      --   Assoc MIB(s):     genVoIP.mi2, adGenVoiceUserMgmt.mi2
      --   Platform:         TA5K
      --   Date/Developer:   09/04/2013 Spartans Team
      --   SysRel/Version:   PSI-9

      -- FeatureID:          127
      --   Revision:         1
      --   Description:      Radius Relay
      --   Assoc MIB(s):     genRadiusAuth.mi2
      --   Platform:         ANOSTOS
      --   Date/Developer:   09/13/2013 G. Fernandez
      --   SysRel/Version:   PSI-9

      -- FeatureID:          128
      --   Revision:         1
      --   Description:      System Uni
      --   Assoc MIB(s):     genEVCMap.mi2
      --   Platform:         TA5K/ONE
      --   Date/Developer:   10/04/2013 Anil Shah
      --   SysRel/Version:   PSI-9

      -- FeatureID:          129
      --   Revision:         1
      --   Description:      LAG Uni
      --   Assoc MIB(s):     genEVCMap.mi2
      --   Platform:         TA5K/ONE
      --   Date/Developer:   10/04/2013 Anil Shah
      --   SysRel/Version:   PSI-9

      -- FeatureID:          130
      --   Revision:         1
      --   Description:      DSL G.INP Downstream Supported
      --   Assoc MIB(s):     adGenVdsl2.mi2
      --   Platform:         TA5K and OSP
      --   Date/Developer:   10/07/2013 DSL Driver & Scramblers Teams
      --   SysRel/Version:   PSI-9

      -- FeatureID:          131
      --   Revision:         1
      --   Description:      DSL G.INP Upstream Supported
      --   Assoc MIB(s):     adGenVdsl2.mi2
      --   Platform:         TA5K and OSP
      --   Date/Developer:   10/07/2013 DSL Driver & Scramblers Teams
      --   SysRel/Version:   PSI-9

      -- FeatureID:          132
      --   Revision:         1
      --   Description:      DSL SRA Supported
      --   Assoc MIB(s):     adGenVdsl2.mi2
      --   Platform:         TA5K and OSP
      --   Date/Developer:   10/07/2013 DSL Driver & Scramblers Teams
      --   SysRel/Version:   PSI-9

      -- FeatureID:          133
      --   Revision:         2
      --   Description:      DSL Vectoring Supported.  Version 2 adds fallback mode.
      --   Assoc MIB(s):     adGenVdsl2.mi2
      --   Platform:         TA5K and OSP
      --   Date/Developer:   10/07/2013 Scramblers Team
      --   SysRel/Version:   PSI-9

      -- FeatureID:          134
      --   Revision:         1
      --   Description:      Option 82 Sub-option 9
      --   Assoc MIB(s):     genEthernetDslamFlow.mi2
      --   Platform:         TA5K/ONE
      --   Date/Developer:   10/09/2013 Craye Hall
      --   SysRel/Version:   PSI-9

      -- FeatureID:          135
      --   Revision:         1
      --   Description:      Per Uni System Policer
      --   Assoc MIB(s):     genPolicer.mi2
      --   Platform:         TA5K/ONE
      --   Date/Developer:   10/17/2013 Anil Shah
      --   SysRel/Version:   PSI-9

      -- FeatureID:          136
      --   Revision:         1
      --   Description:      Per Uni LAG Policer
      --   Assoc MIB(s):     genPolicer.mi2
      --   Platform:         TA5K/ONE
      --   Date/Developer:   10/17/2013 Anil Shah
      --   SysRel/Version:   PSI-9

      -- FeatureID:          137
      --   Revision:         1
      --   Description:      Match source MAC address (aka MAC OUI)
      --   Assoc MIB(s):     genEthernetDslamFlow.mi2
      --   Platform:         TA5K
      --   Date/Developer:   11/08/2013 Ron Zuckerman
      --   SysRel/Version:   PSI-10

      -- FeatureID:          138
      --   Revision:         1
      --   Description:      Resource allocation mode
      --   Assoc MIB(s):     adGenGpon.mi2
      --   Platform:         TA5K
      --   Date/Developer:   12/12/2013 Connor Lawson
      --   SysRel/Version:   PSI-10

      -- FeatureID:          139
      --   Revision:         1
      --   Description:      ONT Rx/Tx Power
      --   Assoc MIB(s):     adGenGpon.mi2
      --   Platform:         TA5K
      --   Date/Developer:   12/12/2013 Xiaoying Lou
      --   SysRel/Version:   PSI-10

      -- FeatureID:          140
      --   Revision:         1
      --   Description:      EFM Peer Bonding
      --   Assoc MIB(s):     adGenGpon.mi2
      --   Platform:         TA5K
      --   Date/Developer:   12/12/2013 Robert Barrett
      --   SysRel/Version:   PSI-9

      -- FeatureID:          141
      --   Revision:         1
      --   Description:      The SELT/DELT can now be started at a remote device.
      --   Assoc MIB(s):     adgenSeltDelt.mi2
      --   Platform:         TA5k
      --   Date/Developer:   01/06/2014 Albert Sue
      --   SysRel/Version:   PSI-10

      -- FeatureID:          142
      --   Revision:         1
      --   Description:      Cross Slot LAG.
      --   Assoc MIB(s):     genMuxponder.mi2
      --   Platform:         TA5K/ONE
      --   Date/Developer:   01/30/2014 Bruce Bender
      --   SysRel/Version:   PSI-10

      -- FeatureID:          143
      --   Revision:         1
      --   Description:      PonLos alarm
      --   Assoc MIB(s):     adGenGpon.mi2
      --   Platform:         TA5K
      --   Date/Developer:   02/7/2014 Alex Melton
      --   SysRel/Version:   PSI-11

      -- FeatureID:          144
      --   Revision:         1
      --   Description:      MGCP Over OMCI
      --   Assoc MIB(s):     genVoIP.mi2, genMGCP.mi2
      --   Platform:         TA5K
      --   Date/Developer:   02/18/2014 Massimo Galliano
      --   SysRel/Version:   PSI-11

      -- FeatureID:          145
      --   Revision:         1
      --   Description:      Setting FXS impedance by loop length
      --   Assoc MIB(s):     adta5kpots.mi2
      --   Platform:         TA5K
      --   Date/Developer:   03/06/2014 Jason Brock
      --   SysRel/Version:   PSI-11

      -- FeatureID:          146
      --   Revision:         1
      --   Description:      Support for 85 vrms ring voltage
      --   Assoc MIB(s):     adta5kpots.mi2
      --   Platform:         TA5K
      --   Date/Developer:   03/06/2014 Jason Brock
      --   SysRel/Version:   PSI-11

      -- FeatureID:          147
      --   Revision:         1
      --   Description:      Centralized voice profiles
      --   Assoc MIB(s):     genVoIP.mi2, genMGCP.mi2
      --   Platform:         TA5K
      --   Date/Developer:   04/02/2014 Massimo Galliano
      --   SysRel/Version:   PSI-10

      -- FeatureID:          148
      --   Revision:         1
      --   Description:      multicast CAC
      --   Assoc MIB(s):     adGenGpon.mi2
      --   Platform:         TA5K
      --   Date/Developer:   04/22/2014 Ganesh Ganesan
      --   SysRel/Version:   PSI-12

      -- FeatureID:          149
      --   Revision:         1
      --   Description:      Send specified number of OAM Loopback requests
      --   Assoc MIB(s):     adta5kgenOam.mi2
      --   Platform:         TA5K
      --   Date/Developer:   05/08/2014 Josh Horton
      --   SysRel/Version:   PSI-12

      -- FeatureID:          150
      --   Revision:         1
      --   Description:      Downstream min-rate
      --   Assoc MIB(s):     adGenGpon.mi2, genEthernetDsalmFlow.mi2
      --   Platform:         TA5K
      --   Date/Developer:   05/13/2014 Massimo Galliano
      --   SysRel/Version:   PSI-12

      -- FeatureID:          151
      --   Revision:         1
      --   Description:      IPV6 support for subtended host
      --   Assoc MIB(s):     genEfmNtu.mi2,  genSubtendedHost.mi2, genTA8xx.mi2
      --   Platform:         TA5K, NCTE
      --   Date/Developer:   05/16/2014 Byron Young
      --   SysRel/Version:   PSI-12

      -- FeatureID:          152
      --   Revision:         1
      --   Description:      NTP support for broadcast client
      --   Assoc MIB(s):     genNTP.mi2
      --   Platform:         NCTE
      --   Date/Developer:   06/10/2014 Sean Osborne
      --   SysRel/Version:   CE6.0

      -- FeatureID:          153
      --   Revision:         1
      --   Description:      Forwarding Group Limited
      --   Assoc MIB(s):     genMuxponder.mi2
      --   Platform:         TA5K/ONE
      --   Date/Developer:   06/16/2014 Bruce Bender
      --   SysRel/Version:   PSI-13

      -- FeatureID:          154
      --   Revision:         1
      --   Description:      Bulk-data-export Path
      --   Assoc MIB(s):     adTAeSCU.mi2
      --   Platform:         TA5K/ONE
      --   Date/Developer:   06/20/2014 Sean Osborne
      --   SysRel/Version:   PSI-12

      -- FeatureID:          155
      --   Revision:         1
      --   Description:      CPOTS support for Ring Trip Mute Interval
      --   Assoc MIB(s):     genFXO.mi2
      --   Platform:         TA5K
      --   Date/Developer:   6/19/2014 David Wachira
      --   SysRel/Version:   PSI-12, SR7.4

      -- FeatureID:          156
      --   Revision:         1
      --   Description:      128 ONT support for GPON OLT
      --   Assoc MIB(s):     adGenGpon.mi2
      --   Platform:         TA5K
      --   Date/Developer:   6/27/2014 Munaf Musani
      --   SysRel/Version:   PSI-13, SR8.7

     -- FeatureID:          157
      --   Revision:         1
      --   Description:      DSCP support for GPON OLT
      --   Assoc MIB(s):     genEthernetDslamFlow.mi2
      --   Platform:         TA5K
      --   Date/Developer:   6/27/2014 Munaf Musani
      --   SysRel/Version:   PSI-13, SR8.7

      -- FeatureID:          158
      --   Revision:         1
      --   Description:      Auto-Config for subtended-host
      --   Assoc MIB(s):     genEfmNtu.mi2, genSubtendedHost.mi2
      --   Platform:         TA5K
      --   Date/Developer:   09/22/2014 Byron Young
      --   SysRel/Version:   PSI-14

      -- FeatureID:          159
      --   Revision:         1
      --   Description:      Auto-Discovery for subtended-host
      --   Assoc MIB(s):     genEfmNtu.mi2,  genSubtendedHost.mi2
      --   Platform:         TA5K
      --   Date/Developer:   09/22/2014 Byron Young
      --   SysRel/Version:   PSI-14

      -- FeatureID:          160
      --   Revision:         1
      --   Description:      Match non-IP customer ingress traffic support
      --   Assoc MIB(s):     genEthernetDslamFlow.mi2
      --   Platform:         TA5K
      --   Date/Developer:   9/15/2014 Seetha Subramanian
      --   SysRel/Version:   PSI-14, SR8.7

      -- FeatureID:          161
      --   Revision:         1
      --   Description:      SIP support for Dialing Profile Description
      --   Assoc MIB(s):     genVoIP.mi2
      --   Platform:         TA5K
      --   Date/Developer:   9/30/2014 David Wachira
      --   SysRel/Version:   SR8.7, PSI-14

      -- FeatureID:          162
      --   Revision:         1
      --   Description:      Auto-Config support
      --   Assoc MIB(s):     genAutoConfig.mi2
      --   Platform:         NCTE
      --   Date/Developer:   10/13/2014 Byron Young
      --   SysRel/Version:   CE 6.1

      -- FeatureID:          163
      --   Revision:         1
      --   Description:      Adding new OID to read AMIO Part Number and Description
      --   Assoc MIB(s):     adta5kgenslot.mi2
      --   Platform:         TA5K
      --   Date/Developer:   10/15/2014 Makenzie Wright
      --   SysRel/Version:   SR8.7, PSI-14

      -- FeatureID:          164
      --   Revision:         1
      --   Description:      Added new OID to retrieve bulk voice users
      --   Assoc MIB(s):     genVoIP.mi2
      --   Platform:         TA5K
      --   Date/Developer:   10/31/2014 David Wachira
      --   SysRel/Version:   SR8.5.1, SR8.7, PSI-14

      -- FeatureID:          165
      --   Revision:         1
      --   Description:      Upstream Forward Error Correction (FEC) on 4th Gen GPON OLT
      --   Assoc MIB(s):     adGenGpon.mi2
      --   Platform:         TA5K
      --   Date/Developer:   12/05/2014 Jason Brock
      --   SysRel/Version:   SR9.0

      -- FeatureID:          166
      --   Revision:         1
      --   Description:      Evc-map Match DA
      --   Assoc MIB(s):     genEVCMap.mi2
      --   Platform:         TA5K/ONE
      --   Date/Developer:   12/04/2014 Bhushan Parikh
      --   SysRel/Version:   PSI-15

      -- FeatureID:          167
      --   Revision:         1
      --   Description:      ERPS V2 Ladders
      --   Assoc MIB(s):     ADTRAN-ERPS-MIB.mi2
      --   Platform:         TA5K/ONE
      --   Date/Developer:   12/04/2014 Bruce Bender
      --   SysRel/Version:   PSI-15

      -- FeatureID:          168
      --   Revision:         1
      --   Description:      ERPS MIB Provisioning
      --   Assoc MIB(s):     ADTRAN-ERPS-MIB.mi2
      --   Platform:         TA5K/ONE
      --   Date/Developer:   12/04/2014 Bhushan Parikh
      --   SysRel/Version:   PSI-15

      -- FeatureID:          169
      --   Revision:         1
      --   Description:      Defer activation and commit of ONT software image after a software download
      --   Assoc MIB(s):     adGenGpon.mi2
      --   Platform:         TA5k
      --   Date/Developer:   12/10/2014 Shobana Rao
      --   SysRel/Version:   PSI-15

      -- FeatureID:          170
      --   Revision:         1
      --   Description:      Link State Awareness Alarm
      --   Assoc MIB(s):     genTA8xx.mi2
      --   Platform:         NCTE
      --   Date/Developer:   12/15/2014 Sean Osborne
      --   SysRel/Version:   CE6.2

      -- FeatureID:          171
      --   Revision:         1
      --   Description:      Added new OIDs to display PWE Detailed Operational Status
      --   Assoc MIB(s):     genPseudowireCEMMgmt.mi2
      --   Platform:         TA5K
      --   Date/Developer:   12/17/2014 David Wachira
      --   SysRel/Version:   PSI-15

      -- FeatureID:          172
      --   Revision:         1
      --   Description:      ONT Invalid SN alarms
      --   Assoc MIB(s):     adGenGpon.mi2
      --   Platform:         TA5K
      --   Date/Developer:   01/06/2015 Jason Bao
      --   SysRel/Version:   PSI-15

      -- FeatureID:          173
      --   Revision:         1
      --   Description:      AM Frequency Masking
      --   Assoc MIB(s):     adGenVdsl2.mi2
      --   Platform:         TA5K
      --   Date/Developer:   01/22/2015 Gary Hunt
      --   SysRel/Version:   PSI-15

      -- FeatureID:          174
      --   Revision:         1
      --   Description:      ONT Software Image
      --   Assoc MIB(s):     adGenGpon.mi2
      --   Platform:         TA5K
      --   Date/Developer:   02/23/2015 John Lu
      --   SysRel/Version:   PSI-16

      -- FeatureID:          175
      --   Revision:         1
      --   Description:      VDSL link-down alarm severity provisioning on GPON OLT
      --   Assoc MIB(s):     adGenVdsl2.mi2
      --   Platform:         TA5K
      --   Date/Developer:   03/19/2015 Shobana Rao
      --   SysRel/Version:   PSI-16

      -- FeatureID:          176
      --   Revision:         1
      --   Description:      Domain Name and DNS in IP Host for GPON/AE OLT
      --   Assoc MIB(s):     genIpHost.mi2
      --   Platform:         TA5K
      --   Date/Developer:   05/07/2015 Massimo Galliano
      --   SysRel/Version:   PSI-17

      -- FeatureID:          177
      --   Revision:         1
      --   Description:      Reset PON upstream and downstream BIP counters for GPON OLT
      --   Assoc MIB(s):     adGenGpon.mi2
      --   Platform:         TA5K
      --   Date/Developer:   08/05/2015 Seetha Subramanian
      --   SysRel/Version:   PSI-18, SR_9.0.1

      -- FeatureID:          178
      --   Revision:         1
      --   Description:      Memory Split Ratio for VDSL
      --   Assoc MIB(s):     adGenVdsl2.mi2
      --   Platform:         TA5K
      --   Date/Developer:   08/12/2015 Josh Horton
      --   SysRel/Version:   PSI-18

      -- FeatureID:          179
      --   Revision:         1
      --   Description:      Downstream SNR per tone for VDSL
      --   Assoc MIB(s):     adGenVdsl2.mi2
      --   Platform:         TA5K
      --   Date/Developer:   08/12/2015 Josh Horton
      --   SysRel/Version:   PSI-18

      -- FeatureID:          180
      --   Revision:         1
      --   Description:      Quiet Line Noise (QLN) per tone for VDSL
      --   Assoc MIB(s):     adGenVdsl2.mi2
      --   Platform:         TA5K
      --   Date/Developer:   09/30/2015 Josh Horton
      --   SysRel/Version:   PSI-19

      -- FeatureID:          181
      --   Revision:         1
      --   Description:      Channel Transfer Function (HLOG) per tone for VDSL
      --   Assoc MIB(s):     adGenVdsl2.mi2
      --   Platform:         TA5K
      --   Date/Developer:   09/30/2015 Josh Horton
      --   SysRel/Version:   PSI-19

      -- FeatureID:          182
      --   Revision:         1
      --   Description:      Supporting single MAC clearing
      --   Assoc MIB(s):     genmac.mi2
      --   Platform:         TA5K
      --   Date/Developer:   10/01/2015 Jason Bao
      --   SysRel/Version:   PSI-19

      -- FeatureID:          183
      --   Revision:         1
      --   Description:      Warble Tone Generation for FXS Interfaces
      --   Assoc MIB(s):     adta5kpots.mi2
      --   Platform:         TA5K
      --   Date/Developer:   10/05/2015 Tim Myers
      --   SysRel/Version:   PSI-19

      -- FeatureID:        184
      --   Revision:         1
      --   Description:      Support adTrapHostTable for trap host provisioning
      --   Assoc MIB(s):     genTrap.mi2
      --   Platform:         TA5K, NetVanta
      --   Date/Developer:   10/29/2015 Byron Young
      --   SysRel/Version:   PSI-19

      -- FeatureID:        185
      --   Revision:         1
      --   Description:      Support IPv6 address format in adTrapHostTable entries
      --   Assoc MIB(s):     genTrap.mi2
      --   Platform:         TA5K, NetVanta
      --   Date/Developer:   10/29/2015 Byron Young
      --   SysRel/Version:   PSI-19

      -- FeatureID:        186
      --   Revision:         1
      --   Description:      Support DNS/hostname format in adTrapHostTable entries
      --   Assoc MIB(s):     genTrap.mi2
      --   Platform:         TA5K
      --   Date/Developer:   10/29/2015 Byron Young
      --   SysRel/Version:   PSI-19

      -- FeatureID:          187
      --   Revision:         1
      --   Description:      Reporting of PON wavelengths and technology types, as well as new ont activations
      --   Assoc MIB(s):     adGenGpon.mi2
      --   Platform:         TA5K
      --   Date/Developer:   01/04/2016 Pete Dietl
      --   SysRel/Version:   PSI-19

      -- FeatureID:          188
      --   Revision:         1
      --   Description:      Replacing ONT 32-bit Ethernet PM counters with 64-bit counters; all associated Counter32
      --                     adGenPmStats OIDs are replaced with Counter64 adGenPmStats OIDs.
      --   Assoc MIB(s):     adGenPm.mi2
      --   Platform:         TA5K
      --   Date/Developer:   02/22/2016 Jason Bao
      --   SysRel/Version:   PSI-20

      -- FeatureID:          189
      --   Revision:         1
      --   Description:      Support of CPU rate limit alarm enable and severity provisioning.
      --   Assoc MIB(s):     genSlot.mi2
      --   Platform:         TA5K
      --   Date/Developer:   03/16/2016 Jason Brock
      --   SysRel/Version:   SR9.5

      -- FeatureID:          190
      --   Revision:         1
      --   Description:      Support of Message-Waiting Indication with neon lamps.
      --   Assoc MIB(s):     adta5kpots.mi2
      --   Platform:         TA5K
      --   Date/Developer:   04/01/2016 Timothy Myers
      --   SysRel/Version:   SR9.7

      -- FeatureID:          191
      --   Revision:         1
      --   Description:      Support of SCM IPV6 server address.
      --   Assoc MIB(s):     adTaeSCU.mi2 adTaSysCtrlProduct.mi2
      --   Platform:         TA5K
      --   Date/Developer:   05/23/2016 Arthur Bill Poleon
      --   SysRel/Version:   PSI-22-1

      -- FeatureID:          192
      --   Revision:         1
      --   Description:      Support for Forcing the Message-Waiting Indicator either off or on with the ability to
      --                     detect the state of the Indicator.
      --   Assoc MIB(s):     adta5kpots.mi2
      --   Platform:         TA5K
      --   Date/Developer:   09/12/2016 Timothy Myers
      --   SysRel/Version:   PSI-23

     -- FeatureID:          193
      --   Revision:         1
      --   Description:      Support for RADIUS server sequence[0-4] and RADIUS names.
      --   Assoc MIB(s):     adTAeSCU.mi2
      --   Platform:         TA5K
      --   Date/Developer:   09/23/2016 Matthew Young
      --   SysRel/Version:   PSI-23

     -- FeatureID:          194
      --   Revision:         1
      --   Description:      Support for SCM SCR reboot mode.
      --   Assoc MIB(s):     adTaSysCtrlProduct.mi2
      --   Platform:         TA5K
      --   Date/Developer:   11/21/2016 Kevin Moore
      --   SysRel/Version:   PSI-24

      -- FeatureID:          195
      --   Revision:         1
      --   Description:      Support of Per-port provisionable Jitter Buffers for FXS ports.
      --   Assoc MIB(s):     adta5kpots.mi2
      --   Platform:         TA5K
      --   Date/Developer:   12/07/2016 Timothy Myers
      --   SysRel/Version:   PSI-24

     -- FeatureID:          196
      --   Revision:         1
      --   Description:      Support of returning slot uptime in seconds.
      --   Assoc MIB(s):     genslot.mi2
      --   Platform:         TA5K
      --   Date/Developer:   4/14/2017 Craye Hall
      --   SysRel/Version:   PSI-26

      -- FeatureID:          197
      --   Revision:         1
      --   Description:      Support of slot based vectoring fallback command and status SNMP OIDS
      --   Assoc MIB(s):     genVector.mi2
      --   Platform:         All SMs on vectoring capable systems (TA5K and OSP)
      --   Date/Developer:   06/14/2017 Gary Hunt
      --   SysRel/Version:   PSI-27

      -- FeatureID:          198
      --   Revision:         1
      --   Description:      Support for DMT EFM Group Uplink
      --   Assoc MIB(s):     none
      --   Platform:         TA5K
      --   Date/Developer:   08/2/2017 Wanda Snoddy
      --   SysRel/Version:   PSI-28

      -- FeatureID:          199
      --   Revision:         1
      --   Description:      Support for the Voice User Reverse Lookup Table (JIRA CN-42025)
      --   Assoc MIB(s):     genVoIP.mi2
      --   Platform:         All TA5K SM's and the 6th gen OSP SM
      --   Date/Developer:   08/10/2017 Andrew Littleton
      --   SysRel/Version:   PSI-28

      -- FeatureID:          200
      --   Revision:         1
      --   Description:      Support for DLV
      --   Assoc MIB(s):     none
      --   Platform:         6thGen and VXP OSP platforms
      --   Date/Developer:   09/13/2017 Justin Baldwin
      --   SysRel/Version:   PSI-28

      -- FeatureID:          201
      --   Revision:         1
      --   Description:      Support for 35B (SVX)
      --   Assoc MIB(s):     none
      --   Platform:         6thGen and VXP OSP platforms
      --   Date/Developer:   10/12/2017 Craye Hall
      --   SysRel/Version:   PSI-29

      -- FeatureID:          202
      --   Revision:         1
      --   Description:      Enable Scheduled Fxs Line Tests, Enable Scheduled Fxs Load Coil Tests, and Scheduled Fxs Line Tests Start Times
      --   Assoc MIB(s):     adta5kpots.mi2
      --   Platform:         48p RPOTS, VXP OSP platforms
      --   Date/Developer:   10/16/2017 Chasely Goodman
      --   SysRel/Version:   PSI-28

      -- FeatureID:          203
      --   Revision:         1
      --   Description:      Support for the Voice User Hotline Feature
      --   Assoc MIB(s):     genVoIP.mi2
      --   Platform:         All TA5K SM's and the 6th gen OSP SM
      --   Date/Developer:   01/17/2018 Timothy Myers
      --   SysRel/Version:   PSI-30

      -- FeatureID:          204
      --   Revision:         1
      --   Description:      Support PON protection Flag for PON Redundancy
      --   Assoc MIB(s):     adGenGpon.mi2
      --   Platform:         TA5K
      --   Date/Developer:   01/26/2018 Joe Onder
      --   SysRel/Version:   PI-4

      -- FeatureID:          205
      --   Revision:         1
      --   Description:      Support for Rate Adaptation (SRA) Auto Config Mode
      --   Assoc MIB(s):     adGenVdsl2.mi2
      --   Platform:         All Broadcom based VDSL2 OSPs and TA5k cards
      --   Date/Developer:   02/22/2018 Gary Hunt
      --   SysRel/Version:   PI-31

      -- FeatureID:          206
      --   Revision:         1
      --   Description:      SNMP access to POTS port descriptions
      --   Assoc MIB(s):     adta5kpots.mi2 and genFXO.mi2
      --   Platform:         All voice capable TA5K cards and the VXP
      --   Date/Developer:   04/02/2018 Andrew Littleton
      --   SysRel/Version:   PSI-31

      -- FeatureID:          207
      --   Revision:         1
      --   Description:      Support for interop with the Huawei softswitch
      --   Assoc MIB(s):     genSIP.mi2 and genVoIP.mi2
      --   Platform:         1187130F1, 1187130F2
      --   Date/Developer:   04/02/2018 Craye Hall
      --   SysRel/Version:   PI6

      -- FeatureID:          208
      --   Revision:         1
      --   Description:      Support for EFM-Group downlink
      --   Assoc MIB(s):     genefm.mi2
      --   Platform:         VXP and 130Fx TA5K Modules
      --   Date/Developer:   08/29/2018 Jeremy Duncan
      --   SysRel/Version:   PI6

      -- FeatureID:          209
      --   Revision:         1
      --   Description:      Support for  VDSL Uplink NTR timing source
      --   Assoc MIB(s):     adGenSystemTiming.mi2
      --   Platform:         VXP DMT Switch Module
      --   Date/Developer:   1/09/2019 Andrew Littleton
      --   SysRel/Version:   PI8

      -- FeatureID:          210
      --   Revision:         1
      --   Description:      Support for FXS pulse digit detection enable/disable
      --   Assoc MIB(s):     adta5kpots.mi2
      --   Platform:         TA5K Voice Modules and ONTs
      --   Date/Developer:   03/21/2019 Jeremy Duncan
      --   SysRel/Version:   PI9

      -- FeatureID:          211
      --   Revision:         1
      --   Description:      Support for Default SIP Trunk
      --   Assoc MIB(s):     genVoIP.mi2
      --   Platform:         TA5K/VXP SMs
      --   Date/Developer:   04/04/2019 Jeremy Duncan
      --   SysRel/Version:   PI9

      -- FeatureID:          212
      --   Revision:         1
      --   Description:      Support for Voice User SIP Trunk Manual Selection
      --   Assoc MIB(s):     genVoIP.mi2
      --   Platform:         TA5K/VXP SMs
      --   Date/Developer:   07/31/2019 Jeremy Duncan
      --   SysRel/Version:   PI11

      -- FeatureID:          213
      --   Revision:         1
      --   Description:      Support for the Voice User Warmline Feature
      --   Assoc MIB(s):     genVoIP.mi2
      --   Platform:         All TA5K SM's and the 6th gen OSP SM
      --   Date/Developer:   10/09/2019 Jeremy Duncan
      --   SysRel/Version:   PI12

      -- FeatureID:          214
      --   Revision:         1
      --   Description:      Support for configurable alarms severities.
      --                     ONT LOS, ONT Powering, Pluggable Fault, Pluggable Missing, Ethernet Link Down Enterprise, Ethernet Link Down RFC
      --   Assoc MIB(s):     adGenGpon.mi2, adGenPluggablePort.mi2, genEthIfc.mi2
      --   Platform:         TA5K GPON and AE OLTs
      --   Date/Developer:   04/13/2020 Jeremy Duncan
      --   SysRel/Version:   PI14

      -- FeatureID:          215
      --   Revision:         1
      --   Description:      Support for configurable EFM Group alarm severities.
      --                     Group Down, Group Partial
      --   Assoc MIB(s):     genefm.mi2
      --   Platform:         TA5K and OSP VDSL Modules
      --   Date/Developer:   05/11/2020 Jeremy Duncan
      --   SysRel/Version:   PI14

      -- FeatureID:          216
      --   Revision:         1
      --   Description:      Support for configurable VDSL2 alarm severities including info and alert.
      --                     Link Down
      --   Assoc MIB(s):     adGenVdsl2.mi2
      --   Platform:         TA5K and OSP VDSL Modules, GPON OLTs
      --   Date/Developer:   05/11/2020 Jeremy Duncan
      --   SysRel/Version:   PI14

      -- FeatureID:          217
      --   Revision:         1
      --   Description:      Support for non-blocking port-breakout configuration.
      --   Assoc MIB(s):     genEthIfc.mi2
      --   Platform:         1187045F1
      --   Date/Developer:   07/21/2020 Matthew Cather
      --   SysRel/Version:   PI16

      -- FeatureID:          218
      --   Revision:         1
      --   Description:      Support for the SIP Registrar Threshold feature.
      --   Assoc MIB(s):     genSIP.mi2
      --   Platform:         All TA5K SM's and the 6th gen OSP SM
      --   Date/Developer:   12/01/2020 Jeremy Duncan
      --   SysRel/Version:   PI17

      -- FeatureID:          219
      --   Revision:         1
      --   Description:      Support for Signed x.509 SSL Certificates
      --   Assoc MIB(s):     adTaSysCtrlProduct.mi2
      --   Platform:         All TA5K/OSP SCMs
      --   Date/Developer:   07/06/2021 Geoff Oltmans/Forrest Evans
      --   SysRel/Version:   PI14

      -- FeatureID:          220
      --   Revision:         1
      --   Description:      Support for the Voice Timeouts Connected feature.
      --   Assoc MIB(s):     getVoIP.mi2
      --   Platform:         All TA5K SM's and the 6th gen OSP SM
      --   Date/Developer:   01/07/2022 Jeremy Duncan
      --   SysRel/Version:   PI22

      -- FeatureID:          221
      --   Revision:         1
      --   Description:      Support for 90 vrms ring voltage 
      --   Assoc MIB(s):     adta5kpots.mi2
      --   Platform:         TA5K
      --   Date/Developer:   01/07/2022 Jeremy Duncan
      --   SysRel/Version:   PI23    

      -- FeatureID:          222
      --   Revision:         1
      --   Description:      Support for ONT reporting temp/bias current/voltage data
      --   Assoc MIB(s):     adGenGpon.mi2
      --   Platform:         TA5K
      --   Date/Developer:   02/23/2022 Ryan Balch
      --   SysRel/Version:   PI24

      -- FeatureID:          223
      --   Revision:         1
      --   Description:      Support for configurable ONT Dying Gasp alarm severities
      --   Assoc MIB(s):     adGenGpon.mi2
      --   Platform:         TA5K
      --   Date/Developer:   03/11/2022 Ryan Balch
      --   SysRel/Version:   PI24

      -- FeatureID:          224
      --   Revision:         1
      --   Description:      Support for the Upstream FEC Rolling Counters
      --   Assoc MIB(s):     adGenGpon.mi2
      --   Platform:         TA5K
      --   Date/Developer:   03/29/2022 Jeremy Duncan
      --   SysRel/Version:   PI24      

      -- FeatureID:          225
      --   Revision:         1
      --   Description:      Support for higher speeds (2.5G, 5G, 10G) on the ONT Ethernet interface
      --   Assoc MIB(s):     adGenGpon.mi2
      --   Platform:         TA5K
      --   Date/Developer:   03/30/2022 Gary Hunt
      --   SysRel/Version:   PI24      

      -- FeatureID:          226
      --   Revision:         1
      --   Description:      Support for GAL Ethernet discarded frames counter
      --   Assoc MIB(s):     adGenGpon.mi2
      --   Platform:         TA5K
      --   Date/Developer:   05/31/2022 Ryan Balch
      --   SysRel/Version:   PI25
--==================================================================================================================

   adGenSystemProductTable OBJECT-TYPE
       SYNTAX  SEQUENCE OF AdGenSystemProductEntry
       MAX-ACCESS  not-accessible
       STATUS  current
       DESCRIPTION
               "Table for system features."
       ::= { adGenSystemProduct 1 }

   adGenSystemProductEntry OBJECT-TYPE
       SYNTAX  AdGenSystemProductEntry
       MAX-ACCESS  not-accessible
       STATUS  current
       DESCRIPTION
               ""
       INDEX   { adGenSlotInfoIndex }
       ::= { adGenSystemProductTable 1 }

   AdGenSystemProductEntry ::=
       SEQUENCE {
       adGenSystemProductSnmpIdentifier       DisplayString,
       adGenSystemFeatureSupport              DisplayString,
       adGenSystemFeatureSupportByteMap      OCTET STRING
       }

    adGenSystemProductSnmpIdentifier  OBJECT-TYPE
        SYNTAX  DisplayString
        MAX-ACCESS  read-only
        STATUS  current
        DESCRIPTION
            "This OID will return the system release of an
            adtran product (i.e card). EMS will use it to
            provide the feature set based on the sys release."
        ::= { adGenSystemProductEntry 1 }

    adGenSystemFeatureSupport  OBJECT-TYPE
        SYNTAX  DisplayString
        MAX-ACCESS  read-only
        STATUS  current
        DESCRIPTION
            "This OID will return a comma delimited abbreviation
            list of the supported features (i.e CLI, SCA, etc)."

        ::= { adGenSystemProductEntry 2 }

       adGenSystemFeatureSupportByteMap  OBJECT-TYPE
        SYNTAX  OCTET STRING
        MAX-ACCESS  read-only
        STATUS  current
        DESCRIPTION
            "encoding scheme, referred to as 'version N' format,
             is as follows...

             header:
               byte 1         - version, meaning version of encoding scheme
                                for this OID; will be 0x01 starting out
               bytes 2-3      - SNMP product ID from adtrantc.mib/.mi2

             payload, in 2-byte increments:
               bytes 4-5      - first feature ID
               ...
               bytes (n-1)-n  - last feature ID
               where...
                 * Feature IDs will be assigned by the Systems Feature
                   Administrator. When an existing feature ID is being
                   considered for use in a new product, the firmware developer
              and/or EMS developer will confirm it with the Systems
                   Feature Administrator. This will serve two purposes.
           It will keep the Systems Feature Admin aware of new
           products from a features point of view, which is obviously
           important to his role. And it will help the firmware and
           EMS developers to better understand how a particular
           product is similar or dissimilar to others that
           they may be drawing information from.
         * All feature IDs will be documented by the firmware
           developer in the Product Style Guide.
            "
        ::= { adGenSystemProductEntry 3 }


   -- *********************************************************************
   -- ********** Provide an extensible branch for new/future use **********
   -- *********************************************************************

   adGenSystemProductMgGrp OBJECT IDENTIFIER ::= { adGenSystemProductMg 1 }


   -- ***************************************************************
   -- ********** Version-Indexed Supported FeatureID Query **********
   -- ***************************************************************

   adGenSystemFeatureSupportVersionTable OBJECT-TYPE
      SYNTAX      SEQUENCE OF AdGenSystemFeatureSupportVersionEntry
      MAX-ACCESS  not-accessible
      STATUS      current
      DESCRIPTION
         "The version-indexed System FeatureID table."
      ::= { adGenSystemProductMgGrp 1 }

   adGenSystemFeatureSupportVersionEntry OBJECT-TYPE
      SYNTAX      AdGenSystemFeatureSupportVersionEntry
      MAX-ACCESS  not-accessible
      STATUS      current
      DESCRIPTION
         "An entry in the version-indexed System FeatureID group table."
      INDEX       { adGenSlotInfoIndex, adGenSystemFeatureSupportVersionIndex }
      ::= { adGenSystemFeatureSupportVersionTable 1 }

   AdGenSystemFeatureSupportVersionEntry ::=
      SEQUENCE {
         adGenSystemFeatureSupportVersionIndex  Integer32,
         adGenSystemFeatureSupportVersionQuery  OCTET STRING
      }

   adGenSystemFeatureSupportVersionIndex OBJECT-TYPE
      SYNTAX      Integer32
      MAX-ACCESS  not-accessible
      STATUS      current
      DESCRIPTION
         "A unique value for the version-indexed System FeatureID group."
      ::= { adGenSystemFeatureSupportVersionEntry 1 }

   adGenSystemFeatureSupportVersionQuery OBJECT-TYPE
      SYNTAX      OCTET STRING
      MAX-ACCESS  read-only
      STATUS      current
      DESCRIPTION
         "This optional OID will return enhanced FeatureID information, indexed
          by slot number and version-format.

          Based upon the version-format index:

          1: (version 1)
             This version will return information identical to the original
             adGenSystemFeatureSupportByteMap OID.

          2: (version 2)
             This version will return similarly formatted Version/ProductID
             info as version 1, but enhances the table portion to include
             FeatureIDVersion information as well.

             - The initial version of a new feature should be 1.
             - Adding a new oid or improving an existing oid will not require
               registering a new FeatureID.  Instead you may simply increment
               the FeatureIDVersion of the existing FeatureID entry.

             ************************************************
             ********** Version 2 Encoding Details **********
             ************************************************

             If you imagine the returned information was mapped onto a packed
             big-endian C++ structure, the header and associated information
             may be viewed simply as:

             #pragma pack(1)             // request byte-alignment and packing
             struct FeatureID_header
             {
                UINT8  Version;          // query format version (1...n)
                UINT16 ProductID;        // module ProductID

                FeatureID_entry entry[]; // an array of 1 or more FeatureID_entry
                                         // entries.
             };
             #pragma pack()              // revert to original alignment and packing


             Where FeatureID_entry (used immed above) is defined as:

             #pragma pack(1)             // request byte-alignment and packing
             struct FeatureID_entry      // in reality, this would be defined first
             {
                UINT16 FeatureID;        // reserved FeatureID (see above)
                UINT16 FeatureIDVersion; // reserved FeatureIDVersion (see above)
             };
             #pragma pack()              // revert to original alignment and packing


             The number of FeatureId entries may be calculated by:

               entries = (bytes_received -3) / sizeof(FeatureID_entry); "
      ::= { adGenSystemFeatureSupportVersionEntry 2 }


-- ******************************************************************************************
-- MIB Groups
-- ******************************************************************************************
adGenSystemMibConformance            OBJECT IDENTIFIER ::= {adGenSystemProduct 2 }
adGenSystemMibGroups                 OBJECT IDENTIFIER ::= {adGenSystemMibConformance 1 }

adGenSystemProductGroup OBJECT-GROUP
   OBJECTS
   {
        adGenSystemProductSnmpIdentifier,
        adGenSystemFeatureSupport,
        adGenSystemFeatureSupportByteMap
   }
   STATUS current
   DESCRIPTION
     "These objects provide support for retrieving system level product information."
   ::= { adGenSystemMibGroups 1 }


    END

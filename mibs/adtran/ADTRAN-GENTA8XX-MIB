ADTRAN-GENTA8XX-MIB

-- TITLE:     The ADTRAN TA8xx MIB
-- PRODUCT:   TA8xx and NV8xx family of EoCu and EoTDM network termination equipment
-- VERSION:   1.0
-- DATE:      2/27/07
-- AUTHOR:    Joey Boyd
-- STATUS:    PRELIMINARY

-- This MIB defines the object identifier (OID) for the
-- ADTRAN GENTA8XX MIB objects

-- HISTORY:
-- 02/27/07 jlb STATUS: PRELIMINARY.
-- 03/07/07 jlb Replaced ErroredFrames and DiscardedFrames with RxCRCAlignErrs,
--		RxUndersizeFrames, RxOversizeFrames, and RxCollisions in the
--		10/100 Ethernet performance table.
-- 04/10/07 jlb Modified the MIB to be fully SNMPv2 compliant.
-- 04/11/07 jlb Added adGenTA8xxFarEndConfigTable
-- 04/23/07 jlb Added adGenTA8xxFarEndSysName
-- 04/30/07 jlb Fixed the enumerations for adGenTA8xx10100EthPortRateDuplex and
--              adGenTA8xx10100EthLinkSpeedDuplex to match the values returned from sw
-- 05/03/07 jlb Added adGenTA8xxBondingPrimaryRef, adGenTA8xxBondingSecondaryRef, adGenTA8xxBondingFunctLineSource,
--              adGenTA8xxBondingPriRefStatus, adGenTA8xxBondingSecRefStatus, adGenTA8xxLoginFailureLevel,
--              adGenTA8xxLoginSuccessLevel
-- 05/18/07 jlb Added Ethernet 15-minute/24-hour thresholds and alarms
-- 05/21/07 jlb Added Ethernet Rx Discarded Frames to the PM, thresholds, and alarms.
--              Changed the MAX-ACCESS of the thresholds to read-write.
-- 05/22/07 jlb Added Bit Descriptions of the Trap Enable OID.
-- 05/29/07 jlb Added adGenTA8xx10100EthPortName and adGenTA8xxGigEthPortName
-- 06/04/07 jlb Added adGenTA8xxCapabilities.
-- 09/04/07 jlb Changed non enumerated INTEGERs to Integer32
-- 09/11/07 jlb Fixed compiler errors
-- 09/17/07 twc Added adGenTA8xxTstBertPrvTable and adGenTA8xxTstBertStatTable support.
-- 10/23/07 jlb Added Rx Multicast and Broadcast Frames to all 10/100 and Gigabit Ethernet PM, thresholds, and alarms.
-- 10/24/07 jlb Added Tx/Rx Unicast, Tx Multicast, and Tx Broadcast Frames to all 10/100 and Gigabit Ethernet PM, thresholds, and alarms.
-- 10/25/07 jlb Changed CONTACT-INFO
-- 10/26/07 jlb Fixed some comments per AT&T
-- 11/02/07 jlb Added adGenTA8xxGigEthPortSpeed
-- 11/08/07 jlb Fixed comment for adGenTA8xxTstBertStartAndStop.  Changed enumeration for adGenTA8xxTstBertStatus.
-- 11/12/07 jlb Fixed the enumeration name for adGenTA8xxTstBertErrorInject
-- 11/15/07 jlb Added adGenTA8xxGigEthSFPTemperature, adGenTA8xxGigEthSFPTxBias, adGenTA8xxGigEthSFPTxPower and adGenTA8xxGigEthSFPRxPower
-- 11/27/07 jlb Added adGenTA8xxGigEthLinkSpeedDuplex
-- 11/28/07 jlb Changed the patterns supported by the BERT.
-- 11/28/07 twc Added adGenTA8xxTstLpbkPrvTable
-- 12/07/07 twc Updated adGenTA8xxTstLpbkPrvTable, now supports Inband and FDL.
-- 12/20/07 twc Added reqSendNoCode(6) enum to adGenTa8xxTstRequestRemoteLoopback oid.
-- 01/15/08 jmh Added enable/disable bit for DSL Alarm traps.
-- 02/06/08 met Added support for management PM statistics
-- 02/20/08 jlb Added an OBJECT-GROUP for management statistics.  Removed the mgmt stats from the NOTIFICATION-GROUP.
-- 02/25/08 twc Added IP Access Control List on the Network Management VLAN
-- 03/12/08 jlb Added adGenTA8xxCurrentCPUUtilization, adGenTA8xxMaxCPUUtilization, and adGenTA8xxResetMaxCPUUtilization.
-- 03/19/08 jlb Added adGenTA8xxTstIncomingInbandLoopbackPatterns and adGenTA8xxTstIncomingFDLLoopbackPatterns.
--              Made adGenTA8xxMgmtStatsCurrentTxFrames and adGenTA8xxMgmtStatsCurrentRxFrames scalars.
-- 03/27/08 jlb Added adGenTA8xx10100EthPerfReset and adGenTA8xxGigEthPerfReset.
-- 04/22/08 jlb Changed adGenTA8xxIpAclEntryIndex from an INTEGER data type to Integer32.
-- 05/02/08 jmh Added adGenTA8xxFanModuleAlm, adGenTA8xxSingleFanFailureAlm, adGenTA8xxMultipleFanFailureAlm
-- 05/05/08 jlb Fixed the alarm severities in the adGenTA8xxFanModeleAlmClr, adGenTA8xxSingleFanFailureAlmClr, and adGenTA8xxMultipleFanFailureAlmClr
-- 05/07/08 jlb Added bertTwoToTwentyThreeMinusOne(5) to adGenTA8xxTstBertPattern.
-- 05/09/08 rpk Added adGenTA8xxIpACLRemoveAll, Deprecated adGenTA8xxCapabilities
-- 05/14/08 jlb Fixed compiler errors.
-- 05/15/08 jlb Changed some of the alarm severities to match the code.
-- 06/02/08 jlb Created deprecated OBJECT-GROUP and added adGenTA8xxCapabilities to it.  Fixed typo in adGenTA8xxFanModeleAlmClear.
-- 06/02/08 jb  Added temperature.
-- 07/03/08 jlb Fixed some compiler errors.
-- 09/22/08 jlb Changed severity of adGenTA8xxTemperatureNormal and adGenTA8xxTemperatureHigh to MAJOR
-- 10/31/08 jlb Changed data type on adGenTA8xxTemperatureFahrenheit and adGenTA8xxTemperatureCelsius to DisplayString.
-- 03/25/09 rpk Modified description of 10/100 CRCAlign entries to indicate they are Rx Alignment & FCS Errors
-- 05/27/10 jmh Added adGenTA8xx10100EthPortLsaBandwidthMinimum,
--              adGenTA8xx10100EthPortLsaLinkMinimum, and
--              adGenTA8xxGigEthLsaBandwidthMinimum, and
--              adGenTA8xxGigEthLsaLinkMinimum
-- 06/14/10 jb  Added AUX1 door alarm.
-- 06/28/10 rpk Added 10Mbps and 2500Mbps speed options to adGenTA8xxGigEthPortSpeed
--		Added 2500Mbps/half-duplex and 2500Mbps/full-duplex options to adGenTA8xxGigEthLinkSpeedDuplex
-- 10/01/10 jb  Added Rolling Average Interval.
--
-- ******************************************************************************************
DEFINITIONS ::= BEGIN

IMPORTS
   MODULE-IDENTITY,
   OBJECT-TYPE,
   NOTIFICATION-TYPE,
   IpAddress,
   Unsigned32,
   Integer32,
   Gauge32
      FROM SNMPv2-SMI
   sysName
      FROM SNMPv2-MIB
   DisplayString,
   TruthValue
      FROM SNMPv2-TC
   InetAddressIPv6,
   InetAddressPrefixLength
      FROM INET-ADDRESS-MIB
   OBJECT-GROUP,
   NOTIFICATION-GROUP
      FROM SNMPv2-CONF
   InterfaceIndex,
   ifIndex
      FROM IF-MIB
   adTrapInformSeqNum
      FROM ADTRAN-GENTRAPINFORM-MIB
   adGenSlotInfoIndex,
   adGenSlotAlarmStatus
      FROM ADTRAN-GENSLOT-MIB
   adGenPortTrapIdentifier
      FROM ADTRAN-GENPORT-MIB
   adGenTA8xx,
   adGenTA8xxID
      FROM ADTRAN-SHARED-EOCU-MIB
   ;

adGenTA8xxMIB MODULE-IDENTITY
   LAST-UPDATED "201510290000Z"
   ORGANIZATION "Adtran, Inc."
   CONTACT-INFO
     "CND Tech Support
         Postal: ADTRAN, Inc.
                 901 Explorer Blvd.
                 Huntsville, AL  35806
                 Tel: +1 800 726-8663
                 Fax: +1 256 963 6217
                 E-mail: support@adtran.com"
   DESCRIPTION
      "This MIB defines the objects for the TA8xx MIB."

   REVISION "201510290000Z"
   DESCRIPTION "Added the following OIDs for Ethernet jabbers and fragments:

        ==========================================
        Ethernet - interval values

        adGenTA8xx10100Eth15MinCurrentRxJabbers
        adGenTA8xx10100Eth15MinCurrentRxFragments

        adGenTA8xx10100Eth15MinIntervalRxJabbers
        adGenTA8xx10100Eth15MinIntervalRxFragments

        adGenTA8xx10100Eth24HrCurrentRxJabbers
        adGenTA8xx10100Eth24HrCurrentRxFragments

        adGenTA8xx10100Eth24HrIntervalRxJabbers
        adGenTA8xx10100Eth24HrIntervalRxFragments

        ==========================================
        Gigabit Ethernet - interval values

        adGenTA8xxGigEth15MinCurrentRxJabbers
        adGenTA8xxGigEth15MinCurrentRxFragments

        adGenTA8xxGigEth15MinIntervalRxJabbers
        adGenTA8xxGigEth15MinIntervalRxFragments

        adGenTA8xxGigEth24HrCurrentRxJabbers
        adGenTA8xxGigEth24HrCurrentRxFragments

        adGenTA8xxGigEth24HrIntervalRxJabbers
        adGenTA8xxGigEth24HrIntervalRxFragments

        ==========================================
        Ethernet - threshold provisioning

        adGenTA8xx10100Eth15MinThreshRxJabbers
        adGenTA8xx10100Eth15MinThreshRxFragments

        adGenTA8xx10100Eth24HrThreshRxJabbers
        adGenTA8xx10100Eth24HrThreshRxFragments

        ==========================================
        Gigabit Ethernet - threshold provisioning

        adGenTA8xxGigEth15MinThreshRxJabbers
        adGenTA8xxGigEth15MinThreshRxFragments

        adGenTA8xxGigEth24HrThreshRxJabbers
        adGenTA8xxGigEth24HrThreshRxFragments

        ==========================================
        Notifications

        adGenTA8xxSet10100Eth15MinRxJabbers
        adGenTA8xxSet10100Eth24HrRxJabbers

        adGenTA8xxSet10100Eth15MinRxFragments
        adGenTA8xxSet10100Eth24HrRxFragments

        adGenTA8xxSetGigEth15MinRxJabbers
        adGenTA8xxSetGigEth24HrRxJabbers

        adGenTA8xxSetGigEth15MinRxFragments
        adGenTA8xxSetGigEth24HrRxFragments
        "

   REVISION "201412100000Z"
   DESCRIPTION "Added the following alarms for link state awareness:
       adGenTA8xxClr10100EthLinkLsaForcedDown,
       adGenTA8xxSet10100EthLinkLsaForcedDown,
       adGenTA8xxClrGigEthLinkLsaForcedDown,
       adGenTA8xxSetGigEthLinkLsaForcedDown"

   REVISION "201405160000Z"
   DESCRIPTION "Added the following OIDs for IPv6 address management:
       adGenTA8xxIpv6AddressLinkLocal,
       adGenTA8xxIpv6AddressLinkLocalOperational,
       adGenTA8xxIpv6Address,
       adGenTA8xxIpv6AddressPrefixLength,
       adGenTA8xxIpv6AddressEui64,
       adGenTA8xxIpv6AddressOperational"

   REVISION "200704050000Z"
   DESCRIPTION "Created"

::= { adGenTA8xxID 1 }


--==================================================================================================================

adGenTA8xxEvents                    OBJECT IDENTIFIER ::= {adGenTA8xx 0}
adGenTA8xxConfiguration             OBJECT IDENTIFIER ::= {adGenTA8xx 1}
adGenTA8xxProvisioning              OBJECT IDENTIFIER ::= {adGenTA8xx 2}
adGenTA8xxStatus	            OBJECT IDENTIFIER ::= {adGenTA8xx 3}
adGenTA8xxPerformance               OBJECT IDENTIFIER ::= {adGenTA8xx 4}
adGenTA8xxTest                      OBJECT IDENTIFIER ::= {adGenTA8xx 5}
adGenTA8xxAlarms                    OBJECT IDENTIFIER ::= {adGenTA8xx 6}
adGenTA8xxMibConformance            OBJECT IDENTIFIER ::= {adGenTA8xx 8 }
adGenTA8xxMibGroups                 OBJECT IDENTIFIER ::= {adGenTA8xxMibConformance 1 }

--==================================================================================================================
-- Configuration
--==================================================================================================================
--==================================================================================================================
-- Card Configuration
--==================================================================================================================
   adGenTA8xxConfigTable OBJECT-TYPE
      SYNTAX  SEQUENCE OF AdGenTA8xxConfigEntry
      MAX-ACCESS  not-accessible
      STATUS  current
      DESCRIPTION
         "The TA838 Configuration table."
      ::= { adGenTA8xxConfiguration 1 }

   adGenTA8xxConfigEntry OBJECT-TYPE
      SYNTAX  AdGenTA8xxConfigEntry
      MAX-ACCESS  not-accessible
      STATUS  current
      DESCRIPTION
         "An entry in the TA838 Config table."
      INDEX   { adGenSlotInfoIndex }
   ::= { adGenTA8xxConfigTable 1 }

   AdGenTA8xxConfigEntry ::=
      SEQUENCE {
         adGenTA8xxBootVersion
            DisplayString,
         adGenTA8xxSwChecksum
            DisplayString,
         adGenTA8xxBootChecksum
            DisplayString,
         adGenTA8xxSavedSwVersion
            DisplayString
         }

      adGenTA8xxBootVersion OBJECT-TYPE
         SYNTAX DisplayString
         MAX-ACCESS  read-only
         STATUS  current
         DESCRIPTION
            "Firmware version for the boot code."
         ::= { adGenTA8xxConfigEntry 1 }

      adGenTA8xxSwChecksum OBJECT-TYPE
         SYNTAX  DisplayString
         MAX-ACCESS  read-only
         STATUS  current
         DESCRIPTION
            "Firmware checksum of the application code."
         ::= { adGenTA8xxConfigEntry 2 }

      adGenTA8xxBootChecksum OBJECT-TYPE
         SYNTAX  DisplayString
         MAX-ACCESS  read-only
         STATUS  current
         DESCRIPTION
            "Firmware checksum of the boot code."
         ::= { adGenTA8xxConfigEntry 3 }

      adGenTA8xxSavedSwVersion OBJECT-TYPE
         SYNTAX  DisplayString
         MAX-ACCESS  read-only
         STATUS  current
         DESCRIPTION
            "Firmware version currently saved.  This value will differ
             from adGenSlotProdSwVersion if the unit has been upgraded,
             but not restarted to run the new code."
         ::= { adGenTA8xxConfigEntry 4 }

--==================================================================================================================
-- Far End Configuration
--==================================================================================================================
   adGenTA8xxFarEndConfigTable OBJECT-TYPE
      SYNTAX  SEQUENCE OF AdGenTA8xxFarEndConfigEntry
      MAX-ACCESS  not-accessible
      STATUS  current
      DESCRIPTION
         "The TA838 FarEnd Configuration table."
      ::= { adGenTA8xxConfiguration 2 }

   adGenTA8xxFarEndConfigEntry OBJECT-TYPE
      SYNTAX  AdGenTA8xxFarEndConfigEntry
      MAX-ACCESS  not-accessible
      STATUS  current
      DESCRIPTION
         "An entry in the TA838 FarEnd Config table."
      INDEX   { ifIndex }
   ::= { adGenTA8xxFarEndConfigTable 1 }

   AdGenTA8xxFarEndConfigEntry ::=
      SEQUENCE {
         adGenTA8xxFarEndIfIndex
            InterfaceIndex,
         adGenTA8xxFarEndIPAddress
            IpAddress,
         adGenTA8xxFarEndSysName
            DisplayString
         }

      adGenTA8xxFarEndIfIndex OBJECT-TYPE
         SYNTAX InterfaceIndex
         MAX-ACCESS  read-only
         STATUS  current
         DESCRIPTION
            "The ifIndex associated with the bonding group of the connected
             far end device."
         ::= { adGenTA8xxFarEndConfigEntry 1 }

      adGenTA8xxFarEndIPAddress OBJECT-TYPE
         SYNTAX IpAddress
         MAX-ACCESS  read-only
         STATUS  current
         DESCRIPTION
            "The IP address associated with the bonding group of the connected
             far end device."
         ::= { adGenTA8xxFarEndConfigEntry 2 }

      adGenTA8xxFarEndSysName OBJECT-TYPE
         SYNTAX DisplayString
         MAX-ACCESS  read-only
         STATUS  current
         DESCRIPTION
            "The SysName associated with the bonding group of the connected
             far end device."
         ::= { adGenTA8xxFarEndConfigEntry 3 }

--==================================================================================================================
-- Provisioning
--==================================================================================================================

   adGenTA8xxPrvScalars  OBJECT IDENTIFIER ::= { adGenTA8xxProvisioning 1 }

      adGenTA8xxAutoLogoffTime OBJECT-TYPE
         SYNTAX  INTEGER {
            disable (1),
            oneMin (2),
            fiveMin (3),
            tenMin (4),
            fifteenMin (5),
            thirtyMin (6),
            fortyfiveMin (7),
            oneHour (8)
         }
         MAX-ACCESS  read-write
         STATUS  current
         DESCRIPTION
            "Disables or selects the Terminal Auto-Logoff time."
         ::= { adGenTA8xxPrvScalars 1 }

      adGenTA8xxSaveProv OBJECT-TYPE
         SYNTAX  INTEGER {
            saveConfig(1)
         }
         MAX-ACCESS  read-write
         STATUS  current
         DESCRIPTION
            "Setting this OID saves the provisioning."
         ::= { adGenTA8xxPrvScalars 2 }

      adGenTA8xxScheduledResetTime   OBJECT-TYPE
         SYNTAX  OCTET STRING (SIZE (17))
         MAX-ACCESS  read-write
         STATUS  current
         DESCRIPTION
            "Set the time for a scheduled reset in the format mm/dd/yy hh:mm:ss.
             This reset can be disabled by setting the time to a time that has
             already passed, but the date selected must be after 01/01/2000."
         ::= { adGenTA8xxPrvScalars 3 }

      adGenTA8xxSecondaryTelnetPort OBJECT-TYPE
         SYNTAX  Integer32
         MAX-ACCESS  read-write
         STATUS  current
         DESCRIPTION
            "The TCP port number used by the secondary telnet server.
             Changing this port number will disconnect anyone currently
             connected through the secondary telnet server."
         ::= { adGenTA8xxPrvScalars 4 }

     adGenTA8xxBondingPrimaryRef OBJECT-TYPE
         SYNTAX  Integer32
         MAX-ACCESS  read-write
         STATUS  current
         DESCRIPTION
            "Selects the primary timing reference for the bonding ports."
         ::= { adGenTA8xxPrvScalars 5 }

     adGenTA8xxBondingSecondaryRef OBJECT-TYPE
         SYNTAX  Integer32
         MAX-ACCESS  read-write
         STATUS  current
         DESCRIPTION
            "Selects the secondary timing reference for the bonding ports."
         ::= { adGenTA8xxPrvScalars 6 }

    adGenTA8xxCapabilities OBJECT-TYPE
         SYNTAX OCTET STRING
         MAX-ACCESS  read-only
         STATUS   deprecated
         DESCRIPTION
            "This object will be used to define any new features added that
             changes the behavior of the management system.  This bits will
             be defined in network order, i.e. bit 0 is the MSB of the first
             octet in the octet string.

          Control is defined as follows:

          Bits:
                 No bits currently defined (default for system release 3.0)"

         ::= { adGenTA8xxPrvScalars 7 }

      adGenTA8xxIpACLState OBJECT-TYPE
         SYNTAX  INTEGER {
            disable(1),
            enable(2)
         }
         MAX-ACCESS  read-write
         STATUS  current
         DESCRIPTION
            "Enables or disables the IP Access Control List."
         ::= { adGenTA8xxPrvScalars 8 }

      adGenTA8xxIpACLInsert OBJECT-TYPE
         SYNTAX IpAddress
         MAX-ACCESS  read-write
         STATUS  current
         DESCRIPTION
            "Add an IP address to the IP Access Control List."
         ::= { adGenTA8xxPrvScalars 9 }

      adGenTA8xxIpACLRemove OBJECT-TYPE
         SYNTAX IpAddress
         MAX-ACCESS  read-write
         STATUS  current
         DESCRIPTION
            "Remove an IP address from the IP Access Control List."
         ::= { adGenTA8xxPrvScalars 10 }

      adGenTA8xxIpACLRemoveAll OBJECT-TYPE
         SYNTAX INTEGER {
	    clearACL(1)
	 }
         MAX-ACCESS  read-write
         STATUS  current
         DESCRIPTION
            "Setting this OID removes all IPs from the IP Access Control List."
         ::= { adGenTA8xxPrvScalars 11 }

      adGenTA8xxTemperatureThresholdCelsuis OBJECT-TYPE
         SYNTAX  Integer32
         MAX-ACCESS  read-write
         STATUS  current
         DESCRIPTION
            "This variable is used to configure the Celsius temperature threshold."
         ::= { adGenTA8xxPrvScalars 12}

      adGenTA8xxTemperatureThresholdFahrenheit OBJECT-TYPE
         SYNTAX  Integer32
         MAX-ACCESS  read-write
         STATUS  current
         DESCRIPTION
            "This variable is used to configure the Fahrenheit temperature threshold."
         ::= { adGenTA8xxPrvScalars 13} 
         
      adGenTA8xxRollingAverageInterval   OBJECT-TYPE
         SYNTAX  Integer32
         MAX-ACCESS  read-write
         STATUS  current
         DESCRIPTION
            "Set the rolling average interval to a valid range from 30 to 300 seconds."
         ::= { adGenTA8xxPrvScalars 14 }


--==================================================================================================================

   adGenTA8xxPrv10100EthPortTable OBJECT-TYPE
      SYNTAX  SEQUENCE OF AdGenTA8xxPrv10100EthPortEntry
      MAX-ACCESS  not-accessible
      STATUS  current
      DESCRIPTION
         "The Ethernet Client Port provisioning table."
      ::= { adGenTA8xxProvisioning 2 }

   adGenTA8xxPrv10100EthPortEntry OBJECT-TYPE
      SYNTAX  AdGenTA8xxPrv10100EthPortEntry
      MAX-ACCESS  not-accessible
      STATUS  current
      DESCRIPTION
         "An entry in the Ethernet Client Port provisioning table."
      INDEX  { ifIndex }
      ::= { adGenTA8xxPrv10100EthPortTable 1 }

   AdGenTA8xxPrv10100EthPortEntry ::=
      SEQUENCE {
         adGenTA8xx10100EthPortState
	    INTEGER,
         adGenTA8xx10100EthPortRateDuplex
            INTEGER,
         adGenTA8xx10100EthPortCrossOverMode
            INTEGER,
	 adGenTA8xx10100EthPortLsa
            INTEGER,
         adGenTA8xx10100EthPortName
            DisplayString,
         adGenTA8xx10100EthPortLsaBandwidthMinimum
            Gauge32,
         adGenTA8xx10100EthPortLsaLinksMinimum
            Gauge32
      }

      adGenTA8xx10100EthPortState OBJECT-TYPE
         SYNTAX  INTEGER {
            disable(1),
            enable(2)
         }
         MAX-ACCESS  read-write
         STATUS  current
         DESCRIPTION
            "Enables or disables the selected 10/100 ethernet port."
         ::= { adGenTA8xxPrv10100EthPortEntry 1 }

      adGenTA8xx10100EthPortRateDuplex OBJECT-TYPE
         SYNTAX  INTEGER {
            auto(4),
            half10Mbps(5),
            full10Mbps(6),
            half100Mbps(7),
            full100Mbps(8)
         }
         MAX-ACCESS  read-write
         STATUS  current
         DESCRIPTION
            "Provisions the rate and duplex for the selected 10/100
             ethernet port."
         ::= { adGenTA8xxPrv10100EthPortEntry 2 }

      adGenTA8xx10100EthPortCrossOverMode OBJECT-TYPE
         SYNTAX  INTEGER {
            mdi(1),
            mdix(2),
	    auto(3)
         }
         MAX-ACCESS  read-write
         STATUS  current
         DESCRIPTION
            "Provisions MDI, MDI-X, or Auto for the selected 10/100
             ethernet port."
         ::= { adGenTA8xxPrv10100EthPortEntry 3 }

      adGenTA8xx10100EthPortLsa OBJECT-TYPE
         SYNTAX  INTEGER {
            disable(1),
            enable(2)
         }
         MAX-ACCESS  read-write
         STATUS  current
         DESCRIPTION
            "Enables or disables the link state awareness
 	     on the selected 10/100 port."
         ::= { adGenTA8xxPrv10100EthPortEntry 4 }

      adGenTA8xx10100EthPortName OBJECT-TYPE
         SYNTAX  DisplayString
         MAX-ACCESS  read-write
         STATUS  current
         DESCRIPTION
            "Sets a display name associated with the selected
             10/100 port."
         ::= { adGenTA8xxPrv10100EthPortEntry 5 }

      adGenTA8xx10100EthPortLsaBandwidthMinimum OBJECT-TYPE
         SYNTAX  Gauge32
         MAX-ACCESS  read-write
         STATUS  current
         DESCRIPTION
           "Sets the low threshold (in kbps) for bandwidth
            on MEN-Ports that can possibly egress traffic
            ingressing this port when acting as a UNI.  This
            is based on EVC and EVC-Map configuration.
            If Link State Awarness is enabled and the
            bandwidth of a MEN-Port falls below this value,
            the path to that MEN-Port is no longer considered
            to be a valid path through the system.  If there
            is no valid path through the system for any frames
            ingressing this UNI, the UNI will be disabled to
            notify the connected device that service is no
            longer available."
         ::= { adGenTA8xxPrv10100EthPortEntry 6 }

      adGenTA8xx10100EthPortLsaLinksMinimum OBJECT-TYPE
         SYNTAX  Gauge32
         MAX-ACCESS  read-write
         STATUS  current
         DESCRIPTION
           "Sets the low threshold (in links) for MEN-Ports
            that can possibly egress traffic ingressing this
            port when acting as a UNI.  This is based on EVC
            and EVC-Map configuration.  If Link State Awarness
            is enabled and the number of links in a MEN-Port
            falls below this value, the path to that MEN-Port
            is no longer considered to be a valid path through
            the system.  If there is no valid path through the
            system for any frames ingressing this UNI, the UNI
            will be disabled to notify the connected device
            that service is no longer available."
         ::= { adGenTA8xxPrv10100EthPortEntry 7 }

--==================================================================================================================

   adGenTA8xxPrvGigEthTable OBJECT-TYPE
      SYNTAX  SEQUENCE OF AdGenTA8xxPrvGigEthEntry
      MAX-ACCESS  not-accessible
      STATUS  current
      DESCRIPTION
         "The Ethernet SFP provisioning table."
      ::= { adGenTA8xxProvisioning 3 }

   adGenTA8xxPrvGigEthEntry OBJECT-TYPE
      SYNTAX  AdGenTA8xxPrvGigEthEntry
      MAX-ACCESS  not-accessible
      STATUS  current
      DESCRIPTION
         "An entry in the Ethernet SFP provisioning table."
      INDEX  { ifIndex }
      ::= { adGenTA8xxPrvGigEthTable 1 }

   AdGenTA8xxPrvGigEthEntry ::=
      SEQUENCE {
         adGenTA8xxGigEthState
	    INTEGER,
         adGenTA8xxGigEthLsa
            INTEGER,
         adGenTA8xxGigEthName
            DisplayString,
         adGenTA8xxGigEthPortSpeed
            INTEGER,
         adGenTA8xxGigEthLsaBandwidthMinimum
            Gauge32,
         adGenTA8xxGigEthLsaLinksMinimum
            Gauge32
      }

      adGenTA8xxGigEthState OBJECT-TYPE
         SYNTAX  INTEGER {
            disable(1),
            enable(2)
         }
         MAX-ACCESS  read-write
         STATUS  current
         DESCRIPTION
            "Enables or disables the selected gigabit ethernet port."
         ::= { adGenTA8xxPrvGigEthEntry 1 }

      adGenTA8xxGigEthLsa OBJECT-TYPE
         SYNTAX  INTEGER {
            disable(1),
            enable(2)
         }
         MAX-ACCESS  read-write
         STATUS  current
         DESCRIPTION
            "Enables or disables the link state awareness
             on the selected gigabit ethernet port."
         ::= { adGenTA8xxPrvGigEthEntry 2 }

      adGenTA8xxGigEthName OBJECT-TYPE
         SYNTAX  DisplayString
         MAX-ACCESS  read-write
         STATUS  current
         DESCRIPTION
            "Sets a display name associated with the selected
             gigabit ethernet port."
         ::= { adGenTA8xxPrvGigEthEntry 3 }

      adGenTA8xxGigEthPortSpeed OBJECT-TYPE
         SYNTAX  INTEGER {
            auto(1),
            speed100Mbps(2),
            speed1000Mbps(3),
	    speed10Mbps(4),
	    speed2500Mbps(5)
         }
         MAX-ACCESS  read-write
         STATUS  current
         DESCRIPTION
            "Provisions the speed for the selected gigabit
             ethernet port."
         ::= { adGenTA8xxPrvGigEthEntry 4 }

      adGenTA8xxGigEthLsaBandwidthMinimum OBJECT-TYPE
         SYNTAX  Gauge32
         MAX-ACCESS  read-write
         STATUS  current
         DESCRIPTION
           "Sets the low threshold (in kbps) for bandwidth
            on MEN-Ports that can possibly egress traffic
            ingressing this port when acting as a UNI.  This
            is based on EVC and EVC-Map configuration.
            If Link State Awarness is enabled and the
            bandwidth of a MEN-Port falls below this value,
            the path to that MEN-Port is no longer considered
            to be a valid path through the system.  If there
            is no valid path through the system for any frames
            ingressing this UNI, the UNI will be disabled to
            notify the connected device that service is no
            longer available."
         ::= { adGenTA8xxPrvGigEthEntry 5 }

      adGenTA8xxGigEthLsaLinksMinimum OBJECT-TYPE
         SYNTAX  Gauge32
         MAX-ACCESS  read-write
         STATUS  current
         DESCRIPTION
           "Sets the low threshold (in links) for MEN-Ports
            that can possibly egress traffic ingressing this
            port when acting as a UNI.  This is based on EVC
            and EVC-Map configuration.  If Link State Awarness
            is enabled and the number of links in a MEN-Port
            falls below this value, the path to that MEN-Port
            is no longer considered to be a valid path through
            the system.  If there is no valid path through the
            system for any frames ingressing this UNI, the UNI
            will be disabled to notify the connected device
            that service is no longer available."
          ::= { adGenTA8xxPrvGigEthEntry 6 }

--==================================================================================================================

   adGenTA8xxCardPrvTable OBJECT-TYPE
      SYNTAX  SEQUENCE OF AdGenTA8xxCardPrvEntry
      MAX-ACCESS  not-accessible
      STATUS  current
      DESCRIPTION
         "The Card Provisioning table."
      ::= { adGenTA8xxProvisioning 4 }

   adGenTA8xxCardPrvEntry OBJECT-TYPE
      SYNTAX  AdGenTA8xxCardPrvEntry
      MAX-ACCESS  not-accessible
      STATUS  current
      DESCRIPTION
         "An entry in the Card Provisioning table."
      INDEX   { adGenSlotInfoIndex }
      ::= { adGenTA8xxCardPrvTable 1 }

   AdGenTA8xxCardPrvEntry ::=
      SEQUENCE {
         adGenTA8xxRestoreFactoryDefaults
            INTEGER,
         adGenTA8xxReset
            INTEGER
      }

      adGenTA8xxRestoreFactoryDefaults OBJECT-TYPE
         SYNTAX  INTEGER {
            restoreFactoryDefaults(1)
         }
         MAX-ACCESS  read-write
         STATUS  current
         DESCRIPTION
            "A Set restores ALL provisioning to the factory defaults.
             Note: The factory default for SNMP is disabled.  SNMP can be
             enabled through a password protected interface (for example,
             through the craft port)."
         ::= { adGenTA8xxCardPrvEntry 1 }

      adGenTA8xxReset   OBJECT-TYPE
         SYNTAX  INTEGER {
            reset(1)
         }
         MAX-ACCESS  read-write
         STATUS  current
         DESCRIPTION
            "A Set restarts the Controller.  A get always returns a 1."
         ::= { adGenTA8xxCardPrvEntry 2 }

--==================================================================================================================
-- Status
--==================================================================================================================

   adGenTA8xxStatScalars                 OBJECT IDENTIFIER ::= { adGenTA8xxStatus 1 }

     adGenTA8xxCardStatus OBJECT-TYPE
         SYNTAX  INTEGER {
            softwareUpdate(3),
            cardFailure(4),
            normal(6)
         }
         MAX-ACCESS  read-only
         STATUS  current
         DESCRIPTION
            "This variable indicates the equipment status of the card."
         ::= { adGenTA8xxStatScalars 1 }

      adGenTA8xxCritRelay OBJECT-TYPE
         SYNTAX  INTEGER {
            inactive(1),
            active(2)
         }
         MAX-ACCESS read-only
         STATUS current
         DESCRIPTION
            "Indicates the current state of the Critical Alarm Relay."
         ::= { adGenTA8xxStatScalars 2 }

      adGenTA8xxMajRelay OBJECT-TYPE
         SYNTAX  INTEGER {
            inactive(1),
            active(2)
         }
         MAX-ACCESS read-only
         STATUS current
         DESCRIPTION
            "Indicates the current state of the Major Alarm Relay."
         ::= { adGenTA8xxStatScalars 3 }

      adGenTA8xxMinRelay OBJECT-TYPE
         SYNTAX  INTEGER {
            inactive(1),
            active(2)
         }
         MAX-ACCESS read-only
         STATUS current
         DESCRIPTION
            "Indicates the current state of the Minor Alarm Relay."
         ::= { adGenTA8xxStatScalars 4 }

      adGenTA8xxacoStatus OBJECT-TYPE
         SYNTAX  INTEGER {
            released (1),
            pressed (2)
         }
         MAX-ACCESS  read-only
         STATUS  current
         DESCRIPTION
            "Indicates the current state of the front panel ACO button."
         ::= { adGenTA8xxStatScalars 5 }

      adGenTA8xxACPwrInStatus OBJECT-TYPE
         SYNTAX  INTEGER {
            inactive (1),
            active (2)
         }
         MAX-ACCESS  read-only
         STATUS  current
         DESCRIPTION
            "Indicates whether or not the AC_PWR_IN alarm input is active."
         ::= { adGenTA8xxStatScalars 6 }

      adGenTA8xxPowerAStatus OBJECT-TYPE
         SYNTAX  INTEGER {
            inactive (1),
            active (2)
         }
         MAX-ACCESS  read-only
         STATUS  current
         DESCRIPTION
            "Indicates the state of the power supply A alarm input."
         ::= { adGenTA8xxStatScalars 7 }

      adGenTA8xxPowerBStatus OBJECT-TYPE
         SYNTAX  INTEGER {
            inactive (1),
            active (2)
         }
         MAX-ACCESS  read-only
         STATUS  current
         DESCRIPTION
            "Indicates the state of the power supply B alarm input."
         ::= { adGenTA8xxStatScalars 8 }

      adGenTA8xxEnvAlarmsAggregateStatus OBJECT-TYPE
         SYNTAX  INTEGER {
            ok(1),
            info(2),
            alert(3),
            minor(4),
            major(5),
            critical(6)
         }
         MAX-ACCESS  read-only
         STATUS  current
         DESCRIPTION
            "Indicates the highest active severity of all the environmental alarms."
         ::= { adGenTA8xxStatScalars 9 }

      adGenTA8xxIPAddress OBJECT-TYPE
         SYNTAX     IpAddress
         MAX-ACCESS  read-only
         STATUS  current
         DESCRIPTION
             "The IP Address assigned to this interface, if any."
         ::= { adGenTA8xxStatScalars 10 }

      adGenTA8xxSubnetMask OBJECT-TYPE
         SYNTAX     IpAddress
         MAX-ACCESS  read-only
         STATUS  current
         DESCRIPTION
             "The Subnet Mask assigned to this interface, if any."
         ::= { adGenTA8xxStatScalars 11 }

      adGenTA8xxDefaultGateway OBJECT-TYPE
         SYNTAX     IpAddress
         MAX-ACCESS  read-only
         STATUS  current
         DESCRIPTION
             "The Default Gateway assigned to this interface, if any."
         ::= { adGenTA8xxStatScalars 12 }

      adGenTA8xxBondingFunctLineSource OBJECT-TYPE
         SYNTAX  INTEGER {
            primaryLine(1),
            secondaryLine(2),
            fail(3)
         }
         MAX-ACCESS  read-only
         STATUS  current
         DESCRIPTION
             "Indicates which timing source is active.  If both timing sources are impaired, fail
             is reported."
         ::= { adGenTA8xxStatScalars 13 }

      adGenTA8xxBondingPriRefStatus OBJECT-TYPE
         SYNTAX  INTEGER {
            ok(1),
            fail(2),
            notApplicable(3)
         }
         MAX-ACCESS  read-only
         STATUS  current
         DESCRIPTION
             "Provides the status of the primary Bonding reference source."
         ::= { adGenTA8xxStatScalars 14 }

      adGenTA8xxBondingSecRefStatus OBJECT-TYPE
         SYNTAX  INTEGER {
            ok(1),
            fail(2),
            notApplicable(3)
         }
         MAX-ACCESS  read-only
         STATUS  current
         DESCRIPTION
             "Provides the status of the secondary Bonding reference source."
         ::= { adGenTA8xxStatScalars 15 }

      adGenTA8xxIpACLDepth OBJECT-TYPE
         SYNTAX  Integer32
         MAX-ACCESS  read-only
         STATUS  current
         DESCRIPTION
            "The current number of entries in the IP Access Control List.
             The maximum value is 64."
         ::= { adGenTA8xxStatScalars 16 }

      adGenTA8xxCurrentCPUUtilization OBJECT-TYPE
         SYNTAX  DisplayString
         MAX-ACCESS  read-only
         STATUS  current
         DESCRIPTION
            "The current CPU utilization."
         ::= { adGenTA8xxStatScalars 17 }

      adGenTA8xxMaxCPUUtilization OBJECT-TYPE
         SYNTAX  DisplayString
         MAX-ACCESS  read-only
         STATUS  current
         DESCRIPTION
            "The maximum CPU utilization since the last time the value was reset."
         ::= { adGenTA8xxStatScalars 18 }

      adGenTA8xxResetMaxCPUUtilization OBJECT-TYPE
         SYNTAX  INTEGER {
            reset(1)
         }
         MAX-ACCESS  read-write
         STATUS  current
         DESCRIPTION
            "Resets the maximum CPU utilization."
         ::= { adGenTA8xxStatScalars 19 }

      adGenTA8xxTemperatureCelsuis OBJECT-TYPE
         SYNTAX  DisplayString
         MAX-ACCESS  read-only
         STATUS  current
         DESCRIPTION
            "This value is the Celsuis temperature."
         ::= { adGenTA8xxStatScalars 20}

      adGenTA8xxTemperatureFahrenheit OBJECT-TYPE
         SYNTAX  DisplayString
         MAX-ACCESS  read-only
         STATUS  current
         DESCRIPTION
            "This value is the Fahrenheit temperature."
         ::= { adGenTA8xxStatScalars 21}

       adGenTA8xxCustomerDoor OBJECT-TYPE
         SYNTAX  INTEGER {
            open(1),
            closed(2)
         }
         MAX-ACCESS  read-only
         STATUS  current
         DESCRIPTION
            "This variable is status of the Customer Door."
         ::= { adGenTA8xxStatScalars 22}

      adGenTA8xxTelcoDoor OBJECT-TYPE
         SYNTAX  INTEGER {
            open(1),
            closed(2)
         }
         MAX-ACCESS  read-only
         STATUS  current
         DESCRIPTION
            "This variable is status of the Telco Door."
         ::= { adGenTA8xxStatScalars 23}

     adGenTA8xxAux1Door OBJECT-TYPE
         SYNTAX  INTEGER {
            open(1),
            closed(2)
         }
         MAX-ACCESS  read-only
         STATUS  current
         DESCRIPTION
            "This variable is status of the Aux1 Door."
         ::= { adGenTA8xxStatScalars 24}

      adGenTA8xxIpv6AddressPrefixLength OBJECT-TYPE
         SYNTAX  InetAddressPrefixLength
         MAX-ACCESS  read-only
         STATUS  current
         DESCRIPTION
            "The provisioned IPv6 unicast address prefix length."
         ::= { adGenTA8xxStatScalars 25 }

      adGenTA8xxIpv6AddressEui64 OBJECT-TYPE
         SYNTAX  TruthValue
         MAX-ACCESS  read-only
         STATUS  current
         DESCRIPTION
            "When true, then the operational IPv6 unicast address is a combination
             of the provisioned prefix and an EUI-64 formatted Interface ID."
         ::= { adGenTA8xxStatScalars 26 }

      adGenTA8xxIpv6Address OBJECT-TYPE
         SYNTAX  InetAddressIPv6
         MAX-ACCESS  read-only
         STATUS  current
         DESCRIPTION
            "The provisioned IPv6 unicast address or address prefix.
             If EUI-64 is false, then the operational unicast address equals
             this value. If EUI-64 is true, then the operational unicast address
             is derived from this value (high-order bits) and the Interface ID
             (low-order bits) in combination with the prefix length."
         ::= { adGenTA8xxStatScalars 27 }
  
      adGenTA8xxIpv6AddressOperational OBJECT-TYPE
         SYNTAX  InetAddressIPv6
         MAX-ACCESS  read-only
         STATUS  current
         DESCRIPTION
            "The operational 128-bit IPv6 unicast address."
         ::= { adGenTA8xxStatScalars 28 }
 
      adGenTA8xxIpv6AddressLinkLocal OBJECT-TYPE
         SYNTAX  InetAddressIPv6
         MAX-ACCESS  read-only
         STATUS  current
         DESCRIPTION
            "The provisioned IPv6 link-local address prefix.
             The prefix length is implicitly 10 bits."
         ::= { adGenTA8xxStatScalars 29 }
  
      adGenTA8xxIpv6AddressLinkLocalOperational OBJECT-TYPE
         SYNTAX  InetAddressIPv6
         MAX-ACCESS  read-only
         STATUS  current
         DESCRIPTION
            "The operational 128-bit IPv6 link-local address."
         ::= { adGenTA8xxStatScalars 30 }
 
--==================================================================================================================

      adGenTA8xxStat10100EthTable OBJECT-TYPE
         SYNTAX  SEQUENCE OF AdGenTA8xxStat10100EthEntry
         MAX-ACCESS  not-accessible
         STATUS  current
         DESCRIPTION
            "The 10/100 Ethernet port status table."
         ::= { adGenTA8xxStatus 2 }

         adGenTA8xxStat10100EthEntry OBJECT-TYPE
            SYNTAX  AdGenTA8xxStat10100EthEntry
            MAX-ACCESS  not-accessible
            STATUS  current
            DESCRIPTION
               "An entry in the 10/100 Ethernet Port status table."
            INDEX  { ifIndex }
            ::= { adGenTA8xxStat10100EthTable 1 }

         AdGenTA8xxStat10100EthEntry ::=
            SEQUENCE {
               adGenTA8xx10100EthLinkStatus
                  INTEGER,
               adGenTA8xx10100EthLinkSpeedDuplex
		  INTEGER
            }

         adGenTA8xx10100EthLinkStatus OBJECT-TYPE
            SYNTAX  INTEGER {
               up(1),
               down(2)
            }
            MAX-ACCESS  read-only
            STATUS  current
            DESCRIPTION
               "Indicates the status of ethernet port."
            ::= { adGenTA8xxStat10100EthEntry 1 }

         adGenTA8xx10100EthLinkSpeedDuplex OBJECT-TYPE
            SYNTAX  INTEGER {
               unknown(1),
               half10Mbps(5),
               full10Mbps(6),
               half100Mbps(7),
               full100Mbps(8)
            }
            MAX-ACCESS  read-only
            STATUS  current
            DESCRIPTION
               "Indicates the link speed and duplex of the ethenet
                port."
            ::= { adGenTA8xxStat10100EthEntry 2 }


--==================================================================================================================
      adGenTA8xxStatGigEthTable OBJECT-TYPE
         SYNTAX  SEQUENCE OF AdGenTA8xxStatGigEthEntry
         MAX-ACCESS  not-accessible
         STATUS  current
         DESCRIPTION
            "The Gigabit Ethernet port status table."
         ::= { adGenTA8xxStatus 3 }

         adGenTA8xxStatGigEthEntry OBJECT-TYPE
            SYNTAX  AdGenTA8xxStatGigEthEntry
            MAX-ACCESS  not-accessible
            STATUS  current
            DESCRIPTION
               "An entry in the Gigabit Ethernet Port status table."
            INDEX  { ifIndex }
            ::= { adGenTA8xxStatGigEthTable 1 }

         AdGenTA8xxStatGigEthEntry ::=
            SEQUENCE {
               adGenTA8xxGigEthLinkStatus
                  INTEGER,
	       adGenTA8xxGigEthSFPDescription
		  DisplayString,
	       adGenTA8xxGigEthSFPADTRANSerialNumber
		  DisplayString,
	       adGenTA8xxGigEthSFPADTRANPartNumber
		  DisplayString,
	       adGenTA8xxGigEthSFPADTRANCLEICode
		  DisplayString,
	       adGenTA8xxGigEthSFPJackType
		  INTEGER,
	       adGenTA8xxGigEthSFPADTRANApproved
                  INTEGER,
               adGenTA8xxGigEthSFPTemperature
		  DisplayString,
               adGenTA8xxGigEthSFPTxBias
		  DisplayString,
               adGenTA8xxGigEthSFPTxPower
		  DisplayString,
               adGenTA8xxGigEthSFPRxPower
                  DisplayString,
               adGenTA8xxGigEthLinkSpeedDuplex
                  INTEGER
            }

         adGenTA8xxGigEthLinkStatus OBJECT-TYPE
            SYNTAX  INTEGER {
               up(1),
               down(2)
            }
            MAX-ACCESS  read-only
            STATUS  current
            DESCRIPTION
               "Indicates the status of the gigabit ethernet port."
            ::= { adGenTA8xxStatGigEthEntry 1 }

         adGenTA8xxGigEthSFPDescription OBJECT-TYPE
            SYNTAX  DisplayString
            MAX-ACCESS  read-only
            STATUS  current
            DESCRIPTION
               "A textual description of the connected SFP."
            ::= { adGenTA8xxStatGigEthEntry 2 }

         adGenTA8xxGigEthSFPADTRANSerialNumber OBJECT-TYPE
            SYNTAX  DisplayString
            MAX-ACCESS  read-only
            STATUS  current
            DESCRIPTION
               "The ADTRAN serial number of the connected SFP."
            ::= { adGenTA8xxStatGigEthEntry 3 }

         adGenTA8xxGigEthSFPADTRANPartNumber OBJECT-TYPE
            SYNTAX  DisplayString
            MAX-ACCESS  read-only
            STATUS  current
            DESCRIPTION
               "The ADTRAN part number of the connected SFP."
            ::= { adGenTA8xxStatGigEthEntry 4 }

         adGenTA8xxGigEthSFPADTRANCLEICode OBJECT-TYPE
            SYNTAX  DisplayString
            MAX-ACCESS  read-only
            STATUS  current
            DESCRIPTION
               "The ADTRAN CLEI code of the connected SFP."
            ::= { adGenTA8xxStatGigEthEntry 5 }

         adGenTA8xxGigEthSFPJackType OBJECT-TYPE
            SYNTAX  INTEGER {
               other(1),
               fiberLC(2),
	       fiberSC(3),
	       mtrj(4),
	       hssdc(5),
	       copperRJ45(6)
            }
            MAX-ACCESS  read-only
            STATUS  current
            DESCRIPTION
               "Indicates the type of the connected SFP."
            ::= { adGenTA8xxStatGigEthEntry 6 }

         adGenTA8xxGigEthSFPADTRANApproved OBJECT-TYPE
            SYNTAX  INTEGER {
               notApplicable(1),
               approved(2),
	       notApproved(3)
            }
            MAX-ACCESS  read-only
            STATUS  current
            DESCRIPTION
               "Indicates if the connected SFP is ADTRAN approved."
            ::= { adGenTA8xxStatGigEthEntry 7 }

         adGenTA8xxGigEthSFPTemperature OBJECT-TYPE
            SYNTAX  DisplayString
            MAX-ACCESS  read-only
            STATUS  current
            DESCRIPTION
               "A textual representation of the current temperature
                of the SFP.  Note that only SFPs that support SFF8472
                Release 9.3 or higher support this status."
            ::= { adGenTA8xxStatGigEthEntry 8 }

         adGenTA8xxGigEthSFPTxBias OBJECT-TYPE
            SYNTAX  DisplayString
            MAX-ACCESS  read-only
            STATUS  current
            DESCRIPTION
               "A textual representation of the current transmit bias
                of the SFP.  Note that only SFPs that support SFF8472
                Release 9.3 or higher support this status."
            ::= { adGenTA8xxStatGigEthEntry 9 }

         adGenTA8xxGigEthSFPTxPower OBJECT-TYPE
            SYNTAX  DisplayString
            MAX-ACCESS  read-only
            STATUS  current
            DESCRIPTION
               "A textual representation of the current transmit power
                of the SFP.  Note that only SFPs that support SFF8472
                Release 9.3 or higher support this status."
            ::= { adGenTA8xxStatGigEthEntry 10 }

         adGenTA8xxGigEthSFPRxPower OBJECT-TYPE
            SYNTAX  DisplayString
            MAX-ACCESS  read-only
            STATUS  current
            DESCRIPTION
               "A textual representation of the current receive power
                of the SFP.  Note that only SFPs that support SFF8472
                Release 9.3 or higher support this status."
            ::= { adGenTA8xxStatGigEthEntry 11 }

         adGenTA8xxGigEthLinkSpeedDuplex OBJECT-TYPE
            SYNTAX  INTEGER {
               unknown(1),
               half10Mbps(2),
               full10Mbps(3),
               half100Mbps(4),
               full100Mbps(5),
               half1000Mbps(6),
               full1000Mbps(7),
               half2500Mbps(8),
               full2500Mbps(9)
            }
            MAX-ACCESS  read-only
            STATUS  current
            DESCRIPTION
               "Indicates the link speed and duplex of the ethenet
                port."
            ::= { adGenTA8xxStatGigEthEntry 12 }


--==================================================================================================================

      adGenTA8xxStatIpAclTable OBJECT-TYPE
         SYNTAX  SEQUENCE OF AdGenTA8xxStatIpAclEntry
         MAX-ACCESS  not-accessible
         STATUS  current
         DESCRIPTION
            "The IP Access Control List port status table."
         ::= { adGenTA8xxStatus 4 }

         adGenTA8xxStatIpAclEntry OBJECT-TYPE
            SYNTAX  AdGenTA8xxStatIpAclEntry
            MAX-ACCESS  not-accessible
            STATUS  current
            DESCRIPTION
               "An entry in the IP Access Control List status table."
            INDEX  { adGenTA8xxIpAclEntryIndex }
            ::= { adGenTA8xxStatIpAclTable 1 }

         AdGenTA8xxStatIpAclEntry ::=
            SEQUENCE {
               adGenTA8xxIpAclEntryIndex
                  Integer32,
               adGenTA8xxIpAclEntries
                  IpAddress
            }

         adGenTA8xxIpAclEntryIndex OBJECT-TYPE
            SYNTAX  Integer32
            MAX-ACCESS  read-only
            STATUS  current
            DESCRIPTION
               "Index of entries in IP Access Control List"
            ::= { adGenTA8xxStatIpAclEntry 1 }

         adGenTA8xxIpAclEntries OBJECT-TYPE
            SYNTAX  IpAddress
            MAX-ACCESS  read-only
            STATUS  current
            DESCRIPTION
               "All of the IP Address permitted by IP Access Control List"
            ::= { adGenTA8xxStatIpAclEntry 2 }



--=================================================================================================================================================================
   adGenTA8xxPerformanceScalars  OBJECT IDENTIFIER ::= { adGenTA8xxPerformance 1 }

      adGenTA8xxRstAllCurrentIntervals OBJECT-TYPE
         SYNTAX  INTEGER {
            rstAllCurrentIntervals(1)
         }
         MAX-ACCESS  read-write
         STATUS  current
         DESCRIPTION
            "Resets ALL current interval PM data."
          ::= { adGenTA8xxPerformanceScalars 1 }

      adGenTA8xxRstAllIntervals OBJECT-TYPE
         SYNTAX  INTEGER {
            rstAllIntervals(1)
         }
         MAX-ACCESS  read-write
         STATUS  current
         DESCRIPTION
            "Resets ALL PM data."
         ::= { adGenTA8xxPerformanceScalars 2 }

      adGenTA8xxMgmtStatsCurrentTxFrames OBJECT-TYPE
         SYNTAX Gauge32
         MAX-ACCESS  read-only
         STATUS  current
         DESCRIPTION
            "The counter associated with the number of Tx Frames
             encountered by the management channel."
         ::= { adGenTA8xxPerformanceScalars 3 }


      adGenTA8xxMgmtStatsCurrentRxFrames OBJECT-TYPE
         SYNTAX Gauge32
         MAX-ACCESS  read-only
         STATUS  current
         DESCRIPTION
            "The counter associated with the number of Rx Frames
             encountered by the management channel."
         ::= { adGenTA8xxPerformanceScalars 4 }

--==================================================================================================================

   adGenTA8xx10100EthPerformance  OBJECT IDENTIFIER ::= { adGenTA8xxPerformance 2 }

   adGenTA8xx10100EthPerformanceScalars	OBJECT IDENTIFIER ::= { adGenTA8xx10100EthPerformance 1}

      adGenTA8xx10100EthRstCurrentIntervals OBJECT-TYPE
         SYNTAX  INTEGER {
            ethRstAllCurrentIntervals(1)
         }
         MAX-ACCESS  read-write
         STATUS  current
         DESCRIPTION
            "Reset current interval PM data on Ethernet ports."
          ::= { adGenTA8xx10100EthPerformanceScalars 1 }

      adGenTA8xx10100EthRstAll OBJECT-TYPE
         SYNTAX  INTEGER {
            ethRstAll(1)
         }
         MAX-ACCESS  read-write
         STATUS  current
         DESCRIPTION
            "Reset PM data on ALL Ethernet ports."
         ::= { adGenTA8xx10100EthPerformanceScalars 2 }

--==================================================================================================================

   adGenTA8xx10100Eth15MinCurrentTable OBJECT-TYPE
      SYNTAX  SEQUENCE OF AdGenTA8xx10100Eth15MinCurrentEntry
      MAX-ACCESS  not-accessible
      STATUS  current
      DESCRIPTION
         "The 10/100 Ethernet 15Min current table."
      ::= { adGenTA8xx10100EthPerformance 2 }

   adGenTA8xx10100Eth15MinCurrentEntry OBJECT-TYPE
      SYNTAX  AdGenTA8xx10100Eth15MinCurrentEntry
      MAX-ACCESS  not-accessible
      STATUS  current
      DESCRIPTION
         "An entry in the 10/100 Ethernet 15Min current table."
      INDEX   { ifIndex }
      ::= { adGenTA8xx10100Eth15MinCurrentTable 1 }

   AdGenTA8xx10100Eth15MinCurrentEntry  ::=
      SEQUENCE {
         adGenTA8xx10100Eth15MinCurrentTxBytes
	        Gauge32,
         adGenTA8xx10100Eth15MinCurrentTxFrames
	        Gauge32,
         adGenTA8xx10100Eth15MinCurrentRxBytes
	        Gauge32,
         adGenTA8xx10100Eth15MinCurrentRxFrames
            Gauge32,
         adGenTA8xx10100Eth15MinCurrentRxCRCAlignErrs
            Gauge32,
         adGenTA8xx10100Eth15MinCurrentRxUndersizeFrames
            Gauge32,
         adGenTA8xx10100Eth15MinCurrentRxOversizeFrames
	        Gauge32,
         adGenTA8xx10100Eth15MinCurrentRxCollisions
	        Gauge32,
         adGenTA8xx10100Eth15MinCurrentRxDiscardedFrames
            Gauge32,
         adGenTA8xx10100Eth15MinCurrentRxMulticastFrames
            Gauge32,
         adGenTA8xx10100Eth15MinCurrentRxBroadcastFrames
            Gauge32,
         adGenTA8xx10100Eth15MinCurrentRxUnicastFrames
            Gauge32,
         adGenTA8xx10100Eth15MinCurrentTxMulticastFrames
            Gauge32,
         adGenTA8xx10100Eth15MinCurrentTxBroadcastFrames
            Gauge32,
         adGenTA8xx10100Eth15MinCurrentTxUnicastFrames
            Gauge32,
         adGenTA8xx10100Eth15MinCurrentRxGoodBytes
	        Gauge32,
         adGenTA8xx10100Eth15MinCurrentRxGoodFrames
            Gauge32,
         adGenTA8xx10100Eth15MinCurrentRxJabbers
            Gauge32,
         adGenTA8xx10100Eth15MinCurrentRxFragments
            Gauge32
       }

      adGenTA8xx10100Eth15MinCurrentTxBytes OBJECT-TYPE
         SYNTAX Gauge32
         MAX-ACCESS  read-only
         STATUS  current
         DESCRIPTION
            "The counter associated with the number of Tx Bytes
	     encountered by an interface in the current interval."
         ::= { adGenTA8xx10100Eth15MinCurrentEntry 1 }

      adGenTA8xx10100Eth15MinCurrentTxFrames OBJECT-TYPE
         SYNTAX Gauge32
         MAX-ACCESS  read-only
         STATUS  current
         DESCRIPTION
            "The counter associated with the number of Tx Frames
             encountered by an interface in the current interval."
         ::= { adGenTA8xx10100Eth15MinCurrentEntry 2 }

      adGenTA8xx10100Eth15MinCurrentRxBytes OBJECT-TYPE
         SYNTAX Gauge32
         MAX-ACCESS  read-only
         STATUS  current
         DESCRIPTION
            "The counter associated with the number of Rx Bytes
             encountered by an interface in the current interval."
         ::= { adGenTA8xx10100Eth15MinCurrentEntry 3 }

      adGenTA8xx10100Eth15MinCurrentRxFrames OBJECT-TYPE
         SYNTAX Gauge32
         MAX-ACCESS  read-only
         STATUS  current
         DESCRIPTION
            "The counter associated with the number of Rx Frames
             encountered by an interface in the current interval."
         ::= { adGenTA8xx10100Eth15MinCurrentEntry 4 }

      adGenTA8xx10100Eth15MinCurrentRxCRCAlignErrs OBJECT-TYPE
         SYNTAX Gauge32
         MAX-ACCESS  read-only
         STATUS  current
         DESCRIPTION
            "The counter associated with the number of Rx Alignment & FCS Errors
             encountered by an interface in the current interval."
         ::= { adGenTA8xx10100Eth15MinCurrentEntry 5 }

      adGenTA8xx10100Eth15MinCurrentRxUndersizeFrames OBJECT-TYPE
         SYNTAX Gauge32
         MAX-ACCESS  read-only
         STATUS  current
         DESCRIPTION
            "The counter associated with the number of Rx Undersized Frames
             encountered by an interface in the current interval."
         ::= { adGenTA8xx10100Eth15MinCurrentEntry 6 }

      adGenTA8xx10100Eth15MinCurrentRxOversizeFrames OBJECT-TYPE
         SYNTAX Gauge32
         MAX-ACCESS  read-only
         STATUS  current
         DESCRIPTION
            "The counter associated with the number of Rx Oversized Frames
             encountered by an interface in the current interval."
         ::= { adGenTA8xx10100Eth15MinCurrentEntry 7 }

      adGenTA8xx10100Eth15MinCurrentRxCollisions OBJECT-TYPE
         SYNTAX Gauge32
         MAX-ACCESS  read-only
         STATUS  current
         DESCRIPTION
            "The counter associated with the number of Rx Collisions
             encountered by an interface in the current interval."
         ::= { adGenTA8xx10100Eth15MinCurrentEntry 8 }

      adGenTA8xx10100Eth15MinCurrentRxDiscardedFrames OBJECT-TYPE
         SYNTAX Gauge32
         MAX-ACCESS  read-only
         STATUS  current
         DESCRIPTION
            "The counter associated with the number of Rx Discarded Frames
             encountered by an interface in the current interval."
         ::= { adGenTA8xx10100Eth15MinCurrentEntry 9 }

      adGenTA8xx10100Eth15MinCurrentRxMulticastFrames OBJECT-TYPE
         SYNTAX Gauge32
         MAX-ACCESS  read-only
         STATUS  current
         DESCRIPTION
            "The counter associated with the number of Rx Multicast Frames
             encountered by an interface in the current interval."
         ::= { adGenTA8xx10100Eth15MinCurrentEntry 10 }

      adGenTA8xx10100Eth15MinCurrentRxBroadcastFrames OBJECT-TYPE
         SYNTAX Gauge32
         MAX-ACCESS  read-only
         STATUS  current
         DESCRIPTION
            "The counter associated with the number of Rx Broadcast Frames
             encountered by an interface in the current interval."
         ::= { adGenTA8xx10100Eth15MinCurrentEntry 11 }

      adGenTA8xx10100Eth15MinCurrentRxUnicastFrames OBJECT-TYPE
         SYNTAX Gauge32
         MAX-ACCESS  read-only
         STATUS  current
         DESCRIPTION
            "The counter associated with the number of Rx Unicast Frames
             encountered by an interface in the current interval."
         ::= { adGenTA8xx10100Eth15MinCurrentEntry 12 }

      adGenTA8xx10100Eth15MinCurrentTxMulticastFrames OBJECT-TYPE
         SYNTAX Gauge32
         MAX-ACCESS  read-only
         STATUS  current
         DESCRIPTION
            "The counter associated with the number of Tx Multicast Frames
             encountered by an interface in the current interval."
         ::= { adGenTA8xx10100Eth15MinCurrentEntry 13 }

      adGenTA8xx10100Eth15MinCurrentTxBroadcastFrames OBJECT-TYPE
         SYNTAX Gauge32
         MAX-ACCESS  read-only
         STATUS  current
         DESCRIPTION
            "The counter associated with the number of Tx Broadcast Frames
             encountered by an interface in the current interval."
         ::= { adGenTA8xx10100Eth15MinCurrentEntry 14 }

      adGenTA8xx10100Eth15MinCurrentTxUnicastFrames OBJECT-TYPE
         SYNTAX Gauge32
         MAX-ACCESS  read-only
         STATUS  current
         DESCRIPTION
            "The counter associated with the number of Tx Unicast Frames
             encountered by an interface in the current interval."
         ::= { adGenTA8xx10100Eth15MinCurrentEntry 15 }

      adGenTA8xx10100Eth15MinCurrentRxGoodBytes OBJECT-TYPE
         SYNTAX Gauge32
         MAX-ACCESS  read-only
         STATUS  current
         DESCRIPTION
            "The counter associated with the number of error-free Rx Bytes
             encountered by an interface in the current interval."
         ::= { adGenTA8xx10100Eth15MinCurrentEntry 16 }

      adGenTA8xx10100Eth15MinCurrentRxGoodFrames OBJECT-TYPE
         SYNTAX Gauge32
         MAX-ACCESS  read-only
         STATUS  current
         DESCRIPTION
            "The counter associated with the number of error-free Rx Frames
             encountered by an interface in the current interval."
         ::= { adGenTA8xx10100Eth15MinCurrentEntry 17 }

      adGenTA8xx10100Eth15MinCurrentRxJabbers OBJECT-TYPE
         SYNTAX Gauge32
         MAX-ACCESS  read-only
         STATUS  current
         DESCRIPTION
            "The counter associated with the number of Rx Jabbers
             encountered by an interface in the current interval."
         ::= { adGenTA8xx10100Eth15MinCurrentEntry 18 }

      adGenTA8xx10100Eth15MinCurrentRxFragments OBJECT-TYPE
         SYNTAX Gauge32
         MAX-ACCESS  read-only
         STATUS  current
         DESCRIPTION
            "The counter associated with the number of Rx Fragments
             encountered by an interface in the current interval."
         ::= { adGenTA8xx10100Eth15MinCurrentEntry 19 }

--==================================================================================================================

   adGenTA8xx10100Eth15MinIntervalTable OBJECT-TYPE
      SYNTAX  SEQUENCE OF AdGenTA8xx10100Eth15MinIntervalEntry
      MAX-ACCESS  not-accessible
      STATUS  current
      DESCRIPTION
         "The 10/100 Ethernet 15Min interval table."
      ::= { adGenTA8xx10100EthPerformance 3 }

   adGenTA8xx10100Eth15MinIntervalEntry OBJECT-TYPE
      SYNTAX  AdGenTA8xx10100Eth15MinIntervalEntry
      MAX-ACCESS  not-accessible
      STATUS  current
      DESCRIPTION
         "An entry in the 10/100 Ethernet 15Min interval table."
      INDEX   { ifIndex, adGenTA8xx10100Eth15MinIntervalNumber }
      ::= { adGenTA8xx10100Eth15MinIntervalTable 1 }

   AdGenTA8xx10100Eth15MinIntervalEntry  ::=
      SEQUENCE {
         adGenTA8xx10100Eth15MinIntervalNumber
            Integer32,
         adGenTA8xx10100Eth15MinIntervalTxBytes
	    Gauge32,
         adGenTA8xx10100Eth15MinIntervalTxFrames
	    Gauge32,
         adGenTA8xx10100Eth15MinIntervalRxBytes
	    Gauge32,
         adGenTA8xx10100Eth15MinIntervalRxFrames
            Gauge32,
         adGenTA8xx10100Eth15MinIntervalRxCRCAlignErrs
            Gauge32,
         adGenTA8xx10100Eth15MinIntervalRxUndersizeFrames
            Gauge32,
         adGenTA8xx10100Eth15MinIntervalRxOversizeFrames
	    Gauge32,
         adGenTA8xx10100Eth15MinIntervalRxCollisions
	    Gauge32,
         adGenTA8xx10100Eth15MinIntervalRxDiscardedFrames
            Gauge32,
         adGenTA8xx10100Eth15MinIntervalRxMulticastFrames
            Gauge32,
         adGenTA8xx10100Eth15MinIntervalRxBroadcastFrames
            Gauge32,
         adGenTA8xx10100Eth15MinIntervalRxUnicastFrames
            Gauge32,
         adGenTA8xx10100Eth15MinIntervalTxMulticastFrames
            Gauge32,
         adGenTA8xx10100Eth15MinIntervalTxUnicastFrames
            Gauge32,
         adGenTA8xx10100Eth15MinIntervalTxBroadcastFrames
            Gauge32,
         adGenTA8xx10100Eth15MinIntervalRxGoodBytes
	    Gauge32,
         adGenTA8xx10100Eth15MinIntervalRxGoodFrames
            Gauge32,
         adGenTA8xx10100Eth15MinIntervalRxJabbers
            Gauge32,
         adGenTA8xx10100Eth15MinIntervalRxFragments
            Gauge32
       }

      adGenTA8xx10100Eth15MinIntervalNumber OBJECT-TYPE
         SYNTAX  Integer32
         MAX-ACCESS  read-only
         STATUS  current
         DESCRIPTION
            "A number between 1 and 96, where 1 is the most
             recently completed 15 minute interval and 96 is
             the least recently completed 15 minutes interval
             (assuming that all 96 intervals are valid)."
         ::= { adGenTA8xx10100Eth15MinIntervalEntry 1 }

      adGenTA8xx10100Eth15MinIntervalTxBytes OBJECT-TYPE
         SYNTAX Gauge32
         MAX-ACCESS  read-only
         STATUS  current
         DESCRIPTION
            "The counter associated with the number of Tx Bytes
	     encountered by an interface in the selected interval."
         ::= { adGenTA8xx10100Eth15MinIntervalEntry 2 }

      adGenTA8xx10100Eth15MinIntervalTxFrames OBJECT-TYPE
         SYNTAX Gauge32
         MAX-ACCESS  read-only
         STATUS  current
         DESCRIPTION
            "The counter associated with the number of Tx Frames
             encountered by an interface in the selected interval."
         ::= { adGenTA8xx10100Eth15MinIntervalEntry 3 }

      adGenTA8xx10100Eth15MinIntervalRxBytes OBJECT-TYPE
         SYNTAX Gauge32
         MAX-ACCESS  read-only
         STATUS  current
         DESCRIPTION
            "The counter associated with the number of Rx Bytes
             encountered by an interface in the selected interval."
         ::= { adGenTA8xx10100Eth15MinIntervalEntry 4 }

      adGenTA8xx10100Eth15MinIntervalRxFrames OBJECT-TYPE
         SYNTAX Gauge32
         MAX-ACCESS  read-only
         STATUS  current
         DESCRIPTION
            "The counter associated with the number of Rx Frames
             encountered by an interface in the selected interval."
         ::= { adGenTA8xx10100Eth15MinIntervalEntry 5 }

      adGenTA8xx10100Eth15MinIntervalRxCRCAlignErrs OBJECT-TYPE
         SYNTAX Gauge32
         MAX-ACCESS  read-only
         STATUS  current
         DESCRIPTION
            "The counter associated with the number of Rx Alignment & FCS Errors
             encountered by an interface in the selected interval."
         ::= { adGenTA8xx10100Eth15MinIntervalEntry 6 }

      adGenTA8xx10100Eth15MinIntervalRxUndersizeFrames OBJECT-TYPE
         SYNTAX Gauge32
         MAX-ACCESS  read-only
         STATUS  current
         DESCRIPTION
            "The counter associated with the number of Rx Undersized Frames
             encountered by an interface in the selected interval."
         ::= { adGenTA8xx10100Eth15MinIntervalEntry 7 }

      adGenTA8xx10100Eth15MinIntervalRxOversizeFrames OBJECT-TYPE
         SYNTAX Gauge32
         MAX-ACCESS  read-only
         STATUS  current
         DESCRIPTION
            "The counter associated with the number of Rx Oversized Frames
             encountered by an interface in the selected interval."
         ::= { adGenTA8xx10100Eth15MinIntervalEntry 8 }

      adGenTA8xx10100Eth15MinIntervalRxCollisions OBJECT-TYPE
         SYNTAX Gauge32
         MAX-ACCESS  read-only
         STATUS  current
         DESCRIPTION
            "The counter associated with the number of Rx Collisions
             encountered by an interface in the selected interval."
         ::= { adGenTA8xx10100Eth15MinIntervalEntry 9 }

      adGenTA8xx10100Eth15MinIntervalRxDiscardedFrames OBJECT-TYPE
         SYNTAX Gauge32
         MAX-ACCESS  read-only
         STATUS  current
         DESCRIPTION
            "The counter associated with the number of Rx Discarded Frames
             encountered by an interface in the selected interval."
         ::= { adGenTA8xx10100Eth15MinIntervalEntry 10 }

      adGenTA8xx10100Eth15MinIntervalRxMulticastFrames OBJECT-TYPE
         SYNTAX Gauge32
         MAX-ACCESS  read-only
         STATUS  current
         DESCRIPTION
            "The counter associated with the number of Rx Multicast Frames
             encountered by an interface in the selected interval."
         ::= { adGenTA8xx10100Eth15MinIntervalEntry 11 }

      adGenTA8xx10100Eth15MinIntervalRxBroadcastFrames OBJECT-TYPE
         SYNTAX Gauge32
         MAX-ACCESS  read-only
         STATUS  current
         DESCRIPTION
            "The counter associated with the number of Rx Broadcast Frames
             encountered by an interface in the selected interval."
         ::= { adGenTA8xx10100Eth15MinIntervalEntry 12 }

      adGenTA8xx10100Eth15MinIntervalRxUnicastFrames OBJECT-TYPE
         SYNTAX Gauge32
         MAX-ACCESS  read-only
         STATUS  current
         DESCRIPTION
            "The counter associated with the number of Rx Unicast Frames
             encountered by an interface in the selected interval."
         ::= { adGenTA8xx10100Eth15MinIntervalEntry 13 }

      adGenTA8xx10100Eth15MinIntervalTxMulticastFrames OBJECT-TYPE
         SYNTAX Gauge32
         MAX-ACCESS  read-only
         STATUS  current
         DESCRIPTION
            "The counter associated with the number of Tx Multicast Frames
             encountered by an interface in the selected interval."
         ::= { adGenTA8xx10100Eth15MinIntervalEntry 14 }

      adGenTA8xx10100Eth15MinIntervalTxBroadcastFrames OBJECT-TYPE
         SYNTAX Gauge32
         MAX-ACCESS  read-only
         STATUS  current
         DESCRIPTION
            "The counter associated with the number of Tx Broadcast Frames
             encountered by an interface in the selected interval."
         ::= { adGenTA8xx10100Eth15MinIntervalEntry 15 }

      adGenTA8xx10100Eth15MinIntervalTxUnicastFrames OBJECT-TYPE
         SYNTAX Gauge32
         MAX-ACCESS  read-only
         STATUS  current
         DESCRIPTION
            "The counter associated with the number of Tx Unicast Frames
             encountered by an interface in the selected interval."
         ::= { adGenTA8xx10100Eth15MinIntervalEntry 16 }

      adGenTA8xx10100Eth15MinIntervalRxGoodBytes OBJECT-TYPE
         SYNTAX Gauge32
         MAX-ACCESS  read-only
         STATUS  current
         DESCRIPTION
            "The counter associated with the number of error-free Rx Bytes
             encountered by an interface in the selected interval."
         ::= { adGenTA8xx10100Eth15MinIntervalEntry 17 }

      adGenTA8xx10100Eth15MinIntervalRxGoodFrames OBJECT-TYPE
         SYNTAX Gauge32
         MAX-ACCESS  read-only
         STATUS  current
         DESCRIPTION
            "The counter associated with the number of error-free Rx Frames
             encountered by an interface in the selected interval."
         ::= { adGenTA8xx10100Eth15MinIntervalEntry 18 }

      adGenTA8xx10100Eth15MinIntervalRxJabbers OBJECT-TYPE
         SYNTAX Gauge32
         MAX-ACCESS  read-only
         STATUS  current
         DESCRIPTION
            "The counter associated with the number of Rx Jabbers
             encountered by an interface in the selected interval."
         ::= { adGenTA8xx10100Eth15MinIntervalEntry 19 }

      adGenTA8xx10100Eth15MinIntervalRxFragments OBJECT-TYPE
         SYNTAX Gauge32
         MAX-ACCESS  read-only
         STATUS  current
         DESCRIPTION
            "The counter associated with the number of Rx Fragments
             encountered by an interface in the selected interval."
         ::= { adGenTA8xx10100Eth15MinIntervalEntry 20 }

--==================================================================================================================

   adGenTA8xx10100Eth24HrCurrentTable OBJECT-TYPE
      SYNTAX  SEQUENCE OF AdGenTA8xx10100Eth24HrCurrentEntry
      MAX-ACCESS  not-accessible
      STATUS  current
      DESCRIPTION
         "The 10/100 Ethernet 24Hr current table."
      ::= { adGenTA8xx10100EthPerformance 4 }

   adGenTA8xx10100Eth24HrCurrentEntry OBJECT-TYPE
      SYNTAX  AdGenTA8xx10100Eth24HrCurrentEntry
      MAX-ACCESS  not-accessible
      STATUS  current
      DESCRIPTION
         "An entry in the 10/100 Ethernet 24Hr current table."
      INDEX   { ifIndex }
      ::= { adGenTA8xx10100Eth24HrCurrentTable 1 }

   AdGenTA8xx10100Eth24HrCurrentEntry  ::=
      SEQUENCE {
         adGenTA8xx10100Eth24HrCurrentTxBytes
	    Gauge32,
         adGenTA8xx10100Eth24HrCurrentTxFrames
	    Gauge32,
         adGenTA8xx10100Eth24HrCurrentRxBytes
	    Gauge32,
         adGenTA8xx10100Eth24HrCurrentRxFrames
            Gauge32,
         adGenTA8xx10100Eth24HrCurrentRxCRCAlignErrs
            Gauge32,
         adGenTA8xx10100Eth24HrCurrentRxUndersizeFrames
            Gauge32,
         adGenTA8xx10100Eth24HrCurrentRxOversizeFrames
	    Gauge32,
         adGenTA8xx10100Eth24HrCurrentRxCollisions
	    Gauge32,
         adGenTA8xx10100Eth24HrCurrentRxDiscardedFrames
            Gauge32,
         adGenTA8xx10100Eth24HrCurrentRxMulticastFrames
            Gauge32,
         adGenTA8xx10100Eth24HrCurrentRxBroadcastFrames
            Gauge32,
         adGenTA8xx10100Eth24HrCurrentRxUnicastFrames
            Gauge32,
         adGenTA8xx10100Eth24HrCurrentTxMulticastFrames
            Gauge32,
         adGenTA8xx10100Eth24HrCurrentTxBroadcastFrames
            Gauge32,
         adGenTA8xx10100Eth24HrCurrentTxUnicastFrames
            Gauge32,
         adGenTA8xx10100Eth24HrCurrentRxGoodBytes
       	    Gauge32,
         adGenTA8xx10100Eth24HrCurrentRxGoodFrames
            Gauge32,
         adGenTA8xx10100Eth24HrCurrentRxJabbers
            Gauge32,
         adGenTA8xx10100Eth24HrCurrentRxFragments
            Gauge32
       }

      adGenTA8xx10100Eth24HrCurrentTxBytes OBJECT-TYPE
         SYNTAX Gauge32
         MAX-ACCESS  read-only
         STATUS  current
         DESCRIPTION
            "The counter associated with the number of Tx Bytes
	     encountered by an interface in the current day."
         ::= { adGenTA8xx10100Eth24HrCurrentEntry 1 }

      adGenTA8xx10100Eth24HrCurrentTxFrames OBJECT-TYPE
         SYNTAX Gauge32
         MAX-ACCESS  read-only
         STATUS  current
         DESCRIPTION
            "The counter associated with the number of Tx Frames
             encountered by an interface in the current day."
         ::= { adGenTA8xx10100Eth24HrCurrentEntry 2 }

      adGenTA8xx10100Eth24HrCurrentRxBytes OBJECT-TYPE
         SYNTAX Gauge32
         MAX-ACCESS  read-only
         STATUS  current
         DESCRIPTION
            "The counter associated with the number of Rx Bytes
             encountered by an interface in the current day."
         ::= { adGenTA8xx10100Eth24HrCurrentEntry 3 }

      adGenTA8xx10100Eth24HrCurrentRxFrames OBJECT-TYPE
         SYNTAX Gauge32
         MAX-ACCESS  read-only
         STATUS  current
         DESCRIPTION
            "The counter associated with the number of Rx Frames
             encountered by an interface in the current day."
         ::= { adGenTA8xx10100Eth24HrCurrentEntry 4 }

      adGenTA8xx10100Eth24HrCurrentRxCRCAlignErrs OBJECT-TYPE
         SYNTAX Gauge32
         MAX-ACCESS  read-only
         STATUS  current
         DESCRIPTION
            "The counter associated with the number of Rx Alignment & FCS Errors
             encountered by an interface in the current day."
         ::= { adGenTA8xx10100Eth24HrCurrentEntry 5 }

      adGenTA8xx10100Eth24HrCurrentRxUndersizeFrames OBJECT-TYPE
         SYNTAX Gauge32
         MAX-ACCESS  read-only
         STATUS  current
         DESCRIPTION
            "The counter associated with the number of Rx Undersized Frames
             encountered by an interface in the current day."
         ::= { adGenTA8xx10100Eth24HrCurrentEntry 6 }

      adGenTA8xx10100Eth24HrCurrentRxOversizeFrames OBJECT-TYPE
         SYNTAX Gauge32
         MAX-ACCESS  read-only
         STATUS  current
         DESCRIPTION
            "The counter associated with the number of Rx Oversized Frames
             encountered by an interface in the current day."
         ::= { adGenTA8xx10100Eth24HrCurrentEntry 7 }

      adGenTA8xx10100Eth24HrCurrentRxCollisions OBJECT-TYPE
         SYNTAX Gauge32
         MAX-ACCESS  read-only
         STATUS  current
         DESCRIPTION
            "The counter associated with the number of Rx Collisions
             encountered by an interface in the current day."
         ::= { adGenTA8xx10100Eth24HrCurrentEntry 8 }

      adGenTA8xx10100Eth24HrCurrentRxDiscardedFrames OBJECT-TYPE
         SYNTAX Gauge32
         MAX-ACCESS  read-only
         STATUS  current
         DESCRIPTION
            "The counter associated with the number of Rx Discarded Frames
             encountered by an interface in the current interval."
         ::= { adGenTA8xx10100Eth24HrCurrentEntry 9 }

      adGenTA8xx10100Eth24HrCurrentRxMulticastFrames OBJECT-TYPE
         SYNTAX Gauge32
         MAX-ACCESS  read-only
         STATUS  current
         DESCRIPTION
            "The counter associated with the number of Rx Multicast Frames
             encountered by an interface in the current interval."
         ::= { adGenTA8xx10100Eth24HrCurrentEntry 10 }

      adGenTA8xx10100Eth24HrCurrentRxBroadcastFrames OBJECT-TYPE
         SYNTAX Gauge32
         MAX-ACCESS  read-only
         STATUS  current
         DESCRIPTION
            "The counter associated with the number of Rx Broadcast Frames
             encountered by an interface in the current interval."
         ::= { adGenTA8xx10100Eth24HrCurrentEntry 11 }

      adGenTA8xx10100Eth24HrCurrentRxUnicastFrames OBJECT-TYPE
         SYNTAX Gauge32
         MAX-ACCESS  read-only
         STATUS  current
         DESCRIPTION
            "The counter associated with the number of Rx Unicast Frames
             encountered by an interface in the current interval."
         ::= { adGenTA8xx10100Eth24HrCurrentEntry 12 }

      adGenTA8xx10100Eth24HrCurrentTxMulticastFrames OBJECT-TYPE
         SYNTAX Gauge32
         MAX-ACCESS  read-only
         STATUS  current
         DESCRIPTION
            "The counter associated with the number of Tx Multicast Frames
             encountered by an interface in the current interval."
         ::= { adGenTA8xx10100Eth24HrCurrentEntry 13 }

      adGenTA8xx10100Eth24HrCurrentTxBroadcastFrames OBJECT-TYPE
         SYNTAX Gauge32
         MAX-ACCESS  read-only
         STATUS  current
         DESCRIPTION
            "The counter associated with the number of Tx Broadcast Frames
             encountered by an interface in the current interval."
         ::= { adGenTA8xx10100Eth24HrCurrentEntry 14 }

      adGenTA8xx10100Eth24HrCurrentTxUnicastFrames OBJECT-TYPE
         SYNTAX Gauge32
         MAX-ACCESS  read-only
         STATUS  current
         DESCRIPTION
            "The counter associated with the number of Tx Unicast Frames
             encountered by an interface in the current interval."
         ::= { adGenTA8xx10100Eth24HrCurrentEntry 15 }

      adGenTA8xx10100Eth24HrCurrentRxGoodBytes OBJECT-TYPE
         SYNTAX Gauge32
         MAX-ACCESS  read-only
         STATUS  current
         DESCRIPTION
            "The counter associated with the number of error-free Rx Bytes
             encountered by an interface in the current day."
         ::= { adGenTA8xx10100Eth24HrCurrentEntry 16 }

      adGenTA8xx10100Eth24HrCurrentRxGoodFrames OBJECT-TYPE
         SYNTAX Gauge32
         MAX-ACCESS  read-only
         STATUS  current
         DESCRIPTION
            "The counter associated with the number of error-free Rx Frames
             encountered by an interface in the current day."
         ::= { adGenTA8xx10100Eth24HrCurrentEntry 17 }

      adGenTA8xx10100Eth24HrCurrentRxJabbers OBJECT-TYPE
         SYNTAX Gauge32
         MAX-ACCESS  read-only
         STATUS  current
         DESCRIPTION
            "The counter associated with the number of Rx Jabbers
             encountered by an interface in the current day."
         ::= { adGenTA8xx10100Eth24HrCurrentEntry 18 }

      adGenTA8xx10100Eth24HrCurrentRxFragments OBJECT-TYPE
         SYNTAX Gauge32
         MAX-ACCESS  read-only
         STATUS  current
         DESCRIPTION
            "The counter associated with the number of Rx Fragments
             encountered by an interface in the current day."
         ::= { adGenTA8xx10100Eth24HrCurrentEntry 19 }

--==================================================================================================================

   adGenTA8xx10100Eth24HrIntervalTable OBJECT-TYPE
      SYNTAX  SEQUENCE OF AdGenTA8xx10100Eth24HrIntervalEntry
      MAX-ACCESS  not-accessible
      STATUS  current
      DESCRIPTION
         "The 10/100 Ethernet 24Hr interval table."
      ::= { adGenTA8xx10100EthPerformance 5 }

   adGenTA8xx10100Eth24HrIntervalEntry OBJECT-TYPE
      SYNTAX  AdGenTA8xx10100Eth24HrIntervalEntry
      MAX-ACCESS  not-accessible
      STATUS  current
      DESCRIPTION
         "An entry in the 10/100 Ethernet 24Hr interval table."
      INDEX   { ifIndex, adGenTA8xx10100Eth24HrIntervalNumber }
      ::= { adGenTA8xx10100Eth24HrIntervalTable 1 }

   AdGenTA8xx10100Eth24HrIntervalEntry  ::=
      SEQUENCE {
         adGenTA8xx10100Eth24HrIntervalNumber
            Integer32,
         adGenTA8xx10100Eth24HrIntervalTxBytes
	    Gauge32,
         adGenTA8xx10100Eth24HrIntervalTxFrames
	    Gauge32,
         adGenTA8xx10100Eth24HrIntervalRxBytes
	    Gauge32,
         adGenTA8xx10100Eth24HrIntervalRxFrames
            Gauge32,
         adGenTA8xx10100Eth24HrIntervalRxCRCAlignErrs
            Gauge32,
         adGenTA8xx10100Eth24HrIntervalRxUndersizeFrames
            Gauge32,
         adGenTA8xx10100Eth24HrIntervalRxOversizeFrames
	    Gauge32,
         adGenTA8xx10100Eth24HrIntervalRxCollisions
	    Gauge32,
         adGenTA8xx10100Eth24HrIntervalRxDiscardedFrames
            Gauge32,
         adGenTA8xx10100Eth24HrIntervalRxMulticastFrames
            Gauge32,
         adGenTA8xx10100Eth24HrIntervalRxBroadcastFrames
            Gauge32,
         adGenTA8xx10100Eth24HrIntervalRxUnicastFrames
            Gauge32,
         adGenTA8xx10100Eth24HrIntervalTxMulticastFrames
            Gauge32,
         adGenTA8xx10100Eth24HrIntervalTxBroadcastFrames
            Gauge32,
         adGenTA8xx10100Eth24HrIntervalTxUnicastFrames
            Gauge32,
         adGenTA8xx10100Eth24HrIntervalRxGoodBytes
	    Gauge32,
         adGenTA8xx10100Eth24HrIntervalRxGoodFrames
            Gauge32,
         adGenTA8xx10100Eth24HrIntervalRxJabbers
            Gauge32,
         adGenTA8xx10100Eth24HrIntervalRxFragments
            Gauge32
       }

      adGenTA8xx10100Eth24HrIntervalNumber OBJECT-TYPE
         SYNTAX  Integer32
         MAX-ACCESS  read-only
         STATUS  current
         DESCRIPTION
            "A number between 1 and 7, where 1 is the most recently
             completed day and 7 is the least recently completed
             day (assuming that all 7 days are valid)."
         ::= { adGenTA8xx10100Eth24HrIntervalEntry 1 }

      adGenTA8xx10100Eth24HrIntervalTxBytes OBJECT-TYPE
         SYNTAX Gauge32
         MAX-ACCESS  read-only
         STATUS  current
         DESCRIPTION
            "The counter associated with the number of Tx Bytes
	     encountered by an interface in the selected day."
         ::= { adGenTA8xx10100Eth24HrIntervalEntry 2 }

      adGenTA8xx10100Eth24HrIntervalTxFrames OBJECT-TYPE
         SYNTAX Gauge32
         MAX-ACCESS  read-only
         STATUS  current
         DESCRIPTION
            "The counter associated with the number of Tx Frames
             encountered by an interface in the selected day."
         ::= { adGenTA8xx10100Eth24HrIntervalEntry 3 }

      adGenTA8xx10100Eth24HrIntervalRxBytes OBJECT-TYPE
         SYNTAX Gauge32
         MAX-ACCESS  read-only
         STATUS  current
         DESCRIPTION
            "The counter associated with the number of Rx Bytes
             encountered by an interface in the selected day."
         ::= { adGenTA8xx10100Eth24HrIntervalEntry 4 }

      adGenTA8xx10100Eth24HrIntervalRxFrames OBJECT-TYPE
         SYNTAX Gauge32
         MAX-ACCESS  read-only
         STATUS  current
         DESCRIPTION
            "The counter associated with the number of Rx Frames
             encountered by an interface in the selected day."
         ::= { adGenTA8xx10100Eth24HrIntervalEntry 5 }

      adGenTA8xx10100Eth24HrIntervalRxCRCAlignErrs OBJECT-TYPE
         SYNTAX Gauge32
         MAX-ACCESS  read-only
         STATUS  current
         DESCRIPTION
            "The counter associated with the number of Rx Alignment & FCS Errors
             encountered by an interface in the selected day."
         ::= { adGenTA8xx10100Eth24HrIntervalEntry 6 }

      adGenTA8xx10100Eth24HrIntervalRxUndersizeFrames OBJECT-TYPE
         SYNTAX Gauge32
         MAX-ACCESS  read-only
         STATUS  current
         DESCRIPTION
            "The counter associated with the number of Rx Undersized Frames
             encountered by an interface in the selected day."
         ::= { adGenTA8xx10100Eth24HrIntervalEntry 7 }

      adGenTA8xx10100Eth24HrIntervalRxOversizeFrames OBJECT-TYPE
         SYNTAX Gauge32
         MAX-ACCESS  read-only
         STATUS  current
         DESCRIPTION
            "The counter associated with the number of Rx Oversized Frames
             encountered by an interface in the selected day."
         ::= { adGenTA8xx10100Eth24HrIntervalEntry 8 }

      adGenTA8xx10100Eth24HrIntervalRxCollisions OBJECT-TYPE
         SYNTAX Gauge32
         MAX-ACCESS  read-only
         STATUS  current
         DESCRIPTION
            "The counter associated with the number of Rx Collisions
             encountered by an interface in the selected day."
         ::= { adGenTA8xx10100Eth24HrIntervalEntry 9 }

      adGenTA8xx10100Eth24HrIntervalRxDiscardedFrames OBJECT-TYPE
         SYNTAX Gauge32
         MAX-ACCESS  read-only
         STATUS  current
         DESCRIPTION
            "The counter associated with the number of Rx Discarded Frames
             encountered by an interface in the selected interval."
         ::= { adGenTA8xx10100Eth24HrIntervalEntry 10 }

      adGenTA8xx10100Eth24HrIntervalRxMulticastFrames OBJECT-TYPE
         SYNTAX Gauge32
         MAX-ACCESS  read-only
         STATUS  current
         DESCRIPTION
            "The counter associated with the number of Rx Multicast Frames
             encountered by an interface in the selected interval."
         ::= { adGenTA8xx10100Eth24HrIntervalEntry 11 }

      adGenTA8xx10100Eth24HrIntervalRxBroadcastFrames OBJECT-TYPE
         SYNTAX Gauge32
         MAX-ACCESS  read-only
         STATUS  current
         DESCRIPTION
            "The counter associated with the number of Rx Broadcast Frames
             encountered by an interface in the selected interval."
         ::= { adGenTA8xx10100Eth24HrIntervalEntry 12 }

      adGenTA8xx10100Eth24HrIntervalRxUnicastFrames OBJECT-TYPE
         SYNTAX Gauge32
         MAX-ACCESS  read-only
         STATUS  current
         DESCRIPTION
            "The counter associated with the number of Rx Unicast Frames
             encountered by an interface in the selected interval."
         ::= { adGenTA8xx10100Eth24HrIntervalEntry 13 }

      adGenTA8xx10100Eth24HrIntervalTxMulticastFrames OBJECT-TYPE
         SYNTAX Gauge32
         MAX-ACCESS  read-only
         STATUS  current
         DESCRIPTION
            "The counter associated with the number of Tx Multicast Frames
             encountered by an interface in the selected interval."
         ::= { adGenTA8xx10100Eth24HrIntervalEntry 14 }

      adGenTA8xx10100Eth24HrIntervalTxBroadcastFrames OBJECT-TYPE
         SYNTAX Gauge32
         MAX-ACCESS  read-only
         STATUS  current
         DESCRIPTION
            "The counter associated with the number of Tx Broadcast Frames
             encountered by an interface in the selected interval."
         ::= { adGenTA8xx10100Eth24HrIntervalEntry 15 }

      adGenTA8xx10100Eth24HrIntervalTxUnicastFrames OBJECT-TYPE
         SYNTAX Gauge32
         MAX-ACCESS  read-only
         STATUS  current
         DESCRIPTION
            "The counter associated with the number of Tx Unicast Frames
             encountered by an interface in the selected interval."
         ::= { adGenTA8xx10100Eth24HrIntervalEntry 16 }

      adGenTA8xx10100Eth24HrIntervalRxGoodBytes OBJECT-TYPE
         SYNTAX Gauge32
         MAX-ACCESS  read-only
         STATUS  current
         DESCRIPTION
            "The counter associated with the number of error-free Rx Bytes
             encountered by an interface in the selected day."
         ::= { adGenTA8xx10100Eth24HrIntervalEntry 17 }

      adGenTA8xx10100Eth24HrIntervalRxGoodFrames OBJECT-TYPE
         SYNTAX Gauge32
         MAX-ACCESS  read-only
         STATUS  current
         DESCRIPTION
            "The counter associated with the number of error-free Rx Frames
             encountered by an interface in the selected day."
         ::= { adGenTA8xx10100Eth24HrIntervalEntry 18 }

      adGenTA8xx10100Eth24HrIntervalRxJabbers OBJECT-TYPE
         SYNTAX Gauge32
         MAX-ACCESS  read-only
         STATUS  current
         DESCRIPTION
            "The counter associated with the number of Rx Jabbers
             encountered by an interface in the selected day."
         ::= { adGenTA8xx10100Eth24HrIntervalEntry 19 }

      adGenTA8xx10100Eth24HrIntervalRxFragments OBJECT-TYPE
         SYNTAX Gauge32
         MAX-ACCESS  read-only
         STATUS  current
         DESCRIPTION
            "The counter associated with the number of Rx Fragments
             encountered by an interface in the selected day."
         ::= { adGenTA8xx10100Eth24HrIntervalEntry 20 }

--==================================================================================================================

   adGenTA8xx10100EthPerfResetTable OBJECT-TYPE
      SYNTAX  SEQUENCE OF AdGenTA8xx10100EthPerfResetEntry
      MAX-ACCESS  not-accessible
      STATUS  current
      DESCRIPTION
         "The 10/100 Ethernet Performance Reset table."
      ::= { adGenTA8xx10100EthPerformance 6 }

   adGenTA8xx10100EthPerfResetEntry OBJECT-TYPE
      SYNTAX  AdGenTA8xx10100EthPerfResetEntry
      MAX-ACCESS  not-accessible
      STATUS  current
      DESCRIPTION
         "An entry in the 10/100 Ethernet 24Hr interval table."
      INDEX   { ifIndex }
      ::= { adGenTA8xx10100EthPerfResetTable 1 }

   AdGenTA8xx10100EthPerfResetEntry  ::=
      SEQUENCE {
         adGenTA8xx10100EthPerfReset
            INTEGER
       }

      adGenTA8xx10100EthPerfReset OBJECT-TYPE
         SYNTAX  INTEGER {
            ethPerfRst(1)
         }
         MAX-ACCESS  read-write
         STATUS  current
         DESCRIPTION
            "Resets all performance history for the selected 10/100 Ethernet Port."
         ::= { adGenTA8xx10100EthPerfResetEntry 1 }


--==================================================================================================================

   adGenTA8xxGigEthPerformance  OBJECT IDENTIFIER ::= { adGenTA8xxPerformance 3 }

   adGenTA8xxGigEthPerformanceScalars	OBJECT IDENTIFIER ::= { adGenTA8xxGigEthPerformance 1}

      adGenTA8xxGigEthRstCurrentIntervals OBJECT-TYPE
         SYNTAX  INTEGER {
            ethRstAllCurrentIntervals(1)
         }
         MAX-ACCESS  read-write
         STATUS  current
         DESCRIPTION
            "Reset current interval PM data on Gigabit Ethernet ports."
          ::= { adGenTA8xxGigEthPerformanceScalars 1 }

      adGenTA8xxGigEthRstAll OBJECT-TYPE
         SYNTAX  INTEGER {
            ethRstAll(1)
         }
         MAX-ACCESS  read-write
         STATUS  current
         DESCRIPTION
            "Reset PM data on ALL Gigabit Ethernet ports."
         ::= { adGenTA8xxGigEthPerformanceScalars 2 }

--==================================================================================================================

   adGenTA8xxGigEth15MinCurrentTable OBJECT-TYPE
      SYNTAX  SEQUENCE OF AdGenTA8xxGigEth15MinCurrentEntry
      MAX-ACCESS  not-accessible
      STATUS  current
      DESCRIPTION
         "The Gigabit Ethernet 15Min current table."
      ::= { adGenTA8xxGigEthPerformance 2 }

   adGenTA8xxGigEth15MinCurrentEntry OBJECT-TYPE
      SYNTAX  AdGenTA8xxGigEth15MinCurrentEntry
      MAX-ACCESS  not-accessible
      STATUS  current
      DESCRIPTION
         "An entry in the Gigabit Ethernet 15Min current table."
      INDEX   { ifIndex }
      ::= { adGenTA8xxGigEth15MinCurrentTable 1 }

   AdGenTA8xxGigEth15MinCurrentEntry  ::=
      SEQUENCE {
         adGenTA8xxGigEth15MinCurrentTxBytes
	    Gauge32,
         adGenTA8xxGigEth15MinCurrentTxFrames
	    Gauge32,
         adGenTA8xxGigEth15MinCurrentRxBytes
	    Gauge32,
         adGenTA8xxGigEth15MinCurrentRxFrames
            Gauge32,
         adGenTA8xxGigEth15MinCurrentRxGoodBytes
            Gauge32,
         adGenTA8xxGigEth15MinCurrentRxGoodFrames
            Gauge32,
         adGenTA8xxGigEth15MinCurrentRxFCSErrors
            Gauge32,
         adGenTA8xxGigEth15MinCurrentRxDroppedFrames
            Gauge32,
         adGenTA8xxGigEth15MinCurrentRxFramesTooBig
            Gauge32,
         adGenTA8xxGigEth15MinCurrentRxFramesTooSmall
            Gauge32,
         adGenTA8xxGigEth15MinCurrentRxMulticastFrames
            Gauge32,
         adGenTA8xxGigEth15MinCurrentRxBroadcastFrames
            Gauge32,
         adGenTA8xxGigEth15MinCurrentRxUnicastFrames
            Gauge32,
         adGenTA8xxGigEth15MinCurrentTxMulticastFrames
            Gauge32,
         adGenTA8xxGigEth15MinCurrentTxBroadcastFrames
            Gauge32,
         adGenTA8xxGigEth15MinCurrentTxUnicastFrames
            Gauge32,
         adGenTA8xxGigEth15MinCurrentRxJabbers
            Gauge32,
         adGenTA8xxGigEth15MinCurrentRxFragments
            Gauge32
       }

      adGenTA8xxGigEth15MinCurrentTxBytes OBJECT-TYPE
         SYNTAX Gauge32
         MAX-ACCESS  read-only
         STATUS  current
         DESCRIPTION
            "The counter associated with the number of Tx Bytes
	     encountered by an interface in the current interval."
         ::= { adGenTA8xxGigEth15MinCurrentEntry 1 }

      adGenTA8xxGigEth15MinCurrentTxFrames OBJECT-TYPE
         SYNTAX Gauge32
         MAX-ACCESS  read-only
         STATUS  current
         DESCRIPTION
            "The counter associated with the number of Tx Frames
             encountered by an interface in the current interval."
         ::= { adGenTA8xxGigEth15MinCurrentEntry 2 }

      adGenTA8xxGigEth15MinCurrentRxBytes OBJECT-TYPE
         SYNTAX Gauge32
         MAX-ACCESS  read-only
         STATUS  current
         DESCRIPTION
            "The counter associated with the number of Rx Bytes
             encountered by an interface in the current interval."
         ::= { adGenTA8xxGigEth15MinCurrentEntry 3 }

      adGenTA8xxGigEth15MinCurrentRxFrames OBJECT-TYPE
         SYNTAX Gauge32
         MAX-ACCESS  read-only
         STATUS  current
         DESCRIPTION
            "The counter associated with the number of Rx Frames
             encountered by an interface in the current interval."
         ::= { adGenTA8xxGigEth15MinCurrentEntry 4 }

      adGenTA8xxGigEth15MinCurrentRxGoodBytes OBJECT-TYPE
         SYNTAX Gauge32
         MAX-ACCESS  read-only
         STATUS  current
         DESCRIPTION
            "The counter associated with the number of Rx Good Bytes
             encountered by an interface in the current interval."
         ::= { adGenTA8xxGigEth15MinCurrentEntry 5 }

      adGenTA8xxGigEth15MinCurrentRxGoodFrames OBJECT-TYPE
         SYNTAX Gauge32
         MAX-ACCESS  read-only
         STATUS  current
         DESCRIPTION
            "The counter associated with the number of Rx Good Frames
             encountered by an interface in the current interval."
         ::= { adGenTA8xxGigEth15MinCurrentEntry 6 }

      adGenTA8xxGigEth15MinCurrentRxFCSErrors OBJECT-TYPE
         SYNTAX Gauge32
         MAX-ACCESS  read-only
         STATUS  current
         DESCRIPTION
            "The counter associated with the number of Rx FCS Errors
             encountered by an interface in the current interval."
         ::= { adGenTA8xxGigEth15MinCurrentEntry 7 }

      adGenTA8xxGigEth15MinCurrentRxDroppedFrames OBJECT-TYPE
         SYNTAX Gauge32
         MAX-ACCESS  read-only
         STATUS  current
         DESCRIPTION
            "The counter associated with the number of Rx Dropped Frames
             encountered by an interface in the current interval."
         ::= { adGenTA8xxGigEth15MinCurrentEntry 8 }

      adGenTA8xxGigEth15MinCurrentRxFramesTooBig OBJECT-TYPE
         SYNTAX Gauge32
         MAX-ACCESS  read-only
         STATUS  current
         DESCRIPTION
            "The counter associated with the number of Rx Frames Too Big
             encountered by an interface in the current interval."
         ::= { adGenTA8xxGigEth15MinCurrentEntry 9 }

      adGenTA8xxGigEth15MinCurrentRxFramesTooSmall OBJECT-TYPE
         SYNTAX Gauge32
         MAX-ACCESS  read-only
         STATUS  current
         DESCRIPTION
            "The counter associated with the number of Rx Frames Too Small
             encountered by an interface in the current interval."
         ::= { adGenTA8xxGigEth15MinCurrentEntry 10 }

      adGenTA8xxGigEth15MinCurrentRxMulticastFrames OBJECT-TYPE
         SYNTAX Gauge32
         MAX-ACCESS  read-only
         STATUS  current
         DESCRIPTION
            "The counter associated with the number of Rx Multicast Frames
             encountered by an interface in the current interval."
         ::= { adGenTA8xxGigEth15MinCurrentEntry 11 }

      adGenTA8xxGigEth15MinCurrentRxBroadcastFrames OBJECT-TYPE
         SYNTAX Gauge32
         MAX-ACCESS  read-only
         STATUS  current
         DESCRIPTION
            "The counter associated with the number of Rx Broadcast Frames
             encountered by an interface in the current interval."
         ::= { adGenTA8xxGigEth15MinCurrentEntry 12 }

      adGenTA8xxGigEth15MinCurrentRxUnicastFrames OBJECT-TYPE
         SYNTAX Gauge32
         MAX-ACCESS  read-only
         STATUS  current
         DESCRIPTION
            "The counter associated with the number of Rx Unicast Frames
             encountered by an interface in the current interval."
         ::= { adGenTA8xxGigEth15MinCurrentEntry 13 }

      adGenTA8xxGigEth15MinCurrentTxMulticastFrames OBJECT-TYPE
         SYNTAX Gauge32
         MAX-ACCESS  read-only
         STATUS  current
         DESCRIPTION
            "The counter associated with the number of Tx Multicast Frames
             encountered by an interface in the current interval."
         ::= { adGenTA8xxGigEth15MinCurrentEntry 14 }

      adGenTA8xxGigEth15MinCurrentTxBroadcastFrames OBJECT-TYPE
         SYNTAX Gauge32
         MAX-ACCESS  read-only
         STATUS  current
         DESCRIPTION
            "The counter associated with the number of Tx Broadcast Frames
             encountered by an interface in the current interval."
         ::= { adGenTA8xxGigEth15MinCurrentEntry 15 }

      adGenTA8xxGigEth15MinCurrentTxUnicastFrames OBJECT-TYPE
         SYNTAX Gauge32
         MAX-ACCESS  read-only
         STATUS  current
         DESCRIPTION
            "The counter associated with the number of Tx Unicast Frames
             encountered by an interface in the current interval."
         ::= { adGenTA8xxGigEth15MinCurrentEntry 16 }

      adGenTA8xxGigEth15MinCurrentRxJabbers OBJECT-TYPE
         SYNTAX Gauge32
         MAX-ACCESS  read-only
         STATUS  current
         DESCRIPTION
            "The counter associated with the number of Rx Jabbers
             encountered by an interface in the current interval."
         ::= { adGenTA8xxGigEth15MinCurrentEntry 17 }

      adGenTA8xxGigEth15MinCurrentRxFragments OBJECT-TYPE
         SYNTAX Gauge32
         MAX-ACCESS  read-only
         STATUS  current
         DESCRIPTION
            "The counter associated with the number of Rx Fragments
             encountered by an interface in the current interval."
         ::= { adGenTA8xxGigEth15MinCurrentEntry 18 }

--==================================================================================================================

   adGenTA8xxGigEth15MinIntervalTable OBJECT-TYPE
      SYNTAX  SEQUENCE OF AdGenTA8xxGigEth15MinIntervalEntry
      MAX-ACCESS  not-accessible
      STATUS  current
      DESCRIPTION
         "The Ethernet 15Min current table."
      ::= { adGenTA8xxGigEthPerformance 3 }

   adGenTA8xxGigEth15MinIntervalEntry OBJECT-TYPE
      SYNTAX  AdGenTA8xxGigEth15MinIntervalEntry
      MAX-ACCESS  not-accessible
      STATUS  current
      DESCRIPTION
         "An entry in the Ethernet 15Min current table."
      INDEX   { ifIndex }
      ::= { adGenTA8xxGigEth15MinIntervalTable 1 }

   AdGenTA8xxGigEth15MinIntervalEntry  ::=
      SEQUENCE {
         adGenTA8xxGigEth15MinIntervalNumber
            Integer32,
         adGenTA8xxGigEth15MinIntervalTxBytes
	    Gauge32,
         adGenTA8xxGigEth15MinIntervalTxFrames
	    Gauge32,
         adGenTA8xxGigEth15MinIntervalRxBytes
	    Gauge32,
         adGenTA8xxGigEth15MinIntervalRxFrames
            Gauge32,
         adGenTA8xxGigEth15MinIntervalRxGoodBytes
            Gauge32,
         adGenTA8xxGigEth15MinIntervalRxGoodFrames
            Gauge32,
         adGenTA8xxGigEth15MinIntervalRxFCSErrors
            Gauge32,
         adGenTA8xxGigEth15MinIntervalRxDroppedFrames
            Gauge32,
         adGenTA8xxGigEth15MinIntervalRxFramesTooBig
            Gauge32,
         adGenTA8xxGigEth15MinIntervalRxFramesTooSmall
            Gauge32,
         adGenTA8xxGigEth15MinIntervalRxMulticastFrames
            Gauge32,
         adGenTA8xxGigEth15MinIntervalRxBroadcastFrames
            Gauge32,
         adGenTA8xxGigEth15MinIntervalRxUnicastFrames
            Gauge32,
         adGenTA8xxGigEth15MinIntervalTxMulticastFrames
            Gauge32,
         adGenTA8xxGigEth15MinIntervalTxBroadcastFrames
            Gauge32,
         adGenTA8xxGigEth15MinIntervalTxUnicastFrames
            Gauge32,
         adGenTA8xxGigEth15MinIntervalRxJabbers
            Gauge32,
         adGenTA8xxGigEth15MinIntervalRxFragments
            Gauge32
       }

      adGenTA8xxGigEth15MinIntervalNumber OBJECT-TYPE
         SYNTAX  Integer32
         MAX-ACCESS  read-only
         STATUS  current
         DESCRIPTION
            "A number between 1 and 96, where 1 is the most
             recently completed 15 minute interval and 96 is
             the least recently completed 15 minutes interval
             (assuming that all 96 intervals are valid)."
         ::= { adGenTA8xxGigEth15MinIntervalEntry 1 }

      adGenTA8xxGigEth15MinIntervalTxBytes OBJECT-TYPE
         SYNTAX Gauge32
         MAX-ACCESS  read-only
         STATUS  current
         DESCRIPTION
            "The counter associated with the number of Tx Bytes
	     encountered by an interface in the selected interval."
         ::= { adGenTA8xxGigEth15MinIntervalEntry 2 }

      adGenTA8xxGigEth15MinIntervalTxFrames OBJECT-TYPE
         SYNTAX Gauge32
         MAX-ACCESS  read-only
         STATUS  current
         DESCRIPTION
            "The counter associated with the number of Tx Frames
             encountered by an interface in the selected interval."
         ::= { adGenTA8xxGigEth15MinIntervalEntry 3 }

      adGenTA8xxGigEth15MinIntervalRxBytes OBJECT-TYPE
         SYNTAX Gauge32
         MAX-ACCESS  read-only
         STATUS  current
         DESCRIPTION
            "The counter associated with the number of Rx Bytes
             encountered by an interface in the selected interval."
         ::= { adGenTA8xxGigEth15MinIntervalEntry 4 }

      adGenTA8xxGigEth15MinIntervalRxFrames OBJECT-TYPE
         SYNTAX Gauge32
         MAX-ACCESS  read-only
         STATUS  current
         DESCRIPTION
            "The counter associated with the number of Rx Frames
             encountered by an interface in the selected interval."
         ::= { adGenTA8xxGigEth15MinIntervalEntry 5 }

      adGenTA8xxGigEth15MinIntervalRxGoodBytes OBJECT-TYPE
         SYNTAX Gauge32
         MAX-ACCESS  read-only
         STATUS  current
         DESCRIPTION
            "The counter associated with the number of Rx Good Bytes
             encountered by an interface in the selected interval."
         ::= { adGenTA8xxGigEth15MinIntervalEntry 6 }

      adGenTA8xxGigEth15MinIntervalRxGoodFrames OBJECT-TYPE
         SYNTAX Gauge32
         MAX-ACCESS  read-only
         STATUS  current
         DESCRIPTION
            "The counter associated with the number of Rx Good Frames
             encountered by an interface in the selected interval."
         ::= { adGenTA8xxGigEth15MinIntervalEntry 7 }

      adGenTA8xxGigEth15MinIntervalRxFCSErrors OBJECT-TYPE
         SYNTAX Gauge32
         MAX-ACCESS  read-only
         STATUS  current
         DESCRIPTION
            "The counter associated with the number of Rx FCS Errors
             encountered by an interface in the selected interval."
         ::= { adGenTA8xxGigEth15MinIntervalEntry 8 }

      adGenTA8xxGigEth15MinIntervalRxDroppedFrames OBJECT-TYPE
         SYNTAX Gauge32
         MAX-ACCESS  read-only
         STATUS  current
         DESCRIPTION
            "The counter associated with the number of Rx Dropped Frames
             encountered by an interface in the selected interval."
         ::= { adGenTA8xxGigEth15MinIntervalEntry 9 }

      adGenTA8xxGigEth15MinIntervalRxFramesTooBig OBJECT-TYPE
         SYNTAX Gauge32
         MAX-ACCESS  read-only
         STATUS  current
         DESCRIPTION
            "The counter associated with the number of Rx Frames Too Big
             encountered by an interface in the selected interval."
         ::= { adGenTA8xxGigEth15MinIntervalEntry 10 }

      adGenTA8xxGigEth15MinIntervalRxFramesTooSmall OBJECT-TYPE
         SYNTAX Gauge32
         MAX-ACCESS  read-only
         STATUS  current
         DESCRIPTION
            "The counter associated with the number of Rx Frames Too Small
             encountered by an interface in the selected interval."
         ::= { adGenTA8xxGigEth15MinIntervalEntry 11 }

      adGenTA8xxGigEth15MinIntervalRxMulticastFrames OBJECT-TYPE
         SYNTAX Gauge32
         MAX-ACCESS  read-only
         STATUS  current
         DESCRIPTION
            "The counter associated with the number of Rx Multicast Frames
             encountered by an interface in the selected interval."
         ::= { adGenTA8xxGigEth15MinIntervalEntry 12 }

      adGenTA8xxGigEth15MinIntervalRxBroadcastFrames OBJECT-TYPE
         SYNTAX Gauge32
         MAX-ACCESS  read-only
         STATUS  current
         DESCRIPTION
            "The counter associated with the number of Rx Broadcast Frames
             encountered by an interface in the selected interval."
         ::= { adGenTA8xxGigEth15MinIntervalEntry 13 }

      adGenTA8xxGigEth15MinIntervalRxUnicastFrames OBJECT-TYPE
         SYNTAX Gauge32
         MAX-ACCESS  read-only
         STATUS  current
         DESCRIPTION
            "The counter associated with the number of Rx Unicast Frames
             encountered by an interface in the selected interval."
         ::= { adGenTA8xxGigEth15MinIntervalEntry 14 }

      adGenTA8xxGigEth15MinIntervalTxMulticastFrames OBJECT-TYPE
         SYNTAX Gauge32
         MAX-ACCESS  read-only
         STATUS  current
         DESCRIPTION
            "The counter associated with the number of Tx Multicast Frames
             encountered by an interface in the selected interval."
         ::= { adGenTA8xxGigEth15MinIntervalEntry 15 }

      adGenTA8xxGigEth15MinIntervalTxBroadcastFrames OBJECT-TYPE
         SYNTAX Gauge32
         MAX-ACCESS  read-only
         STATUS  current
         DESCRIPTION
            "The counter associated with the number of Tx Broadcast Frames
             encountered by an interface in the selected interval."
         ::= { adGenTA8xxGigEth15MinIntervalEntry 16 }

      adGenTA8xxGigEth15MinIntervalTxUnicastFrames OBJECT-TYPE
         SYNTAX Gauge32
         MAX-ACCESS  read-only
         STATUS  current
         DESCRIPTION
            "The counter associated with the number of Tx Unicast Frames
             encountered by an interface in the selected interval."
         ::= { adGenTA8xxGigEth15MinIntervalEntry 17 }

      adGenTA8xxGigEth15MinIntervalRxJabbers OBJECT-TYPE
         SYNTAX Gauge32
         MAX-ACCESS  read-only
         STATUS  current
         DESCRIPTION
            "The counter associated with the number of Rx Jabbers
             encountered by an interface in the selected interval."
         ::= { adGenTA8xxGigEth15MinIntervalEntry 18 }

      adGenTA8xxGigEth15MinIntervalRxFragments OBJECT-TYPE
         SYNTAX Gauge32
         MAX-ACCESS  read-only
         STATUS  current
         DESCRIPTION
            "The counter associated with the number of Rx Fragments
             encountered by an interface in the selected interval."
         ::= { adGenTA8xxGigEth15MinIntervalEntry 19 }

--==================================================================================================================

   adGenTA8xxGigEth24HrCurrentTable OBJECT-TYPE
      SYNTAX  SEQUENCE OF AdGenTA8xxGigEth24HrCurrentEntry
      MAX-ACCESS  not-accessible
      STATUS  current
      DESCRIPTION
         "The Gigabit Ethernet 24Hr current table."
      ::= { adGenTA8xxGigEthPerformance 4 }

   adGenTA8xxGigEth24HrCurrentEntry OBJECT-TYPE
      SYNTAX  AdGenTA8xxGigEth24HrCurrentEntry
      MAX-ACCESS  not-accessible
      STATUS  current
      DESCRIPTION
         "An entry in the Gigabit Ethernet 24Hr current table."
      INDEX   { ifIndex }
      ::= { adGenTA8xxGigEth24HrCurrentTable 1 }

   AdGenTA8xxGigEth24HrCurrentEntry  ::=
      SEQUENCE {
         adGenTA8xxGigEth24HrCurrentTxBytes
	    Gauge32,
         adGenTA8xxGigEth24HrCurrentTxFrames
	    Gauge32,
         adGenTA8xxGigEth24HrCurrentRxBytes
	    Gauge32,
         adGenTA8xxGigEth24HrCurrentRxFrames
            Gauge32,
         adGenTA8xxGigEth24HrCurrentRxGoodBytes
            Gauge32,
         adGenTA8xxGigEth24HrCurrentRxGoodFrames
            Gauge32,
         adGenTA8xxGigEth24HrCurrentRxFCSErrors
            Gauge32,
         adGenTA8xxGigEth24HrCurrentRxDroppedFrames
            Gauge32,
         adGenTA8xxGigEth24HrCurrentRxFramesTooBig
            Gauge32,
         adGenTA8xxGigEth24HrCurrentRxFramesTooSmall
            Gauge32,
         adGenTA8xxGigEth24HrCurrentRxMulticastFrames
            Gauge32,
         adGenTA8xxGigEth24HrCurrentRxBroadcastFrames
            Gauge32,
         adGenTA8xxGigEth24HrCurrentRxUnicastFrames
            Gauge32,
         adGenTA8xxGigEth24HrCurrentTxMulticastFrames
            Gauge32,
         adGenTA8xxGigEth24HrCurrentTxBroadcastFrames
            Gauge32,
         adGenTA8xxGigEth24HrCurrentTxUnicastFrames
            Gauge32,
         adGenTA8xxGigEth24HrCurrentRxJabbers
            Gauge32,
         adGenTA8xxGigEth24HrCurrentRxFragments
            Gauge32
       }

      adGenTA8xxGigEth24HrCurrentTxBytes OBJECT-TYPE
         SYNTAX Gauge32
         MAX-ACCESS  read-only
         STATUS  current
         DESCRIPTION
            "The counter associated with the number of Tx Bytes
	     encountered by an interface in the current day."
         ::= { adGenTA8xxGigEth24HrCurrentEntry 1 }

      adGenTA8xxGigEth24HrCurrentTxFrames OBJECT-TYPE
         SYNTAX Gauge32
         MAX-ACCESS  read-only
         STATUS  current
         DESCRIPTION
            "The counter associated with the number of Tx Frames
             encountered by an interface in the current day."
         ::= { adGenTA8xxGigEth24HrCurrentEntry 2 }

      adGenTA8xxGigEth24HrCurrentRxBytes OBJECT-TYPE
         SYNTAX Gauge32
         MAX-ACCESS  read-only
         STATUS  current
         DESCRIPTION
            "The counter associated with the number of Rx Bytes
             encountered by an interface in the current day."
         ::= { adGenTA8xxGigEth24HrCurrentEntry 3 }

      adGenTA8xxGigEth24HrCurrentRxFrames OBJECT-TYPE
         SYNTAX Gauge32
         MAX-ACCESS  read-only
         STATUS  current
         DESCRIPTION
            "The counter associated with the number of Rx Frames
             encountered by an interface in the current day."
         ::= { adGenTA8xxGigEth24HrCurrentEntry 4 }

      adGenTA8xxGigEth24HrCurrentRxGoodBytes OBJECT-TYPE
         SYNTAX Gauge32
         MAX-ACCESS  read-only
         STATUS  current
         DESCRIPTION
            "The counter associated with the number of Rx Good Bytes
             encountered by an interface in the current day."
         ::= { adGenTA8xxGigEth24HrCurrentEntry 5 }

      adGenTA8xxGigEth24HrCurrentRxGoodFrames OBJECT-TYPE
         SYNTAX Gauge32
         MAX-ACCESS  read-only
         STATUS  current
         DESCRIPTION
            "The counter associated with the number of Rx Good Frames
             encountered by an interface in the current day."
         ::= { adGenTA8xxGigEth24HrCurrentEntry 6 }

      adGenTA8xxGigEth24HrCurrentRxFCSErrors OBJECT-TYPE
         SYNTAX Gauge32
         MAX-ACCESS  read-only
         STATUS  current
         DESCRIPTION
            "The counter associated with the number of Rx FCS Errors
             encountered by an interface in the current day."
         ::= { adGenTA8xxGigEth24HrCurrentEntry 7 }

      adGenTA8xxGigEth24HrCurrentRxDroppedFrames OBJECT-TYPE
         SYNTAX Gauge32
         MAX-ACCESS  read-only
         STATUS  current
         DESCRIPTION
            "The counter associated with the number of Rx Dropped Frames
             encountered by an interface in the current day."
         ::= { adGenTA8xxGigEth24HrCurrentEntry 8 }

      adGenTA8xxGigEth24HrCurrentRxFramesTooBig OBJECT-TYPE
         SYNTAX Gauge32
         MAX-ACCESS  read-only
         STATUS  current
         DESCRIPTION
            "The counter associated with the number of Rx Frames Too Big
             encountered by an interface in the current day."
         ::= { adGenTA8xxGigEth24HrCurrentEntry 9 }

      adGenTA8xxGigEth24HrCurrentRxFramesTooSmall OBJECT-TYPE
         SYNTAX Gauge32
         MAX-ACCESS  read-only
         STATUS  current
         DESCRIPTION
            "The counter associated with the number of Rx Frames Too Small
             encountered by an interface in the current day."
         ::= { adGenTA8xxGigEth24HrCurrentEntry 10 }

      adGenTA8xxGigEth24HrCurrentRxMulticastFrames OBJECT-TYPE
         SYNTAX Gauge32
         MAX-ACCESS  read-only
         STATUS  current
         DESCRIPTION
            "The counter associated with the number of Rx Multicast Frames
             encountered by an interface in the current day."
         ::= { adGenTA8xxGigEth24HrCurrentEntry 11 }

      adGenTA8xxGigEth24HrCurrentRxBroadcastFrames OBJECT-TYPE
         SYNTAX Gauge32
         MAX-ACCESS  read-only
         STATUS  current
         DESCRIPTION
            "The counter associated with the number of Rx Broadcast Frames
             encountered by an interface in the current day."
         ::= { adGenTA8xxGigEth24HrCurrentEntry 12 }

      adGenTA8xxGigEth24HrCurrentRxUnicastFrames OBJECT-TYPE
         SYNTAX Gauge32
         MAX-ACCESS  read-only
         STATUS  current
         DESCRIPTION
            "The counter associated with the number of Rx Unicast Frames
             encountered by an interface in the current day."
         ::= { adGenTA8xxGigEth24HrCurrentEntry 13 }

      adGenTA8xxGigEth24HrCurrentTxMulticastFrames OBJECT-TYPE
         SYNTAX Gauge32
         MAX-ACCESS  read-only
         STATUS  current
         DESCRIPTION
            "The counter associated with the number of Tx Multicast Frames
             encountered by an interface in the current day."
         ::= { adGenTA8xxGigEth24HrCurrentEntry 14 }

      adGenTA8xxGigEth24HrCurrentTxBroadcastFrames OBJECT-TYPE
         SYNTAX Gauge32
         MAX-ACCESS  read-only
         STATUS  current
         DESCRIPTION
            "The counter associated with the number of Tx Broadcast Frames
             encountered by an interface in the current day."
         ::= { adGenTA8xxGigEth24HrCurrentEntry 15 }

      adGenTA8xxGigEth24HrCurrentTxUnicastFrames OBJECT-TYPE
         SYNTAX Gauge32
         MAX-ACCESS  read-only
         STATUS  current
         DESCRIPTION
            "The counter associated with the number of Tx Unicast Frames
             encountered by an interface in the current day."
         ::= { adGenTA8xxGigEth24HrCurrentEntry 16 }

      adGenTA8xxGigEth24HrCurrentRxJabbers OBJECT-TYPE
         SYNTAX Gauge32
         MAX-ACCESS  read-only
         STATUS  current
         DESCRIPTION
            "The counter associated with the number of Rx Jabbers
             encountered by an interface in the current day."
         ::= { adGenTA8xxGigEth24HrCurrentEntry 17 }

      adGenTA8xxGigEth24HrCurrentRxFragments OBJECT-TYPE
         SYNTAX Gauge32
         MAX-ACCESS  read-only
         STATUS  current
         DESCRIPTION
            "The counter associated with the number of Rx Fragments
             encountered by an interface in the current day."
         ::= { adGenTA8xxGigEth24HrCurrentEntry 18 }

--==================================================================================================================

   adGenTA8xxGigEth24HrIntervalTable OBJECT-TYPE
      SYNTAX  SEQUENCE OF AdGenTA8xxGigEth24HrIntervalEntry
      MAX-ACCESS  not-accessible
      STATUS  current
      DESCRIPTION
         "The Gigabit Ethernet 24Hr interval table."
      ::= { adGenTA8xxGigEthPerformance 5 }

   adGenTA8xxGigEth24HrIntervalEntry OBJECT-TYPE
      SYNTAX  AdGenTA8xxGigEth24HrIntervalEntry
      MAX-ACCESS  not-accessible
      STATUS  current
      DESCRIPTION
         "An entry in the Gigabit Ethernet 24Hr interval table."
      INDEX   { ifIndex }
      ::= { adGenTA8xxGigEth24HrIntervalTable 1 }

   AdGenTA8xxGigEth24HrIntervalEntry  ::=
      SEQUENCE {
         adGenTA8xxGigEth24HrIntervalNumber
            Integer32,
         adGenTA8xxGigEth24HrIntervalTxBytes
	    Gauge32,
         adGenTA8xxGigEth24HrIntervalTxFrames
	    Gauge32,
         adGenTA8xxGigEth24HrIntervalRxBytes
	    Gauge32,
         adGenTA8xxGigEth24HrIntervalRxFrames
            Gauge32,
         adGenTA8xxGigEth24HrIntervalRxGoodBytes
            Gauge32,
         adGenTA8xxGigEth24HrIntervalRxGoodFrames
            Gauge32,
         adGenTA8xxGigEth24HrIntervalRxFCSErrors
            Gauge32,
         adGenTA8xxGigEth24HrIntervalRxDroppedFrames
            Gauge32,
         adGenTA8xxGigEth24HrIntervalRxFramesTooBig
            Gauge32,
         adGenTA8xxGigEth24HrIntervalRxFramesTooSmall
            Gauge32,
         adGenTA8xxGigEth24HrIntervalRxMulticastFrames
            Gauge32,
         adGenTA8xxGigEth24HrIntervalRxBroadcastFrames
            Gauge32,
         adGenTA8xxGigEth24HrIntervalRxUnicastFrames
            Gauge32,
         adGenTA8xxGigEth24HrIntervalTxMulticastFrames
            Gauge32,
         adGenTA8xxGigEth24HrIntervalTxBroadcastFrames
            Gauge32,
         adGenTA8xxGigEth24HrIntervalTxUnicastFrames
            Gauge32,
         adGenTA8xxGigEth24HrIntervalRxJabbers
            Gauge32,
         adGenTA8xxGigEth24HrIntervalRxFragments
            Gauge32
       }

      adGenTA8xxGigEth24HrIntervalNumber OBJECT-TYPE
         SYNTAX  Integer32
         MAX-ACCESS  read-only
         STATUS  current
         DESCRIPTION
            "A number between 1 and 7, where 1 is the most recently
             completed day and 7 is the least recently completed
             day (assuming that all 7 days are valid)."
         ::= { adGenTA8xxGigEth24HrIntervalEntry 1 }

      adGenTA8xxGigEth24HrIntervalTxBytes OBJECT-TYPE
         SYNTAX Gauge32
         MAX-ACCESS  read-only
         STATUS  current
         DESCRIPTION
            "The counter associated with the number of Tx Bytes
	     encountered by an interface in the selected day."
         ::= { adGenTA8xxGigEth24HrIntervalEntry 2 }

      adGenTA8xxGigEth24HrIntervalTxFrames OBJECT-TYPE
         SYNTAX Gauge32
         MAX-ACCESS  read-only
         STATUS  current
         DESCRIPTION
            "The counter associated with the number of Tx Frames
             encountered by an interface in the selected day."
         ::= { adGenTA8xxGigEth24HrIntervalEntry 3 }

      adGenTA8xxGigEth24HrIntervalRxBytes OBJECT-TYPE
         SYNTAX Gauge32
         MAX-ACCESS  read-only
         STATUS  current
         DESCRIPTION
            "The counter associated with the number of Rx Bytes
             encountered by an interface in the selected day."
         ::= { adGenTA8xxGigEth24HrIntervalEntry 4 }

      adGenTA8xxGigEth24HrIntervalRxFrames OBJECT-TYPE
         SYNTAX Gauge32
         MAX-ACCESS  read-only
         STATUS  current
         DESCRIPTION
            "The counter associated with the number of Rx Frames
             encountered by an interface in the selected day."
         ::= { adGenTA8xxGigEth24HrIntervalEntry 5 }

      adGenTA8xxGigEth24HrIntervalRxGoodBytes OBJECT-TYPE
         SYNTAX Gauge32
         MAX-ACCESS  read-only
         STATUS  current
         DESCRIPTION
            "The counter associated with the number of Rx Good Bytes
             encountered by an interface in the selected day."
         ::= { adGenTA8xxGigEth24HrIntervalEntry 6 }

      adGenTA8xxGigEth24HrIntervalRxGoodFrames OBJECT-TYPE
         SYNTAX Gauge32
         MAX-ACCESS  read-only
         STATUS  current
         DESCRIPTION
            "The counter associated with the number of Rx Good Frames
             encountered by an interface in the selected day."
         ::= { adGenTA8xxGigEth24HrIntervalEntry 7 }

      adGenTA8xxGigEth24HrIntervalRxFCSErrors OBJECT-TYPE
         SYNTAX Gauge32
         MAX-ACCESS  read-only
         STATUS  current
         DESCRIPTION
            "The counter associated with the number of Rx FCS Errors
             encountered by an interface in the selected day."
         ::= { adGenTA8xxGigEth24HrIntervalEntry 8 }

      adGenTA8xxGigEth24HrIntervalRxDroppedFrames OBJECT-TYPE
         SYNTAX Gauge32
         MAX-ACCESS  read-only
         STATUS  current
         DESCRIPTION
            "The counter associated with the number of Rx Dropped Frames
             encountered by an interface in the selected day."
         ::= { adGenTA8xxGigEth24HrIntervalEntry 9 }

      adGenTA8xxGigEth24HrIntervalRxFramesTooBig OBJECT-TYPE
         SYNTAX Gauge32
         MAX-ACCESS  read-only
         STATUS  current
         DESCRIPTION
            "The counter associated with the number of Rx Frames Too Big
             encountered by an interface in the selected day."
         ::= { adGenTA8xxGigEth24HrIntervalEntry 10 }

      adGenTA8xxGigEth24HrIntervalRxFramesTooSmall OBJECT-TYPE
         SYNTAX Gauge32
         MAX-ACCESS  read-only
         STATUS  current
         DESCRIPTION
            "The counter associated with the number of Rx Frames Too Small
             encountered by an interface in the selected day."
         ::= { adGenTA8xxGigEth24HrIntervalEntry 11 }

      adGenTA8xxGigEth24HrIntervalRxMulticastFrames OBJECT-TYPE
         SYNTAX Gauge32
         MAX-ACCESS  read-only
         STATUS  current
         DESCRIPTION
            "The counter associated with the number of Rx Multicast Frames
             encountered by an interface in the selected day."
         ::= { adGenTA8xxGigEth24HrIntervalEntry 12 }

      adGenTA8xxGigEth24HrIntervalRxBroadcastFrames OBJECT-TYPE
         SYNTAX Gauge32
         MAX-ACCESS  read-only
         STATUS  current
         DESCRIPTION
            "The counter associated with the number of Rx Broadcast Frames
             encountered by an interface in the selected day."
         ::= { adGenTA8xxGigEth24HrIntervalEntry 13 }

      adGenTA8xxGigEth24HrIntervalRxUnicastFrames OBJECT-TYPE
         SYNTAX Gauge32
         MAX-ACCESS  read-only
         STATUS  current
         DESCRIPTION
            "The counter associated with the number of Rx Unicast Frames
             encountered by an interface in the selected day."
         ::= { adGenTA8xxGigEth24HrIntervalEntry 14 }

      adGenTA8xxGigEth24HrIntervalTxMulticastFrames OBJECT-TYPE
         SYNTAX Gauge32
         MAX-ACCESS  read-only
         STATUS  current
         DESCRIPTION
            "The counter associated with the number of Tx Multicast Frames
             encountered by an interface in the selected day."
         ::= { adGenTA8xxGigEth24HrIntervalEntry 15 }

      adGenTA8xxGigEth24HrIntervalTxBroadcastFrames OBJECT-TYPE
         SYNTAX Gauge32
         MAX-ACCESS  read-only
         STATUS  current
         DESCRIPTION
            "The counter associated with the number of Tx Broadcast Frames
             encountered by an interface in the selected day."
         ::= { adGenTA8xxGigEth24HrIntervalEntry 16 }

      adGenTA8xxGigEth24HrIntervalTxUnicastFrames OBJECT-TYPE
         SYNTAX Gauge32
         MAX-ACCESS  read-only
         STATUS  current
         DESCRIPTION
            "The counter associated with the number of Tx Unicast Frames
             encountered by an interface in the selected day."
         ::= { adGenTA8xxGigEth24HrIntervalEntry 17 }

      adGenTA8xxGigEth24HrIntervalRxJabbers OBJECT-TYPE
         SYNTAX Gauge32
         MAX-ACCESS  read-only
         STATUS  current
         DESCRIPTION
            "The counter associated with the number of Rx Jabbers
             encountered by an interface in the selected day."
         ::= { adGenTA8xxGigEth24HrIntervalEntry 18 }

      adGenTA8xxGigEth24HrIntervalRxFragments OBJECT-TYPE
         SYNTAX Gauge32
         MAX-ACCESS  read-only
         STATUS  current
         DESCRIPTION
            "The counter associated with the number of Rx Fragments
             encountered by an interface in the selected day."
         ::= { adGenTA8xxGigEth24HrIntervalEntry 19 }

--==================================================================================================================

   adGenTA8xxGigEthPerfResetTable OBJECT-TYPE
      SYNTAX  SEQUENCE OF AdGenTA8xxGigEthPerfResetEntry
      MAX-ACCESS  not-accessible
      STATUS  current
      DESCRIPTION
         "The Gigabit Ethernet Performance Reset table."
      ::= { adGenTA8xxGigEthPerformance 6 }

   adGenTA8xxGigEthPerfResetEntry OBJECT-TYPE
      SYNTAX  AdGenTA8xxGigEthPerfResetEntry
      MAX-ACCESS  not-accessible
      STATUS  current
      DESCRIPTION
         "An entry in the Gigabit Ethernet 24Hr interval table."
      INDEX   { ifIndex }
      ::= { adGenTA8xxGigEthPerfResetTable 1 }

   AdGenTA8xxGigEthPerfResetEntry  ::=
      SEQUENCE {
         adGenTA8xxGigEthPerfReset
            INTEGER
       }

      adGenTA8xxGigEthPerfReset OBJECT-TYPE
         SYNTAX  INTEGER {
            ethPerfRst(1)
         }
         MAX-ACCESS  read-write
         STATUS  current
         DESCRIPTION
            "Resets all performance history for the selected Gigabit Ethernet Port."
         ::= { adGenTA8xxGigEthPerfResetEntry 1 }


--==================================================================================================================
   adGenTA8xx10100EthPerfThresholds  OBJECT IDENTIFIER ::= { adGenTA8xxPerformance 4 }

   adGenTA8xx10100Eth15MinThreshTable OBJECT-TYPE
      SYNTAX  SEQUENCE OF AdGenTA8xx10100Eth15MinThreshEntry
      MAX-ACCESS  not-accessible
      STATUS  current
      DESCRIPTION
         "The 10/100 Ethernet 15 minute threshold table."
      ::= { adGenTA8xx10100EthPerfThresholds 1 }

   adGenTA8xx10100Eth15MinThreshEntry OBJECT-TYPE
      SYNTAX  AdGenTA8xx10100Eth15MinThreshEntry
      MAX-ACCESS  not-accessible
      STATUS  current
      DESCRIPTION
         "An entry in the 10/100 Ethernet 15 minute threshold table."
      INDEX   { ifIndex }
      ::= { adGenTA8xx10100Eth15MinThreshTable 1 }

   AdGenTA8xx10100Eth15MinThreshEntry  ::=
      SEQUENCE {
         adGenTA8xx10100Eth15MinThreshRxCRCAlignErrs
            Gauge32,
         adGenTA8xx10100Eth15MinThreshRxUndersizeFrames
            Gauge32,
         adGenTA8xx10100Eth15MinThreshRxOversizeFrames
	    Gauge32,
         adGenTA8xx10100Eth15MinThreshRxCollisions
            Gauge32,
         adGenTA8xx10100Eth15MinThreshRxDiscardedFrames
            Gauge32,
         adGenTA8xx10100Eth15MinThreshRxMulticastFrames
            Gauge32,
         adGenTA8xx10100Eth15MinThreshRxBroadcastFrames
            Gauge32,
         adGenTA8xx10100Eth15MinThreshRxJabbers
            Gauge32,
         adGenTA8xx10100Eth15MinThreshRxFragments
            Gauge32
       }

      adGenTA8xx10100Eth15MinThreshRxCRCAlignErrs OBJECT-TYPE
         SYNTAX Gauge32
         MAX-ACCESS  read-write
         STATUS  current
         DESCRIPTION
            "The 15 minute threshold associated with the number of Rx Alignment & FCS Errors
             encountered by an interface in the current interval."
         ::= { adGenTA8xx10100Eth15MinThreshEntry 1 }

      adGenTA8xx10100Eth15MinThreshRxUndersizeFrames OBJECT-TYPE
         SYNTAX Gauge32
         MAX-ACCESS  read-write
         STATUS  current
         DESCRIPTION
            "The 15 minute threshold associated with the number of Rx Undersized Frames
             encountered by an interface in the current interval."
         ::= { adGenTA8xx10100Eth15MinThreshEntry 2 }

      adGenTA8xx10100Eth15MinThreshRxOversizeFrames OBJECT-TYPE
         SYNTAX Gauge32
         MAX-ACCESS  read-write
         STATUS  current
         DESCRIPTION
            "The 15 minute threshold associated with the number of Rx Oversized Frames
             encountered by an interface in the current interval."
         ::= { adGenTA8xx10100Eth15MinThreshEntry 3 }

      adGenTA8xx10100Eth15MinThreshRxCollisions OBJECT-TYPE
         SYNTAX Gauge32
         MAX-ACCESS  read-write
         STATUS  current
         DESCRIPTION
            "The 15 minute threshold associated with the number of Rx Collisions
             encountered by an interface in the current interval."
         ::= { adGenTA8xx10100Eth15MinThreshEntry 4 }

      adGenTA8xx10100Eth15MinThreshRxDiscardedFrames OBJECT-TYPE
         SYNTAX Gauge32
         MAX-ACCESS  read-write
         STATUS  current
         DESCRIPTION
            "The 15 minute threshold associated with the number of Rx Discarded Frames
             encountered by an interface in the current interval."
         ::= { adGenTA8xx10100Eth15MinThreshEntry 5 }

      adGenTA8xx10100Eth15MinThreshRxMulticastFrames OBJECT-TYPE
         SYNTAX Gauge32
         MAX-ACCESS  read-write
         STATUS  current
         DESCRIPTION
            "The 15 minute threshold associated with the number of Rx Multicast Frames
             encountered by an interface in the current interval."
         ::= { adGenTA8xx10100Eth15MinThreshEntry 6 }

      adGenTA8xx10100Eth15MinThreshRxBroadcastFrames OBJECT-TYPE
         SYNTAX Gauge32
         MAX-ACCESS  read-write
         STATUS  current
         DESCRIPTION
            "The 15 minute threshold associated with the number of Rx Broadcast Frames
             encountered by an interface in the current interval."
         ::= { adGenTA8xx10100Eth15MinThreshEntry 7 }

      adGenTA8xx10100Eth15MinThreshRxJabbers OBJECT-TYPE
         SYNTAX Gauge32
         MAX-ACCESS  read-write
         STATUS  current
         DESCRIPTION
            "The 15 minute threshold associated with the number of Rx Jabbers
             encountered by an interface in the current interval."
         ::= { adGenTA8xx10100Eth15MinThreshEntry 8 }

      adGenTA8xx10100Eth15MinThreshRxFragments OBJECT-TYPE
         SYNTAX Gauge32
         MAX-ACCESS  read-write
         STATUS  current
         DESCRIPTION
            "The 15 minute threshold associated with the number of Rx Fragments
             encountered by an interface in the current interval."
         ::= { adGenTA8xx10100Eth15MinThreshEntry 9 }

--===================================================================
   adGenTA8xx10100Eth24HrThreshTable OBJECT-TYPE
      SYNTAX  SEQUENCE OF AdGenTA8xx10100Eth24HrThreshEntry
      MAX-ACCESS  not-accessible
      STATUS  current
      DESCRIPTION
         "The 10/100 Ethernet 24 hour threshold table."
      ::= { adGenTA8xx10100EthPerfThresholds 2 }

   adGenTA8xx10100Eth24HrThreshEntry OBJECT-TYPE
      SYNTAX  AdGenTA8xx10100Eth24HrThreshEntry
      MAX-ACCESS  not-accessible
      STATUS  current
      DESCRIPTION
         "An entry in the 10/100 Ethernet 24 hour threshold table."
      INDEX   { ifIndex }
      ::= { adGenTA8xx10100Eth24HrThreshTable 1 }

   AdGenTA8xx10100Eth24HrThreshEntry  ::=
      SEQUENCE {
         adGenTA8xx10100Eth24HrThreshRxCRCAlignErrs
            Gauge32,
         adGenTA8xx10100Eth24HrThreshRxUndersizeFrames
            Gauge32,
         adGenTA8xx10100Eth24HrThreshRxOversizeFrames
	    Gauge32,
         adGenTA8xx10100Eth24HrThreshRxCollisions
            Gauge32,
         adGenTA8xx10100Eth24HrThreshRxDiscardedFrames
            Gauge32,
         adGenTA8xx10100Eth24HrThreshRxMulticastFrames
            Gauge32,
         adGenTA8xx10100Eth24HrThreshRxBroadcastFrames
            Gauge32,
         adGenTA8xx10100Eth24HrThreshRxJabbers
            Gauge32,
         adGenTA8xx10100Eth24HrThreshRxFragments
            Gauge32
       }

      adGenTA8xx10100Eth24HrThreshRxCRCAlignErrs OBJECT-TYPE
         SYNTAX Gauge32
         MAX-ACCESS  read-write
         STATUS  current
         DESCRIPTION
            "The 24 hour threshold associated with the number of Rx Alignment & FCS Errors
             encountered by an interface in the current interval."
         ::= { adGenTA8xx10100Eth24HrThreshEntry 1 }

      adGenTA8xx10100Eth24HrThreshRxUndersizeFrames OBJECT-TYPE
         SYNTAX Gauge32
         MAX-ACCESS  read-write
         STATUS  current
         DESCRIPTION
            "The 24 hour threshold associated with the number of Rx Undersized Frames
             encountered by an interface in the current interval."
         ::= { adGenTA8xx10100Eth24HrThreshEntry 2 }

      adGenTA8xx10100Eth24HrThreshRxOversizeFrames OBJECT-TYPE
         SYNTAX Gauge32
         MAX-ACCESS  read-write
         STATUS  current
         DESCRIPTION
            "The 24 hour threshold associated with the number of Rx Oversized Frames
             encountered by an interface in the current interval."
         ::= { adGenTA8xx10100Eth24HrThreshEntry 3 }

      adGenTA8xx10100Eth24HrThreshRxCollisions OBJECT-TYPE
         SYNTAX Gauge32
         MAX-ACCESS  read-write
         STATUS  current
         DESCRIPTION
            "The 24 hour threshold associated with the number of Rx Collisions
             encountered by an interface in the current interval."
         ::= { adGenTA8xx10100Eth24HrThreshEntry 4 }

      adGenTA8xx10100Eth24HrThreshRxDiscardedFrames OBJECT-TYPE
         SYNTAX Gauge32
         MAX-ACCESS  read-write
         STATUS  current
         DESCRIPTION
            "The 24 hour threshold associated with the number of Rx Discarded Frames
             encountered by an interface in the current interval."
         ::= { adGenTA8xx10100Eth24HrThreshEntry 5 }

      adGenTA8xx10100Eth24HrThreshRxMulticastFrames OBJECT-TYPE
         SYNTAX Gauge32
         MAX-ACCESS  read-write
         STATUS  current
         DESCRIPTION
            "The 24 hour threshold associated with the number of Rx Multicast Frames
             encountered by an interface in the current interval."
         ::= { adGenTA8xx10100Eth24HrThreshEntry 6 }

      adGenTA8xx10100Eth24HrThreshRxBroadcastFrames OBJECT-TYPE
         SYNTAX Gauge32
         MAX-ACCESS  read-write
         STATUS  current
         DESCRIPTION
            "The 24 hour threshold associated with the number of Rx Broadcast Frames
             encountered by an interface in the current interval."
         ::= { adGenTA8xx10100Eth24HrThreshEntry 7 }

      adGenTA8xx10100Eth24HrThreshRxJabbers OBJECT-TYPE
         SYNTAX Gauge32
         MAX-ACCESS  read-write
         STATUS  current
         DESCRIPTION
            "The 24 hour threshold associated with the number of Rx Jabbers
             encountered by an interface in the current interval."
         ::= { adGenTA8xx10100Eth24HrThreshEntry 8 }

      adGenTA8xx10100Eth24HrThreshRxFragments OBJECT-TYPE
         SYNTAX Gauge32
         MAX-ACCESS  read-write
         STATUS  current
         DESCRIPTION
            "The 24 hour threshold associated with the number of Rx Fragments
             encountered by an interface in the current interval."
         ::= { adGenTA8xx10100Eth24HrThreshEntry 9 }

--==================================================================================================================

   adGenTA8xxGigEthPerfThresholds  OBJECT IDENTIFIER ::= { adGenTA8xxPerformance 5 }

   adGenTA8xxGigEth15MinThreshTable OBJECT-TYPE
      SYNTAX  SEQUENCE OF AdGenTA8xxGigEth15MinThreshEntry
      MAX-ACCESS  not-accessible
      STATUS  current
      DESCRIPTION
         "The Gigabit Ethernet 15 minute threshold table."
      ::= { adGenTA8xxGigEthPerfThresholds 1 }

   adGenTA8xxGigEth15MinThreshEntry OBJECT-TYPE
      SYNTAX  AdGenTA8xxGigEth15MinThreshEntry
      MAX-ACCESS  not-accessible
      STATUS  current
      DESCRIPTION
         "An entry in the Gigabit Ethernet 15 minute threshold table."
      INDEX   { ifIndex }
      ::= { adGenTA8xxGigEth15MinThreshTable 1 }

   AdGenTA8xxGigEth15MinThreshEntry  ::=
      SEQUENCE {
         adGenTA8xxGigEth15MinThreshRxFCSErrors
            Gauge32,
         adGenTA8xxGigEth15MinThreshRxDroppedFrames
            Gauge32,
         adGenTA8xxGigEth15MinThreshRxFramesTooBig
            Gauge32,
         adGenTA8xxGigEth15MinThreshRxFramesTooSmall
            Gauge32,
         adGenTA8xxGigEth15MinThreshRxMulticastFrames
            Gauge32,
         adGenTA8xxGigEth15MinThreshRxBroadcastFrames
            Gauge32,
         adGenTA8xxGigEth15MinThreshRxJabbers
            Gauge32,
         adGenTA8xxGigEth15MinThreshRxFragments
            Gauge32
       }

      adGenTA8xxGigEth15MinThreshRxFCSErrors OBJECT-TYPE
         SYNTAX Gauge32
         MAX-ACCESS  read-write
         STATUS  current
         DESCRIPTION
            "The 15 minute threshold associated with the number of Rx FCS Errors
             encountered by an interface in the current interval."
         ::= { adGenTA8xxGigEth15MinThreshEntry 1 }

      adGenTA8xxGigEth15MinThreshRxDroppedFrames OBJECT-TYPE
         SYNTAX Gauge32
         MAX-ACCESS  read-write
         STATUS  current
         DESCRIPTION
            "The 15 minute threshold associated with the number of Rx Dropped Frames
             encountered by an interface in the current interval."
         ::= { adGenTA8xxGigEth15MinThreshEntry 2 }

      adGenTA8xxGigEth15MinThreshRxFramesTooBig OBJECT-TYPE
         SYNTAX Gauge32
         MAX-ACCESS  read-write
         STATUS  current
         DESCRIPTION
            "The 15 minute threshold associated with the number of Rx Frames Too Big
             encountered by an interface in the current interval."
         ::= { adGenTA8xxGigEth15MinThreshEntry 3 }

      adGenTA8xxGigEth15MinThreshRxFramesTooSmall OBJECT-TYPE
         SYNTAX Gauge32
         MAX-ACCESS  read-write
         STATUS  current
         DESCRIPTION
            "The 15 minute threshold associated with the number of Rx Frames Too Small
             encountered by an interface in the current interval."
         ::= { adGenTA8xxGigEth15MinThreshEntry 4 }

      adGenTA8xxGigEth15MinThreshRxMulticastFrames OBJECT-TYPE
         SYNTAX Gauge32
         MAX-ACCESS  read-write
         STATUS  current
         DESCRIPTION
            "The 15 minute threshold associated with the number of Rx Multicast Frames
             encountered by an interface in the current interval."
         ::= { adGenTA8xxGigEth15MinThreshEntry 5 }

      adGenTA8xxGigEth15MinThreshRxBroadcastFrames OBJECT-TYPE
         SYNTAX Gauge32
         MAX-ACCESS  read-write
         STATUS  current
         DESCRIPTION
            "The 15 minute threshold associated with the number of Rx Broadcast Frames
             encountered by an interface in the current interval."
         ::= { adGenTA8xxGigEth15MinThreshEntry 6 }

      adGenTA8xxGigEth15MinThreshRxJabbers OBJECT-TYPE
         SYNTAX Gauge32
         MAX-ACCESS  read-write
         STATUS  current
         DESCRIPTION
            "The 15 minute threshold associated with the number of Rx Jabbers
             encountered by an interface in the current interval."
         ::= { adGenTA8xxGigEth15MinThreshEntry 7 }

      adGenTA8xxGigEth15MinThreshRxFragments OBJECT-TYPE
         SYNTAX Gauge32
         MAX-ACCESS  read-write
         STATUS  current
         DESCRIPTION
            "The 15 minute threshold associated with the number of Rx Fragments
             encountered by an interface in the current interval."
         ::= { adGenTA8xxGigEth15MinThreshEntry 8 }

--===================================================================

   adGenTA8xxGigEth24HrThreshTable OBJECT-TYPE
      SYNTAX  SEQUENCE OF AdGenTA8xxGigEth24HrThreshEntry
      MAX-ACCESS  not-accessible
      STATUS  current
      DESCRIPTION
         "The Gigabit Ethernet 24 hour threshold table."
      ::= { adGenTA8xxGigEthPerfThresholds 2 }

   adGenTA8xxGigEth24HrThreshEntry OBJECT-TYPE
      SYNTAX  AdGenTA8xxGigEth24HrThreshEntry
      MAX-ACCESS  not-accessible
      STATUS  current
      DESCRIPTION
         "An entry in the Gigabit Ethernet 24 hour threshold table."
      INDEX   { ifIndex }
      ::= { adGenTA8xxGigEth24HrThreshTable 1 }

   AdGenTA8xxGigEth24HrThreshEntry  ::=
      SEQUENCE {
         adGenTA8xxGigEth24HrThreshRxFCSErrors
            Gauge32,
         adGenTA8xxGigEth24HrThreshRxDroppedFrames
            Gauge32,
         adGenTA8xxGigEth24HrThreshRxFramesTooBig
            Gauge32,
         adGenTA8xxGigEth24HrThreshRxFramesTooSmall
            Gauge32,
         adGenTA8xxGigEth24HrThreshRxMulticastFrames
            Gauge32,
         adGenTA8xxGigEth24HrThreshRxBroadcastFrames
            Gauge32,
         adGenTA8xxGigEth24HrThreshRxJabbers
            Gauge32,
         adGenTA8xxGigEth24HrThreshRxFragments
            Gauge32
       }

      adGenTA8xxGigEth24HrThreshRxFCSErrors OBJECT-TYPE
         SYNTAX Gauge32
         MAX-ACCESS  read-write
         STATUS  current
         DESCRIPTION
            "The 24 hour threshold associated with the number of Rx FCS Errors
             encountered by an interface in the current interval."
         ::= { adGenTA8xxGigEth24HrThreshEntry 1 }

      adGenTA8xxGigEth24HrThreshRxDroppedFrames OBJECT-TYPE
         SYNTAX Gauge32
         MAX-ACCESS  read-write
         STATUS  current
         DESCRIPTION
            "The 24 hour threshold associated with the number of Rx Dropped Frames
             encountered by an interface in the current interval."
         ::= { adGenTA8xxGigEth24HrThreshEntry 2 }

      adGenTA8xxGigEth24HrThreshRxFramesTooBig OBJECT-TYPE
         SYNTAX Gauge32
         MAX-ACCESS  read-write
         STATUS  current
         DESCRIPTION
            "The 24 hour threshold associated with the number of Rx Frames Too Big
             encountered by an interface in the current interval."
         ::= { adGenTA8xxGigEth24HrThreshEntry 3 }

      adGenTA8xxGigEth24HrThreshRxFramesTooSmall OBJECT-TYPE
         SYNTAX Gauge32
         MAX-ACCESS  read-write
         STATUS  current
         DESCRIPTION
            "The 24 hour threshold associated with the number of Rx Frames Too Small
             encountered by an interface in the current interval."
         ::= { adGenTA8xxGigEth24HrThreshEntry 4 }

      adGenTA8xxGigEth24HrThreshRxMulticastFrames OBJECT-TYPE
         SYNTAX Gauge32
         MAX-ACCESS  read-write
         STATUS  current
         DESCRIPTION
            "The 24 hour threshold associated with the number of Rx Multicast Frames
             encountered by an interface in the current interval."
         ::= { adGenTA8xxGigEth24HrThreshEntry 5 }

      adGenTA8xxGigEth24HrThreshRxBroadcastFrames OBJECT-TYPE
         SYNTAX Gauge32
         MAX-ACCESS  read-write
         STATUS  current
         DESCRIPTION
            "The 24 hour threshold associated with the number of Rx Broadcast Frames
             encountered by an interface in the current interval."
         ::= { adGenTA8xxGigEth24HrThreshEntry 6 }

      adGenTA8xxGigEth24HrThreshRxJabbers OBJECT-TYPE
         SYNTAX Gauge32
         MAX-ACCESS  read-write
         STATUS  current
         DESCRIPTION
            "The 24 hour threshold associated with the number of Rx Jabbers
             encountered by an interface in the current interval."
         ::= { adGenTA8xxGigEth24HrThreshEntry 7 }

      adGenTA8xxGigEth24HrThreshRxFragments OBJECT-TYPE
         SYNTAX Gauge32
         MAX-ACCESS  read-write
         STATUS  current
         DESCRIPTION
            "The 24 hour threshold associated with the number of Rx Fragments
             encountered by an interface in the current interval."
         ::= { adGenTA8xxGigEth24HrThreshEntry 8 }

--===================================================================

   adGenTA8xxTstScalars  OBJECT IDENTIFIER ::= { adGenTA8xxTest 1 }

      adGenTA8xxResetTests OBJECT-TYPE
         SYNTAX  INTEGER {
            resetTests(1)
         }
         MAX-ACCESS  read-write
         STATUS  current
         DESCRIPTION
            "A Set operation with value of 1 will reset all loopbacks currently in effect."
         ::= { adGenTA8xxTstScalars 1 }

      adGenTA8xxTestTimeout OBJECT-TYPE
         SYNTAX  INTEGER {
            disable(1),
            oneMin(2),
            fiveMin(3),
            tenMin(4),
            fifteenMin(5),
            thirtyMin(6),
            fortyfiveMin(7),
            sixtyMin(8)
         }
         MAX-ACCESS  read-write
         STATUS  current
         DESCRIPTION
            "Indicates the amount of time that a test will remain in
             effect before self-release occurs."
            ::= { adGenTA8xxTstScalars 2 }

      adGenTA8xxRelayTest OBJECT-TYPE
         SYNTAX  INTEGER {
            disable (1),
            enable (2)
         }
         MAX-ACCESS  read-write
         STATUS  current
         DESCRIPTION
            "Enable or Disable the testing of the alarm relays.  When disabled the
             Alarm Relays are activated/deactivated based on system alarms.  When
             enabled the Alarm relays can be controlled with
             adGenTA8xxToggleCriticalRelay, adGenTA8xxToggleMajorRelay, and
             adGenTA8xxToggleMinorRelay."
         ::= { adGenTA8xxTstScalars 3 }

      adGenTA8xxTestCriticalRelay OBJECT-TYPE
         SYNTAX  INTEGER {
            inactive (1),
            active (2)
         }
         MAX-ACCESS  read-write
         STATUS  current
         DESCRIPTION
            "Set the Critical Alarm Relay if adGenTA8xxRelayTest is enabled.
             A read returns last value set."
         ::= { adGenTA8xxTstScalars 4  }

      adGenTA8xxTestMajorRelay OBJECT-TYPE
         SYNTAX  INTEGER {
            inactive (1),
            active (2)
         }
         MAX-ACCESS  read-write
         STATUS  current
         DESCRIPTION
            "Set the Major Alarm Relay if adGenTA8xxRelayTest is enabled.
             A read returns last value set."
         ::= { adGenTA8xxTstScalars 5  }

      adGenTA8xxTestMinorRelay OBJECT-TYPE
         SYNTAX  INTEGER {
            inactive (1),
            active (2)
         }
         MAX-ACCESS  read-write
         STATUS  current
         DESCRIPTION
            "Set the Minor Alarm Relay if adGenTA8xxRelayTest is enabled.
             A read returns last value set."
         ::= { adGenTA8xxTstScalars 6  }

--==================================================================================================================

   adGenTA8xxTstBertPrvTable OBJECT-TYPE
      SYNTAX  SEQUENCE OF AdGenTA8xxTstBertPrvEntry
      MAX-ACCESS  not-accessible
      STATUS  current
      DESCRIPTION
         "The Bit Error Rate Test (BERT) Provisioning table."
      ::= { adGenTA8xxTest 2 }

   adGenTA8xxTstBertPrvEntry OBJECT-TYPE
      SYNTAX  AdGenTA8xxTstBertPrvEntry
      MAX-ACCESS  not-accessible
      STATUS  current
      DESCRIPTION
         "An entry in the Bit Error Rate Test (BERT) Provisioning table."
      INDEX  { ifIndex }
      ::= { adGenTA8xxTstBertPrvTable 1 }

   AdGenTA8xxTstBertPrvEntry ::=
      SEQUENCE {
         adGenTA8xxTstBertStartAndStop
            INTEGER,
         adGenTA8xxTstBertResetStatistics
            INTEGER,
         adGenTA8xxTstBertPattern
            INTEGER,
         adGenTA8xxTstBertPatternPolarity
            INTEGER,
         adGenTA8xxTstBertErrorInject
            INTEGER
      }

      adGenTA8xxTstBertStartAndStop OBJECT-TYPE
         SYNTAX  INTEGER {
            stopBert(1),
            startBert(2)
         }
         MAX-ACCESS  read-write
         STATUS  current
         DESCRIPTION
            "Starts or Stops the BERT on the selected port."
         ::= { adGenTA8xxTstBertPrvEntry 1 }

      adGenTA8xxTstBertResetStatistics   OBJECT-TYPE
         SYNTAX  INTEGER {
            restart(1)
         }
         MAX-ACCESS  read-write
         STATUS  current
         DESCRIPTION
            "A Set resets the BERT statistics on the selected port.  A get always returns a 1."
         ::= { adGenTA8xxTstBertPrvEntry 2 }

       adGenTA8xxTstBertPattern OBJECT-TYPE
         SYNTAX  INTEGER {
            bertTwoToFifteenMinusOne(1),
            bertTwoToTwentyMinusOne(2),
            bertAllOnes(3),
            bertAllZeroes(4),
            bertTwoToTwentyThreeMinusOne(5)
         }
         MAX-ACCESS  read-write
         STATUS  current
         DESCRIPTION
            "Selects the BERT pattern for the selected port."
         ::= { adGenTA8xxTstBertPrvEntry 3 }

       adGenTA8xxTstBertPatternPolarity OBJECT-TYPE
         SYNTAX  INTEGER {
            normal(1),
            inverted(2)
         }
         MAX-ACCESS  read-write
         STATUS  current
         DESCRIPTION
            "Sets the BERT pattern polarity on the selected port."
         ::= { adGenTA8xxTstBertPrvEntry 4 }

      adGenTA8xxTstBertErrorInject   OBJECT-TYPE
         SYNTAX  INTEGER {
            inject(1)
         }
         MAX-ACCESS  read-write
         STATUS  current
         DESCRIPTION
            "A Set injects a single bit error into the current Bit Error Rate Test on the selected port.  A get always returns a 1."
         ::= { adGenTA8xxTstBertPrvEntry 5 }

--==================================================================================================================

   adGenTA8xxTstBertStatTable OBJECT-TYPE
      SYNTAX  SEQUENCE OF AdGenTA8xxTstBertStatEntry
      MAX-ACCESS  not-accessible
      STATUS  current
      DESCRIPTION
         "The Bit Error Rate Test (BERT) Provisioning table."
      ::= { adGenTA8xxTest 3 }

   adGenTA8xxTstBertStatEntry OBJECT-TYPE
      SYNTAX  AdGenTA8xxTstBertStatEntry
      MAX-ACCESS  not-accessible
      STATUS  current
      DESCRIPTION
         "An entry in the Bit Error Rate Test (BERT) Provisioning table."
      INDEX  { ifIndex }
      ::= { adGenTA8xxTstBertStatTable 1 }

   AdGenTA8xxTstBertStatEntry ::=
      SEQUENCE {
         adGenTA8xxTstBertStatus
            INTEGER,
         adGenTA8xxTstBertBER
            DisplayString,
         adGenTA8xxTstBertErrorCount
	    Gauge32,
         adGenTA8xxTstBertPattSyncLossCount
	    Gauge32,
         adGenTA8xxTstBertErroredSeconds
	    Gauge32,
         adGenTA8xxTstBertElapsedTime
            DisplayString
      }

      adGenTA8xxTstBertStatus OBJECT-TYPE
         SYNTAX  INTEGER {
            disabled(1),
            enabledPatternSync(2),
            enabledNoPatternSync(3)
         }
         MAX-ACCESS  read-only
         STATUS  current
         DESCRIPTION
            "Status of the BERT on the selected port."
         ::= { adGenTA8xxTstBertStatEntry 1 }

      adGenTA8xxTstBertBER   OBJECT-TYPE
         SYNTAX  DisplayString
         MAX-ACCESS  read-only
         STATUS  current
         DESCRIPTION
            "Returns the Bit Error Rate results of the BERT on the selected port."
         ::= { adGenTA8xxTstBertStatEntry 2 }

       adGenTA8xxTstBertErrorCount OBJECT-TYPE
	 SYNTAX  Gauge32
         MAX-ACCESS  read-only
         STATUS  current
         DESCRIPTION
            "The counter associated with the number of BERT bit errors on the selected port."
         ::= { adGenTA8xxTstBertStatEntry 3 }

       adGenTA8xxTstBertPattSyncLossCount OBJECT-TYPE
	 SYNTAX  Gauge32
         MAX-ACCESS  read-only
         STATUS  current
         DESCRIPTION
            "The counter associated with the number of pattern sync losses on the selected port."
         ::= { adGenTA8xxTstBertStatEntry 4 }

       adGenTA8xxTstBertErroredSeconds OBJECT-TYPE
	 SYNTAX  Gauge32
         MAX-ACCESS  read-only
         STATUS  current
         DESCRIPTION
            "The counter associated with the number of BERT errored seconds on the selected port."
         ::= { adGenTA8xxTstBertStatEntry 5 }

      adGenTA8xxTstBertElapsedTime   OBJECT-TYPE
         SYNTAX  DisplayString
         MAX-ACCESS  read-only
         STATUS  current
         DESCRIPTION
            "Returns the elapsed time in DD:HH:MM:SS format of the BERT on the selected port."
         ::= { adGenTA8xxTstBertStatEntry 6 }

--==================================================================================================================

   adGenTA8xxTstLpbkPrvTable OBJECT-TYPE
      SYNTAX  SEQUENCE OF AdGenTA8xxTstLpbkPrvEntry
      MAX-ACCESS  not-accessible
      STATUS  current
      DESCRIPTION
         "The Loopback Provisioning table."
      ::= { adGenTA8xxTest 4 }

   adGenTA8xxTstLpbkPrvEntry OBJECT-TYPE
      SYNTAX  AdGenTA8xxTstLpbkPrvEntry
      MAX-ACCESS  not-accessible
      STATUS  current
      DESCRIPTION
         "An entry in the Loopback Provisioning table."
      INDEX  { ifIndex }
      ::= { adGenTA8xxTstLpbkPrvTable 1 }

   AdGenTA8xxTstLpbkPrvEntry ::=
      SEQUENCE {
         adGenTA8xxTstIncomingLoopbackPatterns
            INTEGER,
	 adGenTA8xxTstRequestRemoteLoopback
            INTEGER,
         adGenTA8xxTstIncomingInbandLoopbackPatterns
            INTEGER,
         adGenTA8xxTstIncomingFDLLoopbackPatterns
            INTEGER
      }

      adGenTA8xxTstIncomingLoopbackPatterns OBJECT-TYPE
         SYNTAX  INTEGER {
            disableInband(1),
            enableInband(2),
	    disableFDL(3),
	    enableFDL(4)
         }
         MAX-ACCESS  read-write
         STATUS  current
         DESCRIPTION
            "Enables/disables detection of specified incoming loopback patterns."
         ::= { adGenTA8xxTstLpbkPrvEntry 1 }

      adGenTA8xxTstRequestRemoteLoopback OBJECT-TYPE
         SYNTAX  INTEGER {
            reqInbandLoopUp(1),
            reqInbandLoopDown(2),
	    reqFDLLoopUp(3),
	    reqFDLLoopDown(4),
	    reqFDLUniversalLoopDown(5),
	    reqSendNoCode(6)
         }
         MAX-ACCESS  read-write
         STATUS  current
         DESCRIPTION
            "Sends specified remote loopback request."
         ::= { adGenTA8xxTstLpbkPrvEntry 2 }

      adGenTA8xxTstIncomingInbandLoopbackPatterns OBJECT-TYPE
         SYNTAX  INTEGER {
            disable(1),
            enable(2)
         }
         MAX-ACCESS  read-write
         STATUS  current
         DESCRIPTION
            "Enables/disables detection of incoming inband loopback patterns."
         ::= { adGenTA8xxTstLpbkPrvEntry 3 }

      adGenTA8xxTstIncomingFDLLoopbackPatterns OBJECT-TYPE
         SYNTAX  INTEGER {
            disable(3),
            enable(4)
         }
         MAX-ACCESS  read-write
         STATUS  current
         DESCRIPTION
            "Enables/disables detection of incoming FDL loopback patterns."
         ::= { adGenTA8xxTstLpbkPrvEntry 4 }

--==================================================================================================================

   adGenTA8xxAlarmScalars  OBJECT IDENTIFIER ::= { adGenTA8xxAlarms 1 }

   adGenTA8xxTrapAlarmLevel OBJECT-TYPE
      SYNTAX INTEGER {
         disabled(1),
         info(2),
         alert(3),
         minor(4),
         major(5),
         critical(6)
      }
      MAX-ACCESS  read-only
      STATUS  current
      DESCRIPTION
         "Alarm Level of a trap.  This value is invalid if read.
          This is used as a varbind in a trap to indicate
          its alarm level."
      ::= { adGenTA8xxAlarmScalars 1 }

   adGenTA8xxACPwrInLevel OBJECT-TYPE
      SYNTAX INTEGER {
         disabled(1),
         info(2),
         alert(3),
         minor(4),
         major(5),
         critical(6),
         aco(7)
      }
      MAX-ACCESS  read-write
      STATUS  current
      DESCRIPTION
         "Alarm level for AC_PWR_IN."
      ::= { adGenTA8xxAlarmScalars 2 }

   adGenTA8xxPwrALevel OBJECT-TYPE
      SYNTAX INTEGER {
         disabled(1),
         info(2),
         alert(3),
         minor(4),
         major(5),
         critical(6)
      }
      MAX-ACCESS  read-write
      STATUS  current
      DESCRIPTION
         "Alarm level for Power Feed A Failure Alarm."
      ::= { adGenTA8xxAlarmScalars 3 }

   adGenTA8xxPwrBLevel OBJECT-TYPE
      SYNTAX INTEGER {
         disabled(1),
         info(2),
         alert(3),
         minor(4),
         major(5),
         critical(6)
      }
      MAX-ACCESS  read-write
      STATUS  current
      DESCRIPTION
         "Alarm level for Power Feed B Failure Alarm."
      ::= { adGenTA8xxAlarmScalars 4 }

   adGenTA8xxAcknowledgeAlarms OBJECT-TYPE
      SYNTAX INTEGER {
         ackControllers(2),
         ackModuleA(3),
         ackModuleB(4),
         ackAll(5)
      }
      MAX-ACCESS  read-write
      STATUS  current
      DESCRIPTION
         "Setting will acknowledge all alarms for the specified card(s).
          ackAll is the equivalent of pressing the ACO button."
      ::= { adGenTA8xxAlarmScalars 5 }

   adGenTA8xxSpecificTrapEnable OBJECT-TYPE
      SYNTAX OCTET STRING
      MAX-ACCESS  read-write
      STATUS   current
      DESCRIPTION
         "Enables/Disables specific traps in the TA8xx.
          1 = Enabled
          0 = Disabled
          Control is defined as follows:

          Bits:
                 0      User Login Success
                 1      User Login Failure
                 2      User Lockout
                 3      DC Power A Fail
                 4      DC Power B Fail
                 5      AC Power Loss
                 6      Ethernet Link Down
                 7      Ethernet Collisions 15 Minute
                 8      Ethernet Collisions 24 Hour
                 9      Ethernet Discarded Frames 15 Minute
                10      Ethernet Discarded Frames 24 Hour
                11      Ethernet Oversized Frames 15 Minute
                12      Ethernet Oversized Frames 24 Hour
                13      Ethernet Undersized Frames 15 Minute
                14      Ethernet Undersized Frames 24 Hour
                15      Ethernet Alignment & FCS Errors 15 Minute
                16      Ethernet Alignment & FCS Errors 24 Hour
                17      Gigabit Ethernet Link Down
                18      Gigabit Ethernet Unapproved SFP
                19      Gigabit Ethernet FCS Errors 15 Minute
                20      Gigabit Ethernet FCS Errors 24 Hour
                21      Gigabit Ethernet Dropped Frames 15 Minute
                22      Gigabit Ethernet Dropped Frames 24 Hour
                23      Gigabit Ethernet Frames Too Big 15 Minute
                24      Gigabit Ethernet Frames Too Big 24 Hour
                25      Gigabit Ethernet Frames Too Small 15 Minute
                26      Gigabit Ethernet Frames Too Small 24 Hour
                27      EFM Group Bad Fragments 15 Minute
                28      EFM Group Bad Fragments 24 Hour
                29      EFM Group Lost Fragments 15 Minute
                30      EFM Group Lost Fragments 24 Hour
                31      EFM Group Lost Starts 15 Minute
                32      EFM Group Lost Stats 24 Hour
                33      EFM Group Lost Ends 15 Minute
                34      EFM Group Lost Ends 24 Hour
                35      EFM Group Down
                36      EFM Group Partial Down
                37      EFM Link Errored Fragments 15 Minute
                38      EFM Link Errored Fragments 24 Hour
                39      EFM Link Small Fragments 15 Minute
                40      EFM Link Small Fragments 24 Hour
                41      EFM Link Large Fragments 15 Minute
                42      EFM Link Large Fragments 24 Hour
                43      EFM Link Discarded Fragments 15 Minute
                44      EFM Link Discarded Fragments 24 Hour
                45      EFM Link FCS Errors 15 Minute
                46      EFM Link FCS Errors 24 Hour
                47      EFM Link Coding Errors 15 Minute
                48      EFM Link Coding Errors 24 Hour
                49      EFM Link Down
                50      SHDSL Loss of Signal
                51      SHDSL Loss of Sync
                52      SHDSL SNR Margin
                53      SHDSL Loop Attenuation
                54      SHDSL ES 15 Minute
                55      SHDSL ES 24 Hour
                56      SHDSL SES 15 Minute
                57      SHDSL SES 24 Hour
                58      SHDSL UAS 15 Minute
                59      SHDSL UAS 24 Hour
                60      SHDSL CVC 15 Minute
                61      SHDSL CVC 24 Hour
                62      SHDSL LOSWS 15 Minute
                63      SHDSL LOSWS 24 Hour
                64      Ethernet Rx Multicast Frames 15 Minute
                65      Ethernet Rx Multicast Frames 24 Hour
                66      Ethernet Rx Broadcast Frames 15 Minute
                67      Ethernet Rx Broadcast Frames 24 Hour
                68      Gigabit Ethernet Rx Multicast Frames 15 Minute
                69      Gigabit Ethernet Rx Multicast Frames 24 Hour
                70      Gigabit Ethernet Rx Broadcast Frames 15 Minute
                71      Gigabit Ethernet Rx Broadcast Frames 24 Hour
                72      DS3 Alarms
                73      DS3 15 Minute Thresholds
                74      DS3 24 Hour Thresholds
                75      DS1 Alarms
                76      DS1 15 Minute Thresholds
                77      DS1 24 Hour Thresholds
		78      DSL Alarms
		79      Fan Module Removed
		80      Single Fan Failure
		81      Multiple Fan Failure

          Bits 0 is the MSB of the first octet in the octet string.

          If a trap is a component in a standard trap
          then the standard trap will take presedence.  To
          generate the specific enterprise trap, the standard
          trap must be disabled (by setting its bit to 0)."
      ::= { adGenTA8xxAlarmScalars 6 }

   adGenTA8xxLoginFailureLevel OBJECT-TYPE
      SYNTAX INTEGER {
         disabled(1),
         info(2),
         alert(3),
         minor(4),
         major(5),
         critical(6)
      }
      MAX-ACCESS  read-write
      STATUS  current
      DESCRIPTION
         "Alarm level for Login Failure Alarm."
      ::= { adGenTA8xxAlarmScalars 7 }

   adGenTA8xxLoginSuccessLevel OBJECT-TYPE
      SYNTAX INTEGER {
         disabled(1),
         info(2),
         alert(3),
         minor(4),
         major(5),
         critical(6)
      }
      MAX-ACCESS  read-write
      STATUS  current
      DESCRIPTION
         "Alarm level for Login Success Alarm."
      ::= { adGenTA8xxAlarmScalars 8 }

-- ******************************************************************************************
-- MIB Groups
-- ******************************************************************************************
adGenTA8xxConfigGroup OBJECT-GROUP
   OBJECTS
   {
        adGenTA8xxBootVersion,
        adGenTA8xxSwChecksum,
        adGenTA8xxBootChecksum,
        adGenTA8xxSavedSwVersion
   }
   STATUS current
   DESCRIPTION
     "These objects provide support for retrieving configuration."
   ::= { adGenTA8xxMibGroups 1 }

adGenTA8xxCardProvGroup OBJECT-GROUP
   OBJECTS
   {
        adGenTA8xxAutoLogoffTime,
        adGenTA8xxSaveProv,
        adGenTA8xxScheduledResetTime,
        adGenTA8xxSecondaryTelnetPort,
        adGenTA8xxRestoreFactoryDefaults,
        adGenTA8xxReset,
        adGenTA8xxBondingPrimaryRef,
        adGenTA8xxBondingSecondaryRef,
        adGenTA8xxIpACLState,
        adGenTA8xxIpACLInsert,
        adGenTA8xxIpACLRemove,
	adGenTA8xxTemperatureThresholdCelsuis,
        adGenTA8xxTemperatureThresholdFahrenheit
   }
   STATUS current
   DESCRIPTION
     "These objects provide support for card level provisioning."
   ::= { adGenTA8xxMibGroups 2 }

adGenTA8xx10100EthProvGroup OBJECT-GROUP
   OBJECTS
   {
        adGenTA8xx10100EthPortState,
        adGenTA8xx10100EthPortRateDuplex,
        adGenTA8xx10100EthPortCrossOverMode,
        adGenTA8xx10100EthPortLsa,
        adGenTA8xx10100EthPortName,
        adGenTA8xx10100EthPortLsaBandwidthMinimum,
        adGenTA8xx10100EthPortLsaLinksMinimum
   }
   STATUS current
   DESCRIPTION
     "These objects provide support for 10/100 Ethernet provisioning."
   ::= { adGenTA8xxMibGroups 3 }

adGenTA8xxGigEthProvGroup OBJECT-GROUP
   OBJECTS
   {
        adGenTA8xxGigEthState,
        adGenTA8xxGigEthLsa,
        adGenTA8xxGigEthName,
        adGenTA8xxGigEthPortSpeed,
        adGenTA8xxGigEthLsaBandwidthMinimum,
        adGenTA8xxGigEthLsaLinksMinimum
   }
   STATUS current
   DESCRIPTION
     "These objects provide support for Gigabit Ethernet provisioning."
   ::= { adGenTA8xxMibGroups 4 }

adGenTA8xxCardStatusGroup OBJECT-GROUP
   OBJECTS
   {
        adGenTA8xxCardStatus,
        adGenTA8xxCritRelay,
        adGenTA8xxMajRelay,
        adGenTA8xxMinRelay,
        adGenTA8xxacoStatus,
        adGenTA8xxACPwrInStatus,
        adGenTA8xxPowerAStatus,
        adGenTA8xxPowerBStatus,
        adGenTA8xxEnvAlarmsAggregateStatus,
        adGenTA8xxIPAddress,
        adGenTA8xxSubnetMask,
        adGenTA8xxDefaultGateway,
        adGenTA8xxBondingFunctLineSource,
        adGenTA8xxBondingPriRefStatus,
        adGenTA8xxBondingSecRefStatus,
        adGenTA8xxIpACLDepth,
        adGenTA8xxCurrentCPUUtilization,
        adGenTA8xxMaxCPUUtilization,
        adGenTA8xxResetMaxCPUUtilization,
	adGenTA8xxTemperatureCelsuis,
        adGenTA8xxTemperatureFahrenheit,
        adGenTA8xxCustomerDoor,
        adGenTA8xxTelcoDoor
   }
   STATUS current
   DESCRIPTION
     "These objects provide support for retrieving card level status."
   ::= { adGenTA8xxMibGroups 5 }

adGenTA8xx10100EthStatusGroup OBJECT-GROUP
   OBJECTS
   {
        adGenTA8xx10100EthLinkStatus,
        adGenTA8xx10100EthLinkSpeedDuplex
   }
   STATUS current
   DESCRIPTION
     "These objects provide support for retrieving 10/100 Ethernet status."
   ::= { adGenTA8xxMibGroups 6 }

adGenTA8xxGigEthStatusGroup OBJECT-GROUP
   OBJECTS
   {
        adGenTA8xxGigEthLinkStatus,
        adGenTA8xxGigEthSFPDescription,
        adGenTA8xxGigEthSFPADTRANSerialNumber,
        adGenTA8xxGigEthSFPADTRANPartNumber,
        adGenTA8xxGigEthSFPADTRANCLEICode,
        adGenTA8xxGigEthSFPJackType,
        adGenTA8xxGigEthSFPADTRANApproved,
        adGenTA8xxGigEthSFPTemperature,
        adGenTA8xxGigEthSFPTxBias,
        adGenTA8xxGigEthSFPTxPower,
        adGenTA8xxGigEthSFPRxPower,
        adGenTA8xxGigEthLinkSpeedDuplex
   }
   STATUS current
   DESCRIPTION
     "These objects provide support for retrieving Gigabit Ethernet status."
   ::= { adGenTA8xxMibGroups 7 }

adGenTA8xxCardPerfGroup OBJECT-GROUP
   OBJECTS
   {
        adGenTA8xxRstAllCurrentIntervals,
        adGenTA8xxRstAllIntervals
   }
   STATUS current
   DESCRIPTION
     "These objects provide support for card level performance."
   ::= { adGenTA8xxMibGroups 8 }

adGenTA8xx10100EthRstPerfGroup OBJECT-GROUP
   OBJECTS
   {

        adGenTA8xx10100EthRstCurrentIntervals,
        adGenTA8xx10100EthRstAll,
        adGenTA8xx10100EthPerfReset
   }
   STATUS current
   DESCRIPTION
     "These objects provide support for 10/100 Ethernet performance reset."
   ::= { adGenTA8xxMibGroups 9 }

adGenTA8xx10100EthCurr15MinPerfGroup OBJECT-GROUP
   OBJECTS
   {
        adGenTA8xx10100Eth15MinCurrentTxBytes,
        adGenTA8xx10100Eth15MinCurrentTxFrames,
        adGenTA8xx10100Eth15MinCurrentRxBytes,
        adGenTA8xx10100Eth15MinCurrentRxFrames,
        adGenTA8xx10100Eth15MinCurrentRxCRCAlignErrs,
        adGenTA8xx10100Eth15MinCurrentRxUndersizeFrames,
        adGenTA8xx10100Eth15MinCurrentRxOversizeFrames,
        adGenTA8xx10100Eth15MinCurrentRxCollisions,
        adGenTA8xx10100Eth15MinCurrentRxDiscardedFrames,
        adGenTA8xx10100Eth15MinCurrentRxMulticastFrames,
        adGenTA8xx10100Eth15MinCurrentRxBroadcastFrames,
        adGenTA8xx10100Eth15MinCurrentRxUnicastFrames,
        adGenTA8xx10100Eth15MinCurrentTxMulticastFrames,
        adGenTA8xx10100Eth15MinCurrentTxBroadcastFrames,
        adGenTA8xx10100Eth15MinCurrentTxUnicastFrames,
        adGenTA8xx10100Eth15MinCurrentRxJabbers,
        adGenTA8xx10100Eth15MinCurrentRxFragments
   }
   STATUS current
   DESCRIPTION
     "These objects provide support for retrieving 10/100 Ethernet
      current 15 minute intervals."
   ::= { adGenTA8xxMibGroups 10 }

adGenTA8xx10100EthInt15MinPerfGroup OBJECT-GROUP
   OBJECTS
   {
        adGenTA8xx10100Eth15MinIntervalNumber,
        adGenTA8xx10100Eth15MinIntervalTxBytes,
        adGenTA8xx10100Eth15MinIntervalTxFrames,
        adGenTA8xx10100Eth15MinIntervalRxBytes,
        adGenTA8xx10100Eth15MinIntervalRxFrames,
        adGenTA8xx10100Eth15MinIntervalRxCRCAlignErrs,
        adGenTA8xx10100Eth15MinIntervalRxUndersizeFrames,
        adGenTA8xx10100Eth15MinIntervalRxOversizeFrames,
        adGenTA8xx10100Eth15MinIntervalRxCollisions,
        adGenTA8xx10100Eth15MinIntervalRxDiscardedFrames,
        adGenTA8xx10100Eth15MinIntervalRxMulticastFrames,
        adGenTA8xx10100Eth15MinIntervalRxBroadcastFrames,
        adGenTA8xx10100Eth15MinIntervalRxUnicastFrames,
        adGenTA8xx10100Eth15MinIntervalTxMulticastFrames,
        adGenTA8xx10100Eth15MinIntervalTxBroadcastFrames,
        adGenTA8xx10100Eth15MinIntervalTxUnicastFrames,
        adGenTA8xx10100Eth15MinIntervalRxJabbers,
        adGenTA8xx10100Eth15MinIntervalRxFragments
   }
   STATUS current
   DESCRIPTION
     "These objects provide support for retrieving 10/100 Ethernet
      selected 15 minute intervals."
   ::= { adGenTA8xxMibGroups 11 }

adGenTA8xx10100EthCurr24HrPerfGroup OBJECT-GROUP
   OBJECTS
   {
        adGenTA8xx10100Eth24HrCurrentTxBytes,
        adGenTA8xx10100Eth24HrCurrentTxFrames,
        adGenTA8xx10100Eth24HrCurrentRxBytes,
        adGenTA8xx10100Eth24HrCurrentRxFrames,
        adGenTA8xx10100Eth24HrCurrentRxCRCAlignErrs,
        adGenTA8xx10100Eth24HrCurrentRxUndersizeFrames,
        adGenTA8xx10100Eth24HrCurrentRxOversizeFrames,
        adGenTA8xx10100Eth24HrCurrentRxCollisions,
        adGenTA8xx10100Eth24HrCurrentRxDiscardedFrames,
        adGenTA8xx10100Eth24HrCurrentRxMulticastFrames,
        adGenTA8xx10100Eth24HrCurrentRxBroadcastFrames,
        adGenTA8xx10100Eth24HrCurrentRxUnicastFrames,
        adGenTA8xx10100Eth24HrCurrentTxMulticastFrames,
        adGenTA8xx10100Eth24HrCurrentTxBroadcastFrames,
        adGenTA8xx10100Eth24HrCurrentTxUnicastFrames,
        adGenTA8xx10100Eth24HrCurrentRxJabbers,
        adGenTA8xx10100Eth24HrCurrentRxFragments
   }
   STATUS current
   DESCRIPTION
     "These objects provide support for retrieving 10/100 Ethernet
      current 24 hour intervals."
   ::= { adGenTA8xxMibGroups 12 }

adGenTA8xx10100EthInt24HrPerfGroup OBJECT-GROUP
   OBJECTS
   {
        adGenTA8xx10100Eth24HrIntervalNumber,
        adGenTA8xx10100Eth24HrIntervalTxBytes,
        adGenTA8xx10100Eth24HrIntervalTxFrames,
        adGenTA8xx10100Eth24HrIntervalRxBytes,
        adGenTA8xx10100Eth24HrIntervalRxFrames,
        adGenTA8xx10100Eth24HrIntervalRxCRCAlignErrs,
        adGenTA8xx10100Eth24HrIntervalRxUndersizeFrames,
        adGenTA8xx10100Eth24HrIntervalRxOversizeFrames,
        adGenTA8xx10100Eth24HrIntervalRxCollisions,
        adGenTA8xx10100Eth24HrIntervalRxDiscardedFrames,
        adGenTA8xx10100Eth24HrIntervalRxMulticastFrames,
        adGenTA8xx10100Eth24HrIntervalRxBroadcastFrames,
        adGenTA8xx10100Eth24HrIntervalRxUnicastFrames,
        adGenTA8xx10100Eth24HrIntervalTxMulticastFrames,
        adGenTA8xx10100Eth24HrIntervalTxBroadcastFrames,
        adGenTA8xx10100Eth24HrIntervalTxUnicastFrames,
        adGenTA8xx10100Eth24HrIntervalRxJabbers,
        adGenTA8xx10100Eth24HrIntervalRxFragments
   }
   STATUS current
   DESCRIPTION
     "These objects provide support for retrieving 10/100 Ethernet
      selected 24 hour intervals."
   ::= { adGenTA8xxMibGroups 13 }

adGenTA8xxGigEthRstPerfGroup OBJECT-GROUP
   OBJECTS
   {
        adGenTA8xxGigEthRstCurrentIntervals,
        adGenTA8xxGigEthRstAll,
        adGenTA8xxGigEthPerfReset
   }
   STATUS current
   DESCRIPTION
     "These objects provide support for Gigabit Ethernet performance reset."
   ::= { adGenTA8xxMibGroups 14 }

adGenTA8xxGigEthCurr15MinPerfGroup OBJECT-GROUP
   OBJECTS
   {
        adGenTA8xxGigEth15MinCurrentTxBytes,
        adGenTA8xxGigEth15MinCurrentTxFrames,
        adGenTA8xxGigEth15MinCurrentRxBytes,
        adGenTA8xxGigEth15MinCurrentRxFrames,
        adGenTA8xxGigEth15MinCurrentRxGoodBytes,
        adGenTA8xxGigEth15MinCurrentRxGoodFrames,
        adGenTA8xxGigEth15MinCurrentRxFCSErrors,
        adGenTA8xxGigEth15MinCurrentRxDroppedFrames,
        adGenTA8xxGigEth15MinCurrentRxFramesTooBig,
        adGenTA8xxGigEth15MinCurrentRxFramesTooSmall,
        adGenTA8xxGigEth15MinCurrentRxMulticastFrames,
        adGenTA8xxGigEth15MinCurrentRxBroadcastFrames,
        adGenTA8xxGigEth15MinCurrentRxUnicastFrames,
        adGenTA8xxGigEth15MinCurrentTxMulticastFrames,
        adGenTA8xxGigEth15MinCurrentTxBroadcastFrames,
        adGenTA8xxGigEth15MinCurrentTxUnicastFrames,
        adGenTA8xxGigEth15MinCurrentRxJabbers,
        adGenTA8xxGigEth15MinCurrentRxFragments
   }
   STATUS current
   DESCRIPTION
     "These objects provide support for retrieving Gigabit Ethernet
      current 15 minute intervals."
   ::= { adGenTA8xxMibGroups 15 }

adGenTA8xxGigEthInt15MinPerfGroup OBJECT-GROUP
   OBJECTS
   {
        adGenTA8xxGigEth15MinIntervalNumber,
        adGenTA8xxGigEth15MinIntervalTxBytes,
        adGenTA8xxGigEth15MinIntervalTxFrames,
        adGenTA8xxGigEth15MinIntervalRxBytes,
        adGenTA8xxGigEth15MinIntervalRxFrames,
        adGenTA8xxGigEth15MinIntervalRxGoodBytes,
        adGenTA8xxGigEth15MinIntervalRxGoodFrames,
        adGenTA8xxGigEth15MinIntervalRxFCSErrors,
        adGenTA8xxGigEth15MinIntervalRxDroppedFrames,
        adGenTA8xxGigEth15MinIntervalRxFramesTooBig,
        adGenTA8xxGigEth15MinIntervalRxFramesTooSmall,
        adGenTA8xxGigEth15MinIntervalRxMulticastFrames,
        adGenTA8xxGigEth15MinIntervalRxBroadcastFrames,
        adGenTA8xxGigEth15MinIntervalRxUnicastFrames,
        adGenTA8xxGigEth15MinIntervalTxMulticastFrames,
        adGenTA8xxGigEth15MinIntervalTxBroadcastFrames,
        adGenTA8xxGigEth15MinIntervalTxUnicastFrames,
        adGenTA8xxGigEth15MinIntervalRxJabbers,
        adGenTA8xxGigEth15MinIntervalRxFragments
   }
   STATUS current
   DESCRIPTION
     "These objects provide support for retrieving Gigabit Ethernet
      selected 15 minute intervals."
   ::= { adGenTA8xxMibGroups 16 }

adGenTA8xxGigEthCurr24HrPerfGroup OBJECT-GROUP
   OBJECTS
   {
        adGenTA8xxGigEth24HrCurrentTxBytes,
        adGenTA8xxGigEth24HrCurrentTxFrames,
        adGenTA8xxGigEth24HrCurrentRxBytes,
        adGenTA8xxGigEth24HrCurrentRxFrames,
        adGenTA8xxGigEth24HrCurrentRxGoodBytes,
        adGenTA8xxGigEth24HrCurrentRxGoodFrames,
        adGenTA8xxGigEth24HrCurrentRxFCSErrors,
        adGenTA8xxGigEth24HrCurrentRxDroppedFrames,
        adGenTA8xxGigEth24HrCurrentRxFramesTooBig,
        adGenTA8xxGigEth24HrCurrentRxFramesTooSmall,
        adGenTA8xxGigEth24HrCurrentRxMulticastFrames,
        adGenTA8xxGigEth24HrCurrentRxBroadcastFrames,
        adGenTA8xxGigEth24HrCurrentRxUnicastFrames,
        adGenTA8xxGigEth24HrCurrentTxMulticastFrames,
        adGenTA8xxGigEth24HrCurrentTxBroadcastFrames,
        adGenTA8xxGigEth24HrCurrentTxUnicastFrames,
        adGenTA8xxGigEth24HrCurrentRxJabbers,
        adGenTA8xxGigEth24HrCurrentRxFragments
   }
   STATUS current
   DESCRIPTION
     "These objects provide support for retrieving Gigabit Ethernet
      current 24 hour intervals."
   ::= { adGenTA8xxMibGroups 17 }

adGenTA8xxGigEthInt24HrPerfGroup OBJECT-GROUP
   OBJECTS
   {
        adGenTA8xxGigEth24HrIntervalNumber,
        adGenTA8xxGigEth24HrIntervalTxBytes,
        adGenTA8xxGigEth24HrIntervalTxFrames,
        adGenTA8xxGigEth24HrIntervalRxBytes,
        adGenTA8xxGigEth24HrIntervalRxFrames,
        adGenTA8xxGigEth24HrIntervalRxGoodBytes,
        adGenTA8xxGigEth24HrIntervalRxGoodFrames,
        adGenTA8xxGigEth24HrIntervalRxFCSErrors,
        adGenTA8xxGigEth24HrIntervalRxDroppedFrames,
        adGenTA8xxGigEth24HrIntervalRxFramesTooBig,
        adGenTA8xxGigEth24HrIntervalRxFramesTooSmall,
        adGenTA8xxGigEth24HrIntervalRxMulticastFrames,
        adGenTA8xxGigEth24HrIntervalRxBroadcastFrames,
        adGenTA8xxGigEth24HrIntervalRxUnicastFrames,
        adGenTA8xxGigEth24HrIntervalTxMulticastFrames,
        adGenTA8xxGigEth24HrIntervalTxBroadcastFrames,
        adGenTA8xxGigEth24HrIntervalTxUnicastFrames,
        adGenTA8xxGigEth24HrIntervalRxJabbers,
        adGenTA8xxGigEth24HrIntervalRxFragments
   }
   STATUS current
   DESCRIPTION
     "These objects provide support for retrieving Gigabit Ethernet
      selected 24 hour intervals."
   ::= { adGenTA8xxMibGroups 18 }

adGenTA8xxTestGroup OBJECT-GROUP
   OBJECTS
   {
        adGenTA8xxResetTests,
        adGenTA8xxTestTimeout,
        adGenTA8xxRelayTest,
        adGenTA8xxTestCriticalRelay,
        adGenTA8xxTestMajorRelay,
        adGenTA8xxTestMinorRelay
   }
   STATUS current
   DESCRIPTION
     "These objects provide support for test functions."
   ::= { adGenTA8xxMibGroups 19 }

adGenTA8xxAlarmGroup OBJECT-GROUP
   OBJECTS
   {
        adGenTA8xxTrapAlarmLevel,
        adGenTA8xxACPwrInLevel,
        adGenTA8xxPwrALevel,
        adGenTA8xxPwrBLevel,
        adGenTA8xxAcknowledgeAlarms,
        adGenTA8xxSpecificTrapEnable,
        adGenTA8xxLoginFailureLevel,
        adGenTA8xxLoginSuccessLevel
   }
   STATUS current
   DESCRIPTION
     "These objects provide support for alarms."
   ::= { adGenTA8xxMibGroups 20 }

adGenTA8xxEventGroup NOTIFICATION-GROUP
   NOTIFICATIONS
   {
        adGenTA8xxClrCardFailure,
        adGenTA8xxSetCardFailure,
        adGenTA8xxClrSACardFailure,
        adGenTA8xxSetSACardFailure,
        adGenTA8xxACPwrInAlmClear,
        adGenTA8xxACPwrInAlm,
        adGenTA8xxBusApwrAlmClear,
        adGenTA8xxBusApowerAlm,
        adGenTA8xxBusBpwrAlmClear,
        adGenTA8xxBusBpowerAlm,
        adGenTA8xxUserLockoutClear,
        adGenTA8xxUserLockoutAlm,
        adGenTA8xxUserLoginSuccess,
        adGenTA8xxUserLoginFailure,
        adGenTA8xxClr10100EthLinkDown,
        adGenTA8xxSet10100EthLinkDown,
        adGenTA8xxClrGigEthLinkDown,
        adGenTA8xxSetGigEthLinkDown,
        adGenTA8xxSet10100Eth15MinRxCRCAlignErrs,
        adGenTA8xxSet10100Eth15MinRxUndersizeFrames,
        adGenTA8xxSet10100Eth15MinRxOversizeFrames,
        adGenTA8xxSet10100Eth15MinRxCollisions,
        adGenTA8xxSet10100Eth24HrRxCRCAlignErrs,
        adGenTA8xxSet10100Eth24HrRxUndersizeFrames,
        adGenTA8xxSet10100Eth24HrRxOversizeFrames,
        adGenTA8xxSet10100Eth24HrRxCollisions,
        adGenTA8xxSetGigEth15MinRxFCSErrors,
        adGenTA8xxSetGigEth15MinRxDroppedFrames,
        adGenTA8xxSetGigEth15MinRxFramesTooBig,
        adGenTA8xxSetGigEth15MinRxFramesTooSmall,
        adGenTA8xxSetGigEth24HrRxFCSErrors,
        adGenTA8xxSetGigEth24HrRxDroppedFrames,
        adGenTA8xxSetGigEth24HrRxFramesTooBig,
        adGenTA8xxSetGigEth24HrRxFramesTooSmall,
        adGenTA8xxSet10100Eth15MinRxMulticastFrames,
        adGenTA8xxSet10100Eth15MinRxBroadcastFrames,
        adGenTA8xxSet10100Eth24HrRxMulticastFrames,
        adGenTA8xxSet10100Eth24HrRxBroadcastFrames,
        adGenTA8xxSetGigEth15MinRxMulticastFrames,
        adGenTA8xxSetGigEth15MinRxBroadcastFrames,
        adGenTA8xxSetGigEth24HrRxMulticastFrames,
        adGenTA8xxSetGigEth24HrRxBroadcastFrames,
        adGenTA8xxFanModuleAlm,
        adGenTA8xxSingleFanFailureAlm,
        adGenTA8xxMultipleFanFailureAlm,
        adGenTA8xxFanModuleAlmClear,
        adGenTA8xxSingleFanFailureAlmClear,
        adGenTA8xxMultipleFanFailureAlmClear,
	adGenTA8xxTemperatureHigh,
        adGenTA8xxTemperatureNormal,
        adGenTA8xxCustomerDoorStatus,
        adGenTA8xxTelcoDoorStatus,
        adGenTA8xxClr10100EthLinkLsaForcedDown,
        adGenTA8xxSet10100EthLinkLsaForcedDown,
        adGenTA8xxClrGigEthLinkLsaForcedDown,
        adGenTA8xxSetGigEthLinkLsaForcedDown,
        adGenTA8xxSet10100Eth15MinRxJabbers,
        adGenTA8xxSet10100Eth24HrRxJabbers,
        adGenTA8xxSetGigEth15MinRxJabbers,
        adGenTA8xxSetGigEth24HrRxJabbers,
        adGenTA8xxSet10100Eth15MinRxFragments,
        adGenTA8xxSet10100Eth24HrRxFragments,
        adGenTA8xxSetGigEth15MinRxFragments,
        adGenTA8xxSetGigEth24HrRxFragments
   }
   STATUS current
   DESCRIPTION
     "These objects provide support for events."
   ::= { adGenTA8xxMibGroups 21 }

adGenTA8xxFarEndConfigGroup OBJECT-GROUP
   OBJECTS
   {
        adGenTA8xxFarEndIfIndex,
        adGenTA8xxFarEndIPAddress,
        adGenTA8xxFarEndSysName
   }
   STATUS current
   DESCRIPTION
     "These objects provide support for retrieving far end configuration."
   ::= { adGenTA8xxMibGroups 22 }

adGenTA8xx10100EthThreshGroup OBJECT-GROUP
   OBJECTS
   {
        adGenTA8xx10100Eth15MinThreshRxCRCAlignErrs,
        adGenTA8xx10100Eth15MinThreshRxUndersizeFrames,
        adGenTA8xx10100Eth15MinThreshRxOversizeFrames,
        adGenTA8xx10100Eth15MinThreshRxCollisions,
        adGenTA8xx10100Eth24HrThreshRxCRCAlignErrs,
        adGenTA8xx10100Eth24HrThreshRxUndersizeFrames,
        adGenTA8xx10100Eth24HrThreshRxOversizeFrames,
        adGenTA8xx10100Eth24HrThreshRxCollisions,
        adGenTA8xx10100Eth15MinThreshRxMulticastFrames,
        adGenTA8xx10100Eth15MinThreshRxBroadcastFrames,
        adGenTA8xx10100Eth24HrThreshRxMulticastFrames,
        adGenTA8xx10100Eth24HrThreshRxBroadcastFrames,
        adGenTA8xx10100Eth15MinThreshRxJabbers,
        adGenTA8xx10100Eth15MinThreshRxFragments,
        adGenTA8xx10100Eth24HrThreshRxJabbers,
        adGenTA8xx10100Eth24HrThreshRxFragments
   }
   STATUS current
   DESCRIPTION
     "These objects provide support for 10/100 Ethernet thresholds."
   ::= { adGenTA8xxMibGroups 23 }

adGenTA8xxGigEthThreshGroup OBJECT-GROUP
   OBJECTS
   {
        adGenTA8xxGigEth15MinThreshRxFCSErrors,
        adGenTA8xxGigEth15MinThreshRxDroppedFrames,
        adGenTA8xxGigEth15MinThreshRxFramesTooBig,
        adGenTA8xxGigEth15MinThreshRxFramesTooSmall,
        adGenTA8xxGigEth24HrThreshRxFCSErrors,
        adGenTA8xxGigEth24HrThreshRxDroppedFrames,
        adGenTA8xxGigEth24HrThreshRxFramesTooBig,
        adGenTA8xxGigEth24HrThreshRxFramesTooSmall,
        adGenTA8xxGigEth15MinThreshRxMulticastFrames,
        adGenTA8xxGigEth15MinThreshRxBroadcastFrames,
        adGenTA8xxGigEth24HrThreshRxMulticastFrames,
        adGenTA8xxGigEth24HrThreshRxBroadcastFrames,
        adGenTA8xxGigEth15MinThreshRxJabbers,
        adGenTA8xxGigEth15MinThreshRxFragments,
        adGenTA8xxGigEth24HrThreshRxJabbers,
        adGenTA8xxGigEth24HrThreshRxFragments
   }
   STATUS current
   DESCRIPTION
     "These objects provide support for Gigabit Ethernet thresholds."
   ::= { adGenTA8xxMibGroups 24 }

adGenTA8xxBertPrvGroup OBJECT-GROUP
   OBJECTS
   {
         adGenTA8xxTstBertStartAndStop,
         adGenTA8xxTstBertResetStatistics,
         adGenTA8xxTstBertPattern,
         adGenTA8xxTstBertPatternPolarity,
         adGenTA8xxTstBertErrorInject
   }
   STATUS current
   DESCRIPTION
     "These objects provide support for BERT provisioning."
   ::= { adGenTA8xxMibGroups 25 }

adGenTA8xxBertStatGroup OBJECT-GROUP
   OBJECTS
   {
         adGenTA8xxTstBertStatus,
         adGenTA8xxTstBertBER,
         adGenTA8xxTstBertErrorCount,
         adGenTA8xxTstBertPattSyncLossCount,
         adGenTA8xxTstBertErroredSeconds,
         adGenTA8xxTstBertElapsedTime
   }
   STATUS current
   DESCRIPTION
     "These objects provide BERT status information."
   ::= { adGenTA8xxMibGroups 26 }

adGenTA8xxTstLpbkPrvGroup OBJECT-GROUP
   OBJECTS
   {
         adGenTA8xxTstIncomingLoopbackPatterns,
         adGenTA8xxTstRequestRemoteLoopback,
         adGenTA8xxTstIncomingInbandLoopbackPatterns,
         adGenTA8xxTstIncomingFDLLoopbackPatterns
   }
   STATUS current
   DESCRIPTION
     "These objects provide support for Loopback provisioning."
   ::= { adGenTA8xxMibGroups 27 }

adGenTA8xxMgmtStatsGroup OBJECT-GROUP
   OBJECTS
   {
         adGenTA8xxMgmtStatsCurrentTxFrames,
         adGenTA8xxMgmtStatsCurrentRxFrames
   }
   STATUS current
   DESCRIPTION
     "These objects provide management statistics."
   ::= { adGenTA8xxMibGroups 28 }

adGenTA8xxDeprecatedGroup OBJECT-GROUP
   OBJECTS
   {
        adGenTA8xxCapabilities
   }
   STATUS deprecated
   DESCRIPTION
     "These objects have been deprecated."
   ::= { adGenTA8xxMibGroups 29 }


--==================================================================================================================
--==================================================================================================================
--==================================================================================================================


   adGenTA8xxClrCardFailure NOTIFICATION-TYPE
      OBJECTS  {
         adTrapInformSeqNum,
         sysName,
         adGenSlotInfoIndex,
         adGenSlotAlarmStatus,
         adGenTA8xxTrapAlarmLevel
      }
      STATUS  current
      DESCRIPTION
         "This trap indicates that the card failure alarm mode has cleared."

         --#TYPE         "Status - Alarm"
         --#SUMMARY      "TA8xx 3: Card Failure Condition Clear"
         --#SEVERITY     MINOR
         --#GENERIC      6
         --#CATEGORY     "Error Events"
         --#SOURCE_ID    "A"
         --#TIMEINDEX    0
      ::= { adGenTA8xxEvents 3 }

   adGenTA8xxSetCardFailure NOTIFICATION-TYPE
      OBJECTS  {
         adTrapInformSeqNum,
         sysName,
         adGenSlotInfoIndex,
         adGenSlotAlarmStatus,
         adGenTA8xxTrapAlarmLevel
      }
      STATUS  current
      DESCRIPTION
         "This trap indicates that the unit has entered a card failure alarm condition."
         --#TYPE         "Status - Alarm"
         --#SUMMARY      "TA8xx 4: Card Failure Condition Active"
         --#SEVERITY     MINOR
         --#GENERIC      6
         --#CATEGORY     "Error Events"
         --#SOURCE_ID    "A"
         --#TIMEINDEX    0
      ::= { adGenTA8xxEvents 4 }

   adGenTA8xxClrSACardFailure NOTIFICATION-TYPE
      OBJECTS  {
         adTrapInformSeqNum,
         sysName,
         adGenSlotInfoIndex,
         adGenTA8xxTrapAlarmLevel
      }
      STATUS  current
      DESCRIPTION
         "This trap indicates that the unit has left a critical card failure alarm condition."

         --#TYPE         "Status - Alarm"
         --#SUMMARY      "TA8xx 51: Critical Card Failure Condition Clear"
         --#SEVERITY     CRITICAL
         --#GENERIC      6
         --#CATEGORY     "Error Events"
         --#SOURCE_ID    "A"
         --#TIMEINDEX    0
      ::= { adGenTA8xxEvents 51 }

   adGenTA8xxSetSACardFailure NOTIFICATION-TYPE
            OBJECTS  {
               adTrapInformSeqNum,
               sysName,
               adGenSlotInfoIndex,
               adGenTA8xxTrapAlarmLevel
            }
            STATUS  current
            DESCRIPTION
               "This trap indicates that the unit has entered a critical card failure alarm condition."

               --#TYPE         "Status - Alarm"
               --#SUMMARY      "TA8xx 52: Critical Card Failure Condition Active"
               --#SEVERITY     CRITICAL
               --#GENERIC      6
               --#CATEGORY     "Error Events"
               --#SOURCE_ID    "A"
               --#TIMEINDEX    0
            ::= { adGenTA8xxEvents 52  }

   adGenTA8xxACPwrInAlmClear    NOTIFICATION-TYPE
      OBJECTS       {
         adTrapInformSeqNum,
         sysName,
         adGenTA8xxACPwrInLevel
      }
      STATUS  current
      DESCRIPTION
         "AC_PWR_IN Alarm clear"

         --#TYPE      "Status - Alarm"
         --#SUMMARY   "TA8xx 61: AC_PWR_IN Alarm cleared"
         --#SEVERITY  CRITICAL
         --#GENERIC   6
         --#CATEGORY  "Error Events"
         --#SOURCE_ID "A"
         --#TIMEINDEX 0
      ::= { adGenTA8xxEvents 61 }

   adGenTA8xxACPwrInAlm    NOTIFICATION-TYPE
      OBJECTS       {
         adTrapInformSeqNum,
         sysName,
         adGenTA8xxACPwrInLevel
      }
      STATUS  current
      DESCRIPTION
         "AC_PWR_IN Alarm active"

         --#TYPE      "Status - Alarm"
         --#SUMMARY   "TA8xx 62: AC_PWR_IN Alarm active"
         --#SEVERITY  CRITICAL
         --#GENERIC   6
         --#CATEGORY  "Error Events"
         --#SOURCE_ID "A"
         --#TIMEINDEX 0
      ::= { adGenTA8xxEvents 62 }

   adGenTA8xxBusApwrAlmClear    NOTIFICATION-TYPE
      OBJECTS       {
         adTrapInformSeqNum,
         sysName,
         adGenTA8xxPwrALevel
      }
      STATUS  current
      DESCRIPTION
         "Bus A Power Failure Alarm clear"

         --#TYPE      "Status - Alarm"
         --#SUMMARY   "TA8xx 69: Bus A Power Failure Alarm cleared"
         --#SEVERITY  MINOR
         --#GENERIC   6
         --#CATEGORY  "Error Events"
         --#SOURCE_ID "A"
         --#TIMEINDEX 0
      ::= { adGenTA8xxEvents 69 }

   adGenTA8xxBusApowerAlm    NOTIFICATION-TYPE
      OBJECTS       {
         adTrapInformSeqNum,
         sysName,
         adGenTA8xxPwrALevel
      }
      STATUS  current
      DESCRIPTION
         "Bus A Power Failure Alarm active"

         --#TYPE      "Status - Alarm"
         --#SUMMARY   "TA8xx 70: Bus A Power Failure Alarm active"
         --#SEVERITY  MINOR
         --#GENERIC   6
         --#CATEGORY  "Error Events"
         --#SOURCE_ID "A"
         --#TIMEINDEX 0
      ::= { adGenTA8xxEvents 70 }

   adGenTA8xxBusBpwrAlmClear    NOTIFICATION-TYPE
      OBJECTS       {
         adTrapInformSeqNum,
         sysName,
         adGenTA8xxPwrBLevel
      }
      STATUS  current
      DESCRIPTION
         "Bus B Power Failure Alarm clear"

         --#TYPE      "Status - Alarm"
         --#SUMMARY   "TA8xx 71: Bus B Power Failure Alarm cleared"
         --#SEVERITY  MINOR
         --#GENERIC   6
         --#CATEGORY  "Error Events"
         --#SOURCE_ID "B"
         --#TIMEINDEX 0
      ::= { adGenTA8xxEvents 71  }

   adGenTA8xxBusBpowerAlm    NOTIFICATION-TYPE
      OBJECTS       {
         adTrapInformSeqNum,
         sysName,
         adGenTA8xxPwrBLevel
      }
      STATUS  current
      DESCRIPTION
         "Bus B Power Failure Alarm active"

         --#TYPE      "Status - Alarm"
         --#SUMMARY   "TA8xx 72: Bus B Power Failure Alarm active"
         --#SEVERITY  MINOR
         --#GENERIC   6
         --#CATEGORY  "Error Events"
         --#SOURCE_ID "B"
         --#TIMEINDEX 0
      ::= { adGenTA8xxEvents 72 }

   adGenTA8xxUserLockoutClear    NOTIFICATION-TYPE
      OBJECTS       {
         adTrapInformSeqNum,
         sysName,
         adGenTA8xxTrapAlarmLevel
      }
      STATUS  current
      DESCRIPTION
         "User lockout for failed logins has cleared."

         --#TYPE      "Status - Alarm"
         --#SUMMARY   "TA8xx 73: User Lockout Cleared"
         --#SEVERITY  INFO
         --#GENERIC   6
         --#CATEGORY  "Security Events"
         --#SOURCE_ID "A"
         --#TIMEINDEX 0
      ::= { adGenTA8xxEvents 73 }

   adGenTA8xxUserLockoutAlm    NOTIFICATION-TYPE
      OBJECTS       {
         adTrapInformSeqNum,
         sysName,
         adGenTA8xxTrapAlarmLevel
      }
      STATUS  current
      DESCRIPTION
         "User lockout due to failed logins active."

         --#TYPE      "Status - Alarm"
         --#SUMMARY   "TA8xx 74: User Lockout Active"
         --#SEVERITY  INFO
         --#GENERIC   6
         --#CATEGORY  "Security Events"
         --#SOURCE_ID "A"
         --#TIMEINDEX 0
      ::= { adGenTA8xxEvents 74 }

   adGenTA8xxUserLoginSuccess    NOTIFICATION-TYPE
      OBJECTS       {
         adTrapInformSeqNum,
         sysName,
         adGenTA8xxTrapAlarmLevel
      }
      STATUS  current
      DESCRIPTION
         "User successfully logged in."

         --#TYPE      "Status - Alarm"
         --#SUMMARY   "TA8xx 75: User Logged In"
         --#SEVERITY  INFO
         --#GENERIC   6
         --#CATEGORY  "Security Events"
         --#SOURCE_ID "A"
         --#TIMEINDEX 0
      ::= { adGenTA8xxEvents 75 }

   adGenTA8xxUserLoginFailure    NOTIFICATION-TYPE
      OBJECTS       {
         adTrapInformSeqNum,
         sysName,
         adGenTA8xxTrapAlarmLevel
      }
      STATUS  current
      DESCRIPTION
         "User login failed."

         --#TYPE      "Status - Alarm"
         --#SUMMARY   "TA8xx 76: User Login Failed"
         --#SEVERITY  INFO
         --#GENERIC   6
         --#CATEGORY  "Security Events"
         --#SOURCE_ID "A"
         --#TIMEINDEX 0
      ::= { adGenTA8xxEvents 76 }

   adGenTA8xxFanModuleAlmClear    NOTIFICATION-TYPE
      OBJECTS       {
         adTrapInformSeqNum,
         sysName,
         adGenTA8xxTrapAlarmLevel
      }
      STATUS  current
      DESCRIPTION
         "Fan Module Removed Alarm clear"

         --#TYPE      "Status - Alarm"
         --#SUMMARY   "TA8xx 77: Fan Module Removed Alarm clear"
         --#SEVERITY  CRITICAL
         --#GENERIC   6
         --#CATEGORY  "Error Events"
         --#SOURCE_ID "A"
         --#TIMEINDEX 0
      ::= { adGenTA8xxEvents 77  }

   adGenTA8xxFanModuleAlm    NOTIFICATION-TYPE
      OBJECTS       {
         adTrapInformSeqNum,
         sysName,
         adGenTA8xxTrapAlarmLevel
      }
      STATUS  current
      DESCRIPTION
         "Fan Module Removed Alarm active"

         --#TYPE      "Status - Alarm"
         --#SUMMARY   "TA8xx 78: Fan Module Removed Alarm active"
         --#SEVERITY  CRITICAL
         --#GENERIC   6
         --#CATEGORY  "Error Events"
         --#SOURCE_ID "A"
         --#TIMEINDEX 0
      ::= { adGenTA8xxEvents 78 }

   adGenTA8xxSingleFanFailureAlmClear    NOTIFICATION-TYPE
      OBJECTS       {
         adTrapInformSeqNum,
         sysName,
         adGenTA8xxTrapAlarmLevel
      }
      STATUS  current
      DESCRIPTION
         "Single Fan Failure Alarm clear"

         --#TYPE      "Status - Alarm"
         --#SUMMARY   "TA8xx 79: Single Fan Failure Alarm clear"
         --#SEVERITY  MAJOR
         --#GENERIC   6
         --#CATEGORY  "Error Events"
         --#SOURCE_ID "A"
         --#TIMEINDEX 0
      ::= { adGenTA8xxEvents 79  }

   adGenTA8xxSingleFanFailureAlm    NOTIFICATION-TYPE
      OBJECTS       {
         adTrapInformSeqNum,
         sysName,
         adGenTA8xxTrapAlarmLevel
      }
      STATUS  current
      DESCRIPTION
         "Single Fan Failure Alarm active"

         --#TYPE      "Status - Alarm"
         --#SUMMARY   "TA8xx 80: Single Fan Failure Alarm  active"
         --#SEVERITY  MAJOR
         --#GENERIC   6
         --#CATEGORY  "Error Events"
         --#SOURCE_ID "A"
         --#TIMEINDEX 0
      ::= { adGenTA8xxEvents 80 }

   adGenTA8xxMultipleFanFailureAlmClear    NOTIFICATION-TYPE
      OBJECTS       {
         adTrapInformSeqNum,
         sysName,
         adGenTA8xxTrapAlarmLevel
      }
      STATUS  current
      DESCRIPTION
         "Multiple Fan Failure Alarm clear"

         --#TYPE      "Status - Alarm"
         --#SUMMARY   "TA8xx 81: Multiple Fan Failure Alarm clear"
         --#SEVERITY  CRITICAL
         --#GENERIC   6
         --#CATEGORY  "Error Events"
         --#SOURCE_ID "A"
         --#TIMEINDEX 0
      ::= { adGenTA8xxEvents 81  }

   adGenTA8xxMultipleFanFailureAlm    NOTIFICATION-TYPE
      OBJECTS       {
         adTrapInformSeqNum,
         sysName,
         adGenTA8xxTrapAlarmLevel
      }
      STATUS  current
      DESCRIPTION
         "Multiple Fan Failure Alarm active"

         --#TYPE      "Status - Alarm"
         --#SUMMARY   "TA8xx 82: Multiple Fan Failure Alarm  active"
         --#SEVERITY  CRITICAL
         --#GENERIC   6
         --#CATEGORY  "Error Events"
         --#SOURCE_ID "A"
         --#TIMEINDEX 0
      ::= { adGenTA8xxEvents 82 }

--==================================================================================================================
   adGenTA8xxClr10100EthLinkDown NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the 10/100 Ethernet Link Down condition clears."
         --#TYPE         "Status - Alarm"
         --#SUMMARY      "TA8xx 89: 10/100 Ethernet Link Down Clears."
         --#SEVERITY     MAJOR
         --#GENERIC      6
         --#CATEGORY     "Error Events"
         --#SOURCE_ID    "A"
         --#TIMEINDEX    0
      ::= { adGenTA8xxEvents 89 }

   adGenTA8xxSet10100EthLinkDown NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface enters 10/100 Ethernet Link Down condition."
         --#TYPE         "Status - Alarm"
         --#SUMMARY      "TA8xx 90: 10/100 Ethernet Link Down Condition Active."
         --#SEVERITY     MAJOR
         --#GENERIC      6
         --#CATEGORY     "Error Events"
         --#SOURCE_ID    "A"
         --#TIMEINDEX    0
      ::= { adGenTA8xxEvents 90 }

   adGenTA8xxClrGigEthLinkDown NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the Gigabit Ethernet Link Down condition clears."
         --#TYPE         "Status - Alarm"
         --#SUMMARY      "TA8xx 91: Gigabit Ethernet Link Down Clears."
         --#SEVERITY     MAJOR
         --#GENERIC      6
         --#CATEGORY     "Error Events"
         --#SOURCE_ID    "A"
         --#TIMEINDEX    0
      ::= { adGenTA8xxEvents 91 }

   adGenTA8xxSetGigEthLinkDown NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface enters Gigabit Ethernet Link Down condition."
         --#TYPE         "Status - Alarm"
         --#SUMMARY      "TA8xx 92: Gigabit Ethernet Link Down Condition Active."
         --#SEVERITY     MAJOR
         --#GENERIC      6
         --#CATEGORY     "Error Events"
         --#SOURCE_ID    "A"
         --#TIMEINDEX    0
      ::= { adGenTA8xxEvents 92 }

   adGenTA8xxClrGigEthUnapprovedSFP NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the Gigabit Ethernet Unapproved SFP condition clears."
         --#TYPE         "Status - Alarm"
         --#SUMMARY      "TA8xx 93: Gigabit Ethernet Unapproved SFP Clears."
         --#SEVERITY     MINOR
         --#GENERIC      6
         --#CATEGORY     "Error Events"
         --#SOURCE_ID    "A"
         --#TIMEINDEX    0
      ::= { adGenTA8xxEvents 93 }

   adGenTA8xxSetGigEthUnapprovedSFP NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface enters Gigabit Ethernet Unapproved SFP condition."
         --#TYPE         "Status - Alarm"
         --#SUMMARY      "TA8xx 94: Gigabit Ethernet Unapproved SFP Condition Active."
         --#SEVERITY     MINOR
         --#GENERIC      6
         --#CATEGORY     "Error Events"
         --#SOURCE_ID    "A"
         --#TIMEINDEX    0
      ::= { adGenTA8xxEvents 94 }

--==================================================================================================================
   adGenTA8xxSet10100Eth15MinRxCRCAlignErrs NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface has crossed the 15 min Rx Alignment & FCS Errors Threshold"
         --#TYPE         "Status - Alarm"
         --#SUMMARY      "TA8xx 100: 10/100 Ethernet Rx Alignment & FCS Errors 15 min Threshold Crossed."
         --#SEVERITY     WARNING
         --#GENERIC      6
         --#CATEGORY     "Error Events"
         --#SOURCE_ID    "A"
         --#TIMEINDEX    0
      ::= { adGenTA8xxEvents 100 }

   adGenTA8xxSet10100Eth15MinRxUndersizeFrames NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface has crossed the 15 min Rx Undersized Frames Threshold"
         --#TYPE         "Status - Alarm"
         --#SUMMARY      "TA8xx 101: 10/100 Ethernet Rx Undersized Frames 15 min Threshold Crossed."
         --#SEVERITY     WARNING
         --#GENERIC      6
         --#CATEGORY     "Error Events"
         --#SOURCE_ID    "A"
         --#TIMEINDEX    0
      ::= { adGenTA8xxEvents 101 }

   adGenTA8xxSet10100Eth15MinRxOversizeFrames NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface has crossed the 15 min Rx Oversized Frames Threshold"
         --#TYPE         "Status - Alarm"
         --#SUMMARY      "TA8xx 102: 10/100 Ethernet Rx Oversized Frames 15 min Threshold Crossed."
         --#SEVERITY     WARNING
         --#GENERIC      6
         --#CATEGORY     "Error Events"
         --#SOURCE_ID    "A"
         --#TIMEINDEX    0
      ::= { adGenTA8xxEvents 102 }

   adGenTA8xxSet10100Eth15MinRxCollisions NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface has crossed the 15 min Rx Collisions Threshold"
         --#TYPE         "Status - Alarm"
         --#SUMMARY      "TA8xx 103: 10/100 Ethernet Rx Collisions 15 min Threshold Crossed."
         --#SEVERITY     WARNING
         --#GENERIC      6
         --#CATEGORY     "Error Events"
         --#SOURCE_ID    "A"
         --#TIMEINDEX    0
      ::= { adGenTA8xxEvents 103 }

   adGenTA8xxSet10100Eth15MinRxDiscardedFrames NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface has crossed the 15 min Rx Discarded Frames Threshold"
         --#TYPE         "Status - Alarm"
         --#SUMMARY      "TA8xx 104: 10/100 Ethernet Rx Discarded Frames 15 min Threshold Crossed."
         --#SEVERITY     WARNING
         --#GENERIC      6
         --#CATEGORY     "Error Events"
         --#SOURCE_ID    "A"
         --#TIMEINDEX    0
      ::= { adGenTA8xxEvents 104 }

   adGenTA8xxSet10100Eth24HrRxCRCAlignErrs NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface has crossed the 24 hour Rx Alignment & FCS Errors Threshold"
         --#TYPE         "Status - Alarm"
         --#SUMMARY      "TA8xx 105: 10/100 Ethernet Rx Alignment & FCS Errors 24 hour Threshold Crossed."
         --#SEVERITY     WARNING
         --#GENERIC      6
         --#CATEGORY     "Error Events"
         --#SOURCE_ID    "A"
         --#TIMEINDEX    0
      ::= { adGenTA8xxEvents 105 }

   adGenTA8xxSet10100Eth24HrRxUndersizeFrames NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface has crossed the 24 hour Rx Undersized Frames Threshold"
         --#TYPE         "Status - Alarm"
         --#SUMMARY      "TA8xx 106: 10/100 Ethernet Rx Undersized Frames 24 hour Threshold Crossed."
         --#SEVERITY     WARNING
         --#GENERIC      6
         --#CATEGORY     "Error Events"
         --#SOURCE_ID    "A"
         --#TIMEINDEX    0
      ::= { adGenTA8xxEvents 106 }

   adGenTA8xxSet10100Eth24HrRxOversizeFrames NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface has crossed the 24 hour Rx Oversized Frames Threshold"
         --#TYPE         "Status - Alarm"
         --#SUMMARY      "TA8xx 107: 10/100 Ethernet Rx Oversized Frames 24 hour Threshold Crossed."
         --#SEVERITY     WARNING
         --#GENERIC      6
         --#CATEGORY     "Error Events"
         --#SOURCE_ID    "A"
         --#TIMEINDEX    0
      ::= { adGenTA8xxEvents 107 }

   adGenTA8xxSet10100Eth24HrRxCollisions NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface has crossed the 24 hour Rx Collisions Threshold"
         --#TYPE         "Status - Alarm"
         --#SUMMARY      "TA8xx 108: 10/100 Ethernet Rx Collisions 24 hour Threshold Crossed."
         --#SEVERITY     WARNING
         --#GENERIC      6
         --#CATEGORY     "Error Events"
         --#SOURCE_ID    "A"
         --#TIMEINDEX    0
      ::= { adGenTA8xxEvents 108 }

   adGenTA8xxSet10100Eth24HrRxDiscardedFrames NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface has crossed the 15 min Rx Discarded Frames Threshold"
         --#TYPE         "Status - Alarm"
         --#SUMMARY      "TA8xx 109: 10/100 Ethernet Rx Discarded Frames 15 min Threshold Crossed."
         --#SEVERITY     WARNING
         --#GENERIC      6
         --#CATEGORY     "Error Events"
         --#SOURCE_ID    "A"
         --#TIMEINDEX    0
      ::= { adGenTA8xxEvents 109 }

   adGenTA8xxSetGigEth15MinRxFCSErrors NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface has crossed the 15 min Rx FCS Errors Threshold"
         --#TYPE         "Status - Alarm"
         --#SUMMARY      "TA8xx 110: Gigabit Ethernet Rx FCS Errors 15 min Threshold Crossed."
         --#SEVERITY     WARNING
         --#GENERIC      6
         --#CATEGORY     "Error Events"
         --#SOURCE_ID    "A"
         --#TIMEINDEX    0
      ::= { adGenTA8xxEvents 110 }

   adGenTA8xxSetGigEth15MinRxDroppedFrames NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface has crossed the 15 min Rx Dropped Frames Threshold"
         --#TYPE         "Status - Alarm"
         --#SUMMARY      "TA8xx 111: Gigabit Ethernet Rx Dropped Frames 15 min Threshold Crossed."
         --#SEVERITY     WARNING
         --#GENERIC      6
         --#CATEGORY     "Error Events"
         --#SOURCE_ID    "A"
         --#TIMEINDEX    0
      ::= { adGenTA8xxEvents 111 }

   adGenTA8xxSetGigEth15MinRxFramesTooBig NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface has crossed the 15 min Rx Frames Too Big Threshold"
         --#TYPE         "Status - Alarm"
         --#SUMMARY      "TA8xx 112: Gigabit Ethernet Rx Frames Too Big 15 min Threshold Crossed."
         --#SEVERITY     WARNING
         --#GENERIC      6
         --#CATEGORY     "Error Events"
         --#SOURCE_ID    "A"
         --#TIMEINDEX    0
      ::= { adGenTA8xxEvents 112 }

   adGenTA8xxSetGigEth15MinRxFramesTooSmall NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface has crossed the 15 min Rx Frames Too Small Threshold"
         --#TYPE         "Status - Alarm"
         --#SUMMARY      "TA8xx 113: Gigabit Ethernet Rx Frames Too Small 15 min Threshold Crossed."
         --#SEVERITY     WARNING
         --#GENERIC      6
         --#CATEGORY     "Error Events"
         --#SOURCE_ID    "A"
         --#TIMEINDEX    0
      ::= { adGenTA8xxEvents 113 }

   adGenTA8xxSetGigEth24HrRxFCSErrors NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface has crossed the 24 hour Rx FCS Errors Threshold"
         --#TYPE         "Status - Alarm"
         --#SUMMARY      "TA8xx 114: Gigabit Ethernet Rx FCS Errors 24 hour Threshold Crossed."
         --#SEVERITY     WARNING
         --#GENERIC      6
         --#CATEGORY     "Error Events"
         --#SOURCE_ID    "A"
         --#TIMEINDEX    0
      ::= { adGenTA8xxEvents 114 }

   adGenTA8xxSetGigEth24HrRxDroppedFrames NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface has crossed the 24 hour Rx Dropped Frames Threshold"
         --#TYPE         "Status - Alarm"
         --#SUMMARY      "TA8xx 115: Gigabit Ethernet Rx Dropped Frames 24 hour Threshold Crossed."
         --#SEVERITY     WARNING
         --#GENERIC      6
         --#CATEGORY     "Error Events"
         --#SOURCE_ID    "A"
         --#TIMEINDEX    0
      ::= { adGenTA8xxEvents 115 }

   adGenTA8xxSetGigEth24HrRxFramesTooBig NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface has crossed the 24 hour Rx Frames Too Big Threshold"
         --#TYPE         "Status - Alarm"
         --#SUMMARY      "TA8xx 116: Gigabit Ethernet Rx Frames Too Big 24 hour Threshold Crossed."
         --#SEVERITY     WARNING
         --#GENERIC      6
         --#CATEGORY     "Error Events"
         --#SOURCE_ID    "A"
         --#TIMEINDEX    0
      ::= { adGenTA8xxEvents 116 }

   adGenTA8xxSetGigEth24HrRxFramesTooSmall NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface has crossed the 24 hour Rx Frames Too Small Threshold"
         --#TYPE         "Status - Alarm"
         --#SUMMARY      "TA8xx 117: Gigabit Ethernet Rx Frames Too Small 24 hour Threshold Crossed."
         --#SEVERITY     WARNING
         --#GENERIC      6
         --#CATEGORY     "Error Events"
         --#SOURCE_ID    "A"
         --#TIMEINDEX    0
      ::= { adGenTA8xxEvents 117 }

   adGenTA8xxSet10100Eth15MinRxMulticastFrames NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface has crossed the 15 min Rx Multicast Frames Threshold"
         --#TYPE         "Status - Alarm"
         --#SUMMARY      "TA8xx 104: 10/100 Ethernet Rx Multicast Frames 15 min Threshold Crossed."
         --#SEVERITY     WARNING
         --#GENERIC      6
         --#CATEGORY     "Error Events"
         --#SOURCE_ID    "A"
         --#TIMEINDEX    0
      ::= { adGenTA8xxEvents 118 }

   adGenTA8xxSet10100Eth15MinRxBroadcastFrames NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface has crossed the 15 min Rx Broadcast Frames Threshold"
         --#TYPE         "Status - Alarm"
         --#SUMMARY      "TA8xx 104: 10/100 Ethernet Rx Broadcast Frames 15 min Threshold Crossed."
         --#SEVERITY     WARNING
         --#GENERIC      6
         --#CATEGORY     "Error Events"
         --#SOURCE_ID    "A"
         --#TIMEINDEX    0
      ::= { adGenTA8xxEvents 119 }

   adGenTA8xxSet10100Eth24HrRxMulticastFrames NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface has crossed the 24 hour Rx Multicast Frames Threshold"
         --#TYPE         "Status - Alarm"
         --#SUMMARY      "TA8xx 104: 10/100 Ethernet Rx Multicast Frames 24 hour Threshold Crossed."
         --#SEVERITY     WARNING
         --#GENERIC      6
         --#CATEGORY     "Error Events"
         --#SOURCE_ID    "A"
         --#TIMEINDEX    0
      ::= { adGenTA8xxEvents 120 }

   adGenTA8xxSet10100Eth24HrRxBroadcastFrames NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface has crossed the 24 hour Rx Broadcast Frames Threshold"
         --#TYPE         "Status - Alarm"
         --#SUMMARY      "TA8xx 104: 10/100 Ethernet Rx Broadcast Frames 24 hour Threshold Crossed."
         --#SEVERITY     WARNING
         --#GENERIC      6
         --#CATEGORY     "Error Events"
         --#SOURCE_ID    "A"
         --#TIMEINDEX    0
      ::= { adGenTA8xxEvents 121 }

   adGenTA8xxSetGigEth15MinRxMulticastFrames NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface has crossed the 15 min Rx Multicast Frames Threshold"
         --#TYPE         "Status - Alarm"
         --#SUMMARY      "TA8xx 104: Gigabit Ethernet Rx Multicast Frames 15 min Threshold Crossed."
         --#SEVERITY     WARNING
         --#GENERIC      6
         --#CATEGORY     "Error Events"
         --#SOURCE_ID    "A"
         --#TIMEINDEX    0
      ::= { adGenTA8xxEvents 122 }

   adGenTA8xxSetGigEth15MinRxBroadcastFrames NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface has crossed the 15 min Rx Broadcast Frames Threshold"
         --#TYPE         "Status - Alarm"
         --#SUMMARY      "TA8xx 104: Gigabit Ethernet Rx Broadcast Frames 15 min Threshold Crossed."
         --#SEVERITY     WARNING
         --#GENERIC      6
         --#CATEGORY     "Error Events"
         --#SOURCE_ID    "A"
         --#TIMEINDEX    0
      ::= { adGenTA8xxEvents 123 }

   adGenTA8xxSetGigEth24HrRxMulticastFrames NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface has crossed the 24 hour Rx Multicast Frames Threshold"
         --#TYPE         "Status - Alarm"
         --#SUMMARY      "TA8xx 104: Gigabit Ethernet Rx Multicast Frames 24 hour Threshold Crossed."
         --#SEVERITY     WARNING
         --#GENERIC      6
         --#CATEGORY     "Error Events"
         --#SOURCE_ID    "A"
         --#TIMEINDEX    0
      ::= { adGenTA8xxEvents 124 }

   adGenTA8xxSetGigEth24HrRxBroadcastFrames NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface has crossed the 24 hour Rx Broadcast Frames Threshold"
         --#TYPE         "Status - Alarm"
         --#SUMMARY      "TA8xx 104: Gigabit Ethernet Rx Broadcast Frames 24 hour Threshold Crossed."
         --#SEVERITY     WARNING
         --#GENERIC      6
         --#CATEGORY     "Error Events"
         --#SOURCE_ID    "A"
         --#TIMEINDEX    0
      ::= { adGenTA8xxEvents 125 }

   adGenTA8xxTemperatureHigh NOTIFICATION-TYPE
      OBJECTS  {
         adTrapInformSeqNum,
         sysName,
         adGenTA8xxTemperatureCelsuis,
         adGenTA8xxTemperatureThresholdCelsuis,
         adGenTA8xxTemperatureFahrenheit,
         adGenTA8xxTemperatureThresholdFahrenheit
      }
      STATUS  current
      DESCRIPTION
         "This trap indicates that the temperature is above the threshold temperature."
         --#TYPE         "Status - Alarm"
         --#SUMMARY      "TA8xx 126: High Temperature Threshold Crossed."
         --#SEVERITY     MAJOR
         --#GENERIC      6
         --#CATEGORY     "Error Events"
         --#SOURCE_ID    "A"
         --#TIMEINDEX    0
      ::= { adGenTA8xxEvents 126 }

   adGenTA8xxTemperatureNormal NOTIFICATION-TYPE
      OBJECTS  {
         adTrapInformSeqNum,
         sysName,
         adGenTA8xxTemperatureCelsuis,
         adGenTA8xxTemperatureThresholdCelsuis,
         adGenTA8xxTemperatureFahrenheit,
         adGenTA8xxTemperatureThresholdFahrenheit
      }
      STATUS  current
      DESCRIPTION
         "This trap indicates that the temperature is below the threshold temperature."
         --#TYPE         "Status - Alarm"
         --#SUMMARY      "TA8xx 127: Temperature below High Temperature Threshold."
         --#SEVERITY     MAJOR
         --#GENERIC      6
         --#CATEGORY     "Error Events"
         --#SOURCE_ID    "A"
         --#TIMEINDEX    0
      ::= { adGenTA8xxEvents 127 }

   adGenTA8xxCustomerDoorStatus NOTIFICATION-TYPE
      OBJECTS  {
         adTrapInformSeqNum,
         sysName,
         adGenTA8xxCustomerDoor
      }
      STATUS  current
      DESCRIPTION
         "This trap indicates the status of the Customer Door."
         --#TYPE         "Status - Alarm"
         --#SUMMARY      "TA8xx 129: Customer Door."
         --#SEVERITY     WARNING
         --#GENERIC      6
         --#CATEGORY     "Error Events"
         --#SOURCE_ID    "A"
         --#TIMEINDEX    0
      ::= { adGenTA8xxEvents 128 }

   adGenTA8xxTelcoDoorStatus NOTIFICATION-TYPE
      OBJECTS  {
         adTrapInformSeqNum,
         sysName,
         adGenTA8xxTelcoDoor
      }
      STATUS  current
      DESCRIPTION
         "This trap indicates the status of the Telco Door."
         --#TYPE         "Status - Alarm"
         --#SUMMARY      "TA8xx 130: Telco Door."
         --#SEVERITY     WARNING
         --#GENERIC      6
         --#CATEGORY     "Error Events"
         --#SOURCE_ID    "A"
         --#TIMEINDEX    0
      ::= { adGenTA8xxEvents 129 }

   adGenTA8xxClr10100EthLinkLsaForcedDown NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the 10/100 Ethernet Link Forced Down by LSA condition clears."
         --#TYPE         "Status - Alarm"
         --#SUMMARY      "TA8xx 130: 10/100 Ethernet Link Forced Down by LSA Clears."
         --#SEVERITY     MAJOR
         --#GENERIC      6
         --#CATEGORY     "Error Events"
         --#SOURCE_ID    "A"
         --#TIMEINDEX    0
      ::= { adGenTA8xxEvents 130 }

   adGenTA8xxSet10100EthLinkLsaForcedDown NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface enters 10/100 Ethernet Link Forced Down by LSA condition."
         --#TYPE         "Status - Alarm"
         --#SUMMARY      "TA8xx 131: 10/100 Ethernet Link Forced Down by LSA Condition Active."
         --#SEVERITY     MAJOR
         --#GENERIC      6
         --#CATEGORY     "Error Events"
         --#SOURCE_ID    "A"
         --#TIMEINDEX    0
      ::= { adGenTA8xxEvents 131 }

   adGenTA8xxClrGigEthLinkLsaForcedDown NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the Gigabit Ethernet Link Forced Down by LSA condition clears."
         --#TYPE         "Status - Alarm"
         --#SUMMARY      "TA8xx 132: Gigabit Ethernet Link Forced Down by LSA Clears."
         --#SEVERITY     MAJOR
         --#GENERIC      6
         --#CATEGORY     "Error Events"
         --#SOURCE_ID    "A"
         --#TIMEINDEX    0
      ::= { adGenTA8xxEvents 132 }

   adGenTA8xxSetGigEthLinkLsaForcedDown NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface enters Gigabit Ethernet Link Forced Down by LSA condition."
         --#TYPE         "Status - Alarm"
         --#SUMMARY      "TA8xx 133: Gigabit Ethernet Link Forced Down by LSA Condition Active."
         --#SEVERITY     MAJOR
         --#GENERIC      6
         --#CATEGORY     "Error Events"
         --#SOURCE_ID    "A"
         --#TIMEINDEX    0
      ::= { adGenTA8xxEvents 133 }
   
   adGenTA8xxSet10100Eth15MinRxJabbers NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface has crossed the 15 min Rx Jabbers Threshold"
         --#TYPE         "Status - Alarm"
         --#SUMMARY      "TA8xx 134: Ethernet Rx Jabbers 15 min Threshold Crossed."
         --#SEVERITY     WARNING
         --#GENERIC      6
         --#CATEGORY     "Error Events"
         --#SOURCE_ID    "A"
         --#TIMEINDEX    0
      ::= { adGenTA8xxEvents 134 }

   adGenTA8xxSet10100Eth24HrRxJabbers NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface has crossed the 24 hour Rx Jabbers Threshold"
         --#TYPE         "Status - Alarm"
         --#SUMMARY      "TA8xx 135: Ethernet Rx Jabbers 24 hour Threshold Crossed."
         --#SEVERITY     WARNING
         --#GENERIC      6
         --#CATEGORY     "Error Events"
         --#SOURCE_ID    "A"
         --#TIMEINDEX    0
      ::= { adGenTA8xxEvents 135 }

   adGenTA8xxSetGigEth15MinRxJabbers NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface has crossed the 15 min Rx Jabbers Threshold"
         --#TYPE         "Status - Alarm"
         --#SUMMARY      "TA8xx 136: Gigabit Ethernet Rx Jabbers 15 min Threshold Crossed."
         --#SEVERITY     WARNING
         --#GENERIC      6
         --#CATEGORY     "Error Events"
         --#SOURCE_ID    "A"
         --#TIMEINDEX    0
      ::= { adGenTA8xxEvents 136 }

   adGenTA8xxSetGigEth24HrRxJabbers NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface has crossed the 24 hour Rx Jabbers Threshold"
         --#TYPE         "Status - Alarm"
         --#SUMMARY      "TA8xx 137: Gigabit Ethernet Rx Jabbers 24 hour Threshold Crossed."
         --#SEVERITY     WARNING
         --#GENERIC      6
         --#CATEGORY     "Error Events"
         --#SOURCE_ID    "A"
         --#TIMEINDEX    0
      ::= { adGenTA8xxEvents 137 }

   adGenTA8xxSet10100Eth15MinRxFragments NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface has crossed the 15 min Rx Fragments Threshold"
         --#TYPE         "Status - Alarm"
         --#SUMMARY      "TA8xx 138: Ethernet Rx Fragments 15 min Threshold Crossed."
         --#SEVERITY     WARNING
         --#GENERIC      6
         --#CATEGORY     "Error Events"
         --#SOURCE_ID    "A"
         --#TIMEINDEX    0
      ::= { adGenTA8xxEvents 138 }

   adGenTA8xxSet10100Eth24HrRxFragments NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface has crossed the 24 hour Rx Fragments Threshold"
         --#TYPE         "Status - Alarm"
         --#SUMMARY      "TA8xx 139: Ethernet Rx Fragments 24 hour Threshold Crossed."
         --#SEVERITY     WARNING
         --#GENERIC      6
         --#CATEGORY     "Error Events"
         --#SOURCE_ID    "A"
         --#TIMEINDEX    0
      ::= { adGenTA8xxEvents 139 }

   adGenTA8xxSetGigEth15MinRxFragments NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface has crossed the 15 min Rx Fragments Threshold"
         --#TYPE         "Status - Alarm"
         --#SUMMARY      "TA8xx 140: Gigabit Ethernet Rx Fragments 15 min Threshold Crossed."
         --#SEVERITY     WARNING
         --#GENERIC      6
         --#CATEGORY     "Error Events"
         --#SOURCE_ID    "A"
         --#TIMEINDEX    0
      ::= { adGenTA8xxEvents 140 }

   adGenTA8xxSetGigEth24HrRxFragments NOTIFICATION-TYPE
      OBJECTS  {
         adTrapInformSeqNum,
         sysName,
         adGenSlotInfoIndex,
         adGenPortTrapIdentifier,
         ifIndex,
         adGenTA8xxTrapAlarmLevel
      }
      STATUS  current
      DESCRIPTION
         "This trap indicates that the interface has crossed the 24 hour Rx Fragments Threshold"
         --#TYPE         "Status - Alarm"
         --#SUMMARY      "TA8xx 141: Gigabit Ethernet Rx Fragments 24 hour Threshold Crossed."
         --#SEVERITY     WARNING
         --#GENERIC      6
         --#CATEGORY     "Error Events"
         --#SOURCE_ID    "A"
         --#TIMEINDEX    0
      ::= { adGenTA8xxEvents 141 }

END

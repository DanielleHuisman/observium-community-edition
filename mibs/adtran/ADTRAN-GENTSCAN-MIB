ADTRAN-GENTSCAN-MIB

    DEFINITIONS ::= BEGIN

    -- ADTRAN Proprietary and Confidential
    --
    -- TITLE:     The ADTRAN Generic TSCAN MIB
    -- PRODUCTS:  1181413Lx
    -- VERSION:   1.0
    -- AUTHOR:    Brian Slack
    -- DATE:      03/06/10
    --
    -- This MIB defines the TSCAN management information for the 3rd gen or higher Single Port
    -- H4TUC access module for a Total Access 3000 shelf.

    --
    -- Contact Information:
    --                CND Tech Support
    --                Postal: ADTRAN, Inc.
    --                        901 Explorer Blvd.
    --                        Huntsville, AL  35806
    --                Tel:    +1 800 726-8663
    --                Fax:    +1 256 963 6217
    --                E-mail: support@adtran.com
    --
    -- HISTORY:
    --   03/06/10 bcs First edition.
    --   03/06/18 bcs Added adGenTSCANLS1 and adGenTSCANLS2. Changed the number of block used
    --                to send the TSCAN data. Modified the descriptions and names.
    --   03/06/20 bcs Added idle as a return value to adGenTSCANTscanDataStatus. Corrected date
    --                structure for the previous history item.
    --   04/03/11 kle Changed the read-write attributes on all items except
    --                  adGenTSCANAccumTscanData to read-only.
    --   07/10/02 jlb Converted to SNMPv2
    --   09/08/03 twc Added adGenTSCANLastTime and adGenTSCANRepeaterIndex
    --   11/06/09 crh Added extra blocks of bad taps for extended reach TSCAN
    --   11/19/09 crh Added adGenTSCANHybridConfig
    --   12/03/09 gmj Added adGenTSCANFullRangeRate to allow all valid rates to be set for TSCAN

    IMPORTS
         Integer32,
         Unsigned32,
         TimeTicks,
         OBJECT-TYPE,
         MODULE-IDENTITY
            FROM SNMPv2-SMI
         OBJECT-GROUP
            FROM SNMPv2-CONF
         DisplayString
            FROM SNMPv2-TC
         ifIndex
            FROM IF-MIB
         adEShdslInvIndex
            FROM ADTRAN-SHDSL-MIB
         adGenHDSL,
         adGenHDSLID
            FROM ADTRAN-GENHDSL-MIB;

adGenTSCANMIB MODULE-IDENTITY
   LAST-UPDATED "201209050000Z"
   ORGANIZATION "Adtran, Inc."
    CONTACT-INFO
        "CND Tech Support
           Postal: ADTRAN, Inc.
                   901 Explorer Blvd.
                   Huntsville, AL  35806
                   Tel: +1 800 726-8663
                   Fax: +1 256 963 6217
                   E-mail: support@adtran.com"
   DESCRIPTION
      "This MIB defines the objects for the TSCAN MIB."

   REVISION "201209050000Z"
   DESCRIPTION "Added adGenTSCANRepeaterTable and adGenTSCANRepeaterPortTable."

   REVISION "200907300000Z"
   DESCRIPTION "Created"
::= { adGenHDSLID 1 }

    -- OBJECT IDENTIFIERS

        adGenTSCANmg                    OBJECT IDENTIFIER ::= { adGenHDSL 1 }

        adGenTSCANProv                  OBJECT IDENTIFIER ::= { adGenTSCANmg 1 }

        adGenTSCANMibConformance        OBJECT IDENTIFIER ::= { adGenTSCANmg 2 }
        adGenTSCANMibGroups             OBJECT IDENTIFIER ::= { adGenTSCANMibConformance 1 }

        adGenTSCANRepeater              OBJECT IDENTIFIER ::= { adGenTSCANmg 3 }

        --###############################################################
        --                          T S C A N
        --###############################################################

         adGenTSCANProvTable OBJECT-TYPE
             SYNTAX  SEQUENCE OF AdGenTSCANProvEntry
             MAX-ACCESS  not-accessible
             STATUS  current
             DESCRIPTION
                 "The TSCAN Prov table."
            ::= { adGenTSCANProv 1 }

         adGenTSCANProvEntry OBJECT-TYPE
             SYNTAX  AdGenTSCANProvEntry
             MAX-ACCESS  not-accessible
             STATUS  current
             DESCRIPTION
                 "An entry in the TSCAN Provisioning table."
            INDEX   { ifIndex }
            ::= { adGenTSCANProvTable 1 }

         AdGenTSCANProvEntry ::=
             SEQUENCE {
                 adGenTSCANAccumTscanData
                     INTEGER,
                 adGenTSCANTscanDataStatus
                     INTEGER,
                 adGenTSCANECTG1B1
                     DisplayString,
                 adGenTSCANECTG1B2
                     DisplayString,
                 adGenTSCANECTG1B3
                     DisplayString,
                 adGenTSCANECTG1B4
                     DisplayString,
                 adGenTSCANECTG1B5
                     DisplayString,
                 adGenTSCANECTG1B6
                     DisplayString,
                 adGenTSCANECTG1B7
                     DisplayString,
                 adGenTSCANECTG1B8
                     DisplayString,
                 adGenTSCANECTG1B9
                     DisplayString,
                 adGenTSCANECTG2B1
                     DisplayString,
                 adGenTSCANECTG2B2
                     DisplayString,
                 adGenTSCANECTG2B3
                     DisplayString,
                 adGenTSCANECTG2B4
                     DisplayString,
                 adGenTSCANECTG2B5
                     DisplayString,
                 adGenTSCANECTG2B6
                     DisplayString,
                 adGenTSCANECTG2B7
                     DisplayString,
                 adGenTSCANECTG2B8
                     DisplayString,
                 adGenTSCANECTG2B9
                     DisplayString,
                 adGenTSCANECTB1B1
                     DisplayString,
                 adGenTSCANECTB1B2
                     DisplayString,
                 adGenTSCANECTB1B3
                     DisplayString,
                 adGenTSCANECTB1B4
                     DisplayString,
                 adGenTSCANECTB1B5
                     DisplayString,
                 adGenTSCANECTB1B6
                     DisplayString,
                 adGenTSCANECTB1B7
                     DisplayString,
                 adGenTSCANECTB1B8
                     DisplayString,
                 adGenTSCANECTB1B9
                     DisplayString,
                 adGenTSCANECTB2B1
                     DisplayString,
                 adGenTSCANECTB2B2
                     DisplayString,
                 adGenTSCANECTB2B3
                     DisplayString,
                 adGenTSCANECTB2B4
                     DisplayString,
                 adGenTSCANECTB2B5
                     DisplayString,
                 adGenTSCANECTB2B6
                     DisplayString,
                 adGenTSCANECTB2B7
                     DisplayString,
                 adGenTSCANECTB2B8
                     DisplayString,
                 adGenTSCANECTB2B9
                     DisplayString,
                 adGenTSCANST1B
                     DisplayString,
                 adGenTSCANST2B
                     DisplayString,
                 adGenTSCANLS1
                     INTEGER,
                 adGenTSCANLS2
                     INTEGER,
                 adGenTSCANRate
                     INTEGER,
                 adGenTSCANLastTime
                     TimeTicks,
                 adGenTSCANRepeaterIndex
                     INTEGER,
                 adGenTSCANECTB1B10
                     DisplayString,
                 adGenTSCANECTB1B11
                     DisplayString,
                 adGenTSCANECTB1B12
                     DisplayString,
                 adGenTSCANECTB2B10
                     DisplayString,
                 adGenTSCANECTB2B11
                     DisplayString,
                 adGenTSCANECTB2B12
                     DisplayString,
                 adGenTSCANHybridConfig
                     INTEGER,
                 adGenTSCANFullRangeRate
                     Unsigned32
             }

        adGenTSCANAccumTscanData OBJECT-TYPE
                SYNTAX  INTEGER {
                        enable(1)
                        }
                MAX-ACCESS  read-write
                STATUS  current
                DESCRIPTION
                    "Starts the accumulation of the TSCAN data. Always returns 1 on get."
                ::= { adGenTSCANProvEntry 1 }

        adGenTSCANTscanDataStatus OBJECT-TYPE
                SYNTAX  INTEGER {
                        done (1),
                        accumulating (2),
                        idle (3)
                        }
                MAX-ACCESS  read-only
                STATUS  current
                DESCRIPTION
                    "Status of the TSCAN data accumulation process."
                ::= { adGenTSCANProvEntry 2 }

        adGenTSCANECTG1B1 OBJECT-TYPE
                SYNTAX  DisplayString
                MAX-ACCESS  read-only
                STATUS  current
                DESCRIPTION
                    "Block of TG information for L1"
                ::= { adGenTSCANProvEntry 3 }

        adGenTSCANECTG1B2 OBJECT-TYPE
                SYNTAX  DisplayString
                MAX-ACCESS  read-only
                STATUS  current
                DESCRIPTION
                    "Block of TG information for L1"
                ::= { adGenTSCANProvEntry 4 }

        adGenTSCANECTG1B3 OBJECT-TYPE
                SYNTAX  DisplayString
                MAX-ACCESS  read-only
                STATUS  current
                DESCRIPTION
                    "Block of TG information for L1"
                ::= { adGenTSCANProvEntry 5 }

        adGenTSCANECTG1B4 OBJECT-TYPE
                SYNTAX  DisplayString
                MAX-ACCESS  read-only
                STATUS  current
                DESCRIPTION
                    "Block of TG information for L1"
                ::= { adGenTSCANProvEntry 6 }

        adGenTSCANECTG1B5 OBJECT-TYPE
                SYNTAX  DisplayString
                MAX-ACCESS  read-only
                STATUS  current
                DESCRIPTION
                    "Block of TG information for L1"
                ::= { adGenTSCANProvEntry 7 }

        adGenTSCANECTG1B6 OBJECT-TYPE
                SYNTAX  DisplayString
                MAX-ACCESS  read-only
                STATUS  current
                DESCRIPTION
                    "Block of TG information for L1"
                ::= { adGenTSCANProvEntry 8 }

        adGenTSCANECTG1B7 OBJECT-TYPE
                SYNTAX  DisplayString
                MAX-ACCESS  read-only
                STATUS  current
                DESCRIPTION
                    "Block of TG information for L1"
                ::= { adGenTSCANProvEntry 9 }

        adGenTSCANECTG1B8 OBJECT-TYPE
                SYNTAX  DisplayString
                MAX-ACCESS  read-only
                STATUS  current
                DESCRIPTION
                    "Block of TG information for L1"
                ::= { adGenTSCANProvEntry 10 }

        adGenTSCANECTG1B9 OBJECT-TYPE
                SYNTAX  DisplayString
                MAX-ACCESS  read-only
                STATUS  current
                DESCRIPTION
                    "Block of TG information for L1"
                ::= { adGenTSCANProvEntry 11 }

        adGenTSCANECTG2B1 OBJECT-TYPE
                SYNTAX  DisplayString
                MAX-ACCESS  read-only
                STATUS  current
                DESCRIPTION
                    "Block of TG information for L2"
                ::= { adGenTSCANProvEntry 12 }

        adGenTSCANECTG2B2 OBJECT-TYPE
                SYNTAX  DisplayString
                MAX-ACCESS  read-only
                STATUS  current
                DESCRIPTION
                    "Block of TG information for L2"
                ::= { adGenTSCANProvEntry 13 }

        adGenTSCANECTG2B3 OBJECT-TYPE
                SYNTAX  DisplayString
                MAX-ACCESS  read-only
                STATUS  current
                DESCRIPTION
                    "Block of TG information for L2"
                ::= { adGenTSCANProvEntry 14 }

        adGenTSCANECTG2B4 OBJECT-TYPE
                SYNTAX  DisplayString
                MAX-ACCESS  read-only
                STATUS  current
                DESCRIPTION
                    "Block of TG information for L2"
                ::= { adGenTSCANProvEntry 15 }

        adGenTSCANECTG2B5 OBJECT-TYPE
                SYNTAX  DisplayString
                MAX-ACCESS  read-only
                STATUS  current
                DESCRIPTION
                    "Block of TG information for L2"
                ::= { adGenTSCANProvEntry 16 }

        adGenTSCANECTG2B6 OBJECT-TYPE
                SYNTAX  DisplayString
                MAX-ACCESS  read-only
                STATUS  current
                DESCRIPTION
                    "Block of TG information for L2"
                ::= { adGenTSCANProvEntry 17 }

        adGenTSCANECTG2B7 OBJECT-TYPE
                SYNTAX  DisplayString
                MAX-ACCESS  read-only
                STATUS  current
                DESCRIPTION
                    "Block of TG information for L2"
                ::= { adGenTSCANProvEntry 18 }

        adGenTSCANECTG2B8 OBJECT-TYPE
                SYNTAX  DisplayString
                MAX-ACCESS  read-only
                STATUS  current
                DESCRIPTION
                    "Block of TG information for L2"
                ::= { adGenTSCANProvEntry 19 }

        adGenTSCANECTG2B9 OBJECT-TYPE
                SYNTAX  DisplayString
                MAX-ACCESS  read-only
                STATUS  current
                DESCRIPTION
                    "Block of TG information for L2"
                ::= { adGenTSCANProvEntry 20 }

        adGenTSCANECTB1B1 OBJECT-TYPE
                SYNTAX  DisplayString
                MAX-ACCESS  read-only
                STATUS  current
                DESCRIPTION
                    "Block of TB information for L1"
                ::= { adGenTSCANProvEntry 21 }

        adGenTSCANECTB1B2 OBJECT-TYPE
                SYNTAX  DisplayString
                MAX-ACCESS  read-only
                STATUS  current
                DESCRIPTION
                    "Block of TB information for L1"
                ::= { adGenTSCANProvEntry 22 }

        adGenTSCANECTB1B3 OBJECT-TYPE
                SYNTAX  DisplayString
                MAX-ACCESS  read-only
                STATUS  current
                DESCRIPTION
                    "Block of TB information for L1"
                ::= { adGenTSCANProvEntry 23 }

        adGenTSCANECTB1B4 OBJECT-TYPE
                SYNTAX  DisplayString
                MAX-ACCESS  read-only
                STATUS  current
                DESCRIPTION
                    "Block of TB information for L1"
                ::= { adGenTSCANProvEntry 24 }

        adGenTSCANECTB1B5 OBJECT-TYPE
                SYNTAX  DisplayString
                MAX-ACCESS  read-only
                STATUS  current
                DESCRIPTION
                    "Block of TB information for L1"
                ::= { adGenTSCANProvEntry 25 }

        adGenTSCANECTB1B6 OBJECT-TYPE
                SYNTAX  DisplayString
                MAX-ACCESS  read-only
                STATUS  current
                DESCRIPTION
                    "Block of TB information for L1"
                ::= { adGenTSCANProvEntry 26 }

        adGenTSCANECTB1B7 OBJECT-TYPE
                SYNTAX  DisplayString
                MAX-ACCESS  read-only
                STATUS  current
                DESCRIPTION
                    "Block of TB information for L1"
                ::= { adGenTSCANProvEntry 27 }

        adGenTSCANECTB1B8 OBJECT-TYPE
                SYNTAX  DisplayString
                MAX-ACCESS  read-only
                STATUS  current
                DESCRIPTION
                    "Block of TB information for L1"
                ::= { adGenTSCANProvEntry 28 }

        adGenTSCANECTB1B9 OBJECT-TYPE
                SYNTAX  DisplayString
                MAX-ACCESS  read-only
                STATUS  current
                DESCRIPTION
                    "Block of TB information for L1"
                ::= { adGenTSCANProvEntry 29 }

        adGenTSCANECTB2B1 OBJECT-TYPE
                SYNTAX  DisplayString
                MAX-ACCESS  read-only
                STATUS  current
                DESCRIPTION
                    "Block of TB information for L2"
                ::= { adGenTSCANProvEntry 30 }

        adGenTSCANECTB2B2 OBJECT-TYPE
                SYNTAX  DisplayString
                MAX-ACCESS  read-only
                STATUS  current
                DESCRIPTION
                    "Block of TB information for L2"
                ::= { adGenTSCANProvEntry 31}

        adGenTSCANECTB2B3 OBJECT-TYPE
                SYNTAX  DisplayString
                MAX-ACCESS  read-only
                STATUS  current
                DESCRIPTION
                    "Block of TB information for L2"
                ::= { adGenTSCANProvEntry 32 }

        adGenTSCANECTB2B4 OBJECT-TYPE
                SYNTAX  DisplayString
                MAX-ACCESS  read-only
                STATUS  current
                DESCRIPTION
                    "Block of TB information for L2"
                ::= { adGenTSCANProvEntry 33}

        adGenTSCANECTB2B5 OBJECT-TYPE
                SYNTAX  DisplayString
                MAX-ACCESS  read-only
                STATUS  current
                DESCRIPTION
                    "Block of TB information for L2"
                ::= { adGenTSCANProvEntry 34 }

        adGenTSCANECTB2B6 OBJECT-TYPE
                SYNTAX  DisplayString
                MAX-ACCESS  read-only
                STATUS  current
                DESCRIPTION
                    "Block of TB information for L2"
                ::= { adGenTSCANProvEntry 35 }

        adGenTSCANECTB2B7 OBJECT-TYPE
                SYNTAX  DisplayString
                MAX-ACCESS  read-only
                STATUS  current
                DESCRIPTION
                    "Block of TB information for L2"
                ::= { adGenTSCANProvEntry 36 }

        adGenTSCANECTB2B8 OBJECT-TYPE
                SYNTAX  DisplayString
                MAX-ACCESS  read-only
                STATUS  current
                DESCRIPTION
                    "Block of TB information for L2"
                ::= { adGenTSCANProvEntry 37 }

        adGenTSCANECTB2B9 OBJECT-TYPE
                SYNTAX  DisplayString
                MAX-ACCESS  read-only
                STATUS  current
                DESCRIPTION
                    "Block of TB information for L2"
                ::= { adGenTSCANProvEntry 38 }

        adGenTSCANST1B OBJECT-TYPE
                SYNTAX  DisplayString
                MAX-ACCESS  read-only
                STATUS  current
                DESCRIPTION
                    "ST information for L1"
                ::= { adGenTSCANProvEntry 39 }

        adGenTSCANST2B OBJECT-TYPE
                SYNTAX  DisplayString
                MAX-ACCESS  read-only
                STATUS  current
                DESCRIPTION
                    "ST information for L2"
                ::= { adGenTSCANProvEntry 40 }

        adGenTSCANLS1 OBJECT-TYPE
                SYNTAX  INTEGER {
                        invalid (1),
                        complete (2)
                        }
                MAX-ACCESS  read-only
                STATUS  current
                DESCRIPTION
                    "Status of current TSCAN data on L1."
                ::= { adGenTSCANProvEntry 41 }

        adGenTSCANLS2 OBJECT-TYPE
                SYNTAX  INTEGER {
                        invalid (1),
                        complete (2)
                        }
                MAX-ACCESS  read-only
                STATUS  current
                DESCRIPTION
                    "Status of current TSCAN data on L2."
                ::= { adGenTSCANProvEntry 42 }

        adGenTSCANRate OBJECT-TYPE
                SYNTAX  INTEGER {
                        sixteenDS0s(1),
                        thirtytwoDS0s(2)
                        }
                MAX-ACCESS  read-write
                STATUS  current
                DESCRIPTION
                    "Provisions the rate that TSCAN will run.  Currently,
                     this applies to SHDSL only.  The default is 32."
                ::= { adGenTSCANProvEntry 43 }

        adGenTSCANLastTime OBJECT-TYPE
                SYNTAX  TimeTicks
                MAX-ACCESS  read-only
                STATUS  current
                DESCRIPTION
                    "Timestamp of last valid results for TScan."
                ::= { adGenTSCANProvEntry 44 }

        adGenTSCANRepeaterIndex OBJECT-TYPE
                SYNTAX  INTEGER {
                        htuc(1),
                        hre1(2),
                        hre2(3),
                        hre3(4)
                        }
                MAX-ACCESS  read-write
                STATUS  current
                DESCRIPTION
                    "Provisions the HTUC or repeater that operation will
                     be performed on.  Only valid for hdsl4."
                ::= { adGenTSCANProvEntry 45 }
        adGenTSCANECTB1B10 OBJECT-TYPE
                SYNTAX  DisplayString
                MAX-ACCESS  read-only
                STATUS  current
                DESCRIPTION
                    "Block of TB information for L1"
                ::= { adGenTSCANProvEntry 46 }
        adGenTSCANECTB1B11 OBJECT-TYPE
                SYNTAX  DisplayString
                MAX-ACCESS  read-only
                STATUS  current
                DESCRIPTION
                    "Block of TB information for L1"
                ::= { adGenTSCANProvEntry 47 }
        adGenTSCANECTB1B12 OBJECT-TYPE
                SYNTAX  DisplayString
                MAX-ACCESS  read-only
                STATUS  current
                DESCRIPTION
                    "Block of TB information for L1"
                ::= { adGenTSCANProvEntry 48 }
        adGenTSCANECTB2B10 OBJECT-TYPE
                SYNTAX  DisplayString
                MAX-ACCESS  read-only
                STATUS  current
                DESCRIPTION
                    "Block of TB information for L2"
                ::= { adGenTSCANProvEntry 49 }
        adGenTSCANECTB2B11 OBJECT-TYPE
                SYNTAX  DisplayString
                MAX-ACCESS  read-only
                STATUS  current
                DESCRIPTION
                    "Block of TB information for L2"
                ::= { adGenTSCANProvEntry 50 }
        adGenTSCANECTB2B12 OBJECT-TYPE
                SYNTAX  DisplayString
                MAX-ACCESS  read-only
                STATUS  current
                DESCRIPTION
                    "Block of TB information for L2"
                ::= { adGenTSCANProvEntry 51 }
        adGenTSCANHybridConfig OBJECT-TYPE
                SYNTAX  INTEGER {
                        enabled(1),
                        disabled(2)
                        }
                MAX-ACCESS  read-write
                STATUS  current
                DESCRIPTION
                    "Enabled connects the hybrid during TSCAN,
                     disabled disconnects the hybrid during TSCAN."
                ::= { adGenTSCANProvEntry 52 }
        adGenTSCANFullRangeRate OBJECT-TYPE
                SYNTAX  Unsigned32
                MAX-ACCESS  read-write
                STATUS  current
                DESCRIPTION
                    "Provisions the rate in DS0s that TSCAN will run.
                     Currently, this applies to SHDSL only.  The default
                     is 32. Allows any valid rate to be set."
                ::= { adGenTSCANProvEntry 53 }


        --###############################################################
        --            R E P E A T E R  T S C A N
        --###############################################################

         adGenTSCANRepeaterTable OBJECT-TYPE
             SYNTAX  SEQUENCE OF AdGenTSCANRepeaterEntry
             MAX-ACCESS  not-accessible
             STATUS  current
             DESCRIPTION
                 "The TSCAN Repeater table."
            ::= { adGenTSCANRepeater 1 }

         adGenTSCANRepeaterEntry OBJECT-TYPE
             SYNTAX  AdGenTSCANRepeaterEntry
             MAX-ACCESS  not-accessible
             STATUS  current
             DESCRIPTION
                 "An entry in the TSCAN Repeater table.  This table is used to initiate
                  and report results on repeaters in the circuit.  Currently, this is only
                  for use with SHDSL repeaters."
            INDEX   { ifIndex, adEShdslInvIndex }
            ::= { adGenTSCANRepeaterTable 1 }

         AdGenTSCANRepeaterEntry ::=
             SEQUENCE {
                 adGenTSCANRepeaterStart
                     INTEGER,
                 adGenTSCANRepeaterStatus
                     INTEGER,
                 adGenTSCANRepeaterLastTestCompleted
                     DisplayString,
                 adGenTSCANRepeaterFault
                     INTEGER,
                 adGenTSCANRepeaterDistanceInFeet
                     Integer32,
                 adGenTSCANRepeaterDistanceInMeters
                     Integer32,
                 adGenTSCANRepeaterRate
                     Integer32
             }

        adGenTSCANRepeaterStart OBJECT-TYPE
                SYNTAX  INTEGER {
                        enable(1)
                        }
                MAX-ACCESS  read-write
                STATUS  current
                DESCRIPTION
                    "Starts the accumulation of the TSCAN data. Always returns 1 on get."
                ::= { adGenTSCANRepeaterEntry 1 }

        adGenTSCANRepeaterStatus OBJECT-TYPE
                SYNTAX  INTEGER {
                        done(1),
                        accumulatingData(2),
                        idle(3),
                        error(4)
                        }
                MAX-ACCESS  read-only
                STATUS  current
                DESCRIPTION
                    "Returns the TSCAN status of the selected repeater."
                ::= { adGenTSCANRepeaterEntry 2 }

        adGenTSCANRepeaterLastTestCompleted OBJECT-TYPE
                SYNTAX  DisplayString
                MAX-ACCESS  read-only
                STATUS  current
                DESCRIPTION
                    "Returns the date/time of the last test ran in a MM/DD/YYYY HH:MM:SS format."
                ::= { adGenTSCANRepeaterEntry 3 }

        adGenTSCANRepeaterFault OBJECT-TYPE
                SYNTAX  INTEGER {
                        unknown(0),
                        open(1),
                        short(2),
                        gfi(3),
                        singleOpen(4),
                        ok(5)
                        }
                MAX-ACCESS  read-only
                STATUS  current
                DESCRIPTION
                    "Returns the fault found during the last test."
                ::= { adGenTSCANRepeaterEntry 4 }

        adGenTSCANRepeaterDistanceInFeet OBJECT-TYPE
                SYNTAX  Integer32
                MAX-ACCESS  read-only
                STATUS  current
                DESCRIPTION
                    "Returns the distance, in feet, of the fault found in the last test."
                ::= { adGenTSCANRepeaterEntry 5 }

        adGenTSCANRepeaterDistanceInMeters OBJECT-TYPE
                SYNTAX  Integer32
                MAX-ACCESS  read-only
                STATUS  current
                DESCRIPTION
                    "Returns the distance, in meters, of the fault found in the last test."
                ::= { adGenTSCANRepeaterEntry 6 }

        adGenTSCANRepeaterRate OBJECT-TYPE
                SYNTAX  Integer32
                MAX-ACCESS  read-only
                STATUS  current
                DESCRIPTION
                    "Returns the SHDSL training rate, in DS0s, used in the last test."
                ::= { adGenTSCANRepeaterEntry 7 }



        --###############################################################
         adGenTSCANRepeaterPortTable OBJECT-TYPE
             SYNTAX  SEQUENCE OF AdGenTSCANRepeaterPortEntry
             MAX-ACCESS  not-accessible
             STATUS  current
             DESCRIPTION
                 "The TSCAN Repeater Port table."
            ::= { adGenTSCANRepeater 2 }

         adGenTSCANRepeaterPortEntry OBJECT-TYPE
             SYNTAX  AdGenTSCANRepeaterPortEntry
             MAX-ACCESS  not-accessible
             STATUS  current
             DESCRIPTION
                 "An entry in the TSCAN Repeater Port table.  This table is used to control
                  and/or report port level information related to running TSCAN on a repeater."
            INDEX   { ifIndex }

            ::= { adGenTSCANRepeaterPortTable 1 }

         AdGenTSCANRepeaterPortEntry ::=
             SEQUENCE {
                 adGenTSCANRepeaterPortLastErrorString
                     DisplayString
             }

        adGenTSCANRepeaterPortLastErrorString OBJECT-TYPE
                SYNTAX  DisplayString
                MAX-ACCESS  read-write
                STATUS  current
                DESCRIPTION
                    "Returns the last error encountered when attempting to initiate a TSCAN test
                     on a repeater."
                ::= { adGenTSCANRepeaterPortEntry 1 }


-- ******************************************************************************************
-- MIB Groups
-- ******************************************************************************************
adGenTSCANGroup OBJECT-GROUP
   OBJECTS
   {
        adGenTSCANAccumTscanData,
        adGenTSCANTscanDataStatus,
        adGenTSCANECTG1B1,
        adGenTSCANECTG1B2,
        adGenTSCANECTG1B3,
        adGenTSCANECTG1B4,
        adGenTSCANECTG1B5,
        adGenTSCANECTG1B6,
        adGenTSCANECTG1B7,
        adGenTSCANECTG1B8,
        adGenTSCANECTG1B9,
        adGenTSCANECTG2B1,
        adGenTSCANECTG2B2,
        adGenTSCANECTG2B3,
        adGenTSCANECTG2B4,
        adGenTSCANECTG2B5,
        adGenTSCANECTG2B6,
        adGenTSCANECTG2B7,
        adGenTSCANECTG2B8,
        adGenTSCANECTG2B9,
        adGenTSCANECTB1B1,
        adGenTSCANECTB1B2,
        adGenTSCANECTB1B3,
        adGenTSCANECTB1B4,
        adGenTSCANECTB1B5,
        adGenTSCANECTB1B6,
        adGenTSCANECTB1B7,
        adGenTSCANECTB1B8,
        adGenTSCANECTB1B9,
        adGenTSCANECTB2B1,
        adGenTSCANECTB2B2,
        adGenTSCANECTB2B3,
        adGenTSCANECTB2B4,
        adGenTSCANECTB2B5,
        adGenTSCANECTB2B6,
        adGenTSCANECTB2B7,
        adGenTSCANECTB2B8,
        adGenTSCANECTB2B9,
        adGenTSCANST1B,
        adGenTSCANST2B,
        adGenTSCANLS1,
        adGenTSCANLS2,
        adGenTSCANRate,
        adGenTSCANLastTime,
        adGenTSCANRepeaterIndex,
        adGenTSCANECTB1B10,
        adGenTSCANECTB1B11,
        adGenTSCANECTB1B12,
        adGenTSCANECTB2B10,
        adGenTSCANECTB2B11,
        adGenTSCANECTB2B12,
        adGenTSCANHybridConfig,
        adGenTSCANFullRangeRate
   }
   STATUS current
   DESCRIPTION
     "These objects provide support for TSCAN."
   ::= { adGenTSCANMibGroups 1 }


        END

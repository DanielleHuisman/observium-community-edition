ADTRAN-SHARED-ADSL2-MIB

-- TITLE:     The ADTRAN ADSL2 IDENTITY MIB
-- PRODUCT:   ADTRAN ADSL2 PRODUCTS
-- VERSION:   1.0
-- DATE:      10/25/2011
-- AUTHOR:    Craye Hall
-- STATUS:    PRELIMINARY

-- This MIB defines the object identifier (OID) for the
-- ADTRAN SHARED ADSL2 MIB objects

-- HISTORY:
-- 10/25/2011 och STATUS: PRELIMINARY.

-- ******************************************************************************************

DEFINITIONS ::= BEGIN

    IMPORTS
        adShared,
        adIdentityShared
            FROM ADTRAN-MIB
        MODULE-IDENTITY
            FROM SNMPv2-SMI
        ;

adAdsl2Identity MODULE-IDENTITY
   LAST-UPDATED "201110250000Z"
   ORGANIZATION "Adtran, Inc."
   CONTACT-INFO "http://www.adtran.com"
   DESCRIPTION
      "This MIB defines the objects for the ADSL2 MIB."
   REVISION "201110250000Z"
   DESCRIPTION "Created"
::= { adIdentityShared 82 }


adAdsl2         OBJECT IDENTIFIER ::= { adShared 82 }

adGenAdsl2      OBJECT IDENTIFIER ::= { adAdsl2 1}
adGenAdsl2ID    OBJECT IDENTIFIER ::= { adAdsl2Identity 1 }

END

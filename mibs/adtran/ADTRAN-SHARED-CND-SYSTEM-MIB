ADTRAN-SHARED-CND-SYSTEM-MIB

-- TITLE:     The ADTRAN CND SYSTEM IDENTITY MIB
-- PRODUCT:   SYSTEM Level Support
-- VERSION:   1.1
-- DATE:      4/13/2010
-- AUTHOR:    Joey Boyd
-- STATUS:    CURRENT

-- This MIB defines the object identifier (OID) for the
-- ADTRAN SHARED CND SYSTEM MIB objects

-- HISTORY:
-- 2008/05/01 jlb - STATUS: PRELIMINARY.
-- 2008/09/30 jlb - Added adGenNtp and adGenNtpID
-- 2008/10/03 jlb - Added adGenCndSystemCompliance, adGenSystemProductCompliance, adGenEthernetDslamFlowCompliance
--                  adGenIPTVCompliance, adGenPluggablePortCompliance, and adGenNtpCompliance
-- 2008/10/03 jlb - Changed adGenCndSystemCompliance to use adComplianceShared 70 instead of 77
-- 2008/11/04 rjf - Added adGenSystemProductMg for use in genSystems mib
-- 2008/12/10 jlb - Added adGenMac, dGenMacID, and adGenMacCompliance
-- 2009/01/20 jlb - Added adGenEgressQueue, dGenEgressQueueID, and adGenEgressQueueCompliance
-- 2009/02/05 jlb - Added adGenEVC, dGenEVCID, and adGenEVCCompliance
-- 2009/03/02 rmz - Added adGenIGMPCache, adGenIGMPCacheID, and adGenIGMPCacheCompliance
-- 2009/03/09 jlb - Added adGenSubtendedHost, adGenSubtendedHostID, and adGenSubtendedHostCompliance.
-- 2009/03/09 jlb - SMIC verified.
-- 2009/03/26 aed - Added adGenSystemTiming, adGenSystemTimingID, and adGenSystemTimingCompliance
-- 2009/03/26 aed - Added adGenSystemTC, adGenSystemTCID, and adGenSystemTCCompliance
-- 2009/04/29 jlb - Added adGenIGMP, dGenIGMPID, and adGenIGMPCompliance
-- 2009/05/01 jlb - Added adGen802dot1x, dGen802dot1xID, and adGen802dot1xCompliance
-- 2009/06/17 sgs - Added adGenIpHost, adGenIpHostID, and adGenIpHostCompliance.
-- 2009/09/03 jlb - Added adGenShaper, adGenShaperID, and adGenShaperCompliance.
-- 2009/10/20 psk - Added adGenVoip, adGenVoipID, adGenVoipCompliance, adGenSip, adGenSipID and adGenSipCompliance.
-- 2010/02/22 jlb - Added adGenProcesses, adGenProcessesID, and adGenProcessesCompliance
-- 2010/04/13 gdo - Added adGenPerformanceMonitoring, adGenPerformanceMonitoringID,
--					and adGenPerformanceMonitoringCompliance
-- 2010/04/29 tgc - Added adGenEZProv, adGenEZProvID, and adGenEZProvCompliance for B. Young
-- 2010/05/19 a s - Added adGenSonet, adGenSonetID, and adGenSonetCompliance
-- 2010/05/24 a s - Added adGenMuxPonder, adGenMuxPonderID, and adGenMuxPonderCompliance
-- 2010/06/07 a s - Added adGenMEVC and adGenEVCMap
-- 2010/06/11  cb - Added adGenFrameRelay, adGenFrameRelayID, and adGenFrameRelayCompliance
-- 2010/07/19 a s - Added adGenTa5kPseudowireCEMMgmt, adGenTa5kPseudowireCEMMgmtID,
--                  and adGenTa5kPseudowireCEMMgmtCompliance
-- 2010/07/20 a s - removed "Ta5k" char from the Pseudowire items.
-- 2010/07/27 rmz - Added adGenIPTVR2, adGenIPTVR2ID, and adGenIPTVR2Compliance
-- 2010/08/13 a s - Added adGenPacketTiming, adGenPacketTimingID, and adGenPacketTimingCompliance
-- 2010/08/30 jlb - Added adGenRemoteDownload, adGenRemoteDownloadID, and adGenRemoteDownloadCompliance
-- 2010/09/15 a s - Added adGenQoS, adGenQoSID, and adGenQoSCompliance
-- 2010/09/15 a s - Added adGenPolicer, adGenPolicerID, and adGenPolicerCompliance
-- 2010/09/16 a s - Updated adGenQoS to genMuxponderQoS
-- 2010/11/05 a s - Added adGenMEgressQueue, adGenMEgressQueueID, and adGenMEgressQueueCompliance
-- 2010/12/20 glf - Added adGenIPVclSubIfc,adGenIPVclSubIfcID, and adGenIPVclSubIfcCompliance
-- 2011/02/07 glf - Rename adGenIPVclSubIfc,adGenIPVclSubIfcID, and adGenIPVclSubIfcCompliance to
--                  adGenSysMgmtFac, adGenSysMgmtFacID, and adGenSysMgmtFacCompliance.
-- 2011/02/11 psk - Added adGenFxo,adGenFxoID, and adGenFxoCompliance
-- 2011/03/09 aed - Revision information should be added to the Module Identity definition.
--                  DO NOT ADD REVISION INFORMATION HERE.
-- ******************************************************************************************

DEFINITIONS ::= BEGIN

    IMPORTS
        adShared,
        adIdentityShared,
        adComplianceShared
            FROM ADTRAN-MIB
        MODULE-IDENTITY
            FROM SNMPv2-SMI
        ;

adGenCndSystemIdentity MODULE-IDENTITY
   LAST-UPDATED "201712150000Z"
   ORGANIZATION "Adtran, Inc."
   CONTACT-INFO
     "CND Tech Support
         Postal: ADTRAN, Inc.
                 901 Explorer Blvd.
                 Huntsville, AL  35806
                 Tel: +1 800 726 8663
                 Fax: +1 256 963 6217
                 E-mail: support@adtran.com"
   DESCRIPTION
      "This MIB defines the objects for the GenCndSystem MIB."

   REVISION "201712150000Z"
   DESCRIPTION "Added adGenMonitorSession and adGenMonitorSessionID"
  
   REVISION "201504150000Z"
   DESCRIPTION "Added adGenLag and adGenLagID"

   REVISION "201410130000Z"
   DESCRIPTION "Added adGenAutoConfig and adGenAutoConfigID"

   REVISION "201312160000Z"
   DESCRIPTION "Add adAOEControlledFeature, and adAOEControlledFeatureID"

   REVISION "201309300000Z"
   DESCRIPTION "Added adGenVector"

   REVISION "201309040000Z"
   DESCRIPTION "Added adGenVoiceUserMgmt, adGenVoiceUserMgmtID and adGenVoiceUserMgmtCompliance"

   REVISION "201306030000Z"
   DESCRIPTION "Added adGenRadiusAuth, adGenRadiusAuthID and adGenRadiusAuthCompliance"

   REVISION "201305230000Z"
   DESCRIPTION "Added adGenMgcp, adGenMgcpID, and adGenMgcpCompliance"

   REVISION "201205020000Z"
   DESCRIPTION "Added adGenOneProtGroup, adGenOneProtGroupID and adGenOneProtGroupCompliance"

   REVISION "201204040000Z"
   DESCRIPTION "Added adGenFibreChannel and adGenFibreChannelID"

   REVISION "201202290000Z"
   DESCRIPTION "Added adGenEthLbk and adGenEthLbkID"

   REVISION "201202080000Z"
   DESCRIPTION "Added ADTRAN-GEN-2544-MIB"

   REVISION "201112280000Z"
   DESCRIPTION "Added adGenAtm, adGenAtmID, and adGenAtmCompliance"

   REVISION "201110260000Z"
   DESCRIPTION  "Added adGenPeerAdjacency, adGenPeerAdjacencyID and adGenPeerAdjacencyCompliance"

   REVISION "201110100000Z"
   DESCRIPTION  "Added adGenLldp, adGenLldpID and adGenLldpCompliance"

   REVISION "201109300000Z"
   DESCRIPTION  "Added adGenPhysicalPeer, adGenPhysicalPeerID and adGenPhysicalPeerCompliance"

   REVISION "201109200000Z"
   DESCRIPTION  "Added adGenOtn, adGenOtnID and adGenOtnCompliance"

   REVISION "201109100000Z"
   DESCRIPTION  "Added adGenOpticalADM, adGenOpticalADMID and adGenOpticalADMCompliance"

   REVISION "201105230000Z"
   DESCRIPTION  "Added adGenOpticalDCM and adGenOpticalDCMID and adGenOpticalDCMCompliance"

   REVISION "201104110000Z"
   DESCRIPTION  "Added adGenOpticalAmplifier and adGenOpticalAmplifierID and adGenOpticalAmplifierCompliance"

   REVISION "201103290000Z"
   DESCRIPTION  "Added adGenVlan and adGenVlanID"

   REVISION "201103170000Z"
   DESCRIPTION  "Added adGenOpticalCarrier and adGenOpticalCarrierID and adGenOpticalCarrierCompliance"

   REVISION "201103090000Z"
   DESCRIPTION  "Added adGenWebGui and adGenWebGuiID"

   REVISION "201004130000Z"
   DESCRIPTION "gdo - Added adGenPerformanceMonitoring, adGenPerformanceMonitoringID,
				and adGenPerformanceMonitoringCompliance"

   REVISION "201002220000Z"
   DESCRIPTION "jlb - Added adGenProcesses, adGenProcessesID, and adGenProcessesCompliance"

   REVISION "200805010000Z"
   DESCRIPTION "Created"
::= { adIdentityShared 70 }

adGenCndSystem                          OBJECT IDENTIFIER ::= { adShared 70 }
adGenCndSystemCompliance                OBJECT IDENTIFIER ::= { adComplianceShared 70 }

adGenSystemProduct                      OBJECT IDENTIFIER ::= { adGenCndSystem 1 }
adGenSystemProductID                    OBJECT IDENTIFIER ::= { adGenCndSystemIdentity 1 }
adGenSystemProductCompliance            OBJECT IDENTIFIER ::= { adGenCndSystemCompliance 1 }

adGenEthernetDslamFlow                  OBJECT IDENTIFIER ::= { adGenCndSystem 2 }
adGenEthernetDslamFlowID                OBJECT IDENTIFIER ::= { adGenCndSystemIdentity 2 }
adGenEthernetDslamFlowCompliance        OBJECT IDENTIFIER ::= { adGenCndSystemCompliance 2 }

adGenIPTV                               OBJECT IDENTIFIER ::= { adGenCndSystem 3 }
adGenIPTVID                             OBJECT IDENTIFIER ::= { adGenCndSystemIdentity 3 }
adGenIPTVCompliance                     OBJECT IDENTIFIER ::= { adGenCndSystemCompliance 3 }

adGenPluggablePort                      OBJECT IDENTIFIER ::= { adGenCndSystem 4 }
adGenPluggablePortID                    OBJECT IDENTIFIER ::= { adGenCndSystemIdentity 4 }
adGenPluggablePortCompliance            OBJECT IDENTIFIER ::= { adGenCndSystemCompliance 4 }

adGenNtp                                OBJECT IDENTIFIER ::= { adGenCndSystem 5 }
adGenNtpID                              OBJECT IDENTIFIER ::= { adGenCndSystemIdentity 5 }
adGenNtpCompliance                      OBJECT IDENTIFIER ::= { adGenCndSystemCompliance 5 }

-- This branch is added here, extending the adGenSystemProduct branch in an unconventional
-- manner due to the way it was originally used (locked-out) within the genSystems.mi2 mib,
-- which prevented child branches from being defined.  This will allow us to easily extend
-- this branch now and in the future.
adGenSystemProductMg                    OBJECT IDENTIFIER ::= { adGenCndSystem 6 }

adGenIf                                	OBJECT IDENTIFIER ::= { adGenCndSystem 7 }
adGenIfID                              	OBJECT IDENTIFIER ::= { adGenCndSystemIdentity 7 }
adGenIfCompliance                      	OBJECT IDENTIFIER ::= { adGenCndSystemCompliance 7 }

adGenMac                                OBJECT IDENTIFIER ::= { adGenCndSystem 8 }
adGenMacID                              OBJECT IDENTIFIER ::= { adGenCndSystemIdentity 8 }
adGenMacCompliance                      OBJECT IDENTIFIER ::= { adGenCndSystemCompliance 8 }

adGenEgressQueue                        OBJECT IDENTIFIER ::= { adGenCndSystem 9 }
adGenEgressQueueID                      OBJECT IDENTIFIER ::= { adGenCndSystemIdentity 9 }
adGenEgressQueueCompliance              OBJECT IDENTIFIER ::= { adGenCndSystemCompliance 9 }

adGenEVC                                OBJECT IDENTIFIER ::= { adGenCndSystem 10 }
adGenEVCID                              OBJECT IDENTIFIER ::= { adGenCndSystemIdentity 10 }
adGenEVCCompliance                      OBJECT IDENTIFIER ::= { adGenCndSystemCompliance 10 }

adGenIGMPCache                          OBJECT IDENTIFIER ::= { adGenCndSystem 11 }
adGenIGMPCacheID                        OBJECT IDENTIFIER ::= { adGenCndSystemIdentity 11 }
adGenIGMPCacheCompliance                OBJECT IDENTIFIER ::= { adGenCndSystemCompliance 11 }

adGenSubtendedHost                      OBJECT IDENTIFIER ::= { adGenCndSystem 12 }
adGenSubtendedHostID                    OBJECT IDENTIFIER ::= { adGenCndSystemIdentity 12 }
adGenSubtendedHostCompliance            OBJECT IDENTIFIER ::= { adGenCndSystemCompliance 12 }

adGenSystemTiming                       OBJECT IDENTIFIER ::= { adGenCndSystem 13 }
adGenSystemTimingID                     OBJECT IDENTIFIER ::= { adGenCndSystemIdentity 13 }
adGenSystemTimingCompliance             OBJECT IDENTIFIER ::= { adGenCndSystemCompliance 13 }

adGenSystemTC                           OBJECT IDENTIFIER ::= { adGenCndSystem 14 }
adGenSystemTCID                         OBJECT IDENTIFIER ::= { adGenCndSystemIdentity 14 }
adGenSystemTCCompliance                 OBJECT IDENTIFIER ::= { adGenCndSystemCompliance 14 }

adGenEthIfc                             OBJECT IDENTIFIER ::= { adGenCndSystem 15 }
adGenEthIfcID                           OBJECT IDENTIFIER ::= { adGenCndSystemIdentity 15 }
adGenEthIfcCompliance                   OBJECT IDENTIFIER ::= { adGenCndSystemCompliance 15 }

adGenIGMP                               OBJECT IDENTIFIER ::= { adGenCndSystem 16 }
adGenIGMPID                             OBJECT IDENTIFIER ::= { adGenCndSystemIdentity 16 }
adGenIGMPCompliance                     OBJECT IDENTIFIER ::= { adGenCndSystemCompliance 16 }

adGen802dot1x                           OBJECT IDENTIFIER ::= { adGenCndSystem 17 }
adGen802dot1xID                         OBJECT IDENTIFIER ::= { adGenCndSystemIdentity 17 }
adGen802dot1xCompliance                 OBJECT IDENTIFIER ::= { adGenCndSystemCompliance 17 }

adGenIpHost                      		OBJECT IDENTIFIER ::= { adGenCndSystem 18 }
adGenIpHostID                    		OBJECT IDENTIFIER ::= { adGenCndSystemIdentity 18 }
adGenIpHostCompliance            		OBJECT IDENTIFIER ::= { adGenCndSystemCompliance 18 }

adGenShaper                      		OBJECT IDENTIFIER ::= { adGenCndSystem 19 }
adGenShaperID                    		OBJECT IDENTIFIER ::= { adGenCndSystemIdentity 19 }
adGenShaperCompliance            		OBJECT IDENTIFIER ::= { adGenCndSystemCompliance 19 }

adGenVoip                               OBJECT IDENTIFIER ::= { adGenCndSystem 20 }
adGenVoipID                             OBJECT IDENTIFIER ::= { adGenCndSystemIdentity 20 }
adGenVoipCompliance                     OBJECT IDENTIFIER ::= { adGenCndSystemCompliance 20 }

adGenSip                                OBJECT IDENTIFIER ::= { adGenCndSystem 21 }
adGenSipID                              OBJECT IDENTIFIER ::= { adGenCndSystemIdentity 21 }
adGenSipCompliance                      OBJECT IDENTIFIER ::= { adGenCndSystemCompliance 21 }

adGenProcesses                          OBJECT IDENTIFIER ::= { adGenCndSystem 22 }
adGenProcessesID                        OBJECT IDENTIFIER ::= { adGenCndSystemIdentity 22 }
adGenProcessesCompliance                OBJECT IDENTIFIER ::= { adGenCndSystemCompliance 22 }

adGenPerformanceMonitoring              OBJECT IDENTIFIER ::= { adGenCndSystem 23 }
adGenPerformanceMonitoringID            OBJECT IDENTIFIER ::= { adGenCndSystemIdentity 23 }
adGenPerformanceMonitoringCompliance    OBJECT IDENTIFIER ::= { adGenCndSystemCompliance 23 }

adGenEZProv                             OBJECT IDENTIFIER ::= { adGenCndSystem 24 }
adGenEZProvID                           OBJECT IDENTIFIER ::= { adGenCndSystemIdentity 24 }
adGenEZProvCompliance                   OBJECT IDENTIFIER ::= { adGenCndSystemCompliance 24 }

adGenSonet                              OBJECT IDENTIFIER ::= { adGenCndSystem 25 }
adGenSonetID                            OBJECT IDENTIFIER ::= { adGenCndSystemIdentity 25 }
adGenSonetCompliance                    OBJECT IDENTIFIER ::= { adGenCndSystemCompliance 25 }

adGenMuxPonder                          OBJECT IDENTIFIER ::= { adGenCndSystem 26 }
adGenMuxPonderID                        OBJECT IDENTIFIER ::= { adGenCndSystemIdentity 26 }
adGenMuxPonderCompliance                OBJECT IDENTIFIER ::= { adGenCndSystemCompliance 26 }

adGenMEVC                               OBJECT IDENTIFIER ::= { adGenCndSystem 27 }
adGenMEVCID                             OBJECT IDENTIFIER ::= { adGenCndSystemIdentity 27 }
adGenMEVCCompliance                     OBJECT IDENTIFIER ::= { adGenCndSystemCompliance 27 }

adGenEVCMap                             OBJECT IDENTIFIER ::= { adGenCndSystem 28 }
adGenEVCMapID                           OBJECT IDENTIFIER ::= { adGenCndSystemIdentity 28 }
adGenEVCMapCompliance                   OBJECT IDENTIFIER ::= { adGenCndSystemCompliance 28 }

adGenFrameRelay                         OBJECT IDENTIFIER ::= { adGenCndSystem 29 }
adGenFrameRelayID                       OBJECT IDENTIFIER ::= { adGenCndSystemIdentity 29 }
adGenFrameRelayCompliance               OBJECT IDENTIFIER ::= { adGenCndSystemCompliance 29 }

adGenPseudowireCEMMgmt                  OBJECT IDENTIFIER ::= { adGenCndSystem 30 }
adGenPseudowireCEMMgmtID                OBJECT IDENTIFIER ::= { adGenCndSystemIdentity 30 }
adGenPseudowireCEMMgmtCompliance        OBJECT IDENTIFIER ::= { adGenCndSystemCompliance 30 }

adGenIPTVR2                             OBJECT IDENTIFIER ::= { adGenCndSystem 31 }
adGenIPTVR2ID                           OBJECT IDENTIFIER ::= { adGenCndSystemIdentity 31 }
adGenIPTVR2Compliance                   OBJECT IDENTIFIER ::= { adGenCndSystemCompliance 31 }

adGenPacketTiming		        OBJECT IDENTIFIER ::= { adGenCndSystem 32 }
adGenPacketTimingID                	OBJECT IDENTIFIER ::= { adGenCndSystemIdentity 32 }
adGenPacketTimingCompliance        	OBJECT IDENTIFIER ::= { adGenCndSystemCompliance 32 }

adGenRemoteDownload		        OBJECT IDENTIFIER ::= { adGenCndSystem 33 }
adGenRemoteDownloadID                	OBJECT IDENTIFIER ::= { adGenCndSystemIdentity 33 }
adGenRemoteDownloadCompliance        	OBJECT IDENTIFIER ::= { adGenCndSystemCompliance 33 }

adGenMuxponderQoS     		        OBJECT IDENTIFIER ::= { adGenCndSystem 34 }
adGenMuxponderQoSID                	OBJECT IDENTIFIER ::= { adGenCndSystemIdentity 34 }
adGenMuxponderQoSCompliance        	OBJECT IDENTIFIER ::= { adGenCndSystemCompliance 34 }

adGenPolicer     		        OBJECT IDENTIFIER ::= { adGenCndSystem 35 }
adGenPolicerID                	        OBJECT IDENTIFIER ::= { adGenCndSystemIdentity 35 }
adGenPolicerCompliance        	        OBJECT IDENTIFIER ::= { adGenCndSystemCompliance 35 }

adGenMEgressQueue                        OBJECT IDENTIFIER ::= { adGenCndSystem 36 }
adGenMEgressQueueID                      OBJECT IDENTIFIER ::= { adGenCndSystemIdentity 36 }
adGenMEgressQueueCompliance              OBJECT IDENTIFIER ::= { adGenCndSystemCompliance 36 }

adGenSysMgmtFac                        OBJECT IDENTIFIER ::= { adGenCndSystem 37 }
adGenSysMgmtFacID                      OBJECT IDENTIFIER ::= { adGenCndSystemIdentity 37 }
adGenSysMgmtFacCompliance              OBJECT IDENTIFIER ::= { adGenCndSystemCompliance 37 }

adGenFxo                                OBJECT IDENTIFIER ::= { adGenCndSystem 38 }
adGenFxoID                              OBJECT IDENTIFIER ::= { adGenCndSystemIdentity 38 }
adGenFxoCompliance                      OBJECT IDENTIFIER ::= { adGenCndSystemCompliance 38 }

adGenVlan                               OBJECT IDENTIFIER ::= { adGenCndSystem 39 }
adGenVlanID                             OBJECT IDENTIFIER ::= { adGenCndSystemIdentity 39 }

adGenOpticalCarrier                     OBJECT IDENTIFIER ::= { adGenCndSystem 40 }
adGenOpticalCarrierID                   OBJECT IDENTIFIER ::= { adGenCndSystemIdentity 40 }
adGenOpticalCarrierCompliance           OBJECT IDENTIFIER ::= { adGenCndSystemCompliance 40 }

adGenOpticalAmplifier                       OBJECT IDENTIFIER ::= { adGenCndSystem 41 }
adGenOpticalAmplifierID                     OBJECT IDENTIFIER ::= { adGenCndSystemIdentity 41 }
adGenOpticalAmplifierIDCompliance     OBJECT IDENTIFIER ::= { adGenCndSystemCompliance 41 }

adGenOpticalDCM                       OBJECT IDENTIFIER ::= { adGenCndSystem 42 }
adGenOpticalDCMID                     OBJECT IDENTIFIER ::= { adGenCndSystemIdentity 42 }
adGenOpticalDCMIDCompliance           OBJECT IDENTIFIER ::= { adGenCndSystemCompliance 42 }

adGenOpticalADM                     OBJECT IDENTIFIER ::= { adGenCndSystem 43 }
adGenOpticalADMID                   OBJECT IDENTIFIER ::= { adGenCndSystemIdentity 43 }
adGenOpticalADMCompliance           OBJECT IDENTIFIER ::= { adGenCndSystemCompliance 43 }

adGenOtn                              OBJECT IDENTIFIER ::= { adGenCndSystem 44 }
adGenOtnID                            OBJECT IDENTIFIER ::= { adGenCndSystemIdentity 44 }
adGenOtnCompliance                    OBJECT IDENTIFIER ::= { adGenCndSystemCompliance 44 }

adGenPhysicalPeer                     OBJECT IDENTIFIER ::= { adGenCndSystem 45 }
adGenPhysicalPeerID                   OBJECT IDENTIFIER ::= { adGenCndSystemIdentity 45 }
adGenPhysicalPeerCompliance           OBJECT IDENTIFIER ::= { adGenCndSystemCompliance 45 }

adGenLldp                             OBJECT IDENTIFIER ::= { adGenCndSystem 46 }
adGenLldpID                           OBJECT IDENTIFIER ::= { adGenCndSystemIdentity 46 }
adGenLldpCompliance                   OBJECT IDENTIFIER ::= { adGenCndSystemCompliance 46 }

adGenPeerAdjacency                    OBJECT IDENTIFIER ::= { adGenCndSystem 47 }
adGenPeerAdjacencyID                  OBJECT IDENTIFIER ::= { adGenCndSystemIdentity 47 }
adGenPeerAdjacencyCompliance          OBJECT IDENTIFIER ::= { adGenCndSystemCompliance 47 }

adGenAtm                              OBJECT IDENTIFIER ::= { adGenCndSystem 48 }
adGenAtmID                            OBJECT IDENTIFIER ::= { adGenCndSystemIdentity 48 }
adGenAtmCompliance                    OBJECT IDENTIFIER ::= { adGenCndSystemCompliance 48 }

adGenRFC2544                          OBJECT IDENTIFIER ::= { adGenCndSystem 49 }
adGenRFC2544ID                        OBJECT IDENTIFIER ::= { adGenCndSystemIdentity 49}

adGenEthLbk                           OBJECT IDENTIFIER ::= { adGenCndSystem 50 }
adGenEthLbkID                         OBJECT IDENTIFIER ::= { adGenCndSystemIdentity 50}

adGenFibreChannel                     OBJECT IDENTIFIER ::= { adGenCndSystem 51 }
adGenFibreChannelID                   OBJECT IDENTIFIER ::= { adGenCndSystemIdentity 51}

adGenOneProtGroup                     OBJECT IDENTIFIER ::= { adGenCndSystem 52 }
adGenOneProtGroupID                   OBJECT IDENTIFIER ::= { adGenCndSystemIdentity 52 }
adGenOneProtGroupCompliance           OBJECT IDENTIFIER ::= { adGenCndSystemCompliance 52 }

adGenDynamicCounter                   OBJECT IDENTIFIER ::= { adGenCndSystem 53 }
adGenDynamicCounterID                 OBJECT IDENTIFIER ::= { adGenCndSystemIdentity 53 }

adGenMgcp                             OBJECT IDENTIFIER ::= { adGenCndSystem 54 }
adGenMgcpID                           OBJECT IDENTIFIER ::= { adGenCndSystemIdentity 54 }
adGenMgcpCompliance                   OBJECT IDENTIFIER ::= { adGenCndSystemCompliance 54 }

adGenRadiusAuth                       OBJECT IDENTIFIER ::= { adGenCndSystem 55 }
adGenRadiusAuthID                     OBJECT IDENTIFIER ::= { adGenCndSystemIdentity 55 }
adGenRadiusAuthCompliance             OBJECT IDENTIFIER ::= { adGenCndSystemCompliance 55 }

adGenVoiceUserMgmt                    OBJECT IDENTIFIER ::= { adGenCndSystem 56 }
adGenVoiceUserMgmtID                  OBJECT IDENTIFIER ::= { adGenCndSystemIdentity 56 }
adGenVoiceUserMgmtCompliance          OBJECT IDENTIFIER ::= { adGenCndSystemCompliance 56 }

adGenVector                           OBJECT IDENTIFIER ::= { adGenCndSystem 57 }
adGenVectorID                         OBJECT IDENTIFIER ::= { adGenCndSystemIdentity 57 }

adAOEControlledFeature                OBJECT IDENTIFIER ::= { adGenCndSystem 58 }
adAOEControlledFeatureID              OBJECT IDENTIFIER ::= { adGenCndSystemIdentity 58 }

adGenAutoConfig                       OBJECT IDENTIFIER ::= { adGenCndSystem 59 }
adGenAutoConfigID                     OBJECT IDENTIFIER ::= { adGenCndSystemIdentity 59 }

adGenLag                              OBJECT IDENTIFIER ::= { adGenCndSystem 60 }
adGenLagID                            OBJECT IDENTIFIER ::= { adGenCndSystemIdentity 60 }

adGenMonitorSession                   OBJECT IDENTIFIER ::= { adGenCndSystem 61 }
adGenMonitorSessionID                 OBJECT IDENTIFIER ::= { adGenCndSystemIdentity 61 }

END

ADTRAN-SHARED-CND-SYSTEM-TC-MIB

-- TITLE:     The ADTRAN CND SYSTEM TEXTUAL CONVENTION MIB
-- PRODUCT:   SYSTEM Level Support
-- VERSION:   1.0
-- DATE:      3/26/09
-- AUTHOR:    Andria Dyess
-- STATUS:    PRELIMINARY

-- This MIB defines textual conventions for Adtran CND System MIBS.

-- HISTORY:
-- 03/26/09 aed STATUS: PRELIMINARY
-- 04/07/09 jlb Changed the enumeration of GenSystemInterfaceType to be more generic.
-- 05/05/10 bly Added AdGenTrapVersion
-- 07/30/10  cb Added frpvc to GenSystemInterfaceType
-- 08/03/10 aed Added ipHost type
-- 08/26/10 a s Added sonet(34) and otn(35)
--          DO NOT ADD REVISION INFORMATION HERE.
-- ******************************************************************************************

DEFINITIONS ::= BEGIN

    IMPORTS
        adGenSystemTCID
            FROM ADTRAN-SHARED-CND-SYSTEM-MIB
        MODULE-IDENTITY
            FROM SNMPv2-SMI
        TEXTUAL-CONVENTION
            FROM SNMPv2-TC
        ;

adGenCndSystemTCIdentity MODULE-IDENTITY
   LAST-UPDATED "201906200000Z"
   ORGANIZATION "Adtran, Inc."
   CONTACT-INFO
     "CND Tech Support
         Postal: ADTRAN, Inc.
                 901 Explorer Blvd.
                 Huntsville, AL  35806
                 Tel: +1 800 726-8663
                 Fax: +1 256 963 6217
                 E-mail: support@adtran.com"
   DESCRIPTION
      "This MIB defines textual conventions for ADTRAN system MIBS."

   REVISION "201906200000Z"
   DESCRIPTION  "Add xgigabitEthernet(43) to GenSystemInterfaceType."

   REVISION "201408260000Z"
   DESCRIPTION  "Added hundredGigabitEthernet(41) and otnHundredGigabitEthernet(42) to GenSystemInterfaceType"

   REVISION "201407020000Z"
   DESCRIPTION  "Added otnTenGigabitEthernet(40) to GenSystemInterfaceType"

   REVISION "201203230000Z"
   DESCRIPTION  "Added fibreChannel(39) to GenSystemInterfaceType"

   REVISION "201203210000Z"
   DESCRIPTION  "Added defaultEthernet(37) and genericBridge(38) to GenSystemInterfaceType"

   REVISION "201201050000Z"
   DESCRIPTION  "Added wan(36)"

   REVISION "200903260000Z"
   DESCRIPTION "Created"
::= { adGenSystemTCID 1 }

   GenSystemInterfaceType ::= TEXTUAL-CONVENTION
        STATUS  current
        DESCRIPTION
                "Specifies the interface types in the system."
        SYNTAX   INTEGER {
                          unknown(1),
                          ds1(2),
                          dsx1(3),
                          e1(4),
                          dsxE1(5),
                          gigabitEthernet(6),
                          ds3(7),
                          portChannel(8),
                          tenGigabitEthernet(9),
                          erps(10),
                          shdsl(11),
                          adsl(12),
                          vdsl(13),
                          efmGroup(14),
                          efmLink(15),
                          efmPort(16),
                          lagGroup(17),
                          pppGroup(18),
                          imaGroup(19),
                          imaLink(20),
                          atm(21),
                          fxs(22),
                          hdsl2(23),
                          hdsl4(24),
                          adsl2(25),
                          vdsl2(26),
                          ethernet(27),
                          fast(28),
                          interleave(29),
                          hdsl(30),
                          gpon(31),
                          ipHost(32),
                          frpvc(33),
                          sonet(34),
                          otn(35),
                          wan(36),
                          defaultEthernet(37),
                          genericBridge(38),
                          fibreChannel(39),
                          otnTenGigabitEthernet(40),
                          hundredGigabitEthernet(41),
                          otnHundredGigabitEthernet(42),
                          xgigabitEthernet(43)
        }

AdGenTrapVersion ::= TEXTUAL-CONVENTION
    STATUS current
    DESCRIPTION
       "SNMP trap version.

        snmpV1 (1)     SNMP version 1 traps
        snmpV2 (2)     SNMP version 2c notifications
       "
    SYNTAX INTEGER {
        snmpV1(1),
        snmpV2(2)
}

END

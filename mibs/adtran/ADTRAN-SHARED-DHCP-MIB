ADTRAN-SHARED-DHCP-MIB

-- TITLE:     The ADTRAN DHCP IDENTITY MIB
-- PRODUCT:   ADTRAN DHCP PRODUCTS
-- VERSION:   1.0
-- DATE:      9/22/09
-- AUTHOR:    Chip Boling
-- STATUS:    PRELIMINARY

-- This MIB defines the object identifier (OID) for the
-- ADTRAN SHARED DHCP MIB objects

-- HISTORY:
-- yy/mm/dd
-- 09/06/07 cb STATUS: PRELIMINARY.

-- ******************************************************************************************

DEFINITIONS ::= BEGIN

    IMPORTS
        adShared,
        adIdentityShared
            FROM ADTRAN-MIB
        MODULE-IDENTITY
            FROM SNMPv2-SMI
        ;

adDhcpIdentity MODULE-IDENTITY
   LAST-UPDATED "200909220000Z"    -- 9/22/2009 00:00GMT
   ORGANIZATION "Adtran, Inc."
   CONTACT-INFO "http://www.adtran.com"
   DESCRIPTION
      "This MIB defines the objects for the SHDSL MIB."
   REVISION "200909220000Z"    -- 9/22/2009 00:00GMT
   DESCRIPTION "Created"
::= { adIdentityShared 80}

adDHCP     		   OBJECT IDENTIFIER ::= { adShared 80}

adGenDhcpClient    OBJECT IDENTIFIER ::= { adDHCP 1 }
adGenDhcpClientId  OBJECT IDENTIFIER ::= { adDhcpIdentity 1 }

END

ADTRAN-SHARED-DS1-MIB

-- TITLE:     The ADTRAN DS1 IDENTITY MIB
-- PRODUCT:   ADTRAN DS1 PRODUCTS
-- VERSION:   1.0
-- DATE:      9/18/08
-- AUTHOR:    Albert Sue
-- STATUS:    PRELIMINARY

-- This MIB defines the object identifier (OID) for the
-- ADTRAN SHARED DS1 MIB objects

-- HISTORY:
-- 09/18/08 Albert S.  - Created

-- ******************************************************************************************

DEFINITIONS ::= BEGIN

    IMPORTS
        adShared,
        adIdentityShared
            FROM ADTRAN-MIB
        MODULE-IDENTITY
            FROM SNMPv2-SMI
        ;

adDS1Identity MODULE-IDENTITY
   LAST-UPDATED "200809180000Z"
   ORGANIZATION "Adtran, Inc."
   CONTACT-INFO "http://www.adtran.com"
   DESCRIPTION
      "This MIB defines the objects for the DS1 MIB."
   REVISION "200809180000Z"
   DESCRIPTION "Created"
::= { adIdentityShared 78 }

adDS1          OBJECT IDENTIFIER ::= { adShared 78 }

adGenDS1Test    OBJECT IDENTIFIER ::= { adDS1 1 }
adGenDS1TestID  OBJECT IDENTIFIER ::= { adDS1Identity 1 }



END

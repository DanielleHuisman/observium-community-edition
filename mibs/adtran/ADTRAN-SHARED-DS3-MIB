ADTRAN-SHARED-DS3-MIB

-- TITLE:     The ADTRAN DS3 IDENTITY MIB
-- PRODUCT:   ADTRAN DS3 PRODUCTS
-- VERSION:   1.0
-- DATE:      4/24/08
-- AUTHOR:    Joey Boyd
-- STATUS:    PRELIMINARY

-- This MIB defines the object identifier (OID) for the
-- ADTRAN SHARED DS3 MIB objects

-- HISTORY:
-- 04/24/08 jlb STATUS: PRELIMINARY.

-- ******************************************************************************************

DEFINITIONS ::= BEGIN

    IMPORTS
        adShared,
        adIdentityShared
            FROM ADTRAN-MIB
        MODULE-IDENTITY
            FROM SNMPv2-SMI
        ;

adDS3Identity MODULE-IDENTITY
   LAST-UPDATED "200704240000Z"
   ORGANIZATION "Adtran, Inc."
   CONTACT-INFO "http://www.adtran.com"
   DESCRIPTION
      "This MIB defines the objects for the DS3 MIB."
   REVISION "200804240000Z"
   DESCRIPTION "Created"
::= { adIdentityShared 74 }

adDS3          OBJECT IDENTIFIER ::= { adShared 74 }

adGenDS3Test    OBJECT IDENTIFIER ::= { adDS3 1 }
adGenDS3TestID  OBJECT IDENTIFIER ::= { adDS3Identity 1 }



END

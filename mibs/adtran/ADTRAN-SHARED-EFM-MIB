ADTRAN-SHARED-EFM-MIB

-- TITLE:     The ADTRAN EFM IDENTITY MIB
-- PRODUCT:   ADTRAN EFM PRODUCTS
-- VERSION:   1.0
-- DATE:      4/05/07
-- AUTHOR:    Joey Boyd
-- STATUS:    PRELIMINARY

-- This MIB defines the object identifier (OID) for the
-- ADTRAN SHARED EFM MIB objects

-- HISTORY:
-- 04/05/07 jlb STATUS: PRELIMINARY.
-- 08/31/07 jlb Added adGenEfmNtu and adGenEfmNtuID

-- ******************************************************************************************

DEFINITIONS ::= BEGIN

    IMPORTS
        adShared,
        adIdentityShared
            FROM ADTRAN-MIB
        MODULE-IDENTITY
            FROM SNMPv2-SMI
        ;

adEfmIdentity MODULE-IDENTITY
   LAST-UPDATED "200704050000Z"
   ORGANIZATION "Adtran, Inc."
   CONTACT-INFO "http://www.adtran.com"
   DESCRIPTION
      "This MIB defines the objects for the EFM MIB."
   REVISION "200704050000Z"
   DESCRIPTION "Created"
::= { adIdentityShared 66 }


adEfm           OBJECT IDENTIFIER ::= { adShared 66 }

adGenEfm        OBJECT IDENTIFIER ::= { adEfm 1}
adGenEfmID      OBJECT IDENTIFIER ::= { adEfmIdentity 1 }

adGenEfmNtu     OBJECT IDENTIFIER ::= { adEfm 2}
adGenEfmNtuID   OBJECT IDENTIFIER ::= { adEfmIdentity 2 }

adGenEfmExt     OBJECT IDENTIFIER ::= { adEfm 3}
adGenEfmExtID   OBJECT IDENTIFIER ::= { adEfmIdentity 3 }

END

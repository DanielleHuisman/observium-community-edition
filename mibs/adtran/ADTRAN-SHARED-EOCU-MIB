ADTRAN-SHARED-EOCU-MIB

-- TITLE:     The ADTRAN SHDSL IDENTITY MIB
-- PRODUCT:   ADTRAN SHDSL PRODUCTS
-- VERSION:   1.0
-- DATE:      4/06/07
-- AUTHOR:    Joey Boyd
-- STATUS:    PRELIMINARY

-- This MIB defines the object identifier (OID) for the
-- ADTRAN SHARED EoCu MIB objects

-- HISTORY:
-- 04/06/07 jlb STATUS: PRELIMINARY.
-- 04/28/08 rpk Added adGenEthCfm

-- ******************************************************************************************

DEFINITIONS ::= BEGIN

    IMPORTS
        adShared,
        adIdentityShared
            FROM ADTRAN-MIB
        MODULE-IDENTITY
            FROM SNMPv2-SMI
        ;

adEoCuIdentity MODULE-IDENTITY
   LAST-UPDATED "200704060000Z"
   ORGANIZATION "Adtran, Inc."
   CONTACT-INFO "http://www.adtran.com"
   DESCRIPTION
      "This MIB defines the objects for the EoCu MIB."
   REVISION "200704060000Z"
   DESCRIPTION "Created"
::= { adIdentityShared 69 }

adEoCu          OBJECT IDENTIFIER ::= { adShared 69 }

adGenMEF        OBJECT IDENTIFIER ::= { adEoCu 1 }
adGenMEFID      OBJECT IDENTIFIER ::= { adEoCuIdentity 1 }

adGenTA8xx      OBJECT IDENTIFIER ::= { adEoCu 2 }
adGenTA8xxID    OBJECT IDENTIFIER ::= { adEoCuIdentity 2 }

adGenOAM        OBJECT IDENTIFIER ::= { adEoCu 3 }
adGenOAMID      OBJECT IDENTIFIER ::= { adEoCuIdentity 3 }

        adSLAProbe       OBJECT IDENTIFIER ::= { adGenOAM 1 }
        adSLAProbeID     OBJECT IDENTIFIER ::= { adGenOAMID 1 }

adGenTA8xxTlv   OBJECT IDENTIFIER ::= { adEoCu 4 }
adGenTA8xxTlvID OBJECT IDENTIFIER ::= { adEoCuIdentity 4 }

adGenTWAMPReflector   	OBJECT IDENTIFIER ::= { adEoCu 5 }
adTWAMPReflectorID 		OBJECT IDENTIFIER ::= { adEoCuIdentity 5 }

adGenEthCfm   	OBJECT IDENTIFIER ::= { adEoCu 6 }
adGenEthCfmID 	OBJECT IDENTIFIER ::= { adEoCuIdentity 6 }


END

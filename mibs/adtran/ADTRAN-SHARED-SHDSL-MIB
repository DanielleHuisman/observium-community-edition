ADTRAN-SHARED-SHDSL-MIB

-- TITLE:     The ADTRAN SHDSL IDENTITY MIB
-- PRODUCT:   ADTRAN SHDSL PRODUCTS
-- VERSION:   1.0
-- DATE:      4/06/07
-- AUTHOR:    Joey Boyd
-- STATUS:    PRELIMINARY

-- This MIB defines the object identifier (OID) for the
-- ADTRAN SHARED SHDSL MIB objects

-- HISTORY:
-- 04/06/07 jlb STATUS: PRELIMINARY.

-- ******************************************************************************************

DEFINITIONS ::= BEGIN

    IMPORTS
        adShared,
        adIdentityShared
            FROM ADTRAN-MIB
        MODULE-IDENTITY
            FROM SNMPv2-SMI
        ;

adShdslIdentity MODULE-IDENTITY
   LAST-UPDATED "200704060000Z"
   ORGANIZATION "Adtran, Inc."
   CONTACT-INFO "http://www.adtran.com"
   DESCRIPTION
      "This MIB defines the objects for the SHDSL MIB."
   REVISION "200704060000Z"
   DESCRIPTION "Created"
::= { adIdentityShared 59 }

adSHDSL         OBJECT IDENTIFIER ::= { adShared 59 }

adGenEShdsl        OBJECT IDENTIFIER ::= { adSHDSL 1 }
adGenEShdslID      OBJECT IDENTIFIER ::= { adShdslIdentity 1 }

-- Reserved from other MIBs
-- adGenShdslIma      OBJECT IDENTIFIER ::= {adSHDSL 2}
-- adVLAN             OBJECT IDENTIFIER ::= {adSHDSL 3}

adGenDslProxy      OBJECT IDENTIFIER ::= { adSHDSL 4 }
adGenDslProxyID    OBJECT IDENTIFIER ::= { adShdslIdentity 4 }

END

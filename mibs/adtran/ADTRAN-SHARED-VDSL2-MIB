ADTRAN-SHARED-VDSL2-MIB

-- TITLE:     The ADTRAN VDSL2 IDENTITY MIB
-- PRODUCT:   ADTRAN VDSL2 PRODUCTS
-- VERSION:   1.0
-- DATE:      07/08/2008
-- AUTHOR:    Craye Hall
-- STATUS:    PRELIMINARY

-- This MIB defines the object identifier (OID) for the
-- ADTRAN SHARED VDSL2 MIB objects

-- HISTORY:
-- 07/08/2008 och STATUS: PRELIMINARY.

-- ******************************************************************************************

DEFINITIONS ::= BEGIN

    IMPORTS
        adShared,
        adIdentityShared
            FROM ADTRAN-MIB
        MODULE-IDENTITY
            FROM SNMPv2-SMI
        ;

adVdsl2Identity MODULE-IDENTITY
   LAST-UPDATED "200807080000Z"
   ORGANIZATION "Adtran, Inc."
   CONTACT-INFO "http://www.adtran.com"
   DESCRIPTION
      "This MIB defines the objects for the VDSL2 MIB."
   REVISION "200807080000Z"
   DESCRIPTION "Created"
::= { adIdentityShared 65 }


adVdsl2         OBJECT IDENTIFIER ::= { adShared 65 }

adGenVdsl2      OBJECT IDENTIFIER ::= { adVdsl2 1}
adGenVdsl2ID    OBJECT IDENTIFIER ::= { adVdsl2Identity 1 }

END

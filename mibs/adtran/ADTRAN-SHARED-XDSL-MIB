ADTRAN-SHARED-XDSL-MIB

-- TITLE:     The ADTRAN XDSL IDENTITY MIB
-- PRODUCT:   ADTRAN XDSL PRODUCTS
-- VERSION:   1.1
-- DATE:      06/10/2010
-- AUTHOR:    Craye Hall
-- STATUS:    PRELIMINARY

-- This MIB defines the object identifier (OID) for the
-- ADTRAN SHARED XDSL MIB objects

-- HISTORY:
-- 07/08/2008 och STATUS: PRELIMINARY.
-- 06/10/2010 gdo Add base OIDs for Geminax mib.

-- ******************************************************************************************

DEFINITIONS ::= BEGIN

    IMPORTS
        adShared,
        adIdentityShared
            FROM ADTRAN-MIB
        MODULE-IDENTITY
            FROM SNMPv2-SMI
        ;

adXdslIdentity MODULE-IDENTITY
   LAST-UPDATED "201006100000Z"
   ORGANIZATION "Adtran, Inc."
   CONTACT-INFO "http://www.adtran.com"
   DESCRIPTION
      "This MIB defines the objects for the xDSL MIB."
   REVISION "201006100000Z"
   DESCRIPTION "Add base OIDs for Geminax MIB"
   REVISION "200807170000Z"
   DESCRIPTION "Created"
::= { adIdentityShared 73 }


adXdsl          OBJECT IDENTIFIER ::= { adShared 73 }

adGenXdsl      OBJECT IDENTIFIER ::= { adXdsl 1}
adGenXdslID    OBJECT IDENTIFIER ::= { adXdslIdentity 1 }

adGenGeminax      OBJECT IDENTIFIER ::= { adXdsl 2}
adGenGeminaxID    OBJECT IDENTIFIER ::= { adXdslIdentity 2 }

END

ADTRAN-SHDSL-MIB

-- TITLE:     The ADTRAN SHDSL MIB
-- PRODUCT:   ADTRAN SHDSL products starting with the 2w4w products going forward
-- VERSION:   1.0
-- DATE:      05/11/04
-- AUTHOR:    Joey Boyd
-- STATUS:    PRELIMINARY

-- This MIB defines the object identifier (OID) for the
-- ADTRAN SHDSL MIB objects

-- HISTORY:
-- 2004/05/11 jlb STATUS: PRELIMINARY.
-- 2004/05/12 jlb Changed STUC and STUR references to LTU and NTU respectively.  Added alarms
--           and other traps.  Added adEShdslPerfTotalTable to allow access to the
--           "since powerup" performance history.
-- 2004/09/21 jlb Added adEShdslStatusMaxAttainableRate.
-- 2004/10/12 jlb Revised adEShdslTestProvLoopbackTimeout comments.
-- 2006/03/08 jlb Added adEShdslProvConstellation
-- 2006/09/08 jlb Added adEShdslSpliceDetection
-- 2006/09/29 jlb Added adEShdslPerfReset
-- 2006/12/21 jlb Added adEShdslProvPowerBackoff
-- 2006/12/22 jlb Updated adEShdslProvPowerBackoff comments
-- 2006/12/28 jlb Added adEShdslStatusUpstreamPBO and adEShdslStatusDownstreamPBO
-- 2007/01/15 jlb Added adEShdslSpliceDistanceType
-- 2007/01/19 jlb Added adEShdslPerf15MinIntTable and adEShdslPerf24HrIntTable
-- 2007/01/22 jlb Added adEShdslStatusCurrRate
-- 2007/04/06 jlb Converted from SNMPv1 to SNMPv2
-- 2007/05/15 twc Added additional entries to adEShdslProvG9912Annex.
-- 2007/05/17 jlb Added 24-Hour thresholds and alarms.
-- 2007/05/29 jlb Added adEShdslProvName
-- 2007/06/08 jlb Modified the alarms to be compatible with existing v1 implementation and
--            all future v2 implementations.
-- 2007/08/31 twc Fixed SMIC compiler errors
-- 2007/09/18 jlb Added repeaters to the AdGenShdslUnitId enumeration
-- 2007/09/20 kle Prepping mib to support items that Brad Tidwell wants for the
--            Netvanta 8xx hdsl-2 and hdsl-4 NCTEs.  I compared this MIB against
--            the shdsl09.mib, the genh2tuc.mib, and the genh4tuc.mib and have
--            added the following items:
--                     Inventory items:
--                              adEShdslInvVendorEOCSoftwareVersion
--                              adEShdslInvMfrDate
--                              adEShdslInvCircuitID
--                              adEShdslInvScratchPad
--                     Provisioning items:
--                              adEShdslProvSpanPower
--                              adEShdslProvNIUloopback
--                     Status items:
--                              adEShdslStatusInfoRepeaterNumber
--                              adEShdslStatusInfoPairReversal
--                              adEShdslStatusInfoLoopAlarmStatus
--                     Test items:
--                              adEShdslTestLoopdownAll
--                              adEShdslTestinitMinMax
--                     Regenerator/Repeater alarms:
--                              adEShdslRemoteLossOfPower
--                              adEShdslRegenLossofSignalAlmCLR
--                              adEShdslRegenLossofSignalAlmACT
--                              adEShdslRegenLossofSyncWordAlmCLR
--                              adEShdslRegenLossofSyncWordAlmACT
--                              adEShdslRegenCRCErrorAlmCLR
--                              adEShdslRegenCRCErrorAlmACT
--                              adEShdslRegenSNRMarginAlmCLR
--                              adEShdslRegenSNRMarginAlmACT
--                              adEShdslRegenLoopAttenAlmCLR
--                              adEShdslRegenLoopAttenAlmACT
--                              adEShdslRegenESThreshCrossed
--                              adEShdslRegenSESThreshCrossed
--                              adEShdslRegenUASThreshCrossed
--                              adEShdslRegenCVCThreshCrossed
--                              adEShdslRegenLOSWSThreshCrossed
--                              adEShdslRegenOSThreshCrossed
--
--                I also changed the description on adEShdslPerf24HrIntNumber to account
--                for optional intervals 8 thru 30.
-- 2007/10/08 twc Added splice detection 24 hr interval table
-- 2007/10/30 jlb Added adEShdslLoopbackEnabledCLR and adEShdslLoopbackEnabledACT
-- 2007/11/29 jlb Added adEShdslTestProvEnumeratedLoopbackTimeout
-- 2007/11/29 jmh Updated the adEShdslTestProvEnumeratedLoopbackTimeout enums.
-- 2007/12/10 twc Fixed adEShdslTestProvEnumeratedLoopbackTimeout compiler warning.
-- 2008/03/31 jlb Added adEShdslPerfPortReset.
-- 2008/04/02 eal Added adEShdslProvAnfpTargetMargin, adEShdslProvAnfp100KhzLoss, and adEShdslProvBitsperSymbolCrossover
--				  Updated the description of adEShdslProvConstellation
-- 2008/04/17 jlb Added 24 Hour threshold alarms to the NOTIFICATION-GROUP
-- 2008/04/22 jlb Fixed compiler errors.
-- 2008/05/19 jlb Changed some alarm severities to fix mismatch issues.
-- 2009/04/21 jlb Added adEShdslStatusIfTrainingMode.  SMIC verified.
-- 2009/10/14 jlb Added enableMaxRate(5), enableT1417(6), and enableG9912(7) to adEShdslProvLineProbing
-- 2010/02/12 jlb Added enableG9912nl to adEShdslProvLineProbing
-- 2011/02/22 jsb Added adEShdslProvEmergencyFreeze
-- *******************************************************************************************************
--    DO NOT MAKE HISTORY COMMENTS HERE!!!! Revision history now in REVISION/DESCRIPTION clauses below
-- *******************************************************************************************************

-- ******************************************************************************************

DEFINITIONS ::= BEGIN

    IMPORTS
	Integer32,
        OBJECT-TYPE,
        MODULE-IDENTITY,
        NOTIFICATION-TYPE
            FROM SNMPv2-SMI
        OBJECT-GROUP,
        NOTIFICATION-GROUP
            FROM SNMPv2-CONF
        sysName
            FROM SNMPv2-MIB
        DisplayString,
        TruthValue
            FROM SNMPv2-TC
        ifIndex
            FROM IF-MIB
        adGenPortTrapIdentifier
            FROM ADTRAN-GENPORT-MIB
        adTrapInformSeqNum
            FROM ADTRAN-GENTRAPINFORM-MIB
        adGenSlotInfoIndex
            FROM ADTRAN-GENSLOT-MIB
        adGenEShdsl,
        adGenEShdslID
            FROM ADTRAN-SHARED-SHDSL-MIB
        adTAeSCUTrapAlarmLevel
            FROM ADTRAN-TAeSCUEXT1-MIB
        ;

adGenEShdslMIB MODULE-IDENTITY
   LAST-UPDATED "201910110000Z"
   ORGANIZATION "Adtran, Inc."
    CONTACT-INFO
        "CND Tech Support
           Postal: ADTRAN, Inc.
                   901 Explorer Blvd.
                   Huntsville, AL  35806
                   Tel: +1 800 726 8663
                   Fax: +1 256 963 6217
                   E-mail: support@adtran.com"
   DESCRIPTION
      "This MIB defines the objects for the SHDSL MIB."

   REVISION "201910110000Z"
   DESCRIPTION "Added adEShdslProvSCIAlarmThresh, adEShdslProvSCIAlarmSeverity, and adEShdslSCIThreshCrossed."

   REVISION "201209240000Z"
   DESCRIPTION "Added adEShdslTestLoopLocatorTable and adEShdslTestLoopLocatorLastErrorTable."

   REVISION "201209130000Z"
   DESCRIPTION "Added adEShdslStatusInfoTopology, adEShdslStatusPhysicalLinkLabel and adEShdslSpliceBadSpliceDetected
                Added bad splice, short, and ground fault alarms."

   REVISION "201207310000Z"
   DESCRIPTION "Added adEShdslInvElementPresent and adEShdslInvPhysicalLinkId"

   REVISION "201207110000Z"
   DESCRIPTION "Added adEShdslTestRepeaterPoweringTable"

   REVISION "201108220000Z"
   DESCRIPTION "Updated the description for adEShdslProvExtendedFixedRateAndConstellation to include constellations 1 and 2."

   REVISION "201106021338Z"
   DESCRIPTION "Added adEShdslInvDspHwVersion and adEShdslInvDspFwVersion to adEShdslInventoryTable"

   REVISION "201104261516Z"
   DESCRIPTION "Added current and previous train SNR margins."

   REVISION "201104250925Z"
   DESCRIPTION "Added minimum and maximum SNR margins to PM."

   REVISION "201104180000Z"
   DESCRIPTION "Added adEShdslProvAnfpMaxLineRate to the adEShdslProvTable."

   REVISION "201104131428Z"
   DESCRIPTION "Added retrains and handshake failures to PM, thresholds, and alarms."

   REVISION "201104041521Z"
   DESCRIPTION "Added AFNP letter entry"

   REVISION "201103291420Z"
   DESCRIPTION "Added adEShdslSpliceRate to adEShdslSpliceDetectionTable.
                Added adEShdslSplice24HrIntRate to adEShdslSpliceDet24HrIntTable.
                Created adEShdslSpliceDet15MinCurrTable,
                  and adEShdslSpliceDet15MinIntTable."

   REVISION "201103240000Z"
   DESCRIPTION "Added disableLineProbeEnableExtFixed(9) to adEShdslProvLineProbing.
		Added adEShdslProvExtendedFixedRateAndConstellation and
                  adEShdslProvExtendedFixedLastError to adEShdslProvTable."

   REVISION "201102220000Z"
   DESCRIPTION "Added adEShdslProvEmergencyFreeze"

   REVISION "201002120000Z"
   DESCRIPTION "Added enableG9912nl to adEShdslProvLineProbing"

   REVISION "200704060000Z"
   DESCRIPTION "Created"
::= { adGenEShdslID 1 }

-- OBJECT IDENTIFIERS

adEShdslIndex           	OBJECT IDENTIFIER ::= {adGenEShdsl 1}
adEShdslInventory       	OBJECT IDENTIFIER ::= {adGenEShdsl 2}
adEShdslProvisioning    	OBJECT IDENTIFIER ::= {adGenEShdsl 3}
adEShdslStatus          	OBJECT IDENTIFIER ::= {adGenEShdsl 4}
adEShdslTest            	OBJECT IDENTIFIER ::= {adGenEShdsl 5}
adEShdslPerformance     	OBJECT IDENTIFIER ::= {adGenEShdsl 6}
adEShdslSpliceDetection		OBJECT IDENTIFIER ::= {adGenEShdsl 7}

adEShdslMibConformance          OBJECT IDENTIFIER ::= {adGenEShdsl 8 }
adEShdslMibGroups               OBJECT IDENTIFIER ::= {adEShdslMibConformance 1 }

adEShdslAlarmsPrefix            OBJECT IDENTIFIER ::= {adGenEShdsl 10}
adEShdslAlarms                  OBJECT IDENTIFIER ::= {adEShdslAlarmsPrefix 0}

adEShdslProductInfo		OBJECT IDENTIFIER ::= {adGenEShdsl 11}

-- ******************************************************************************************

-- Textual Conventions used in this MIB

---   This is the unique identification for all units in a
--    SHDSL Span.  It is based on the EOC unit addressing
--    scheme with reference to the LTU.
AdEShdslUnitId ::=  INTEGER
           {
           ltu(1),                  --same as STUC
           ntu(2),                  --same as STUR
           xru1(3),                 --repeater 1
           xru2(4),                 --repeater 1
           xru3(5),                 --repeater 3
           xru4(6),                 --repeater 4
           xru5(7),                 --repeater 5
           xru6(8),                 --repeater 6
           xru7(9),                 --repeater 7
           xru8(10)                 --repeater 8
           }

---   This is the referenced side of a SHDSL unit - Network
--    or Customer side.  The side facing the Network is the Network
--    side, while the side facing the Customer is the Customer side.
--    For a LTU, the SHDSL interface is on the customer side.  For a
--    NTU, the SHDSL interface is on the network side.  This is being
--    put here in case of future repeater support.
AdEShdslUnitSide ::=  INTEGER
           {
           networkSide(1),
           customerSide(2)
           }

---   This is the referenced pair of wires in a SHDSL Segment.
AdEShdslWirePair ::=  INTEGER
           {
           wirePair1(1),
           wirePair2(2)
           }

-- ******************************************************************************************

-- Index Declaration Group
--

adEShdslIndexTable OBJECT-TYPE
   SYNTAX     SEQUENCE OF AdEShdslIndexEntry
   MAX-ACCESS not-accessible
   STATUS     current
   DESCRIPTION
     "This table declares the indeces to be used throughout the ADTRAN-SHDSL-MIB."
   ::= { adEShdslIndex 1 }

adEShdslIndexEntry OBJECT-TYPE
   SYNTAX      AdEShdslIndexEntry
   MAX-ACCESS  not-accessible
   STATUS      current
   DESCRIPTION
     "An entry in the adEShdslIndexTable. "
   INDEX { ifIndex, adEShdslInvIndex, adEShdslSideIndex, adEShdslWirePairIndex }
   ::= { adEShdslIndexTable 1 }

AdEShdslIndexEntry ::=
   SEQUENCE
   {
   adEShdslInvIndex                      AdEShdslUnitId,
   adEShdslSideIndex                     AdEShdslUnitSide,
   adEShdslWirePairIndex                 AdEShdslWirePair
   }

adEShdslInvIndex OBJECT-TYPE
   SYNTAX      AdEShdslUnitId
   MAX-ACCESS  read-only
   STATUS      current
   DESCRIPTION
      "Each entry in this table corresponds to a physical element
      in a SHDSL Span.  It is based on the EOC unit addressing
      scheme with reference to the xtuC."
   ::= { adEShdslIndexEntry 1 }

adEShdslSideIndex OBJECT-TYPE
   SYNTAX      AdEShdslUnitSide
   MAX-ACCESS  read-only
   STATUS      current
   DESCRIPTION
     "This is the referenced side of a SHDSL unit - Network
      or Customer side.  The side facing the Network is the Network
      side, while the side facing the Customer is the Customer side."
   ::= { adEShdslIndexEntry 2 }

adEShdslWirePairIndex OBJECT-TYPE
   SYNTAX      AdEShdslWirePair
   MAX-ACCESS  read-only
   STATUS      current
   DESCRIPTION
     "This is the referenced pair of wires in a SHDSL Segment."
   ::= { adEShdslIndexEntry 3 }

-- ******************************************************************************************

-- Unit Inventory Group
--

adEShdslInventoryTable OBJECT-TYPE
   SYNTAX     SEQUENCE OF AdEShdslInventoryEntry
   MAX-ACCESS not-accessible
   STATUS     current
   DESCRIPTION
     "This table supports retrieval of unit inventory information
      available via the EOC from units in a SHDSL line.

      Entries in this table are dynamically created during the
      line discovery process.  The life cycle for these entries
      is as follows:

         - stu discovers a device, either a far-end stu or an sru
         - an inventory table entry is created for the device
         - the line goes down for whatever reason
         - inventory table entries for unreachable devices are
           destroyed.

      As these entries are created/destroyed dynamically, they
      are NOT persistent."
   ::= { adEShdslInventory 1 }

adEShdslInventoryEntry OBJECT-TYPE
   SYNTAX      AdEShdslInventoryEntry
   MAX-ACCESS  not-accessible
   STATUS      current
   DESCRIPTION
     "An entry in the adEShdslInventoryTable.  Each entry
      represents inventory information for a single unit in a
      SHDSL line.  It is indexed by the ifIndex of the
      SHDSL line and the adEShdslUnitId of the
      associated unit."
   INDEX { ifIndex, adEShdslInvIndex }
   ::= { adEShdslInventoryTable 1 }

AdEShdslInventoryEntry ::=
   SEQUENCE
   {
   adEShdslInvVendorID                   OCTET STRING,
   adEShdslInvVendorModelNumber          OCTET STRING,
   adEShdslInvVendorSerialNumber         OCTET STRING,
   adEShdslInvStandardVersion            Integer32,
   adEShdslInvVendorListNumber           OCTET STRING,
   adEShdslInvVendorIssueNumber          OCTET STRING,
   adEShdslInvVendorSoftwareVersion      OCTET STRING,
   adEShdslInvEquipmentCode              OCTET STRING,
   adEShdslInvVendorOther                OCTET STRING,
   adEShdslInvVendorEOCSoftwareVersion   Integer32,
   adEShdslInvMfrDate                    DisplayString,
   adEShdslInvCircuitID                  DisplayString,
   adEShdslInvScratchPad                 DisplayString,
   adEShdslInvDspHwVersion               DisplayString,
   adEShdslInvDspFwVersion               DisplayString,
   adEShdslInvElementPresent             TruthValue,
   adEShdslInvPhysicalLinkId             Integer32
   }

adEShdslInvVendorID OBJECT-TYPE
   SYNTAX      OCTET STRING(SIZE(8))
   MAX-ACCESS  read-only
   STATUS      current
   DESCRIPTION
     "Vendor ID as reported in an Inventory Response message."
   ::= { adEShdslInventoryEntry 1 }

adEShdslInvVendorModelNumber OBJECT-TYPE
   SYNTAX      OCTET STRING(SIZE(12))
   MAX-ACCESS  read-only
   STATUS      current
   DESCRIPTION
     "Vendor model number as reported in an Inventory Response
      message."
   ::= { adEShdslInventoryEntry 2 }

adEShdslInvVendorSerialNumber OBJECT-TYPE
   SYNTAX      OCTET STRING(SIZE(25))
   MAX-ACCESS  read-only
   STATUS      current
   DESCRIPTION
     "Vendor serial number as reported in an Inventory Response
      message."
   ::= { adEShdslInventoryEntry 3 }

adEShdslInvStandardVersion OBJECT-TYPE
   SYNTAX      Integer32
   MAX-ACCESS  read-only
   STATUS      current
   DESCRIPTION
     "Version of the SHDSL standard implemented, as reported
      in an Inventory Response message."
   ::= { adEShdslInventoryEntry 4 }

adEShdslInvVendorListNumber OBJECT-TYPE
   SYNTAX      OCTET STRING(SIZE(3))
   MAX-ACCESS  read-only
   STATUS      current
   DESCRIPTION
     "Vendor list number as reported in an Inventory Response
      message."
   ::= { adEShdslInventoryEntry 5 }

adEShdslInvVendorIssueNumber OBJECT-TYPE
   SYNTAX      OCTET STRING(SIZE(2))
   MAX-ACCESS  read-only
   STATUS      current
   DESCRIPTION
     "Vendor issue number as reported in an Inventory Response
      message."
   ::= { adEShdslInventoryEntry 6 }

adEShdslInvVendorSoftwareVersion OBJECT-TYPE
   SYNTAX      OCTET STRING(SIZE(6))
   MAX-ACCESS  read-only
   STATUS      current
   DESCRIPTION
     "Vendor software version as reported in an Inventory Response
      message."
   ::= { adEShdslInventoryEntry 7 }

adEShdslInvEquipmentCode OBJECT-TYPE
   SYNTAX      OCTET STRING(SIZE(10))
   MAX-ACCESS  read-only
   STATUS      current
   DESCRIPTION
     "Equipment code conforming to ANSI T1.213, Coded Identification
      of Equipment Entities."
   ::= { adEShdslInventoryEntry 8 }

adEShdslInvVendorOther OBJECT-TYPE
   SYNTAX      OCTET STRING(SIZE(12))
   MAX-ACCESS  read-only
   STATUS      current
   DESCRIPTION
     "Other vendor information as reported in an Inventory Response
      message."
   ::= { adEShdslInventoryEntry 9 }

adEShdslInvVendorEOCSoftwareVersion OBJECT-TYPE
    SYNTAX      Integer32
    MAX-ACCESS  read-only
    STATUS      current
    DESCRIPTION
        "Vendor EOC version as reported in a Discovery Response
         message."
   ::= { adEShdslInventoryEntry 10 }

adEShdslInvMfrDate OBJECT-TYPE
    SYNTAX  DisplayString
    MAX-ACCESS  read-only
    STATUS  current
    DESCRIPTION
        "Optional Date of manufacture. Some products support."
   ::= { adEShdslInventoryEntry 11 }

adEShdslInvCircuitID OBJECT-TYPE
    SYNTAX  DisplayString
    MAX-ACCESS  read-write
    STATUS  current
    DESCRIPTION
        "Optional Circuit ID assigned to all elements in the xdsl circuit."
   ::= { adEShdslInventoryEntry 12 }

adEShdslInvScratchPad OBJECT-TYPE
    SYNTAX  DisplayString
    MAX-ACCESS  read-write
    STATUS  current
    DESCRIPTION
        "Optional Scratch Pad.  50 bytes long."
   ::= { adEShdslInventoryEntry 13 }

adEShdslInvDspHwVersion OBJECT-TYPE
   SYNTAX       DisplayString
   MAX-ACCESS   read-only
   STATUS       current
   DESCRIPTION
     "Returns the hardware version of the DSP"
   ::= { adEShdslInventoryEntry 14 }

adEShdslInvDspFwVersion OBJECT-TYPE
   SYNTAX       DisplayString
   MAX-ACCESS   read-only
   STATUS       current
   DESCRIPTION
     "Returns the firmware version of the DSP"
   ::= { adEShdslInventoryEntry 15 }

adEShdslInvElementPresent OBJECT-TYPE
   SYNTAX       TruthValue
   MAX-ACCESS   read-only
   STATUS       current
   DESCRIPTION
     "Returns true(1) if the element specified by adEShdslInvIndex is
      present in the circuit.  Returns false(2) otherwise"
   ::= { adEShdslInventoryEntry 16 }

adEShdslInvPhysicalLinkId OBJECT-TYPE
   SYNTAX       Integer32
   MAX-ACCESS   read-only
   STATUS       current
   DESCRIPTION
     "Returns the physical link number associated with the element
      specified by adEShdslInvIndex.  For example, a 2 port repeater
      would return 1 or 2 while an 8 port NTU would return a value
      between 1 and 8 depending on which physical interface this circuit
      is connected to."
   ::= { adEShdslInventoryEntry 17 }


-- ******************************************************************************************

-- Provisioning Group
--

-- ********************************************
-- SHDSL Provisioning
-- ********************************************

adEShdslProvTable OBJECT-TYPE
   SYNTAX      SEQUENCE OF AdEShdslProvEntry
   MAX-ACCESS  not-accessible
   STATUS      current
   DESCRIPTION
     "This table supports definitions of the configuration
      of SHDSL lines."
   ::= { adEShdslProvisioning 1 }

adEShdslProvEntry OBJECT-TYPE
   SYNTAX      AdEShdslProvEntry
   MAX-ACCESS  not-accessible
   STATUS      current
   DESCRIPTION
     "An entry in the adEShdslProvTable."
   INDEX { ifIndex }
   ::= { adEShdslProvTable 1 }

AdEShdslProvEntry ::=
   SEQUENCE
   {
   adEShdslProvWireInterfaceMode                    	INTEGER,
   adEShdslProvMinLineRate                          	Integer32,
   adEShdslProvMaxLineRate                          	Integer32,
   adEShdslProvG9912Annex                           	INTEGER,
   adEShdslProvCurrCondTargetMargin                 	Integer32,
   adEShdslProvWorstCaseTargetMargin                	Integer32,
   adEShdslProvUsedTargetMargins                    	INTEGER,
   adEShdslProvClockMode                            	INTEGER,
   adEShdslProvLineProbing                          	INTEGER,
   adEShdslProvConstellation                        	INTEGER,
   adEShdslProvPowerBackoff                         	Integer32,
   adEShdslProvName                                 	DisplayString,
   adEShdslProvSpanPower                            	INTEGER,
   adEShdslProvNIUloopback                      	INTEGER,
   adEShdslProvConstellationCrossoverRate		Integer32,
   adEShdslProvAnfp100KhzLoss				Integer32,
   adEShdslProvAnfpTargetMargin				Integer32,
   adEShdslProvEmergencyFreeze                  	INTEGER,
   adEShdslProvExtendedFixedRateAndConstellation 	OCTET STRING,
   adEShdslProvExtendedFixedLastError                   DisplayString,
   adEShdslProvAnfp100KhzLossLetter                     INTEGER,
   adEShdslProvAnfpMaxLineRate                        	Integer32,
   adEShdslProvSCIAlarmThresh                           Integer32,
   adEShdslProvSCIAlarmSeverity                         INTEGER
   }

adEShdslProvWireInterfaceMode OBJECT-TYPE
   SYNTAX      INTEGER
               {
               twoWire(1),
               fourWire(2)
               }
   MAX-ACCESS  read-write
   STATUS      current
   DESCRIPTION
     "This object configures the two-wire or optional four-wire
      operation for SHDSL Lines."
   ::= { adEShdslProvEntry 1 }

adEShdslProvMinLineRate OBJECT-TYPE
   SYNTAX      Integer32
   MAX-ACCESS  read-write
   STATUS      current
   DESCRIPTION
     "This object configures the minimum transmission rate for
      the associated SHDSL Line in bits-per-second (bps).  If
      the minimum line rate equals the maximum line rate
      (adEShdslSpanMaxLineRate), the line rate is considered
      'fixed'.  If the minimum line rate is less than the maximum
      line rate, the line rate is considered 'rate-adaptive'."
   ::= { adEShdslProvEntry 2 }


adEShdslProvMaxLineRate OBJECT-TYPE
   SYNTAX      Integer32
   MAX-ACCESS  read-write
   STATUS      current
   DESCRIPTION
     "This object configures the maximum transmission rate for
      the associated SHDSL Line in bits-per-second (bps).  If
      the minimum line rate equals the maximum line rate
      (adEShdslSpanMaxLineRate), the line rate is considered
      'fixed'.  If the minimum line rate is less than the maximum
      line rate, the line rate is considered 'rate-adaptive'."
   ::= { adEShdslProvEntry 3 }

adEShdslProvG9912Annex OBJECT-TYPE
   SYNTAX      INTEGER
               {
               annexA(1),                       --Region 1
               annexB(2),                       --Region 2
               annexAorB(3),                    --Region 1 or 2
	       efm(4),                          --EFM
	       annexAorEfm(5),                  --Region 1 or EFM
	       annexBorEfm(6),                  --Region 2 or EFM
	       annexAorBorEfm(7)		--Region 1 or 2 or EFM
               }
   MAX-ACCESS  read-write
   STATUS      current
   DESCRIPTION
     "This object specifies the G991.2 Annex setting for the SHDSL
      line."
   ::= { adEShdslProvEntry 4 }

adEShdslProvCurrCondTargetMargin OBJECT-TYPE
   SYNTAX      Integer32
   MAX-ACCESS  read-write
   STATUS      current
   DESCRIPTION
     "This object specifies the current condition target
      SNR margin for a SHDSL line.  The SNR margin is the difference
      between the desired SNR and the actual SNR.  Target SNR margin
      is the desired SNR margin for a unit."
   ::= { adEShdslProvEntry 5 }

adEShdslProvWorstCaseTargetMargin OBJECT-TYPE
   SYNTAX      Integer32
   MAX-ACCESS  read-write
   STATUS      current
   DESCRIPTION
     "This object specifies the worst case target
      SNR margin for a SHDSL line.  The SNR margin is the difference
      between the desired SNR and the actual SNR.  Target SNR margin
      is the desired SNR margin for a unit."
   ::= { adEShdslProvEntry 6 }

adEShdslProvUsedTargetMargins OBJECT-TYPE
   SYNTAX      INTEGER
               {
               currCond(1),
               worstCase(2)
               }
   MAX-ACCESS  read-only
   STATUS      current
   DESCRIPTION
     "Indicates which target SNR margin is enabled currently being used
      in line probing.  This has no meaning if line probing is disabled."
   ::= { adEShdslProvEntry 7 }

adEShdslProvClockMode OBJECT-TYPE
   SYNTAX      INTEGER
               {
               clockMode1(1),                   --Plesio
               clockMode2(2),                   --Plesio w/ Reference
               clockMode3a(3),                  --Sync
               clockMode3b(4)                   --Sync Hybrid
               }
   MAX-ACCESS  read-write
   STATUS      current
   DESCRIPTION
     "This object configures the clock reference for the STU-C
     in a SHDSL Line."
   ::= { adEShdslProvEntry 8 }

adEShdslProvLineProbing OBJECT-TYPE
   SYNTAX      INTEGER
               {
               	disable(1),
               	enableCurrCond(2),
                enableWorseCase(3),
                enableANFP(4),
				enableMaxRate(5),
				enableT1417(6),
				enableG9912(7),
				enableG9912nl(8),
                disableLineProbeEnableExtFixed(9),
                enableANFPWorstCase(10),
                enableANFPCurrentCond(11)
                }
   MAX-ACCESS  read-write
   STATUS      current
   DESCRIPTION
     "This object enables/disables support for Line Probe of
     the units in a SHDSL line.  When Line Probe is enabled, the
     system performs Line Probing to find the best possible
     rate.

     A SET to disable(1) enables fixed rate mode where
     adEShdslProvMinLineRate, adEShdslProvMaxLineRate, and
     adEShdslProvG9912Annex are exchanged with the other endpoints.
     If a common rate and annex is found across all endpoints,
     the span will train.

     A SET to disableLineProbeEnableExtFixed(9) disables line probing
     and enables extended fixed mode.  In this mode, the rate and
     constellation are specified by adEShdslProvExtendedFixedRateAndConstellation.

     A SET to enableANFP(4) enables ANFP mode. In this mode the rate is controlled by
     adEShdslProvAnfp100KhzLoss.

     A SET to enableANFPWorstCase(10) or enableANFPCurrentCond(11) enables ANFP mode.
     In these modes, the rate is controlled by adEShdslProvAnfp100KhzLossLetter."

   ::= { adEShdslProvEntry 9 }

adEShdslProvConstellation OBJECT-TYPE
   SYNTAX      INTEGER
               {
               tcpam16(1),
               tcpam32(2)
               }
   MAX-ACCESS  read-write
   STATUS      current
   DESCRIPTION
     "This object sets the constellation size for each SHDSL
     line.  The selected constellation size is rate dependent.
     16-TCPAM can only be used for rates ranging from 3 to 60
     DS0's (192kbps to 3840kbps).  32-TCPAM can only be used for
     rates ranging from 12 to 89 DS0's (768kbps to 5696kbps)."
     ::= { adEShdslProvEntry 10 }

adEShdslProvPowerBackoff OBJECT-TYPE
   SYNTAX      Integer32
   MAX-ACCESS  read-write
   STATUS      current
   DESCRIPTION
     "This object sets the power backoff value for each SHDSL
     line.  If 255 is selected, the power backoff will automatically
     be applied up to 6 dB.  Valid values for forcing the backoff
     are from 0 to 31dB."
   ::= { adEShdslProvEntry 11 }

adEShdslProvName OBJECT-TYPE
   SYNTAX      DisplayString
   MAX-ACCESS  read-write
   STATUS      current
   DESCRIPTION
     "This object sets a display name associated with the selected
     SHDSL interface."
   ::= { adEShdslProvEntry 12 }

adEShdslProvSpanPower OBJECT-TYPE
   SYNTAX  INTEGER {
           disable(1),
           enable(2)
           }
   MAX-ACCESS  read-write
   STATUS      current
   DESCRIPTION
       "Span power.  This is usually NOT applicable to a remote/NCTE unit.
        Usually only applies for CO equipment (e.g. an access module)."
   ::= { adEShdslProvEntry 13 }

adEShdslProvNIUloopback OBJECT-TYPE
   SYNTAX  INTEGER {
           disable(1),
           enable(2)
           }
   MAX-ACCESS  read-write
   STATUS      current
   DESCRIPTION
       "NIU Loopback enable.  May not be applicate for all units."
   ::= { adEShdslProvEntry 14 }

adEShdslProvConstellationCrossoverRate OBJECT-TYPE
   SYNTAX      Integer32
   MAX-ACCESS  read-write
   STATUS      current
   DESCRIPTION
     "This object defines the rate (in bits per second) at which the number
      of bits per symbol used automatically changes from 3 (16-TCPAM) to
	4 (32-TCPAM). When the SHDSL line rate reaches this value, the \
	constellation size changes to 32-TCPAM. The acceptable range is 12 to
	60 DS0's (768000 to 3840000 bps)."
   ::= { adEShdslProvEntry 15 }

adEShdslProvAnfp100KhzLoss OBJECT-TYPE
   SYNTAX      Integer32
   MAX-ACCESS  read-write
   STATUS      current
   DESCRIPTION
"This object specifies the customer measured loss at 100Khz on the respective
SHDSL line. When adEShdslProvLineProbing is set to enableANFP(4) this value
sets the maximum rate according to the ANFP spec"

   ::= { adEShdslProvEntry 16 }

adEShdslProvAnfpTargetMargin OBJECT-TYPE
   SYNTAX      Integer32
   MAX-ACCESS  read-write
   STATUS      current
   DESCRIPTION
"This object specifies the target SNR margin for a SHDSL line when the ANFP
rate mode has been selected. The SNR margin is the difference between the
desired SNR and the actual SNR. Target SNR margin is the desired SNR
margin for a SHDSL line."
   ::= { adEShdslProvEntry 17 }

adEShdslProvEmergencyFreeze OBJECT-TYPE
   SYNTAX  INTEGER {
           disable(1),
           enable(2)
           }
   MAX-ACCESS  read-write
   STATUS      current
   DESCRIPTION
     "This object controls Emergency Freeze operation which provides enhanced
     immunity to micro interruptions and short duration overvoltage conditions."
   ::= { adEShdslProvEntry 18 }

adEShdslProvExtendedFixedRateAndConstellation OBJECT-TYPE
   SYNTAX  OCTET STRING  (SIZE(2))
   MAX-ACCESS  read-write
   STATUS      current
   DESCRIPTION
     "This object provisions the rate and constellation to be used in Extended Fixed mode.
      The first octet contains the rate in 64kbps increments (Nx64k).  The second octet contains
      the constellation in bits/baud.  One thing to note is that DSP hardware version 2.1 has
      reduced upper limits.  Use adEShdslInvDspHwVersion to retrieve the hardware
      version.  The valid combinations are as follows:

		Constellation		Rates(v2.1)
		-------------		----------
                     1                  1 - 39(34)
                     2                  2 - 79(69)
		     3			3 - 119(104)
		     4			12 - 159(139)
		     5			15 - 199(174)
		     6			18 - 239(204)

     For example, to set the rate to 120 (7680kbps) and the constellation to 5 bits/baud, the octet
     string would be 78 05.  If a SET returns an error, perform a GET on adEShdslProvExtendedFixedLastError
     for details."

   ::= { adEShdslProvEntry 19 }

adEShdslProvExtendedFixedLastError OBJECT-TYPE
   SYNTAX  DisplayString
   MAX-ACCESS  read-only
   STATUS  current
   DESCRIPTION
     "This object returns the last error encountered during a SET of adEShdslProvExtendedFixedRateAndConstellation."

   ::= { adEShdslProvEntry 20 }

 adEShdslProvAnfp100KhzLossLetter OBJECT-TYPE
   SYNTAX      INTEGER {
               ultrashortU(1),
               extrashortX(2),
               shortS(3),
               mediumM(4),
               longL(5)
               }
   MAX-ACCESS  read-write
   STATUS      current
   DESCRIPTION
     "When adEShdslProvLineProbing is set to enableANFPWorstCase(10)
     or enableANFPCurrentCond(11) this object sets the maximum
     rate according to the ANFP spec
      U (Ultra Short, 100k loss<=11)
      X (Extra Short, 100k loss<=21)
      S (Short,       100k loss<=26)
      M (Medium,      100k loss<=29)
      L (Long,        100k loss>=30)"
     ::= { adEShdslProvEntry 21 }

adEShdslProvAnfpMaxLineRate OBJECT-TYPE
   SYNTAX      Integer32
   MAX-ACCESS  read-write
   STATUS      current
   DESCRIPTION
     "This object configures the maximum transmission rate for
      the associated SHDSL Line in bits-per-second (bps) when
      an ANFP training mode is enabled.  The maximum train rate
      of the line will be the minimum of the ANFP limit rate
      (determined by the ANFP 100 Khz Loss Letter), the
      ANFP Max Line Rate, and the rate set by Rate Control (if
      enabled)."
   ::= { adEShdslProvEntry 22 }

adEShdslProvSCIAlarmThresh OBJECT-TYPE
   SYNTAX      Integer32
   MAX-ACCESS  read-write
   STATUS      current
   DESCRIPTION
     "This object configures the SCI alarm threshold for adEShdslSCIThreshCrossed in seconds.
      A value of 0 means the alarm is disabled."
   ::= { adEShdslProvEntry 23 }

adEShdslProvSCIAlarmSeverity OBJECT-TYPE
   SYNTAX         INTEGER {
                         info(2),
                         alert(3),
                         minor(4),
                         major(5),
                         critical(6)
                  }
   MAX-ACCESS     read-write
   STATUS         current
   DESCRIPTION
    "Sets the severity for adEShdslSCIThreshCrossed.
     Valid options listed below:
         critical  (0)
         major     (1)
         minor     (2)
         alert     (3)
         info      (4)"
   DEFVAL  { alert }
   ::= { adEShdslProvEntry 24 }


-- ********************************************
-- SHDSL Alarm Threshold Provisioning
-- ********************************************

adEShdslAlarmProvTable OBJECT-TYPE
   SYNTAX      SEQUENCE OF AdEShdslAlarmProvEntry
   MAX-ACCESS  not-accessible
   STATUS      current
   DESCRIPTION
     "This table supports definitions of the alarm configuration
      of SHDSL lines."
   ::= { adEShdslProvisioning 2 }

adEShdslAlarmProvEntry OBJECT-TYPE
   SYNTAX      AdEShdslAlarmProvEntry
   MAX-ACCESS  not-accessible
   STATUS      current
   DESCRIPTION
     "An entry in the adEShdslAlarmProvTable."
   INDEX { ifIndex, adEShdslInvIndex, adEShdslSideIndex, adEShdslWirePairIndex}
   ::= { adEShdslAlarmProvTable 1 }

AdEShdslAlarmProvEntry ::=
   SEQUENCE
   {
   adEShdslAlarmProvLoopAttenThresh                     Integer32,
   adEShdslAlarmProvSNRMarginThresh                     Integer32,
   adEShdslAlarmProvESThresh                            Integer32,
   adEShdslAlarmProvSESThresh                           Integer32,
   adEShdslAlarmProvUASThresh                           Integer32,
   adEShdslAlarmProvCVCThresh                           Integer32,
   adEShdslAlarmProvLOSWSThresh                         Integer32,
   adEShdslAlarmProvOSThresh                            Integer32,
   adEShdslAlarmProvES24HrThresh                        Integer32,
   adEShdslAlarmProvSES24HrThresh                       Integer32,
   adEShdslAlarmProvUAS24HrThresh                       Integer32,
   adEShdslAlarmProvCVC24HrThresh                       Integer32,
   adEShdslAlarmProvLOSWS24HrThresh                     Integer32,
   adEShdslAlarmProvOS24HrThresh                        Integer32,
   adEShdslAlarmProvRetrains15MinThresh                 Integer32,
   adEShdslAlarmProvHandshakeFailures15MinThresh        Integer32,
   adEShdslAlarmProvRetrains24HrThresh                  Integer32,
   adEShdslAlarmProvHandshakeFailures24HrThresh         Integer32
   }

adEShdslAlarmProvLoopAttenThresh OBJECT-TYPE
   SYNTAX      Integer32
   MAX-ACCESS  read-write
   STATUS      current
   DESCRIPTION
     "This object configures the loop attenuation alarm threshold.
      A value of 0 means the alarm is disabled."
   ::= { adEShdslAlarmProvEntry 1 }

adEShdslAlarmProvSNRMarginThresh OBJECT-TYPE
   SYNTAX      Integer32
   MAX-ACCESS  read-write
   STATUS      current
   DESCRIPTION
     "This object configures the SNR margin alarm threshold.
      A value of 0 means the alarm is disabled."
   ::= { adEShdslAlarmProvEntry 2 }

adEShdslAlarmProvESThresh OBJECT-TYPE
   SYNTAX      Integer32
   MAX-ACCESS  read-write
   STATUS      current
   DESCRIPTION
     "This object configures the 15-Minute Errored Second alarm threshold.
      A value of 0 means the alarm is disabled."
   ::= { adEShdslAlarmProvEntry 3 }

adEShdslAlarmProvSESThresh OBJECT-TYPE
   SYNTAX      Integer32
   MAX-ACCESS  read-write
   STATUS      current
   DESCRIPTION
     "This object configures the 15-Minute Severely Errored Second alarm threshold.
      A value of 0 means the alarm is disabled."
   ::= { adEShdslAlarmProvEntry 4 }

adEShdslAlarmProvUASThresh OBJECT-TYPE
   SYNTAX      Integer32
   MAX-ACCESS  read-write
   STATUS      current
   DESCRIPTION
     "This object configures the 15-Minute Unavailable Second alarm threshold.
      A value of 0 means the alarm is disabled."
   ::= { adEShdslAlarmProvEntry 5 }

adEShdslAlarmProvCVCThresh OBJECT-TYPE
   SYNTAX      Integer32
   MAX-ACCESS  read-write
   STATUS      current
   DESCRIPTION
     "This object configures the 15-Minute Code Violation Count alarm threshold.
      A value of 0 means the alarm is disabled."
   ::= { adEShdslAlarmProvEntry 6 }

adEShdslAlarmProvLOSWSThresh OBJECT-TYPE
   SYNTAX      Integer32
   MAX-ACCESS  read-write
   STATUS      current
   DESCRIPTION
     "This object configures the 15-Minute Loss of Sync Word Second alarm threshold.
      A value of 0 means the alarm is disabled."
   ::= { adEShdslAlarmProvEntry 7 }

adEShdslAlarmProvOSThresh OBJECT-TYPE
   SYNTAX      Integer32(0..900)
   MAX-ACCESS  read-write
   STATUS      current
   DESCRIPTION
     "This object configures the 15-Minute Outage Second alarm threshold.
      A value of 0 means the alarm is disabled."
   ::= { adEShdslAlarmProvEntry 8 }

adEShdslAlarmProvES24HrThresh OBJECT-TYPE
   SYNTAX      Integer32
   MAX-ACCESS  read-write
   STATUS      current
   DESCRIPTION
     "This object configures the 24-Hour Errored Second alarm threshold.
      A value of 0 means the alarm is disabled."
   ::= { adEShdslAlarmProvEntry 9 }

adEShdslAlarmProvSES24HrThresh OBJECT-TYPE
   SYNTAX      Integer32
   MAX-ACCESS  read-write
   STATUS      current
   DESCRIPTION
     "This object configures the 24-Hour Severely Errored Second alarm threshold.
      A value of 0 means the alarm is disabled."
   ::= { adEShdslAlarmProvEntry 10 }

adEShdslAlarmProvUAS24HrThresh OBJECT-TYPE
   SYNTAX      Integer32
   MAX-ACCESS  read-write
   STATUS      current
   DESCRIPTION
     "This object configures the 24-Hour Unavailable Second alarm threshold.
      A value of 0 means the alarm is disabled."
   ::= { adEShdslAlarmProvEntry 11 }

adEShdslAlarmProvCVC24HrThresh OBJECT-TYPE
   SYNTAX      Integer32
   MAX-ACCESS  read-write
   STATUS      current
   DESCRIPTION
     "This object configures the 24-Hour Code Violation Count alarm threshold.
      A value of 0 means the alarm is disabled."
   ::= { adEShdslAlarmProvEntry 12 }

adEShdslAlarmProvLOSWS24HrThresh OBJECT-TYPE
   SYNTAX      Integer32
   MAX-ACCESS  read-write
   STATUS      current
   DESCRIPTION
     "This object configures the 24-Hour Loss of Sync Word Second alarm threshold.
      A value of 0 means the alarm is disabled."
   ::= { adEShdslAlarmProvEntry 13 }

adEShdslAlarmProvOS24HrThresh OBJECT-TYPE
   SYNTAX      Integer32(0..900)
   MAX-ACCESS  read-write
   STATUS      current
   DESCRIPTION
     "This object configures the 24-Hour Outage Second alarm threshold.
      A value of 0 means the alarm is disabled."
   ::= { adEShdslAlarmProvEntry 14 }

adEShdslAlarmProvRetrains15MinThresh OBJECT-TYPE
   SYNTAX      Integer32
   MAX-ACCESS  read-write
   STATUS      current
   DESCRIPTION
     "This object configures the 15 minute alarm threshold for the number
      of times the specified interface transitions from handshaking to
      training.
      A value of 0 means the alarm is disabled."
   ::= { adEShdslAlarmProvEntry 15 }

adEShdslAlarmProvHandshakeFailures15MinThresh OBJECT-TYPE
   SYNTAX      Integer32
   MAX-ACCESS  read-write
   STATUS      current
   DESCRIPTION
     "This object configures the 15 minute alarm threshold for the number
      of times a handshake session fails to converge on the specified interface
      A value of 0 means the alarm is disabled."
   ::= { adEShdslAlarmProvEntry 16 }

adEShdslAlarmProvRetrains24HrThresh OBJECT-TYPE
   SYNTAX      Integer32
   MAX-ACCESS  read-write
   STATUS      current
   DESCRIPTION
     "This object configures the 24 hour alarm threshold for the number
      of times the specified interface transitions from handshaking to
      training.
      A value of 0 means the alarm is disabled."
   ::= { adEShdslAlarmProvEntry 17 }

adEShdslAlarmProvHandshakeFailures24HrThresh OBJECT-TYPE
   SYNTAX      Integer32
   MAX-ACCESS  read-write
   STATUS      current
   DESCRIPTION
     "This object configures the 24 hour alarm threshold for the number
      of times a handshake session fails to converge on the specified interface
      A value of 0 means the alarm is disabled."
   ::= { adEShdslAlarmProvEntry 18 }

-- ********************************************
-- SHDSL Test Provisioning
-- ********************************************

adEShdslTestProvTable OBJECT-TYPE
   SYNTAX      SEQUENCE OF AdEShdslTestProvEntry
   MAX-ACCESS  not-accessible
   STATUS      current
   DESCRIPTION
     "This table supports definitions of the test configuration
      of SHDSL lines."
   ::= { adEShdslProvisioning 3 }

adEShdslTestProvEntry OBJECT-TYPE
   SYNTAX      AdEShdslTestProvEntry
   MAX-ACCESS  not-accessible
   STATUS      current
   DESCRIPTION
     "An entry in the adEShdslTestProvTable."
   INDEX { ifIndex, adEShdslInvIndex }
   ::= { adEShdslTestProvTable 1 }

AdEShdslTestProvEntry ::=
   SEQUENCE
   {
   adEShdslTestProvLoopbackTimeout              Integer32,
   adEShdslTestProvEnumeratedLoopbackTimeout    INTEGER
   }

adEShdslTestProvLoopbackTimeout OBJECT-TYPE
   SYNTAX      Integer32
   MAX-ACCESS  read-write
   STATUS      current
   DESCRIPTION
     "This object configures the loopback timeout.  The
	  timeout is a 12-bit unsigned integer that represents
	  the number of minutes after which the loopback will be
	  removed. A value of 0 means there is no timeout and
	  any loopback will remain until the user removes it.
	  The maximum possible timeout is 4095 minutes, but some
          interfaces may have a lower maximum timeout.  Products that
          support this method do not support adEShdslTestProvEnumeratedLoopbackTimeout."
   ::= { adEShdslTestProvEntry 1 }

adEShdslTestProvEnumeratedLoopbackTimeout OBJECT-TYPE
   SYNTAX  INTEGER {
           timeoutDisabled(1),
           timeout20Minutes(2),
           timeout60Minutes(3),
           timeout120Minutes(4),
           timeout8Hours(5),
           timeout24Hours(6)
           }
   MAX-ACCESS  read-write
   STATUS      current
   DESCRIPTION
     "This object configures the loopback timeout.  The
          timeout is selected from the enumerated list.  Products that
          support this method do not support adEShdslTestProvLoopbackTimeout."
   ::= { adEShdslTestProvEntry 2 }

-- ******************************************************************************************

-- Status Group
--

adEShdslStatusTable OBJECT-TYPE
   SYNTAX      SEQUENCE OF AdEShdslStatusEntry
   MAX-ACCESS  not-accessible
   STATUS      current
   DESCRIPTION
     "This table contains entries that report the current status of each point
      along the SHDSL line."
   ::= { adEShdslStatus 1 }

adEShdslStatusEntry OBJECT-TYPE
   SYNTAX      AdEShdslStatusEntry
   MAX-ACCESS  not-accessible
   STATUS      current
   DESCRIPTION
     "An entry in the adEShdslStatusTable."
   INDEX { ifIndex, adEShdslInvIndex, adEShdslSideIndex, adEShdslWirePairIndex}
   ::= { adEShdslStatusTable 1 }

AdEShdslStatusEntry ::=
   SEQUENCE
   {
   adEShdslStatusCurrStatus                       INTEGER,
   adEShdslStatusCurrLoopAtten                    Integer32,
   adEShdslStatusMinLoopAtten                     Integer32,
   adEShdslStatusMaxLoopAtten                     Integer32,
   adEShdslStatusCurrSNRMargin                    Integer32,
   adEShdslStatusMinSNRMargin                     Integer32,
   adEShdslStatusMaxSNRMargin                     Integer32,
   adEShdslStatusES                               Integer32,
   adEShdslStatusSES                              Integer32,
   adEShdslStatusUAS                              Integer32,
   adEShdslStatusCVC                              Integer32,
   adEShdslStatusLOSWS                            Integer32,
   adEShdslStatusOS                               Integer32,
   adEShdslStatusResetStatistics                  INTEGER,
   adEShdslStatusMaxAttainableRate                Integer32,
   adEShdslStatusUpstreamPBO                      Integer32,
   adEShdslStatusDownstreamPBO                    Integer32,
   adEShdslStatusCurrRate                         Integer32,
   adEShdslStatusRetrains                         Integer32,
   adEShdslStatusHandshakeFailures                Integer32,
   adEShdslStatusCurrSNRMarginCurrTrain           Integer32,
   adEShdslStatusMinSNRMarginCurrTrain            Integer32,
   adEShdslStatusMaxSNRMarginCurrTrain            Integer32,
   adEShdslStatusMinSNRMarginPrevTrain            Integer32,
   adEShdslStatusMaxSNRMarginPrevTrain            Integer32,
   adEShdslStatusPhysicalLinkLabel                DisplayString
   }

adEShdslStatusCurrStatus OBJECT-TYPE
   SYNTAX      INTEGER
               {
               linkDown(1),
               handshaking(2),
               training(3),
               linkUp(4),
               alarmsPresent(5),
               inTest(6)
               }
   MAX-ACCESS  read-only
   STATUS      current
   DESCRIPTION
     "Indicates the current status of the requested SHDSL interface."
   ::= { adEShdslStatusEntry 1 }

adEShdslStatusCurrLoopAtten OBJECT-TYPE
   SYNTAX      Integer32
   MAX-ACCESS  read-only
   STATUS      current
   DESCRIPTION
     "Indicates the current value of the loop attenuation at the requested
      SHDSL interface."
   ::= { adEShdslStatusEntry 2 }

adEShdslStatusMinLoopAtten OBJECT-TYPE
   SYNTAX      Integer32
   MAX-ACCESS  read-only
   STATUS      current
   DESCRIPTION
     "Indicates the minimum value of the loop attenuation since the last reset."
   ::= { adEShdslStatusEntry 3 }

adEShdslStatusMaxLoopAtten OBJECT-TYPE
   SYNTAX      Integer32
   MAX-ACCESS  read-only
   STATUS      current
   DESCRIPTION
     "Indicates the maximum value of the loop attenuation since the last reset."
   ::= { adEShdslStatusEntry 4 }

adEShdslStatusCurrSNRMargin OBJECT-TYPE
   SYNTAX      Integer32
   MAX-ACCESS  read-only
   STATUS      current
   DESCRIPTION
     "Indicates the current value of the SNR margin at the requested
      SHDSL interface."
   ::= { adEShdslStatusEntry 5 }

adEShdslStatusMinSNRMargin OBJECT-TYPE
   SYNTAX      Integer32
   MAX-ACCESS  read-only
   STATUS      current
   DESCRIPTION
     "Indicates the minimum value of the SNR margin since the last reset."
   ::= { adEShdslStatusEntry 6 }

adEShdslStatusMaxSNRMargin OBJECT-TYPE
   SYNTAX      Integer32
   MAX-ACCESS  read-only
   STATUS      current
   DESCRIPTION
     "Indicates the maximum value of the SNR margin since the last reset."
   ::= { adEShdslStatusEntry 7 }

adEShdslStatusES OBJECT-TYPE
   SYNTAX      Integer32
   MAX-ACCESS  read-only
   STATUS      current
   DESCRIPTION
     "Indicates the number of Errored Seconds since the last reset."
   ::= { adEShdslStatusEntry 8 }

adEShdslStatusSES OBJECT-TYPE
   SYNTAX      Integer32
   MAX-ACCESS  read-only
   STATUS      current
   DESCRIPTION
     "Indicates the number of Severely Errored Seconds since the last reset."
   ::= { adEShdslStatusEntry 9 }

adEShdslStatusUAS OBJECT-TYPE
   SYNTAX      Integer32
   MAX-ACCESS  read-only
   STATUS      current
   DESCRIPTION
     "Indicates the number of Unavailable Seconds since the last reset."
   ::= { adEShdslStatusEntry 10 }

adEShdslStatusCVC OBJECT-TYPE
   SYNTAX      Integer32
   MAX-ACCESS  read-only
   STATUS      current
   DESCRIPTION
     "Indicates the number of Code Violations since the last reset."
   ::= { adEShdslStatusEntry 11 }

adEShdslStatusLOSWS OBJECT-TYPE
   SYNTAX      Integer32
   MAX-ACCESS  read-only
   STATUS      current
   DESCRIPTION
     "Indicates the number of Loss of Sync Word Seconds since the last reset."
   ::= { adEShdslStatusEntry 12 }

adEShdslStatusOS OBJECT-TYPE
   SYNTAX      Integer32
   MAX-ACCESS  read-only
   STATUS      current
   DESCRIPTION
     "Indicates the number of Outage Seconds since the last reset."
   ::= { adEShdslStatusEntry 13 }

adEShdslStatusResetStatistics OBJECT-TYPE
   SYNTAX      INTEGER
               {
               reset(1)
               }
   MAX-ACCESS  read-write
   STATUS      current
   DESCRIPTION
     "A SET causes the status information to be reset.  A GET returns a 1."
   ::= { adEShdslStatusEntry 14 }

adEShdslStatusMaxAttainableRate OBJECT-TYPE
   SYNTAX      Integer32
   MAX-ACCESS  read-only
   STATUS      current
   DESCRIPTION
     "Indicates the maximum attainable line rate for this interface in bps."
   ::= { adEShdslStatusEntry 15 }

adEShdslStatusUpstreamPBO OBJECT-TYPE
   SYNTAX      Integer32
   MAX-ACCESS  read-only
   STATUS      current
   DESCRIPTION
     "Indicates the value of the power backoff (in dB) in the upstream direction.
	  (i.e. the closest SHDSL network interface to the endpoint selected."
   ::= { adEShdslStatusEntry 16 }

adEShdslStatusDownstreamPBO OBJECT-TYPE
   SYNTAX      Integer32
   MAX-ACCESS  read-only
   STATUS      current
   DESCRIPTION
     "Indicates the value of the power backoff (in dB) in the downstream direction.
	  (i.e. the closest SHDSL customer interface to the endpoint selected."
   ::= { adEShdslStatusEntry 17 }

adEShdslStatusCurrRate OBJECT-TYPE
   SYNTAX      Integer32
   MAX-ACCESS  read-only
   STATUS      current
   DESCRIPTION
     "This object returns the currently configured rate for
      the associated SHDSL Line in bits-per-second (bps).  This
	  represents the actual rate the line is trained at."
   ::= { adEShdslStatusEntry 18 }

adEShdslStatusRetrains OBJECT-TYPE
   SYNTAX      Integer32
   MAX-ACCESS  read-only
   STATUS      current
   DESCRIPTION
     "Indicates the number of times, since last reset, that
      the specified interface has transitioned from handshaking
      to training."
   ::= { adEShdslStatusEntry 19 }

adEShdslStatusHandshakeFailures OBJECT-TYPE
   SYNTAX      Integer32
   MAX-ACCESS  read-only
   STATUS      current
   DESCRIPTION
     "Indicates the number of times, since last reset, that
      a handshake session failed to converge on the specified
      interface"
   ::= { adEShdslStatusEntry 20 }

adEShdslStatusCurrSNRMarginCurrTrain OBJECT-TYPE
   SYNTAX      Integer32
   MAX-ACCESS  read-only
   STATUS      current
   DESCRIPTION
     "Indicates the current value of the SNR margin at the requested
      SHDSL interface."
   ::= { adEShdslStatusEntry 21 }

adEShdslStatusMinSNRMarginCurrTrain OBJECT-TYPE
   SYNTAX      Integer32
   MAX-ACCESS  read-only
   STATUS      current
   DESCRIPTION
     "Indicates the minimum value of the SNR margin observed since the
      last retrain."
   ::= { adEShdslStatusEntry 22 }

adEShdslStatusMaxSNRMarginCurrTrain OBJECT-TYPE
   SYNTAX      Integer32
   MAX-ACCESS  read-only
   STATUS      current
   DESCRIPTION
     "Indicates the maximum value of the SNR margin observed since the
      last retrain."
   ::= { adEShdslStatusEntry 23 }

adEShdslStatusMinSNRMarginPrevTrain OBJECT-TYPE
   SYNTAX      Integer32
   MAX-ACCESS  read-only
   STATUS      current
   DESCRIPTION
     "Indicates the minimum value of the SNR margin observed before the
      last retrain."
   ::= { adEShdslStatusEntry 24 }

adEShdslStatusMaxSNRMarginPrevTrain OBJECT-TYPE
   SYNTAX      Integer32
   MAX-ACCESS  read-only
   STATUS      current
   DESCRIPTION
     "Indicates the maximum value of the SNR margin observed before the
      last retrain."
   ::= { adEShdslStatusEntry 25 }

adEShdslStatusPhysicalLinkLabel OBJECT-TYPE
   SYNTAX       DisplayString (SIZE(0..1))
   MAX-ACCESS   read-only
   STATUS       current
   DESCRIPTION
     "Returns the label used to physically identify the specified side of an element.
      For example, SHDSL repeaters have an A side and a B side.
      For elements without such a label, this will return an empty string."
   ::= { adEShdslStatusEntry 26 }


adEShdslStatusInfoTable OBJECT-TYPE
   SYNTAX      SEQUENCE OF AdEShdslStatusInfoEntry
   MAX-ACCESS  not-accessible
   STATUS      current
   DESCRIPTION
     "This table contains entries that report the current status of each point
      along the SHDSL line."
   ::= { adEShdslStatus 2 }

adEShdslStatusInfoEntry OBJECT-TYPE
   SYNTAX      AdEShdslStatusInfoEntry
   MAX-ACCESS  not-accessible
   STATUS      current
   DESCRIPTION
     "An entry in the adEShdslStatusInfoTable."
   INDEX { ifIndex }
   ::= { adEShdslStatusInfoTable 1 }

AdEShdslStatusInfoEntry ::=
   SEQUENCE
   {
   adEShdslStatusInfoRepeaterNumber                   Integer32,
   adEShdslStatusInfoPairReversal                     OCTET STRING,
   adEShdslStatusInfoLoopAlarmStatus                  OCTET STRING,
   adEShdslStatusInfoTopology                         OCTET STRING

   }
adEShdslStatusInfoRepeaterNumber   OBJECT-TYPE
   SYNTAX      Integer32
   MAX-ACCESS  read-only
   STATUS      current
   DESCRIPTION
       "Number of repeaters/regenerators detected on this interface"
   ::= { adEShdslStatusInfoEntry 1 }

adEShdslStatusInfoPairReversal OBJECT-TYPE
   SYNTAX      OCTET STRING(SIZE(8))
   MAX-ACCESS  read-only
   STATUS      current
   DESCRIPTION
       "A stream of bytes representing the pair reversal status for
        each span.  The MSB is for span 1 (e.g. from the H4TUC to the
        H4TUR/H4RU1), the next byte is for span 2 (e.g. from the H4RU1 to the
        H4TUR/H4RU2), and next byte is for span 3 (e.g. from the H4RU2 to
        the H4TUR), etc.  For each byte, 0 = pairs not reversed, 1 = pairs
        are reversed.

        If a span is not applicable, such as when no repeaters are present,
        that byte will be zero."
   ::= { adEShdslStatusInfoEntry 2 }

adEShdslStatusInfoLoopAlarmStatus   OBJECT-TYPE
   SYNTAX     OCTET STRING
   MAX-ACCESS read-only
   STATUS     current
   DESCRIPTION
    "A stream of byte codes identifying the current alarm status
     of each DSL loop point.

     For SHDSL:The bytes are in order from the MSB:
     LTU L1, LTU L2, NTU L1, NTU L2, then (if necessary)
         0 = No alarms, loop is up
         1 = loss of sync (LOS)
         2 = running unavailable seconds (UAS)
         3 = running severely errored seconds (SES)
         4 = running errored seconds (ES)
         255 = unknown.

     For HDSL-4:The bytes are in order from the MSB:
     H4TUC L1, H4TUC L2, H4TUR L1, H4TUR L2, then (if necessary)
     H4RU1 Netw L1, H4RU1 Netw L2, H4RU1 Cust L1, H4RU1 Cust L2,
     H4RU2 Netw L1, H4RU2 Netw L2, H4RU2 Cust L1, H4RU2 Cust L2.
     H4RU3 Netw L1, H4RU3 Netw L2, H4RU3 Cust L1, H4RU3 Cust L2.
         0 = No alarms, loop is up
         1 = loss of sync (LOS)
         2 = running unavailable seconds (UAS)
         3 = running severely errored seconds (SES)
         4 = running errored seconds (ES)
         255 = unknown.

     For HDSL-2:The bytes are in order from the MSB:
     H2TUC L1, H2TUR L2, then (if necessary)
     H2RU1 Netw L1, H2RU1 Cust L1.
         0 = No alarms, loop is up
         1 = loss of sync (LOS)
         2 = running unavailable seconds (UAS)
         3 = running severely errored seconds (SES)
         4 = running errored seconds (ES)
         255 = unknown."
   ::= { adEShdslStatusInfoEntry 3 }

adEShdslStatusInfoTopology   OBJECT-TYPE
   SYNTAX     OCTET STRING
   MAX-ACCESS read-only
   STATUS     current
   DESCRIPTION
    "A stream of bytes used to represent the topology of a given circuit.
     The format is show below:

    Version 1
    ---------

                Octet           Description
                -----           -----------
    Common        0             Version number of this OID.  Any time an addition is made, this number shall be incremented.
    Block         1             Total number of elements in this circuit including endpoints(LTU and/or NTU) and repeaters(SRU1-8)

                  0             adEShdslInvIndex
                  1             adEShdslInvPhysicalLinkNumber
    Element       2             adEShdslStatusPhysicalLinkLabel (network side)
    Block         3             adEShdslStatusPhysicalLinkLabel (customer side)
                 4-15           adEShdslInvVendorSerialNumber
                  16            adEShdslStatusCurrStatus
                  17            adEShdslSpliceBadSpliceDetected (network side)
                  18            adEShdslSpliceBadSpliceDetected (customer side)

    Notes:  The Element Block will repeat for each element in the circuit.

    For example, a circuit with an LTU, NTU and 2 repeaters will be constructed like this if the view is from the LTU.

        <Common Block>.<Element Block for LTU>.<Element Block for SRU1>.<Element Block for SRU2>.<Element Block for NTU>
    "
   ::= { adEShdslStatusInfoEntry 4 }

-- ******************************************************************************************
adEShdslStatusIfTable OBJECT-TYPE
   SYNTAX      SEQUENCE OF AdEShdslStatusIfEntry
   MAX-ACCESS  not-accessible
   STATUS      current
   DESCRIPTION
     "This table contains entries that report the current status of each SHDSL interface."
   ::= { adEShdslStatus 3 }

adEShdslStatusIfEntry OBJECT-TYPE
   SYNTAX      AdEShdslStatusIfEntry
   MAX-ACCESS  not-accessible
   STATUS      current
   DESCRIPTION
     "An entry in the adEShdslStatusIfTable."
   INDEX { ifIndex }
   ::= { adEShdslStatusIfTable 1 }

AdEShdslStatusIfEntry ::=
   SEQUENCE
   {
   adEShdslStatusIfTrainingMode                 INTEGER
   }

adEShdslStatusIfTrainingMode OBJECT-TYPE
   SYNTAX      INTEGER
               {
           		ltu(1),                  --same as STUC
           		ntu(2)                   --same as STUR
               }
   MAX-ACCESS  read-only
   STATUS      current
   DESCRIPTION
     "Indicates the mode of the SHDSL interface.  Only valid for products that
	  support direct MIB access."
   ::= { adEShdslStatusIfEntry 1 }


-- ******************************************************************************************

-- Test Group
--

adEShdslTestTable OBJECT-TYPE
   SYNTAX      SEQUENCE OF AdEShdslTestEntry
   MAX-ACCESS  not-accessible
   STATUS      current
   DESCRIPTION
     "This table contains entries that allow the user to run tests at
      different points along the SHDSL line."
   ::= { adEShdslTest 1 }

adEShdslTestEntry OBJECT-TYPE
   SYNTAX      AdEShdslTestEntry
   MAX-ACCESS  not-accessible
   STATUS      current
   DESCRIPTION
     "An entry in the adEShdslTestTable."
   INDEX { ifIndex, adEShdslInvIndex}
   ::= { adEShdslTestTable 1 }

AdEShdslTestEntry ::=
   SEQUENCE
   {
   adEShdslTestLoopback             INTEGER,
   adEShdslTestLoopdownAll          INTEGER,
   adEShdslTestinitMinMax           INTEGER
   }

adEShdslTestLoopback OBJECT-TYPE
   SYNTAX      INTEGER
               {
               dualSidedLoopback(1),
               networkTransparentLoopback(2),
               networkNonTransparentLoopback(3),
               customerTransparentLoopback(4),
               customerNonTransparentLoopback(5),
               noLoopback(6)
               }
   MAX-ACCESS  read-write
   STATUS      current
   DESCRIPTION
     "Controls enabling/disabling loopbacks along each SHDSL interface"
   ::= { adEShdslTestEntry 1 }

adEShdslTestLoopdownAll OBJECT-TYPE
   SYNTAX  INTEGER {
           loopdownAllNow (1)
           }
   MAX-ACCESS  read-write
   STATUS      current
   DESCRIPTION
       "This object is a command to loopdown all the interfaces in the
        circuit when set. This applies to all interfaces currently looped
        back. There is no significance on a get. A get always returns 1,
        but does not imply any status. See the loopback status object for
        loopback settings."
   ::= { adEShdslTestEntry 2 }

adEShdslTestinitMinMax OBJECT-TYPE
   SYNTAX  INTEGER {
           resetMinMax(1)
           }
   MAX-ACCESS  read-write
   STATUS      current
   DESCRIPTION
       "Reset Min/Max characteristics of the Loops.  Always returns 1 on get."
   ::= { adEShdslTestEntry 3 }

-- ********************************************
-- Repeater Powering
-- ********************************************
adEShdslTestRepeaterPoweringTable OBJECT-TYPE
   SYNTAX      SEQUENCE OF AdEShdslTestRepeaterPoweringEntry
   MAX-ACCESS  not-accessible
   STATUS      current
   DESCRIPTION
     "This table contains entries that allow the user control
      the powering sequence of SHDSL repeaters."
   ::= { adEShdslTest 2 }

adEShdslTestRepeaterPoweringEntry OBJECT-TYPE
   SYNTAX      AdEShdslTestRepeaterPoweringEntry
   MAX-ACCESS  not-accessible
   STATUS      current
   DESCRIPTION
     "An entry in the adEShdslTestRepeaterPoweringTable."
   INDEX { ifIndex }
   ::= { adEShdslTestRepeaterPoweringTable 1 }

AdEShdslTestRepeaterPoweringEntry ::=
   SEQUENCE
   {
        adEShdslTestRepeaterPoweringState                INTEGER,
        adEShdslTestRepeaterPoweringNumRepeaters         Integer32,
        adEShdslTestRepeaterPoweringTimeout              Integer32,
        adEShdslTestRepeaterPoweringTimeRemaining        Integer32,
        adEShdslTestRepeaterPoweringSRU1Discovered       TruthValue,
        adEShdslTestRepeaterPoweringSRU2Discovered       TruthValue,
        adEShdslTestRepeaterPoweringSRU3Discovered       TruthValue,
        adEShdslTestRepeaterPoweringSRU4Discovered       TruthValue,
        adEShdslTestRepeaterPoweringShortDetected        INTEGER,
        adEShdslTestRepeaterPoweringGroundFaultDetected  INTEGER,
        adEShdslTestRepeaterPoweringLastErrorString      DisplayString
   }

adEShdslTestRepeaterPoweringState  OBJECT-TYPE
   SYNTAX      INTEGER
               {
                normal(1),
                manual(2)
               }
   MAX-ACCESS  read-write
   STATUS      current
   DESCRIPTION
     "Determines the method by which the repeaters provide power.  The default mode is normal(1) where
      the repeaters read their hardware dip switches to determine whether to send power on to the next
      repeater.  Setting the state to manual(2) allows the user to override the switch settings any
      only power a set number of repeaters.  This is used primarily to diagnose powering issues."
   ::= { adEShdslTestRepeaterPoweringEntry 1 }

adEShdslTestRepeaterPoweringNumRepeaters  OBJECT-TYPE
   SYNTAX      Integer32 (1..4)
   MAX-ACCESS  read-write
   STATUS      current
   DESCRIPTION
     "The number of repeaters to power.  Only valid if adEShdslTestRepeaterPoweringState is set to manual(2)."
   ::= { adEShdslTestRepeaterPoweringEntry 2 }

adEShdslTestRepeaterPoweringTimeout  OBJECT-TYPE
   SYNTAX      Integer32 (0..99999)
   UNITS       "minutes"
   MAX-ACCESS  read-write
   STATUS      current
   DESCRIPTION
     "The amount of time after which adEShdslTestRepeaterPoweringState will be set back to normal(1).
      A value of 0 means there is no timeout and the state will not revert to normal(1) automatically.
      Only valid if adEShdslTestRepeaterPoweringState is set to manual(2)."
   ::= { adEShdslTestRepeaterPoweringEntry 3 }

adEShdslTestRepeaterPoweringTimeRemaining  OBJECT-TYPE
   SYNTAX      Integer32 (0..99999)
   UNITS       "minutes"
   MAX-ACCESS  read-only
   STATUS      current
   DESCRIPTION
     "The amount of time remaining before adEShdslTestRepeaterPoweringState will be set back to normal(1).
      Only valid if adEShdslTestRepeaterPoweringTimeout is non-zero and
      adEShdslTestRepeaterPoweringState is set to manual(2)."
   ::= { adEShdslTestRepeaterPoweringEntry 4 }

adEShdslTestRepeaterPoweringSRU1Discovered  OBJECT-TYPE
   SYNTAX      TruthValue
   MAX-ACCESS  read-only
   STATUS      current
   DESCRIPTION
     "Returns true(1) if SRU1 is present.  Returns false(2) otherwise.
      Only valid if adEShdslTestRepeaterPoweringState is set to manual(2)."
   ::= { adEShdslTestRepeaterPoweringEntry 5 }

adEShdslTestRepeaterPoweringSRU2Discovered  OBJECT-TYPE
   SYNTAX      TruthValue
   MAX-ACCESS  read-only
   STATUS      current
   DESCRIPTION
     "Returns true(1) if SRU2 is present.  Returns false(2) otherwise.
      Only valid if adEShdslTestRepeaterPoweringState is set to manual(2)."
   ::= { adEShdslTestRepeaterPoweringEntry 6 }

adEShdslTestRepeaterPoweringSRU3Discovered  OBJECT-TYPE
   SYNTAX      TruthValue
   MAX-ACCESS  read-only
   STATUS      current
   DESCRIPTION
     "Returns true(1) if SRU3 is present.  Returns false(2) otherwise.
      Only valid if adEShdslTestRepeaterPoweringState is set to manual(2)."
   ::= { adEShdslTestRepeaterPoweringEntry 7 }

adEShdslTestRepeaterPoweringSRU4Discovered  OBJECT-TYPE
   SYNTAX      TruthValue
   MAX-ACCESS  read-only
   STATUS      current
   DESCRIPTION
     "Returns true(1) if SRU4 is present.  Returns false(2) otherwise.
      Only valid if adEShdslTestRepeaterPoweringState is set to manual(2)."
   ::= { adEShdslTestRepeaterPoweringEntry 8 }

adEShdslTestRepeaterPoweringShortDetected  OBJECT-TYPE
   SYNTAX      INTEGER
               {
                none(0),
                sru1(1),
                sru2(2),
                sru3(3),
                sru4(4)
               }
   MAX-ACCESS  read-only
   STATUS      current
   DESCRIPTION
     "Returns the location of a detected powering short.  This will be the repeater
      at the end of the powered span.  Returns none(0) if no short has been detected.
      Only valid if adEShdslTestRepeaterPoweringState is set to manual(2)."
   ::= { adEShdslTestRepeaterPoweringEntry 9 }

adEShdslTestRepeaterPoweringGroundFaultDetected  OBJECT-TYPE
   SYNTAX      INTEGER
               {
                none(0),
                sru1(1),
                sru2(2),
                sru3(3),
                sru4(4)
               }
   MAX-ACCESS  read-only
   STATUS      current
   DESCRIPTION
     "Returns the location of a detected powering ground fault.  This will be the repeater
      at the end of the powered span.  Returns none(0) if no short has been detected.
      Only valid if adEShdslTestRepeaterPoweringState is set to manual(2)."
   ::= { adEShdslTestRepeaterPoweringEntry 10 }

adEShdslTestRepeaterPoweringLastErrorString  OBJECT-TYPE
   SYNTAX      DisplayString
   MAX-ACCESS  read-only
   STATUS      current
   DESCRIPTION
     "Text string describing the last error encountered when attempting to SET one of the entries
      in this table."
   ::= { adEShdslTestRepeaterPoweringEntry 11 }


-- ********************************************
-- Loop Locator
-- ********************************************
adEShdslTestLoopLocatorLastErrorTable OBJECT-TYPE
   SYNTAX      SEQUENCE OF AdEShdslTestLoopLocatorLastErrorEntry
   MAX-ACCESS  not-accessible
   STATUS      current
   DESCRIPTION
     "This table contains the last error message generated by operations on the entries in 
      adEShdslTestLoopLocatorTable."
   ::= { adEShdslTest 3 }

adEShdslTestLoopLocatorLastErrorEntry OBJECT-TYPE
   SYNTAX      AdEShdslTestLoopLocatorLastErrorEntry
   MAX-ACCESS  not-accessible
   STATUS      current
   DESCRIPTION
     "An entry in the adEShdslTestLoopLocatorLastErrorTable."
   INDEX { ifIndex }
   ::= { adEShdslTestLoopLocatorLastErrorTable 1 }

AdEShdslTestLoopLocatorLastErrorEntry ::=
   SEQUENCE
   {
        adEShdslTestLoopLocatorLastErrorString      DisplayString
   }

adEShdslTestLoopLocatorLastErrorString  OBJECT-TYPE
   SYNTAX      DisplayString
   MAX-ACCESS  read-only
   STATUS      current
   DESCRIPTION
     "Text string describing the last error encountered when attempting to SET one of the entries
      in adEShdslTestLoopLocatorTable."
   ::= { adEShdslTestLoopLocatorLastErrorEntry 1 }


adEShdslTestLoopLocatorTable OBJECT-TYPE
   SYNTAX      SEQUENCE OF AdEShdslTestLoopLocatorEntry
   MAX-ACCESS  not-accessible
   STATUS      current
   DESCRIPTION
     "This table contains entries that allows the user to inject modulated noise to identify
      a particular loop with a handset."
   ::= { adEShdslTest 4 }

adEShdslTestLoopLocatorEntry OBJECT-TYPE
   SYNTAX      AdEShdslTestLoopLocatorEntry
   MAX-ACCESS  not-accessible
   STATUS      current
   DESCRIPTION
     "An entry in the adEShdslTestLoopLocatorTable."
   INDEX { ifIndex, adEShdslInvIndex }
   ::= { adEShdslTestLoopLocatorTable 1 }

AdEShdslTestLoopLocatorEntry ::=
   SEQUENCE
   {
        adEShdslTestLoopLocatorState                INTEGER,
        adEShdslTestLoopLocatorTimeout              Integer32,
        adEShdslTestLoopLocatorTimeRemaining        Integer32
   }

adEShdslTestLoopLocatorState  OBJECT-TYPE
   SYNTAX      INTEGER
               {
                disabled(1),
                enabled(2)
               }
   MAX-ACCESS  read-write
   STATUS      current
   DESCRIPTION
     "Activates the loop locator test, injecting modulated noise onto the specified loop.  The default 
      mode is disabled(1). This is primarily used to diagnose wiring issues."
   ::= { adEShdslTestLoopLocatorEntry 1 }

adEShdslTestLoopLocatorTimeout  OBJECT-TYPE
   SYNTAX      Integer32 (0..99999)
   UNITS       "minutes"
   MAX-ACCESS  read-write
   STATUS      current
   DESCRIPTION
     "The amount of time after which adEShdslTestLoopLocatorState will be set back to disabled(1).
      A value of 0 means there is no timeout and the state will not revert to disabled(1) automatically.
      Only valid if adEShdslTestLoopLocatorState is set to enabled(2)."
   ::= { adEShdslTestLoopLocatorEntry 2 }

adEShdslTestLoopLocatorTimeRemaining  OBJECT-TYPE
   SYNTAX      Integer32 (0..99999)
   UNITS       "minutes"
   MAX-ACCESS  read-only
   STATUS      current
   DESCRIPTION
     "The amount of time remaining before adEShdslTestLoopLocatorState will be set back to disabled(1).
      Only valid if adEShdslTestLoopLocatorTimeout is non-zero and adEShdslTestLoopLocatorState is 
      set to enabled(2)."
   ::= { adEShdslTestLoopLocatorEntry 3 }

-- ******************************************************************************************

-- Performance History Group
--

-- ********************************************
-- Current Interval Performance History
-- ********************************************

adEShdslPerfCurrTable OBJECT-TYPE
   SYNTAX      SEQUENCE OF AdEShdslPerfCurrEntry
   MAX-ACCESS  not-accessible
   STATUS      current
   DESCRIPTION
     "This table contains entries that allow the user to retrieve
      the current performance history values at different points
      along the SHDSL line."
   ::= { adEShdslPerformance 1 }

adEShdslPerfCurrEntry OBJECT-TYPE
   SYNTAX      AdEShdslPerfCurrEntry
   MAX-ACCESS  not-accessible
   STATUS      current
   DESCRIPTION
     "An entry in the adEShdslPerfCurrTable."
   INDEX { ifIndex, adEShdslInvIndex, adEShdslSideIndex, adEShdslWirePairIndex }
   ::= { adEShdslPerfCurrTable 1 }

AdEShdslPerfCurrEntry ::=
   SEQUENCE
   {
   adEShdslPerfCurr15MinES                          Integer32,
   adEShdslPerfCurr15MinSES                         Integer32,
   adEShdslPerfCurr15MinUAS                         Integer32,
   adEShdslPerfCurr15MinCVC                         Integer32,
   adEShdslPerfCurr15MinLOSWS                       Integer32,
   adEShdslPerfCurr15MinOS                          Integer32,
   adEShdslPerfCurr24HrES                           Integer32,
   adEShdslPerfCurr24HrSES                          Integer32,
   adEShdslPerfCurr24HrUAS                          Integer32,
   adEShdslPerfCurr24HrCVC                          Integer32,
   adEShdslPerfCurr24HrLOSWS                        Integer32,
   adEShdslPerfCurr24HrOS                           Integer32,
   adEShdslPerf15MinValidIntervals                  Integer32,
   adEShdslPerf24HrValidIntervals                   Integer32,
   adEShdslPerfCurr15MinRetrains                    Integer32,
   adEShdslPerfCurr15MinHandshakeFailures           Integer32,
   adEShdslPerfCurr24HrRetrains                     Integer32,
   adEShdslPerfCurr24HrHandshakeFailures            Integer32,
   adEShdslPerfCurr15MinMinSNRMargin                Integer32,
   adEShdslPerfCurr15MinMaxSNRMargin                Integer32,
   adEShdslPerfCurr24HrMinSNRMargin                 Integer32,
   adEShdslPerfCurr24HrMaxSNRMargin                 Integer32
   }

adEShdslPerfCurr15MinES OBJECT-TYPE
   SYNTAX      Integer32
   MAX-ACCESS  read-only
   STATUS      current
   DESCRIPTION
     "Indicates the number of Errored Seconds in the
      current 15 minute interval."
   ::= { adEShdslPerfCurrEntry 1 }

adEShdslPerfCurr15MinSES OBJECT-TYPE
   SYNTAX      Integer32
   MAX-ACCESS  read-only
   STATUS      current
   DESCRIPTION
     "Indicates the number of Severely Errored Seconds in the
      current 15 minute interval."
   ::= { adEShdslPerfCurrEntry 2 }

adEShdslPerfCurr15MinUAS OBJECT-TYPE
   SYNTAX      Integer32
   MAX-ACCESS  read-only
   STATUS      current
   DESCRIPTION
     "Indicates the number of Unavailable Seconds in the
      current 15 minute interval."
   ::= { adEShdslPerfCurrEntry 3 }

adEShdslPerfCurr15MinCVC OBJECT-TYPE
   SYNTAX      Integer32
   MAX-ACCESS  read-only
   STATUS      current
   DESCRIPTION
     "Indicates the number of Code Violations in the
      current 15 minute interval."
   ::= { adEShdslPerfCurrEntry 4 }

adEShdslPerfCurr15MinLOSWS OBJECT-TYPE
   SYNTAX      Integer32
   MAX-ACCESS  read-only
   STATUS      current
   DESCRIPTION
     "Indicates the number of Loss of Sync Word Seconds in the
      current 15 minute interval."
   ::= { adEShdslPerfCurrEntry 5 }

adEShdslPerfCurr15MinOS OBJECT-TYPE
   SYNTAX      Integer32
   MAX-ACCESS  read-only
   STATUS      current
   DESCRIPTION
     "Indicates the number of Outage Seconds in the
      current 15 minute interval."
   ::= { adEShdslPerfCurrEntry 6 }

adEShdslPerfCurr24HrES OBJECT-TYPE
   SYNTAX      Integer32
   MAX-ACCESS  read-only
   STATUS      current
   DESCRIPTION
     "Indicates the number of Errored Seconds in the
      current 24 hour interval."
   ::= { adEShdslPerfCurrEntry 7 }

adEShdslPerfCurr24HrSES OBJECT-TYPE
   SYNTAX      Integer32
   MAX-ACCESS  read-only
   STATUS      current
   DESCRIPTION
     "Indicates the number of Severely Errored Seconds in the
      current 24 hour interval."
   ::= { adEShdslPerfCurrEntry 8 }

adEShdslPerfCurr24HrUAS OBJECT-TYPE
   SYNTAX      Integer32
   MAX-ACCESS  read-only
   STATUS      current
   DESCRIPTION
     "Indicates the number of Unavailable Seconds in the
      current 24 hour interval."
   ::= { adEShdslPerfCurrEntry 9 }

adEShdslPerfCurr24HrCVC OBJECT-TYPE
   SYNTAX      Integer32
   MAX-ACCESS  read-only
   STATUS      current
   DESCRIPTION
     "Indicates the number of Code Violations in the
      current 24 hour interval."
   ::= { adEShdslPerfCurrEntry 10 }

adEShdslPerfCurr24HrLOSWS OBJECT-TYPE
   SYNTAX      Integer32
   MAX-ACCESS  read-only
   STATUS      current
   DESCRIPTION
     "Indicates the number of Loss of Sync Word Seconds in the
      current 24 hour interval."
   ::= { adEShdslPerfCurrEntry 11 }

adEShdslPerfCurr24HrOS OBJECT-TYPE
   SYNTAX      Integer32
   MAX-ACCESS  read-only
   STATUS      current
   DESCRIPTION
     "Indicates the number of Outage Seconds in the
      current 24 hour interval."
   ::= { adEShdslPerfCurrEntry 12 }

adEShdslPerf15MinValidIntervals OBJECT-TYPE
   SYNTAX      	Integer32
   MAX-ACCESS   read-only
   STATUS       current
   DESCRIPTION
     "The number of valid 15-Minute intervals."
   ::= { adEShdslPerfCurrEntry 13 }

adEShdslPerf24HrValidIntervals OBJECT-TYPE
   SYNTAX      	Integer32
   MAX-ACCESS   read-only
   STATUS       current
   DESCRIPTION
     "The number of valid 24-Hour intervals."
   ::= { adEShdslPerfCurrEntry 14 }

 adEShdslPerfCurr15MinRetrains OBJECT-TYPE
   SYNTAX      Integer32
   MAX-ACCESS  read-only
   STATUS      current
   DESCRIPTION
     "Indicates the number of times in the current 15 minute interval that
      the specified interface has transitioned from handshaking
      to training."
   ::= { adEShdslPerfCurrEntry 15 }

 adEShdslPerfCurr15MinHandshakeFailures OBJECT-TYPE
   SYNTAX      Integer32
   MAX-ACCESS  read-only
   STATUS      current
   DESCRIPTION
     "Indicates the number of times in the current 15 minute interval that
      a handshake session failed to converge on the specified
      interface"
   ::= { adEShdslPerfCurrEntry 16 }

 adEShdslPerfCurr24HrRetrains OBJECT-TYPE
   SYNTAX      Integer32
   MAX-ACCESS  read-only
   STATUS      current
   DESCRIPTION
     "Indicates the number of times in the current 24 hour interval that
      the specified interface has transitioned from handshaking
      to training."
   ::= { adEShdslPerfCurrEntry 17 }

 adEShdslPerfCurr24HrHandshakeFailures OBJECT-TYPE
   SYNTAX      Integer32
   MAX-ACCESS  read-only
   STATUS      current
   DESCRIPTION
     "Indicates the number of times in the current 24 hour interval that
      a handshake session failed to converge on the specified
      interface"
   ::= { adEShdslPerfCurrEntry 18 }

 adEShdslPerfCurr15MinMinSNRMargin OBJECT-TYPE
   SYNTAX      Integer32
   MAX-ACCESS  read-only
   STATUS      current
   DESCRIPTION
     "Indicates the minimum SNR margin observed in the current 15 minute interval."
   ::= { adEShdslPerfCurrEntry 19 }

 adEShdslPerfCurr15MinMaxSNRMargin OBJECT-TYPE
   SYNTAX      Integer32
   MAX-ACCESS  read-only
   STATUS      current
   DESCRIPTION
     "Indicates the maximum SNR margin observed in the current 15 minute interval."
   ::= { adEShdslPerfCurrEntry 20 }

 adEShdslPerfCurr24HrMinSNRMargin OBJECT-TYPE
   SYNTAX      Integer32
   MAX-ACCESS  read-only
   STATUS      current
   DESCRIPTION
     "Indicates the minimum SNR margin observed in the current 24 hour interval."
   ::= { adEShdslPerfCurrEntry 21 }

 adEShdslPerfCurr24HrMaxSNRMargin OBJECT-TYPE
   SYNTAX      Integer32
   MAX-ACCESS  read-only
   STATUS      current
   DESCRIPTION
     "Indicates the maximum SNR margin observed in the current 24 hour interval."
   ::= { adEShdslPerfCurrEntry 22 }


-- ********************************************
-- Prior Interval Performance History
-- ********************************************

adEShdslPerfPriorTable OBJECT-TYPE
   SYNTAX      SEQUENCE OF AdEShdslPerfPriorEntry
   MAX-ACCESS  not-accessible
   STATUS      current
   DESCRIPTION
     "This table contains entries that allow the user to retrieve
      the prior performance history values at different points
      along the SHDSL line."
   ::= { adEShdslPerformance 2 }

adEShdslPerfPriorEntry OBJECT-TYPE
   SYNTAX      AdEShdslPerfPriorEntry
   MAX-ACCESS  not-accessible
   STATUS      current
   DESCRIPTION
     "An entry in the adEShdslPerfPriorTable."
   INDEX { ifIndex, adEShdslInvIndex, adEShdslSideIndex, adEShdslWirePairIndex }
   ::= { adEShdslPerfPriorTable 1 }

AdEShdslPerfPriorEntry ::=
   SEQUENCE
   {
   adEShdslPerfPrior15MinES                          Integer32,
   adEShdslPerfPrior15MinSES                         Integer32,
   adEShdslPerfPrior15MinUAS                         Integer32,
   adEShdslPerfPrior15MinCVC                         Integer32,
   adEShdslPerfPrior15MinLOSWS                       Integer32,
   adEShdslPerfPrior15MinOS                          Integer32,
   adEShdslPerfPrior24HrES                           Integer32,
   adEShdslPerfPrior24HrSES                          Integer32,
   adEShdslPerfPrior24HrUAS                          Integer32,
   adEShdslPerfPrior24HrCVC                          Integer32,
   adEShdslPerfPrior24HrLOSWS                        Integer32,
   adEShdslPerfPrior24HrOS                           Integer32
   }

adEShdslPerfPrior15MinES OBJECT-TYPE
   SYNTAX      Integer32
   MAX-ACCESS  read-only
   STATUS      current
   DESCRIPTION
     "Indicates the number of Errored Seconds in the
      prior 15 minute interval."
   ::= { adEShdslPerfPriorEntry 1 }

adEShdslPerfPrior15MinSES OBJECT-TYPE
   SYNTAX      Integer32
   MAX-ACCESS  read-only
   STATUS      current
   DESCRIPTION
     "Indicates the number of Severely Errored Seconds in the
      prior 15 minute interval."
   ::= { adEShdslPerfPriorEntry 2 }

adEShdslPerfPrior15MinUAS OBJECT-TYPE
   SYNTAX      Integer32
   MAX-ACCESS  read-only
   STATUS      current
   DESCRIPTION
     "Indicates the number of Unavailable Seconds in the
      prior 15 minute interval."
   ::= { adEShdslPerfPriorEntry 3 }

adEShdslPerfPrior15MinCVC OBJECT-TYPE
   SYNTAX      Integer32
   MAX-ACCESS  read-only
   STATUS      current
   DESCRIPTION
     "Indicates the number of Code Violations in the
      prior 15 minute interval."
   ::= { adEShdslPerfPriorEntry 4 }

adEShdslPerfPrior15MinLOSWS OBJECT-TYPE
   SYNTAX      Integer32
   MAX-ACCESS  read-only
   STATUS      current
   DESCRIPTION
     "Indicates the number of Loss of Sync Word Seconds in the
      prior 15 minute interval."
   ::= { adEShdslPerfPriorEntry 5 }

adEShdslPerfPrior15MinOS OBJECT-TYPE
   SYNTAX      Integer32
   MAX-ACCESS  read-only
   STATUS      current
   DESCRIPTION
     "Indicates the number of Outage Seconds in the
      prior 15 minute interval."
   ::= { adEShdslPerfPriorEntry 6 }

adEShdslPerfPrior24HrES OBJECT-TYPE
   SYNTAX      Integer32
   MAX-ACCESS  read-only
   STATUS      current
   DESCRIPTION
     "Indicates the number of Errored Seconds in the
      prior 24 hour interval."
   ::= { adEShdslPerfPriorEntry 7 }

adEShdslPerfPrior24HrSES OBJECT-TYPE
   SYNTAX      Integer32
   MAX-ACCESS  read-only
   STATUS      current
   DESCRIPTION
     "Indicates the number of Severely Errored Seconds in the
      prior 24 hour interval."
   ::= { adEShdslPerfPriorEntry 8 }

adEShdslPerfPrior24HrUAS OBJECT-TYPE
   SYNTAX      Integer32
   MAX-ACCESS  read-only
   STATUS      current
   DESCRIPTION
     "Indicates the number of Unavailable Seconds in the
      prior 24 hour interval."
   ::= { adEShdslPerfPriorEntry 9 }

adEShdslPerfPrior24HrCVC OBJECT-TYPE
   SYNTAX      Integer32
   MAX-ACCESS  read-only
   STATUS      current
   DESCRIPTION
     "Indicates the number of Code Violations in the
      prior 24 hour interval."
   ::= { adEShdslPerfPriorEntry 10 }

adEShdslPerfPrior24HrLOSWS OBJECT-TYPE
   SYNTAX      Integer32
   MAX-ACCESS  read-only
   STATUS      current
   DESCRIPTION
     "Indicates the number of Loss of Sync Word Seconds in the
      prior 24 hour interval."
   ::= { adEShdslPerfPriorEntry 11 }

adEShdslPerfPrior24HrOS OBJECT-TYPE
   SYNTAX      Integer32
   MAX-ACCESS  read-only
   STATUS      current
   DESCRIPTION
     "Indicates the number of Outage Seconds in the
      prior 24 hour interval."
   ::= { adEShdslPerfPriorEntry 12 }

-- ********************************************
-- Performance History Reset
-- ********************************************

adEShdslPerfResetTable OBJECT-TYPE
   SYNTAX      SEQUENCE OF AdEShdslPerfResetEntry
   MAX-ACCESS  not-accessible
   STATUS      current
   DESCRIPTION
     "This table contains entries that allow the user to reset
      the performance history values at different points
      along the SHDSL line."
   ::= { adEShdslPerformance 3 }

adEShdslPerfResetEntry OBJECT-TYPE
   SYNTAX      AdEShdslPerfResetEntry
   MAX-ACCESS  not-accessible
   STATUS      current
   DESCRIPTION
     "An entry in the adEShdslPerfResetTable."
   INDEX { ifIndex, adEShdslInvIndex, adEShdslSideIndex, adEShdslWirePairIndex }
   ::= { adEShdslPerfResetTable 1 }

AdEShdslPerfResetEntry ::=
   SEQUENCE
   {
   adEShdslPerfReset			INTEGER
   }

adEShdslPerfReset OBJECT-TYPE
   SYNTAX      INTEGER
   			   {
			   reset(1)
			   }
   MAX-ACCESS  read-write
   STATUS      current
   DESCRIPTION
     "Resets the performance history values on the selected interface."
   ::= { adEShdslPerfResetEntry 1 }

-- ********************************************
-- 15 Minute Interval Performance History
-- ********************************************

adEShdslPerf15MinIntTable OBJECT-TYPE
   SYNTAX      SEQUENCE OF AdEShdslPerf15MinIntEntry
   MAX-ACCESS  not-accessible
   STATUS      current
   DESCRIPTION
     "This table contains entries that allow the user to retrieve
      the 15 minute performance history values at different points
      along the SHDSL line."
   ::= { adEShdslPerformance 4 }

adEShdslPerf15MinIntEntry OBJECT-TYPE
   SYNTAX      AdEShdslPerf15MinIntEntry
   MAX-ACCESS  not-accessible
   STATUS      current
   DESCRIPTION
     "An entry in the adEShdslPerf15MinIntTable."
   INDEX { ifIndex, adEShdslInvIndex, adEShdslSideIndex, adEShdslWirePairIndex, adEShdslPerf15MinIntNumber }
   ::= { adEShdslPerf15MinIntTable 1 }

AdEShdslPerf15MinIntEntry ::=
   SEQUENCE
   {
   adEShdslPerf15MinIntNumber                      Integer32,
   adEShdslPerf15MinIntES                          Integer32,
   adEShdslPerf15MinIntSES                         Integer32,
   adEShdslPerf15MinIntUAS                         Integer32,
   adEShdslPerf15MinIntCVC                         Integer32,
   adEShdslPerf15MinIntLOSWS                       Integer32,
   adEShdslPerf15MinIntOS                          Integer32,
   adEShdslPerf15MinIntRetrains                    Integer32,
   adEShdslPerf15MinIntHandshakeFailures           Integer32,
   adEShdslPerf15MinIntMinSNRMargin                Integer32,
   adEShdslPerf15MinIntMaxSNRMargin                Integer32
   }

adEShdslPerf15MinIntNumber OBJECT-TYPE
   SYNTAX      	Integer32
   MAX-ACCESS   read-only
   STATUS       current
   DESCRIPTION
     "15-minute performance interval.  Interval 1 represents the most recent
	  previous interval.  Interval 96 represents 24 hours ago.  Intervals 2
	  through 96 are optional."
   ::= { adEShdslPerf15MinIntEntry 1 }

adEShdslPerf15MinIntES OBJECT-TYPE
   SYNTAX      Integer32
   MAX-ACCESS  read-only
   STATUS      current
   DESCRIPTION
     "Indicates the number of Errored Seconds in the
      selected 15 minute interval."
   ::= { adEShdslPerf15MinIntEntry 2 }

adEShdslPerf15MinIntSES OBJECT-TYPE
   SYNTAX      Integer32
   MAX-ACCESS  read-only
   STATUS      current
   DESCRIPTION
     "Indicates the number of Severely Errored Seconds in the
      selected 15 minute interval."
   ::= { adEShdslPerf15MinIntEntry 3 }

adEShdslPerf15MinIntUAS OBJECT-TYPE
   SYNTAX      Integer32
   MAX-ACCESS  read-only
   STATUS      current
   DESCRIPTION
     "Indicates the number of Unavailable Seconds in the
      selected 15 minute interval."
   ::= { adEShdslPerf15MinIntEntry 4 }

adEShdslPerf15MinIntCVC OBJECT-TYPE
   SYNTAX      Integer32
   MAX-ACCESS  read-only
   STATUS      current
   DESCRIPTION
     "Indicates the number of Code Violations in the
      selected 15 minute interval."
   ::= { adEShdslPerf15MinIntEntry 5 }

adEShdslPerf15MinIntLOSWS OBJECT-TYPE
   SYNTAX      Integer32
   MAX-ACCESS  read-only
   STATUS      current
   DESCRIPTION
     "Indicates the number of Loss of Sync Word Seconds in the
      selected 15 minute interval."
   ::= { adEShdslPerf15MinIntEntry 6 }

adEShdslPerf15MinIntOS OBJECT-TYPE
   SYNTAX      Integer32
   MAX-ACCESS  read-only
   STATUS      current
   DESCRIPTION
     "Indicates the number of Outage Seconds in the
      selected 15 minute interval."
   ::= { adEShdslPerf15MinIntEntry 7 }

 adEShdslPerf15MinIntRetrains OBJECT-TYPE
   SYNTAX      Integer32
   MAX-ACCESS  read-only
   STATUS      current
   DESCRIPTION
     "Indicates the number of times in the selected 15 minute interval that
      the specified interface has transitioned from handshaking
      to training."
   ::= { adEShdslPerf15MinIntEntry 8 }

 adEShdslPerf15MinIntHandshakeFailures OBJECT-TYPE
   SYNTAX      Integer32
   MAX-ACCESS  read-only
   STATUS      current
   DESCRIPTION
     "Indicates the number of times in the selected 15 minute interval that
      a handshake session failed to converge on the specified
      interface"
   ::= { adEShdslPerf15MinIntEntry 9 }

 adEShdslPerf15MinIntMinSNRMargin OBJECT-TYPE
   SYNTAX      Integer32
   MAX-ACCESS  read-only
   STATUS      current
   DESCRIPTION
     "Indicates the minimum SNR margin observed in the specified 15 minute interval."
   ::= { adEShdslPerf15MinIntEntry 10 }

 adEShdslPerf15MinIntMaxSNRMargin OBJECT-TYPE
   SYNTAX      Integer32
   MAX-ACCESS  read-only
   STATUS      current
   DESCRIPTION
     "Indicates the maximum SNR margin observed in the specified 15 minute interval."
   ::= { adEShdslPerf15MinIntEntry 11 }

-- ********************************************
-- 24 hour Interval Performance History
-- ********************************************

adEShdslPerf24HrIntTable OBJECT-TYPE
   SYNTAX      SEQUENCE OF AdEShdslPerf24HrIntEntry
   MAX-ACCESS  not-accessible
   STATUS      current
   DESCRIPTION
     "This table contains entries that allow the user to retrieve
      the 24 hour performance history values at different points
      along the SHDSL line."
   ::= { adEShdslPerformance 5 }

adEShdslPerf24HrIntEntry OBJECT-TYPE
   SYNTAX      AdEShdslPerf24HrIntEntry
   MAX-ACCESS  not-accessible
   STATUS      current
   DESCRIPTION
     "An entry in the adEShdslPerf24HrIntTable."
   INDEX { ifIndex, adEShdslInvIndex, adEShdslSideIndex, adEShdslWirePairIndex, adEShdslPerf24HrIntNumber }
   ::= { adEShdslPerf24HrIntTable 1 }

AdEShdslPerf24HrIntEntry ::=
   SEQUENCE
   {
   adEShdslPerf24HrIntNumber                      Integer32,
   adEShdslPerf24HrIntES                          Integer32,
   adEShdslPerf24HrIntSES                         Integer32,
   adEShdslPerf24HrIntUAS                         Integer32,
   adEShdslPerf24HrIntCVC                         Integer32,
   adEShdslPerf24HrIntLOSWS                       Integer32,
   adEShdslPerf24HrIntOS                          Integer32,
   adEShdslPerf24HrIntRetrains                    Integer32,
   adEShdslPerf24HrIntHandshakeFailures           Integer32,
   adEShdslPerf24HrIntMinSNRMargin                Integer32,
   adEShdslPerf24HrIntMaxSNRMargin                Integer32
   }

adEShdslPerf24HrIntNumber OBJECT-TYPE
   SYNTAX      	Integer32
   MAX-ACCESS   read-only
   STATUS       current
   DESCRIPTION
     "24-hour performance interval.  Interval 1 represents the most recent
	  previous interval.  Interval 7 represents 7 days ago.  Intervals 2
          through 7 are optional.  Also, intervals 8 through 30 are optional."
   ::= { adEShdslPerf24HrIntEntry 1 }

adEShdslPerf24HrIntES OBJECT-TYPE
   SYNTAX      Integer32
   MAX-ACCESS  read-only
   STATUS      current
   DESCRIPTION
     "Indicates the number of Errored Seconds in the
      selected 24 hour interval."
   ::= { adEShdslPerf24HrIntEntry 2 }

adEShdslPerf24HrIntSES OBJECT-TYPE
   SYNTAX      Integer32
   MAX-ACCESS  read-only
   STATUS      current
   DESCRIPTION
     "Indicates the number of Severely Errored Seconds in the
      selected 24 hour interval."
   ::= { adEShdslPerf24HrIntEntry 3 }

adEShdslPerf24HrIntUAS OBJECT-TYPE
   SYNTAX      Integer32
   MAX-ACCESS  read-only
   STATUS      current
   DESCRIPTION
     "Indicates the number of Unavailable Seconds in the
      selected 24 hour interval."
   ::= { adEShdslPerf24HrIntEntry 4 }

adEShdslPerf24HrIntCVC OBJECT-TYPE
   SYNTAX      Integer32
   MAX-ACCESS  read-only
   STATUS      current
   DESCRIPTION
     "Indicates the number of Code Violations in the
      selected 24 hour interval."
   ::= { adEShdslPerf24HrIntEntry 5 }

adEShdslPerf24HrIntLOSWS OBJECT-TYPE
   SYNTAX      Integer32
   MAX-ACCESS  read-only
   STATUS      current
   DESCRIPTION
     "Indicates the number of Loss of Sync Word Seconds in the
      selected 24 hour interval."
   ::= { adEShdslPerf24HrIntEntry 6 }

adEShdslPerf24HrIntOS OBJECT-TYPE
   SYNTAX      Integer32
   MAX-ACCESS  read-only
   STATUS      current
   DESCRIPTION
     "Indicates the number of Outage Seconds in the
      selected 24 hour interval."
   ::= { adEShdslPerf24HrIntEntry 7 }

 adEShdslPerf24HrIntRetrains OBJECT-TYPE
   SYNTAX      Integer32
   MAX-ACCESS  read-only
   STATUS      current
   DESCRIPTION
     "Indicates the number of times in the selected 24 hour interval that
      the specified interface has transitioned from handshaking
      to training."
   ::= { adEShdslPerf24HrIntEntry 8 }

 adEShdslPerf24HrIntHandshakeFailures OBJECT-TYPE
   SYNTAX      Integer32
   MAX-ACCESS  read-only
   STATUS      current
   DESCRIPTION
     "Indicates the number of times in the selected 24 hour interval that
      a handshake session failed to converge on the specified
      interface"
   ::= { adEShdslPerf24HrIntEntry 9 }

 adEShdslPerf24HrIntMinSNRMargin OBJECT-TYPE
   SYNTAX      Integer32
   MAX-ACCESS  read-only
   STATUS      current
   DESCRIPTION
     "Indicates the minimum SNR margin observed in the specified 24 hour interval."
   ::= { adEShdslPerf24HrIntEntry 10 }

 adEShdslPerf24HrIntMaxSNRMargin OBJECT-TYPE
   SYNTAX      Integer32
   MAX-ACCESS  read-only
   STATUS      current
   DESCRIPTION
     "Indicates the maximum SNR margin observed in the specified 24 hour interval."
   ::= { adEShdslPerf24HrIntEntry 11 }

-- ********************************************
-- Performance History Port Reset
-- ********************************************

adEShdslPerfPortResetTable OBJECT-TYPE
   SYNTAX      SEQUENCE OF AdEShdslPerfPortResetEntry
   MAX-ACCESS  not-accessible
   STATUS      current
   DESCRIPTION
     "This table contains entries that allow the user to reset
      the performance history values for each SHDSL port."
   ::= { adEShdslPerformance 6 }

adEShdslPerfPortResetEntry OBJECT-TYPE
   SYNTAX      AdEShdslPerfPortResetEntry
   MAX-ACCESS  not-accessible
   STATUS      current
   DESCRIPTION
     "An entry in the adEShdslPerfPortResetTable."
   INDEX { ifIndex }
   ::= { adEShdslPerfPortResetTable 1 }

AdEShdslPerfPortResetEntry ::=
   SEQUENCE
   {
   adEShdslPerfPortReset                    INTEGER
   }

adEShdslPerfPortReset OBJECT-TYPE
   SYNTAX      INTEGER
               {
               reset(1)
               }
   MAX-ACCESS  read-write
   STATUS      current
   DESCRIPTION
     "Resets the performance history values for all interfaces connected to
      the selected port."
   ::= { adEShdslPerfPortResetEntry 1 }



-- ******************************************************************************************
-- Splice Detect Group
--

adEShdslSpliceDetectionTable OBJECT-TYPE
   SYNTAX      SEQUENCE OF AdEShdslSpliceDetectionEntry
   MAX-ACCESS  not-accessible
   STATUS      current
   DESCRIPTION
     "This table contains entries that allow the user to retrieve
      the splice detection data."
   ::= { adEShdslSpliceDetection 1 }

adEShdslSpliceDetectionEntry OBJECT-TYPE
   SYNTAX      AdEShdslSpliceDetectionEntry
   MAX-ACCESS  not-accessible
   STATUS      current
   DESCRIPTION
     "An entry in the adEShdslSpliceDetectionTable."
   INDEX { ifIndex, adEShdslInvIndex, adEShdslSideIndex, adEShdslWirePairIndex }
   ::= { adEShdslSpliceDetectionTable 1 }

AdEShdslSpliceDetectionEntry ::=
   SEQUENCE
   {
   adEShdslSpliceDetectionSummary		DisplayString,
   adEShdslSpliceCounts				DisplayString,
   adEShdslSpliceDistances			DisplayString,
   adEShdslSpliceRestart			INTEGER,
   adEShdslSpliceDistanceType                   INTEGER,
   adEShdslSpliceRate                           Integer32,
   adEShdslSpliceBadSpliceDetected              TruthValue
   }

adEShdslSpliceDetectionSummary OBJECT-TYPE
   SYNTAX      DisplayString
   MAX-ACCESS  read-only
   STATUS      current
   DESCRIPTION
     "The splice detection summary for this endpoint.
      A series of items in the following format:  STR0.STR1.STR2 ... STR14
      representing the daily splice detection summary.  The first item (STR1)
      represents the current day, the second is one day back, and so on.
      The potential items are loss of sync (LOS), no trouble found (NTF), or
      a number representing the approximate distance at which a splice event is
      believed to have occured for that day."
   ::= { adEShdslSpliceDetectionEntry 1 }

adEShdslSpliceCounts OBJECT-TYPE
   SYNTAX      DisplayString
   MAX-ACCESS  read-only
   STATUS      current
   DESCRIPTION
     "A series of numbers (0-99) in the following format:  N0.N1.N3 ... N17
      These values represent the splice detection histogram values for the
      corresponding distance values from adEShdslSpliceDistances.  Note that
      some rates may not support 18 counts."
   ::= { adEShdslSpliceDetectionEntry 2 }

adEShdslSpliceDistances OBJECT-TYPE
   SYNTAX      DisplayString
   MAX-ACCESS  read-only
   STATUS      current
   DESCRIPTION
     "A series of distances in the following format:  D0.D1.D3 ... D17
      These values represent the distances corresponding to each bucket
      in the splice detection histogram.  Note that some rates may not
	  support 18 distances"
   ::= { adEShdslSpliceDetectionEntry 3 }

adEShdslSpliceRestart OBJECT-TYPE
   SYNTAX      INTEGER
               {
		   restart(1)
               }
   MAX-ACCESS  read-write
   STATUS      current
   DESCRIPTION
     "Restarts the splice detection on the selected interface.  This
      will cause all 24 hour counts for this interface to be cleared."
   ::= { adEShdslSpliceDetectionEntry 4 }

adEShdslSpliceDistanceType OBJECT-TYPE
   SYNTAX      INTEGER
               {
		   meters(1),
		   feet(2)
               }
   MAX-ACCESS  read-write
   STATUS      current
   DESCRIPTION
     "Sets the unit of measurement used when returning the values for
	  adEShdslSpliceDistances.  This value is set globally for the unit
	  and will return the same value for all interfaces on the unit."
   ::= { adEShdslSpliceDetectionEntry 5 }

adEShdslSpliceRate OBJECT-TYPE
   SYNTAX      Integer32
   MAX-ACCESS  read-only
   STATUS      current
   DESCRIPTION
     "A last trained rate during the current interval.  The value returned is the
      rate in 64kbps increments (N x 64k)."

   ::= { adEShdslSpliceDetectionEntry 6 }

adEShdslSpliceBadSpliceDetected OBJECT-TYPE
   SYNTAX      TruthValue
   MAX-ACCESS  read-only
   STATUS      current
   DESCRIPTION
     "Returns true if a bad splice has been detected on the specified interface.  Returns false otherwise."

   ::= { adEShdslSpliceDetectionEntry 7 }


-- ******************************************************************************************
-- Splice Detect 24 Hour Interval History
-- ******************************************************************************************
adEShdslSpliceDet24HrIntTable OBJECT-TYPE
   SYNTAX      SEQUENCE OF AdEShdslSpliceDet24HrIntEntry
   MAX-ACCESS  not-accessible
   STATUS      current
   DESCRIPTION
     "This table contains entries that allow the user to retrieve
      24 hour splice detection historical interval data."
   ::= { adEShdslSpliceDetection 2 }

adEShdslSpliceDet24HrIntEntry OBJECT-TYPE
   SYNTAX      AdEShdslSpliceDet24HrIntEntry
   MAX-ACCESS  not-accessible
   STATUS      current
   DESCRIPTION
     "An entry in the adEShdslSpliceDet24HrIntTable."
   INDEX { ifIndex, adEShdslInvIndex, adEShdslSideIndex, adEShdslWirePairIndex, adEShdslSpliceDet24HrIntNumber }
   ::= { adEShdslSpliceDet24HrIntTable 1 }

AdEShdslSpliceDet24HrIntEntry ::=
   SEQUENCE
   {
   adEShdslSpliceDet24HrIntNumber       Integer32,
   adEShdslSplice24HrIntCounts		DisplayString,
   adEShdslSplice24HrIntDistances	DisplayString,
   adEShdslSplice24HrIntRate		Integer32
   }

adEShdslSpliceDet24HrIntNumber OBJECT-TYPE
   SYNTAX      	Integer32
   MAX-ACCESS   read-only
   STATUS       current
   DESCRIPTION
     "24-hour splice detect interval.  Interval 1 represents the most recent
	  previous interval.  Interval 7 represents 7 days ago.  Intervals 2
          through 7 are optional."
   ::= { adEShdslSpliceDet24HrIntEntry 1 }

adEShdslSplice24HrIntCounts OBJECT-TYPE
   SYNTAX      DisplayString
   MAX-ACCESS  read-only
   STATUS      current
   DESCRIPTION
     "A series of numbers (0-99) in the following format:  N0.N1.N3 ... N17
      These values represent the splice detection histogram values for the
      corresponding distance values from adEShdslSpliceDistances for the selected
      interval. Note that some rates may not support 18 counts."
   ::= { adEShdslSpliceDet24HrIntEntry 2 }

adEShdslSplice24HrIntDistances OBJECT-TYPE
   SYNTAX      DisplayString
   MAX-ACCESS  read-only
   STATUS      current
   DESCRIPTION
     "A series of distances in the following format:  D0.D1.D3 ... D17
      These values represent the distances corresponding to each bucket in the splice detection
      histogram for the selected interval. Note that some rates may not support 18 distances"
   ::= { adEShdslSpliceDet24HrIntEntry 3 }

adEShdslSplice24HrIntRate OBJECT-TYPE
   SYNTAX      Integer32
   MAX-ACCESS  read-only
   STATUS      current
   DESCRIPTION
     "A last trained rate during the specified interval.  The value returned is the
      rate in 64kbps increments (N x 64k)."

   ::= { adEShdslSpliceDet24HrIntEntry 4 }

-- ******************************************************************************************
-- Splice Detect 15 Minute Current Interval
-- ******************************************************************************************
adEShdslSpliceDet15MinCurrTable OBJECT-TYPE
   SYNTAX      SEQUENCE OF AdEShdslSpliceDet15MinCurrEntry
   MAX-ACCESS  not-accessible
   STATUS      current
   DESCRIPTION
     "This table contains entries that allow the user to retrieve
      15 minute splice detection current interval data."
   ::= { adEShdslSpliceDetection 3 }

adEShdslSpliceDet15MinCurrEntry OBJECT-TYPE
   SYNTAX      AdEShdslSpliceDet15MinCurrEntry
   MAX-ACCESS  not-accessible
   STATUS      current
   DESCRIPTION
     "An entry in the adEShdslSpliceDet15MinCurrTable."
   INDEX { ifIndex, adEShdslInvIndex, adEShdslSideIndex, adEShdslWirePairIndex }
   ::= { adEShdslSpliceDet15MinCurrTable 1 }

AdEShdslSpliceDet15MinCurrEntry ::=
   SEQUENCE
   {
   adEShdslSplice15MinCurrCounts	  DisplayString,
   adEShdslSplice15MinCurrDistances	  DisplayString,
   adEShdslSplice15MinCurrRate		  Integer32
   }

adEShdslSplice15MinCurrCounts OBJECT-TYPE
   SYNTAX      DisplayString
   MAX-ACCESS  read-only
   STATUS      current
   DESCRIPTION
     "A series of numbers (0-99) in the following format:  N0.N1.N3 ... N17
      These values represent the splice detection histogram values for the
      corresponding distance values from adEShdslSpliceDistances for the selected
      interval. Note that some rates may not support 18 counts."
   ::= { adEShdslSpliceDet15MinCurrEntry 1 }

adEShdslSplice15MinCurrDistances OBJECT-TYPE
   SYNTAX      DisplayString
   MAX-ACCESS  read-only
   STATUS      current
   DESCRIPTION
     "A series of distances in the following format:  D0.D1.D3 ... D17
      These values represent the distances corresponding to each bucket in the splice detection
      histogram for the current interval. Note that some rates may not support 18 distances"
   ::= { adEShdslSpliceDet15MinCurrEntry 2 }

adEShdslSplice15MinCurrRate OBJECT-TYPE
   SYNTAX      Integer32
   MAX-ACCESS  read-only
   STATUS      current
   DESCRIPTION
     "A last trained rate during the current interval.  The value returned is the
      rate in 64kbps increments (N x 64k)."

   ::= { adEShdslSpliceDet15MinCurrEntry 3 }

-- ******************************************************************************************
-- Splice Detect 15 Minute Interval History
-- ******************************************************************************************
adEShdslSpliceDet15MinIntTable OBJECT-TYPE
   SYNTAX      SEQUENCE OF AdEShdslSpliceDet15MinIntEntry
   MAX-ACCESS  not-accessible
   STATUS      current
   DESCRIPTION
     "This table contains entries that allow the user to retrieve
      15 minute splice detection historical interval data."
   ::= { adEShdslSpliceDetection 4 }

adEShdslSpliceDet15MinIntEntry OBJECT-TYPE
   SYNTAX      AdEShdslSpliceDet15MinIntEntry
   MAX-ACCESS  not-accessible
   STATUS      current
   DESCRIPTION
     "An entry in the adEShdslSpliceDet15MinIntTable."
   INDEX { ifIndex, adEShdslInvIndex, adEShdslSideIndex, adEShdslWirePairIndex, adEShdslSpliceDet15MinIntNumber }
   ::= { adEShdslSpliceDet15MinIntTable 1 }

AdEShdslSpliceDet15MinIntEntry ::=
   SEQUENCE
   {
   adEShdslSpliceDet15MinIntNumber    	Integer32,
   adEShdslSplice15MinIntCounts		DisplayString,
   adEShdslSplice15MinIntDistances	DisplayString,
   adEShdslSplice15MinIntRate		Integer32
   }

adEShdslSpliceDet15MinIntNumber OBJECT-TYPE
   SYNTAX      	Integer32
   MAX-ACCESS   read-only
   STATUS       current
   DESCRIPTION
     "15 minute splice detect interval.  Interval 1 represents the most recent
	  previous interval."
   ::= { adEShdslSpliceDet15MinIntEntry 1 }

adEShdslSplice15MinIntCounts OBJECT-TYPE
   SYNTAX      DisplayString
   MAX-ACCESS  read-only
   STATUS      current
   DESCRIPTION
     "A series of numbers (0-99) in the following format:  N0.N1.N3 ... N17
      These values represent the splice detection histogram values for the
      corresponding distance values from adEShdslSpliceDistances for the selected
      interval. Note that some rates may not support 18 counts."
   ::= { adEShdslSpliceDet15MinIntEntry 2 }

adEShdslSplice15MinIntDistances OBJECT-TYPE
   SYNTAX      DisplayString
   MAX-ACCESS  read-only
   STATUS      current
   DESCRIPTION
     "A series of distances in the following format:  D0.D1.D3 ... D17
      These values represent the distances corresponding to each bucket in the splice detection
      histogram for the selected interval. Note that some rates may not support 18 distances"
   ::= { adEShdslSpliceDet15MinIntEntry 3 }

adEShdslSplice15MinIntRate OBJECT-TYPE
   SYNTAX      Integer32
   MAX-ACCESS  read-only
   STATUS      current
   DESCRIPTION
     "A last trained rate during the specified interval.  The value returned is the
      rate in 64kbps increments (N x 64k)."

   ::= { adEShdslSpliceDet15MinIntEntry 4 }


-- ******************************************************************************************
-- MIB Groups
-- ******************************************************************************************
adGenEShdslIndexGroup OBJECT-GROUP
   OBJECTS
   {
        adEShdslInvIndex,
        adEShdslSideIndex,
        adEShdslWirePairIndex
   }
   STATUS current
   DESCRIPTION
     "These objects provide support for SHDSL indexing."
   ::= { adEShdslMibGroups 1 }

adGenEShdslInvGroup OBJECT-GROUP
   OBJECTS
   {
        adEShdslInvVendorID,
        adEShdslInvVendorModelNumber,
        adEShdslInvVendorSerialNumber,
        adEShdslInvStandardVersion,
        adEShdslInvVendorListNumber,
        adEShdslInvVendorIssueNumber,
        adEShdslInvVendorSoftwareVersion,
        adEShdslInvEquipmentCode,
        adEShdslInvVendorOther,
        adEShdslInvVendorEOCSoftwareVersion,
        adEShdslInvMfrDate,
        adEShdslInvCircuitID,
        adEShdslInvScratchPad

   }
   STATUS current
   DESCRIPTION
     "These objects provide support for SHDSL inventory retrieval."
   ::= { adEShdslMibGroups 2 }

adGenEShdslProvGroup OBJECT-GROUP
   OBJECTS
   {
        adEShdslProvWireInterfaceMode,
        adEShdslProvMinLineRate,
        adEShdslProvMaxLineRate,
        adEShdslProvG9912Annex,
        adEShdslProvCurrCondTargetMargin,
        adEShdslProvWorstCaseTargetMargin,
        adEShdslProvUsedTargetMargins,
        adEShdslProvClockMode,
        adEShdslProvLineProbing,
        adEShdslProvConstellation,
        adEShdslProvPowerBackoff,
        adEShdslAlarmProvLoopAttenThresh,
        adEShdslAlarmProvSNRMarginThresh,
        adEShdslAlarmProvESThresh,
        adEShdslAlarmProvSESThresh,
        adEShdslAlarmProvUASThresh,
        adEShdslAlarmProvCVCThresh,
        adEShdslAlarmProvLOSWSThresh,
        adEShdslAlarmProvOSThresh,
        adEShdslTestProvLoopbackTimeout,
        adEShdslAlarmProvES24HrThresh,
        adEShdslAlarmProvSES24HrThresh,
        adEShdslAlarmProvUAS24HrThresh,
        adEShdslAlarmProvCVC24HrThresh,
        adEShdslAlarmProvLOSWS24HrThresh,
        adEShdslAlarmProvOS24HrThresh,
        adEShdslProvName,
        adEShdslProvSpanPower,
        adEShdslProvNIUloopback,
        adEShdslTestProvEnumeratedLoopbackTimeout
   }
   STATUS current
   DESCRIPTION
     "These objects provide support for SHDSL provisioning."
   ::= { adEShdslMibGroups 3 }

adGenEShdslStatusGroup OBJECT-GROUP
   OBJECTS
   {
        adEShdslStatusCurrStatus,
        adEShdslStatusCurrLoopAtten,
        adEShdslStatusMinLoopAtten,
        adEShdslStatusMaxLoopAtten,
        adEShdslStatusCurrSNRMargin,
        adEShdslStatusMinSNRMargin,
        adEShdslStatusMaxSNRMargin,
        adEShdslStatusES,
        adEShdslStatusSES,
        adEShdslStatusUAS,
        adEShdslStatusCVC,
        adEShdslStatusLOSWS,
        adEShdslStatusOS,
        adEShdslStatusResetStatistics,
        adEShdslStatusMaxAttainableRate,
        adEShdslStatusUpstreamPBO,
        adEShdslStatusDownstreamPBO,
        adEShdslStatusCurrRate,
        adEShdslStatusInfoRepeaterNumber,
        adEShdslStatusInfoPairReversal,
        adEShdslStatusInfoLoopAlarmStatus,
		adEShdslStatusIfTrainingMode
   }
   STATUS current
   DESCRIPTION
     "These objects provide support for SHDSL status retrieval."
   ::= { adEShdslMibGroups 4 }

adGenEShdslTestGroup OBJECT-GROUP
   OBJECTS
   {
        adEShdslTestLoopback,
        adEShdslTestLoopdownAll,
        adEShdslTestinitMinMax
   }
   STATUS current
   DESCRIPTION
     "These objects provide access for the testing
      of SHDSL links"
   ::= { adEShdslMibGroups 5 }

adGenEShdslCurr15MinPerfGroup OBJECT-GROUP
   OBJECTS
   {
        adEShdslPerfCurr15MinES,
        adEShdslPerfCurr15MinSES,
        adEShdslPerfCurr15MinUAS,
        adEShdslPerfCurr15MinCVC,
        adEShdslPerfCurr15MinLOSWS,
        adEShdslPerfCurr15MinOS,
        adEShdslPerf15MinValidIntervals
   }
   STATUS current
   DESCRIPTION
     "These objects provide support for the reporting of the
      current 15 minute interval of PM data."
   ::= { adEShdslMibGroups 6 }

adGenEShdslCurr24HrPerfGroup OBJECT-GROUP
   OBJECTS
   {
        adEShdslPerfCurr24HrES,
        adEShdslPerfCurr24HrSES,
        adEShdslPerfCurr24HrUAS,
        adEShdslPerfCurr24HrCVC,
        adEShdslPerfCurr24HrLOSWS,
        adEShdslPerfCurr24HrOS,
        adEShdslPerf24HrValidIntervals
   }
   STATUS current
   DESCRIPTION
     "These objects provide support for the reporting of the
      current 24 hour interval of PM data."
   ::= { adEShdslMibGroups 7 }

adGenEShdslPrior15MinPerfGroup OBJECT-GROUP
   OBJECTS
   {
        adEShdslPerfPrior15MinES,
        adEShdslPerfPrior15MinSES,
        adEShdslPerfPrior15MinUAS,
        adEShdslPerfPrior15MinCVC,
        adEShdslPerfPrior15MinLOSWS,
        adEShdslPerfPrior15MinOS
   }
   STATUS current
   DESCRIPTION
     "These objects provide support for the reporting of the
      prior 15 minute interval of PM data."
   ::= { adEShdslMibGroups 8 }

adGenEShdslPrior24HrPerfGroup OBJECT-GROUP
   OBJECTS
   {
        adEShdslPerfPrior24HrES,
        adEShdslPerfPrior24HrSES,
        adEShdslPerfPrior24HrUAS,
        adEShdslPerfPrior24HrCVC,
        adEShdslPerfPrior24HrLOSWS,
        adEShdslPerfPrior24HrOS
   }
   STATUS current
   DESCRIPTION
     "These objects provide support for the reporting of the
      prior 24 hour interval of PM data."
   ::= { adEShdslMibGroups 9 }

adGenEShdslInt15MinPerfGroup OBJECT-GROUP
   OBJECTS
   {
        adEShdslPerf15MinIntNumber,
        adEShdslPerf15MinIntES,
        adEShdslPerf15MinIntSES,
        adEShdslPerf15MinIntUAS,
        adEShdslPerf15MinIntCVC,
        adEShdslPerf15MinIntLOSWS,
        adEShdslPerf15MinIntOS
   }
   STATUS current
   DESCRIPTION
     "These objects provide support for the reporting of the
      selected 15 minute interval of PM data."
   ::= { adEShdslMibGroups 10 }

adGenEShdslInt24HrPerfGroup OBJECT-GROUP
   OBJECTS
   {
        adEShdslPerf24HrIntNumber,
        adEShdslPerf24HrIntES,
        adEShdslPerf24HrIntSES,
        adEShdslPerf24HrIntUAS,
        adEShdslPerf24HrIntCVC,
        adEShdslPerf24HrIntLOSWS,
        adEShdslPerf24HrIntOS
   }
   STATUS current
   DESCRIPTION
     "These objects provide support for the reporting of the
      selected 24 hour interval of PM data."
   ::= { adEShdslMibGroups 11 }

adGenEShdslSpliceGroup OBJECT-GROUP
   OBJECTS
   {
        adEShdslSpliceDetectionSummary,
        adEShdslSpliceCounts,
        adEShdslSpliceDistances,
        adEShdslSpliceRestart,
        adEShdslSpliceDistanceType
   }
   STATUS current
   DESCRIPTION
     "These objects provide support for bad splice detection."
   ::= { adEShdslMibGroups 12 }

adGenEShdslEventGroup NOTIFICATION-GROUP
   NOTIFICATIONS
   {
        adEShdslLossofSignalAlmCLR,
        adEShdslLossofSignalAlmACT,
        adEShdslLTULossofSyncWordAlmCLR,
        adEShdslLTULossofSyncWordAlmACT,
        adEShdslLTUCRCErrorAlmCLR,
        adEShdslLTUCRCErrorAlmACT,
        adEShdslLTUSNRMarginAlmCLR,
        adEShdslLTUSNRMarginAlmACT,
        adEShdslLTULoopAttenAlmCLR,
        adEShdslLTULoopAttenAlmACT,
        adEShdslNTULossofSyncWordAlmCLR,
        adEShdslNTULossofSyncWordAlmACT,
        adEShdslNTUCRCErrorAlmCLR,
        adEShdslNTUCRCErrorAlmACT,
        adEShdslNTUSNRMarginAlmCLR,
        adEShdslNTUSNRMarginAlmACT,
        adEShdslNTULoopAttenAlmCLR,
        adEShdslNTULoopAttenAlmACT,
        adEShdslLTUESThreshCrossed,
        adEShdslLTUSESThreshCrossed,
        adEShdslLTUUASThreshCrossed,
        adEShdslLTUCVCThreshCrossed,
        adEShdslLTULOSWSThreshCrossed,
        adEShdslLTUOSThreshCrossed,
        adEShdslNTUESThreshCrossed,
        adEShdslNTUSESThreshCrossed,
        adEShdslNTUUASThreshCrossed,
        adEShdslNTUCVCThreshCrossed,
        adEShdslNTULOSWSThreshCrossed,
        adEShdslNTUOSThreshCrossed,
        adEShdslRemoteLossOfPower,
        adEShdslRegenLossofSignalAlmCLR,
        adEShdslRegenLossofSignalAlmACT,
        adEShdslRegenLossofSyncWordAlmCLR,
        adEShdslRegenLossofSyncWordAlmACT,
        adEShdslRegenCRCErrorAlmCLR,
        adEShdslRegenCRCErrorAlmACT,
        adEShdslRegenSNRMarginAlmCLR,
        adEShdslRegenSNRMarginAlmACT,
        adEShdslRegenLoopAttenAlmCLR,
        adEShdslRegenLoopAttenAlmACT,
        adEShdslRegenESThreshCrossed,
        adEShdslRegenSESThreshCrossed,
        adEShdslRegenUASThreshCrossed,
        adEShdslRegenCVCThreshCrossed,
        adEShdslRegenLOSWSThreshCrossed,
        adEShdslRegenOSThreshCrossed,
        adEShdslLoopbackEnabledCLR,
        adEShdslLoopbackEnabledACT,
        adEShdslLTUES24HrThreshCrossed,
        adEShdslLTUSES24HrThreshCrossed,
        adEShdslLTUUAS24HrThreshCrossed,
        adEShdslLTUCVC24HrThreshCrossed,
        adEShdslLTULOSWS24HrThreshCrossed,
        adEShdslLTUOS24HrThreshCrossed,
        adEShdslNTUES24HrThreshCrossed,
        adEShdslNTUSES24HrThreshCrossed,
        adEShdslNTUUAS24HrThreshCrossed,
        adEShdslNTUCVC24HrThreshCrossed,
        adEShdslNTULOSWS24HrThreshCrossed,
        adEShdslNTUOS24HrThreshCrossed
   }
   STATUS current
   DESCRIPTION
      "GenEShdsl Notification Group"
   ::= { adEShdslMibGroups 13 }

adGenEShdslInt24HrSpliceDetGroup OBJECT-GROUP
   OBJECTS
   {
   adEShdslSpliceDet24HrIntNumber,
   adEShdslSplice24HrIntCounts,
   adEShdslSplice24HrIntDistances
   }
   STATUS current
   DESCRIPTION
     "These objects provide support for bad splice detection for the
      selected 24 hour interval."
   ::= { adEShdslMibGroups 14 }

adGenEShdslPerfResetGroup OBJECT-GROUP
   OBJECTS
   {
   adEShdslPerfReset,
   adEShdslPerfPortReset
   }
   STATUS current
   DESCRIPTION
     "These objects provide support for resetting of performance history."
   ::= { adEShdslMibGroups 15 }

-- ******************************************************************************************

-- Alarms
--

-- ********************************************
-- Active/Clear Type Alarms
-- ********************************************

adEShdslLossofSignalAlmCLR    NOTIFICATION-TYPE
    OBJECTS         {
                    adTrapInformSeqNum,
                    sysName,
                    adGenSlotInfoIndex,
                    adGenPortTrapIdentifier
                    }
    STATUS          current
    DESCRIPTION
                    "Loss of Signal Alarm"
    --#TYPE         "Status - Alarm"
    --#SUMMARY      "Loss of Signal Alarm "
    --#SUMMARY      "cleared at shelf: %s, slot: %d and port: %d"
    --#ARGUMENTS    {1,2,3}
    --#SEVERITY     MAJOR
    --#GENERIC      6
    --#CATEGORY     "Error Events"
    --#SOURCE_ID    "A"
    --#TIMEINDEX    0
    ::= {adEShdslAlarms 2}

adEShdslLossofSignalAlmACT    NOTIFICATION-TYPE
    OBJECTS         {
                    adTrapInformSeqNum,
                    sysName,
                    adGenSlotInfoIndex,
                    adGenPortTrapIdentifier
                    }
    STATUS          current
    DESCRIPTION
                    "Loss of Signal Alarm"
    --#TYPE         "Status - Alarm"
    --#SUMMARY      "Loss of Signal Alarm "
    --#SUMMARY      "detected at shelf: %s, slot: %d and port: %d"
    --#ARGUMENTS    {1,2,3}
    --#SEVERITY     MAJOR
    --#GENERIC      6
    --#CATEGORY     "Error Events"
    --#SOURCE_ID    "A"
    --#TIMEINDEX    0
    ::= {adEShdslAlarms 3}

adEShdslLTULossofSyncWordAlmCLR    NOTIFICATION-TYPE
    OBJECTS         {
                    adTrapInformSeqNum,
                    sysName,
                    adGenSlotInfoIndex,
                    adGenPortTrapIdentifier
                    }
    STATUS          current
    DESCRIPTION
                    "LTU Loss of Sync Word Alarm"
    --#TYPE         "Status - Alarm"
    --#SUMMARY      "LTU Loss of Sync Word Alarm "
    --#SUMMARY      "cleared at shelf: %s, slot: %d and port: %d"
    --#ARGUMENTS    {1,2,3}
    --#SEVERITY     MAJOR
    --#GENERIC      6
    --#CATEGORY     "Error Events"
    --#SOURCE_ID    "A"
    --#TIMEINDEX    0
    ::= {adEShdslAlarms 4}

adEShdslLTULossofSyncWordAlmACT    NOTIFICATION-TYPE
    OBJECTS         {
                    adTrapInformSeqNum,
                    sysName,
                    adGenSlotInfoIndex,
                    adGenPortTrapIdentifier
                    }
    STATUS          current
    DESCRIPTION
                    "LTU Loss of Sync Word Alarm"
    --#TYPE         "Status - Alarm"
    --#SUMMARY      "LTU Loss of Sync Word Alarm "
    --#SUMMARY      "detected at shelf: %s, slot: %d and port: %d"
    --#ARGUMENTS    {1,2,3}
    --#SEVERITY     MAJOR
    --#GENERIC      6
    --#CATEGORY     "Error Events"
    --#SOURCE_ID    "A"
    --#TIMEINDEX    0
    ::= {adEShdslAlarms 5}

adEShdslLTUCRCErrorAlmCLR    NOTIFICATION-TYPE
    OBJECTS         {
                    adTrapInformSeqNum,
                    sysName,
                    adGenSlotInfoIndex,
                    adGenPortTrapIdentifier
                    }
    STATUS          current
    DESCRIPTION
                    "LTU CRC Error"
    --#TYPE         "Status - Alarm"
    --#SUMMARY      "LTU CRC Error "
    --#SUMMARY      "cleared at shelf: %s, slot: %d and port: %d"
    --#ARGUMENTS    {1,2,3}
    --#SEVERITY     MINOR
    --#GENERIC      6
    --#CATEGORY     "Error Events"
    --#SOURCE_ID    "A"
    --#TIMEINDEX    0
    ::= {adEShdslAlarms 6}

adEShdslLTUCRCErrorAlmACT    NOTIFICATION-TYPE
    OBJECTS         {
                    adTrapInformSeqNum,
                    sysName,
                    adGenSlotInfoIndex,
                    adGenPortTrapIdentifier
                    }
    STATUS          current
    DESCRIPTION
                    "LTU CRC Error"
    --#TYPE         "Status - Alarm"
    --#SUMMARY      "LTU CRC Error "
    --#SUMMARY      "detected at shelf: %s, slot: %d and port: %d"
    --#ARGUMENTS    {1,2,3}
    --#SEVERITY     MINOR
    --#GENERIC      6
    --#CATEGORY     "Error Events"
    --#SOURCE_ID    "A"
    --#TIMEINDEX    0
    ::= {adEShdslAlarms 7}

adEShdslLTUSNRMarginAlmCLR    NOTIFICATION-TYPE
    OBJECTS         {
                    adTrapInformSeqNum,
                    sysName,
                    adGenSlotInfoIndex,
                    adGenPortTrapIdentifier
                    }
    STATUS          current
    DESCRIPTION
                    "LTU SNR Margin Alarm"
    --#TYPE         "Status - Alarm"
    --#SUMMARY      "LTU SNR Margin Alarm "
    --#SUMMARY      "cleared at shelf: %s, slot: %d and port: %d"
    --#ARGUMENTS    {1,2,3}
    --#SEVERITY     MINOR
    --#GENERIC      6
    --#CATEGORY     "Error Events"
    --#SOURCE_ID    "A"
    --#TIMEINDEX    0
    ::= {adEShdslAlarms 8}

adEShdslLTUSNRMarginAlmACT    NOTIFICATION-TYPE
    OBJECTS         {
                    adTrapInformSeqNum,
                    sysName,
                    adGenSlotInfoIndex,
                    adGenPortTrapIdentifier
                    }
    STATUS          current
    DESCRIPTION
                    "LTU SNR Margin Alarm"
    --#TYPE         "Status - Alarm"
    --#SUMMARY      "LTU SNR Margin Alarm "
    --#SUMMARY      "detected at shelf: %s, slot: %d and port: %d"
    --#ARGUMENTS    {1,2,3}
    --#SEVERITY     MINOR
    --#GENERIC      6
    --#CATEGORY     "Error Events"
    --#SOURCE_ID    "A"
    --#TIMEINDEX    0
    ::= {adEShdslAlarms 9}

adEShdslLTULoopAttenAlmCLR    NOTIFICATION-TYPE
    OBJECTS         {
                    adTrapInformSeqNum,
                    sysName,
                    adGenSlotInfoIndex,
                    adGenPortTrapIdentifier
                    }
    STATUS          current
    DESCRIPTION
                    "LTU Loop Attenuation Alarm"
    --#TYPE         "Status - Alarm"
    --#SUMMARY      "LTU Loop Attenuation Alarm "
    --#SUMMARY      "cleared at shelf: %s, slot: %d and port: %d"
    --#ARGUMENTS    {1,2,3}
    --#SEVERITY     MINOR
    --#GENERIC      6
    --#CATEGORY     "Error Events"
    --#SOURCE_ID    "A"
    --#TIMEINDEX    0
    ::= {adEShdslAlarms 10}

adEShdslLTULoopAttenAlmACT    NOTIFICATION-TYPE
    OBJECTS         {
                    adTrapInformSeqNum,
                    sysName,
                    adGenSlotInfoIndex,
                    adGenPortTrapIdentifier
                    }
    STATUS          current
    DESCRIPTION
                    "LTU Loop Attenuation Alarm"
    --#TYPE         "Status - Alarm"
    --#SUMMARY      "LTU Loop Attenuation Alarm "
    --#SUMMARY      "detected at shelf: %s, slot: %d and port: %d"
    --#ARGUMENTS    {1,2,3}
    --#SEVERITY     MINOR
    --#GENERIC      6
    --#CATEGORY     "Error Events"
    --#SOURCE_ID    "A"
    --#TIMEINDEX    0
    ::= {adEShdslAlarms 11}

adEShdslNTULossofSyncWordAlmCLR    NOTIFICATION-TYPE
    OBJECTS         {
                    adTrapInformSeqNum,
                    sysName,
                    adGenSlotInfoIndex,
                    adGenPortTrapIdentifier
                    }
    STATUS          current
    DESCRIPTION
                    "NTU Loss of Sync Word Alarm"
    --#TYPE         "Status - Alarm"
    --#SUMMARY      "NTU Loss of Sync Word Alarm "
    --#SUMMARY      "cleared at shelf: %s, slot: %d and port: %d"
    --#ARGUMENTS    {1,2,3}
    --#SEVERITY     MAJOR
    --#GENERIC      6
    --#CATEGORY     "Error Events"
    --#SOURCE_ID    "A"
    --#TIMEINDEX    0
    ::= {adEShdslAlarms 12}

adEShdslNTULossofSyncWordAlmACT    NOTIFICATION-TYPE
    OBJECTS         {
                    adTrapInformSeqNum,
                    sysName,
                    adGenSlotInfoIndex,
                    adGenPortTrapIdentifier
                    }
    STATUS          current
    DESCRIPTION
                    "NTU Loss of Sync Word Alarm"
    --#TYPE         "Status - Alarm"
    --#SUMMARY      "NTU Loss of Sync Word Alarm "
    --#SUMMARY      "detected at shelf: %s, slot: %d and port: %d"
    --#ARGUMENTS    {1,2,3}
    --#SEVERITY     MAJOR
    --#GENERIC      6
    --#CATEGORY     "Error Events"
    --#SOURCE_ID    "A"
    --#TIMEINDEX    0
    ::= {adEShdslAlarms 13}

adEShdslNTUCRCErrorAlmCLR    NOTIFICATION-TYPE
    OBJECTS         {
                    adTrapInformSeqNum,
                    sysName,
                    adGenSlotInfoIndex,
                    adGenPortTrapIdentifier
                    }
    STATUS          current
    DESCRIPTION
                    "NTU CRC Error"
    --#TYPE         "Status - Alarm"
    --#SUMMARY      "NTU CRC Error "
    --#SUMMARY      "cleared at shelf: %s, slot: %d and port: %d"
    --#ARGUMENTS    {1,2,3}
    --#SEVERITY     MINOR
    --#GENERIC      6
    --#CATEGORY     "Error Events"
    --#SOURCE_ID    "A"
    --#TIMEINDEX    0
    ::= {adEShdslAlarms 14}

adEShdslNTUCRCErrorAlmACT    NOTIFICATION-TYPE
    OBJECTS         {
                    adTrapInformSeqNum,
                    sysName,
                    adGenSlotInfoIndex,
                    adGenPortTrapIdentifier
                    }
    STATUS          current
    DESCRIPTION
                    "NTU CRC Error"
    --#TYPE         "Status - Alarm"
    --#SUMMARY      "NTU CRC Error "
    --#SUMMARY      "detected at shelf: %s, slot: %d and port: %d"
    --#ARGUMENTS    {1,2,3}
    --#SEVERITY     MINOR
    --#GENERIC      6
    --#CATEGORY     "Error Events"
    --#SOURCE_ID    "A"
    --#TIMEINDEX    0
    ::= {adEShdslAlarms 15}

adEShdslNTUSNRMarginAlmCLR    NOTIFICATION-TYPE
    OBJECTS         {
                    adTrapInformSeqNum,
                    sysName,
                    adGenSlotInfoIndex,
                    adGenPortTrapIdentifier
                    }
    STATUS          current
    DESCRIPTION
                    "NTU SNR Margin Alarm"
    --#TYPE         "Status - Alarm"
    --#SUMMARY      "NTU SNR Margin Alarm "
    --#SUMMARY      "cleared at shelf: %s, slot: %d and port: %d"
    --#ARGUMENTS    {1,2,3}
    --#SEVERITY     MINOR
    --#GENERIC      6
    --#CATEGORY     "Error Events"
    --#SOURCE_ID    "A"
    --#TIMEINDEX    0
    ::= {adEShdslAlarms 16}

adEShdslNTUSNRMarginAlmACT    NOTIFICATION-TYPE
    OBJECTS         {
                    adTrapInformSeqNum,
                    sysName,
                    adGenSlotInfoIndex,
                    adGenPortTrapIdentifier
                    }
    STATUS          current
    DESCRIPTION
                    "NTU SNR Margin Alarm"
    --#TYPE         "Status - Alarm"
    --#SUMMARY      "NTU SNR Margin Alarm "
    --#SUMMARY      "detected at shelf: %s, slot: %d and port: %d"
    --#ARGUMENTS    {1,2,3}
    --#SEVERITY     MINOR
    --#GENERIC      6
    --#CATEGORY     "Error Events"
    --#SOURCE_ID    "A"
    --#TIMEINDEX    0
    ::= {adEShdslAlarms 17}

adEShdslNTULoopAttenAlmCLR    NOTIFICATION-TYPE
    OBJECTS         {
                    adTrapInformSeqNum,
                    sysName,
                    adGenSlotInfoIndex,
                    adGenPortTrapIdentifier
                    }
    STATUS          current
    DESCRIPTION
                    "NTU Loop Attenuation Alarm"
    --#TYPE         "Status - Alarm"
    --#SUMMARY      "NTU Loop Attenuation Alarm "
    --#SUMMARY      "cleared at shelf: %s, slot: %d and port: %d"
    --#ARGUMENTS    {1,2,3}
    --#SEVERITY     MINOR
    --#GENERIC      6
    --#CATEGORY     "Error Events"
    --#SOURCE_ID    "A"
    --#TIMEINDEX    0
    ::= {adEShdslAlarms 18}

adEShdslNTULoopAttenAlmACT    NOTIFICATION-TYPE
    OBJECTS         {
                    adTrapInformSeqNum,
                    sysName,
                    adGenSlotInfoIndex,
                    adGenPortTrapIdentifier
                    }
    STATUS          current
    DESCRIPTION
                    "NTU Loop Attenuation Alarm"
    --#TYPE         "Status - Alarm"
    --#SUMMARY      "NTU Loop Attenuation Alarm "
    --#SUMMARY      "detected at shelf: %s, slot: %d and port: %d"
    --#ARGUMENTS    {1,2,3}
    --#SEVERITY     MINOR
    --#GENERIC      6
    --#CATEGORY     "Error Events"
    --#SOURCE_ID    "A"
    --#TIMEINDEX    0
    ::= {adEShdslAlarms 19}


-- ********************************************
-- Auto-clearing Alert Type Alarms
-- ********************************************

-- ********************************************
-- LTU 15-Minute PM Threshold Alarms
-- ********************************************
adEShdslLTUESThreshCrossed    NOTIFICATION-TYPE
    OBJECTS         {
                    adTrapInformSeqNum,
                    sysName,
                    adGenSlotInfoIndex,
                    adGenPortTrapIdentifier
                    }
    STATUS          current
    DESCRIPTION
                    "LTU Errored Seconds Threshold Crossed"
    --#TYPE         "Threshold Crossing Alarm - LTU ES"
    --#SUMMARY      "LTU Errored Seconds Alarm "
    --#SUMMARY      "detected at shelf: %s, slot: %d and port: %d"
    --#ARGUMENTS    {1,2,3}
    --#SEVERITY     WARNING
    --#GENERIC      6
    --#CATEGORY     "Threshold Events"
    --#SOURCE_ID    "A"
    --#TIMEINDEX    0
    ::= {adEShdslAlarms 20}

adEShdslLTUSESThreshCrossed    NOTIFICATION-TYPE
    OBJECTS         {
                    adTrapInformSeqNum,
                    sysName,
                    adGenSlotInfoIndex,
                    adGenPortTrapIdentifier
                    }
    STATUS          current
    DESCRIPTION
                    "LTU Severely Errored Seconds Threshold Crossed"
    --#TYPE         "Threshold Crossing Alarm - LTU SES"
    --#SUMMARY      "LTU Severely Errored Seconds Alarm "
    --#SUMMARY      "detected at shelf: %s, slot: %d and port: %d"
    --#ARGUMENTS    {1,2,3}
    --#SEVERITY     WARNING
    --#GENERIC      6
    --#CATEGORY     "Threshold Events"
    --#SOURCE_ID    "A"
    --#TIMEINDEX    0
    ::= {adEShdslAlarms 21}

adEShdslLTUUASThreshCrossed    NOTIFICATION-TYPE
    OBJECTS         {
                    adTrapInformSeqNum,
                    sysName,
                    adGenSlotInfoIndex,
                    adGenPortTrapIdentifier
                    }
    STATUS          current
    DESCRIPTION
                    "LTU Unavailable Seconds Threshold Crossed"
    --#TYPE         "Threshold Crossing Alarm - LTU UAS"
    --#SUMMARY      "LTU Unavailable Seconds Alarm "
    --#SUMMARY      "detected at shelf: %s, slot: %d and port: %d"
    --#ARGUMENTS    {1,2,3}
    --#SEVERITY     WARNING
    --#GENERIC      6
    --#CATEGORY     "Threshold Events"
    --#SOURCE_ID    "A"
    --#TIMEINDEX    0
    ::= {adEShdslAlarms 22}

adEShdslLTUCVCThreshCrossed    NOTIFICATION-TYPE
    OBJECTS         {
                    adTrapInformSeqNum,
                    sysName,
                    adGenSlotInfoIndex,
                    adGenPortTrapIdentifier
                    }
    STATUS          current
    DESCRIPTION
                    "LTU Code Violation Count Threshold Crossed"
    --#TYPE         "Threshold Crossing Alarm - LTU CVC"
    --#SUMMARY      "LTU Code Violation Count Alarm "
    --#SUMMARY      "detected at shelf: %s, slot: %d and port: %d"
    --#ARGUMENTS    {1,2,3}
    --#SEVERITY     WARNING
    --#GENERIC      6
    --#CATEGORY     "Threshold Events"
    --#SOURCE_ID    "A"
    --#TIMEINDEX    0
    ::= {adEShdslAlarms 23}

adEShdslLTULOSWSThreshCrossed    NOTIFICATION-TYPE
    OBJECTS         {
                    adTrapInformSeqNum,
                    sysName,
                    adGenSlotInfoIndex,
                    adGenPortTrapIdentifier
                    }
    STATUS          current
    DESCRIPTION
                    "LTU Loss of Sync Word Seconds Threshold Crossed"
    --#TYPE         "Threshold Crossing Alarm - LTU LOSWS"
    --#SUMMARY      "LTU Loss of Sync Word Seconds Alarm "
    --#SUMMARY      "detected at shelf: %s, slot: %d and port: %d"
    --#ARGUMENTS    {1,2,3}
    --#SEVERITY     WARNING
    --#GENERIC      6
    --#CATEGORY     "Threshold Events"
    --#SOURCE_ID    "A"
    --#TIMEINDEX    0
    ::= {adEShdslAlarms 24}

adEShdslLTUOSThreshCrossed    NOTIFICATION-TYPE
    OBJECTS         {
                    adTrapInformSeqNum,
                    sysName,
                    adGenSlotInfoIndex,
                    adGenPortTrapIdentifier
                    }
    STATUS          current
    DESCRIPTION
                    "LTU Outage Seconds Threshold Crossed"
    --#TYPE         "Threshold Crossing Alarm - LTU OS"
    --#SUMMARY      "LTU Outage Seconds Alarm "
    --#SUMMARY      "detected at shelf: %s, slot: %d and port: %d"
    --#ARGUMENTS    {1,2,3}
    --#SEVERITY     WARNING
    --#GENERIC      6
    --#CATEGORY     "Threshold Events"
    --#SOURCE_ID    "A"
    --#TIMEINDEX    0
    ::= {adEShdslAlarms 25}

-- ********************************************
-- NTU 15-Minute PM Threshold Alarms
-- ********************************************
adEShdslNTUESThreshCrossed    NOTIFICATION-TYPE
    OBJECTS         {
                    adTrapInformSeqNum,
                    sysName,
                    adGenSlotInfoIndex,
                    adGenPortTrapIdentifier
                    }
    STATUS          current
    DESCRIPTION
                    "NTU Errored Seconds Threshold Crossed"
    --#TYPE         "Threshold Crossing Alarm - NTU ES"
    --#SUMMARY      "NTU Errored Seconds Alarm "
    --#SUMMARY      "detected at shelf: %s, slot: %d and port: %d"
    --#ARGUMENTS    {1,2,3}
    --#SEVERITY     WARNING
    --#GENERIC      6
    --#CATEGORY     "Threshold Events"
    --#SOURCE_ID    "A"
    --#TIMEINDEX    0
    ::= {adEShdslAlarms 26}

adEShdslNTUSESThreshCrossed    NOTIFICATION-TYPE
    OBJECTS         {
                    adTrapInformSeqNum,
                    sysName,
                    adGenSlotInfoIndex,
                    adGenPortTrapIdentifier
                    }
    STATUS          current
    DESCRIPTION
                    "NTU Severely Errored Seconds Threshold Crossed"
    --#TYPE         "Threshold Crossing Alarm - NTU SES"
    --#SUMMARY      "NTU Severely Errored Seconds Alarm "
    --#SUMMARY      "detected at shelf: %s, slot: %d and port: %d"
    --#ARGUMENTS    {1,2,3}
    --#SEVERITY     WARNING
    --#GENERIC      6
    --#CATEGORY     "Threshold Events"
    --#SOURCE_ID    "A"
    --#TIMEINDEX    0
    ::= {adEShdslAlarms 27}

adEShdslNTUUASThreshCrossed    NOTIFICATION-TYPE
    OBJECTS         {
                    adTrapInformSeqNum,
                    sysName,
                    adGenSlotInfoIndex,
                    adGenPortTrapIdentifier
                    }
    STATUS          current
    DESCRIPTION
                    "NTU Unavailable Seconds Threshold Crossed"
    --#TYPE         "Threshold Crossing Alarm - NTU UAS"
    --#SUMMARY      "NTU Unavailable Seconds Alarm "
    --#SUMMARY      "detected at shelf: %s, slot: %d and port: %d"
    --#ARGUMENTS    {1,2,3}
    --#SEVERITY     WARNING
    --#GENERIC      6
    --#CATEGORY     "Threshold Events"
    --#SOURCE_ID    "A"
    --#TIMEINDEX    0
    ::= {adEShdslAlarms 28}

adEShdslNTUCVCThreshCrossed    NOTIFICATION-TYPE
    OBJECTS         {
                    adTrapInformSeqNum,
                    sysName,
                    adGenSlotInfoIndex,
                    adGenPortTrapIdentifier
                    }
    STATUS          current
    DESCRIPTION
                    "NTU Code Violation Count Threshold Crossed"
    --#TYPE         "Threshold Crossing Alarm - NTU CVC"
    --#SUMMARY      "NTU Code Violation Count Alarm "
    --#SUMMARY      "detected at shelf: %s, slot: %d and port: %d"
    --#ARGUMENTS    {1,2,3}
    --#SEVERITY     WARNING
    --#GENERIC      6
    --#CATEGORY     "Threshold Events"
    --#SOURCE_ID    "A"
    --#TIMEINDEX    0
    ::= {adEShdslAlarms 29}

adEShdslNTULOSWSThreshCrossed    NOTIFICATION-TYPE
    OBJECTS         {
                    adTrapInformSeqNum,
                    sysName,
                    adGenSlotInfoIndex,
                    adGenPortTrapIdentifier
                    }
    STATUS          current
    DESCRIPTION
                    "NTU Loss of Sync Word Seconds Threshold Crossed"
    --#TYPE         "Threshold Crossing Alarm - NTU LOSWS"
    --#SUMMARY      "NTU Loss of Sync Word Seconds Alarm "
    --#SUMMARY      "detected at shelf: %s, slot: %d and port: %d"
    --#ARGUMENTS    {1,2,3}
    --#SEVERITY     WARNING
    --#GENERIC      6
    --#CATEGORY     "Threshold Events"
    --#SOURCE_ID    "A"
    --#TIMEINDEX    0
    ::= {adEShdslAlarms 30}

adEShdslNTUOSThreshCrossed    NOTIFICATION-TYPE
    OBJECTS         {
                    adTrapInformSeqNum,
                    sysName,
                    adGenSlotInfoIndex,
                    adGenPortTrapIdentifier
                    }
    STATUS          current
    DESCRIPTION
                    "NTU Outage Seconds Threshold Crossed"
    --#TYPE         "Threshold Crossing Alarm - NTU OS"
    --#SUMMARY      "NTU Outage Seconds Alarm "
    --#SUMMARY      "detected at shelf: %s, slot: %d and port: %d"
    --#ARGUMENTS    {1,2,3}
    --#SEVERITY     WARNING
    --#GENERIC      6
    --#CATEGORY     "Threshold Events"
    --#SOURCE_ID    "A"
    --#TIMEINDEX    0
    ::= {adEShdslAlarms 31}

-- ********************************************
-- Miscellaneous Alerts
-- ********************************************

adEShdslRemoteLossOfPower    NOTIFICATION-TYPE
    OBJECTS         {
                    adTrapInformSeqNum,
                    sysName,
                    adGenSlotInfoIndex,
                    adGenPortTrapIdentifier
                    }
    STATUS          current
    DESCRIPTION
                    "Remote Unit has lost power"
    --#TYPE         "Status - Alarm"
    --#SUMMARY      "Remote Loss of Power  "
    --#SUMMARY      "detected at shelf: %s, slot: %d and port: %d"
    --#ARGUMENTS    {1,2,3}
    --#SEVERITY     WARNING
    --#GENERIC      6
    --#CATEGORY     "Error Events"
    --#SOURCE_ID    "A"
    --#TIMEINDEX    0
    ::= {adEShdslAlarms 32}

-- ********************************************
-- LTU 24-Hour PM Threshold Alarms
-- ********************************************
adEShdslLTUES24HrThreshCrossed    NOTIFICATION-TYPE
    OBJECTS         {
                    adTrapInformSeqNum,
                    sysName,
                    adGenSlotInfoIndex,
                    adGenPortTrapIdentifier
                    }
    STATUS          current
    DESCRIPTION
                    "LTU 24-Hour Errored Seconds Threshold Crossed"
    --#TYPE         "Threshold Crossing Alarm - LTU 24-Hour ES"
    --#SUMMARY      "LTU 24-Hour Errored Seconds Alarm "
    --#SUMMARY      "detected at shelf: %s, slot: %d and port: %d"
    --#ARGUMENTS    {1,2,3}
    --#SEVERITY     WARNING
    --#GENERIC      6
    --#CATEGORY     "Threshold Events"
    --#SOURCE_ID    "A"
    --#TIMEINDEX    0
    ::= {adEShdslAlarms 33}

adEShdslLTUSES24HrThreshCrossed    NOTIFICATION-TYPE
    OBJECTS         {
                    adTrapInformSeqNum,
                    sysName,
                    adGenSlotInfoIndex,
                    adGenPortTrapIdentifier
                    }
    STATUS          current
    DESCRIPTION
                    "LTU 24-Hour Severely Errored Seconds Threshold Crossed"
    --#TYPE         "Threshold Crossing Alarm - LTU 24-Hour SES"
    --#SUMMARY      "LTU 24-Hour Severely Errored Seconds Alarm "
    --#SUMMARY      "detected at shelf: %s, slot: %d and port: %d"
    --#ARGUMENTS    {1,2,3}
    --#SEVERITY     WARNING
    --#GENERIC      6
    --#CATEGORY     "Threshold Events"
    --#SOURCE_ID    "A"
    --#TIMEINDEX    0
    ::= {adEShdslAlarms 34}

adEShdslLTUUAS24HrThreshCrossed    NOTIFICATION-TYPE
    OBJECTS         {
                    adTrapInformSeqNum,
                    sysName,
                    adGenSlotInfoIndex,
                    adGenPortTrapIdentifier
                    }
    STATUS          current
    DESCRIPTION
                    "LTU 24-Hour Unavailable Seconds Threshold Crossed"
    --#TYPE         "Threshold Crossing Alarm - LTU 24-Hour UAS"
    --#SUMMARY      "LTU 24-Hour Unavailable Seconds Alarm "
    --#SUMMARY      "detected at shelf: %s, slot: %d and port: %d"
    --#ARGUMENTS    {1,2,3}
    --#SEVERITY     WARNING
    --#GENERIC      6
    --#CATEGORY     "Threshold Events"
    --#SOURCE_ID    "A"
    --#TIMEINDEX    0
    ::= {adEShdslAlarms 35}

adEShdslLTUCVC24HrThreshCrossed    NOTIFICATION-TYPE
    OBJECTS         {
                    adTrapInformSeqNum,
                    sysName,
                    adGenSlotInfoIndex,
                    adGenPortTrapIdentifier
                    }
    STATUS          current
    DESCRIPTION
                    "LTU 24-Hour Code Violation Count Threshold Crossed"
    --#TYPE         "Threshold Crossing Alarm - LTU 24-Hour CVC"
    --#SUMMARY      "LTU 24-Hour Code Violation Count Alarm "
    --#SUMMARY      "detected at shelf: %s, slot: %d and port: %d"
    --#ARGUMENTS    {1,2,3}
    --#SEVERITY     WARNING
    --#GENERIC      6
    --#CATEGORY     "Threshold Events"
    --#SOURCE_ID    "A"
    --#TIMEINDEX    0
    ::= {adEShdslAlarms 36}

adEShdslLTULOSWS24HrThreshCrossed    NOTIFICATION-TYPE
    OBJECTS         {
                    adTrapInformSeqNum,
                    sysName,
                    adGenSlotInfoIndex,
                    adGenPortTrapIdentifier
                    }
    STATUS          current
    DESCRIPTION
                    "LTU 24-Hour Loss of Sync Word Seconds Threshold Crossed"
    --#TYPE         "Threshold Crossing Alarm - LTU 24-Hour LOSWS"
    --#SUMMARY      "LTU 24-Hour Loss of Sync Word Seconds Alarm "
    --#SUMMARY      "detected at shelf: %s, slot: %d and port: %d"
    --#ARGUMENTS    {1,2,3}
    --#SEVERITY     WARNING
    --#GENERIC      6
    --#CATEGORY     "Threshold Events"
    --#SOURCE_ID    "A"
    --#TIMEINDEX    0
    ::= {adEShdslAlarms 37}

adEShdslLTUOS24HrThreshCrossed    NOTIFICATION-TYPE
    OBJECTS         {
                    adTrapInformSeqNum,
                    sysName,
                    adGenSlotInfoIndex,
                    adGenPortTrapIdentifier
                    }
    STATUS          current
    DESCRIPTION
                    "LTU 24-Hour Outage Seconds Threshold Crossed"
    --#TYPE         "Threshold Crossing Alarm - LTU 24-Hour OS"
    --#SUMMARY      "LTU 24-Hour Outage Seconds Alarm "
    --#SUMMARY      "detected at shelf: %s, slot: %d and port: %d"
    --#ARGUMENTS    {1,2,3}
    --#SEVERITY     WARNING
    --#GENERIC      6
    --#CATEGORY     "Threshold Events"
    --#SOURCE_ID    "A"
    --#TIMEINDEX    0
    ::= {adEShdslAlarms 38}

-- ********************************************
-- NTU 24-Hour 24-Hour PM Threshold Alarms
-- ********************************************
adEShdslNTUES24HrThreshCrossed    NOTIFICATION-TYPE
    OBJECTS         {
                    adTrapInformSeqNum,
                    sysName,
                    adGenSlotInfoIndex,
                    adGenPortTrapIdentifier
                    }
    STATUS          current
    DESCRIPTION
                    "NTU 24-Hour Errored Seconds Threshold Crossed"
    --#TYPE         "Threshold Crossing Alarm - NTU 24-Hour ES"
    --#SUMMARY      "NTU 24-Hour Errored Seconds Alarm "
    --#SUMMARY      "detected at shelf: %s, slot: %d and port: %d"
    --#ARGUMENTS    {1,2,3}
    --#SEVERITY     WARNING
    --#GENERIC      6
    --#CATEGORY     "Threshold Events"
    --#SOURCE_ID    "A"
    --#TIMEINDEX    0
    ::= {adEShdslAlarms 39}

adEShdslNTUSES24HrThreshCrossed    NOTIFICATION-TYPE
    OBJECTS         {
                    adTrapInformSeqNum,
                    sysName,
                    adGenSlotInfoIndex,
                    adGenPortTrapIdentifier
                    }
    STATUS          current
    DESCRIPTION
                    "NTU 24-Hour Severely Errored Seconds Threshold Crossed"
    --#TYPE         "Threshold Crossing Alarm - NTU 24-Hour SES"
    --#SUMMARY      "NTU 24-Hour Severely Errored Seconds Alarm "
    --#SUMMARY      "detected at shelf: %s, slot: %d and port: %d"
    --#ARGUMENTS    {1,2,3}
    --#SEVERITY     WARNING
    --#GENERIC      6
    --#CATEGORY     "Threshold Events"
    --#SOURCE_ID    "A"
    --#TIMEINDEX    0
    ::= {adEShdslAlarms 40}

adEShdslNTUUAS24HrThreshCrossed    NOTIFICATION-TYPE
    OBJECTS         {
                    adTrapInformSeqNum,
                    sysName,
                    adGenSlotInfoIndex,
                    adGenPortTrapIdentifier
                    }
    STATUS          current
    DESCRIPTION
                    "NTU 24-Hour Unavailable Seconds Threshold Crossed"
    --#TYPE         "Threshold Crossing Alarm - NTU 24-Hour UAS"
    --#SUMMARY      "NTU 24-Hour Unavailable Seconds Alarm "
    --#SUMMARY      "detected at shelf: %s, slot: %d and port: %d"
    --#ARGUMENTS    {1,2,3}
    --#SEVERITY     WARNING
    --#GENERIC      6
    --#CATEGORY     "Threshold Events"
    --#SOURCE_ID    "A"
    --#TIMEINDEX    0
    ::= {adEShdslAlarms 41}

adEShdslNTUCVC24HrThreshCrossed    NOTIFICATION-TYPE
    OBJECTS         {
                    adTrapInformSeqNum,
                    sysName,
                    adGenSlotInfoIndex,
                    adGenPortTrapIdentifier
                    }
    STATUS          current
    DESCRIPTION
                    "NTU 24-Hour Code Violation Count Threshold Crossed"
    --#TYPE         "Threshold Crossing Alarm - NTU 24-Hour CVC"
    --#SUMMARY      "NTU 24-Hour Code Violation Count Alarm "
    --#SUMMARY      "detected at shelf: %s, slot: %d and port: %d"
    --#ARGUMENTS    {1,2,3}
    --#SEVERITY     WARNING
    --#GENERIC      6
    --#CATEGORY     "Threshold Events"
    --#SOURCE_ID    "A"
    --#TIMEINDEX    0
    ::= {adEShdslAlarms 42}

adEShdslNTULOSWS24HrThreshCrossed    NOTIFICATION-TYPE
    OBJECTS         {
                    adTrapInformSeqNum,
                    sysName,
                    adGenSlotInfoIndex,
                    adGenPortTrapIdentifier
                    }
    STATUS          current
    DESCRIPTION
                    "NTU 24-Hour Loss of Sync Word Seconds Threshold Crossed"
    --#TYPE         "Threshold Crossing Alarm - NTU 24-Hour LOSWS"
    --#SUMMARY      "NTU 24-Hour Loss of Sync Word Seconds Alarm "
    --#SUMMARY      "detected at shelf: %s, slot: %d and port: %d"
    --#ARGUMENTS    {1,2,3}
    --#SEVERITY     WARNING
    --#GENERIC      6
    --#CATEGORY     "Threshold Events"
    --#SOURCE_ID    "A"
    --#TIMEINDEX    0
    ::= {adEShdslAlarms 43}

adEShdslNTUOS24HrThreshCrossed    NOTIFICATION-TYPE
    OBJECTS         {
                    adTrapInformSeqNum,
                    sysName,
                    adGenSlotInfoIndex,
                    adGenPortTrapIdentifier
                    }
    STATUS          current
    DESCRIPTION
                    "NTU 24-Hour Outage Seconds Threshold Crossed"
    --#TYPE         "Threshold Crossing Alarm - NTU 24-Hour OS"
    --#SUMMARY      "NTU 24-Hour Outage Seconds Alarm "
    --#SUMMARY      "detected at shelf: %s, slot: %d and port: %d"
    --#ARGUMENTS    {1,2,3}
    --#SEVERITY     WARNING
    --#GENERIC      6
    --#CATEGORY     "Threshold Events"
    --#SOURCE_ID    "A"
    --#TIMEINDEX    0
    ::= {adEShdslAlarms 44}


-- ********************************************
-- REGENERATOR Active/Clear Type Alarms
-- ********************************************
adEShdslRegenLossofSignalAlmCLR    NOTIFICATION-TYPE
    OBJECTS         {
                    adTrapInformSeqNum,
                    sysName,
                    adGenSlotInfoIndex,
                    adGenPortTrapIdentifier,
                    adEShdslInvIndex,
                    adEShdslSideIndex,
                    adEShdslWirePairIndex
                    }
    STATUS          current
    DESCRIPTION
                    "Loss of Signal Alarm"
    --#TYPE         "Status - Alarm"
    --#SUMMARY      "Loss of Signal Alarm "
    --#SUMMARY      "cleared at shelf: %s, slot: %d, port: %d, invindex: %d, sideindex: %d, and pairindex: %d"
    --#ARGUMENTS    {1,2,3,4,5,6}
    --#SEVERITY     MAJOR
    --#GENERIC      6
    --#CATEGORY     "Error Events"
    --#SOURCE_ID    "A"
    --#TIMEINDEX    0
    ::= {adEShdslAlarms 45}

adEShdslRegenLossofSignalAlmACT    NOTIFICATION-TYPE
    OBJECTS         {
                    adTrapInformSeqNum,
                    sysName,
                    adGenSlotInfoIndex,
                    adGenPortTrapIdentifier,
                    adEShdslInvIndex,
                    adEShdslSideIndex,
                    adEShdslWirePairIndex
                    }
    STATUS          current
    DESCRIPTION
                    "Loss of Signal Alarm"
    --#TYPE         "Status - Alarm"
    --#SUMMARY      "Loss of Signal Alarm "
    --#SUMMARY      "detected at shelf: %s, slot: %d, port: %d, invindex: %d, sideindex: %d, and pairindex: %d"
    --#ARGUMENTS    {1,2,3,4,5,6}
    --#SEVERITY     MAJOR
    --#GENERIC      6
    --#CATEGORY     "Error Events"
    --#SOURCE_ID    "A"
    --#TIMEINDEX    0
    ::= {adEShdslAlarms 46}

adEShdslRegenLossofSyncWordAlmCLR    NOTIFICATION-TYPE
    OBJECTS         {
                    adTrapInformSeqNum,
                    sysName,
                    adGenSlotInfoIndex,
                    adGenPortTrapIdentifier,
                    adEShdslInvIndex,
                    adEShdslSideIndex,
                    adEShdslWirePairIndex
                    }
    STATUS          current
    DESCRIPTION
                    "Loss of Sync Word Alarm"
    --#TYPE         "Status - Alarm"
    --#SUMMARY      "Loss of Sync Word Alarm "
    --#SUMMARY      "cleared at shelf: %s, slot: %d, port: %d, invindex: %d, sideindex: %d, and pairindex: %d"
    --#ARGUMENTS    {1,2,3,4,5,6}
    --#SEVERITY     MAJOR
    --#GENERIC      6
    --#CATEGORY     "Error Events"
    --#SOURCE_ID    "A"
    --#TIMEINDEX    0
    ::= {adEShdslAlarms 47}

adEShdslRegenLossofSyncWordAlmACT    NOTIFICATION-TYPE
    OBJECTS         {
                    adTrapInformSeqNum,
                    sysName,
                    adGenSlotInfoIndex,
                    adGenPortTrapIdentifier,
                    adEShdslInvIndex,
                    adEShdslSideIndex,
                    adEShdslWirePairIndex
                    }
    STATUS          current
    DESCRIPTION
                    "Loss of Sync Word Alarm"
    --#TYPE         "Status - Alarm"
    --#SUMMARY      "Loss of Sync Word Alarm "
    --#SUMMARY      "detected at shelf: %s, slot: %d and port: %d"
    --#ARGUMENTS    {1,2,3,4,5,6}
    --#SEVERITY     MAJOR
    --#GENERIC      6
    --#CATEGORY     "Error Events"
    --#SOURCE_ID    "A"
    --#TIMEINDEX    0
    ::= {adEShdslAlarms 48}

adEShdslRegenCRCErrorAlmCLR    NOTIFICATION-TYPE
    OBJECTS         {
                    adTrapInformSeqNum,
                    sysName,
                    adGenSlotInfoIndex,
                    adGenPortTrapIdentifier,
                    adEShdslInvIndex,
                    adEShdslSideIndex,
                    adEShdslWirePairIndex
                    }
    STATUS          current
    DESCRIPTION
                    "CRC Error"
    --#TYPE         "Status - Alarm"
    --#SUMMARY      "CRC Error "
    --#SUMMARY      "cleared at shelf: %s, slot: %d, port: %d, invindex: %d, sideindex: %d, and pairindex: %d"
    --#ARGUMENTS    {1,2,3,4,5,6}
    --#SEVERITY     MINOR
    --#GENERIC      6
    --#CATEGORY     "Error Events"
    --#SOURCE_ID    "A"
    --#TIMEINDEX    0
    ::= {adEShdslAlarms 49}

adEShdslRegenCRCErrorAlmACT    NOTIFICATION-TYPE
    OBJECTS         {
                    adTrapInformSeqNum,
                    sysName,
                    adGenSlotInfoIndex,
                    adGenPortTrapIdentifier,
                    adEShdslInvIndex,
                    adEShdslSideIndex,
                    adEShdslWirePairIndex
                    }
    STATUS          current
    DESCRIPTION
                    "CRC Error"
    --#TYPE         "Status - Alarm"
    --#SUMMARY      "CRC Error "
    --#SUMMARY      "detected at shelf: %s, slot: %d, port: %d, invindex: %d, sideindex: %d, and pairindex: %d"
    --#ARGUMENTS    {1,2,3,4,5,6}
    --#SEVERITY     MINOR
    --#GENERIC      6
    --#CATEGORY     "Error Events"
    --#SOURCE_ID    "A"
    --#TIMEINDEX    0
    ::= {adEShdslAlarms 50}

adEShdslRegenSNRMarginAlmCLR    NOTIFICATION-TYPE
    OBJECTS         {
                    adTrapInformSeqNum,
                    sysName,
                    adGenSlotInfoIndex,
                    adGenPortTrapIdentifier,
                    adEShdslInvIndex,
                    adEShdslSideIndex,
                    adEShdslWirePairIndex
                    }
    STATUS          current
    DESCRIPTION
                    "SNR Margin Alarm"
    --#TYPE         "Status - Alarm"
    --#SUMMARY      "SNR Margin Alarm "
    --#SUMMARY      "cleared at shelf: %s, slot: %d, port: %d, invindex: %d, sideindex: %d, and pairindex: %d"
    --#ARGUMENTS    {1,2,3,4,5,6}
    --#SEVERITY     MINOR
    --#GENERIC      6
    --#CATEGORY     "Error Events"
    --#SOURCE_ID    "A"
    --#TIMEINDEX    0
    ::= {adEShdslAlarms 51}

adEShdslRegenSNRMarginAlmACT    NOTIFICATION-TYPE
    OBJECTS         {
                    adTrapInformSeqNum,
                    sysName,
                    adGenSlotInfoIndex,
                    adGenPortTrapIdentifier,
                    adEShdslInvIndex,
                    adEShdslSideIndex,
                    adEShdslWirePairIndex
                    }
    STATUS          current
    DESCRIPTION
                    "SNR Margin Alarm"
    --#TYPE         "Status - Alarm"
    --#SUMMARY      "SNR Margin Alarm "
    --#SUMMARY      "detected at shelf: %s, slot: %d, port: %d, invindex: %d, sideindex: %d, and pairindex: %d"
    --#ARGUMENTS    {1,2,3,4,5,6}
    --#SEVERITY     MINOR
    --#GENERIC      6
    --#CATEGORY     "Error Events"
    --#SOURCE_ID    "A"
    --#TIMEINDEX    0
    ::= {adEShdslAlarms 52}

adEShdslRegenLoopAttenAlmCLR    NOTIFICATION-TYPE
    OBJECTS         {
                    adTrapInformSeqNum,
                    sysName,
                    adGenSlotInfoIndex,
                    adGenPortTrapIdentifier,
                    adEShdslInvIndex,
                    adEShdslSideIndex,
                    adEShdslWirePairIndex
                    }
    STATUS          current
    DESCRIPTION
                    "Loop Attenuation Alarm"
    --#TYPE         "Status - Alarm"
    --#SUMMARY      "Loop Attenuation Alarm "
    --#SUMMARY      "cleared at shelf: %s, slot: %d, port: %d, invindex: %d, sideindex: %d, and pairindex: %d"
    --#ARGUMENTS    {1,2,3,4,5,6}
    --#SEVERITY     MINOR
    --#GENERIC      6
    --#CATEGORY     "Error Events"
    --#SOURCE_ID    "A"
    --#TIMEINDEX    0
    ::= {adEShdslAlarms 53}

adEShdslRegenLoopAttenAlmACT    NOTIFICATION-TYPE
    OBJECTS         {
                    adTrapInformSeqNum,
                    sysName,
                    adGenSlotInfoIndex,
                    adGenPortTrapIdentifier,
                    adEShdslInvIndex,
                    adEShdslSideIndex,
                    adEShdslWirePairIndex
                    }
    STATUS          current
    DESCRIPTION
                    "Loop Attenuation Alarm"
    --#TYPE         "Status - Alarm"
    --#SUMMARY      "Loop Attenuation Alarm "
    --#SUMMARY      "detected at shelf: %s, slot: %d, port: %d, invindex: %d, sideindex: %d, and pairindex: %d"
    --#ARGUMENTS    {1,2,3,4,5,6}
    --#SEVERITY     MINOR
    --#GENERIC      6
    --#CATEGORY     "Error Events"
    --#SOURCE_ID    "A"
    --#TIMEINDEX    0
    ::= {adEShdslAlarms 54}

-- ********************************************
-- Auto-clearing Alert Type Alarms
-- ********************************************

-- ********************************************
-- Regenerator 15-Minute PM Threshold Alarms
-- ********************************************
adEShdslRegenESThreshCrossed    NOTIFICATION-TYPE
    OBJECTS         {
                    adTrapInformSeqNum,
                    sysName,
                    adGenSlotInfoIndex,
                    adGenPortTrapIdentifier,
                    adEShdslInvIndex,
                    adEShdslSideIndex,
                    adEShdslWirePairIndex
                    }
    STATUS          current
    DESCRIPTION
                    "Errored Seconds Threshold Crossed"
    --#TYPE         "Threshold Crossing Alarm - ES"
    --#SUMMARY      "Errored Seconds Alarm "
    --#SUMMARY      "detected at shelf: %s, slot: %d, port: %d, invindex: %d, sideindex: %d, and pairindex: %d"
    --#ARGUMENTS    {1,2,3,4,5,6}
    --#SEVERITY     WARNING
    --#GENERIC      6
    --#CATEGORY     "Threshold Events"
    --#SOURCE_ID    "A"
    --#TIMEINDEX    0
    ::= {adEShdslAlarms 55}

adEShdslRegenSESThreshCrossed    NOTIFICATION-TYPE
    OBJECTS         {
                    adTrapInformSeqNum,
                    sysName,
                    adGenSlotInfoIndex,
                    adGenPortTrapIdentifier,
                    adEShdslInvIndex,
                    adEShdslSideIndex,
                    adEShdslWirePairIndex
                    }
    STATUS          current
    DESCRIPTION
                    "Severely Errored Seconds Threshold Crossed"
    --#TYPE         "Threshold Crossing Alarm - SES"
    --#SUMMARY      "Severely Errored Seconds Alarm "
    --#SUMMARY      "detected at shelf: %s, slot: %d, port: %d, invindex: %d, sideindex: %d, and pairindex: %d"
    --#ARGUMENTS    {1,2,3,4,5,6}
    --#SEVERITY     WARNING
    --#GENERIC      6
    --#CATEGORY     "Threshold Events"
    --#SOURCE_ID    "A"
    --#TIMEINDEX    0
    ::= {adEShdslAlarms 56}

adEShdslRegenUASThreshCrossed    NOTIFICATION-TYPE
    OBJECTS         {
                    adTrapInformSeqNum,
                    sysName,
                    adGenSlotInfoIndex,
                    adGenPortTrapIdentifier,
                    adEShdslInvIndex,
                    adEShdslSideIndex,
                    adEShdslWirePairIndex
                    }
    STATUS          current
    DESCRIPTION
                    "Unavailable Seconds Threshold Crossed"
    --#TYPE         "Threshold Crossing Alarm - UAS"
    --#SUMMARY      "Unavailable Seconds Alarm "
    --#SUMMARY      "detected at shelf: %s, slot: %d, port: %d, invindex: %d, sideindex: %d, and pairindex: %d"
    --#ARGUMENTS    {1,2,3,4,5,6}
    --#SEVERITY     WARNING
    --#GENERIC      6
    --#CATEGORY     "Threshold Events"
    --#SOURCE_ID    "A"
    --#TIMEINDEX    0
    ::= {adEShdslAlarms 57}

adEShdslRegenCVCThreshCrossed    NOTIFICATION-TYPE
    OBJECTS         {
                    adTrapInformSeqNum,
                    sysName,
                    adGenSlotInfoIndex,
                    adGenPortTrapIdentifier,
                    adEShdslInvIndex,
                    adEShdslSideIndex,
                    adEShdslWirePairIndex
                    }
    STATUS          current
    DESCRIPTION
                    "Code Violation Count Threshold Crossed"
    --#TYPE         "Threshold Crossing Alarm - CVC"
    --#SUMMARY      "Code Violation Count Alarm "
    --#SUMMARY      "detected at shelf: %s, slot: %d, port: %d, invindex: %d, sideindex: %d, and pairindex: %d"
    --#ARGUMENTS    {1,2,3,4,5,6}
    --#SEVERITY     WARNING
    --#GENERIC      6
    --#CATEGORY     "Threshold Events"
    --#SOURCE_ID    "A"
    --#TIMEINDEX    0
    ::= {adEShdslAlarms 58}

adEShdslRegenLOSWSThreshCrossed    NOTIFICATION-TYPE
    OBJECTS         {
                    adTrapInformSeqNum,
                    sysName,
                    adGenSlotInfoIndex,
                    adGenPortTrapIdentifier,
                    adEShdslInvIndex,
                    adEShdslSideIndex,
                    adEShdslWirePairIndex
                    }
    STATUS          current
    DESCRIPTION
                    "Loss of Sync Word Seconds Threshold Crossed"
    --#TYPE         "Threshold Crossing Alarm - LOSWS"
    --#SUMMARY      "Loss of Sync Word Seconds Alarm "
    --#SUMMARY      "detected at shelf: %s, slot: %d, port: %d, invindex: %d, sideindex: %d, and pairindex: %d"
    --#ARGUMENTS    {1,2,3,4,5,6}
    --#SEVERITY     WARNING
    --#GENERIC      6
    --#CATEGORY     "Threshold Events"
    --#SOURCE_ID    "A"
    --#TIMEINDEX    0
    ::= {adEShdslAlarms 59}

adEShdslRegenOSThreshCrossed    NOTIFICATION-TYPE
    OBJECTS         {
                    adTrapInformSeqNum,
                    sysName,
                    adGenSlotInfoIndex,
                    adGenPortTrapIdentifier,
                    adEShdslInvIndex,
                    adEShdslSideIndex,
                    adEShdslWirePairIndex
                    }
    STATUS          current
    DESCRIPTION
                    "Outage Seconds Threshold Crossed"
    --#TYPE         "Threshold Crossing Alarm - OS"
    --#SUMMARY      "Outage Seconds Alarm "
    --#SUMMARY      "detected at shelf: %s, slot: %d, port: %d, invindex: %d, sideindex: %d, and pairindex: %d"
    --#ARGUMENTS    {1,2,3,4,5,6}
    --#SEVERITY     WARNING
    --#GENERIC      6
    --#CATEGORY     "Threshold Events"
    --#SOURCE_ID    "A"
    --#TIMEINDEX    0
    ::= {adEShdslAlarms 60}

-- ********************************************
-- 24-Hour PM Threshold Alarms
-- ********************************************
adEShdslRegenES24HrThreshCrossed    NOTIFICATION-TYPE
    OBJECTS         {
                    adTrapInformSeqNum,
                    sysName,
                    adGenSlotInfoIndex,
                    adGenPortTrapIdentifier,
                    adEShdslInvIndex,
                    adEShdslSideIndex,
                    adEShdslWirePairIndex
                    }
    STATUS          current
    DESCRIPTION
                    "24-Hour Errored Seconds Threshold Crossed"
    --#TYPE         "Threshold Crossing Alarm - 24-Hour ES"
    --#SUMMARY      "24-Hour Errored Seconds Alarm "
    --#SUMMARY      "detected at shelf: %s, slot: %d, port: %d, invindex: %d, sideindex: %d, and pairindex: %d"
    --#ARGUMENTS    {1,2,3,4,5,6}
    --#SEVERITY     WARNING
    --#GENERIC      6
    --#CATEGORY     "Threshold Events"
    --#SOURCE_ID    "A"
    --#TIMEINDEX    0
    ::= {adEShdslAlarms 61}

adEShdslRegenSES24HrThreshCrossed    NOTIFICATION-TYPE
    OBJECTS         {
                    adTrapInformSeqNum,
                    sysName,
                    adGenSlotInfoIndex,
                    adGenPortTrapIdentifier,
                    adEShdslInvIndex,
                    adEShdslSideIndex,
                    adEShdslWirePairIndex
                    }
    STATUS          current
    DESCRIPTION
                    "24-Hour Severely Errored Seconds Threshold Crossed"
    --#TYPE         "Threshold Crossing Alarm - 24-Hour SES"
    --#SUMMARY      "24-Hour Severely Errored Seconds Alarm "
    --#SUMMARY      "detected at shelf: %s, slot: %d, port: %d, invindex: %d, sideindex: %d, and pairindex: %d"
    --#ARGUMENTS    {1,2,3,4,5,6}
    --#SEVERITY     WARNING
    --#GENERIC      6
    --#CATEGORY     "Threshold Events"
    --#SOURCE_ID    "A"
    --#TIMEINDEX    0
    ::= {adEShdslAlarms 62}

adEShdslRegenUAS24HrThreshCrossed    NOTIFICATION-TYPE
    OBJECTS         {
                    adTrapInformSeqNum,
                    sysName,
                    adGenSlotInfoIndex,
                    adGenPortTrapIdentifier,
                    adEShdslInvIndex,
                    adEShdslSideIndex,
                    adEShdslWirePairIndex
                    }
    STATUS          current
    DESCRIPTION
                    "24-Hour Unavailable Seconds Threshold Crossed"
    --#TYPE         "Threshold Crossing Alarm - 24-Hour UAS"
    --#SUMMARY      "24-Hour Unavailable Seconds Alarm "
    --#SUMMARY      "detected at shelf: %s, slot: %d, port: %d, invindex: %d, sideindex: %d, and pairindex: %d"
    --#ARGUMENTS    {1,2,3,4,5,6}
    --#SEVERITY     WARNING
    --#GENERIC      6
    --#CATEGORY     "Threshold Events"
    --#SOURCE_ID    "A"
    --#TIMEINDEX    0
    ::= {adEShdslAlarms 63}

adEShdslRegenCVC24HrThreshCrossed    NOTIFICATION-TYPE
    OBJECTS         {
                    adTrapInformSeqNum,
                    sysName,
                    adGenSlotInfoIndex,
                    adGenPortTrapIdentifier,
                    adEShdslInvIndex,
                    adEShdslSideIndex,
                    adEShdslWirePairIndex
                    }
    STATUS          current
    DESCRIPTION
                    "24-Hour Code Violation Count Threshold Crossed"
    --#TYPE         "Threshold Crossing Alarm - 24-Hour CVC"
    --#SUMMARY      "24-Hour Code Violation Count Alarm "
    --#SUMMARY      "detected at shelf: %s, slot: %d, port: %d, invindex: %d, sideindex: %d, and pairindex: %d"
    --#ARGUMENTS    {1,2,3,4,5,6}
    --#SEVERITY     WARNING
    --#GENERIC      6
    --#CATEGORY     "Threshold Events"
    --#SOURCE_ID    "A"
    --#TIMEINDEX    0
    ::= {adEShdslAlarms 64}

adEShdslRegenLOSWS24HrThreshCrossed    NOTIFICATION-TYPE
    OBJECTS         {
                    adTrapInformSeqNum,
                    sysName,
                    adGenSlotInfoIndex,
                    adGenPortTrapIdentifier,
                    adEShdslInvIndex,
                    adEShdslSideIndex,
                    adEShdslWirePairIndex
                    }
    STATUS          current
    DESCRIPTION
                    "24-Hour Loss of Sync Word Seconds Threshold Crossed"
    --#TYPE         "Threshold Crossing Alarm - 24-Hour LOSWS"
    --#SUMMARY      "24-Hour Loss of Sync Word Seconds Alarm "
    --#SUMMARY      "detected at shelf: %s, slot: %d, port: %d, invindex: %d, sideindex: %d, and pairindex: %d"
    --#ARGUMENTS    {1,2,3,4,5,6}
    --#SEVERITY     WARNING
    --#GENERIC      6
    --#CATEGORY     "Threshold Events"
    --#SOURCE_ID    "A"
    --#TIMEINDEX    0
    ::= {adEShdslAlarms 65}

adEShdslRegenOS24HrThreshCrossed    NOTIFICATION-TYPE
    OBJECTS         {
                    adTrapInformSeqNum,
                    sysName,
                    adGenSlotInfoIndex,
                    adGenPortTrapIdentifier,
                    adEShdslInvIndex,
                    adEShdslSideIndex,
                    adEShdslWirePairIndex
                    }
    STATUS          current
    DESCRIPTION
                    "24-Hour Outage Seconds Threshold Crossed"
    --#TYPE         "Threshold Crossing Alarm - 24-Hour OS"
    --#SUMMARY      "24-Hour Outage Seconds Alarm "
    --#SUMMARY      "detected at shelf: %s, slot: %d, port: %d, invindex: %d, sideindex: %d, and pairindex: %d"
    --#ARGUMENTS    {1,2,3,4,5,6}
    --#SEVERITY     WARNING
    --#GENERIC      6
    --#CATEGORY     "Threshold Events"
    --#SOURCE_ID    "A"
    --#TIMEINDEX    0
    ::= {adEShdslAlarms 66}


adEShdslLoopbackEnabledCLR    NOTIFICATION-TYPE
    OBJECTS         {
                    adTrapInformSeqNum,
                    sysName,
                    adGenSlotInfoIndex,
                    adGenPortTrapIdentifier,
                    adEShdslInvIndex,
                    adEShdslSideIndex,
                    adEShdslWirePairIndex
                    }
    STATUS          current
    DESCRIPTION
                    "Loopback Enabled Alarm"
    --#TYPE         "Status - Alarm"
    --#SUMMARY      "Loopback Enabled Alarm "
    --#SUMMARY      "cleared at shelf: %s, slot: %d, port: %d, invindex: %d, sideindex: %d, and pairindex: %d"
    --#ARGUMENTS    {1,2,3,4,5,6}
    --#SEVERITY     MINOR
    --#GENERIC      6
    --#CATEGORY     "Error Events"
    --#SOURCE_ID    "A"
    --#TIMEINDEX    0
    ::= {adEShdslAlarms 71}

adEShdslLoopbackEnabledACT    NOTIFICATION-TYPE
    OBJECTS         {
                    adTrapInformSeqNum,
                    sysName,
                    adGenSlotInfoIndex,
                    adGenPortTrapIdentifier,
                    adEShdslInvIndex,
                    adEShdslSideIndex,
                    adEShdslWirePairIndex
                    }
    STATUS          current
    DESCRIPTION
                    "Loopback Enabled Alarm"
    --#TYPE         "Status - Alarm"
    --#SUMMARY      "Loopback Enabled Alarm "
    --#SUMMARY      "detected at shelf: %s, slot: %d, port: %d, invindex: %d, sideindex: %d, and pairindex: %d"
    --#ARGUMENTS    {1,2,3,4,5,6}
    --#SEVERITY     MINOR
    --#GENERIC      6
    --#CATEGORY     "Error Events"
    --#SOURCE_ID    "A"
    --#TIMEINDEX    0
    ::= {adEShdslAlarms 72}

-- ********************************************
-- Retrain and Handshake Failure Threshold Alarms
-- ********************************************
adEShdslRetrains15MinThreshCrossed    NOTIFICATION-TYPE
    OBJECTS         {
                    adTrapInformSeqNum,
                    sysName,
                    adGenSlotInfoIndex,
                    adGenPortTrapIdentifier
                    }
    STATUS          current
    DESCRIPTION
                    "15 Minute Retrains Threshold Crossed"
    --#TYPE         "Threshold Crossing Alarm - 15 Minute Retrains"
    --#SUMMARY      "15 Minute Retrains Alarm "
    --#SUMMARY      "detected at shelf: %s, slot: %d and port: %d"
    --#ARGUMENTS    {1,2,3}
    --#SEVERITY     WARNING
    --#GENERIC      6
    --#CATEGORY     "Threshold Events"
    --#SOURCE_ID    "A"
    --#TIMEINDEX    0
    ::= {adEShdslAlarms 80}

adEShdslHandshakeFailures15MinThreshCrossed    NOTIFICATION-TYPE
    OBJECTS         {
                    adTrapInformSeqNum,
                    sysName,
                    adGenSlotInfoIndex,
                    adGenPortTrapIdentifier
                    }
    STATUS          current
    DESCRIPTION
                    "15 Minute Handshake Failures Threshold Crossed"
    --#TYPE         "Threshold Crossing Alarm - 15 Minute Handshake Failures"
    --#SUMMARY      "15 Minute Handshake Failures Alarm "
    --#SUMMARY      "detected at shelf: %s, slot: %d and port: %d"
    --#ARGUMENTS    {1,2,3}
    --#SEVERITY     WARNING
    --#GENERIC      6
    --#CATEGORY     "Threshold Events"
    --#SOURCE_ID    "A"
    --#TIMEINDEX    0
    ::= {adEShdslAlarms 81}

adEShdslRetrains24HrThreshCrossed    NOTIFICATION-TYPE
    OBJECTS         {
                    adTrapInformSeqNum,
                    sysName,
                    adGenSlotInfoIndex,
                    adGenPortTrapIdentifier
                    }
    STATUS          current
    DESCRIPTION
                    "24 Hour Retrains Threshold Crossed"
    --#TYPE         "Threshold Crossing Alarm - 24 Hour Retrains"
    --#SUMMARY      "24 Hour Retrains Alarm "
    --#SUMMARY      "detected at shelf: %s, slot: %d and port: %d"
    --#ARGUMENTS    {1,2,3}
    --#SEVERITY     WARNING
    --#GENERIC      6
    --#CATEGORY     "Threshold Events"
    --#SOURCE_ID    "A"
    --#TIMEINDEX    0
    ::= {adEShdslAlarms 82}

adEShdslHandshakeFailures24HrThreshCrossed    NOTIFICATION-TYPE
    OBJECTS         {
                    adTrapInformSeqNum,
                    sysName,
                    adGenSlotInfoIndex,
                    adGenPortTrapIdentifier
                    }
    STATUS          current
    DESCRIPTION
                    "24 Hour Handshake Failures Threshold Crossed"
    --#TYPE         "Threshold Crossing Alarm - 24 Hour Handshake Failures"
    --#SUMMARY      "24 Hour Handshake Failures Alarm "
    --#SUMMARY      "detected at shelf: %s, slot: %d and port: %d"
    --#ARGUMENTS    {1,2,3}
    --#SEVERITY     WARNING
    --#GENERIC      6
    --#CATEGORY     "Threshold Events"
    --#SOURCE_ID    "A"
    --#TIMEINDEX    0
    ::= {adEShdslAlarms 83}

adEShdslBadSpliceDetected    NOTIFICATION-TYPE
    OBJECTS         {
                    adTrapInformSeqNum,
                    sysName,
                    adGenSlotInfoIndex,
                    adGenPortTrapIdentifier,
                    adEShdslInvIndex,
                    adEShdslSideIndex,
                    adEShdslInvPhysicalLinkId
                    }
    STATUS          current
    DESCRIPTION
                    "Bad Splice Detection Alarm is generated when the BSD algorithm detects a potential bad splice event."
    --#TYPE         "Status - Alarm"
    --#SUMMARY      "Bad Splice Detection Alarm"
    --#SUMMARY      "detected at shelf: %s, slot: %d, port: %d, invindex: %d, sideindex: %d, and physicallinkid: %d"
    --#ARGUMENTS    {1,2,3,4,5,6}
    --#SEVERITY     WARNING
    --#GENERIC      6
    --#CATEGORY     "Error Events"
    --#SOURCE_ID    "A"
    --#TIMEINDEX    0
    ::= {adEShdslAlarms 84}

adEShdslSruShortDetectAlmCLR    NOTIFICATION-TYPE
    OBJECTS         {
                    adTrapInformSeqNum,
                    sysName,
                    adGenSlotInfoIndex,
                    adGenPortTrapIdentifier,
                    adEShdslInvIndex,
                    adEShdslSideIndex,
                    adEShdslInvPhysicalLinkId
                    }
    STATUS          current
    DESCRIPTION
                    "Short Detection Alarm clear"
    --#TYPE         "Status - Alarm"
    --#SUMMARY      "Short Detection Alarm clear"
    --#SUMMARY      "cleared at shelf: %s, slot: %d, port: %d, invindex: %d, sideindex: %d, and physicallinkid: %d"
    --#ARGUMENTS    {1,2,3,4,5,6}
    --#SEVERITY     MAJOR
    --#GENERIC      6
    --#CATEGORY     "Error Events"
    --#SOURCE_ID    "A"
    --#TIMEINDEX    0
    ::= {adEShdslAlarms 85}

adEShdslSruShortDetectAlmACT    NOTIFICATION-TYPE
    OBJECTS         {
                    adTrapInformSeqNum,
                    sysName,
                    adGenSlotInfoIndex,
                    adGenPortTrapIdentifier,
                    adEShdslInvIndex,
                    adEShdslSideIndex,
                    adEShdslInvPhysicalLinkId
                    }
    STATUS          current
    DESCRIPTION
                    "Short Detection Alarm is generated when a regenerator element indicates a short has been detected on the span power interface."
    --#TYPE         "Status - Alarm"
    --#SUMMARY      "Short Detection Alarm active"
    --#SUMMARY      "detected at shelf: %s, slot: %d, port: %d, invindex: %d, sideindex: %d, and physicallinkid: %d"
    --#ARGUMENTS    {1,2,3,4,5,6}
    --#SEVERITY     MAJOR
    --#GENERIC      6
    --#CATEGORY     "Error Events"
    --#SOURCE_ID    "A"
    --#TIMEINDEX    0
    ::= {adEShdslAlarms 86}

adEShdslSruGroundFaultDetectAlmCLR    NOTIFICATION-TYPE
    OBJECTS         {
                    adTrapInformSeqNum,
                    sysName,
                    adGenSlotInfoIndex,
                    adGenPortTrapIdentifier,
                    adEShdslInvIndex,
                    adEShdslSideIndex,
                    adEShdslInvPhysicalLinkId
                    }
    STATUS          current
    DESCRIPTION
                    "Ground Fault Detection Alarm clear"
    --#TYPE         "Status - Alarm"
    --#SUMMARY      "Short Detection Alarm clear"
    --#SUMMARY      "cleared at shelf: %s, slot: %d, port: %d, invindex: %d, sideindex: %d, and physicallinkid: %d"
    --#ARGUMENTS    {1,2,3,4,5,6}
    --#SEVERITY     MAJOR
    --#GENERIC      6
    --#CATEGORY     "Error Events"
    --#SOURCE_ID    "A"
    --#TIMEINDEX    0
    ::= {adEShdslAlarms 87}

adEShdslSruGroundFaultDetectAlmACT    NOTIFICATION-TYPE
    OBJECTS         {
                    adTrapInformSeqNum,
                    sysName,
                    adGenSlotInfoIndex,
                    adGenPortTrapIdentifier,
                    adEShdslInvIndex,
                    adEShdslSideIndex,
                    adEShdslInvPhysicalLinkId
                    }
    STATUS          current
    DESCRIPTION
                    "Ground Fault Detection Alarm is generated when a regenerator element indicates a ground fault has been detected on the span power interface."
    --#TYPE         "Status - Alarm"
    --#SUMMARY      "Ground Fault Detection Alarm active"
    --#SUMMARY      "detected at shelf: %s, slot: %d, port: %d, invindex: %d, sideindex: %d, and physicallinkid: %d"
    --#ARGUMENTS    {1,2,3,4,5,6}
    --#SEVERITY     MAJOR
    --#GENERIC      6
    --#CATEGORY     "Error Events"
    --#SOURCE_ID    "A"
    --#TIMEINDEX    0
    ::= {adEShdslAlarms 88}

adEShdslSCIThreshCrossed    NOTIFICATION-TYPE
    OBJECTS         {
                    adTrapInformSeqNum,
                    sysName,
                    adGenSlotInfoIndex,
                    adGenPortTrapIdentifier,
                    adTAeSCUTrapAlarmLevel
                    }
    STATUS          current
    DESCRIPTION
                    "This alarm is generated when no command responses have been received within the configured threshold window."
    --#TYPE         "Threshold Crossing Alarm - SCI Alarm"
    --#SUMMARY      "SCI Alarm"
    --#SUMMARY      "detected at shelf: %s, slot: %d and port: %d"
    --#ARGUMENTS    {1,2,3}
    --#SEVERITY     WARNING
    --#GENERIC      6
    --#CATEGORY     "Threshold Events"
    --#SOURCE_ID    "A"
    --#TIMEINDEX    0
    ::= {adEShdslAlarms 89}

END

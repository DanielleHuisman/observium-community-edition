ADTRAN-TA1100FSCM-MIB

   DEFINITIONS ::= BEGIN

   -- TITLE:     The ADTRAN enhanced System Controller Unit MIB
   -- PRODUCT:   1181018L2
   -- VERSION:   1.0
   -- DATE:      08/25/05

   -- This MIB defines the object identifier (OID) for the
   -- Total Access 1100F SCM.  It also defines product specific objects.

    -- adGenSlotAlarmStatus description
    -- The various bit positions are:
    -- ==========================================================================
    -- Bits Details
    -- ==========================================================================
    --
    --   Bit  1 adTAeSCUCraftLoginNotfication
    --   Bit  2 adTASoftwareVerMisMatch
    --   Bit  3 adSCM5kExternalAlm
    --   Bit  4 adSCM5kExternalAlm
    --   Bit  5 adSCM5kExternalAlm
    --   Bit  6 adSCM5kExternalAlm
    --   Bit  7 adSCM5kExternalAlm
    --   Bit  8 adTACriticalAudibleRelayActive
    --   Bit  9 adTAMajAudibleRelayActive
    --   Bit 10 adTAMinorAudibleRelayActive
    --   Bit 11 undefined
    --   Bit 12 adTAPowerSheddingInputAsserted
    --   Bit 13 adTAPowerSheddingActivated
    --
    -- ==========================================================================
    -- ==========================================================================

   -- MIBs supported:

   -- HISTORY:
      -- 08/25/2005  JMC   Created.
      -- 08/26/2005  JMC   Small touches for correctness and added imports.
      -- 11/11/2005  JMC   Added adTATIDSysNameSyncEnable.
      -- 04/20/2006  JMC   Added identifiers for 1248e and 1200f.
      -- 11/28/2006  KGG   Added 1124P T1 / HDSL Identifiers
     -- 01/16/2007	 KGG   Commented out HDSL-SCM Identifier as we will only need 1 for the 1124P System.
      -- 06/14/2007  WFE   Added alarm bits to adGenSlotAlarmStatus.

   -- Operational notes
     -- When the SCM is addressed by IP address with scalar objects, it usually replies
     -- as a proxy for the shelf in which it is contained, providing MIB-2 system group
     -- support and ADTRAN.MIB object support. To address information on specific cards,
     -- card/port selection can be done via the ADTRAN generic MIBs, or internet standard
     -- MIBs that are indexed by ifIndex. Mapping between these indexing methods is provided
     -- in the genport MIB.
     --
     -- The exception to scalars being processed directely by the SCM are those in Internet
     -- standard MIBs that are specially identified to belong to a Multiplexor, and for which
     -- special provision has been made to direct these anonymous requests to the appropriate
     -- Mux. Otherwise scalars are not supported on line cards as there is no way to select which
     -- card is the intended target.

   IMPORTS
       adProducts,
       adMgmt
           FROM ADTRAN-MIB
       adTrapInformSeqNum
           FROM ADTRAN-GENTRAPINFORM-MIB
       adGenSlotInfoIndex, adGenSlotProdName
           FROM ADTRAN-GENSLOT-MIB
       sysName
            FROM SNMPv2-MIB
       adTAeSCUTrapAlarmLevel
           FROM ADTRAN-TAeSCUEXT1-MIB
       NOTIFICATION-TYPE, MODULE-IDENTITY,
       OBJECT-TYPE, OBJECT-IDENTITY
           FROM SNMPv2-SMI
   ;

   adTA1100Fcfmg MODULE-IDENTITY
         LAST-UPDATED "201002241300Z"
         ORGANIZATION "Adtran, Inc."
         CONTACT-INFO
           "CND Tech Support
               Postal: ADTRAN, Inc.
                       901 Explorer Blvd.
                       Huntsville, AL  35806
                       Tel: +1 800 726-8663
                       Fax: +1 256 963 6217
                       E-mail: support@adtran.com"
         DESCRIPTION
            "This MIB defines the objects for the adta1100fSCM MIB."
         REVISION "201002241300Z"
         DESCRIPTION "Converted from SNMPv1 adta1100fSCM.mib file."
      ::= { adMgmt 827 }

   -- OBJECT IDENTIFIERS

   -- 1100F Copper-Based (a.k.a. Copper-Fed)    (P/N: 1179762L1 - L3)
   adTA1100Fcf              OBJECT IDENTIFIER ::= { adProducts 827 }
   -- adTA1100Fcfmg            OBJECT IDENTIFIER ::= { adMgmt     827 }
   adTA1100FcfScm           OBJECT IDENTIFIER ::= { adProducts 828 }

   -- 1100F SFP-Based (a.k.a. Fiber-Fed)        (P/N: 1179760L1 - L3)
   adTA1100Fff              OBJECT IDENTIFIER ::= { adProducts 824 }
   adTA1100Fffmg            OBJECT IDENTIFIER ::= { adMgmt     824 }
   adTA1100FffScm           OBJECT IDENTIFIER ::= { adProducts 825 }

   -- 1248e                                     (P/N: 1179641AL3)
   adTA1248EthIP            OBJECT IDENTIFIER ::= { adProducts 867 }
   adTA1248EthIPScm         OBJECT IDENTIFIER ::= { adProducts 886 }

   -- 1200f    (P/N: 1179660L1)
   adTA1200Fff              OBJECT IDENTIFIER ::= { adProducts 883 }
   adTA1200FffScm           OBJECT IDENTIFIER ::= { adProducts 884 }

   -- 1124P T1 TA1124P T1-EFM Fed Minidslam 24 port ADSL2+ digital Pots          (P/N: 1179713L1 - L3)
   adTA1124PT1              OBJECT IDENTIFIER ::= { adProducts 958 }
   adTA1124PT1Scm           OBJECT IDENTIFIER ::= { adProducts 959 }

   -- 1124P HDSL TA1124P HDSL4-EFM Fed Minidslam 24 port ADSL2+ digital Pots     (P/N: 1179718L1 - L3)
   adTA1124PHDSL4           OBJECT IDENTIFIER ::= { adProducts 962 }
   -- adTA1124PHDSL4Scm        OBJECT IDENTIFIER ::= { adProducts 963 }  Only using 959, kept as reference.




   -- Subtree for Prov Items
   adTA1100FSysConfig       OBJECT IDENTIFIER ::= { adTA1100Fcfmg 10 }




   -- PROV ITEMS

        adTATIDSysNameSyncEnable OBJECT-TYPE
             SYNTAX  INTEGER {
                                  enable(1),
                                  disable(2)
                             }
                     MAX-ACCESS  read-write
                     STATUS  current
                     DESCRIPTION
                        "Enable or disable the synchronization of the TID and SNMP SysName provisions.
                        Enabling this option will overwrite the current SysName with the TID and any
                        subsequent set to the SysName must meet TID syntax restrictions."
                     ::= { adTA1100FSysConfig 1 }



   -- ALARMS

   adTA1100FcfSCMNotificationEvents OBJECT-IDENTITY
                STATUS current
                DESCRIPTION "The SCM controller events"
                ::= { adTA1100Fcf 0 }

        adTADeviceMgmtRestored   NOTIFICATION-TYPE
                OBJECTS {
                        adTrapInformSeqNum,
                        sysName,
                        adGenSlotInfoIndex,
                        adTAeSCUTrapAlarmLevel,
                        adGenSlotProdName
                        }
                STATUS current
                DESCRIPTION
                     "Management communication with a device has been restored"
        --#TYPE      "Informational - Communication with device restored"
        --#SUMMARY   "TA1100F 82402: Communication with device restored;"
        --#SUMMARY   "detected at chassis: %s, slot: %d productname: %s"
        --#ARGUMENTS { 1, 2, 4}
        --#SEVERITY  MAJOR
        --#GENERIC   6
        --#CATEGORY  "Error Events"
        --#SOURCE_ID "A"
        --#TIMEINDEX 0
        ::= { adTA1100FcfSCMNotificationEvents 82402 }


        adTADeviceMgmtFail   NOTIFICATION-TYPE
                OBJECTS {
                        adTrapInformSeqNum,
                        sysName,
                        adGenSlotInfoIndex,
                        adTAeSCUTrapAlarmLevel,
                        adGenSlotProdName
                        }
                STATUS current
                DESCRIPTION
                        "Management communication with a device has failed"
        --#TYPE      "Informational - Communication with device failed"
        --#SUMMARY   "TA1100F 82403: Communication with device failed;"
        --#SUMMARY   "detected at chassis: %s, slot: %d productname: %s"
        --#ARGUMENTS { 1, 2, 4}
        --#SEVERITY  MAJOR
        --#GENERIC   6
        --#CATEGORY  "Error Events"
        --#SOURCE_ID "A"
        --#TIMEINDEX 0
        ::= { adTA1100FcfSCMNotificationEvents 82403 }



        adTADeviceInserted   NOTIFICATION-TYPE
                OBJECTS {
                        adTrapInformSeqNum,
                        sysName,
                        adGenSlotInfoIndex,
                        adTAeSCUTrapAlarmLevel,
                        adGenSlotProdName
                        }
                STATUS current
                DESCRIPTION
                        "A device has been inserted into the system"
        --#TYPE      "Informational - A device has been inserted into the system"
        --#SUMMARY   "TA1100F 82404: Device inserted into system;"
        --#SUMMARY   "detected at chassis: %s, slot: %d productname: %s"
        --#ARGUMENTS { 1, 2, 4}
        --#SEVERITY  INFORMATIONAL
        --#GENERIC   6
        --#CATEGORY  "Configuration Events"
        --#SOURCE_ID "A"
        --#TIMEINDEX 0
        ::= { adTA1100FcfSCMNotificationEvents 82404 }


        adTADeviceRemoved   NOTIFICATION-TYPE
                OBJECTS {
                        adTrapInformSeqNum,
                        sysName,
                        adGenSlotInfoIndex,
                        adTAeSCUTrapAlarmLevel,
                        adGenSlotProdName
                        }
                STATUS current
                DESCRIPTION
                        "A device has been removed from the system"
        --#TYPE      "Informational - A device has been removed from the system"
        --#SUMMARY   "TA1100F 82405: Device removed from system;"
        --#SUMMARY   "detected at chassis: %s, slot: %d productname: %s"
        --#ARGUMENTS { 1, 2, 4}
        --#SEVERITY  WARNING
        --#GENERIC   6
        --#CATEGORY  "Configuration Events"
        --#SOURCE_ID "A"
        --#TIMEINDEX 0
        ::= { adTA1100FcfSCMNotificationEvents 82405 }

   END

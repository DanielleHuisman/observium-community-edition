ADTRAN-TA5K-ATM-LM-MIB

    DEFINITIONS ::= BEGIN

    -- TITLE:     The ADTRAN Total Access 5000 Gen ATM Line Modules
    -- PRODUCT:   1187200L1, 1187201L1, 1187210L1, 1187211L1
    -- VERSION:   1.0
    -- DATE:      April 24, 2007

    -- This MIB defines the object identifier (OID) for the Total Access
    -- 5000 Line Modules containing ATM interfaces.

    -- MIBs supported:
    --   None

    -- HISTORY:
       -- Mar. 09, 2007  GLF Added to TACore based of the product specific mib for the ATM Line Modules to use
       -- Apr. 22, 2008  AD  Add support for VP Switching
       -- Apr. 24, 2008  DCC Add support for selecting up to 32 ports for timing
       -- Oct. 31, 2008  DCC Add support for bandwidth utilization stats
       -- 7/06/2009      jlb Corrected SMICng compile errors
       -- 11/20/2009     glf add missing OIDs in the adGenTa5kAtmVpStatusTable that already have RMD support
       -- 02/16/2010	 glf add Vcl learned count OID (adGenTa5kAtmLMCardVclLearnedCount).
       -- 08/17/2010 	 glf add AAL5 stats to the adGenTa5kAtmVplStatsTable, needed for WebGUI.
	   -- 01/18/2010     glf add adGenTa5kAtmLMCardCurrentOAMID and adGenTa5kAtmLMCardFutureOAMID to the adGenTa5kAtmLMCardProvTable
	   -- 01/27/2011     glf filled in missing descriptions
       --                DO NOT ADD REVISION INFORMATION HERE

    IMPORTS
        MODULE-IDENTITY, OBJECT-TYPE, Integer32, Counter32, Gauge32, NOTIFICATION-TYPE
            FROM SNMPv2-SMI

        DisplayString, TruthValue, MacAddress
            FROM SNMPv2-TC

        ifIndex
            FROM IF-MIB

--        sysName
--            FROM RFC1213-MIB

        adGenSlotInfoIndex
            FROM ADTRAN-GENSLOT-MIB

        atmVclVpi, atmVclVci, atmVplVpi
            FROM ATM-MIB

		adTrapInformSeqNum
			FROM ADTRAN-GENTRAPINFORM-MIB

		sysName
            FROM SNMPv2-MIB

        adGenTa5kAtmLM, adGenTa5kAtmLMID
            FROM ADTRAN-GENTA5K-MIB;


-- *********************************************************************************************************

    adTa5kAtmLMModuleIdentity MODULE-IDENTITY
        LAST-UPDATED "201308050000Z"
        ORGANIZATION
            "ADTRAN, Inc."
        CONTACT-INFO
            "CND Tech Support
                Postal: ADTRAN, Inc.
                        901 Explorer Blvd.
                        Huntsville, AL  35806
                        Tel: +1 800 726-8663
                        Fax: +1 256 963 6217
                        E-mail: support@adtran.com"
        DESCRIPTION
            "Total Access 5000 ATM LM MIB"

        REVISION "201308050000Z"
        DESCRIPTION  "Added new OID adGenTa5kAtmPortProvShapingUBR to the adGenTa5kAtmPortProvisioningTable Table."                                          
        REVISION "201201300000Z"
        DESCRIPTION  "Added OIDs to reset DHCP card level PM history and rolling counters."                                          
        REVISION "201201040000Z"
        DESCRIPTION  "Added DHCP Relay Agent PM history counters at the ATM interface and card level"                     
        REVISION "201110070000Z"
        DESCRIPTION  "Added an OID to provision DHCP Option 82 Circuit ID string for an ATM port"                     
        REVISION "201108310000Z"
        DESCRIPTION  "Added OID to return cell delineation status for an ATM port"
        REVISION "201106010000Z"
        DESCRIPTION  "Added OIDs to retrieve VCL and VPL connection information"
        REVISION "201104140000Z"
        DESCRIPTION  "Added OIDs for free-rolling counters"
       
        ::= { adGenTa5kAtmLMID 1 }


    -- OBJECT IDENTIFIERS

    adGenTa5kAtmLMConfig           OBJECT IDENTIFIER ::= { adGenTa5kAtmLM 1 }
    adGenTa5kAtmLMProvisioning     OBJECT IDENTIFIER ::= { adGenTa5kAtmLM 2 }
    adGenTa5kAtmLMPMStats          OBJECT IDENTIFIER ::= { adGenTa5kAtmLM 3 }
    adGenTa5kAtmLMVpStatus         OBJECT IDENTIFIER ::= { adGenTa5kAtmLM 4 }
    adGenTa5kAtmLMAlarmPrefix      OBJECT IDENTIFIER ::= { adGenTa5kAtmLM 5 }
    adGenTa5kAtmLMAlarm            OBJECT IDENTIFIER ::= { adGenTa5kAtmLMAlarmPrefix 0 }

-- *********************************************************************************************************
    adGenTa5kAtmLMConfigTable OBJECT-TYPE
        SYNTAX      SEQUENCE OF AdGenTa5kAtmLMConfigEntry
        MAX-ACCESS  not-accessible
        STATUS      current
        DESCRIPTION
                   "ATM Line Module Configuration"
        ::= { adGenTa5kAtmLMConfig 1 }

    adGenTa5kAtmLMConfigEntry OBJECT-TYPE
        SYNTAX  AdGenTa5kAtmLMConfigEntry
        MAX-ACCESS  not-accessible
        STATUS      current
        DESCRIPTION
                   "Table Entry"
        INDEX   { adGenSlotInfoIndex}
        ::= { adGenTa5kAtmLMConfigTable 1 }

    AdGenTa5kAtmLMConfigEntry ::=
        SEQUENCE {
                        adGenTa5kAtmLMConfigBootCodeRev         DisplayString,
                        adGenTa5kAtmLMConfigSystemSWRev         DisplayString,
                        adGenTa5kAtmLMConfigBootSysSWRev        DisplayString,
                        adGenTa5kAtmLMConfigMacAddress          MacAddress,
                        adGenTa5kAtmLMConfigFPGARev             DisplayString,
                        adGenTa5kAtmLMConfigCPLDRev             DisplayString,
                        adGenTa5kAtmLMConfigWDDIRev             DisplayString,
                        adGenTa5kAtmLMConfigDPSRev              DisplayString						
                }

    adGenTa5kAtmLMConfigBootCodeRev OBJECT-TYPE
        SYNTAX          DisplayString
        MAX-ACCESS      read-only
        STATUS          current
        DESCRIPTION
                "Returns Code revision for the boot code xxx.xxx format"
        ::= { adGenTa5kAtmLMConfigEntry 1 }

    adGenTa5kAtmLMConfigSystemSWRev OBJECT-TYPE
        SYNTAX          DisplayString
        MAX-ACCESS      read-only
        STATUS          current
        DESCRIPTION
                "Returns code revision for the application code in the system format xx.xx.xx.xx"
        ::= { adGenTa5kAtmLMConfigEntry 2 }

    adGenTa5kAtmLMConfigBootSysSWRev OBJECT-TYPE
        SYNTAX          DisplayString
        MAX-ACCESS      read-only
        STATUS          current
        DESCRIPTION
                "Returns code revision for the boot code in the system format xx.xx.xx.xx.xx"
        ::= { adGenTa5kAtmLMConfigEntry 3 }

    adGenTa5kAtmLMConfigMacAddress OBJECT-TYPE
        SYNTAX          MacAddress
        MAX-ACCESS      read-only
        STATUS          current
        DESCRIPTION
                "Returns the MAC address of the card"
        ::= { adGenTa5kAtmLMConfigEntry 4 }

    adGenTa5kAtmLMConfigFPGARev OBJECT-TYPE
        SYNTAX          DisplayString
        MAX-ACCESS      read-only
        STATUS          current
        DESCRIPTION
                "Returns the FPGA revision"
        ::= { adGenTa5kAtmLMConfigEntry 5 }

    adGenTa5kAtmLMConfigCPLDRev OBJECT-TYPE
        SYNTAX          DisplayString
        MAX-ACCESS      read-only
        STATUS          current
        DESCRIPTION
                "Returns the CPLD Revision"
        ::= { adGenTa5kAtmLMConfigEntry 6 }

    adGenTa5kAtmLMConfigWDDIRev OBJECT-TYPE
        SYNTAX          DisplayString
        MAX-ACCESS      read-only
        STATUS          current
        DESCRIPTION
                "Resturns the WDDI revision"
        ::= { adGenTa5kAtmLMConfigEntry 7 }

    adGenTa5kAtmLMConfigDPSRev OBJECT-TYPE
        SYNTAX          DisplayString
        MAX-ACCESS      read-only
        STATUS          current
        DESCRIPTION
                "Returns the DPS revision"
        ::= { adGenTa5kAtmLMConfigEntry 8 }
		
-- *********************************************************************************************************
    adGenTa5kAtmPortProvisioningTable OBJECT-TYPE
        SYNTAX      SEQUENCE OF AdGenTa5kAtmPortProvisioningEntry
        MAX-ACCESS  not-accessible
        STATUS      current
        DESCRIPTION
                   "ATM Port Provisioning"
        ::= { adGenTa5kAtmLMProvisioning 1}

    adGenTa5kAtmPortProvisioningEntry OBJECT-TYPE
        SYNTAX  AdGenTa5kAtmPortProvisioningEntry
        MAX-ACCESS  not-accessible
        STATUS      current
        DESCRIPTION
                   "Table Entry"
        INDEX   { ifIndex}
        ::= { adGenTa5kAtmPortProvisioningTable 1 }

    AdGenTa5kAtmPortProvisioningEntry ::=
        SEQUENCE {
                        adGenTa5kAtmPortProvPortID         		DisplayString,
                        adGenTa5kAtmPortProvPortType       		INTEGER,
                        adGenTa5kAtmPortProvScrambler			INTEGER,
                        adGenTa5kAtmPortProvIdleCellType   		INTEGER,
                        adGenTa5kAtmPortProvMaxVccs        		Integer32,
                        adGenTa5kAtmPortProvAISRDIGen      		INTEGER,
                        adGenTa5kAtmPortProvInterfaceMode  		INTEGER,
      			     adGenTa5kAtmPortProvDhcpCircuitIdFormat DisplayString,
                        adGenTa5kAtmPortProvShapingUBR            INTEGER
                 }

    adGenTa5kAtmPortProvPortID OBJECT-TYPE
        SYNTAX          DisplayString
        MAX-ACCESS      read-write
        STATUS          current
        DESCRIPTION
                "used to set ID of the ATM Port"
        ::= { adGenTa5kAtmPortProvisioningEntry 1 }

    adGenTa5kAtmPortProvPortType OBJECT-TYPE
        SYNTAX          INTEGER {
                                        uni(1),
                                        nni(2)
                                }
        MAX-ACCESS      read-write
        STATUS          current
        DESCRIPTION
                "UNI/NNI provisioning"
        ::= { adGenTa5kAtmPortProvisioningEntry 2 }

    adGenTa5kAtmPortProvScrambler OBJECT-TYPE
        SYNTAX          INTEGER {
                                        enable(1),
                                        disable(2)
                                }
        MAX-ACCESS      read-write
        STATUS          current
        DESCRIPTION
                "used to enable/disable cell scrambling on an ATM Port"
        ::= { adGenTa5kAtmPortProvisioningEntry 3 }

    adGenTa5kAtmPortProvIdleCellType OBJECT-TYPE
        SYNTAX          INTEGER  {
                                        bellcore(1),
                                        itu(2)
                                  }

        MAX-ACCESS      read-write
        STATUS          current
        DESCRIPTION
                "used to set the idle cell type on an ATM port"
        ::= { adGenTa5kAtmPortProvisioningEntry 4 }

    adGenTa5kAtmPortProvMaxVccs OBJECT-TYPE
        SYNTAX          Integer32
        MAX-ACCESS      read-write
        STATUS          current
        DESCRIPTION
                "Maximum Vccs Allowed on this port"
        ::= { adGenTa5kAtmPortProvisioningEntry 5 }

    adGenTa5kAtmPortProvAISRDIGen OBJECT-TYPE
        SYNTAX          INTEGER {
                                        enable(1),
                                        disable(2)
                                }
        MAX-ACCESS      read-write
        STATUS          current
        DESCRIPTION
                "used to enable/disable AIS/RDI generation"
        ::= { adGenTa5kAtmPortProvisioningEntry 6 }

    adGenTa5kAtmPortProvInterfaceMode OBJECT-TYPE
        SYNTAX          INTEGER {
                                        uplink(1),
                                        aggregation(2)
                                }
        MAX-ACCESS      read-write
        STATUS          current
        DESCRIPTION
                "Indicates if this interface is used for uplink or aggregation"
        ::= { adGenTa5kAtmPortProvisioningEntry 7 }      

	adGenTa5kAtmPortProvDhcpCircuitIdFormat OBJECT-TYPE
       SYNTAX          DisplayString (SIZE (0..63))
       MAX-ACCESS      read-write
       STATUS          current
       DESCRIPTION
           "Used to provision the format of the circuit ID string. This string is used 
            to provision DHCP Option 82 sub-option 1 cirduit id that will be added to 
            the DHCP messages.
            TR-101 states that the format of the circuit ID 
            should be user defineable. The string may contain both fixed 
            static string elements specified by the user and also variable 
            and fixed length elements which are populated by the network 
            element. Variable length elements are specified by enclosing 
            the names of the variables with a dollar sign '$'. For instance, 
            a user could specify a circuit id string as follows:
            'TA1148-$accessnodeid$ Port: $port$ $vpi$/$vci$'

            which would expand to
            'TA1148-TID Port: 1 0/35'.

            In this implementation, the access-node-id is equivalent to the
            system's provisioned TID or SNMP sysName. If this string is
            provisioned zero-length, then the default format is used.
            The total length of the expanded string MUST NOT exceed
            63 characters.

            Variables include (but are not limited to) the following:
                Variable Name               Character Length
                accessnodeid                Varies
                slot                        3
                port                        3
                vpi                         4
                vci                         5

            If a user defined circuit ID is not desired, this object can
            be set to simply 'default' and the default format described in
            TR-101 will be used:

            access-node-id atm slot/port:vpi.vci"
         ::= { adGenTa5kAtmPortProvisioningEntry 8}                        
    
    adGenTa5kAtmPortProvShapingUBR OBJECT-TYPE
        SYNTAX          INTEGER {
                                        enable(1),
                                        disable(2)
                                }
        MAX-ACCESS      read-write
        STATUS          current
        DESCRIPTION
                "Indicates if this interface activates ubr shaping"
        DEFVAL  { disable }
        ::= { adGenTa5kAtmPortProvisioningEntry 9 }      


-- *********************************************************************************************************

    adGenTa5kManagementChannelTable OBJECT-TYPE
        SYNTAX      SEQUENCE OF AdGenTa5kManagementChannelEntry
        MAX-ACCESS  not-accessible
        STATUS      current
        DESCRIPTION
                   "Management Provisioning"
        ::= { adGenTa5kAtmLMProvisioning 2 }

    adGenTa5kManagementChannelEntry OBJECT-TYPE
        SYNTAX  AdGenTa5kManagementChannelEntry
        MAX-ACCESS  not-accessible
        STATUS      current
        DESCRIPTION
                   "Table Entry"
        INDEX   { adGenSlotInfoIndex}
        ::= { adGenTa5kManagementChannelTable 1 }

    AdGenTa5kManagementChannelEntry ::=
        SEQUENCE {

                        adGenTa5kManagementChannelVpi       INTEGER,
                        adGenTa5kManagementChannelVci       INTEGER,
                        adGenTa5kManagementChannelMode      INTEGER,
                        adGenTa5kManagementChannelEncap     INTEGER,
                        adGenTa5kManagementChannelMultiplex INTEGER,
                        adGenTa5kManagementChannelEnable    INTEGER,
                        adGenTa5kManagementChannelPort      Integer32
                 }

    adGenTa5kManagementChannelVpi OBJECT-TYPE
        SYNTAX          INTEGER (1..4095)
        MAX-ACCESS      read-write
        STATUS          current
        DESCRIPTION
                "Vpi of the management channel"
        ::= { adGenTa5kManagementChannelEntry 1 }

    adGenTa5kManagementChannelVci OBJECT-TYPE
        SYNTAX          INTEGER (1..4095)
        MAX-ACCESS      read-write
        STATUS          current
        DESCRIPTION
                "Vci of the management channel"
        ::= { adGenTa5kManagementChannelEntry 2 }

    adGenTa5kManagementChannelMode OBJECT-TYPE
        SYNTAX          INTEGER {
                                        routed(1)
                                }
        MAX-ACCESS      read-write
        STATUS          current
        DESCRIPTION
                "used to set the mode of the management channel"
        ::= { adGenTa5kManagementChannelEntry 3 }

    adGenTa5kManagementChannelEncap OBJECT-TYPE
        SYNTAX          INTEGER {
                                        vcMultiplexRoutedProtocol(1),
                                        vcMultiplexBridgedProtocol8023(2),
                                        vcMultiplexBridgedProtocol8025(3),
                                        vcMultiplexBridgedProtocol8026(4),
                                        vcMultiplexLANemulation8023(5),
                                        vcMultiplexLANemulation8025(6),
                                        llcEncapsulation(7),
                                        multiprotocolFrameRelaySscs(8),
                                        other(9),
                                        unknown(10)
                                }
        MAX-ACCESS      read-write
        STATUS          current
        DESCRIPTION
                "used to set the encapsulation type of the management channel"
        ::= { adGenTa5kManagementChannelEntry 4 }

    adGenTa5kManagementChannelMultiplex OBJECT-TYPE
        SYNTAX          INTEGER {
                                        llc(1)
                                }
        MAX-ACCESS      read-write
        STATUS          current
        DESCRIPTION
                ""
        ::= { adGenTa5kManagementChannelEntry 5 }

    adGenTa5kManagementChannelEnable OBJECT-TYPE
        SYNTAX          INTEGER {
                                        enable(1),
                                        disable(2)
                                }
        MAX-ACCESS      read-write
        STATUS          current
        DESCRIPTION
                "used to enable/disable the management channel"
        ::= { adGenTa5kManagementChannelEntry 6 }

    adGenTa5kManagementChannelPort OBJECT-TYPE
        SYNTAX          Integer32
        MAX-ACCESS      read-write
        STATUS          current
        DESCRIPTION
                "used to set which port is the management channel"
        ::= { adGenTa5kManagementChannelEntry 7 }

-- *********************************************************************************************************
    adGenTa5kAtmLMSWUploadTable OBJECT-TYPE
        SYNTAX      SEQUENCE OF AdGenTa5kAtmLMSWUploadEntry
        MAX-ACCESS  not-accessible
        STATUS      current
        DESCRIPTION
                   "Software Upload"
        ::= { adGenTa5kAtmLMProvisioning 3}

    adGenTa5kAtmLMSWUploadEntry OBJECT-TYPE
        SYNTAX  AdGenTa5kAtmLMSWUploadEntry
        MAX-ACCESS  not-accessible
        STATUS      current
        DESCRIPTION
                   "Table Entry"
        INDEX   { adGenSlotInfoIndex}
        ::= { adGenTa5kAtmLMSWUploadTable 1 }

    AdGenTa5kAtmLMSWUploadEntry ::=
        SEQUENCE {
                         adGenTa5kAtmLMReboot                   Integer32
                 }

    adGenTa5kAtmLMReboot OBJECT-TYPE
        SYNTAX          Integer32
        MAX-ACCESS      read-write
        STATUS          current
        DESCRIPTION
                "used to reboot the card"
        ::= { adGenTa5kAtmLMSWUploadEntry 1 }

-- *********************************************************************************************************
    adGenTa5kAtmLMCardProvTable OBJECT-TYPE
        SYNTAX      SEQUENCE OF AdGenTa5kAtmLMCardProvEntry
        MAX-ACCESS  not-accessible
        STATUS      current
        DESCRIPTION
                   "Card Level Provisioning"
        ::= { adGenTa5kAtmLMProvisioning 4}

    adGenTa5kAtmLMCardProvEntry OBJECT-TYPE
        SYNTAX  AdGenTa5kAtmLMCardProvEntry
        MAX-ACCESS  not-accessible
        STATUS      current
        DESCRIPTION
                   "Table Entry"
        INDEX   { adGenSlotInfoIndex}
        ::= { adGenTa5kAtmLMCardProvTable 1 }

    AdGenTa5kAtmLMCardProvEntry ::=
        SEQUENCE {
                         adGenTa5kAtmLMCardProvLearningMode                 INTEGER,
                         adGenTa5kAtmLMCardVclLearnedCount         			Integer32,
						 adGenTa5kAtmLMCardCurrentOAMID						OCTET STRING,
						 adGenTa5kAtmLMCardFutureOAMID                      OCTET STRING,
						 adGenTa5kAtmLMCardResetDHCPPMStats                 INTEGER,
						 adGenTa5kAtmLMCardResetDHCPRollingCounters         INTEGER
				 }
    adGenTa5kAtmLMCardProvLearningMode OBJECT-TYPE
        SYNTAX          INTEGER  {
                                        enable(1),
                                        disable(2)
                                }
        MAX-ACCESS      read-write
        STATUS          current
        DESCRIPTION
                "Learning Mode"
        ::= { adGenTa5kAtmLMCardProvEntry 1 }
        
   adGenTa5kAtmLMCardVclLearnedCount OBJECT-TYPE
        SYNTAX          Integer32
        MAX-ACCESS      read-only
        STATUS          current
        DESCRIPTION
                "returns the number of VCLs learned"
        ::= { adGenTa5kAtmLMCardProvEntry 2 }
		
   adGenTa5kAtmLMCardCurrentOAMID OBJECT-TYPE
        SYNTAX          OCTET STRING (SIZE(16))
        MAX-ACCESS      read-only
        STATUS          current
        DESCRIPTION
        "Card Level OAM Identification that is currently used"
        ::= { adGenTa5kAtmLMCardProvEntry 3 }
        
   adGenTa5kAtmLMCardFutureOAMID OBJECT-TYPE
        SYNTAX          OCTET STRING (SIZE(16))
        MAX-ACCESS      read-write
        STATUS          current
        DESCRIPTION
        "The  object is used to set the OAM ID for the specified access module.  
        Some access modules must be restarted in order for the new OAM ID to take effect.  
        To determine if a reboot is required, retrieve both the adGenTa5kAtmLMCardFutureOAMID  
        and the adGenTa5kAtmLMCardCurrentOAMID after a successful set and compare the returned 
        values.  If the values are different, the access module will have to be rebooted for the 
        OAM ID to take effect.   If the values are equivalent, the OAM ID took effect immediately
        and no reboot is required"
        ::= { adGenTa5kAtmLMCardProvEntry 4 }   
        
  adGenTa5kAtmLMCardResetDHCPPMStats OBJECT-TYPE
        SYNTAX  INTEGER { reset(1) }
        MAX-ACCESS      read-write
        STATUS          current
        DESCRIPTION
                "A set will reset all dhcp card level pm stats"
        ::= { adGenTa5kAtmLMCardProvEntry 5 }

  adGenTa5kAtmLMCardResetDHCPRollingCounters OBJECT-TYPE
        SYNTAX  INTEGER { reset(1) }
        MAX-ACCESS      read-write
        STATUS          current
        DESCRIPTION
                "A set will reset all dhcp card level rolling
                 counters"
        ::= { adGenTa5kAtmLMCardProvEntry 6 }

-- *********************************************************************************************************

    -- Loop Timing Table
    adGenTa5kAtmLMLoopTimingTable OBJECT-TYPE
        SYNTAX  SEQUENCE OF AdGenTa5kAtmLMLoopTimingEntry
        MAX-ACCESS  not-accessible
        STATUS      current
        DESCRIPTION
            "Table to set the Loop A and B timing used to provided timing
                to the shelf"
        ::= { adGenTa5kAtmLMProvisioning 5 }

     adGenTa5kAtmLMLoopTimingEntry OBJECT-TYPE
        SYNTAX  AdGenTa5kAtmLMLoopTimingEntry
        MAX-ACCESS  not-accessible
        STATUS      current
        DESCRIPTION
                   ""
        INDEX   { adGenSlotInfoIndex }
        ::= { adGenTa5kAtmLMLoopTimingTable 1 }

    AdGenTa5kAtmLMLoopTimingEntry ::=
        SEQUENCE {
           adGenTa5kAtmLMLoopTimingA    INTEGER,
           adGenTa5kAtmLMLoopTimingB    INTEGER
        }

    adGenTa5kAtmLMLoopTimingA OBJECT-TYPE
        SYNTAX  INTEGER {
                                loop1(1),
                                loop2(2),
                                loop3(3),
                                loop4(4),
                                loop5(5),
                                loop6(6),
                                loop7(7),
                                loop8(8),
                                loop9(9),
                                loop10(10),
                                loop11(11),
                                loop12(12),
                                loop13(13),
                                loop14(14),
                                loop15(15),
                                loop16(16),
                                loop17(17),
                                loop18(18),
                                loop19(19),
                                loop20(20),
                                loop21(21),
                                loop22(22),
                                loop23(23),
                                loop24(24),
                                loop25(25),
                                loop26(26),
                                loop27(27),
                                loop28(28),
                                loop29(29),
                                loop30(30),
                                loop31(31),
                                loop32(32),
                                none(255)
                        }
        MAX-ACCESS  read-write
        STATUS      current
        DESCRIPTION
            "LoopA Timing Source."
        ::= { adGenTa5kAtmLMLoopTimingEntry 1 }

    adGenTa5kAtmLMLoopTimingB OBJECT-TYPE
        SYNTAX  INTEGER {
                                loop1(1),
                                loop2(2),
                                loop3(3),
                                loop4(4),
                                loop5(5),
                                loop6(6),
                                loop7(7),
                                loop8(8),
                                loop9(9),
                                loop10(10),
                                loop11(11),
                                loop12(12),
                                loop13(13),
                                loop14(14),
                                loop15(15),
                                loop16(16),
                                loop17(17),
                                loop18(18),
                                loop19(19),
                                loop20(20),
                                loop21(21),
                                loop22(22),
                                loop23(23),
                                loop24(24),
                                loop25(25),
                                loop26(26),
                                loop27(27),
                                loop28(28),
                                loop29(29),
                                loop30(30),
                                loop31(31),
                                loop32(32),
                                none(255)
                        }
        MAX-ACCESS  read-write
        STATUS      current
        DESCRIPTION
            "LoopB Timing Source."
        ::= { adGenTa5kAtmLMLoopTimingEntry 2 }

-- *********************************************************************************************************
-- *********************************************************************************************************
    adGenTa5kAtmPortStatsCurrentTable OBJECT-TYPE
        SYNTAX      SEQUENCE OF AdGenTa5kAtmPortStatsCurrentEntry
        MAX-ACCESS  not-accessible
        STATUS      current
        DESCRIPTION
                   "ATM Port Stats Current"
        ::= { adGenTa5kAtmLMPMStats 1 }

    adGenTa5kAtmPortStatsCurrentEntry OBJECT-TYPE
        SYNTAX  AdGenTa5kAtmPortStatsCurrentEntry
        MAX-ACCESS  not-accessible
        STATUS      current
        DESCRIPTION
                   "Table Entry"
        INDEX   { ifIndex }
        ::= { adGenTa5kAtmPortStatsCurrentTable 1 }

    AdGenTa5kAtmPortStatsCurrentEntry ::=
        SEQUENCE {
                        adGenTa5kAtmPortStatsCurrentRxCells             Counter32,
                        adGenTa5kAtmPortStatsCurrentRxClp1Cells         Counter32,
                        adGenTa5kAtmPortStatsCurrentRxClp0Cells         Counter32,
                        adGenTa5kAtmPortStatsCurrentRxOamCells          Counter32,
                        adGenTa5kAtmPortStatsCurrentTxCells             Counter32,
                        adGenTa5kAtmPortStatsCurrentTxClp1Cells         Counter32,
                        adGenTa5kAtmPortStatsCurrentTxClp0Cells         Counter32,
                        adGenTa5kAtmPortStatsCurrentTxOamCells          Counter32,
                        adGenTa5kAtmPortStatsCurrentResetStats          Integer32,
                        adGenTa5kAtmPortStatsCurrentRxCellsPercentUtil  Gauge32,                        
                        adGenTa5kAtmPortStatsCurrentTxCellsPercentUtil  Gauge32
                 }

    adGenTa5kAtmPortStatsCurrentRxCells OBJECT-TYPE
        SYNTAX          Counter32
        MAX-ACCESS      read-only
        STATUS          current
        DESCRIPTION
                "Current counter for RX cells"
        ::= { adGenTa5kAtmPortStatsCurrentEntry 1 }

    adGenTa5kAtmPortStatsCurrentRxClp1Cells OBJECT-TYPE
        SYNTAX          Counter32
        MAX-ACCESS      read-only
        STATUS          current
        DESCRIPTION
                "Current counter for RX CLP1 cells"
        ::= { adGenTa5kAtmPortStatsCurrentEntry 2 }

    adGenTa5kAtmPortStatsCurrentRxClp0Cells OBJECT-TYPE
        SYNTAX          Counter32
        MAX-ACCESS      read-only
        STATUS          current
        DESCRIPTION
                "Current counter for RX CLP0 cells"
        ::= { adGenTa5kAtmPortStatsCurrentEntry 3 }

    adGenTa5kAtmPortStatsCurrentRxOamCells OBJECT-TYPE
        SYNTAX          Counter32
        MAX-ACCESS      read-only
        STATUS          current
        DESCRIPTION
                "Current counter for RX OAM cells"
        ::= { adGenTa5kAtmPortStatsCurrentEntry 4 }

    adGenTa5kAtmPortStatsCurrentTxCells OBJECT-TYPE
        SYNTAX          Counter32
        MAX-ACCESS      read-only
        STATUS          current
        DESCRIPTION
                "Current counter for TX cells"
        ::= { adGenTa5kAtmPortStatsCurrentEntry 5 }

    adGenTa5kAtmPortStatsCurrentTxClp1Cells OBJECT-TYPE
        SYNTAX          Counter32
        MAX-ACCESS      read-only
        STATUS          current
        DESCRIPTION
                "Current counter for TX CLP1 cells"
        ::= { adGenTa5kAtmPortStatsCurrentEntry 6 }

    adGenTa5kAtmPortStatsCurrentTxClp0Cells OBJECT-TYPE
        SYNTAX          Counter32
        MAX-ACCESS      read-only
        STATUS          current
        DESCRIPTION
                "Current counter for TX CLP0 cells"
        ::= { adGenTa5kAtmPortStatsCurrentEntry 7 }

    adGenTa5kAtmPortStatsCurrentTxOamCells OBJECT-TYPE
        SYNTAX          Counter32
        MAX-ACCESS      read-only
        STATUS          current
        DESCRIPTION
                "Current counter for TX OAM cells"
        ::= { adGenTa5kAtmPortStatsCurrentEntry 8 }

    adGenTa5kAtmPortStatsCurrentResetStats OBJECT-TYPE
        SYNTAX          Integer32
        MAX-ACCESS      read-write
        STATUS          current
        DESCRIPTION
                "A Set will reset all stats on interface "
        ::= { adGenTa5kAtmPortStatsCurrentEntry 9 }

    adGenTa5kAtmPortStatsCurrentRxCellsPercentUtil OBJECT-TYPE
        SYNTAX          Gauge32
        MAX-ACCESS      read-only
        STATUS          current
        DESCRIPTION
                "Current percentage Utilization on the Rx links 
                 (Divide by hundred to get the actual percentage value). "
        ::= { adGenTa5kAtmPortStatsCurrentEntry 10 }

    adGenTa5kAtmPortStatsCurrentTxCellsPercentUtil OBJECT-TYPE
        SYNTAX          Gauge32
        MAX-ACCESS      read-only
        STATUS          current
        DESCRIPTION
                "Current percentage Utilization on the Tx links                 
                 (Divide by hundred to get the actual percentage value). "
        ::= { adGenTa5kAtmPortStatsCurrentEntry 11 }

-- *********************************************************************************************************

    adGenTa5kAtmPortStatsIntervalTable OBJECT-TYPE
        SYNTAX      SEQUENCE OF AdGenTa5kAtmPortStatsIntervalEntry
        MAX-ACCESS  not-accessible
        STATUS      current
        DESCRIPTION
                   "ATM Port Interval Stats"
        ::= { adGenTa5kAtmLMPMStats 2 }

    adGenTa5kAtmPortStatsIntervalEntry OBJECT-TYPE
        SYNTAX  AdGenTa5kAtmPortStatsIntervalEntry
        MAX-ACCESS  not-accessible
        STATUS      current
        DESCRIPTION
                   "Table Entry"
        INDEX   { ifIndex, adGenTa5kAtmPortStatsIntervalIndex}
        ::= { adGenTa5kAtmPortStatsIntervalTable 1 }

    AdGenTa5kAtmPortStatsIntervalEntry ::=
        SEQUENCE {
                        adGenTa5kAtmPortStatsIntervalIndex                Integer32,
                        adGenTa5kAtmPortStatsIntervalRxCells              Counter32,
                        adGenTa5kAtmPortStatsIntervalRxClp1Cells          Counter32,
                        adGenTa5kAtmPortStatsIntervalRxClp0Cells          Counter32,
                        adGenTa5kAtmPortStatsIntervalRxOamCells           Counter32,
                        adGenTa5kAtmPortStatsIntervalTxCells              Counter32,
                        adGenTa5kAtmPortStatsIntervalTxClp1Cells          Counter32,
                        adGenTa5kAtmPortStatsIntervalTxClp0Cells          Counter32,
                        adGenTa5kAtmPortStatsIntervalTxOamCells           Counter32,
                        adGenTa5kAtmPortStatsIntervalTimeStamp            DisplayString,
                        adGenTa5kAtmPortStatsIntervalRxCellsPercentUtil   Gauge32,                        
                        adGenTa5kAtmPortStatsIntervalTxCellsPercentUtil   Gauge32                        
                }

    adGenTa5kAtmPortStatsIntervalIndex OBJECT-TYPE
        SYNTAX          Integer32
        MAX-ACCESS      not-accessible
        STATUS          current
        DESCRIPTION
                "Index of the 15-minute interval"
        ::= { adGenTa5kAtmPortStatsIntervalEntry 1 }

    adGenTa5kAtmPortStatsIntervalRxCells OBJECT-TYPE
        SYNTAX          Counter32
        MAX-ACCESS      read-only
        STATUS          current
        DESCRIPTION
                "Rx Cells in 15-minute interval"
        ::= { adGenTa5kAtmPortStatsIntervalEntry 2 }

    adGenTa5kAtmPortStatsIntervalRxClp1Cells OBJECT-TYPE
        SYNTAX          Counter32
        MAX-ACCESS      read-only
        STATUS          current
        DESCRIPTION
                "Rx Clp1 Cells in 15-minute interval"
        ::= { adGenTa5kAtmPortStatsIntervalEntry 3 }

    adGenTa5kAtmPortStatsIntervalRxClp0Cells OBJECT-TYPE
        SYNTAX          Counter32
        MAX-ACCESS      read-only
        STATUS          current
        DESCRIPTION
                "Rx Clp0 Cells in 15-minute interval"
        ::= { adGenTa5kAtmPortStatsIntervalEntry 4 }

    adGenTa5kAtmPortStatsIntervalRxOamCells OBJECT-TYPE
        SYNTAX          Counter32
        MAX-ACCESS      read-only
        STATUS          current
        DESCRIPTION
                "Rx OAM Cells in 15-minute interval"
        ::= { adGenTa5kAtmPortStatsIntervalEntry 5 }

    adGenTa5kAtmPortStatsIntervalTxCells OBJECT-TYPE
        SYNTAX          Counter32
        MAX-ACCESS      read-only
        STATUS          current
        DESCRIPTION
                "Tx Cells in 15-minute interval"
        ::= { adGenTa5kAtmPortStatsIntervalEntry 6 }

    adGenTa5kAtmPortStatsIntervalTxClp1Cells OBJECT-TYPE
        SYNTAX          Counter32
        MAX-ACCESS      read-only
        STATUS          current
        DESCRIPTION
                "Tx Clp1 Cells in 15-minute interval"
        ::= { adGenTa5kAtmPortStatsIntervalEntry 7 }

    adGenTa5kAtmPortStatsIntervalTxClp0Cells OBJECT-TYPE
        SYNTAX          Counter32
        MAX-ACCESS      read-only
        STATUS          current
        DESCRIPTION
                "Tx Clp0 Cells in 15-minute interval"
        ::= { adGenTa5kAtmPortStatsIntervalEntry 8 }

    adGenTa5kAtmPortStatsIntervalTxOamCells OBJECT-TYPE
        SYNTAX          Counter32
        MAX-ACCESS      read-only
        STATUS          current
        DESCRIPTION
                "Tx OAM Cells in 15-minute interval"
        ::= { adGenTa5kAtmPortStatsIntervalEntry 9 }

    adGenTa5kAtmPortStatsIntervalTimeStamp OBJECT-TYPE
        SYNTAX          DisplayString
        MAX-ACCESS      read-only
        STATUS          current
        DESCRIPTION
                "Timestamp of the 15-minute interval"
        ::= { adGenTa5kAtmPortStatsIntervalEntry 10 }

    adGenTa5kAtmPortStatsIntervalRxCellsPercentUtil OBJECT-TYPE
        SYNTAX          Gauge32
        MAX-ACCESS      read-only
        STATUS          current
        DESCRIPTION
                "Percentage Utilization for the 15 min interval on the Rx links 
                 (Divide by hundred to get the actual percentage value). "
        ::= { adGenTa5kAtmPortStatsIntervalEntry 11 }

    adGenTa5kAtmPortStatsIntervalTxCellsPercentUtil OBJECT-TYPE
        SYNTAX          Gauge32
        MAX-ACCESS      read-only
        STATUS          current
        DESCRIPTION
                "Percentage Utilization for the 15 min interval on the Tx links 
                 (Divide by hundred to get the actual percentage value). "
        ::= { adGenTa5kAtmPortStatsIntervalEntry 12 }
        

-- *********************************************************************************************************

    adGenTa5kAtmPortStats24hrCurrentTable OBJECT-TYPE
        SYNTAX      SEQUENCE OF AdGenTa5kAtmPortStats24hrCurrentEntry
        MAX-ACCESS  not-accessible
        STATUS      current
        DESCRIPTION
                   "ATM Port 24hr Current Stats"
        ::= { adGenTa5kAtmLMPMStats 3 }

    adGenTa5kAtmPortStats24hrCurrentEntry OBJECT-TYPE
        SYNTAX  AdGenTa5kAtmPortStats24hrCurrentEntry
        MAX-ACCESS  not-accessible
        STATUS      current
        DESCRIPTION
                   "Table Entry"
        INDEX   { ifIndex}
        ::= { adGenTa5kAtmPortStats24hrCurrentTable 1 }

    AdGenTa5kAtmPortStats24hrCurrentEntry ::=
        SEQUENCE {
                        adGenTa5kAtmPortStats24hrCurrentRxCells            Counter32,
                        adGenTa5kAtmPortStats24hrCurrentRxClp1Cells        Counter32,
                        adGenTa5kAtmPortStats24hrCurrentRxClp0Cells        Counter32,
                        adGenTa5kAtmPortStats24hrCurrentRxOamCells         Counter32,
                        adGenTa5kAtmPortStats24hrCurrentTxCells            Counter32,
                        adGenTa5kAtmPortStats24hrCurrentTxClp1Cells        Counter32,
                        adGenTa5kAtmPortStats24hrCurrentTxClp0Cells        Counter32,
                        adGenTa5kAtmPortStats24hrCurrentTxOamCells         Counter32
                }


    adGenTa5kAtmPortStats24hrCurrentRxCells OBJECT-TYPE
        SYNTAX          Counter32
        MAX-ACCESS      read-only
        STATUS          current
        DESCRIPTION
                "Rx Cells in the current 24 hour period"
        ::= { adGenTa5kAtmPortStats24hrCurrentEntry 1 }

    adGenTa5kAtmPortStats24hrCurrentRxClp1Cells OBJECT-TYPE
        SYNTAX          Counter32
        MAX-ACCESS      read-only
        STATUS          current
        DESCRIPTION
                "Rx Clp1 Cells in the current 24 hour period"
        ::= { adGenTa5kAtmPortStats24hrCurrentEntry 2 }

    adGenTa5kAtmPortStats24hrCurrentRxClp0Cells OBJECT-TYPE
        SYNTAX          Counter32
        MAX-ACCESS      read-only
        STATUS          current
        DESCRIPTION
                "Rx Clp0 Cells the current 24 hour period"
        ::= { adGenTa5kAtmPortStats24hrCurrentEntry 3 }

    adGenTa5kAtmPortStats24hrCurrentRxOamCells OBJECT-TYPE
        SYNTAX          Counter32
        MAX-ACCESS      read-only
        STATUS          current
        DESCRIPTION
                "Rx OAM Cells in the current 24 hour period"
        ::= { adGenTa5kAtmPortStats24hrCurrentEntry 4 }

    adGenTa5kAtmPortStats24hrCurrentTxCells OBJECT-TYPE
        SYNTAX          Counter32
        MAX-ACCESS      read-only
        STATUS          current
        DESCRIPTION
                "Tx Cells in the current 24 hour period"
        ::= { adGenTa5kAtmPortStats24hrCurrentEntry 5 }

    adGenTa5kAtmPortStats24hrCurrentTxClp1Cells OBJECT-TYPE
        SYNTAX          Counter32
        MAX-ACCESS      read-only
        STATUS          current
        DESCRIPTION
                "Tx Clp1 Cells in the current 24 hour period"
        ::= { adGenTa5kAtmPortStats24hrCurrentEntry 6 }

    adGenTa5kAtmPortStats24hrCurrentTxClp0Cells OBJECT-TYPE
        SYNTAX          Counter32
        MAX-ACCESS      read-only
        STATUS          current
        DESCRIPTION
                "Tx Clp0 Cells in the current 24 hour period"
        ::= { adGenTa5kAtmPortStats24hrCurrentEntry 7 }

    adGenTa5kAtmPortStats24hrCurrentTxOamCells OBJECT-TYPE
        SYNTAX          Counter32
        MAX-ACCESS      read-only
        STATUS          current
        DESCRIPTION
                "Tx OAM Cells in the current 24 hour period"
        ::= { adGenTa5kAtmPortStats24hrCurrentEntry 8 }


-- *********************************************************************************************************

    adGenTa5kAtmPortStats24hrTable OBJECT-TYPE
        SYNTAX      SEQUENCE OF AdGenTa5kAtmPortStats24hrEntry
        MAX-ACCESS  not-accessible
        STATUS      current
        DESCRIPTION
                   "ATM Port 24hr Stats"
        ::= { adGenTa5kAtmLMPMStats 4 }

    adGenTa5kAtmPortStats24hrEntry OBJECT-TYPE
        SYNTAX  AdGenTa5kAtmPortStats24hrEntry
        MAX-ACCESS  not-accessible
        STATUS      current
        DESCRIPTION
                   "Table Entry"
        INDEX   { ifIndex, adGenTa5kAtmPortStats24hrIndex}
        ::= { adGenTa5kAtmPortStats24hrTable 1 }

    AdGenTa5kAtmPortStats24hrEntry ::=
        SEQUENCE {
                        adGenTa5kAtmPortStats24hrIndex              Integer32,
                        adGenTa5kAtmPortStats24hrRxCells            Counter32,
                        adGenTa5kAtmPortStats24hrRxClp1Cells        Counter32,
                        adGenTa5kAtmPortStats24hrRxClp0Cells        Counter32,
                        adGenTa5kAtmPortStats24hrRxOamCells         Counter32,
                        adGenTa5kAtmPortStats24hrTxCells            Counter32,
                        adGenTa5kAtmPortStats24hrTxClp1Cells        Counter32,
                        adGenTa5kAtmPortStats24hrTxClp0Cells        Counter32,
                        adGenTa5kAtmPortStats24hrTxOamCells         Counter32,
                        adGenTa5kAtmPortStats24hrTimeStamp          DisplayString
                }

    adGenTa5kAtmPortStats24hrIndex OBJECT-TYPE
        SYNTAX          Integer32
        MAX-ACCESS      not-accessible
        STATUS          current
        DESCRIPTION
                "Index of the 24 hour period"
        ::= { adGenTa5kAtmPortStats24hrEntry 1 }

    adGenTa5kAtmPortStats24hrRxCells OBJECT-TYPE
        SYNTAX          Counter32
        MAX-ACCESS      read-only
        STATUS          current
        DESCRIPTION
                "Rx Cells in a 24 hour period"
        ::= { adGenTa5kAtmPortStats24hrEntry 2 }

    adGenTa5kAtmPortStats24hrRxClp1Cells OBJECT-TYPE
        SYNTAX          Counter32
        MAX-ACCESS      read-only
        STATUS          current
        DESCRIPTION
                "Rx Clp1 Cells in a 24 hour period"
        ::= { adGenTa5kAtmPortStats24hrEntry 3 }

    adGenTa5kAtmPortStats24hrRxClp0Cells OBJECT-TYPE
        SYNTAX          Counter32
        MAX-ACCESS      read-only
        STATUS          current
        DESCRIPTION
                "Rx Clp0 Cells a 24 hour period"
        ::= { adGenTa5kAtmPortStats24hrEntry 4 }

    adGenTa5kAtmPortStats24hrRxOamCells OBJECT-TYPE
        SYNTAX          Counter32
        MAX-ACCESS      read-only
        STATUS          current
        DESCRIPTION
                "Rx OAM Cells in a 24 hour period"
        ::= { adGenTa5kAtmPortStats24hrEntry 5 }

    adGenTa5kAtmPortStats24hrTxCells OBJECT-TYPE
        SYNTAX          Counter32
        MAX-ACCESS      read-only
        STATUS          current
        DESCRIPTION
                "Tx Cells in a 24 hour period"
        ::= { adGenTa5kAtmPortStats24hrEntry 6 }

    adGenTa5kAtmPortStats24hrTxClp1Cells OBJECT-TYPE
        SYNTAX          Counter32
        MAX-ACCESS      read-only
        STATUS          current
        DESCRIPTION
                "Tx Clp1 Cells in a 24 hour period"
        ::= { adGenTa5kAtmPortStats24hrEntry 7 }

    adGenTa5kAtmPortStats24hrTxClp0Cells OBJECT-TYPE
        SYNTAX          Counter32
        MAX-ACCESS      read-only
        STATUS          current
        DESCRIPTION
                "Tx Clp0 Cells in a 24 hour period"
        ::= { adGenTa5kAtmPortStats24hrEntry 8 }

    adGenTa5kAtmPortStats24hrTxOamCells OBJECT-TYPE
        SYNTAX          Counter32
        MAX-ACCESS      read-only
        STATUS          current
        DESCRIPTION
                "Tx OAM Cells in a 24 hour period"
        ::= { adGenTa5kAtmPortStats24hrEntry 9 }

    adGenTa5kAtmPortStats24hrTimeStamp OBJECT-TYPE
        SYNTAX          DisplayString
        MAX-ACCESS      read-only
        STATUS          current
        DESCRIPTION
                "Timestamp of 24 hour period (Date)"
        ::= { adGenTa5kAtmPortStats24hrEntry 10 }

-- *********************************************************************************************************

    adGenTa5kAtmVclStatsTable OBJECT-TYPE
        SYNTAX      SEQUENCE OF AdGenTa5kAtmVclStatsEntry
        MAX-ACCESS  not-accessible
        STATUS      current
        DESCRIPTION
                   "ATM Vcl Stats"
        ::= { adGenTa5kAtmLMPMStats 5 }

    adGenTa5kAtmVclStatsEntry OBJECT-TYPE
        SYNTAX  AdGenTa5kAtmVclStatsEntry
        MAX-ACCESS  not-accessible
        STATUS      current
        DESCRIPTION
                   "Table Entry"
        INDEX   { ifIndex, atmVclVpi, atmVclVci}
        ::= { adGenTa5kAtmVclStatsTable 1 }

    AdGenTa5kAtmVclStatsEntry ::=
        SEQUENCE {
                        adGenTa5kAtmVclStatsResetPM             Integer32,
                        adGenTa5kAtmVclStatsRxAIS               INTEGER,
                        adGenTa5kAtmVclStatsRxRDI               INTEGER,
                        adGenTa5kAtmVclStatsGenAISRDI           TruthValue,
                        adGenTa5kAtmVclStatsOamTxLbReqs         Integer32,
                        adGenTa5kAtmVclStatsOamRxLbReqs         Integer32,
                        adGenTa5kAtmVclStatsOamTxLbResps        Integer32,
                        adGenTa5kAtmVclStatsOamRxLbResps        Integer32,
                        adGenTa5kAtmVclStatsOamLbTimeouts       Integer32,
                        adGenTa5kAtmVclStatsOamLbLastResult     INTEGER,
                        adGenTa5kAtmVclStatsConnectionInfo      DisplayString
        }

    adGenTa5kAtmVclStatsResetPM OBJECT-TYPE
        SYNTAX          Integer32
        MAX-ACCESS      read-write
        STATUS          current
        DESCRIPTION
                "Reset Stats"
        ::= { adGenTa5kAtmVclStatsEntry 1 }

    adGenTa5kAtmVclStatsRxAIS OBJECT-TYPE
        SYNTAX  INTEGER {
                                true(1),
                                false(2),
                                na(3)
                        }
        MAX-ACCESS      read-only
        STATUS          current
        DESCRIPTION
                "True - indicates Rx AIS"
        ::= { adGenTa5kAtmVclStatsEntry 2 }

    adGenTa5kAtmVclStatsRxRDI OBJECT-TYPE
        SYNTAX  INTEGER {
                                true(1),
                                false(2),
                                na(3)
                        }
        MAX-ACCESS      read-only
        STATUS          current
        DESCRIPTION
                "True - indicates Rx RDI"
        ::= { adGenTa5kAtmVclStatsEntry 3 }

    adGenTa5kAtmVclStatsGenAISRDI OBJECT-TYPE
        SYNTAX          TruthValue
        MAX-ACCESS      read-only
        STATUS          current
        DESCRIPTION
                "True - indicates Vcl is generating AIS/RDI"
        ::= { adGenTa5kAtmVclStatsEntry 4 }

    adGenTa5kAtmVclStatsOamTxLbReqs OBJECT-TYPE
        SYNTAX          Integer32
        MAX-ACCESS      read-only
        STATUS          current
        DESCRIPTION
                "Number of transmitted F5 OAM Loopback Requests"
        ::= { adGenTa5kAtmVclStatsEntry 5 }

    adGenTa5kAtmVclStatsOamRxLbReqs OBJECT-TYPE
        SYNTAX          Integer32
        MAX-ACCESS      read-only
        STATUS          current
        DESCRIPTION
                "Number of received F5 OAM Loopback Requests"
        ::= { adGenTa5kAtmVclStatsEntry 6 }

    adGenTa5kAtmVclStatsOamTxLbResps OBJECT-TYPE
        SYNTAX          Integer32
        MAX-ACCESS      read-only
        STATUS          current
        DESCRIPTION
                "Number of transmitted F5 OAM Loopback Responses"
        ::= { adGenTa5kAtmVclStatsEntry 7 }

    adGenTa5kAtmVclStatsOamRxLbResps OBJECT-TYPE
        SYNTAX          Integer32
        MAX-ACCESS      read-only
        STATUS          current
        DESCRIPTION
                "Number of received F5 OAM Loopback Responses"
        ::= { adGenTa5kAtmVclStatsEntry 8 }

    adGenTa5kAtmVclStatsOamLbTimeouts OBJECT-TYPE
        SYNTAX          Integer32
        MAX-ACCESS      read-only
        STATUS          current
        DESCRIPTION
                "Number of transmitted F5 OAM Loopback Requests which timed out with no response"
        ::= { adGenTa5kAtmVclStatsEntry 9 }

    adGenTa5kAtmVclStatsOamLbLastResult OBJECT-TYPE
        SYNTAX          INTEGER {
                                    noneSent(0),
                                    cellOutstanding(1),
                                    responseReceived(2),
                                    timedOut(3)
                                }
        MAX-ACCESS      read-only
        STATUS          current
        DESCRIPTION
                "Result of the last loopback request"
        ::= { adGenTa5kAtmVclStatsEntry 10 }

    adGenTa5kAtmVclStatsConnectionInfo OBJECT-TYPE
        SYNTAX          DisplayString
        MAX-ACCESS      read-only
        STATUS          current
        DESCRIPTION
                "VCL connection information"
        ::= { adGenTa5kAtmVclStatsEntry 11 }


-- *********************************************************************************************************

    adGenTa5kAtmVplStatsTable OBJECT-TYPE
        SYNTAX      SEQUENCE OF AdGenTa5kAtmVplStatsEntry
        MAX-ACCESS  not-accessible
        STATUS      current
        DESCRIPTION
                   "ATM Vpl Stats"
        ::= { adGenTa5kAtmLMPMStats 6 }

    adGenTa5kAtmVplStatsEntry OBJECT-TYPE
        SYNTAX  AdGenTa5kAtmVplStatsEntry
        MAX-ACCESS  not-accessible
        STATUS      current
        DESCRIPTION
                   "Table Entry"
        INDEX   { ifIndex, atmVplVpi}
        ::= { adGenTa5kAtmVplStatsTable 1 }

    AdGenTa5kAtmVplStatsEntry ::=
        SEQUENCE {
                        adGenTa5kAtmVplStatsResetPM             Integer32,
                        adGenTa5kAtmVplStatsRxAIS               INTEGER,
                        adGenTa5kAtmVplStatsRxRDI               INTEGER,
                        adGenTa5kAtmVplStatsGenAISRDI           TruthValue,
                        adGenTa5kAtmVplStatsOamTxLbReqs         Integer32,
                        adGenTa5kAtmVplStatsOamRxLbReqs         Integer32,
                        adGenTa5kAtmVplStatsOamTxLbResps        Integer32,
                        adGenTa5kAtmVplStatsOamRxLbResps        Integer32,
                        adGenTa5kAtmVplStatsOamLbTimeouts       Integer32,
                        adGenTa5kAtmVplStatsOamLbLastResult     INTEGER,
                        adGenTa5kAtmVplStatsAal5InPkts          Counter32,
                        adGenTa5kAtmVplStatsAal5OutPkts         Counter32,
                        adGenTa5kAtmVplStatsAal5InOctets        Counter32,
                        adGenTa5kAtmVplStatsAal5OutOctets       Counter32,
                        adGenTa5kAtmVplStatsConnectionInfo      DisplayString
        }

    adGenTa5kAtmVplStatsResetPM OBJECT-TYPE
        SYNTAX          Integer32
        MAX-ACCESS      read-write
        STATUS          current
        DESCRIPTION
                "Reset Stats"
        ::= { adGenTa5kAtmVplStatsEntry 1 }

    adGenTa5kAtmVplStatsRxAIS OBJECT-TYPE
        SYNTAX  INTEGER {
                                true(1),
                                false(2),
                                na(3)
                        }
        MAX-ACCESS      read-only
        STATUS          current
        DESCRIPTION
                "True - indicates Rx AIS"
        ::= { adGenTa5kAtmVplStatsEntry 2 }

    adGenTa5kAtmVplStatsRxRDI OBJECT-TYPE
        SYNTAX  INTEGER {
                                true(1),
                                false(2),
                                na(3)
                        }
        MAX-ACCESS      read-only
        STATUS          current
        DESCRIPTION
                "True - indicates Rx RDI"
        ::= { adGenTa5kAtmVplStatsEntry 3 }

    adGenTa5kAtmVplStatsGenAISRDI OBJECT-TYPE
        SYNTAX          TruthValue
        MAX-ACCESS      read-only
        STATUS          current
        DESCRIPTION
                "True - indicates Vpl is generating AIS/RDI"
        ::= { adGenTa5kAtmVplStatsEntry 4 }

    adGenTa5kAtmVplStatsOamTxLbReqs OBJECT-TYPE
        SYNTAX          Integer32
        MAX-ACCESS      read-only
        STATUS          current
        DESCRIPTION
                "Number of transmitted F4 OAM Loopback Requests"
        ::= { adGenTa5kAtmVplStatsEntry 5 }

    adGenTa5kAtmVplStatsOamRxLbReqs OBJECT-TYPE
        SYNTAX          Integer32
        MAX-ACCESS      read-only
        STATUS          current
        DESCRIPTION
                "Number of received F4 OAM Loopback Requests"
        ::= { adGenTa5kAtmVplStatsEntry 6 }

    adGenTa5kAtmVplStatsOamTxLbResps OBJECT-TYPE
        SYNTAX          Integer32
        MAX-ACCESS      read-only
        STATUS          current
        DESCRIPTION
                "Number of transmitted F4 OAM Loopback Responses"
        ::= { adGenTa5kAtmVplStatsEntry 7 }

    adGenTa5kAtmVplStatsOamRxLbResps OBJECT-TYPE
        SYNTAX          Integer32
        MAX-ACCESS      read-only
        STATUS          current
        DESCRIPTION
                "Number of received F4 OAM Loopback Responses"
        ::= { adGenTa5kAtmVplStatsEntry 8 }

    adGenTa5kAtmVplStatsOamLbTimeouts OBJECT-TYPE
        SYNTAX          Integer32
        MAX-ACCESS      read-only
        STATUS          current
        DESCRIPTION
                "Number of transmitted F4 OAM Loopback Requests which timed out with no response"
        ::= { adGenTa5kAtmVplStatsEntry 9 }

    adGenTa5kAtmVplStatsOamLbLastResult OBJECT-TYPE
        SYNTAX          INTEGER {
                                    noneSent(0),
                                    cellOutstanding(1),
                                    responseReceived(2),
                                    timedOut(3)
                                }
        MAX-ACCESS      read-only
        STATUS          current
        DESCRIPTION
                "Result of the last loopback request"
        ::= { adGenTa5kAtmVplStatsEntry 10 }

   adGenTa5kAtmVplStatsAal5InPkts OBJECT-TYPE
        SYNTAX       Counter32
        MAX-ACCESS   read-only
        STATUS       current
        DESCRIPTION
            "The number of AAL5 CPCS PDUs received on the AAL5
            VPC at the interface identified by the ifIndex."
        ::= { adGenTa5kAtmVplStatsEntry 11 }

    adGenTa5kAtmVplStatsAal5OutPkts   OBJECT-TYPE
        SYNTAX       Counter32
        MAX-ACCESS   read-only
        STATUS       current
        DESCRIPTION
            "The number of AAL5 CPCS PDUs transmitted on the
            AAL5 VPC at the interface identified by the
            ifIndex."
        ::= { adGenTa5kAtmVplStatsEntry 12 }

    adGenTa5kAtmVplStatsAal5InOctets   OBJECT-TYPE
        SYNTAX       Counter32
        MAX-ACCESS   read-only
        STATUS       current
        DESCRIPTION
            "The number of octets contained in AAL5 CPCS PDUs
            received on the AAL5 VPC at the interface
            identified by the ifIndex."
        ::= { adGenTa5kAtmVplStatsEntry 13 }

    adGenTa5kAtmVplStatsAal5OutOctets   OBJECT-TYPE
        SYNTAX       Counter32
        MAX-ACCESS   read-only
        STATUS       current
        DESCRIPTION
            "The number of octets contained in AAL5 CPCS PDUs
            transmitted on the AAL5 VPC at the interface
            identified by the ifIndex."
        ::= { adGenTa5kAtmVplStatsEntry 14 }

    adGenTa5kAtmVplStatsConnectionInfo OBJECT-TYPE
        SYNTAX          DisplayString
        MAX-ACCESS      read-only
        STATUS          current
        DESCRIPTION
                "VPL connection information"
        ::= { adGenTa5kAtmVplStatsEntry 15 }

-- *********************************************************************************************************
    adGenTa5kAtmPortStatsTable OBJECT-TYPE
        SYNTAX      SEQUENCE OF AdGenTa5kAtmPortStatsEntry
        MAX-ACCESS  not-accessible
        STATUS      current
        DESCRIPTION
                   "ATM Port Stats Free-Rolling Counters"
        ::= { adGenTa5kAtmLMPMStats 7 }

    adGenTa5kAtmPortStatsEntry OBJECT-TYPE
        SYNTAX  AdGenTa5kAtmPortStatsEntry
        MAX-ACCESS  not-accessible
        STATUS      current
        DESCRIPTION
                   "Table Entry"
        INDEX   { ifIndex }
        ::= { adGenTa5kAtmPortStatsTable 1 }

    AdGenTa5kAtmPortStatsEntry ::=
        SEQUENCE {
                        adGenTa5kAtmPortStatsRxCells             Counter32,
                        adGenTa5kAtmPortStatsRxClp1Cells         Counter32,
                        adGenTa5kAtmPortStatsRxClp0Cells         Counter32,
                        adGenTa5kAtmPortStatsRxOamCells          Counter32,
                        adGenTa5kAtmPortStatsTxCells             Counter32,
                        adGenTa5kAtmPortStatsTxClp1Cells         Counter32,
                        adGenTa5kAtmPortStatsTxClp0Cells         Counter32,
                        adGenTa5kAtmPortStatsTxOamCells          Counter32,
                        adGenTa5kAtmPortStatsResetStats          INTEGER,
						adGenTa5kAtmPortStatsCellDelineation     TruthValue
                 }

    adGenTa5kAtmPortStatsRxCells OBJECT-TYPE
        SYNTAX          Counter32
        MAX-ACCESS      read-only
        STATUS          current
        DESCRIPTION
                "Rolling counter for RX cells"
        ::= { adGenTa5kAtmPortStatsEntry 1 }

    adGenTa5kAtmPortStatsRxClp1Cells OBJECT-TYPE
        SYNTAX          Counter32
        MAX-ACCESS      read-only
        STATUS          current
        DESCRIPTION
                "Rolling counter for RX CLP1 cells"
        ::= { adGenTa5kAtmPortStatsEntry 2 }

    adGenTa5kAtmPortStatsRxClp0Cells OBJECT-TYPE
        SYNTAX          Counter32
        MAX-ACCESS      read-only
        STATUS          current
        DESCRIPTION
                "Rolling counter for RX CLP0 cells"
        ::= { adGenTa5kAtmPortStatsEntry 3 }

    adGenTa5kAtmPortStatsRxOamCells OBJECT-TYPE
        SYNTAX          Counter32
        MAX-ACCESS      read-only
        STATUS          current
        DESCRIPTION
                "Rolling counter for RX OAM cells"
        ::= { adGenTa5kAtmPortStatsEntry 4 }

    adGenTa5kAtmPortStatsTxCells OBJECT-TYPE
        SYNTAX          Counter32
        MAX-ACCESS      read-only
        STATUS          current
        DESCRIPTION
                "Rolling counter for TX cells"
        ::= { adGenTa5kAtmPortStatsEntry 5 }

    adGenTa5kAtmPortStatsTxClp1Cells OBJECT-TYPE
        SYNTAX          Counter32
        MAX-ACCESS      read-only
        STATUS          current
        DESCRIPTION
                "Rolling counter for TX CLP1 cells"
        ::= { adGenTa5kAtmPortStatsEntry 6 }

    adGenTa5kAtmPortStatsTxClp0Cells OBJECT-TYPE
        SYNTAX          Counter32
        MAX-ACCESS      read-only
        STATUS          current
        DESCRIPTION
                "Rolling counter for TX CLP0 cells"
        ::= { adGenTa5kAtmPortStatsEntry 7 }

    adGenTa5kAtmPortStatsTxOamCells OBJECT-TYPE
        SYNTAX          Counter32
        MAX-ACCESS      read-only
        STATUS          current
        DESCRIPTION
                "Rolling counter for TX OAM cells"
        ::= { adGenTa5kAtmPortStatsEntry 8 }

    adGenTa5kAtmPortStatsResetStats OBJECT-TYPE
        SYNTAX  INTEGER { reset(1) }
        MAX-ACCESS      read-write
        STATUS          current
        DESCRIPTION
                "A Set will reset all rolling
                 counters on interface "
        ::= { adGenTa5kAtmPortStatsEntry 9 }
		
	adGenTa5kAtmPortStatsCellDelineation OBJECT-TYPE
        SYNTAX  TruthValue
        MAX-ACCESS      read-only
        STATUS          current
        DESCRIPTION
				"Returns cell delineation status: 
				true = cell delineation, 
				false = out of cell delineation"
        ::= { adGenTa5kAtmPortStatsEntry 10 }       
                                 
-- *********************************************************************************************************     
                            
    adGenTa5kAtmDhcpStatsCurrentTable OBJECT-TYPE
        SYNTAX      SEQUENCE OF AdGenTa5kAtmDhcpStatsCurrentEntry
        MAX-ACCESS  not-accessible
        STATUS      current
        DESCRIPTION
                   "DHCP Relay Agent Stats Current"
        ::= { adGenTa5kAtmLMPMStats 8 }

    adGenTa5kAtmDhcpStatsCurrentEntry OBJECT-TYPE
        SYNTAX  AdGenTa5kAtmDhcpStatsCurrentEntry
        MAX-ACCESS  not-accessible
        STATUS      current
        DESCRIPTION
                   "Table Entry"
        INDEX   { ifIndex }
        ::= { adGenTa5kAtmDhcpStatsCurrentTable 1 }

    AdGenTa5kAtmDhcpStatsCurrentEntry ::=
        SEQUENCE {
						adGenTa5kAtmDhcpStatsCurrentUpstreamFwdPktCnt		Counter32,
						adGenTa5kAtmDhcpStatsCurrentDownstreamFwdPktCnt		Counter32,
						adGenTa5kAtmDhcpStatsCurrentUpstreamDiscardPktCnt	Counter32,
						adGenTa5kAtmDhcpStatsCurrentDownstreamDiscardPktCnt	Counter32                        
                 }       
                 
    adGenTa5kAtmDhcpStatsCurrentUpstreamFwdPktCnt OBJECT-TYPE
        SYNTAX          Counter32
        MAX-ACCESS      read-only
        STATUS          current
        DESCRIPTION
                "Current counter for upstream valid DHCP messages processed"
        ::= { adGenTa5kAtmDhcpStatsCurrentEntry 1 }

    adGenTa5kAtmDhcpStatsCurrentDownstreamFwdPktCnt OBJECT-TYPE
        SYNTAX          Counter32
        MAX-ACCESS      read-only
        STATUS          current
        DESCRIPTION
                "Current counter for downstream valid DHCP messages processed"
        ::= { adGenTa5kAtmDhcpStatsCurrentEntry 2 }

    adGenTa5kAtmDhcpStatsCurrentUpstreamDiscardPktCnt OBJECT-TYPE
        SYNTAX          Counter32
        MAX-ACCESS      read-only
        STATUS          current
        DESCRIPTION
                "Current counter for upstream dropped invalid or malformed DHCP messages"
        ::= { adGenTa5kAtmDhcpStatsCurrentEntry 3 }

    adGenTa5kAtmDhcpStatsCurrentDownstreamDiscardPktCnt OBJECT-TYPE
        SYNTAX          Counter32
        MAX-ACCESS      read-only
        STATUS          current
        DESCRIPTION
                "Current counter for downstream dropped invalid or malformed DHCP messages"
        ::= { adGenTa5kAtmDhcpStatsCurrentEntry 4 }
        
-- *********************************************************************************************************

    adGenTa5kAtmDhcpStatsIntervalTable OBJECT-TYPE
        SYNTAX      SEQUENCE OF AdGenTa5kAtmDhcpStatsIntervalEntry
        MAX-ACCESS  not-accessible
        STATUS      current
        DESCRIPTION
                   "DHCP Relay Agent Interval Stats"
        ::= { adGenTa5kAtmLMPMStats 9 }

    adGenTa5kAtmDhcpStatsIntervalEntry OBJECT-TYPE
        SYNTAX  AdGenTa5kAtmDhcpStatsIntervalEntry
        MAX-ACCESS  not-accessible
        STATUS      current
        DESCRIPTION
                   "Table Entry"
        INDEX   { ifIndex, adGenTa5kAtmDhcpStatsIntervalIndex}
        ::= { adGenTa5kAtmDhcpStatsIntervalTable 1 }

    AdGenTa5kAtmDhcpStatsIntervalEntry ::=
        SEQUENCE {
                        adGenTa5kAtmDhcpStatsIntervalIndex						Integer32, 
                        adGenTa5kAtmDhcpStatsIntervalUpstreamFwdPktCnt			Counter32,
						adGenTa5kAtmDhcpStatsIntervalDownstreamFwdPktCnt		Counter32,
						adGenTa5kAtmDhcpStatsIntervalUpstreamDiscardPktCnt		Counter32,
						adGenTa5kAtmDhcpStatsIntervalDownstreamDiscardPktCnt	Counter32,  
                        adGenTa5kAtmDhcpStatsIntervalTimeStamp					DisplayString						
                }
        
    adGenTa5kAtmDhcpStatsIntervalIndex OBJECT-TYPE
        SYNTAX          Integer32
        MAX-ACCESS      not-accessible
        STATUS          current
        DESCRIPTION
                "Index of the 15-minute interval"
        ::= { adGenTa5kAtmDhcpStatsIntervalEntry 1 }

    adGenTa5kAtmDhcpStatsIntervalUpstreamFwdPktCnt OBJECT-TYPE
        SYNTAX          Counter32
        MAX-ACCESS      read-only
        STATUS          current
        DESCRIPTION
                "Upstream valid DHCP messages processed in 15-minute interval"
        ::= { adGenTa5kAtmDhcpStatsIntervalEntry 2 }

    adGenTa5kAtmDhcpStatsIntervalDownstreamFwdPktCnt OBJECT-TYPE
        SYNTAX          Counter32
        MAX-ACCESS      read-only
        STATUS          current
        DESCRIPTION
                "Downstream valid DHCP messages processed in 15-minute interval"
        ::= { adGenTa5kAtmDhcpStatsIntervalEntry 3 }

    adGenTa5kAtmDhcpStatsIntervalUpstreamDiscardPktCnt OBJECT-TYPE
        SYNTAX          Counter32
        MAX-ACCESS      read-only
        STATUS          current
        DESCRIPTION
                "Upstream dropped invalid or malformed DHCP messages in 15-minute interval"
        ::= { adGenTa5kAtmDhcpStatsIntervalEntry 4 }

    adGenTa5kAtmDhcpStatsIntervalDownstreamDiscardPktCnt OBJECT-TYPE
        SYNTAX          Counter32
        MAX-ACCESS      read-only
        STATUS          current
        DESCRIPTION
                "Downstream dropped invalid or malformed DHCP messages in 15-minute interval"
        ::= { adGenTa5kAtmDhcpStatsIntervalEntry 5 }                        

    adGenTa5kAtmDhcpStatsIntervalTimeStamp OBJECT-TYPE
        SYNTAX          DisplayString
        MAX-ACCESS      read-only
        STATUS          current
        DESCRIPTION
                "Timestamp of the 15-minute interval"
        ::= { adGenTa5kAtmDhcpStatsIntervalEntry 6 }        

-- *********************************************************************************************************

    adGenTa5kAtmDhcpStats24hrCurrentTable OBJECT-TYPE
        SYNTAX      SEQUENCE OF AdGenTa5kAtmDhcpStats24hrCurrentEntry
        MAX-ACCESS  not-accessible
        STATUS      current
        DESCRIPTION
                   "DHCP Relay Agent 24hr Current Stats"
        ::= { adGenTa5kAtmLMPMStats 10 }

    adGenTa5kAtmDhcpStats24hrCurrentEntry OBJECT-TYPE
        SYNTAX  AdGenTa5kAtmDhcpStats24hrCurrentEntry
        MAX-ACCESS  not-accessible
        STATUS      current
        DESCRIPTION
                   "Table Entry"
        INDEX   { ifIndex}
        ::= { adGenTa5kAtmDhcpStats24hrCurrentTable 1 }

    AdGenTa5kAtmDhcpStats24hrCurrentEntry ::=
        SEQUENCE {   
                        adGenTa5kAtmDhcpStats24hrCurrentUpstreamFwdPktCnt		Counter32,
						adGenTa5kAtmDhcpStats24hrCurrentDownstreamFwdPktCnt		Counter32,
						adGenTa5kAtmDhcpStats24hrCurrentUpstreamDiscardPktCnt	Counter32,
						adGenTa5kAtmDhcpStats24hrCurrentDownstreamDiscardPktCnt	Counter32                           
                }                                
                
    adGenTa5kAtmDhcpStats24hrCurrentUpstreamFwdPktCnt OBJECT-TYPE
        SYNTAX          Counter32
        MAX-ACCESS      read-only
        STATUS          current
        DESCRIPTION
                "Upstream valid DHCP messages processed in the current 24 hour period"
        ::= { adGenTa5kAtmDhcpStats24hrCurrentEntry 1 }

    adGenTa5kAtmDhcpStats24hrCurrentDownstreamFwdPktCnt OBJECT-TYPE
        SYNTAX          Counter32
        MAX-ACCESS      read-only
        STATUS          current
        DESCRIPTION
                "Downstream valid DHCP messages processed in the current 24 hour period"
        ::= { adGenTa5kAtmDhcpStats24hrCurrentEntry 2 }

    adGenTa5kAtmDhcpStats24hrCurrentUpstreamDiscardPktCnt OBJECT-TYPE
        SYNTAX          Counter32
        MAX-ACCESS      read-only
        STATUS          current
        DESCRIPTION
                "Upstream dropped invalid or malformed DHCP messages in the current 24 hour period"
        ::= { adGenTa5kAtmDhcpStats24hrCurrentEntry 3 }

    adGenTa5kAtmDhcpStats24hrCurrentDownstreamDiscardPktCnt OBJECT-TYPE
        SYNTAX          Counter32
        MAX-ACCESS      read-only
        STATUS          current
        DESCRIPTION
                "Downstream dropped invalid or malformed DHCP messages in the current 24 hour period"
        ::= { adGenTa5kAtmDhcpStats24hrCurrentEntry 4 }                                                   
                                                                                                          
-- *********************************************************************************************************

    adGenTa5kAtmDhcpStats24hrTable OBJECT-TYPE
        SYNTAX      SEQUENCE OF AdGenTa5kAtmDhcpStats24hrEntry
        MAX-ACCESS  not-accessible
        STATUS      current
        DESCRIPTION
                   "DHCP Relay Agent 24hr Interval Stats"
        ::= { adGenTa5kAtmLMPMStats 11 }

    adGenTa5kAtmDhcpStats24hrEntry OBJECT-TYPE
        SYNTAX  AdGenTa5kAtmDhcpStats24hrEntry
        MAX-ACCESS  not-accessible
        STATUS      current
        DESCRIPTION
                   "Table Entry"
        INDEX   { ifIndex, adGenTa5kAtmDhcpStats24hrIndex}
        ::= { adGenTa5kAtmDhcpStats24hrTable 1 }

    AdGenTa5kAtmDhcpStats24hrEntry ::=
        SEQUENCE {
                        adGenTa5kAtmDhcpStats24hrIndex              		Integer32,
                        adGenTa5kAtmDhcpStats24hrUpstreamFwdPktCnt			Counter32,
						adGenTa5kAtmDhcpStats24hrDownstreamFwdPktCnt		Counter32,
						adGenTa5kAtmDhcpStats24hrUpstreamDiscardPktCnt		Counter32,
						adGenTa5kAtmDhcpStats24hrDownstreamDiscardPktCnt	Counter32,
                        adGenTa5kAtmDhcpStats24hrTimeStamp          		DisplayString                          
                }
                                                                          
    adGenTa5kAtmDhcpStats24hrIndex OBJECT-TYPE
        SYNTAX          Integer32
        MAX-ACCESS      not-accessible
        STATUS          current
        DESCRIPTION
                "Index of the 24 hour period"
        ::= { adGenTa5kAtmDhcpStats24hrEntry 1 }

    adGenTa5kAtmDhcpStats24hrUpstreamFwdPktCnt OBJECT-TYPE
        SYNTAX          Counter32
        MAX-ACCESS      read-only
        STATUS          current
        DESCRIPTION
                "Upstream valid DHCP messages processed in a 24 hour period"
        ::= { adGenTa5kAtmDhcpStats24hrEntry 2 }

    adGenTa5kAtmDhcpStats24hrDownstreamFwdPktCnt OBJECT-TYPE
        SYNTAX          Counter32
        MAX-ACCESS      read-only
        STATUS          current
        DESCRIPTION
                "Downstream valid DHCP messages processed in a 24 hour period"
        ::= { adGenTa5kAtmDhcpStats24hrEntry 3 }

    adGenTa5kAtmDhcpStats24hrUpstreamDiscardPktCnt OBJECT-TYPE
        SYNTAX          Counter32
        MAX-ACCESS      read-only
        STATUS          current
        DESCRIPTION
                "Upstream dropped invalid or malformed DHCP messages in a 24 hour period"
        ::= { adGenTa5kAtmDhcpStats24hrEntry 4 }

    adGenTa5kAtmDhcpStats24hrDownstreamDiscardPktCnt OBJECT-TYPE
        SYNTAX          Counter32
        MAX-ACCESS      read-only
        STATUS          current
        DESCRIPTION
                "Downstream dropped invalid or malformed DHCP messages in a 24 hour period"
        ::= { adGenTa5kAtmDhcpStats24hrEntry 5 }                  

    adGenTa5kAtmDhcpStats24hrTimeStamp OBJECT-TYPE
        SYNTAX          DisplayString
        MAX-ACCESS      read-only
        STATUS          current
        DESCRIPTION
                "Timestamp of 24 hour period (Date)"
        ::= { adGenTa5kAtmDhcpStats24hrEntry 6 }          

-- *********************************************************************************************************
    adGenTa5kAtmDhcpStatsTable OBJECT-TYPE
        SYNTAX      SEQUENCE OF AdGenTa5kAtmDhcpStatsEntry
        MAX-ACCESS  not-accessible
        STATUS      current
        DESCRIPTION
                   "DHCP Relay Agent Stats Free-Rolling Counters"
        ::= { adGenTa5kAtmLMPMStats 12 }

    adGenTa5kAtmDhcpStatsEntry OBJECT-TYPE
        SYNTAX  AdGenTa5kAtmDhcpStatsEntry
        MAX-ACCESS  not-accessible
        STATUS      current
        DESCRIPTION
                   "Table Entry"
        INDEX   { ifIndex }
        ::= { adGenTa5kAtmDhcpStatsTable 1 }

    AdGenTa5kAtmDhcpStatsEntry ::=
        SEQUENCE {
                        adGenTa5kAtmDhcpStatsUpstreamFwdPktCnt			Counter32,
						adGenTa5kAtmDhcpStatsDownstreamFwdPktCnt		Counter32,
						adGenTa5kAtmDhcpStatsUpstreamDiscardPktCnt		Counter32,
						adGenTa5kAtmDhcpStatsDownstreamDiscardPktCnt	Counter32                          
                 }

    adGenTa5kAtmDhcpStatsUpstreamFwdPktCnt OBJECT-TYPE
        SYNTAX          Counter32
        MAX-ACCESS      read-only
        STATUS          current
        DESCRIPTION
                "Rolling counter for upstream valid DHCP messages processed"
        ::= { adGenTa5kAtmDhcpStatsEntry 1 }

    adGenTa5kAtmDhcpStatsDownstreamFwdPktCnt OBJECT-TYPE
        SYNTAX          Counter32
        MAX-ACCESS      read-only
        STATUS          current
        DESCRIPTION
                "Rolling counter for downstream valid DHCP messages processed"
        ::= { adGenTa5kAtmDhcpStatsEntry 2 }

    adGenTa5kAtmDhcpStatsUpstreamDiscardPktCnt OBJECT-TYPE
        SYNTAX          Counter32
        MAX-ACCESS      read-only
        STATUS          current
        DESCRIPTION
                "Rolling counter for upstream dropped invalid or malformed DHCP messages"
        ::= { adGenTa5kAtmDhcpStatsEntry 3 }

    adGenTa5kAtmDhcpStatsDownstreamDiscardPktCnt OBJECT-TYPE
        SYNTAX          Counter32
        MAX-ACCESS      read-only
        STATUS          current
        DESCRIPTION
                "Rolling counter for downstream dropped invalid or malformed DHCP messages"
        ::= { adGenTa5kAtmDhcpStatsEntry 4 }                 
                                                 
-- *********************************************************************************************************     
                            
    adGenTa5kAtmDhcpPerCardStatsCurrentTable OBJECT-TYPE
        SYNTAX      SEQUENCE OF AdGenTa5kAtmDhcpPerCardStatsCurrentEntry
        MAX-ACCESS  not-accessible
        STATUS      current
        DESCRIPTION
                   "DHCP Relay Agent Card Level Stats Current"
        ::= { adGenTa5kAtmLMPMStats 13 }

    adGenTa5kAtmDhcpPerCardStatsCurrentEntry OBJECT-TYPE
        SYNTAX  AdGenTa5kAtmDhcpPerCardStatsCurrentEntry
        MAX-ACCESS  not-accessible
        STATUS      current
        DESCRIPTION
                   "Table Entry"
        INDEX   { adGenSlotInfoIndex }
        ::= { adGenTa5kAtmDhcpPerCardStatsCurrentTable 1 }

    AdGenTa5kAtmDhcpPerCardStatsCurrentEntry ::=
        SEQUENCE {
						adGenTa5kAtmDhcpPerCardStatsCurrentUpstreamDroppedPktCnt	Counter32,
						adGenTa5kAtmDhcpPerCardStatsCurrentDownstreamDroppedPktCnt	Counter32                      
                 }       
                 
    adGenTa5kAtmDhcpPerCardStatsCurrentUpstreamDroppedPktCnt OBJECT-TYPE
        SYNTAX          Counter32
        MAX-ACCESS      read-only
        STATUS          current
        DESCRIPTION
                "Current counter for upstream dropped messages due to policing of DHCP messages"
        ::= { adGenTa5kAtmDhcpPerCardStatsCurrentEntry 1 }

    adGenTa5kAtmDhcpPerCardStatsCurrentDownstreamDroppedPktCnt OBJECT-TYPE
        SYNTAX          Counter32
        MAX-ACCESS      read-only
        STATUS          current
        DESCRIPTION
                "Current counter for downstream dropped messages due to policing of DHCP messages"
        ::= { adGenTa5kAtmDhcpPerCardStatsCurrentEntry 2 }

-- *********************************************************************************************************

    adGenTa5kAtmDhcpPerCardStatsIntervalTable OBJECT-TYPE
        SYNTAX      SEQUENCE OF AdGenTa5kAtmDhcpPerCardStatsIntervalEntry
        MAX-ACCESS  not-accessible
        STATUS      current
        DESCRIPTION
                   "DHCP Relay Agent Card Level Interval Stats"
        ::= { adGenTa5kAtmLMPMStats 14 }

    adGenTa5kAtmDhcpPerCardStatsIntervalEntry OBJECT-TYPE
        SYNTAX  AdGenTa5kAtmDhcpPerCardStatsIntervalEntry
        MAX-ACCESS  not-accessible
        STATUS      current
        DESCRIPTION
                   "Table Entry"
        INDEX   { adGenSlotInfoIndex, adGenTa5kAtmDhcpPerCardStatsIntervalIndex}
        ::= { adGenTa5kAtmDhcpPerCardStatsIntervalTable 1 }

    AdGenTa5kAtmDhcpPerCardStatsIntervalEntry ::=
        SEQUENCE {
                        adGenTa5kAtmDhcpPerCardStatsIntervalIndex					Integer32, 
						adGenTa5kAtmDhcpPerCardStatsIntervalUpstreamDroppedPktCnt	Counter32,
						adGenTa5kAtmDhcpPerCardStatsIntervalDownstreamDroppedPktCnt	Counter32,                      						
                        adGenTa5kAtmDhcpPerCardStatsIntervalTimeStamp				DisplayString						
                }
        
    adGenTa5kAtmDhcpPerCardStatsIntervalIndex OBJECT-TYPE
        SYNTAX          Integer32
        MAX-ACCESS      not-accessible
        STATUS          current
        DESCRIPTION
                "Index of the 15-minute interval"
        ::= { adGenTa5kAtmDhcpPerCardStatsIntervalEntry 1 }

    adGenTa5kAtmDhcpPerCardStatsIntervalUpstreamDroppedPktCnt OBJECT-TYPE
        SYNTAX          Counter32
        MAX-ACCESS      read-only
        STATUS          current
        DESCRIPTION
                "Upstream dropped messages due to policing of DHCP messages in 15-minute interval"
        ::= { adGenTa5kAtmDhcpPerCardStatsIntervalEntry 2 }

    adGenTa5kAtmDhcpPerCardStatsIntervalDownstreamDroppedPktCnt OBJECT-TYPE
        SYNTAX          Counter32
        MAX-ACCESS      read-only
        STATUS          current
        DESCRIPTION
                "Downstream dropped messages due to policing of DHCP messages in 15-minute interval"
        ::= { adGenTa5kAtmDhcpPerCardStatsIntervalEntry 3 }
    
    adGenTa5kAtmDhcpPerCardStatsIntervalTimeStamp OBJECT-TYPE
        SYNTAX          DisplayString
        MAX-ACCESS      read-only
        STATUS          current
        DESCRIPTION
                "Timestamp of the 15-minute interval"
        ::= { adGenTa5kAtmDhcpPerCardStatsIntervalEntry 4 }        
                                     
-- *********************************************************************************************************

    adGenTa5kAtmDhcpPerCardStats24hrCurrentTable OBJECT-TYPE
        SYNTAX      SEQUENCE OF AdGenTa5kAtmDhcpPerCardStats24hrCurrentEntry
        MAX-ACCESS  not-accessible
        STATUS      current
        DESCRIPTION
                   "DHCP Relay Agent Card Level 24hr Current Stats"
        ::= { adGenTa5kAtmLMPMStats 15 }

    adGenTa5kAtmDhcpPerCardStats24hrCurrentEntry OBJECT-TYPE
        SYNTAX  AdGenTa5kAtmDhcpPerCardStats24hrCurrentEntry
        MAX-ACCESS  not-accessible
        STATUS      current
        DESCRIPTION
                   "Table Entry"
        INDEX   { adGenSlotInfoIndex }
        ::= { adGenTa5kAtmDhcpPerCardStats24hrCurrentTable 1 }

    AdGenTa5kAtmDhcpPerCardStats24hrCurrentEntry ::=
        SEQUENCE {   
						adGenTa5kAtmDhcpPerCardStats24hrCurrentUpstreamDroppedPktCnt	Counter32,
						adGenTa5kAtmDhcpPerCardStats24hrCurrentDownstreamDroppedPktCnt	Counter32                      						
				}     
                
    adGenTa5kAtmDhcpPerCardStats24hrCurrentUpstreamDroppedPktCnt OBJECT-TYPE
        SYNTAX          Counter32
        MAX-ACCESS      read-only
        STATUS          current
        DESCRIPTION
                "Upstream dropped messages due to policing of DHCP messages in the current 24 hour period"
        ::= { adGenTa5kAtmDhcpPerCardStats24hrCurrentEntry 1 }

    adGenTa5kAtmDhcpPerCardStats24hrCurrentDownstreamDroppedPktCnt OBJECT-TYPE
        SYNTAX          Counter32
        MAX-ACCESS      read-only
        STATUS          current
        DESCRIPTION
                "Downstream dropped messages due to policing of DHCP messages in the current 24 hour period"
        ::= { adGenTa5kAtmDhcpPerCardStats24hrCurrentEntry 2 }
                                           
-- *********************************************************************************************************

    adGenTa5kAtmDhcpPerCardStats24hrTable OBJECT-TYPE
        SYNTAX      SEQUENCE OF AdGenTa5kAtmDhcpPerCardStats24hrEntry
        MAX-ACCESS  not-accessible
        STATUS      current
        DESCRIPTION
                   "DHCP Relay Agent Card Level 24hr Interval Stats"
        ::= { adGenTa5kAtmLMPMStats 16 }

    adGenTa5kAtmDhcpPerCardStats24hrEntry OBJECT-TYPE
        SYNTAX  AdGenTa5kAtmDhcpPerCardStats24hrEntry
        MAX-ACCESS  not-accessible
        STATUS      current
        DESCRIPTION
                   "Table Entry"
        INDEX   { adGenSlotInfoIndex, adGenTa5kAtmDhcpPerCardStats24hrIndex}
        ::= { adGenTa5kAtmDhcpPerCardStats24hrTable 1 }

    AdGenTa5kAtmDhcpPerCardStats24hrEntry ::=
        SEQUENCE {
                        adGenTa5kAtmDhcpPerCardStats24hrIndex     				Integer32,
						adGenTa5kAtmDhcpPerCardStats24hrUpstreamDroppedPktCnt	Counter32,
						adGenTa5kAtmDhcpPerCardStats24hrDownstreamDroppedPktCnt	Counter32,                      						
                        adGenTa5kAtmDhcpPerCardStats24hrTimeStamp          		DisplayString                          
                }   
                
	adGenTa5kAtmDhcpPerCardStats24hrIndex OBJECT-TYPE
        SYNTAX          Integer32
        MAX-ACCESS      not-accessible
        STATUS          current
        DESCRIPTION
                "Index of the 24 hour period"
        ::= { adGenTa5kAtmDhcpPerCardStats24hrEntry 1 }

    adGenTa5kAtmDhcpPerCardStats24hrUpstreamDroppedPktCnt OBJECT-TYPE
        SYNTAX          Counter32
        MAX-ACCESS      read-only
        STATUS          current
        DESCRIPTION
                "Upstream dropped messages due to policing of DHCP messages in a 24 hour period"
        ::= { adGenTa5kAtmDhcpPerCardStats24hrEntry 2 }

    adGenTa5kAtmDhcpPerCardStats24hrDownstreamDroppedPktCnt OBJECT-TYPE
        SYNTAX          Counter32
        MAX-ACCESS      read-only
        STATUS          current
        DESCRIPTION
                "Downstream dropped messages due to policing of DHCP messages in a 24 hour period"
        ::= { adGenTa5kAtmDhcpPerCardStats24hrEntry 3 }   
        
	adGenTa5kAtmDhcpPerCardStats24hrTimeStamp OBJECT-TYPE
        SYNTAX          DisplayString
        MAX-ACCESS      read-only
        STATUS          current
        DESCRIPTION
                "Timestamp of 24 hour period (Date)"
        ::= { adGenTa5kAtmDhcpPerCardStats24hrEntry 4 }  
        
-- *********************************************************************************************************
    adGenTa5kAtmDhcpPerCardStatsTable OBJECT-TYPE
        SYNTAX      SEQUENCE OF AdGenTa5kAtmDhcpPerCardStatsEntry
        MAX-ACCESS  not-accessible
        STATUS      current
        DESCRIPTION
                   "DHCP Relay Agent Card Level Stats Free-Rolling Counters"
        ::= { adGenTa5kAtmLMPMStats 17 }

    adGenTa5kAtmDhcpPerCardStatsEntry OBJECT-TYPE
        SYNTAX  AdGenTa5kAtmDhcpPerCardStatsEntry
        MAX-ACCESS  not-accessible
        STATUS      current
        DESCRIPTION
                   "Table Entry"
        INDEX   { adGenSlotInfoIndex }
        ::= { adGenTa5kAtmDhcpPerCardStatsTable 1 }

    AdGenTa5kAtmDhcpPerCardStatsEntry ::=
        SEQUENCE {
						adGenTa5kAtmDhcpPerCardStatsUpstreamDroppedPktCnt	Counter32,
						adGenTa5kAtmDhcpPerCardStatsDownstreamDroppedPktCnt	Counter32                      												                      
                 }
                
    adGenTa5kAtmDhcpPerCardStatsUpstreamDroppedPktCnt OBJECT-TYPE
        SYNTAX          Counter32
        MAX-ACCESS      read-only
        STATUS          current
        DESCRIPTION
                "Rolling counter for upstream dropped messages due to policing of DHCP messages"
        ::= { adGenTa5kAtmDhcpPerCardStatsEntry 1 }

    adGenTa5kAtmDhcpPerCardStatsDownstreamDroppedPktCnt OBJECT-TYPE
        SYNTAX          Counter32
        MAX-ACCESS      read-only
        STATUS          current
        DESCRIPTION
                "Rolling counter for downstream dropped messages due to policing of DHCP messages"
        ::= { adGenTa5kAtmDhcpPerCardStatsEntry 2 }

-- *********************************************************************************************************
-- *********************************************************************************************************
    adGenTa5kAtmLMErrorVcTable OBJECT-TYPE
        SYNTAX      SEQUENCE OF AdGenTa5kAtmLMErrorVcEntry
        MAX-ACCESS  not-accessible
        STATUS      current
        DESCRIPTION
            "Table containing each ATM interface's last Interworked VP Cross Connect Errored VC"
        ::= { adGenTa5kAtmLMVpStatus 1 }
    adGenTa5kAtmLMErrorVcEntry OBJECT-TYPE
        SYNTAX  AdGenTa5kAtmLMErrorVcEntry
        MAX-ACCESS  not-accessible
        STATUS      current
        DESCRIPTION
                   "Table Entry"
        INDEX   { ifIndex }
        ::= { adGenTa5kAtmLMErrorVcTable 1 }
    AdGenTa5kAtmLMErrorVcEntry ::=
        SEQUENCE {
                        adGenTa5kAtmLMRecentErrorVC           DisplayString,
                        adGenTa5kAtmLMRecentErrorVCClear      INTEGER
                 }
    adGenTa5kAtmLMRecentErrorVC OBJECT-TYPE
        SYNTAX          DisplayString
        MAX-ACCESS      read-only
        STATUS          current
        DESCRIPTION
                "String that represents the most recent Errored VC on this ATM interface"
        ::= { adGenTa5kAtmLMErrorVcEntry 1 }
    adGenTa5kAtmLMRecentErrorVCClear OBJECT-TYPE
        SYNTAX          INTEGER{ reset(1) }
        MAX-ACCESS      read-write
        STATUS          current
        DESCRIPTION
                "String that represents the most recent Errored VC on this ATM interface"
        ::= { adGenTa5kAtmLMErrorVcEntry 2 }
-- *********************************************************************************************************
    adGenTa5kAtmVpStatusTable OBJECT-TYPE
        SYNTAX      SEQUENCE OF AdGenTa5kAtmVpStatusEntry
        MAX-ACCESS  not-accessible
        STATUS      current
        DESCRIPTION
            "ATM Vpl Status"
        ::= { adGenTa5kAtmLMVpStatus 2 }
    adGenTa5kAtmVpStatusEntry OBJECT-TYPE
        SYNTAX  AdGenTa5kAtmVpStatusEntry
        MAX-ACCESS  not-accessible
        STATUS      current
        DESCRIPTION
            "Table Entry"
        INDEX   { ifIndex, atmVclVpi, atmVclVci}
        ::= { adGenTa5kAtmVpStatusTable 1 }
    AdGenTa5kAtmVpStatusEntry ::=
        SEQUENCE {
		    adGenTa5kAtmVpStatusVc            INTEGER,
    		adGenTa5kAtmVpStatusVcEncaps	  INTEGER,
    		adGenTa5kAtmVpStatusVcDelete	  INTEGER
    		
        }
    adGenTa5kAtmVpStatusVc OBJECT-TYPE
        SYNTAX          INTEGER {
                                  exists(1),
                                  missing(2)
                                }
        MAX-ACCESS      read-only
        STATUS          current
        DESCRIPTION
                "Returns exists(1) for a VC that are currently active on an Interworked VP"
        ::= { adGenTa5kAtmVpStatusEntry 1 }
        
    adGenTa5kAtmVpStatusVcEncaps OBJECT-TYPE
        SYNTAX          INTEGER {
                                  vcmuxrouted(1),
                                  vcmuxbridged8023(2),
                                  vcmuxbridged8025(3),
                                  vcmuxbridged8026(4),
                                  lanemul8023(5),
                                  lanemul8025(6),
                                  llcencap(7),
                                  framerelay(8),
                                  other(9),
                                  unknown(10),
                                  vcmuxpppoapppoeiw(11),
                                  llcpppoapppoeiw(12),
                                  llcautodiscover(13)
                                }
        MAX-ACCESS      read-only
        STATUS          current
        DESCRIPTION
                ""
        ::= { adGenTa5kAtmVpStatusEntry 2 }
        
	adGenTa5kAtmVpStatusVcDelete OBJECT-TYPE
        SYNTAX          INTEGER { delete(1) }
        MAX-ACCESS      read-write
        STATUS          current
        DESCRIPTION
                "Gets will always return 1, Sets 1 will delete the Vc if it exist"
        ::= { adGenTa5kAtmVpStatusEntry 3 }
        
-- *********************************************************************************************************
    adGenTa5kAtmLMUnlearnableVCL  NOTIFICATION-TYPE
        OBJECTS       {
                           adTrapInformSeqNum,
                           sysName,
                           ifIndex,
                           adGenTa5kAtmLMRecentErrorVC
                      }
        STATUS  current
        DESCRIPTION
            "TA 5000 ATM Line Module Unlearnable VCL"
            --#TYPE      "Unlearnable VCL"
            --#SUMMARY   "The ATM Cell Processor Discovered a VC that it cannot learn"
            --#SUMMARY   "set at shelf: %s, slot: %d"
            --#ARGUMENTS { 1, 2 }
            --#SEVERITY  INFO
            --#GENERIC   6
            --#CATEGORY  "Error Events"
            --#SOURCE_ID "A"
            --#TIMEINDEX 0
        ::=  { adGenTa5kAtmLMAlarm 1 }
END

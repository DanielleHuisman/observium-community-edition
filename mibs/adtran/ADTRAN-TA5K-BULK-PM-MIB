ADTRAN-TA5K-BULK-PM-MIB

    DEFINITIONS ::= BEGIN

    -- TITLE:     The ADTRAN Total Access TA5000 Bulk PM MIB
    -- PRODUCT:   1187020L1, 11872xx
    -- VERSION:   1.0
    -- DATE:      July 18, 2007

    -- This MIB allows the EMS to get the instance value for bulk PM gets
    --

    -- MIBs supported:

    -- HISTORY:
    --     07/18/07     aed         First edition



    IMPORTS
        MODULE-IDENTITY,
        OBJECT-TYPE,
        Integer32
            FROM SNMPv2-SMI

        adIdentity,
        adIdentityShared,
        adProducts,
        adMgmt
            FROM ADTRAN-MIB

        adGenTa5kBulkPM,
        adGenTa5kBulkPMID
            FROM ADTRAN-GENTA5K-MIB

--        IANAifType
--          FROM IANAifType-MIB

--        sysName
--            FROM RFC1213-MIB

        adGenPortInfoIndex
            FROM ADTRAN-GENPORT-MIB

        adGenSlotInfoIndex
            FROM ADTRAN-GENSLOT-MIB;

-- *******************************************************************************

    adTa5kBulkPMModuleIdentity MODULE-IDENTITY
        LAST-UPDATED "200709200000Z"
        ORGANIZATION
            "ADTRAN, Inc."
        CONTACT-INFO
            "CND Tech Support
                Postal: ADTRAN, Inc.
                        901 Explorer Blvd.
                        Huntsville, AL  35806
                        Tel: +1 800 726-8663
                        Fax: +1 256 963 6217
                        E-mail: support@adtran.com"
        DESCRIPTION
            "Total Access 5000 Bulk Performance Monitoring MIB"
        ::= { adGenTa5kBulkPMID 1 }

-- *******************************************************************************

    adTa5kBulkPMSlotTable OBJECT-TYPE
       SYNTAX      SEQUENCE OF AdTa5kBulkPMSlotEntry
       MAX-ACCESS  not-accessible
       STATUS      current
       DESCRIPTION
           "..."
       ::= { adGenTa5kBulkPM 1 }

    adTa5kBulkPMSlotEntry OBJECT-TYPE
       SYNTAX      AdTa5kBulkPMSlotEntry
       MAX-ACCESS  not-accessible
       STATUS      current
       DESCRIPTION
           "Index is the slot number."
       INDEX { adGenSlotInfoIndex }
       ::= { adTa5kBulkPMSlotTable 1 }

    AdTa5kBulkPMSlotEntry ::=
       SEQUENCE {
           adTa5kBulkPMSlotInstance           Integer32,
           adTa5kBulkPM15MinSlotInstance      Integer32
       }

    adTa5kBulkPMSlotInstance      OBJECT-TYPE
       SYNTAX                    Integer32
       MAX-ACCESS                read-only
       STATUS                    current
       DESCRIPTION
           "Used to index the Tlv table, each time this is called it
            creates an instance for that viewer to read bulk PM data by slot."
        ::= { adTa5kBulkPMSlotEntry 1 }

    adTa5kBulkPM15MinSlotInstance      OBJECT-TYPE
       SYNTAX                    Integer32
       MAX-ACCESS                read-only
       STATUS                    current
       DESCRIPTION
           "Used to index the Tlv table, each time this is called it
            creates an instance for that viewer to read 15 minute bulk PM data by slot."
        ::= { adTa5kBulkPMSlotEntry 2 }

-- *******************************************************************************

   adTa5kBulkPMPortTable OBJECT-TYPE
       SYNTAX      SEQUENCE OF AdTa5kBulkPMPortEntry
       MAX-ACCESS  not-accessible
       STATUS      current
       DESCRIPTION
           "..."
       ::= { adGenTa5kBulkPM 2 }

    adTa5kBulkPMPortEntry OBJECT-TYPE
       SYNTAX      AdTa5kBulkPMPortEntry
       MAX-ACCESS  not-accessible
       STATUS      current
       DESCRIPTION
           "Indexes are the slot number and port number"
       INDEX { adGenSlotInfoIndex, adGenPortInfoIndex }
       ::= { adTa5kBulkPMPortTable 1 }

    AdTa5kBulkPMPortEntry ::=
       SEQUENCE {
           adTa5kBulkPMPortInstance           Integer32

       }

    adTa5kBulkPMPortInstance      OBJECT-TYPE
       SYNTAX                    Integer32
       MAX-ACCESS                read-only
       STATUS                    current
       DESCRIPTION
           "Used to index the Tlv table, each time this is called it
            creates an instance for that viewer to read bulk PM data by slot and port."
        ::= { adTa5kBulkPMPortEntry 1 }

   END

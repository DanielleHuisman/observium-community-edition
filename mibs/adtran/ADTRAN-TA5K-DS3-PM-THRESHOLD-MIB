ADTRAN-TA5K-DS3-PM-THRESHOLD-MIB

DEFINITIONS ::= BEGIN

-- TITLE:     The ADTRAN Total Access TA5000 DS3 PM MIB
-- PRODUCT:
-- VERSION:   1.0
-- DATE:      Sept 18, 2007

-- This MIB contains information for configuring DS3 PM Threshold

-- This MIB also defines the Threshold crossing alarms and other DS3 alarms

-- MIBs supported:

-- Revision History:
--		09/18/2007	First Revision
--              09/20/2007      twc - Fixed SMIC compiler errors
--              05/20/2008      jlb - Changed alarm severities to match SR4.0 firmware
--              07/10/2008      jlb - Added adGenPortInfoIndex to adTA5kds3LOSTrapClear.

-- **************************************************************************

	IMPORTS
		MODULE-IDENTITY, OBJECT-TYPE,
		Integer32,
        NOTIFICATION-TYPE
             FROM SNMPv2-SMI                    -- [RFC2578]

        OBJECT-GROUP,
        NOTIFICATION-GROUP
            FROM SNMPv2-CONF

        ifIndex
             FROM IF-MIB                        -- [RFC2863]

        sysName
             FROM SNMPv2-MIB

		adIdentity,
		adProducts,
        adMgmt
            FROM ADTRAN-MIB

        adTrapInformSeqNum
			FROM ADTRAN-GENTRAPINFORM-MIB

	    adGenSlotInfoIndex
			FROM ADTRAN-GENSLOT-MIB

        adGenTa5kDs3,
        adGenTa5kDs3ID
            FROM ADTRAN-GENTA5K-MIB

        adGenPortTrapIdentifier,
	adGenPortInfoIndex
			FROM ADTRAN-GENPORT-MIB;

-- ***************************************************************************
    adTa5kDs3PMThresholdModuleIdentity MODULE-IDENTITY
        LAST-UPDATED "200709200000Z"
        ORGANIZATION
            "ADTRAN, Inc."
        CONTACT-INFO
            "CND Tech Support
                Postal: ADTRAN, Inc.
                        901 Explorer Blvd.
                        Huntsville, AL  35806
                        Tel: +1 800 726-8663
                        Fax: +1 256 963 6217
                        E-mail: support@adtran.com"
        DESCRIPTION
            "Total Access 5000 DS3 PM Threshold MIB"
        ::= { adGenTa5kDs3ID 1 }


-- -------------------------------------
-- Object Identifiers
-- -------------------------------------
adTA5kds3TrapsPrefix    OBJECT IDENTIFIER ::= { adGenTa5kDs3 1 }
adTA5kds3Traps          OBJECT IDENTIFIER ::= { adTA5kds3TrapsPrefix 0 }

adTA5kds3PMThreshold OBJECT IDENTIFIER ::= { adGenTa5kDs3 2 }

adTA5kds3MibConformance	OBJECT IDENTIFIER ::= { adGenTa5kDs3 3 }
adTA5kds3MibGroups	OBJECT IDENTIFIER ::= { adTA5kds3MibConformance 1 }

-- -------------------------------------
-- DS3 PM Thresholds
-- -------------------------------------

adTa5kDS3PMqtrThresholdTable	OBJECT-TYPE
		SYNTAX  SEQUENCE OF AdTa5kDS3PMqtrThresholdEntry
		MAX-ACCESS not-accessible
                STATUS  current
		DESCRIPTION
		 	"The DS3 PM Thresholds Table."
		::= { adTA5kds3PMThreshold 1 }

adTa5kDS3PMqtrThresholdEntry	OBJECT-TYPE
		SYNTAX  AdTa5kDS3PMqtrThresholdEntry
		MAX-ACCESS not-accessible
                STATUS  current
		DESCRIPTION
			"An entry in the DS3 PM Threshold Table."
		INDEX	{ ifIndex }
		::= { adTa5kDS3PMqtrThresholdTable 1 }

AdTa5kDS3PMqtrThresholdEntry ::=
	SEQUENCE {
				adTa5kDs3PMqtrThresholdPESs    Integer32,
        		adTa5kDs3PMqtrThresholdPSESs   Integer32,
        		adTa5kDs3PMqtrThresholdSEFSs   Integer32,
        		adTa5kDs3PMqtrThresholdUASs    Integer32,
        		adTa5kDs3PMqtrThresholdLCVs    Integer32,
        		adTa5kDs3PMqtrThresholdPCVs    Integer32,
        		adTa5kDs3PMqtrThresholdLESs    Integer32,
        		adTa5kDs3PMqtrThresholdCCVs    Integer32,
        		adTa5kDs3PMqtrThresholdCESs    Integer32,
        		adTa5kDs3PMqtrThresholdCSESs   Integer32
			}

adTa5kDs3PMqtrThresholdPESs OBJECT-TYPE
		SYNTAX  Integer32
		MAX-ACCESS read-write
        STATUS  current
        DESCRIPTION
        	"A parameter indicating the threshold value for the 15-minute PES counter."
		::= { adTa5kDS3PMqtrThresholdEntry 1 }

adTa5kDs3PMqtrThresholdPSESs OBJECT-TYPE
		SYNTAX  Integer32
		MAX-ACCESS read-write
        STATUS  current
        DESCRIPTION
        	"A parameter indicating the threshold value for the 15-minute PSES counter."
		::= { adTa5kDS3PMqtrThresholdEntry 2 }

adTa5kDs3PMqtrThresholdSEFSs OBJECT-TYPE
		SYNTAX  Integer32
		MAX-ACCESS read-write
        STATUS  current
        DESCRIPTION
        	"A parameter indicating the threshold value for the 15-minute SEFS counter."
		::= { adTa5kDS3PMqtrThresholdEntry 3 }

adTa5kDs3PMqtrThresholdUASs OBJECT-TYPE
		SYNTAX  Integer32
		MAX-ACCESS read-write
        STATUS  current
        DESCRIPTION
        	"A parameter indicating the threshold value for the 15-minute UAS counter."
		::= { adTa5kDS3PMqtrThresholdEntry 4 }

adTa5kDs3PMqtrThresholdLCVs OBJECT-TYPE
		SYNTAX  Integer32
		MAX-ACCESS read-write
        STATUS  current
        DESCRIPTION
        	"A parameter indicating the threshold value for the 15-minute LCV counter."
		::= { adTa5kDS3PMqtrThresholdEntry 5 }

adTa5kDs3PMqtrThresholdPCVs OBJECT-TYPE
		SYNTAX  Integer32
		MAX-ACCESS read-write
        STATUS  current
        DESCRIPTION
        	"A parameter indicating the threshold value for the 15-minute PCV counter."
		::= { adTa5kDS3PMqtrThresholdEntry 6 }

adTa5kDs3PMqtrThresholdLESs OBJECT-TYPE
		SYNTAX  Integer32
		MAX-ACCESS read-write
        STATUS  current
        DESCRIPTION
        	"A parameter indicating the threshold value for the 15-minute LES counter."
		::= { adTa5kDS3PMqtrThresholdEntry 7 }

adTa5kDs3PMqtrThresholdCCVs OBJECT-TYPE
		SYNTAX  Integer32
		MAX-ACCESS read-write
        STATUS  current
        DESCRIPTION
        	"A parameter indicating the threshold value for the 15-minute CCV counter."
		::= { adTa5kDS3PMqtrThresholdEntry 8 }

adTa5kDs3PMqtrThresholdCESs OBJECT-TYPE
		SYNTAX  Integer32
		MAX-ACCESS read-write
        STATUS  current
        DESCRIPTION
        	"A parameter indicating the threshold value for the 15-minute CES counter."
		::= { adTa5kDS3PMqtrThresholdEntry 9 }

adTa5kDs3PMqtrThresholdCSESs OBJECT-TYPE
		SYNTAX  Integer32
		MAX-ACCESS read-write
        STATUS  current
        DESCRIPTION
        	"A parameter indicating the threshold value for the 15-minute CSES counter."
		::= { adTa5kDS3PMqtrThresholdEntry 10 }

-- ********************************************************************
--                 DS3 PM Daily Threshold
-- ********************************************************************

adTa5kDs3PMDayThresholdTable OBJECT-TYPE
        SYNTAX  SEQUENCE OF AdTa5kDs3PMDayThresholdEntry
        MAX-ACCESS  not-accessible
        STATUS      current
        DESCRIPTION
                   " Performance Monitoring Daily Threshold Table"
        ::= { adTA5kds3PMThreshold 2 }

adTa5kDs3PMDayThresholdEntry OBJECT-TYPE
        SYNTAX  AdTa5kDs3PMDayThresholdEntry
        MAX-ACCESS  not-accessible
        STATUS      current
        DESCRIPTION
                   "Table Entry"
        INDEX   { ifIndex }
        ::= { adTa5kDs3PMDayThresholdTable 1 }

AdTa5kDs3PMDayThresholdEntry ::=
        SEQUENCE {
                    adTa5kDs3PMDayThresholdPES    Integer32,
                    adTa5kDs3PMDayThresholdPSES   Integer32,
                    adTa5kDs3PMDayThresholdSEFS   Integer32,
                    adTa5kDs3PMDayThresholdUAS    Integer32,
                    adTa5kDs3PMDayThresholdLCV    Integer32,
                    adTa5kDs3PMDayThresholdPCV    Integer32,
                    adTa5kDs3PMDayThresholdLES    Integer32,
                    adTa5kDs3PMDayThresholdCCV    Integer32,
                    adTa5kDs3PMDayThresholdCES    Integer32,
                    adTa5kDs3PMDayThresholdCSES   Integer32
                 }

adTa5kDs3PMDayThresholdPES OBJECT-TYPE
           SYNTAX       Integer32
           MAX-ACCESS   read-write
           STATUS       current
           DESCRIPTION
                        "A parameter indicating the threshold value for 24-hour PES counter."
     ::= { adTa5kDs3PMDayThresholdEntry 1 }

adTa5kDs3PMDayThresholdPSES OBJECT-TYPE
           SYNTAX       Integer32
           MAX-ACCESS   read-write
           STATUS       current
           DESCRIPTION
                        "A parameter indicating the threshold value for 24-hour PSES counter."
     ::= { adTa5kDs3PMDayThresholdEntry 2 }

adTa5kDs3PMDayThresholdSEFS OBJECT-TYPE
           SYNTAX       Integer32
           MAX-ACCESS   read-write
           STATUS       current
           DESCRIPTION
                        "A parameter indicating the threshold value for 24-hour SEFS counter."
     ::= { adTa5kDs3PMDayThresholdEntry 3 }

adTa5kDs3PMDayThresholdUAS OBJECT-TYPE
           SYNTAX       Integer32
           MAX-ACCESS   read-write
           STATUS       current
           DESCRIPTION
                        "A parameter indicating the threshold value for 24-hour UAS counter."
     ::= { adTa5kDs3PMDayThresholdEntry 4 }

adTa5kDs3PMDayThresholdLCV OBJECT-TYPE
           SYNTAX       Integer32
           MAX-ACCESS   read-write
           STATUS       current
           DESCRIPTION
                        "A parameter indicating the threshold value for 24-hour LCV counter."
	::= { adTa5kDs3PMDayThresholdEntry 5 }

adTa5kDs3PMDayThresholdPCV OBJECT-TYPE
           SYNTAX       Integer32
           MAX-ACCESS   read-write
           STATUS       current
           DESCRIPTION
                        "A parameter indicating the threshold value for 24-hour PCV counter."
     ::= { adTa5kDs3PMDayThresholdEntry 6 }

adTa5kDs3PMDayThresholdLES OBJECT-TYPE
           SYNTAX       Integer32
           MAX-ACCESS   read-write
           STATUS       current
           DESCRIPTION
                        "A parameter indicating the threshold value for 24-hour LES counter."
     ::= { adTa5kDs3PMDayThresholdEntry 7 }

adTa5kDs3PMDayThresholdCCV OBJECT-TYPE
           SYNTAX       Integer32
           MAX-ACCESS   read-write
           STATUS       current
           DESCRIPTION
                        "A parameter indicating the threshold value for 24-hour CCV counter."
     ::= { adTa5kDs3PMDayThresholdEntry 8 }

adTa5kDs3PMDayThresholdCES OBJECT-TYPE
           SYNTAX       Integer32
           MAX-ACCESS   read-write
           STATUS       current
           DESCRIPTION
                        "A parameter indicating the threshold value for 24-hour CES counter."
     ::= { adTa5kDs3PMDayThresholdEntry 9 }

adTa5kDs3PMDayThresholdCSES OBJECT-TYPE
           SYNTAX       Integer32
           MAX-ACCESS   read-write
           STATUS       current
           DESCRIPTION
                        "A parameter indicating the threshold value for 24-hour CES counter."
     ::= { adTa5kDs3PMDayThresholdEntry 10 }


-- -------------------------------------
-- DS3 Alarms
-- -------------------------------------

adTA5kds3LOSTrapActive  NOTIFICATION-TYPE
        OBJECTS {
                	adTrapInformSeqNum,
                	sysName,
                	adGenSlotInfoIndex,
                	adGenPortInfoIndex
        		}
        STATUS		current
        DESCRIPTION
                "Indicates DS3 framer LOS Active."
        --#TYPE         "Loss of Signal Alarm"
        --#SUMMARY      "DS3 < >: Loss of Signal Alarm "
        --#SUMMARY      "detected on shelf: %s, slot: %d, %s"
        --#ARGUMENTS    "{1,2,3}
        --#SEVERITY     MAJOR
        --#GENERIC      6
        --#CATEGORY     "Error events"
        --#Source_ID    "A"
        --#TIMEINDEX    "0"
        ::= {adTA5kds3Traps 1}

adTA5kds3LOSTrapClear  NOTIFICATION-TYPE
        OBJECTS {
                	adTrapInformSeqNum,
                	sysName,
                	adGenSlotInfoIndex,
                        adGenPortTrapIdentifier,
                	adGenPortInfoIndex
        		}
        STATUS		current
        DESCRIPTION
                "Indicates DS3 framer LOS clear."
        --#TYPE         "Loss of Signal Alarm"
        --#SUMMARY      "DS3 < >: Loss of Signal Alarm "
        --#SUMMARY      "cleared on shelf: %s, slot: %d, %s"
        --#ARGUMENTS    "{1,2,3}
        --#SEVERITY     MAJOR
        --#GENERIC      6
        --#CATEGORY     "Error events"
        --#Source_ID    "A"
        --#TIMEINDEX    "0"
        ::= {adTA5kds3Traps 2}

adTA5kds3LOFTrapActive  NOTIFICATION-TYPE
        OBJECTS {
                	adTrapInformSeqNum,
                	sysName,
                	adGenSlotInfoIndex,
                	adGenPortInfoIndex
        		}
        STATUS		current
        DESCRIPTION
                "Indicates DS3 framer LOF Alarm Active."
        --#TYPE         "Loss of Frame Alarm"
        --#SUMMARY      "DS3 < >: Loss of Frame Alarm "
        --#SUMMARY      "detected on shelf: %s, slot: %d, %s"
        --#ARGUMENTS    "{1,2,3}
        --#SEVERITY     MAJOR
        --#GENERIC      6
        --#CATEGORY     "Error events"
        --#Source_ID    "A"
        --#TIMEINDEX    "0"
        ::= {adTA5kds3Traps 3}

adTA5kds3LOFTrapClear  NOTIFICATION-TYPE
        OBJECTS {
        			adTrapInformSeqNum,
                	sysName,
                	adGenSlotInfoIndex,
                	adGenPortInfoIndex
        		}
        STATUS		current
        DESCRIPTION
                "Indicates DS3 framer LOF Alarm Clear."
        --#TYPE         "Loss of Frame Alarm"
        --#SUMMARY      "DS3 < >: Loss of Frame Alarm "
        --#SUMMARY      "cleared on shelf: %s, slot: %d, %s"
        --#ARGUMENTS    "{1,2,3}
        --#SEVERITY     MAJOR
        --#GENERIC      6
        --#CATEGORY     "Error events"
        --#Source_ID    "A"
        --#TIMEINDEX    "0"
        ::= {adTA5kds3Traps 4}

adTA5kds3RAITrapActive  NOTIFICATION-TYPE
        OBJECTS {
                	adTrapInformSeqNum,
                	sysName,
                	adGenSlotInfoIndex,
                	adGenPortInfoIndex
        		}
        STATUS		current
        DESCRIPTION
                "Indicates RAI Alarm Active."
        --#TYPE         "Rx RAI Alarm"
        --#SUMMARY      "DS3 < >: Rx RAI Alarm "
        --#SUMMARY      "detected on shelf: %s, slot: %d, %s"
        --#ARGUMENTS    "{1,2,3}
        --#SEVERITY     MINOR
        --#GENERIC      6
        --#CATEGORY     "Error events"
        --#Source_ID    "A"
        --#TIMEINDEX    "0"
        ::= {adTA5kds3Traps 5}

adTA5kds3RAITrapClear  NOTIFICATION-TYPE
        OBJECTS {
               		adTrapInformSeqNum,
                	sysName,
                	adGenSlotInfoIndex,
                	adGenPortInfoIndex
        		}
        STATUS		current
        DESCRIPTION
                "Indicates DS3 framer RAI clear."
        --#TYPE         "Rx RAI Alarm"
        --#SUMMARY      "DS3 < >: Rx RAI Alarm "
        --#SUMMARY      "cleared on shelf: %s, slot: %d, %s"
        --#ARGUMENTS    "{1,2,3}
        --#SEVERITY     MINOR
        --#GENERIC      6
        --#CATEGORY     "Error events"
        --#Source_ID    "A"
        --#TIMEINDEX    "0"
        ::= {adTA5kds3Traps 6}

adTA5kds3AISTrapActive  NOTIFICATION-TYPE
        OBJECTS {
                	adTrapInformSeqNum,
                	sysName,
                	adGenSlotInfoIndex,
                	adGenPortInfoIndex
        		}
        STATUS		current
        DESCRIPTION
                "Indicates AIS Alarm Active."
        --#TYPE         "Rx AIS Alarm"
        --#SUMMARY      "DS3 < >: Rx AIS Alarm "
        --#SUMMARY      "detected on shelf: %s, slot: %d, %s"
        --#ARGUMENTS    "{1,2,3}
        --#SEVERITY     MAJOR
        --#GENERIC      6
        --#CATEGORY     "Error events"
        --#Source_ID    "A"
        --#TIMEINDEX    "0"
        ::= {adTA5kds3Traps 7}

adTA5kds3AISTrapClear  NOTIFICATION-TYPE
        OBJECTS {
                	adTrapInformSeqNum,
                	sysName,
                	adGenSlotInfoIndex,
                	adGenPortInfoIndex
        		}
		STATUS		current
        DESCRIPTION
                "Indicates DS3 framer AIS clear."
        --#TYPE         "Rx AIS Alarm"
        --#SUMMARY      "DS3 < >: Rx AIS Alarm "
        --#SUMMARY      "cleared on shelf: %s, slot: %d, %s"
        --#ARGUMENTS    "{1,2,3}
        --#SEVERITY     MAJOR
        --#GENERIC      6
        --#CATEGORY     "Error events"
        --#Source_ID    "A"
        --#TIMEINDEX    "0"
        ::= {adTA5kds3Traps 8}

-- *******************************************
-- DS3 15-Minute PM Threshold Crossing Alarms
-- *******************************************

adTA5kds3almQtrPESThresholdCrossed  NOTIFICATION-TYPE
		OBJECTS	{
	        		adTrapInformSeqNum,
	        		sysName,
	        		adGenSlotInfoIndex,
	        		adGenPortTrapIdentifier
	        	}
	    STATUS		current
	    DESCRIPTION
	    	"Indicates the Quarter-Hour PES threshold has been exceeded."
	    --#TYPE			"Status - Threshold Exceeded"
        --#SUMMARY      "DS3 1: QTR PES Threshold Exceeded"
	    --#SUMMARY  	"shelf: %s, slot: %d, %s"
	    --#ARGUMENTS 	"{1,2,3}
            --#SEVERITY         WARNING
	    --#GENERIC  	6
	    --#CATEGORY  	"Status events"
	    --#Source_ID    "A"
	    --#TIMEINDEX    "0"
	    ::= {adTA5kds3Traps 9}

adTA5kds3almQtrPSESThresholdCrossed  NOTIFICATION-TYPE
		OBJECTS	{
	        		adTrapInformSeqNum,
	        		sysName,
	        		adGenSlotInfoIndex,
	        		adGenPortTrapIdentifier
	        	}
	    STATUS		current
	    DESCRIPTION
	    	"Indicates the Quarter-Hour PSES threshold has been exceeded."
	    --#TYPE			"Status - Threshold Exceeded"
        --#SUMMARY      "DS3 < >: QTR PSES Threshold Exceeded"
	    --#SUMMARY  	"shelf: %s, slot: %d, %s"
	    --#ARGUMENTS 	"{1,2,3}
            --#SEVERITY         WARNING
	    --#GENERIC  	6
	    --#CATEGORY  	"Status events"
	    --#Source_ID    "A"
	    --#TIMEINDEX    "0"
	    ::= {adTA5kds3Traps 10}

adTA5kds3almQtrSEFSThresholdCrossed  NOTIFICATION-TYPE
		OBJECTS	{
	        		adTrapInformSeqNum,
	        		sysName,
	        		adGenSlotInfoIndex,
	        		adGenPortTrapIdentifier
	        	}
	    STATUS		current
	    DESCRIPTION
	    	"Indicates the Quarter-Hour SEFS threshold has been exceeded."
	    --#TYPE			"Status - Threshold Exceeded"
        --#SUMMARY      "DS3 < >: QTR SEFS Threshold Exceeded"
	    --#SUMMARY  	"shelf: %s, slot: %d, %s"
	    --#ARGUMENTS 	"{1,2,3}
            --#SEVERITY         WARNING
	    --#GENERIC  	6
	    --#CATEGORY  	"Status events"
	    --#Source_ID    "A"
	    --#TIMEINDEX    "0"
	    ::= {adTA5kds3Traps 11}

adTA5kds3almQtrUASThresholdCrossed  NOTIFICATION-TYPE
		OBJECTS	{
	        		adTrapInformSeqNum,
	        		sysName,
	        		adGenSlotInfoIndex,
	        		adGenPortTrapIdentifier
	        }
	    STATUS		current
	    DESCRIPTION
	    	"Indicates the Quarter-Hour UAS threshold has been exceeded."
	    --#TYPE			"Status - Threshold Exceeded"
        --#SUMMARY      "DS3 < >: QTR UAS Threshold Exceeded"
	    --#SUMMARY  	"shelf: %s, slot: %d, %s"
	    --#ARGUMENTS 	"{1,2,3}
            --#SEVERITY         WARNING
	    --#GENERIC  	6
	    --#CATEGORY  	"Status events"
	    --#Source_ID    "A"
	    --#TIMEINDEX    "0"
	    ::= {adTA5kds3Traps 12}

adTA5kds3almQtrLCVThresholdCrossed  NOTIFICATION-TYPE
		OBJECTS	{
	        		adTrapInformSeqNum,
	        		sysName,
	        		adGenSlotInfoIndex,
	        		adGenPortTrapIdentifier
	        	}
		STATUS		current
	    DESCRIPTION
	    	"Indicates the Quarter-Hour LCV threshold has been exceeded."
	    --#TYPE			"Status - Threshold Exceeded"
        --#SUMMARY      "DS3 < >: QTR LCV Threshold Exceeded"
	    --#SUMMARY  	"shelf: %s, slot: %d, %s"
	    --#ARGUMENTS 	"{1,2,3}
            --#SEVERITY         WARNING
	    --#GENERIC  	6
	    --#CATEGORY  	"Status events"
	    --#Source_ID    "A"
	    --#TIMEINDEX    "0"
	    ::= {adTA5kds3Traps 13}

adTA5kds3almQtrPCVThresholdCrossed  NOTIFICATION-TYPE
		OBJECTS	{
	        		adTrapInformSeqNum,
	        		sysName,
	        		adGenSlotInfoIndex,
	        		adGenPortTrapIdentifier
	        	}
	    STATUS		current
	    DESCRIPTION
	    	"Indicates the Quarter-Hour PCV threshold has been exceeded."
	    --#TYPE			"Status - Threshold Exceeded"
        --#SUMMARY      "DS3 < >: QTR PCV Threshold Exceeded"
	    --#SUMMARY  	"shelf: %s, slot: %d, %s"
	    --#ARGUMENTS 	"{1,2,3}
            --#SEVERITY         WARNING
	    --#GENERIC  	6
	    --#CATEGORY  	"Status events"
	    --#Source_ID    "A"
	    --#TIMEINDEX    "0"
	    ::= {adTA5kds3Traps 14}

adTA5kds3almQtrLESThresholdCrossed  NOTIFICATION-TYPE
		OBJECTS	{
	        		adTrapInformSeqNum,
	        		sysName,
	        		adGenSlotInfoIndex,
	        		adGenPortTrapIdentifier
	        	}
	    STATUS		current
	    DESCRIPTION
	    	"Indicates the Quarter-Hour LES threshold has been exceeded."
	    --#TYPE			"Status - Threshold Exceeded"
        --#SUMMARY      "DS3 < >: QTR LES Threshold Exceeded"
	    --#SUMMARY  	"shelf: %s, slot: %d, %s"
	    --#ARGUMENTS 	"{1,2,3}
            --#SEVERITY         WARNING
	    --#GENERIC  	6
	    --#CATEGORY  	"Status events"
	    --#Source_ID    "A"
	    --#TIMEINDEX    "0"
	    ::= {adTA5kds3Traps 15}

adTA5kds3almQtrCCVThresholdCrossed  NOTIFICATION-TYPE
		OBJECTS	{
	        		adTrapInformSeqNum,
	        		sysName,
	        		adGenSlotInfoIndex,
	        		adGenPortTrapIdentifier
	        	}
	    STATUS		current
	    DESCRIPTION
	    	"Indicates the Quarter-Hour CCV threshold has been exceeded."
	    --#TYPE			"Status - Threshold Exceeded"
        --#SUMMARY      "DS3 < >: QTR CCV Threshold Exceeded"
	    --#SUMMARY  	"shelf: %s, slot: %d, %s"
	    --#ARGUMENTS 	"{1,2,3}
            --#SEVERITY         WARNING
	    --#GENERIC  	6
	    --#CATEGORY  	"Status events"
	    --#Source_ID    "A"
	    --#TIMEINDEX    "0"
	    ::= {adTA5kds3Traps 16}

adTA5kds3almQtrCESThresholdCrossed  NOTIFICATION-TYPE
		OBJECTS	{
	        		adTrapInformSeqNum,
	        		sysName,
	        		adGenSlotInfoIndex,
	        		adGenPortTrapIdentifier
	        	}
	    STATUS		current
	    DESCRIPTION
	    	"Indicates the Quarter-Hour CES threshold has been exceeded."
	    --#TYPE			"Status - Threshold Exceeded"
        --#SUMMARY      "DS3 < >: QTR CES Threshold Exceeded"
	    --#SUMMARY  	"shelf: %s, slot: %d, %s"
	    --#ARGUMENTS 	"{1,2,3}
            --#SEVERITY         WARNING
	    --#GENERIC  	6
	    --#CATEGORY  	"Status events"
	    --#Source_ID    "A"
	    --#TIMEINDEX    "0"
	    ::= {adTA5kds3Traps 17}

adTA5kds3almQtrCSESThresholdCrossed  NOTIFICATION-TYPE
		OBJECTS	{
	        		adTrapInformSeqNum,
	        		sysName,
	        		adGenSlotInfoIndex,
	        		adGenPortTrapIdentifier
	        	}
	    STATUS		current
	    DESCRIPTION
	    	"Indicates the Quarter-Hour CSES threshold has been exceeded."
	    --#TYPE			"Status - Threshold Exceeded"
        --#SUMMARY      "DS3 < >: QTR CES Threshold Exceeded"
	    --#SUMMARY  	"shelf: %s, slot: %d, %s"
	    --#ARGUMENTS 	"{1,2,3}
            --#SEVERITY         WARNING
	    --#GENERIC  	6
	    --#CATEGORY  	"Status events"
	    --#Source_ID    "A"
	    --#TIMEINDEX    "0"
	    ::= {adTA5kds3Traps 18}

-- ********************************************************************
--                 DS3 PM Daily Threshold Crossing Alarms
-- ********************************************************************

adTA5kds3PMDayPESThresholdCrossed  NOTIFICATION-TYPE
		OBJECTS	{
	        		adTrapInformSeqNum,
	        		sysName,
	        		adGenSlotInfoIndex,
	        		adGenPortTrapIdentifier
	        	}
	    STATUS		current
	    DESCRIPTION
	    	"Indicates the Quarter-Hour PES threshold has been exceeded."
	    --#TYPE			"Status - Threshold Exceeded"
        --#SUMMARY      "DS3 1: QTR PES Threshold Exceeded"
	    --#SUMMARY  	"shelf: %s, slot: %d, %s"
	    --#ARGUMENTS 	"{1,2,3}
            --#SEVERITY         WARNING
	    --#GENERIC  	6
	    --#CATEGORY  	"Status events"
	    --#Source_ID    "A"
	    --#TIMEINDEX    "0"
	    ::= {adTA5kds3Traps 19}

adTA5kds3PMDayPSESThresholdCrossed  NOTIFICATION-TYPE
		OBJECTS	{
	        		adTrapInformSeqNum,
	        		sysName,
	        		adGenSlotInfoIndex,
	        		adGenPortTrapIdentifier
	        	}
	    STATUS		current
	    DESCRIPTION
	    	"Indicates the Quarter-Hour PES threshold has been exceeded."
	    --#TYPE			"Status - Threshold Exceeded"
        --#SUMMARY      "DS3 1: QTR PES Threshold Exceeded"
	    --#SUMMARY  	"shelf: %s, slot: %d, %s"
	    --#ARGUMENTS 	"{1,2,3}
            --#SEVERITY         WARNING
	    --#GENERIC  	6
	    --#CATEGORY  	"Status events"
	    --#Source_ID    "A"
	    --#TIMEINDEX    "0"
	    ::= {adTA5kds3Traps 20}

adTA5kds3PMDaySEFSThresholdCrossed  NOTIFICATION-TYPE
		OBJECTS	{
	        		adTrapInformSeqNum,
	        		sysName,
	        		adGenSlotInfoIndex,
	        		adGenPortTrapIdentifier
	        	}
	    STATUS		current
	    DESCRIPTION
	    	"Indicates the Quarter-Hour PES threshold has been exceeded."
	    --#TYPE			"Status - Threshold Exceeded"
        --#SUMMARY      "DS3 1: QTR PES Threshold Exceeded"
	    --#SUMMARY  	"shelf: %s, slot: %d, %s"
	    --#ARGUMENTS 	"{1,2,3}
            --#SEVERITY         WARNING
	    --#GENERIC  	6
	    --#CATEGORY  	"Status events"
	    --#Source_ID    "A"
	    --#TIMEINDEX    "0"
	    ::= {adTA5kds3Traps 21}

adTA5kds3PMDayUASThresholdCrossed  NOTIFICATION-TYPE
		OBJECTS	{
	        		adTrapInformSeqNum,
	        		sysName,
	        		adGenSlotInfoIndex,
	        		adGenPortTrapIdentifier
	        	}
	    STATUS		current
	    DESCRIPTION
	    	"Indicates the Quarter-Hour PES threshold has been exceeded."
	    --#TYPE			"Status - Threshold Exceeded"
        --#SUMMARY      "DS3 1: QTR PES Threshold Exceeded"
	    --#SUMMARY  	"shelf: %s, slot: %d, %s"
	    --#ARGUMENTS 	"{1,2,3}
            --#SEVERITY         WARNING
	    --#GENERIC  	6
	    --#CATEGORY  	"Status events"
	    --#Source_ID    "A"
	    --#TIMEINDEX    "0"
	    ::= {adTA5kds3Traps 22}

adTA5kds3PMDayLCVThresholdCrossed  NOTIFICATION-TYPE
		OBJECTS	{
	        		adTrapInformSeqNum,
	        		sysName,
	        		adGenSlotInfoIndex,
	        		adGenPortTrapIdentifier
	        	}
	    STATUS		current
	    DESCRIPTION
	    	"Indicates the Quarter-Hour PES threshold has been exceeded."
	    --#TYPE			"Status - Threshold Exceeded"
        --#SUMMARY      "DS3 1: QTR PES Threshold Exceeded"
	    --#SUMMARY  	"shelf: %s, slot: %d, %s"
	    --#ARGUMENTS 	"{1,2,3}
            --#SEVERITY         WARNING
	    --#GENERIC  	6
	    --#CATEGORY  	"Status events"
	    --#Source_ID    "A"
	    --#TIMEINDEX    "0"
	    ::= {adTA5kds3Traps 23}

adTA5kds3PMDayPCVThresholdCrossed  NOTIFICATION-TYPE
		OBJECTS	{
	        		adTrapInformSeqNum,
	        		sysName,
	        		adGenSlotInfoIndex,
	        		adGenPortTrapIdentifier
	        	}
	    STATUS		current
	    DESCRIPTION
	    	"Indicates the Quarter-Hour PES threshold has been exceeded."
	    --#TYPE			"Status - Threshold Exceeded"
        --#SUMMARY      "DS3 1: QTR PES Threshold Exceeded"
	    --#SUMMARY  	"shelf: %s, slot: %d, %s"
	    --#ARGUMENTS 	"{1,2,3}
            --#SEVERITY         WARNING
	    --#GENERIC  	6
	    --#CATEGORY  	"Status events"
	    --#Source_ID    "A"
	    --#TIMEINDEX    "0"
	    ::= {adTA5kds3Traps 24}

adTA5kds3PMDayLESThresholdCrossed  NOTIFICATION-TYPE
		OBJECTS	{
	        		adTrapInformSeqNum,
	        		sysName,
	        		adGenSlotInfoIndex,
	        		adGenPortTrapIdentifier
	        	}
	    STATUS		current
	    DESCRIPTION
	    	"Indicates the Quarter-Hour PES threshold has been exceeded."
	    --#TYPE			"Status - Threshold Exceeded"
        --#SUMMARY      "DS3 1: QTR PES Threshold Exceeded"
	    --#SUMMARY  	"shelf: %s, slot: %d, %s"
	    --#ARGUMENTS 	"{1,2,3}
            --#SEVERITY         WARNING
	    --#GENERIC  	6
	    --#CATEGORY  	"Status events"
	    --#Source_ID    "A"
	    --#TIMEINDEX    "0"
	    ::= {adTA5kds3Traps 25}

adTA5kds3PMDayCCVThresholdCrossed  NOTIFICATION-TYPE
		OBJECTS	{
	        		adTrapInformSeqNum,
	        		sysName,
	        		adGenSlotInfoIndex,
	        		adGenPortTrapIdentifier
	        	}
	    STATUS		current
	    DESCRIPTION
	    	"Indicates the Quarter-Hour PES threshold has been exceeded."
	    --#TYPE			"Status - Threshold Exceeded"
        --#SUMMARY      "DS3 1: QTR PES Threshold Exceeded"
	    --#SUMMARY  	"shelf: %s, slot: %d, %s"
	    --#ARGUMENTS 	"{1,2,3}
            --#SEVERITY         WARNING
	    --#GENERIC  	6
	    --#CATEGORY  	"Status events"
	    --#Source_ID    "A"
	    --#TIMEINDEX    "0"
	    ::= {adTA5kds3Traps 26}

adTA5kds3PMDayCESThresholdCrossed  NOTIFICATION-TYPE
		OBJECTS	{
	        		adTrapInformSeqNum,
	        		sysName,
	        		adGenSlotInfoIndex,
	        		adGenPortTrapIdentifier
	        	}
	    STATUS		current
	    DESCRIPTION
	    	"Indicates the Quarter-Hour PES threshold has been exceeded."
	    --#TYPE			"Status - Threshold Exceeded"
        --#SUMMARY      "DS3 1: QTR PES Threshold Exceeded"
	    --#SUMMARY  	"shelf: %s, slot: %d, %s"
	    --#ARGUMENTS 	"{1,2,3}
            --#SEVERITY         WARNING
	    --#GENERIC  	6
	    --#CATEGORY  	"Status events"
	    --#Source_ID    "A"
	    --#TIMEINDEX    "0"
	    ::= {adTA5kds3Traps 27}

adTA5kds3PMDayCSESThresholdCrossed  NOTIFICATION-TYPE
		OBJECTS	{
	        		adTrapInformSeqNum,
	        		sysName,
	        		adGenSlotInfoIndex,
	        		adGenPortTrapIdentifier
	        	}
	    STATUS		current
	    DESCRIPTION
	    	"Indicates the Quarter-Hour PES threshold has been exceeded."
	    --#TYPE			"Status - Threshold Exceeded"
        --#SUMMARY      "DS3 1: QTR PES Threshold Exceeded"
	    --#SUMMARY  	"shelf: %s, slot: %d, %s"
	    --#ARGUMENTS 	"{1,2,3}
            --#SEVERITY         WARNING
	    --#GENERIC  	6
	    --#CATEGORY  	"Status events"
	    --#Source_ID    "A"
	    --#TIMEINDEX    "0"
	    ::= {adTA5kds3Traps 28}

-- ******************************************************************************************
-- MIB Groups
-- ******************************************************************************************
adTa5kDS3PMqtrThresholdGroup	OBJECT-GROUP
	OBJECTS
	{
		adTa5kDs3PMqtrThresholdPESs,
        adTa5kDs3PMqtrThresholdPSESs,
        adTa5kDs3PMqtrThresholdSEFSs,
        adTa5kDs3PMqtrThresholdUASs,
        adTa5kDs3PMqtrThresholdLCVs,
        adTa5kDs3PMqtrThresholdPCVs,
        adTa5kDs3PMqtrThresholdLESs,
        adTa5kDs3PMqtrThresholdCCVs,
        adTa5kDs3PMqtrThresholdCESs,
        adTa5kDs3PMqtrThresholdCSESs
	}
	STATUS current
   	DESCRIPTION
     "These objects provide support for DS3 15-Min PM Threshold provisioning."
   ::= { adTA5kds3MibGroups 1 }

adTa5kDS3PMdayThresholdGroup	OBJECT-GROUP
	OBJECTS
	{
		adTa5kDs3PMDayThresholdPES,
        adTa5kDs3PMDayThresholdPSES,
        adTa5kDs3PMDayThresholdSEFS,
        adTa5kDs3PMDayThresholdUAS,
        adTa5kDs3PMDayThresholdLCV,
        adTa5kDs3PMDayThresholdPCV,
        adTa5kDs3PMDayThresholdLES,
        adTa5kDs3PMDayThresholdCCV,
        adTa5kDs3PMDayThresholdCES,
        adTa5kDs3PMDayThresholdCSES
	}
	STATUS current
   	DESCRIPTION
     "These objects provide support for DS3 24-Hr PM Threshold provisioning."
   ::= { adTA5kds3MibGroups 2 }

adTa5kDS3EventGroup	NOTIFICATION-GROUP
	NOTIFICATIONS
	{
		adTA5kds3LOSTrapActive,
		adTA5kds3LOSTrapClear,
		adTA5kds3LOFTrapActive,
		adTA5kds3LOFTrapClear,
		adTA5kds3RAITrapActive,
		adTA5kds3RAITrapClear,
		adTA5kds3AISTrapActive,
		adTA5kds3AISTrapClear,
		adTA5kds3almQtrPESThresholdCrossed,
		adTA5kds3almQtrPSESThresholdCrossed,
		adTA5kds3almQtrSEFSThresholdCrossed,
		adTA5kds3almQtrUASThresholdCrossed,
		adTA5kds3almQtrLCVThresholdCrossed,
		adTA5kds3almQtrPCVThresholdCrossed,
		adTA5kds3almQtrLESThresholdCrossed,
		adTA5kds3almQtrCCVThresholdCrossed,
		adTA5kds3almQtrCESThresholdCrossed,
		adTA5kds3almQtrCSESThresholdCrossed,
		adTA5kds3PMDayPESThresholdCrossed,
		adTA5kds3PMDayPSESThresholdCrossed,
		adTA5kds3PMDaySEFSThresholdCrossed,
		adTA5kds3PMDayUASThresholdCrossed,
		adTA5kds3PMDayLCVThresholdCrossed,
		adTA5kds3PMDayPCVThresholdCrossed,
		adTA5kds3PMDayLESThresholdCrossed,
		adTA5kds3PMDayCCVThresholdCrossed,
		adTA5kds3PMDayCESThresholdCrossed,
		adTA5kds3PMDayCSESThresholdCrossed
	}
	STATUS current
   	DESCRIPTION
      "DS3 Notification Group"
   ::= { adTA5kds3MibGroups 3 }

END

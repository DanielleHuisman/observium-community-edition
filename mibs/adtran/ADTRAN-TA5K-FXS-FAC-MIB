ADTRAN-TA5K-FXS-FAC-MIB

-- TITLE:     The ADTRAN TA5000 FXS Factory MIB
-- PRODUCT:   TA5000
-- VERSION:   1.0
-- DATE:      11/09/11
-- AUTHOR:    Peter Kerr
-- STATUS:    PRELIMINARY

-- This MIB defines the object identifiers (OIDs) for use
-- during factory calibration tests involving TA5000 FXS
-- products.

-- *****************************************************************************
DEFINITIONS ::= BEGIN

IMPORTS

    OBJECT-TYPE,
    MODULE-IDENTITY
        FROM SNMPv2-SMI

    TEXTUAL-CONVENTION
        FROM SNMPv2-TC

    adTa5kFxsFac,
    adTa5kFxsFacID
        FROM ADTRAN-GENTA5K-MIB

    adGenSlotInfoIndex
        FROM ADTRAN-GENSLOT-MIB
   ;

-- *****************************************************************************

adTa5kFxsFacIdentity MODULE-IDENTITY
    LAST-UPDATED "201111090000Z"
    ORGANIZATION "Adtran, Inc."
    CONTACT-INFO
        "CND Tech Support
            Postal: ADTRAN, Inc.
                 901 Explorer Blvd.
                 Huntsville, AL  35806
            Tel: +1 800 726-8663
            Fax: +1 256 963 6217
            E-mail: support@adtran.com"
    DESCRIPTION
        "This MIB defines the object identifiers (OIDs) for use
         during factory calibration tests involving TA5000 FXS
         products."
    REVISION "201111090000Z"
        DESCRIPTION "Created"
    ::= { adTa5kFxsFacID 1 }

--==============================================================================
-- Limited THL test table
--==============================================================================

adTa5kFxsFacLimitedThlTable OBJECT-TYPE
    SYNTAX      SEQUENCE OF AdTa5kFxsFacLimitedThlEntry
    MAX-ACCESS  not-accessible
    STATUS      current
    DESCRIPTION
        "The Limited THL test is used during the factory calibration of the
         TA5000 CPOTS Module (1187160F1). It sends three tones port port towards
         the CPOTS module, which should be off-hook, and measures the resultant
         Echo Return Loss (ERL)."
    ::= { adTa5kFxsFac 1 }

adTa5kFxsFacLimitedThlEntry OBJECT-TYPE
    SYNTAX      AdTa5kFxsFacLimitedThlEntry
    MAX-ACCESS  not-accessible
    STATUS      current
    DESCRIPTION
        "..."
    INDEX { adGenSlotInfoIndex }
    ::= { adTa5kFxsFacLimitedThlTable 1 }

AdTa5kFxsFacLimitedThlEntry ::=
    SEQUENCE {
        adTa5kFxsFacLimitedThlStart                         INTEGER,
        adTa5kFxsFacLimitedThlStatus                        INTEGER,
        adTa5kFxsFacLimitedThlResults                       OCTET STRING
    }

adTa5kFxsFacLimitedThlStart     OBJECT-TYPE
    SYNTAX                      INTEGER {
                                    begin(1)
                                    }
    MAX-ACCESS                  read-write
    STATUS                      current
    DESCRIPTION
        "Used to start the test."
    ::= { adTa5kFxsFacLimitedThlEntry 1 }

adTa5kFxsFacLimitedThlStatus    OBJECT-TYPE
    SYNTAX                      INTEGER {
                                    na(1),
                                    complete(2),
                                    fault(3),
                                    running(4)
                                    }
    MAX-ACCESS                  read-only
    STATUS                      current
    DESCRIPTION
        "Use to monitor test progress:
             1 = na         Returned when test has never been run.
             2 = complete   Returned once test has completed successfully.
             3 = fault      Returned if test aborted due to a failure.
             4 = running    Returned while test is in progress."
    ::= { adTa5kFxsFacLimitedThlEntry 2 }

adTa5kFxsFacLimitedThlResults   OBJECT-TYPE
    SYNTAX                      OCTET STRING (SIZE(1..256))
    MAX-ACCESS                  read-only
    STATUS                      current
    DESCRIPTION
        "Returns a vector of 32-bit unsigned integers (split into octets
         containing the measured ERL for each port of the card under test
         in mdB units. The first uint32 is always empty. The first port
         can be found in the second unint32."
    ::= { adTa5kFxsFacLimitedThlEntry 3 }

   END

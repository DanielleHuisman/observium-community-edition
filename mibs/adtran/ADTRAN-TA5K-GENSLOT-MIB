ADTRAN-TA5K-GENSLOT-MIB   DEFINITIONS ::= BEGIN

    -- TITLE:       Generic TA5k chassis slot MIB
    -- PRODUCT:     All TA5k products
    -- VERSION:     1.0
    -- DATE:        06/07/27 (yy/mm/dd)
    -- AUTHOR:      Daniel Corley <dan.corley@adtran.com>
    -- SNMP:        SNMPv2
    -- MIB ARC:     adtran.adShared.adGenTa5k.adGenTa5kSlot


    -- HISTORY:
        -- 06/07/27 DTC - Created based on GenSlot.mib.

    -- NOTES:
        -- adGenTa5kSlotMacAddressIndex:
        -- The correspondence between a particular MAC address Index and it's intended 
        -- target interface (e.g. POTS vs. ADSL i/f) is up to the module software designer
        -- and should be documented in the module's enterprise MIB and coordinated with
        -- test engineering for ATP.

        -- adGenTa5kSlotDeviceRevision:
        -- The mapping between index number and device type is up to the card developer 
        -- and should be documented in the module's enterprise MIB so that the device
        -- revisions can be interpreted correctly. The data returned by the module should
        -- also include a descriptive device name as part of the string.
        -- For example: 'BackplaneFPGA: 0x0005' or 'VoiceDSP A: 08.05'.

    IMPORTS
        MODULE-IDENTITY,
        OBJECT-TYPE,
        Integer32
            FROM SNMPv2-SMI

        DisplayString,
        PhysAddress,
        TEXTUAL-CONVENTION
            FROM SNMPv2-TC
            
        AdPresence,
        AdProductIdentifier
            FROM ADTRAN-TC

        adGenTa5kSlot,
        adGenTa5kSlotID
            FROM ADTRAN-GENTA5K-MIB

        adGenSlotInfoIndex
            FROM ADTRAN-GENSLOT-MIB

        adGenericShelves
            FROM ADTRAN-GENCHASSIS-MIB;


-- Module ID ================================================================================================

    adGenTa5kSlotModuleIdentity         MODULE-IDENTITY
        LAST-UPDATED    "201410090000Z"
        ORGANIZATION
            "ADTRAN, Inc."
        CONTACT-INFO
            "CND Tech Support
                Postal: ADTRAN, Inc.
                        901 Explorer Blvd.
                        Huntsville, AL  35806
                        Tel: +1 800 726-8663
                        Fax: +1 256 963 6217
                        E-mail: support@adtran.com"
        DESCRIPTION
            "Total Access 5000 GenSlot MIB"
        
		REVISION "201410090000Z"
		DESCRIPTION
                            "Added the following OID: adGenTa5kSlotIOModuleID"
        
		REVISION "201310030000Z"
                DESCRIPTION "Added the following OID to the adGenTa5kSlotTable:
                             adGenTa5kSlotSwVerInstallTime (the date and time
                             that this software version was installed on the hw)"

        ::= { adGenTa5kSlotID 1 }

-- OBJECT IDENTIFIERS =======================================================================================

    adGenTa5kSlotTable                  OBJECT-TYPE
        SYNTAX          SEQUENCE OF AdGenTa5kSlotEntry
        MAX-ACCESS      not-accessible
        STATUS          current
        DESCRIPTION
            "..."
    ::= { adGenTa5kSlot 1 }

    adGenTa5kSlotEntry                  OBJECT-TYPE
        SYNTAX          AdGenTa5kSlotEntry
        MAX-ACCESS      not-accessible
        STATUS          current
        DESCRIPTION
            "..."
        INDEX { adGenSlotInfoIndex }
    ::= { adGenTa5kSlotTable 1 }

   AdGenTa5kSlotEntry ::=
        SEQUENCE {
            adGenTa5kSlotRestoreFactoryDefaults             Integer32,
            adGenTa5kSlotReboot                             Integer32,
            adGenTa5kSlotMaxMacs                            Integer32,
            adGenTa5kSlotFlashStatus                        INTEGER,
            adGenTa5kSlotSystemSwVersion                    DisplayString,
            adGenTa5kSlotBootSwVersion                      DisplayString,
            adGenTa5kSlotBootSystemSwVersion                DisplayString,
            adGenTa5kSlotDateOfManufacture                  DisplayString,
            adGenTa5kSlotSwVerInstallTime                   DisplayString,
            adGenTa5kSlotIOModuleID                         DisplayString
        }

   adGenTa5kSlotRestoreFactoryDefaults  OBJECT-TYPE
        SYNTAX          Integer32
        MAX-ACCESS      read-write
        STATUS          current
        DESCRIPTION
            "Set used to restore all parameters on the target to
             factory defaults. The values that can be set may vary
             for different factory options. The values to set and
             the effect will be card specific and documented in the
             ATP. Always returns 1 on get."
    ::= { adGenTa5kSlotEntry 1 }

   adGenTa5kSlotReboot                  OBJECT-TYPE
        SYNTAX          Integer32
        MAX-ACCESS      read-write
        STATUS          current
        DESCRIPTION
            "Setting this item to 1 will initiate a reboot on the target module. 
             Always returns 1 on get."
    ::= { adGenTa5kSlotEntry 2 }

    -- NOTE: adGenTa5kSlotMaxMacs is not included in adGenTa5kMacAddressTable
    -- because it is indexed by slot, not by slot & MAC number.
    adGenTa5kSlotMaxMacs                OBJECT-TYPE
        SYNTAX          Integer32
        MAX-ACCESS      read-only
        STATUS          current
        DESCRIPTION
            "This returns the number of MAC addresses supported by the target."
    ::= { adGenTa5kSlotEntry 3 }

    adGenTa5kSlotFlashStatus            OBJECT-TYPE
        SYNTAX  INTEGER {
             busy(1),
             idle(2)
        }
        MAX-ACCESS      read-only
        STATUS          current
        DESCRIPTION
            "This item indicates whether or not the non-volatile storage device is currently busy.
                busy(1) = The storage device is currently in a write operation or a write
                    operation is pending.
                idle(2) = The storage device is currently idle and no writes are pending."
    ::= { adGenTa5kSlotEntry 4 }
    
    adGenTa5kSlotSystemSwVersion        OBJECT-TYPE
        SYNTAX          DisplayString
        MAX-ACCESS      read-only
        STATUS          current
        DESCRIPTION
            "The TA5000 Module Application System Software Version Number."
    ::= { adGenTa5kSlotEntry 5 }

    adGenTa5kSlotBootSwVersion          OBJECT-TYPE
        SYNTAX          DisplayString
        MAX-ACCESS      read-only
        STATUS          current
        DESCRIPTION
            "The TA5000 Module Boot Software Version Number."
    ::= { adGenTa5kSlotEntry 6 }

    adGenTa5kSlotBootSystemSwVersion    OBJECT-TYPE
        SYNTAX          DisplayString
        MAX-ACCESS      read-only
        STATUS          current
        DESCRIPTION
            "The TA5000 Module Boot System Software Version Number."
    ::= { adGenTa5kSlotEntry 7 }
    
    adGenTa5kSlotDateOfManufacture    OBJECT-TYPE
        SYNTAX          DisplayString
        MAX-ACCESS      read-only
        STATUS          current
        DESCRIPTION
            "The TA5000 Module's date of manufacture."
    ::= { adGenTa5kSlotEntry 8 }

    adGenTa5kSlotSwVerInstallTime    OBJECT-TYPE
        SYNTAX          DisplayString
        MAX-ACCESS      read-only
        STATUS          current
        DESCRIPTION
            "The install time of the current software image"
    ::= { adGenTa5kSlotEntry 9 }

    adGenTa5kSlotIOModuleID    OBJECT-TYPE
        SYNTAX         DisplayString(SIZE (0..80))
        MAX-ACCESS     read-only
        STATUS         current
        DESCRIPTION
            "Input-Output Module Part Number and Description"
    ::= { adGenTa5kSlotEntry 10}

-- MAC ADDRESS OBJECT IDENTIFIERS ===========================================================================

    adGenTa5kSlotMacAddressTable        OBJECT-TYPE
        SYNTAX          SEQUENCE OF AdGenTa5kSlotMacAddressEntry
        MAX-ACCESS      not-accessible
        STATUS          current
        DESCRIPTION
            "This table provides one row for each MAC
            address entry per slot in a TA5000 system."
    ::= { adGenTa5kSlot 2 }

    adGenTa5kSlotMacAddressEntry        OBJECT-TYPE
        SYNTAX          AdGenTa5kSlotMacAddressEntry
        MAX-ACCESS      not-accessible
        STATUS          current
        DESCRIPTION     "An entry in the adGenTa5kSlotMacAddressTable."
        INDEX           { adGenSlotInfoIndex, adGenTa5kSlotMacAddressIndex }
    ::= { adGenTa5kSlotMacAddressTable 1 }

    AdGenTa5kSlotMacAddressEntry ::=
        SEQUENCE {
            adGenTa5kSlotMacAddressIndex        Integer32,
            adGenTa5kSlotMacAddress             OCTET STRING
        }

    adGenTa5kSlotMacAddressIndex        OBJECT-TYPE
        SYNTAX          Integer32(1..255)
        MAX-ACCESS      not-accessible
        STATUS          current
        DESCRIPTION
            "TA5000 general module MAC Address index."
    ::= { adGenTa5kSlotMacAddressEntry 1 }

    -- See NOTES section for additional info on this object.
    adGenTa5kSlotMacAddress             OBJECT-TYPE
        SYNTAX          OCTET STRING (SIZE (6))
        MAX-ACCESS      read-only
        STATUS          current
        DESCRIPTION
            "Used to get all of the MAC addresses in the selected card.
             This only applies to modules that require a MAC address."
    ::= {  adGenTa5kSlotMacAddressEntry 2 }

-- DEVICE VERSION OBJECT IDENTIFIERS ========================================================================

    adGenTa5kSlotDeviceTable            OBJECT-TYPE
        SYNTAX          SEQUENCE OF AdGenTa5kSlotDeviceEntry
        MAX-ACCESS      not-accessible
        STATUS          current
        DESCRIPTION
            "This table provides one row for each device
             entry per slot in a TA5000 system."
    ::= { adGenTa5kSlot 3 }

    adGenTa5kSlotDeviceEntry            OBJECT-TYPE
        SYNTAX          AdGenTa5kSlotDeviceEntry
        MAX-ACCESS      not-accessible
        STATUS          current
        DESCRIPTION     "An entry in the adGenTa5kSlotDeviceTable."
        INDEX           { adGenSlotInfoIndex, adGenTa5kSlotDeviceIndex }
    ::= { adGenTa5kSlotDeviceTable 1 }

    AdGenTa5kSlotDeviceEntry ::=
        SEQUENCE {
            adGenTa5kSlotDeviceIndex            Integer32,
            adGenTa5kSlotDeviceDesc             DisplayString,
            adGenTa5kSlotDeviceRevision         DisplayString
        }

    adGenTa5kSlotDeviceIndex            OBJECT-TYPE
        SYNTAX          Integer32(1..255)
        MAX-ACCESS      not-accessible
        STATUS          current
        DESCRIPTION
            "TA5000 module Device index."
    ::= { adGenTa5kSlotDeviceEntry 1 }

    
    adGenTa5kSlotDeviceDesc             OBJECT-TYPE
        SYNTAX          DisplayString
        MAX-ACCESS      read-only
        STATUS          current
        DESCRIPTION
            "This item returns a string representing the device

             an FPGA, datapump, etc."
    ::= {  adGenTa5kSlotDeviceEntry 2 }

    -- See NOTES section for additional info on this object.
    adGenTa5kSlotDeviceRevision         OBJECT-TYPE
        SYNTAX          DisplayString
        MAX-ACCESS      read-only
        STATUS          current
        DESCRIPTION
            "This item returns a string representing the revision or
             version of a device embedded in the target module such as
             an FPGA, datapump, etc."
    ::= {  adGenTa5kSlotDeviceEntry 3 }

END

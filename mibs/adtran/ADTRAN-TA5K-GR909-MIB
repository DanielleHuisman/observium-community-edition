ADTRAN-TA5K-GR909-MIB  DEFINITIONS ::= BEGIN

-- TITLE:     The ADTRAN GR909 MIB
-- PRODUCT:   ADTRAN TA5K POTS PRODUCTS

-- This MIB defines the object identifier (OID) for the
-- ADTRAN GR909 MIB objects

-- The GR909 MIB defines the table for the GR-909 Loop Tests
-- 08/13/2009 och Fixed a problem that caused smicng.cmd to fail. adGenGr909BeginTest (define the INTEGER value)
-- DO NOT MAKE HISTORY COMMENTS HERE!!!! Revision history now in REVISION/DESCRIPTION clauses below
-- ******************************************************************************************

    IMPORTS
           MODULE-IDENTITY, OBJECT-TYPE, Integer32
                FROM SNMPv2-SMI
           DisplayString
                FROM SNMPv2-TC
           ifIndex
                FROM IF-MIB
           adGenGr909, adGenGr909ID
                FROM ADTRAN-GENTA5K-MIB
           ;

      adGenGr909MIB MODULE-IDENTITY
        LAST-UPDATED "201202030832Z"
        ORGANIZATION
            "ADTRAN, Inc."
        CONTACT-INFO
            "CND Tech Support
                Postal: ADTRAN, Inc.
                        901 Explorer Blvd.
                        Huntsville, AL  35806
                        Tel: +1 800 726-8663
                        Fax: +1 256 963 6217
                        E-mail: support@adtran.com"   

        DESCRIPTION
            "Generic GR909 MIB"
                         
        REVISION "201203070000Z"
        DESCRIPTION "PSK - Corrected a missing enum value in adGenGr909IdleNoiseResult OID"

        REVISION "201202030832Z"
        DESCRIPTION "Added Noise and Load Coil tests."

        REVISION "200703300832Z"
        DESCRIPTION "Created"
        ::= { adGenGr909ID 1 }

-- OBJECT IDENTIFIERS

    adGenGr909Table OBJECT-TYPE
       SYNTAX  SEQUENCE OF AdGenGr909Entry
       MAX-ACCESS  not-accessible
       STATUS  current
       DESCRIPTION
            "Table of GR909  Table info."
       ::= { adGenGr909 1 }

    adGenGr909Entry OBJECT-TYPE
       SYNTAX  AdGenGr909Entry
       MAX-ACCESS  not-accessible
       STATUS  current
       DESCRIPTION
               ""
       INDEX   { ifIndex }
       ::= { adGenGr909Table 1 }

    AdGenGr909Entry ::=
       SEQUENCE {
           adGenGr909HPTResult
               INTEGER,
           adGenGr909FEMFResult
               INTEGER,
           adGenGr909RFaultResult
               INTEGER,
           adGenGr909RingerResult
               INTEGER,
           adGenGr909ROHResult
               INTEGER,
           adGenGr909FVAcTipToGndMeas
               DisplayString,
           adGenGr909FVAcRingToGndMeas
               DisplayString,
           adGenGr909FVDcTipToGndMeas
               DisplayString,
           adGenGr909FVDcRingToGndMeas
               DisplayString,
           adGenGr909FVAcTipToGndResult
               INTEGER,
           adGenGr909FVAcRingToGndResult
               INTEGER,
           adGenGr909FVDcTipToGndResult
               INTEGER,
           adGenGr909FVDcRingToGndResult
               INTEGER,
           adGenGr909LoopImpTipToRingMeas
               DisplayString,
           adGenGr909LoopImpTipToGndMeas
               DisplayString,
           adGenGr909LoopImpRingToGndMeas
               DisplayString,
           adGenGr909LoopImpTipToRingResult
               INTEGER,
           adGenGr909LoopImpTipToGndResult
               INTEGER,
           adGenGr909LoopImpRingToGndResult
               INTEGER,
           adGenGr909RingerMeas
               DisplayString,
           adGenGr909LastTestComplete
               DisplayString,
           adGenGr909LastTestAttempt
               DisplayString,
           adGenGr909LastTestResult
               INTEGER,
           adGenGr909FailureCode
               DisplayString,
           adGenGr909BeginTest
               INTEGER,
           adGenGr909LoopCapTipToRingMeas
               DisplayString,
           adGenGr909LoopCapTipToGndMeas
               DisplayString,
           adGenGr909LoopCapRingToGndMeas
               DisplayString,      
           adGenGr909IdleNoiseMeasure
               Integer32,  
           adGenGr909IdleNoiseResult               
               INTEGER,
           adGenGr909NumLoadCoils                  
               INTEGER,
           adGenGr909LoadCoilsDistance
               OCTET STRING,  
           adGenGr909LoadCoilsResult      
               INTEGER,
           adGenGr909TestFlag  
               INTEGER,           
           adGenGr909TestCapFlag
               INTEGER,           
           adGenGr909TestNoiseFlag
               INTEGER,           
           adGenGr909TestLoadCoilFlag               
               INTEGER            
       }

    adGenGr909HPTResult               OBJECT-TYPE
        SYNTAX  INTEGER {
             pass(1),
             fail(2),
             na(3)
        }
        MAX-ACCESS  read-only
        STATUS  current
        DESCRIPTION
            "This item indicates the result for the HPT test.
             Pass(1) = The HPT test Passed.
             Fail(2) = The HPT test failed.
             N/A(3) = The HPT test result is not ready."
        ::= { adGenGr909Entry 1 }

    adGenGr909FEMFResult              OBJECT-TYPE
        SYNTAX  INTEGER {
             pass(1),
             fail(2),
             na(3)
        }
        MAX-ACCESS  read-only
        STATUS  current
        DESCRIPTION
            "This item indicates the result for the FEMF test.
             Pass(1) = The FEMF test Passed.
             Fail(2) = The FEMF test failed.
             N/A(3) = The FEMF test result is not ready."
        ::= { adGenGr909Entry 2 }

    adGenGr909RFaultResult            OBJECT-TYPE
        SYNTAX  INTEGER {
             pass(1),
             fail(2),
             na(3)
        }
        MAX-ACCESS  read-only
        STATUS  current
        DESCRIPTION
            "This item indicates the result for the RFault test.
             Pass(1) = The RFault test Passed.
             Fail(2) = The RFault test failed.
             N/A(3) = The RFault test result is not ready."
        ::= { adGenGr909Entry 3 }

    adGenGr909RingerResult            OBJECT-TYPE
        SYNTAX  INTEGER {
             pass(1),
             fail(2),
             na(3)
        }
        MAX-ACCESS  read-only
        STATUS  current
        DESCRIPTION
            "This item indicates the result for the Ringer test.
             Pass(1) = The Ringer test Passed.
             Fail(2) = The Ringer test failed.
             N/A(3) = The Ringer test result is not ready."
        ::= { adGenGr909Entry 4 }

    adGenGr909ROHResult               OBJECT-TYPE
        SYNTAX  INTEGER {
             pass(1),
             fail(2),
             na(3)
        }
        MAX-ACCESS  read-only
        STATUS  current
        DESCRIPTION
            "This item indicates the result for the ROH test.
             Pass(1) = The ROH test Passed.
             Fail(2) = The ROH test failed.
             N/A(3) = The ROH test result is not ready."
        ::= { adGenGr909Entry 5 }

    adGenGr909FVAcTipToGndMeas        OBJECT-TYPE
        SYNTAX  DisplayString
        MAX-ACCESS  read-only
        STATUS  current
        DESCRIPTION
            "The value for the Foreign Voltage AC
             Tip to Ground measurement."
        ::= { adGenGr909Entry 6 }

    adGenGr909FVAcRingToGndMeas       OBJECT-TYPE
        SYNTAX  DisplayString
        MAX-ACCESS  read-only
        STATUS  current
        DESCRIPTION
            "The value for the Foreign Voltage AC
             Ring to Ground measurement."
        ::= { adGenGr909Entry 7 }

    adGenGr909FVDcTipToGndMeas        OBJECT-TYPE
        SYNTAX  DisplayString
        MAX-ACCESS  read-only
        STATUS  current
        DESCRIPTION
            "The value for the Foreign Voltage DC
             Tip to Ground measurement."
        ::= { adGenGr909Entry 8 }

    adGenGr909FVDcRingToGndMeas       OBJECT-TYPE
        SYNTAX  DisplayString
        MAX-ACCESS  read-only
        STATUS  current
        DESCRIPTION
            "The value for the Foreign Voltage DC
             Ring to Ground measurement."
        ::= { adGenGr909Entry 9 }

    adGenGr909FVAcTipToGndResult      OBJECT-TYPE
        SYNTAX  INTEGER {
             pass(1),
             fail(2)
        }
        MAX-ACCESS  read-only
        STATUS  current
        DESCRIPTION
            "The result for the Foreign Voltage AC
             Tip to Ground test."
        ::= { adGenGr909Entry 10 }

    adGenGr909FVAcRingToGndResult     OBJECT-TYPE
        SYNTAX  INTEGER {
             pass(1),
             fail(2)
        }
        MAX-ACCESS  read-only
        STATUS  current
        DESCRIPTION
            "The result for the Foreign Voltage AC
             Ring to Ground test."
        ::= { adGenGr909Entry 11 }

    adGenGr909FVDcTipToGndResult      OBJECT-TYPE
        SYNTAX  INTEGER {
             pass(1),
             fail(2)
        }
        MAX-ACCESS  read-only
        STATUS  current
        DESCRIPTION
            "The result for the Foreign Voltage DC
             Tip to Ground test."
        ::= { adGenGr909Entry 12 }

    adGenGr909FVDcRingToGndResult     OBJECT-TYPE
        SYNTAX  INTEGER {
             pass(1),
             fail(2)
        }
        MAX-ACCESS  read-only
        STATUS  current
        DESCRIPTION
            "The result for the Foreign Voltage DC
             Ring to Ground test."
        ::= { adGenGr909Entry 13 }

    adGenGr909LoopImpTipToRingMeas    OBJECT-TYPE
        SYNTAX  DisplayString
        MAX-ACCESS  read-only
        STATUS  current
        DESCRIPTION
            "The value for the Loop Impedance
             Tip to Ring measurement."
        ::= { adGenGr909Entry 14 }

    adGenGr909LoopImpTipToGndMeas     OBJECT-TYPE
        SYNTAX  DisplayString
        MAX-ACCESS  read-only
        STATUS  current
        DESCRIPTION
            "The value for the Loop Impedance
             Tip to Ground measurement."
        ::= { adGenGr909Entry 15 }

    adGenGr909LoopImpRingToGndMeas    OBJECT-TYPE
        SYNTAX  DisplayString
        MAX-ACCESS  read-only
        STATUS  current
        DESCRIPTION
            "The value for the Loop Impedance
             Ring to Ground measurement."
        ::= { adGenGr909Entry 16 }

    adGenGr909LoopImpTipToRingResult  OBJECT-TYPE
        SYNTAX  INTEGER {
             pass(1),
             fail(2)
        }
        MAX-ACCESS  read-only
        STATUS  current
        DESCRIPTION
            "The result for the Loop Impedance
             Tip to Ring test."
        ::= { adGenGr909Entry 17 }

    adGenGr909LoopImpTipToGndResult   OBJECT-TYPE
        SYNTAX  INTEGER {
             pass(1),
             fail(2)
        }
        MAX-ACCESS  read-only
        STATUS  current
        DESCRIPTION
            "The result for the Loop Impedance
             Tip to Ground test."
        ::= { adGenGr909Entry 18 }

    adGenGr909LoopImpRingToGndResult  OBJECT-TYPE
        SYNTAX  INTEGER {
             pass(1),
             fail(2)
        }
        MAX-ACCESS  read-only
        STATUS  current
        DESCRIPTION
            "The result for the Loop Impedance
             Ring to Ground test."
        ::= { adGenGr909Entry 19 }

    adGenGr909RingerMeas              OBJECT-TYPE
        SYNTAX  DisplayString
        MAX-ACCESS  read-only
        STATUS  current
        DESCRIPTION
            "The value for the Ringer measurement."
        ::= { adGenGr909Entry 20 }

    adGenGr909LastTestComplete        OBJECT-TYPE
        SYNTAX  DisplayString
        MAX-ACCESS  read-only
        STATUS  current
        DESCRIPTION
            "The last test time the GR909 test was completed."
        ::= { adGenGr909Entry 21 }

    adGenGr909LastTestAttempt         OBJECT-TYPE
        SYNTAX  DisplayString
        MAX-ACCESS  read-only
        STATUS  current
        DESCRIPTION
            "The last test time the GR909 test was completed."
        ::= { adGenGr909Entry 22 }

    adGenGr909LastTestResult          OBJECT-TYPE
        SYNTAX  INTEGER {
             na(1),
             complete(2),
             fault(3),
             running(4)
        }
        MAX-ACCESS  read-only
        STATUS  current
        DESCRIPTION
            "This item indicates the result for the last test.
             N/A(1) = The last test result is not valid.
             Complete(2) = The last test is Complete.
             Fault(3) = The last test had a fault.
             Running(4) = The test is running."
        ::= { adGenGr909Entry 23 }

    adGenGr909FailureCode             OBJECT-TYPE
        SYNTAX  DisplayString
        MAX-ACCESS  read-only
        STATUS  current
        DESCRIPTION
            "The Failure Code for the last GR909 test."
        ::= { adGenGr909Entry 24 }

    adGenGr909BeginTest               OBJECT-TYPE
        SYNTAX  INTEGER{
             begin(1)
        }

        MAX-ACCESS  read-write
        STATUS  current
        DESCRIPTION
            "Begin running the GR909 test."
        ::= { adGenGr909Entry 25 }

    adGenGr909LoopCapTipToRingMeas    OBJECT-TYPE
        SYNTAX  DisplayString
        MAX-ACCESS  read-only
        STATUS  current
        DESCRIPTION
            "The value for the Loop Capacitance
             Tip to Ring measurement."
        ::= { adGenGr909Entry 26 }

    adGenGr909LoopCapTipToGndMeas     OBJECT-TYPE
        SYNTAX  DisplayString
        MAX-ACCESS  read-only
        STATUS  current
        DESCRIPTION
            "The value for the Loop Capacitance
             Tip to Ground measurement."
        ::= { adGenGr909Entry 27 }

    adGenGr909LoopCapRingToGndMeas    OBJECT-TYPE
        SYNTAX  DisplayString
        MAX-ACCESS  read-only
        STATUS  current
        DESCRIPTION
            "The value for the Loop Capacitance
             Ring to Ground measurement."
        ::= { adGenGr909Entry 28 }

    adGenGr909IdleNoiseMeasure OBJECT-TYPE
        SYNTAX      Integer32 (0..120000)      
        UNITS       "-0.001 dBm"
        MAX-ACCESS  read-only
        STATUS      current        
        DESCRIPTION
             "Noise on the line."
        ::= { adGenGr909Entry 29 }

    adGenGr909IdleNoiseResult     OBJECT-TYPE
        SYNTAX  INTEGER {
             pass(1),
             fail(2),
             na(3)
        }
        MAX-ACCESS  read-only
        STATUS  current
        DESCRIPTION
            "The result of the noise measurement test on the line.
             pass(1) = Idle Channel Noise Measurement passed.
             fail(2) = Idle Channel Noise Measurement exceeded threshold.
             na(3) = Idle Channel Measurement results are invalid, because
                     test has never been run, was not run in last test
                     sweep, or there was a fault during test execution."
        ::= { adGenGr909Entry 30 }

    adGenGr909NumLoadCoils OBJECT-TYPE
        SYNTAX      INTEGER (0..10)
        MAX-ACCESS  read-only
        STATUS      current
        DESCRIPTION
             "Number of load coils on the line."
        ::= { adGenGr909Entry 31 }

    adGenGr909LoadCoilsDistance    OBJECT-TYPE
        SYNTAX  OCTET STRING
        MAX-ACCESS  read-only
        STATUS  current
        DESCRIPTION
            "Returns a vector of 32-bit unsigned integers (split into octets)
             containing the measured distance to each detected load coil
             in feet. 
             If no load coil is detected then the system will return 
             a NULL. If one load coil is detected, then it will return four bytes 
             that will contain the distance in feet to that load coil from the node. 
             Similarly if a second load coil is detected then eight bytes 
             will be returned with the last four bytes containing the distance
             to the second load coil from the node. Since this method allows 
             detection of up to 5 load coils, possibly 20 bytes containing the 
             distances to each of the coils from the node could be returned.
                          
             For example, a return of 0x00 00 04 1A 00 00 08 7F corresponds 
             to two load coils at distances of 1050 ft. and 2175 ft. from the node."
             
        ::= { adGenGr909Entry 32 }

    adGenGr909LoadCoilsResult    OBJECT-TYPE
        SYNTAX  INTEGER {
             valid(1),
             invalid(2)
        }
        MAX-ACCESS  read-only
        STATUS  current
        DESCRIPTION
            "This item indicates the result for the load coils test.
             Valid(1) = The load coil test results are valid.
             Invalid(2) = The load coil test results are invalid."
        ::= { adGenGr909Entry 33 }


    adGenGr909TestFlag OBJECT-TYPE
        SYNTAX      INTEGER {
             enable(1),
             disable(2)
        }
        MAX-ACCESS  read-write
        STATUS      current
        DESCRIPTION
            "Use to enable/disable the GR909 line tests."
        ::= { adGenGr909Entry 34 }


    adGenGr909TestCapFlag OBJECT-TYPE
        SYNTAX      INTEGER {
             enable(1),
             disable(2)
        }
        MAX-ACCESS  read-write
        STATUS      current
        DESCRIPTION
            "Use to enable/disable the capacitance test on the line."
        ::= { adGenGr909Entry 35 }
        

    adGenGr909TestNoiseFlag OBJECT-TYPE
        SYNTAX      INTEGER {
             enable(1),
             disable(2)
        }
        MAX-ACCESS  read-write
        STATUS      current
        DESCRIPTION
            "Use to enable/disable the noise test on the line."
        ::= { adGenGr909Entry 36 }
        
                
    adGenGr909TestLoadCoilFlag OBJECT-TYPE
        SYNTAX      INTEGER {
             enable(1),
             disable(2)
        }
        MAX-ACCESS  read-write
        STATUS      current
        DESCRIPTION
            "Use to enable/disable the load coil tests on the line."
        ::= { adGenGr909Entry 37 }
        

   END

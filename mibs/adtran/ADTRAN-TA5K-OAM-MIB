ADTRAN-TA5K-OAM-MIB

    DEFINITIONS ::= BEGIN

    -- TITLE:     The ADTRAN Total Access 5000 OAM Control
    -- PRODUCT:   1187200L1, 1187201L1, 1187210L1, 1187211L1
    -- VERSION:   1.0
    -- DATE:      Sept 5, 2007

    -- This MIB defines the object identifier (OID) for modules wishing
    -- to support ATM OAM functionality.

    -- MIBs supported:
    --   None

    -- HISTORY:
       -- 9/5/07    NRA - created
	   -- 04/23/09  jsb - Added adGenTa5kOamLBTxRequests and adGenTa5kOamLBRxResponses.
	   -- 04/24/09  joey - Changed the import of sysName from RFC1213-MIB to SNMPv2-MIB.  RFC1213 is a v1 MIB
	   --                 and you are not allowed to import from a v1 MIB into a v2 MIB.  Changed INTEGER data
	   --                 types to Unsigned32 for OIDs that do not have a specific range of values.  Added InterfaceIndex
	   --                 to the import list.  SMIC verified.
	   -- 04/24/09  joey - Changed Unsigned32 to Integer32 in the above referenced change.  Integer32 is compatible with INTEGER.
       -- 04/08/10  BCK  - Updating adGenTa5kOamLBVpi from 1..4095 to 0..4095 to allow VPI of 0 to set

    IMPORTS
        MODULE-IDENTITY, OBJECT-TYPE, Unsigned32, Integer32, Counter32, NOTIFICATION-TYPE
            FROM SNMPv2-SMI

        DisplayString, TruthValue, MacAddress
            FROM SNMPv2-TC

        ifIndex,
		InterfaceIndex
            FROM IF-MIB

        sysName
            FROM SNMPv2-MIB

		adGenPortInfoIndex
            FROM ADTRAN-GENPORT-MIB

        adGenSlotInfoIndex
            FROM ADTRAN-GENSLOT-MIB

        atmVclVpi, atmVclVci
            FROM ATM-MIB

        adGenTa5kOam, adGenTa5kOamID
            FROM ADTRAN-GENTA5K-MIB;


-- *********************************************************************************************************

    adTa5kOamModuleIdentity MODULE-IDENTITY
        LAST-UPDATED "201405050000Z"
        ORGANIZATION
            "ADTRAN, Inc."
        CONTACT-INFO
            "CND Tech Support
                Postal: ADTRAN, Inc.
                        901 Explorer Blvd.
                        Huntsville, AL  35806
                        Tel: +1 800 726-8663
                        Fax: +1 256 963 6217
                        E-mail: support@adtran.com"
        DESCRIPTION
            "Total Access 5000 OAM MIB"

        REVISION "201405050000Z"
        DESCRIPTION "Added OID adGenTa5kOamLBSendSpecifiedNumber which sends a specific number
                     of OAM loopback requests."
        ::= { adGenTa5kOamID 1 }

-- *********************************************************************************************************
    adGenTa5kOamTable OBJECT-TYPE
        SYNTAX      SEQUENCE OF AdGenTa5kOamEntry
        MAX-ACCESS  not-accessible
        STATUS      current
        DESCRIPTION
                   "Oam Control Functions"
        ::= { adGenTa5kOam 1 }

    adGenTa5kOamEntry OBJECT-TYPE
        SYNTAX  AdGenTa5kOamEntry
        MAX-ACCESS  not-accessible
        STATUS      current
        DESCRIPTION
                   "Table Entry"
        INDEX   { adGenSlotInfoIndex}
        ::= { adGenTa5kOamTable 1 }

    AdGenTa5kOamEntry ::=
        SEQUENCE {
                        adGenTa5kOamLBIfId                      InterfaceIndex,
                        adGenTa5kOamLBVpi                       INTEGER,
                        adGenTa5kOamLBVci                       INTEGER,
                        adGenTa5kOamLBType                      INTEGER,
                        adGenTa5kOamLBDestLlid                  OCTET STRING,
                        adGenTa5kOamLBSend                      Integer32,
                        adGenTa5kOamLBResetCounts               Integer32,
                        adGenTa5kOamLocalLlid                   OCTET STRING,
                        adGenTa5kOamLBTxRequests                Integer32,
                        adGenTa5kOamLBRxResponses	        Integer32,
                        adGenTa5kOamLBSendSpecifiedNumber       Integer32
                }

    adGenTa5kOamLBIfId OBJECT-TYPE
        SYNTAX          InterfaceIndex
        MAX-ACCESS      read-write
        STATUS          current
        DESCRIPTION
                "IfId on which to send an OAM Loopback"
        ::= { adGenTa5kOamEntry 1 }

    adGenTa5kOamLBVpi OBJECT-TYPE
        SYNTAX          INTEGER (0..4095)
        MAX-ACCESS      read-write
        STATUS          current
        DESCRIPTION
                "Vpi on which to send an OAM Loopback"
        ::= { adGenTa5kOamEntry 2 }

    adGenTa5kOamLBVci OBJECT-TYPE
        SYNTAX          INTEGER (1..65535)
        MAX-ACCESS      read-write
        STATUS          current
        DESCRIPTION
                "Vci on which to send an OAM Loopback"
        ::= { adGenTa5kOamEntry 3 }

    adGenTa5kOamLBType OBJECT-TYPE
        SYNTAX          INTEGER {
                            segment(1),
                            end-to-end(2)
                        }
        MAX-ACCESS      read-write
        STATUS          current
        DESCRIPTION
                "Type of OAM Loopback to generate"
        ::= { adGenTa5kOamEntry 4 }

    adGenTa5kOamLBDestLlid OBJECT-TYPE
        SYNTAX          OCTET STRING
        MAX-ACCESS      read-write
        STATUS          current
        DESCRIPTION
                "Remote LLID for OAM Loopbacks"
        ::= { adGenTa5kOamEntry 5 }

    adGenTa5kOamLBSend OBJECT-TYPE
        SYNTAX          Integer32
        MAX-ACCESS      read-write
        STATUS          current
        DESCRIPTION
                "A Set will send an OAM loopback cell now"
        ::= { adGenTa5kOamEntry 6 }

    adGenTa5kOamLBResetCounts OBJECT-TYPE
        SYNTAX          Integer32
        MAX-ACCESS      read-write
        STATUS          current
        DESCRIPTION
                "A Set will reset the OAM loopback counters on the current VC"
        ::= { adGenTa5kOamEntry 7}

    adGenTa5kOamLocalLlid OBJECT-TYPE
        SYNTAX          OCTET STRING
        MAX-ACCESS      read-write
        STATUS          current
        DESCRIPTION
                "Local LLID for OAM Loopbacks"
        ::= { adGenTa5kOamEntry 8 }

    adGenTa5kOamLBTxRequests OBJECT-TYPE
        SYNTAX          Integer32
        MAX-ACCESS      read-only
        STATUS          current
        DESCRIPTION
                "Number of OAM loopback requests transmitted"
        ::= { adGenTa5kOamEntry 9 }

    adGenTa5kOamLBRxResponses OBJECT-TYPE
        SYNTAX          Integer32
        MAX-ACCESS      read-only
        STATUS          current
        DESCRIPTION
                "Number of OAM loopback responses received"
        ::= { adGenTa5kOamEntry 10 }

    adGenTa5kOamLBSendSpecifiedNumber OBJECT-TYPE
        SYNTAX          Integer32 (1..1000000)
        MAX-ACCESS      read-write
        STATUS          current
        DESCRIPTION
                "Send the specified number of OAM loopback cells now.  This is 
                 an updated version of adGenTa5kOamLBSend that allows the user 
                 to send more than one OAM loopback request."
        DEFVAL { 1 }
        ::= { adGenTa5kOamEntry 11 }

-- *********************************************************************************************************
-- *********************************************************************************************************
END

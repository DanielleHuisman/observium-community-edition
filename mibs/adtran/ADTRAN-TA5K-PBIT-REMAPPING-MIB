ADTRAN-TA5K-PBIT-REMAPPING-MIB

    DEFINITIONS ::= BEGIN

    -- TITLE:     The ADTRAN Total Access TA5000 P-bit Remapping MIB
    -- PRODUCT:   TA5000 SMs
    -- VERSION:   1.0
    -- DATE:      February 18, 2013

    -- MIBs supported:



    IMPORTS
        MODULE-IDENTITY,
        OBJECT-TYPE,
        Integer32
            FROM SNMPv2-SMI

        RowStatus,
        DisplayString
            FROM SNMPv2-TC

        ifIndex
            FROM IF-MIB

        adTa5kPbitRemapping,
        adTa5kPbitRemappingID
            FROM ADTRAN-GENTA5K-MIB;

-- *********************************************************************************************************

    adTa5kPbitRemappingModuleIdentity MODULE-IDENTITY
        LAST-UPDATED "201302182030Z"
        ORGANIZATION
            "ADTRAN, Inc."
        CONTACT-INFO
            "CND Tech Support
                Postal: ADTRAN, Inc.
                        901 Explorer Blvd.
                        Huntsville, AL  35806
                        Tel: +1 800 726-8663
                        Fax: +1 256 963 6217
                        E-mail: support@adtran.com"
        DESCRIPTION
            "Total Access 5000 P-bit Remapping MIB"

        REVISION        "201302182030Z"
        DESCRIPTION     "Initial draft"


        ::= { adTa5kPbitRemappingID 1 }

-- OBJECT IDENTIFIERS
    adTa5kPbitRemappingProvisioning   OBJECT IDENTIFIER ::= { adTa5kPbitRemapping 1}
    adTa5kPbitRemappingStatus         OBJECT IDENTIFIER ::= { adTa5kPbitRemapping 2}

-- ******************************************************************************************
-- Provisioning Table
-- ******************************************************************************************

   adTa5kPbitRemappingTable OBJECT-TYPE
      SYNTAX  SEQUENCE OF AdTa5kPbitRemappingEntry
      MAX-ACCESS  not-accessible
      STATUS  current
      DESCRIPTION
         "The P-bit Remapping Provisioning Table."
      ::= { adTa5kPbitRemappingProvisioning 1 }

   adTa5kPbitRemappingEntry OBJECT-TYPE
      SYNTAX  AdTa5kPbitRemappingEntry
      MAX-ACCESS  not-accessible
      STATUS  current
      DESCRIPTION
         "An entry in the P-bit Remapping Table.  The first index is the ifIndex of an SM network port (type IANA_ethernet_csmacd)."
      INDEX   { ifIndex, adTa5kPbitRemappingIngressVlanID, adTa5kPbitRemappingIngressPriority }
      ::= { adTa5kPbitRemappingTable 1 }

   AdTa5kPbitRemappingEntry  ::=
      SEQUENCE {
         adTa5kPbitRemappingIngressVlanID       INTEGER,
         adTa5kPbitRemappingIngressPriority     INTEGER,
         adTa5kPbitRemappingNewPriority         INTEGER,
         adTa5kPbitRemappingRowStatus           RowStatus
      }

    adTa5kPbitRemappingIngressVlanID            OBJECT-TYPE
        SYNTAX                  INTEGER (2..4094)
        MAX-ACCESS              not-accessible
        STATUS                  current
        DESCRIPTION
            "Ingress VLAN identifier.  The system will only manipulate packets ingressing with this VLAN ID."
        ::= {adTa5kPbitRemappingEntry 1}

    adTa5kPbitRemappingIngressPriority            OBJECT-TYPE
        SYNTAX                  INTEGER (0..7)
        MAX-ACCESS              not-accessible
        STATUS                  current
        DESCRIPTION
            "Ingress priority.  The system will manipulate ingress packets tagged with this priority."
        ::= {adTa5kPbitRemappingEntry 2}

   adTa5kPbitRemappingNewPriority            OBJECT-TYPE
        SYNTAX                  INTEGER (0..7)
        MAX-ACCESS              read-create
        STATUS                  current
        DESCRIPTION
            "New priority.  For ingress packets that match the given VLAN ID and ingress priority, remap the p-bits to this new value."
        ::= {adTa5kPbitRemappingEntry 3}

   adTa5kPbitRemappingRowStatus         OBJECT-TYPE
        SYNTAX                  RowStatus
        MAX-ACCESS              read-create
        STATUS                  current
        DESCRIPTION
                "Used to add or remove rows in the adTa5kPbitRemappingTable."
        ::= {adTa5kPbitRemappingEntry 4}


-- ******************************************************************************************
-- Status
-- ******************************************************************************************

   adTa5kPbitRemappingMaxSupported         OBJECT-TYPE
        SYNTAX                  Integer32
        MAX-ACCESS              read-only
        STATUS                  current
        DESCRIPTION
                "Maximum number of rows allowed in the adTa5kPbitRemappingTable.  This value represents the
                maximum number of p-bit mappings that can be supported in the system."
        ::= {adTa5kPbitRemappingStatus 1}

   adTa5kPbitRemappingLastError         OBJECT-TYPE
        SYNTAX                  DisplayString
        MAX-ACCESS              read-only
        STATUS                  current
        DESCRIPTION
                "This string returns the last error encountered when creating a row in the adTa5kPbitRemappingTable."
        ::= {adTa5kPbitRemappingStatus 2}

   END

ADTRAN-TA5K-SingleDS3-MIB

    DEFINITIONS ::= BEGIN

    -- TITLE:     The ADTRAN Total Access TA5000 DS3 Single Port MIB
    -- PRODUCT:   1187200L1
    -- VERSION:   1.0
    -- DATE:      Dec 7, 2006

    -- This MIB Contains tables specific to the single port DS3 card

    -- MIBs supported:

    -- HISTORY:
--  12/07/2006	First Revision
--  09/20/2007  twc - Fixed SMIC compiler errors
--  12/04/2008	glf - added provisioning OIDs for severity, suppression, and enable/disable of alarms
--  05/05/2010  jb  - Changed  adSingleDs3IdleTrapClear and adSingleDs3IdleTrapActive descriptions.

    IMPORTS
        MODULE-IDENTITY,
        OBJECT-TYPE,
        NOTIFICATION-TYPE,
        Integer32,
        Gauge32
                FROM SNMPv2-SMI
        sysName
                FROM SNMPv2-MIB
        DisplayString, TruthValue
                FROM SNMPv2-TC
        OBJECT-GROUP,
        NOTIFICATION-GROUP
                FROM SNMPv2-CONF
		ifIndex
			FROM IF-MIB

        adTrapInformSeqNum
                FROM ADTRAN-GENTRAPINFORM-MIB

        adIdentity,
        adProducts,
        adMgmt
                FROM ADTRAN-MIB

        adGenSlotInfoIndex,
        adGenSlotAlarmStatus
                FROM ADTRAN-GENSLOT-MIB

        adGenPortTrapIdentifier,
		adGenPortInfoIndex
                FROM ADTRAN-GENPORT-MIB
        adTAeSCUTrapAlarmLevel
	        FROM ADTRAN-TAeSCUEXT1-MIB;

-- *********************************************************************************************************

    adTa5kSingleDs3ModuleIdentity MODULE-IDENTITY
        LAST-UPDATED "200612071652Z"
        ORGANIZATION
            "ADTRAN, Inc."
        CONTACT-INFO
            "CND Tech Support
                Postal: ADTRAN, Inc.
                        901 Explorer Blvd.
                        Huntsville, AL  35806
                        Tel: +1 800 726-8663
                        Fax: +1 256 963 6217
                        E-mail: support@adtran.com"
        DESCRIPTION
            "Total Access 5000 Single Port DS3 1187200L1 MIB"
        ::= { adIdentity 896 }

-- OBJECT IDENTIFIERS
        adTa5kSingleDs3                     OBJECT IDENTIFIER ::= { adMgmt 896 }
        adTa5kSingleDs3TrapsPrefix          OBJECT IDENTIFIER ::= { adProducts 896 }

        adTa5kSingleDS3Traps                OBJECT IDENTIFIER ::= { adTa5kSingleDs3TrapsPrefix 0 }

        adTa5kSingleDS3PortProv             OBJECT IDENTIFIER ::= { adTa5kSingleDs3 1 }
        -- { adTa5kSingleDs3 2 } is used by adTa5kDS3_ExtraPerfs.mi2
        adTa5kSingleDS3AlmProv				OBJECT IDENTIFIER ::= { adTa5kSingleDs3 3 }
        adTa5kSingleDS3MibConformance       OBJECT IDENTIFIER ::= { adTa5kSingleDs3 6 }
        adTa5kSingleDS3MibGroups            OBJECT IDENTIFIER ::= { adTa5kSingleDS3MibConformance 1 }


-- ****************************************************************************
-- DS3 Provisioning
-- ****************************************************************************

adTa5kSingleDS3PortProvTable   OBJECT-TYPE
    SYNTAX      SEQUENCE OF AdTa5kSingleDS3PortProvEntry
    MAX-ACCESS  not-accessible
    STATUS      current
    DESCRIPTION
        "This table contains provisioning information for the DS3 interface that
         was not included in the rfc2496 mib."
    ::= { adTa5kSingleDS3PortProv 1 }

adTa5kSingleDS3PortProvEntry   OBJECT-TYPE
    SYNTAX      AdTa5kSingleDS3PortProvEntry
    MAX-ACCESS  not-accessible
    STATUS      current
    DESCRIPTION
        "An entry in the adTa5kSingleDS3PortProvTable."
    INDEX       { ifIndex }
    ::= { adTa5kSingleDS3PortProvTable 1 }

AdTa5kSingleDS3PortProvEntry  ::=
    SEQUENCE
    {
        adTa5kSingleDS3PortLineType        INTEGER,
        adTa5kSingleDS3PortScrambler       INTEGER
    }

adTa5kSingleDS3PortLineType OBJECT-TYPE
        SYNTAX  INTEGER {
             dsx3other(1),
             dsx3M23(2),
             dsx3SYNTRAN(3),
             dsx3CbitParity(4),
             dsx3ClearChannel(5),
             e3other(6),
             e3Framed(7),
             e3Plcp(8),
             dsx3CbitParityPlcp(9),
             dsx3M23Plcp(10)
         }
  MAX-ACCESS  read-write
  STATUS  current
  DESCRIPTION
         "This variable indicates the variety of DS3 C-bit
         or E3 application implementing this interface. The
         type of interface affects the interpretation of
         the usage and error statistics.  The rate of DS3
         is 44.736 Mbps and E3 is 34.368 Mbps.  The
         dsx3ClearChannel value means that the C-bits are
         not used except for sending/receiving AIS. This item
         was taken from the rfc2496 MIB. There are two additional
         enumerations to support plcp on C-Bit and M23.
         The values, in sequence, describe:

         TITLE:            SPECIFICATION:
         dsx3M23            ANSI T1.107-1988 [9]
         dsx3SYNTRAN        ANSI T1.107-1988 [9]
         dsx3CbitParity     ANSI T1.107a-1990 [9a]
         dsx3ClearChannel   ANSI T1.102-1987 [8]
         e3Framed           CCITT G.751 [12]
         e3Plcp             ETSI T/NA(91)18 [13]
         dsx3CbitParityPlcp
         dsx3M23Plcp."
  ::= { adTa5kSingleDS3PortProvEntry 1 }

adTa5kSingleDS3PortScrambler OBJECT-TYPE
        SYNTAX          INTEGER { true(1), false(2) }
        MAX-ACCESS      read-write
        STATUS          current
        DESCRIPTION
    "Enable or Disable scrambling on the specified port"
        ::= { adTa5kSingleDS3PortProvEntry 2 }


-- ****************************************************************************
-- DS3 Enhanced Alarm Provisioning
-- ****************************************************************************

    adTa5kSingleDS3EnhancedAlmSlotProvTable OBJECT-TYPE
        SYNTAX  SEQUENCE OF AdTa5kSingleDS3EnhancedAlmSlotProvEntry
        MAX-ACCESS  not-accessible
        STATUS  current
        DESCRIPTION
             "The DSX3 Alarm Provisioning Table."
        ::= { adTa5kSingleDS3AlmProv 1 }

    adTa5kSingleDS3EnhancedAlmSlotProvEntry  OBJECT-TYPE
        SYNTAX  AdTa5kSingleDS3EnhancedAlmSlotProvEntry
        MAX-ACCESS  not-accessible
        STATUS  current
        DESCRIPTION
            "."
        INDEX    { adGenSlotInfoIndex }
        ::= { adTa5kSingleDS3EnhancedAlmSlotProvTable 1 }

    AdTa5kSingleDS3EnhancedAlmSlotProvEntry ::=
        SEQUENCE {
        			adSingleDs3EnhancedAlmSlotLOSSeverity			INTEGER,
        			adSingleDs3EnhancedAlmSlotLOSSuppression		INTEGER,
        			adSingleDs3EnhancedAlmSlotLOFSeverity			INTEGER,
        			adSingleDs3EnhancedAlmSlotLOFSuppression		INTEGER,
        			adSingleDs3EnhancedAlmSlotAISSeverity			INTEGER,
        			adSingleDs3EnhancedAlmSlotAISSuppression		INTEGER,
        			adSingleDs3EnhancedAlmSlotRAISeverity			INTEGER,
        			adSingleDs3EnhancedAlmSlotRAISuppression		INTEGER,
        			adSingleDS3EnhancedAlmSlotLOSEnable			TruthValue,
        			adSingleDS3EnhancedAlmSlotLOFEnable			TruthValue,
        			adSingleDS3EnhancedAlmSlotAISEnable			TruthValue,
        			adSingleDS3EnhancedAlmSlotRAIEnable			TruthValue
        }

	adSingleDs3EnhancedAlmSlotLOSSeverity OBJECT-TYPE
        SYNTAX INTEGER {
                                                info(2),
						alert(3),
						minor(4),
						major(5),
						critical(6)
                       }

    	MAX-ACCESS read-write
    	STATUS current
    	DESCRIPTION
        	"Sets the Service Affecting LOS Severity (affects all DS3 Ports)"
        DEFVAL    { major }
        ::= { adTa5kSingleDS3EnhancedAlmSlotProvEntry 1 }

        adSingleDs3EnhancedAlmSlotLOSSuppression OBJECT-TYPE
        SYNTAX INTEGER (0..3)
    	MAX-ACCESS  read-write
    	STATUS      current
    	DESCRIPTION
        	"Bit Map that Enables/Disables SNMP and TL1 LOS Alarm suppression (affects all DS3 Ports)
        	LSB Bit 0: 0 - Disable SNMP Alarm suppression, 1 - Enable SNMP Alarm suppression
        		Bit 1: 0 - Disable TL1 Alarm suppression, 1 - Enable TL1 Alarm suppression"

        DEFVAL {0}
        ::= { adTa5kSingleDS3EnhancedAlmSlotProvEntry 2 }

   	adSingleDs3EnhancedAlmSlotLOFSeverity OBJECT-TYPE
		SYNTAX INTEGER {
                        info(2),
						alert(3),
						minor(4),
						major(5),
						critical(6)
                       }

    	MAX-ACCESS      read-write
    	STATUS      current
    	DESCRIPTION
        	"Sets the Service Affecting LOF Severity (affects all DS3 Ports)"
        DEFVAL    { major }
        ::= { adTa5kSingleDS3EnhancedAlmSlotProvEntry 3 }

	adSingleDs3EnhancedAlmSlotLOFSuppression OBJECT-TYPE
		SYNTAX INTEGER (0..3)

    	MAX-ACCESS  read-write
    	STATUS      current
    	DESCRIPTION
        	"Bit Map that Enables/Disables SNMP and TL1 LOF Alarm suppression (affects all DS3 Ports)
        	LSB Bit 0: 0 - Disable SNMP Alarm suppression, 1 - Enable SNMP Alarm suppression
        		Bit 1: 0 - Disable TL1 Alarm suppression, 1 - Enable TL1 Alarm suppression"

        DEFVAL {0}
        ::= { adTa5kSingleDS3EnhancedAlmSlotProvEntry 4 }

	adSingleDs3EnhancedAlmSlotAISSeverity OBJECT-TYPE
		SYNTAX INTEGER {
                        info(2),
						alert(3),
						minor(4),
						major(5),
						critical(6)
                       }

    	MAX-ACCESS      read-write
    	STATUS      current
    	DESCRIPTION
        	"Sets the Service Affecting AIS Severity (affects all DS3 Ports)"
    	DEFVAL    { major }
        ::= { adTa5kSingleDS3EnhancedAlmSlotProvEntry 5 }

	adSingleDs3EnhancedAlmSlotAISSuppression OBJECT-TYPE
		SYNTAX INTEGER (0..3)

    	MAX-ACCESS  read-write
    	STATUS      current
    	DESCRIPTION
        	"Bit Map that Enables/Disables SNMP and TL1 AIS Alarm suppression (affects all DS3 Ports)
        	LSB Bit 0: 0 - Disable SNMP Alarm suppression, 1 - Enable SNMP Alarm suppression
        		Bit 1: 0 - Disable TL1 Alarm suppression, 1 - Enable TL1 Alarm suppression"

        DEFVAL {0}
        ::= { adTa5kSingleDS3EnhancedAlmSlotProvEntry 6 }

	adSingleDs3EnhancedAlmSlotRAISeverity OBJECT-TYPE
		SYNTAX INTEGER {
                        info(2),
						alert(3),
						minor(4),
						major(5),
						critical(6)
                       }

    	MAX-ACCESS      read-write
    	STATUS      current
    	DESCRIPTION
        	"Sets the Service Affecting RAI Severity (affects all DS3 Ports)"
    	DEFVAL    { minor }
        ::= { adTa5kSingleDS3EnhancedAlmSlotProvEntry 7 }

	adSingleDs3EnhancedAlmSlotRAISuppression OBJECT-TYPE
		SYNTAX INTEGER (0..3)

    	MAX-ACCESS  read-write
    	STATUS      current
    	DESCRIPTION
        	"Bit Map that Enables/Disables SNMP and TL1 RAI Alarm suppression (affects all DS3 Ports)
        	LSB Bit 0: 0 - Disable SNMP Alarm suppression, 1 - Enable SNMP Alarm suppression
        		Bit 1: 0 - Disable TL1 Alarm suppression, 1 - Enable TL1 Alarm suppression"

        DEFVAL {0}
        ::= { adTa5kSingleDS3EnhancedAlmSlotProvEntry 8 }

    adSingleDS3EnhancedAlmSlotLOSEnable OBJECT-TYPE
        SYNTAX TruthValue
    	MAX-ACCESS  read-write
    	STATUS      current
    	DESCRIPTION
        	"True - activates the alarm (affects all DS3 Ports)"

        DEFVAL {true}
        ::= { adTa5kSingleDS3EnhancedAlmSlotProvEntry 9 }

    adSingleDS3EnhancedAlmSlotLOFEnable OBJECT-TYPE
        SYNTAX TruthValue
    	MAX-ACCESS  read-write
    	STATUS      current
    	DESCRIPTION
        	"True - activates the alarm (affects all DS3 Ports)"

        DEFVAL {true}
        ::= { adTa5kSingleDS3EnhancedAlmSlotProvEntry 10 }

    adSingleDS3EnhancedAlmSlotAISEnable OBJECT-TYPE
        SYNTAX TruthValue
    	MAX-ACCESS  read-write
    	STATUS      current
    	DESCRIPTION
        	"True - activates the alarm (affects all DS3 Ports)"

        DEFVAL {true}
        ::= { adTa5kSingleDS3EnhancedAlmSlotProvEntry 11 }

    adSingleDS3EnhancedAlmSlotRAIEnable OBJECT-TYPE
        SYNTAX TruthValue
    	MAX-ACCESS  read-write
    	STATUS      current
    	DESCRIPTION
        	"True - activates the alarm (affects all DS3 Ports)"

        DEFVAL {true}
        ::= { adTa5kSingleDS3EnhancedAlmSlotProvEntry 12 }

-- -------------------------------------
-- Single DS3 Alarms
-- -------------------------------------
adSingleDs3LOSTrapClear  NOTIFICATION-TYPE
        OBJECTS {
                adTrapInformSeqNum,
                sysName,
                adGenSlotInfoIndex,
                adGenPortInfoIndex
        }
        STATUS  current
        DESCRIPTION
                "Indicates DS3 framer LOS clear."
        --#TYPE       "Status - LOS Alarm Clear"
        --#SUMMARY    "DS3: LOS Alarm Clear for "
        --#SUMMARY    "Shelf: %s, Slot %d, Port %d"
        --#ARGUMENTS  {1, 2, 3}
        --#SEVERITY   MAJOR
        --#GENERIC    6
        --#CATEGORY   "Error Events"
        --#SOURCE_ID  "A"
        --#TIMEINDEX  0
        ::= { adTa5kSingleDS3Traps 2 }

adSingleDs3LOSTrapActive  NOTIFICATION-TYPE
        OBJECTS {
                adTrapInformSeqNum,
                sysName,
                adGenSlotInfoIndex,
                adGenPortInfoIndex
        }
        STATUS  current
        DESCRIPTION
                "Indicates Backplane Timing Alarm Active."
        --#TYPE       "Status - LOS Alarm Active"
        --#SUMMARY    "DS3: LOS Alarm Active for "
        --#SUMMARY    "Shelf: %s, Slot %d, Port %d"
        --#ARGUMENTS  {1, 2, 3}
        --#SEVERITY   MAJOR
        --#GENERIC    6
        --#CATEGORY   "Error Events"
        --#SOURCE_ID  "A"
        --#TIMEINDEX  0
        ::= { adTa5kSingleDS3Traps 3 }

adSingleDs3LOFTrapClear  NOTIFICATION-TYPE
        OBJECTS {
                adTrapInformSeqNum,
                sysName,
                adGenSlotInfoIndex,
                adGenPortInfoIndex
        }
        STATUS  current
        DESCRIPTION
                "Indicates DS3 framer LOF Alarm Clear."
        --#TYPE       "Status - LOF Alarm Clear"
        --#SUMMARY    "DS3: LOF Alarm Clear for "
        --#SUMMARY    "Shelf: %s, Slot %d, Port %d"
        --#ARGUMENTS  {1, 2, 3}
        --#SEVERITY   MAJOR
        --#GENERIC    6
        --#CATEGORY   "Error Events"
        --#SOURCE_ID  "A"
        --#TIMEINDEX  0
        ::= { adTa5kSingleDS3Traps 4 }

adSingleDs3LOFTrapActive  NOTIFICATION-TYPE
        OBJECTS {
                adTrapInformSeqNum,
                sysName,
                adGenSlotInfoIndex,
                adGenPortInfoIndex
        }
        STATUS  current
        DESCRIPTION
                "Indicates DS3 framer LOF Alarm Active."
        --#TYPE       "Status - LOF Alarm Active"
        --#SUMMARY    "DS3: LOF Alarm Active for "
        --#SUMMARY    "Shelf: %s, Slot %d, Port %d"
        --#ARGUMENTS  {1, 2, 3}
        --#SEVERITY   MAJOR
        --#GENERIC    6
        --#CATEGORY   "Error Events"
        --#SOURCE_ID  "A"
        --#TIMEINDEX  0
        ::= { adTa5kSingleDS3Traps 5 }

adSingleDs3RAITrapClear  NOTIFICATION-TYPE
        OBJECTS {
                adTrapInformSeqNum,
                sysName,
                adGenSlotInfoIndex,
                adGenPortInfoIndex
        }
        STATUS  current
        DESCRIPTION
                "Indicates DS3 framer RAI clear."
        --#TYPE       "Status - RAI Alarm Clear"
        --#SUMMARY    "DS3: RAI Alarm Clear for "
        --#SUMMARY    "Shelf: %s, Slot %d, Port %d"
        --#ARGUMENTS  {1, 2, 3}
        --#SEVERITY   MINOR
        --#GENERIC    6
        --#CATEGORY   "Error Events"
        --#SOURCE_ID  "A"
        --#TIMEINDEX  0
        ::= { adTa5kSingleDS3Traps 6 }

adSingleDs3RAITrapActive  NOTIFICATION-TYPE
        OBJECTS {
                adTrapInformSeqNum,
                sysName,
                adGenSlotInfoIndex,
                adGenPortInfoIndex
        }
        STATUS  current
        DESCRIPTION
                "Indicates RAI Alarm Active."
        --#TYPE       "Status - RAI Alarm Active"
        --#SUMMARY    "DS3: RAI Alarm Active for "
        --#SUMMARY    "Shelf: %s, Slot %d, Port %d"
        --#ARGUMENTS  {1, 2, 3}
        --#SEVERITY   MINOR
        --#GENERIC    6
        --#CATEGORY   "Error Events"
        --#SOURCE_ID  "A"
        --#TIMEINDEX  0
        ::= { adTa5kSingleDS3Traps 7 }

adSingleDs3AISTrapClear  NOTIFICATION-TYPE
        OBJECTS {
                adTrapInformSeqNum,
                sysName,
                adGenSlotInfoIndex,
                adGenPortInfoIndex
        }
        STATUS  current
        DESCRIPTION
                "Indicates DS3 framer AIS clear."
        --#TYPE       "Status - AIS Alarm Clear"
        --#SUMMARY    "DS3: AIS Alarm Clear for "
        --#SUMMARY    "Shelf: %s, Slot %d, Port %d"
        --#ARGUMENTS  {1, 2, 3}
        --#SEVERITY   MAJOR
        --#GENERIC    6
        --#CATEGORY   "Error Events"
        --#SOURCE_ID  "A"
        --#TIMEINDEX  0
        ::= { adTa5kSingleDS3Traps 8 }

adSingleDs3AISTrapActive  NOTIFICATION-TYPE
        OBJECTS {
                adTrapInformSeqNum,
                sysName,
                adGenSlotInfoIndex,
                adGenPortInfoIndex
        }
        STATUS  current
        DESCRIPTION
                "Indicates AIS Alarm Active."
        --#TYPE       "Status - AIS Alarm Active"
        --#SUMMARY    "DS3: AIS Alarm Active for "
        --#SUMMARY    "Shelf: %s, Slot %d, Port %d"
        --#ARGUMENTS  {1, 2, 3}
        --#SEVERITY   MAJOR
        --#GENERIC    6
        --#CATEGORY   "Error Events"
        --#SOURCE_ID  "A"
        --#TIMEINDEX  0
        ::= { adTa5kSingleDS3Traps 9 }

adSingleDs3LoopTrapClear  NOTIFICATION-TYPE
        OBJECTS {
                adTrapInformSeqNum,
                sysName,
                adGenSlotInfoIndex,
                adGenPortInfoIndex
        }
        STATUS  current
        DESCRIPTION
                "Indicates DS3 loopback state clear"
        --#TYPE       "Status - loopback clear"
        --#SUMMARY    "DS3: loopback state clear for "
        --#SUMMARY    "Shelf: %s, Slot %d, Port %d"
        --#ARGUMENTS  {1, 2, 3}
        --#SEVERITY   INFO
        --#GENERIC    6
        --#CATEGORY   "Error Events"
        --#SOURCE_ID  "A"
        --#TIMEINDEX  0
        ::= { adTa5kSingleDS3Traps 10 }

adSingleDs3LoopTrapActive  NOTIFICATION-TYPE
        OBJECTS {
                adTrapInformSeqNum,
                sysName,
                adGenSlotInfoIndex,
                adGenPortInfoIndex
        }
        STATUS  current
        DESCRIPTION
                "Indicates DS3 loopback state active"
        --#TYPE       "Status - loopback active"
        --#SUMMARY    "DS3: loopback state active for "
        --#SUMMARY    "Shelf: %s, Slot %d, Port %d"
        --#ARGUMENTS  {1, 2, 3}
        --#SEVERITY   INFO
        --#GENERIC    6
        --#CATEGORY   "Error Events"
        --#SOURCE_ID  "A"
        --#TIMEINDEX  0
        ::= { adTa5kSingleDS3Traps 11 }

adSingleDs3IdleTrapClear  NOTIFICATION-TYPE
        OBJECTS {
                adTrapInformSeqNum,
                sysName,
                adGenSlotInfoIndex,
                adGenPortInfoIndex
        }
        STATUS  current
        DESCRIPTION
                "Indicates DS3 Idle signal clear"
        --#TYPE       "Status - Idle signal clear"
        --#SUMMARY    "DS3: Idle signal clear for "
        --#SUMMARY    "Shelf: %s, Slot %d, Port %d"
        --#ARGUMENTS  {1, 2, 3}
        --#SEVERITY   INFO
        --#GENERIC    6
        --#CATEGORY   "Error Events"
        --#SOURCE_ID  "A"
        --#TIMEINDEX  0
        ::= { adTa5kSingleDS3Traps 12 }

adSingleDs3IdleTrapActive  NOTIFICATION-TYPE
        OBJECTS {
                adTrapInformSeqNum,
                sysName,
                adGenSlotInfoIndex,
                adGenPortInfoIndex
        }
        STATUS  current
        DESCRIPTION
                "Indicates DS3 Idle signal active"
        --#TYPE       "Status - Idle signal active"
        --#SUMMARY    "DS3: Idle signal active for "
        --#SUMMARY    "Shelf: %s, Slot %d, Port %d"
        --#ARGUMENTS  {1, 2, 3}
        --#SEVERITY   INFO
        --#GENERIC    6
        --#CATEGORY   "Error Events"
        --#SOURCE_ID  "A"
        --#TIMEINDEX  0
        ::= { adTa5kSingleDS3Traps 13 }

-- -------------------------------------
-- Enhanced DS3 Alarms
-- -------------------------------------
adSingleDs3EnhancedLOSTrapClear  NOTIFICATION-TYPE
        OBJECTS {
                adTrapInformSeqNum,
                sysName,
                adGenSlotInfoIndex,
                adGenPortInfoIndex,
                adTAeSCUTrapAlarmLevel
        }
        STATUS  current
        DESCRIPTION
                "Indicates DS3 framer LOS clear."
        --#TYPE       "Status - LOS Alarm Clear"
        --#SUMMARY    "DS3: LOS Alarm Clear for "
        --#SUMMARY    "Shelf: %s, Slot %d, Port %d"
        --#ARGUMENTS  {1, 2, 3}
        --#SEVERITY   MAJOR
        --#GENERIC    6
        --#CATEGORY   "Error Events"
        --#SOURCE_ID  "A"
        --#TIMEINDEX  0
        ::= { adTa5kSingleDS3Traps 14 }

adSingleDs3EnhancedLOSTrapActive  NOTIFICATION-TYPE
        OBJECTS {
                adTrapInformSeqNum,
                sysName,
                adGenSlotInfoIndex,
                adGenPortInfoIndex,
                adTAeSCUTrapAlarmLevel
        }
        STATUS  current
        DESCRIPTION
                "Indicates Backplane Timing Alarm Active."
        --#TYPE       "Status - LOS Alarm Active"
        --#SUMMARY    "DS3: LOS Alarm Active for "
        --#SUMMARY    "Shelf: %s, Slot %d, Port %d"
        --#ARGUMENTS  {1, 2, 3}
        --#SEVERITY   MAJOR
        --#GENERIC    6
        --#CATEGORY   "Error Events"
        --#SOURCE_ID  "A"
        --#TIMEINDEX  0
        ::= { adTa5kSingleDS3Traps 15 }

adSingleDs3EnhancedLOFTrapClear  NOTIFICATION-TYPE
        OBJECTS {
                adTrapInformSeqNum,
                sysName,
                adGenSlotInfoIndex,
                adGenPortInfoIndex,
                adTAeSCUTrapAlarmLevel
        }
        STATUS  current
        DESCRIPTION
                "Indicates DS3 framer LOF Alarm Clear."
        --#TYPE       "Status - LOF Alarm Clear"
        --#SUMMARY    "DS3: LOF Alarm Clear for "
        --#SUMMARY    "Shelf: %s, Slot %d, Port %d"
        --#ARGUMENTS  {1, 2, 3}
        --#SEVERITY   MAJOR
        --#GENERIC    6
        --#CATEGORY   "Error Events"
        --#SOURCE_ID  "A"
        --#TIMEINDEX  0
        ::= { adTa5kSingleDS3Traps 16 }

adSingleDs3EnhancedLOFTrapActive  NOTIFICATION-TYPE
        OBJECTS {
                adTrapInformSeqNum,
                sysName,
                adGenSlotInfoIndex,
                adGenPortInfoIndex,
                adTAeSCUTrapAlarmLevel
        }
        STATUS  current
        DESCRIPTION
                "Indicates DS3 framer LOF Alarm Active."
        --#TYPE       "Status - LOF Alarm Active"
        --#SUMMARY    "DS3: LOF Alarm Active for "
        --#SUMMARY    "Shelf: %s, Slot %d, Port %d"
        --#ARGUMENTS  {1, 2, 3}
        --#SEVERITY   MAJOR
        --#GENERIC    6
        --#CATEGORY   "Error Events"
        --#SOURCE_ID  "A"
        --#TIMEINDEX  0
        ::= { adTa5kSingleDS3Traps 17 }

adSingleDs3EnhancedRAITrapClear  NOTIFICATION-TYPE
        OBJECTS {
                adTrapInformSeqNum,
                sysName,
                adGenSlotInfoIndex,
                adGenPortInfoIndex,
                adTAeSCUTrapAlarmLevel
        }
        STATUS  current
        DESCRIPTION
                "Indicates DS3 framer RAI clear."
        --#TYPE       "Status - RAI Alarm Clear"
        --#SUMMARY    "DS3: RAI Alarm Clear for "
        --#SUMMARY    "Shelf: %s, Slot %d, Port %d"
        --#ARGUMENTS  {1, 2, 3}
        --#SEVERITY   MINOR
        --#GENERIC    6
        --#CATEGORY   "Error Events"
        --#SOURCE_ID  "A"
        --#TIMEINDEX  0
        ::= { adTa5kSingleDS3Traps 18 }

adSingleDs3EnhancedRAITrapActive  NOTIFICATION-TYPE
        OBJECTS {
                adTrapInformSeqNum,
                sysName,
                adGenSlotInfoIndex,
                adGenPortInfoIndex,
                adTAeSCUTrapAlarmLevel
        }
        STATUS  current
        DESCRIPTION
                "Indicates RAI Alarm Active."
        --#TYPE       "Status - RAI Alarm Active"
        --#SUMMARY    "DS3: RAI Alarm Active for "
        --#SUMMARY    "Shelf: %s, Slot %d, Port %d"
        --#ARGUMENTS  {1, 2, 3}
        --#SEVERITY   MINOR
        --#GENERIC    6
        --#CATEGORY   "Error Events"
        --#SOURCE_ID  "A"
        --#TIMEINDEX  0
        ::= { adTa5kSingleDS3Traps 19 }

adSingleDs3EnhancedAISTrapClear  NOTIFICATION-TYPE
        OBJECTS {
                adTrapInformSeqNum,
                sysName,
                adGenSlotInfoIndex,
                adGenPortInfoIndex,
                adTAeSCUTrapAlarmLevel
        }
        STATUS  current
        DESCRIPTION
                "Indicates DS3 framer AIS clear."
        --#TYPE       "Status - AIS Alarm Clear"
        --#SUMMARY    "DS3: AIS Alarm Clear for "
        --#SUMMARY    "Shelf: %s, Slot %d, Port %d"
        --#ARGUMENTS  {1, 2, 3}
        --#SEVERITY   MAJOR
        --#GENERIC    6
        --#CATEGORY   "Error Events"
        --#SOURCE_ID  "A"
        --#TIMEINDEX  0
        ::= { adTa5kSingleDS3Traps 20 }

adSingleDs3EnhancedAISTrapActive  NOTIFICATION-TYPE
        OBJECTS {
                adTrapInformSeqNum,
                sysName,
                adGenSlotInfoIndex,
                adGenPortInfoIndex,
                adTAeSCUTrapAlarmLevel
        }
        STATUS  current
        DESCRIPTION
                "Indicates AIS Alarm Active."
        --#TYPE       "Status - AIS Alarm Active"
        --#SUMMARY    "DS3: AIS Alarm Active for "
        --#SUMMARY    "Shelf: %s, Slot %d, Port %d"
        --#ARGUMENTS  {1, 2, 3}
        --#SEVERITY   MAJOR
        --#GENERIC    6
        --#CATEGORY   "Error Events"
        --#SOURCE_ID  "A"
        --#TIMEINDEX  0
        ::= { adTa5kSingleDS3Traps 21 }

-- ******************************************************************************************
-- MIB Groups
-- ******************************************************************************************
adTa5kSingleDS3PortProvGroup OBJECT-GROUP
   OBJECTS
   {
        adTa5kSingleDS3PortLineType,
        adTa5kSingleDS3PortScrambler
   }
   STATUS current
   DESCRIPTION
     "These objects provide support for DS3 port provisioning."
   ::= { adTa5kSingleDS3MibGroups 1 }

adTa5kSingleDS3TrapGroup NOTIFICATION-GROUP
   NOTIFICATIONS
   {
        adSingleDs3LOSTrapClear,
        adSingleDs3LOSTrapActive,
        adSingleDs3LOFTrapClear,
        adSingleDs3LOFTrapActive,
        adSingleDs3RAITrapClear,
        adSingleDs3RAITrapActive,
        adSingleDs3AISTrapClear,
        adSingleDs3AISTrapActive,
        adSingleDs3LoopTrapClear,
        adSingleDs3LoopTrapActive,
        adSingleDs3IdleTrapClear,
        adSingleDs3IdleTrapActive,
        adSingleDs3EnhancedLOSTrapClear,
        adSingleDs3EnhancedLOSTrapActive,
        adSingleDs3EnhancedLOFTrapClear,
        adSingleDs3EnhancedLOFTrapActive,
        adSingleDs3EnhancedRAITrapClear,
        adSingleDs3EnhancedRAITrapActive,
        adSingleDs3EnhancedAISTrapClear,
        adSingleDs3EnhancedAISTrapActive
   }
   STATUS current
   DESCRIPTION
     "These objects provide support for traps."
   ::= { adTa5kSingleDS3MibGroups 2 }



   END

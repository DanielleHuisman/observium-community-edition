ADTRAN-TA5K-TLV-MIB

    DEFINITIONS ::= BEGIN

    -- TITLE:     The ADTRAN Total Access TA5000 Tlv MIB
    -- PRODUCT:   1187020L1, 1187800L1, 1187300L1
    -- VERSION:   1.0
    -- DATE:      April 26, 2006

    -- This MIB Contains tables specific to the TA5000 TLV structures for bulk gets
    --

    -- MIBs supported:

    -- HISTORY:
    --     04/18/06    tpm    First edition
    --     04/18/06    nra    updated to include support for BulkPM (added slot-
    --                        indexed OIDs)



    IMPORTS
        MODULE-IDENTITY,
        OBJECT-TYPE,
        Integer32
--        Counter32,
--        IpAddress
--        Gauge32,
--        Counter64,
--        TimeTicks,
--        Unsigned32,
            FROM SNMPv2-SMI

        ifIndex
--        InterfaceIndexOrZero,
--        InterfaceIndex
            FROM IF-MIB

--        DisplayString,
--        TruthValue,
--        RowStatus,
--        TimeInterval,
--        MacAddress,
--        TEXTUAL-CONVENTION
--            FROM SNMPv2-TC

--        SnmpAdminString
--            FROM SNMP-FRAMEWORK-MIB

        adIdentity,
        adIdentityShared,
        adProducts,
        adMgmt
            FROM ADTRAN-MIB

        adGenTa5kTlv,
        adGenTa5kTlvID
            FROM ADTRAN-GENTA5K-MIB

--        IANAifType
--                FROM IANAifType-MIB

		adGenPortInfoIndex
            FROM ADTRAN-GENPORT-MIB

        adGenSlotInfoIndex
            FROM ADTRAN-GENSLOT-MIB;

-- *********************************************************************************************************

    adTa5kTlvModuleIdentity MODULE-IDENTITY
        LAST-UPDATED "201209180000Z"
        ORGANIZATION
            "ADTRAN, Inc."
        CONTACT-INFO
            "CND Tech Support
                Postal: ADTRAN, Inc.
                        901 Explorer Blvd.
                        Huntsville, AL  35806
                        Tel: +1 800 726-8663
                        Fax: +1 256 963 6217
                        E-mail: support@adtran.com"
        DESCRIPTION
            "Total Access 5000 Tlv MIB"
            
        REVISION "201209180000Z"
		DESCRIPTION  "Added new OIDs to allow explicit deletion TLV instances"
		
        ::= { adGenTa5kTlvID 1 }

-- OBJECT IDENTIFIERS

    adTa5kTlvCountTable OBJECT-TYPE
       SYNTAX      SEQUENCE OF AdTa5kTlvCountEntry
       MAX-ACCESS  not-accessible
       STATUS      current
       DESCRIPTION
           "..."
       ::= { adGenTa5kTlv 1 }

    adTa5kTlvCountEntry OBJECT-TYPE
       SYNTAX      AdTa5kTlvCountEntry
       MAX-ACCESS  not-accessible
       STATUS      current
       DESCRIPTION
           ""
       INDEX { adTa5kTlvInstance }
       ::= { adTa5kTlvCountTable 1 }

   AdTa5kTlvCountEntry ::=
       SEQUENCE {
           adTa5kTlvCount        Integer32,
           adTa5kTlvInstance     Integer32,
           adTa5kTlvDelete       Integer32
       }

   adTa5kTlvCount                OBJECT-TYPE
       SYNTAX                    Integer32
       MAX-ACCESS                read-write
       STATUS                    current
       DESCRIPTION
           "The number of fragments for an instance."
       ::= { adTa5kTlvCountEntry 1 }

   adTa5kTlvInstance             OBJECT-TYPE
       SYNTAX                    Integer32
       MAX-ACCESS                not-accessible
       STATUS                    current
       DESCRIPTION
           "The instance number.  Returned by card specific MIB to create an instance."
       ::= { adTa5kTlvCountEntry 2 }

   adTa5kTlvDelete               OBJECT-TYPE
       SYNTAX                    Integer32
       MAX-ACCESS                read-write
       STATUS                    current
       DESCRIPTION
           "A set will delete TLV instance"
       ::= { adTa5kTlvCountEntry 3 }

-- *******************************************************************************

    adTa5kTlvTable OBJECT-TYPE
       SYNTAX      SEQUENCE OF AdTa5kTlvEntry
       MAX-ACCESS  not-accessible
       STATUS      current
       DESCRIPTION
           "..."
       ::= { adGenTa5kTlv 2 }

    adTa5kTlvEntry OBJECT-TYPE
       SYNTAX      AdTa5kTlvEntry
       MAX-ACCESS  not-accessible
       STATUS      current
       DESCRIPTION
           "First index is an instance, second index is the sequence number ranging from 0 to count - 1"
       INDEX { adTa5kTlvInstance, adTa5kTlvSequence }
       ::= { adTa5kTlvTable 1 }

   AdTa5kTlvEntry ::=
       SEQUENCE {
           adTa5kTlvBulk               OCTET STRING,
           adTa5kTlvSequence           Integer32
       }
   adTa5kTlvBulk                 OBJECT-TYPE
       SYNTAX                    OCTET STRING
       MAX-ACCESS                read-only
       STATUS                    current
       DESCRIPTION
           "Type Length Value Structure containing all topology data."
       ::= { adTa5kTlvEntry 1 }

   adTa5kTlvSequence             OBJECT-TYPE
       SYNTAX                    Integer32
       MAX-ACCESS                not-accessible
       STATUS                    current
       DESCRIPTION
           "Sequence number ranging from 0 to adTa5kTlvCount minus one."
       ::= { adTa5kTlvEntry 2 }


-- *******************************************************************************
-- **********      NRA - Added to support Bulk PM       **************************
-- *******************************************************************************

    adTa5kTlvBySlotCountTable OBJECT-TYPE
       SYNTAX      SEQUENCE OF AdTa5kTlvBySlotCountEntry
       MAX-ACCESS  not-accessible
       STATUS      current
       DESCRIPTION
           "..."
       ::= { adGenTa5kTlv 3 }

    adTa5kTlvBySlotCountEntry OBJECT-TYPE
       SYNTAX      AdTa5kTlvBySlotCountEntry
       MAX-ACCESS  not-accessible
       STATUS      current
       DESCRIPTION
           "Indexed on slot and instance number"
       INDEX { adGenSlotInfoIndex, adTa5kTlvBySlotInstance }
       ::= { adTa5kTlvBySlotCountTable 1 }

   AdTa5kTlvBySlotCountEntry ::=
       SEQUENCE {
           adTa5kTlvBySlotCount        Integer32,
           adTa5kTlvBySlotInstance     Integer32,
           adTa5kTlvBySlotDelete       Integer32
       }

   adTa5kTlvBySlotCount                OBJECT-TYPE
       SYNTAX                    Integer32
       MAX-ACCESS                read-write
       STATUS                    current
       DESCRIPTION
           "The number of fragments for an instance."
       ::= { adTa5kTlvBySlotCountEntry 1 }

   adTa5kTlvBySlotInstance             OBJECT-TYPE
       SYNTAX                    Integer32
       MAX-ACCESS                not-accessible
       STATUS                    current
       DESCRIPTION
           "The instance number.  Returned by card specific MIB to create an instance."
       ::= { adTa5kTlvBySlotCountEntry 2 }

   adTa5kTlvBySlotDelete               OBJECT-TYPE
       SYNTAX                    Integer32
       MAX-ACCESS                read-write
       STATUS                    current
       DESCRIPTION
           "A set will delete TLV instance."
       ::= { adTa5kTlvBySlotCountEntry 3 }

-- *******************************************************************************

    adTa5kTlvBySlotTable OBJECT-TYPE
       SYNTAX      SEQUENCE OF AdTa5kTlvBySlotEntry
       MAX-ACCESS  not-accessible
       STATUS      current
       DESCRIPTION
           "..."
       ::= { adGenTa5kTlv 4 }

    adTa5kTlvBySlotEntry OBJECT-TYPE
       SYNTAX      AdTa5kTlvBySlotEntry
       MAX-ACCESS  not-accessible
       STATUS      current
       DESCRIPTION
           "Indexes are slot, instance number, and a sequence number ranging from 0 to count - 1"
       INDEX { adGenSlotInfoIndex, adTa5kTlvBySlotInstance, adTa5kTlvBySlotSequence }
       ::= { adTa5kTlvBySlotTable 1 }

   AdTa5kTlvBySlotEntry ::=
       SEQUENCE {
           adTa5kTlvBySlotBulk               OCTET STRING,
           adTa5kTlvBySlotSequence           Integer32
       }
       
   adTa5kTlvBySlotBulk                 OBJECT-TYPE
       SYNTAX                    OCTET STRING
       MAX-ACCESS                read-only
       STATUS                    current
       DESCRIPTION
           "Type Length Value Structure containing all topology data."
       ::= { adTa5kTlvBySlotEntry 1 }

   adTa5kTlvBySlotSequence             OBJECT-TYPE
       SYNTAX                    Integer32
       MAX-ACCESS                not-accessible
       STATUS                    current
       DESCRIPTION
           "Sequence number ranging from 0 to adTa5kTlvBySlotCount minus one."
       ::= { adTa5kTlvBySlotEntry 2 }

END

ADTRAN-TACONTROLER-PRODUCT2-MIB

DEFINITIONS ::= BEGIN

     -- TITLE:       Controller Version 2 Extention System MIB
     -- PRODUCT:     TA Controllers
     -- VERSION:     1.0
     -- DATE:        2009/03/12
     -- AUTHOR:      Arthur Bill Poleon
     -- SNMP:        SNMPv2
     -- MIB ARC:     adtran.adShared.adTaControllerMgmt
     -- HISTORY:
       -- 03/12/09   SA - created

     IMPORTS
          NOTIFICATION-TYPE,
          OBJECT-TYPE,
          MODULE-IDENTITY,
          IpAddress
               FROM SNMPv2-SMI
          sysName
               FROM SNMPv2-MIB
          DateAndTime
               FROM SNMPv2-TC
          adTaControllerMgmt
               FROM ADTRAN-TACONTROLER-PRODUCT-MIB
          adTrapInformSeqNum
                FROM ADTRAN-GENTRAPINFORM-MIB

          ;

adTaCtrlProduct2 MODULE-IDENTITY
   LAST-UPDATED "200903121300Z"
   ORGANIZATION "Adtran, Inc."
   CONTACT-INFO
     "CND Tech Support
         Postal: ADTRAN, Inc.
                 901 Explorer Blvd.
                 Huntsville, AL  35806
                 Tel: +1 800 726-8663
                 Fax: +1 256 963 6217
                 E-mail: support@adtran.com"
   DESCRIPTION
      "This MIB defines the objects for the adTaCtrlProduct2 MIB."
   REVISION "200705010000Z"
   DESCRIPTION "Created"
::= { adTaControllerMgmt 1 }

adTaSysCtrlNotifications OBJECT IDENTIFIER      ::= { adTaCtrlProduct2 0 }
adTaSysCtrlScalars            OBJECT IDENTIFIER ::= { adTaCtrlProduct2 10}
adTaSysCtrlSnmpProvChange     OBJECT IDENTIFIER ::= { adTaCtrlProduct2 11}


-- ***********************************************************************************
   adTaCtrlChassisSlotNumber OBJECT-TYPE
   SYNTAX  INTEGER (1..255)
   MAX-ACCESS   read-only
   STATUS  current
   DESCRIPTION
         "The slot listed on the shelf.  This is only valid in a SNMP Trap."
   ::= { adTaSysCtrlScalars 10}

   adTaCtrlChassisShelfNumber OBJECT-TYPE
   SYNTAX  INTEGER (1..255)
   MAX-ACCESS   read-only
   STATUS  current
   DESCRIPTION
         "The Shelf number of the module.  This is only valid in a SNMP Trap."
   ::= { adTaSysCtrlScalars 11 }

   adTaCtrlChassisTimeStamp OBJECT-TYPE
   SYNTAX      DateAndTime
   MAX-ACCESS   read-write
   STATUS      current
   DESCRIPTION
       "Indicates the date and time in TimeStamp format."
   ::= { adTaSysCtrlScalars 12 }

   adTaCtrlEventDetails OBJECT-TYPE
   SYNTAX      OCTET STRING
   MAX-ACCESS       read-only
   STATUS      current
   DESCRIPTION
       "Indicates the Details of an event attached to the provision change Trap."
   ::= { adTaSysCtrlScalars 15 }

   adTaCtrlProvisionSnmpOID OBJECT-TYPE
   SYNTAX      OBJECT IDENTIFIER
   MAX-ACCESS       read-only
   STATUS      current
   DESCRIPTION
       "Indicates the SNMP OID an event attached to the provision change Trap."
   ::= { adTaSysCtrlScalars 16 }

   adTaCtrlProvisionSnmpOIDIndex OBJECT-TYPE
   SYNTAX      OBJECT IDENTIFIER
   MAX-ACCESS       read-only
   STATUS      current
   DESCRIPTION
       "Indicates the SNMP index of an event attached to the provision change Trap."
   ::= { adTaSysCtrlScalars 17 }

   adTaCtrlProvisionClientIPAddress OBJECT-TYPE
   SYNTAX      IpAddress
   MAX-ACCESS       read-only
   STATUS      current
   DESCRIPTION
       "Indicates the IP Address of the Client initiating the change."
   ::= { adTaSysCtrlScalars 18 }

   adTaCtrlProvisionScmIPAddress OBJECT-TYPE
   SYNTAX      IpAddress
        MAX-ACCESS       read-only
        STATUS      current
   DESCRIPTION
       "Indicates the IP Address of the SCM/Agent/Network Element."
   ::= { adTaSysCtrlScalars 19 }

   -- ***********************************************************************************
   adTaSysCtrlSnmpProvChgMode OBJECT-TYPE
       SYNTAX  INTEGER { enable(1), disable(2) }
       MAX-ACCESS   read-write
       STATUS  current
       DESCRIPTION
         "Enable or disable SNMP Provision Change trap feature."
       ::= { adTaSysCtrlSnmpProvChange 2 }

   adTaSysCtrlSCMProvChgTrapMode OBJECT-TYPE
       SYNTAX  INTEGER { enable(1), disable(2) }
       MAX-ACCESS   read-write
       STATUS  current
       DESCRIPTION
         "Enable or disable SNMP Provision Change trap for SCM only."
       ::= { adTaSysCtrlSnmpProvChange 3 }

   adTaSysCtrlSnmpNotifyHost1 OBJECT-TYPE
       SYNTAX  INTEGER { enable(1), disable(2) }
       MAX-ACCESS   read-write
       STATUS  current
       DESCRIPTION
         "Enable or disable SNMP Trap to configured SNMP Host Trap 1"
       ::= { adTaSysCtrlSnmpProvChange 5 }

   adTaSysCtrlSnmpNotifyHost2 OBJECT-TYPE
       SYNTAX  INTEGER { enable(1), disable(2) }
       MAX-ACCESS   read-write
       STATUS  current
       DESCRIPTION
         "Enable or disable SNMP Trap to configured SNMP Host Trap 2"
       ::= { adTaSysCtrlSnmpProvChange 6 }

   adTaSysCtrlSnmpNotifyHost3 OBJECT-TYPE
       SYNTAX  INTEGER { enable(1), disable(2) }
       MAX-ACCESS   read-write
       STATUS  current
       DESCRIPTION
         "Enable or disable SNMP Trap to configured SNMP Host Trap 3"
       ::= { adTaSysCtrlSnmpProvChange 7 }

   adTaSysCtrlSnmpNotifyHost4 OBJECT-TYPE
       SYNTAX  INTEGER { enable(1), disable(2) }
       MAX-ACCESS   read-write
       STATUS  current
       DESCRIPTION
         "Enable or disable SNMP Trap to configured SNMP Host Trap 4"
       ::= { adTaSysCtrlSnmpProvChange 8 }

   adTaSysCtrlOriginatorHostTable OBJECT-TYPE
       SYNTAX    SEQUENCE OF AdTaSysCtrlOriginatorHostEntry
       MAX-ACCESS     not-accessible
       STATUS    current
       DESCRIPTION
              "Expansion OIDs for the HDX system."
      ::= { adTaSysCtrlSnmpProvChange 10 }

   adTaSysCtrlOriginatorHostEntry OBJECT-TYPE
     SYNTAX      AdTaSysCtrlOriginatorHostEntry
     MAX-ACCESS       not-accessible
     STATUS      current
     DESCRIPTION
             ""
     INDEX      { adTaSysCtrlHostIndex }
       ::= { adTaSysCtrlOriginatorHostTable 1 }

   AdTaSysCtrlOriginatorHostEntry ::=
        SEQUENCE {
            adTaSysCtrlHostIndex
                INTEGER,
            adTaSysCtrlOriginatorHostDisable
                IpAddress
        }

    adTaSysCtrlHostIndex OBJECT-TYPE
    SYNTAX  INTEGER (1..10)
       MAX-ACCESS   not-accessible
       STATUS  current
       DESCRIPTION
         "adTaSysCtrlOriginatorHostTable Table index.."
       ::= { adTaSysCtrlOriginatorHostEntry 1 }

    adTaSysCtrlOriginatorHostDisable OBJECT-TYPE
                  SYNTAX  IpAddress
                  MAX-ACCESS   read-write
                  STATUS  current
                  DESCRIPTION
                    "The user will have the ability to configure 'Exclude Trap Generation from Originating Hosts'
                     This parameter gives the user the ability to not send snmp traps to the hosts who originated the
                     provisioning changed.
                     Up to ten IP addresses (Originating Hosts) can be configured for this parameter.
                     If no IP address is configured, then all hosts will received snmp traps.
                     Example:
                     Host address (10.0.0.1) originates Prov Changes to the NE.
                     Exclude Trap Generation from Originating Hosts = 10.0.0.1
                     Then Host will NOT be receiving snmp trap informs"
                  ::= { adTaSysCtrlOriginatorHostEntry 2 }

   -- ***********************************************************************************
   --
   -- TA System Controller Traps
   --

   adTAModuleProvisionChange  NOTIFICATION-TYPE
           OBJECTS  { adTrapInformSeqNum,sysName, adTaCtrlProvisionSnmpOID, adTaCtrlProvisionSnmpOIDIndex,
                      adTaCtrlChassisTimeStamp, adTaCtrlProvisionScmIPAddress, adTaCtrlProvisionClientIPAddress,
                      adTaCtrlChassisShelfNumber, adTaCtrlChassisSlotNumber,adTaCtrlEventDetails}
           STATUS         current
           DESCRIPTION
              "This notification signifies that a provision occurred."

        --#TYPE      "Warning - Provision Change Notification."
        --#SUMMARY   "Controller 24170: The module has restarted;"
        --#SUMMARY   "detected at chassis: %s, slot: %d"
        --#ARGUMENTS { 1, 2 }
        --#SEVERITY  WARNING
        --#GENERIC   6
        --#CATEGORY  "Warning Events"
        --#SOURCE_ID "A"
        --#TIMEINDEX 0
        ::= { adTaSysCtrlNotifications 2 }


   END

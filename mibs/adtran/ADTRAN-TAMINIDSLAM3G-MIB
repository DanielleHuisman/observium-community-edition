ADTRAN-TAMINIDSLAM3G-MIB

    DEFINITIONS ::= BEGIN

    -- TITLE:     The ADTRAN Mini-DSLAM 3rd Generation Specific MIB
    -- PRODUCT:   Multiple
    -- DATE:      2011/09/21

    -- This MIB defines the object identifiers (OIDs) for the 3rd Generation
    -- Total Access Mini-DSLAM family of products.

    -- HISTORY:
       -- 2005/01/13 gdo First edition (0.1). STATUS: PRELIMINARY
       -- 2007/10/24 gdo Add retrain criteria objects
       -- 2008/01/23 gdo Add rate limiting objects
       -- 2008/01/23 gdo Add PM stat objects, Circuit ID change trap
       -- 2008/02/06 gdo Changes to Circuit ID change trap format
       -- 2008/02/13 gdo Changes to several objects descriptions in MacTable... changed a couple
       --                        Unsigned32's to enumerated INTEGERs in this table as well.
       -- 2008/05/23 jlb Added Multicast Session Control options
       -- 2008/06/12 jlb Changed Multicast Session Control Start and End IP values to IpAddress object-type
       -- 2008/08/08 gdo Add adGenMiniDslam3gMacAgingTime, adGenMiniDslam3gMacVpi, adGenMiniDslam3gMacVci
       -- 2009/07/28 jlb Added severities to alarm notifications and changed adGenMiniDslam3gUserTempActive severity
       --                to MAJOR
       -- 2010/10/27 gdo Add adGenMiniDslam3gSpanPowerPair, adGenMiniDslam3gSpanPowerAlarmEnable,
       --                adGenMiniDslamSpanPowerFailureActive/Cleared, adGenMiniDslamSpanPowerStatus
       -- "DO NOT MAKE HISTORY COMMENTS HERE!!!! Revision history now in REVISION/DESCRIPTION clauses below"

--*********************************************************************************************************
    IMPORTS
        MODULE-IDENTITY,
        OBJECT-TYPE,
        NOTIFICATION-TYPE,
            Integer32,
            Unsigned32,
            Counter32,
            IpAddress,
            TimeTicks
            FROM SNMPv2-SMI
        ifIndex
            FROM IF-MIB
         adGenSlotInfoIndex
            FROM ADTRAN-GENSLOT-MIB
         adTAMiniDslam3gID
            FROM ADTRAN-GENMINIDSLAM-MIB
        DisplayString
            FROM SNMPv2-TC
        InetAddress,
        InetAddressType,
        InetAddressPrefixLength
            FROM INET-ADDRESS-MIB;

--*********************************************************************************************************
    adGenMiniDslam3g MODULE-IDENTITY
         LAST-UPDATED "201409040000Z"
         ORGANIZATION "ADTRAN, Inc."
         CONTACT-INFO
           "Web: http://www.adtran.com
            E-mail: support@adtran.com"
         DESCRIPTION
              "This is the MIB module that describes
               Total Access Mini-DSLAM SMIv2 objects."
         REVISION "201409040000Z"
         DESCRIPTION "Added adGenMiniDslam3gInfoBondingMode."
         REVISION "201303220000Z"
         DESCRIPTION "Added adGenMiniDslam3gInfoLegacyDeployment."
         REVISION "201206270000Z"
         DESCRIPTION "Added adGenMiniDslam3gMacIpAddressType, adGenMiniDslam3gMacIpAddress, and
         			  adGenMiniDslam3gMacIpAddressPrefix for showing IPv6 address information.
         			  Added more detailed description to adGenMiniDslam3gMacInterfaceState."
         REVISION "201109210000Z"
         DESCRIPTION "add pbit remapping oids"
         REVISION "201109090000Z"
         DESCRIPTION "add adGenMiniDslam3gMacCTag, adGenMiniDslam3gMacCEVlan"
         REVISION "201010270000Z"
         DESCRIPTION "gdo Add adGenMiniDslam3gSpanPowerChannel, adGenMiniDslam3gSpanPowerAlarmEnable,
                      adGenMiniDslamSpanPowerFailureActive/Cleared"
        ::= { adTAMiniDslam3gID 1 }

--********************************************************************************************************
    -- OBJECT IDENTIFIERS

    adGenMiniDslam3gMib             OBJECT IDENTIFIER ::= { adGenMiniDslam3g 1 }


-- *************************************************************************
-- prov
-- ************************************************************************
    adGenMiniDslam3gInfoTable        OBJECT-TYPE
        SYNTAX        SEQUENCE OF AdGenMiniDslam3gInfoEntry
        MAX-ACCESS    not-accessible
        STATUS        current
        DESCRIPTION
                 "This table contains all objects for provisioning the DSLAM
                  at the shelf level."
        ::= { adGenMiniDslam3gMib 1 }

    adGenMiniDslam3gInfoEntry   OBJECT-TYPE
        SYNTAX        AdGenMiniDslam3gInfoEntry
        MAX-ACCESS    not-accessible
        STATUS        current
        DESCRIPTION     "An entry in the adGenMiniDslamShelfInfoTable."
             INDEX           { adGenSlotInfoIndex }
        ::= { adGenMiniDslam3gInfoTable 1 }

    AdGenMiniDslam3gInfoEntry ::=
             SEQUENCE {
         adGenMiniDslam3gInfoUserTempThresh                          INTEGER,
              adGenMiniDslam3gInfoUserTempTrapEnable                 INTEGER,
              adGenMiniDslam3gInfoDspWarmStartEnable                 INTEGER,
              adGenMiniDslam3gInfoCurrentTemp                        INTEGER,
--              adGenMiniDslam3gFanTrayNumber                          INTEGER,
              adGenMiniDslam3gInfoFanNumber                          INTEGER,
              adGenMiniDslam3gInfoDspWarmStartReason                 DisplayString,
              adGenMiniDslam3gInfoDownstreamRateLimitPriority        INTEGER,
              adGenMiniDslam3gInfoCircuitIdChanges                   DisplayString,
              adGenMiniDslam3gInfoMCastSessionControlStartIP         IpAddress,
              adGenMiniDslam3gInfoMCastSessionControlEndIP           IpAddress,
              adGenMiniDslam3gInfoMCastSessionControlBitrate         Integer32,
              adGenMiniDslam3gInfoMacAgingTime                       Unsigned32,
              adGenMiniDslam3gInfoLegacyDeployment                   INTEGER,
              adGenMiniDslam3gInfoBondingMode                        INTEGER
             }

    adGenMiniDslam3gInfoUserTempThresh OBJECT-TYPE
        SYNTAX        INTEGER (-40..125)
        MAX-ACCESS    read-write
        STATUS        current
        DESCRIPTION
                 "User temperature threshold in degrees
                  celcius."
        ::= { adGenMiniDslam3gInfoEntry 1 }

    adGenMiniDslam3gInfoUserTempTrapEnable OBJECT-TYPE
        SYNTAX        INTEGER {
                          enable (1),
                          disable (2)
                          }
        MAX-ACCESS    read-write
        STATUS        current
        DESCRIPTION
                 "Used to enable or disable the
                   adGenMiniDslamShelfUserTempActive trap."
        ::= { adGenMiniDslam3gInfoEntry 2 }

    adGenMiniDslam3gInfoDspWarmStartEnable OBJECT-TYPE
        SYNTAX        INTEGER {
                          enable (1),
                          disable (2)
                      }
        MAX-ACCESS    read-write
        STATUS        current
        DESCRIPTION
                 "Used to enable or disable the DSP warm start
                  function."
        ::= { adGenMiniDslam3gInfoEntry 3 }

    adGenMiniDslam3gInfoCurrentTemp OBJECT-TYPE
        SYNTAX        INTEGER (-40..125)
        MAX-ACCESS    read-only
        STATUS        current
        DESCRIPTION
                 "Current temperature of the shelf
                  in degrees celcius."
        ::= { adGenMiniDslam3gInfoEntry 4 }

--         adGenMiniDslam3gFanTrayNumber OBJECT-TYPE
--        SYNTAX        INTEGER (1..99)
--        MAX-ACCESS    accessible-for-notify
--        STATUS        current
--        DESCRIPTION
--                "Fan tray number on the shelf."
--        ::= { adGenMiniDslam3gProvEntry 5 }

    adGenMiniDslam3gInfoFanNumber OBJECT-TYPE
        SYNTAX        INTEGER (1..99)
        MAX-ACCESS    read-only
        STATUS        current
        DESCRIPTION
                "Fan number on the fan tray. This object
                 is intended to be returned only as a
                 varbind for a notification, therefore
                 reading this variable is normally undefined."
        ::= { adGenMiniDslam3gInfoEntry 5 }

    adGenMiniDslam3gInfoDspWarmStartReason OBJECT-TYPE
        SYNTAX        DisplayString
        MAX-ACCESS    read-only
        STATUS        current
        DESCRIPTION
                "Reason that a DSP was reset. This object
                 is intended to be returned only as a
                 varbind for a notification, therefore
                 reading this variable is normally undefined."
        ::= { adGenMiniDslam3gInfoEntry 6 }

    adGenMiniDslam3gInfoDownstreamRateLimitPriority OBJECT-TYPE
        SYNTAX        INTEGER(0..7)
        MAX-ACCESS    read-write
        STATUS        current
        DESCRIPTION
                "Sets the priority threshold for downstream rate limiting.
                 Downstream traffic is rate limited up to the VID specified.
                 Traffic which is tagged with a higher priority than what is
                 set here will not be limited. To limit all traffic, this
                 should be set to 7."
        ::= { adGenMiniDslam3gInfoEntry 7 }

    adGenMiniDslam3gInfoCircuitIdChanges OBJECT-TYPE
        SYNTAX        DisplayString
        MAX-ACCESS    read-only
        STATUS        current
        DESCRIPTION
                "This object is intended to be returned only as a varbind
                for the adGenMiniDslamAdslCircuitIdChange notification below.

                This object is a comma delimited list of all the ports and associated
                ports which have changed and has the following format:

                portnumA/ifTypeA:circuitIdA,portnumB/ifTypeB:circuitIdB[,...].

                The portnum given is the same as the port's adGenPortInfoIndex,
                ifTypeA is the same as the port's adGenIfTypeIndex."
        ::= { adGenMiniDslam3gInfoEntry 8 }

    adGenMiniDslam3gInfoMCastSessionControlStartIP    OBJECT-TYPE
        SYNTAX        IpAddress
        MAX-ACCESS    read-write
        STATUS        current
        DESCRIPTION
                "The first Multicast IP Address in a range of IP addresses
                that are used by the Multicast Session Control."
        ::= { adGenMiniDslam3gInfoEntry 9 }

    adGenMiniDslam3gInfoMCastSessionControlEndIP    OBJECT-TYPE
        SYNTAX        IpAddress
        MAX-ACCESS    read-write
        STATUS        current
        DESCRIPTION
                "The last Multicast IP Address in a range of IP addresses
                that are used by the Multicast Session Control."
        ::= { adGenMiniDslam3gInfoEntry 10 }

    adGenMiniDslam3gInfoMCastSessionControlBitrate    OBJECT-TYPE
        SYNTAX        Integer32
        MAX-ACCESS    read-write
        STATUS        current
        DESCRIPTION
                "Used to set the bitrate associated with the multicast IP address range
                of the Multicast Session Control."
        ::= { adGenMiniDslam3gInfoEntry 11 }


    adGenMiniDslam3gInfoMacAgingTime OBJECT-TYPE
        SYNTAX        Unsigned32
            --    UNITS     "seconds"
        MAX-ACCESS    read-write
        STATUS        current
        DESCRIPTION
                "Used on the switch to determine how long to wait before MAC table
                 entries are removed from the table. If 0 is specified, then the
                 switch will learn and lock each MAC address."
        ::= { adGenMiniDslam3gInfoEntry 12 }

    adGenMiniDslam3gInfoLegacyDeployment OBJECT-TYPE
        SYNTAX        INTEGER {
                          enable (1),
                          disable (2)
                          }
        MAX-ACCESS    read-write
        STATUS        current
        DESCRIPTION
                 "Used to enable or disable the
                  Legacy Deployment provisioning for a third generation DSLAM
                  to work under a TA1x00."
        DEFVAL { disable }
        ::= { adGenMiniDslam3gInfoEntry 13 }

    adGenMiniDslam3gInfoBondingMode OBJECT-TYPE
        SYNTAX        INTEGER {
                          atm (1),
                          efm (2)
                          }
        MAX-ACCESS    read-only
        STATUS        current
        DESCRIPTION
                 "Used to determine the provisioned bonding mode on products that can
		  not suppot ATM and EFM bonding simultaneously."
        ::= { adGenMiniDslam3gInfoEntry 14 }

-- *************************************************************************
-- notifications
-- ************************************************************************

    adGenMiniDslam3gTraps                OBJECT IDENTIFIER   ::= { adGenMiniDslam3gMib 2 }
-- equipment related traps
    adGenMiniDslam3gTrapsv1Patch         OBJECT IDENTIFIER ::= { adGenMiniDslam3gTraps 0 } -- for backward compatibility with some compilers


    adGenMiniDslam3gFanFailureActive      NOTIFICATION-TYPE
             OBJECTS { adGenSlotInfoIndex,
--                        adGenMiniDslam3gFanTrayNumber,
                        adGenMiniDslam3gInfoFanNumber }
        STATUS  current
        DESCRIPTION
                 "Equipment fan failure due to hardware problem."
            --#SEVERITY         MAJOR
         ::= { adGenMiniDslam3gTrapsv1Patch 1 }

    adGenMiniDslam3gFanFailureInactive      NOTIFICATION-TYPE
             OBJECTS { adGenSlotInfoIndex,
--                        adGenMiniDslam3gFanTrayNumber,
                        adGenMiniDslam3gInfoFanNumber }
        STATUS  current
        DESCRIPTION
                 "Equipment fan failure alarm cleared."
            --#SEVERITY         MAJOR
        ::= { adGenMiniDslam3gTrapsv1Patch 2 }

    adGenMiniDslam3gFanTrayRemoved  NOTIFICATION-TYPE
             OBJECTS {  adGenSlotInfoIndex
--                         adGenMiniDslam3gFanTrayNumber
                         }
        STATUS  current
        DESCRIPTION
                 "Fan tray removed from equipment."
            --#SEVERITY         MAJOR
        ::= { adGenMiniDslam3gTrapsv1Patch 3 }

    adGenMiniDslam3gFanTrayInserted  NOTIFICATION-TYPE
             OBJECTS {  adGenSlotInfoIndex
--                         adGenMiniDslam3gFanTrayNumber
                         }
        STATUS  current
        DESCRIPTION
                 "Fan tray inserted into equipment."
            --#SEVERITY         MAJOR
        ::= { adGenMiniDslam3gTrapsv1Patch 4 }

    adGenMiniDslam3gUserTempActive NOTIFICATION-TYPE
             OBJECTS { adGenSlotInfoIndex,
                        adGenMiniDslam3gInfoCurrentTemp,
                        adGenMiniDslam3gInfoUserTempThresh }
        STATUS  current
        DESCRIPTION
                     "Sent when the temperature crosses the
                      user defined threshold."
            --#SEVERITY         MAJOR
        ::= { adGenMiniDslam3gTrapsv1Patch 5 }

    adGenMiniDslam3gUserTempCleared NOTIFICATION-TYPE
             OBJECTS { adGenSlotInfoIndex,
                        adGenMiniDslam3gInfoCurrentTemp,
                        adGenMiniDslam3gInfoUserTempThresh }
        STATUS  current
        DESCRIPTION
                     "Sent when the temperature returns to
                      below the user defined threshold."
            --#SEVERITY         MAJOR
        ::= { adGenMiniDslam3gTrapsv1Patch 6 }

    adGenMiniDslam3gCriticalHiTempActive NOTIFICATION-TYPE
             OBJECTS { adGenSlotInfoIndex }
        STATUS  current
        DESCRIPTION
                     "Indication that temperature had reached the
                      critical threshold."
            --#SEVERITY         CRITICAL
        ::= { adGenMiniDslam3gTrapsv1Patch 7 }

    adGenMiniDslam3gCriticalHiTempCleared NOTIFICATION-TYPE
             OBJECTS { adGenSlotInfoIndex }
        STATUS  current
        DESCRIPTION
                     "Indication that the temperature has
                      returned to normal operating range."
            --#SEVERITY         CRITICAL
        ::= { adGenMiniDslam3gTrapsv1Patch 8 }

    adGenMiniDslamDspWarmStart NOTIFICATION-TYPE
             OBJECTS { adGenSlotInfoIndex,
                        adGenMiniDslam3gInfoDspWarmStartReason }
        STATUS  current
        DESCRIPTION
                     "Indication that a DSP has reset on the referenced
                      3g. The reason contains the DSP number."
            --#SEVERITY         MINOR
        ::= { adGenMiniDslam3gTrapsv1Patch 9 }

    adGenMiniDslamImaLinksOutOfOrderActive NOTIFICATION-TYPE
             OBJECTS { adGenSlotInfoIndex }
        STATUS  current
        DESCRIPTION
                     "Indication that the IMA Link IDs are
                      received out of order on the links in the
                      network feed IMA group."
        ::= { adGenMiniDslam3gTrapsv1Patch 11 }

    adGenMiniDslamImaLinksOutOfOrderCleared NOTIFICATION-TYPE
             OBJECTS { adGenSlotInfoIndex }
        STATUS  current
        DESCRIPTION
                     "Indication that the IMA Link IDs are
                      received in order on the links in the
                      network feed IMA group that were
                      previously out of order."
        ::= { adGenMiniDslam3gTrapsv1Patch 12 }

    adGenMiniDslamConfigErrorActive NOTIFICATION-TYPE
             OBJECTS { adGenSlotInfoIndex }
        STATUS  current
        DESCRIPTION
                     "Indication that a problem occured while
                  a config restore or save was attempted.
                      Points to a flash/filesystem problem."
            --#SEVERITY         MAJOR
        ::= { adGenMiniDslam3gTrapsv1Patch 13 }

    adGenMiniDslamConfigErrorCleared NOTIFICATION-TYPE
             OBJECTS { adGenSlotInfoIndex }
        STATUS  current
        DESCRIPTION
                     "Indication that a new config file
                  has been written to replace the
                  faulty one."
            --#SEVERITY         MAJOR
        ::= { adGenMiniDslam3gTrapsv1Patch 14 }

    adGenMiniDslamCircuitIdChange NOTIFICATION-TYPE
             OBJECTS { adGenSlotInfoIndex,
                        adGenMiniDslam3gInfoCircuitIdChanges }
        STATUS  current
        DESCRIPTION
                     "Indication that the customer use OID (aka Circuit ID) was
                     changed for the referenced port."
            --#SEVERITY         INFORMATIONAL
        ::= { adGenMiniDslam3gTrapsv1Patch 15 }

    adGenMiniDslamSpanPowerFailureActive NOTIFICATION-TYPE
             OBJECTS { adGenSlotInfoIndex,
                        adGenMiniDslam3gSpanPowerChannel }
        STATUS        current
        DESCRIPTION
                     "A loss of span power was detected on a span power
                      channel. The varbind adGenMiniDslam3gSpanPowerChannel
                      indicates which channel was responsible for
                      the condition."
            --#SEVERITY         MINOR
        ::= { adGenMiniDslam3gTrapsv1Patch 16 }

    adGenMiniDslamSpanPowerFailureCleared NOTIFICATION-TYPE
             OBJECTS { adGenSlotInfoIndex,
                        adGenMiniDslam3gSpanPowerChannel }
        STATUS        current
        DESCRIPTION
                     "A loss of span power alarm was cleared on a span power
                      channel. The varbind adGenMiniDslam3gSpanPowerChannel
                      indicates which channel was responsible for
                      the condition."
            --#SEVERITY         MINOR
        ::= { adGenMiniDslam3gTrapsv1Patch 17 }

-- *************************************************************************
-- test
-- ************************************************************************
    adGenMiniDslam3gTestTable     OBJECT-TYPE
        SYNTAX        SEQUENCE OF AdGenMiniDslam3gTestEntry
        MAX-ACCESS    not-accessible
        STATUS        current
        DESCRIPTION
                 "This table contains all objects for performing tests on
                  the DSLAM at the slot level."
        ::= { adGenMiniDslam3gMib 3 }

    adGenMiniDslam3gTestEntry   OBJECT-TYPE
        SYNTAX        AdGenMiniDslam3gTestEntry
        MAX-ACCESS    not-accessible
        STATUS        current
        DESCRIPTION
            "An entry in the adGenMiniDslam3gTestTable."
        INDEX { adGenSlotInfoIndex }
        ::= { adGenMiniDslam3gTestTable 1 }

    AdGenMiniDslam3gTestEntry ::=
             SEQUENCE {
              adGenMiniDslam3gTestPortNumber                         INTEGER,
              adGenMiniDslam3gTestFilename                           DisplayString,
              adGenMiniDslam3gSELTTestStart                          INTEGER,
              adGenMiniDslam3gDELTTestStart                          INTEGER,
              adGenMiniDslam3gTestStop                               INTEGER,
              adGenMiniDslam3gTestSELTDELTStatus                     DisplayString
             }


    adGenMiniDslam3gTestPortNumber OBJECT-TYPE
        SYNTAX        INTEGER (1..48)
        MAX-ACCESS    read-write
        STATUS        current
        DESCRIPTION
            "Selected port number for test operation.
             This is functionally equivalent to the
             adGenPortInfoIndex of the selected interface."
         ::= { adGenMiniDslam3gTestEntry 1 }

    adGenMiniDslam3gTestFilename OBJECT-TYPE
        SYNTAX        DisplayString
        MAX-ACCESS    read-write
        STATUS        current
        DESCRIPTION
            "Name of the file to be transmitted via TFTP
             containing all of the test data for the selected
             interface."
        ::= { adGenMiniDslam3gTestEntry 2 }

    adGenMiniDslam3gSELTTestStart OBJECT-TYPE
        SYNTAX        INTEGER {
                          start(1)
                          }
        MAX-ACCESS    read-write
        STATUS        current
        DESCRIPTION
                 "Used to initiate the SELT test for the ADSL port. When
                  the SELT test has completed the data file will automatically
                  be tranferred using TFTP to the server specified by
                   adGenChassisTftpAddr. A get is meaningless and always
                  returns start(1). Note: only one SELT or DELT test
                  can be performed at a time."
        ::= { adGenMiniDslam3gTestEntry 3 }

    adGenMiniDslam3gDELTTestStart OBJECT-TYPE
        SYNTAX        INTEGER {
                          start(1)
                      }
        MAX-ACCESS    read-write
        STATUS        current
        DESCRIPTION
                 "Used to initiate the DELT test for the ADSL port. When
                  the DELT test has completed the data file will automatically
                  be tranferred using TFTP to the server specified by
                   adGenChassisTftpAddr. A get is meaningless and always
                  returns start(1). Note: only one SELT or DELT test
                  can be performed at a time."
        ::= { adGenMiniDslam3gTestEntry 4 }

    adGenMiniDslam3gTestStop OBJECT-TYPE
        SYNTAX        INTEGER {
                          stop(1)
                          }
        MAX-ACCESS  read-write
        STATUS      current
        DESCRIPTION
                 "Used to cancel any test running for the selected the ADSL port.
                  A get is meaningless and always returns stop(1)."
        ::= { adGenMiniDslam3gTestEntry 5 }

    adGenMiniDslam3gTestSELTDELTStatus OBJECT-TYPE
        SYNTAX        DisplayString
        MAX-ACCESS    read-only
        STATUS        current
        DESCRIPTION
                 "Status of the currently active SELT or DELT
                  test."
        ::= { adGenMiniDslam3gTestEntry 6 }

-- *************************************************************************
-- ADSL Prov
-- ************************************************************************
    adGenMiniDslam3gAdslProvTable      OBJECT-TYPE
        SYNTAX        SEQUENCE OF AdGenMiniDslam3gAdslProvEntry
        MAX-ACCESS    not-accessible
        STATUS        current
        DESCRIPTION
                 "This table contains objects for provisioning the DSLAM
                  ADSL Ports."
        ::= { adGenMiniDslam3gMib 4 }

    adGenMiniDslam3gAdslProvEntry   OBJECT-TYPE
        SYNTAX        AdGenMiniDslam3gAdslProvEntry
        MAX-ACCESS    not-accessible
        STATUS        current
        DESCRIPTION   "An entry in the adGenMiniDslam3gAdslProvTable."
        INDEX         { ifIndex }
        ::= { adGenMiniDslam3gAdslProvTable 1 }

    AdGenMiniDslam3gAdslProvEntry ::=
             SEQUENCE {
               adGenMiniDslam3gAdslProvRetrainUasNe                  INTEGER,
               adGenMiniDslam3gAdslProvRetrainMarginNe               INTEGER,
               adGenMiniDslam3gAdslProvRetrainSesFe                  INTEGER,
               adGenMiniDslam3gAdslProvRetrainUasFe                  INTEGER,
               adGenMiniDslam3gAdslProvRetrainMarginFe               INTEGER,
              adGenMiniDslam3gAdslProvDownstreamRateLimit            Integer32

             }

    adGenMiniDslam3gAdslProvRetrainUasNe OBJECT-TYPE
        SYNTAX        INTEGER {
                          enable(1),
                          disable(2)
                          }
        MAX-ACCESS    read-write
        STATUS        current
        DESCRIPTION
                 "Enable Retrain criteria for UAS NE."
         ::= { adGenMiniDslam3gAdslProvEntry 1 }

    adGenMiniDslam3gAdslProvRetrainMarginNe OBJECT-TYPE
        SYNTAX        INTEGER {
                          enable(1),
                          disable(2)
                          }
        MAX-ACCESS    read-write
        STATUS        current
        DESCRIPTION
                 "Enable Retrain criteria for SNR Margin NE."
        ::= { adGenMiniDslam3gAdslProvEntry 2 }

    adGenMiniDslam3gAdslProvRetrainSesFe OBJECT-TYPE
        SYNTAX        INTEGER {
                          enable(1),
                          disable(2)
                          }
        MAX-ACCESS    read-write
        STATUS        current
        DESCRIPTION
                 "Enable Retrain criteria for SES FE."
        ::= { adGenMiniDslam3gAdslProvEntry 3 }

    adGenMiniDslam3gAdslProvRetrainUasFe OBJECT-TYPE
        SYNTAX        INTEGER {
                          enable(1),
                          disable(2)
                          }
        MAX-ACCESS    read-write
        STATUS        current
        DESCRIPTION
                 "Enable Retrain criteria for UAS FE."
        ::= { adGenMiniDslam3gAdslProvEntry 4 }

    adGenMiniDslam3gAdslProvRetrainMarginFe OBJECT-TYPE
        SYNTAX        INTEGER {
                          enable(1),
                          disable(2)
                          }
        MAX-ACCESS    read-write
        STATUS        current
        DESCRIPTION
                 "Enable Retrain criteria for SNR Margin FE."
        ::= { adGenMiniDslam3gAdslProvEntry 5 }

    adGenMiniDslam3gAdslProvDownstreamRateLimit OBJECT-TYPE
        SYNTAX        Integer32
        MAX-ACCESS    read-write
        STATUS        current
        DESCRIPTION
                 "Sets the downstream rate limit in bps."
        ::= { adGenMiniDslam3gAdslProvEntry 6 }

-- *************************************************************************
-- Device MAC Table
-- ************************************************************************

    adGenMiniDslam3gMacTable OBJECT-TYPE
        SYNTAX        SEQUENCE OF AdGenMiniDslam3gMacEntry
        MAX-ACCESS    not-accessible
        STATUS        current
        DESCRIPTION
           "Subscriber Mac Table."
        ::= { adGenMiniDslam3gMib 5 }

    adGenMiniDslam3gMacEntry OBJECT-TYPE
        SYNTAX        AdGenMiniDslam3gMacEntry
        MAX-ACCESS    not-accessible
        STATUS        current
        DESCRIPTION
           "Each entry corresponds to an entry in the Subscriber Mac Table.
           The ifIndex used here is the customer etherlike port ifIndex
           associated with the DSL port of interest."
       INDEX { ifIndex, adGenMiniDslam3gMacIndex }
        ::= { adGenMiniDslam3gMacTable 1 }

    AdGenMiniDslam3gMacEntry ::=
       SEQUENCE {
            adGenMiniDslam3gMacIndex                                 Unsigned32,
            adGenMiniDslam3gMacAddress                               OCTET STRING,
            adGenMiniDslam3gMacVID                                   INTEGER,
            adGenMiniDslam3gMacType                                  INTEGER,
            adGenMiniDslam3gMacIP                                    IpAddress,
            adGenMiniDslam3gMacLeaseTime                             Unsigned32,
            adGenMiniDslam3gMacGatewayMac                            OCTET STRING,
            adGenMiniDslam3gMacGatewayIP                             IpAddress,
            adGenMiniDslam3gMacInterfaceState                        Unsigned32,
            adGenMiniDslam3gMacXid                                   Unsigned32,
            adGenMiniDslam3gMacEncapsulationMode                     Unsigned32,
            adGenMiniDslam3gMacStartTime                             Unsigned32,
            adGenMiniDslam3gMacVpi                                   Unsigned32,
            adGenMiniDslam3gMacVci                                   Unsigned32,
 	        adGenMiniDslam3gMacCTag                                  INTEGER,
	        adGenMiniDslam3gMacCEVlan                                INTEGER,
	        adGenMiniDslam3gMacIpAddressType                         InetAddressType,
	        adGenMiniDslam3gMacIpAddress                             InetAddress,
	        adGenMiniDslam3gMacIpAddressPrefix                       InetAddressPrefixLength
       }

    adGenMiniDslam3gMacIndex OBJECT-TYPE
        SYNTAX        Unsigned32
        MAX-ACCESS    not-accessible
        STATUS        current
        DESCRIPTION  "Index of the entry. Each port can have 0 up
       to the maximum number allowed for a port, given by the object
        adGenIpPortMaxMacAddr."
        ::= { adGenMiniDslam3gMacEntry 1 }

    adGenMiniDslam3gMacAddress OBJECT-TYPE
        SYNTAX        OCTET STRING
        MAX-ACCESS    read-only
        STATUS        current
        DESCRIPTION  "Mac Address for this entry."
        ::= { adGenMiniDslam3gMacEntry 2 }

    adGenMiniDslam3gMacVID OBJECT-TYPE
        SYNTAX        INTEGER(1..4094)
        MAX-ACCESS    read-only
        STATUS        current
        DESCRIPTION  "VLAN ID"
        ::= { adGenMiniDslam3gMacEntry 3 }

    adGenMiniDslam3gMacType OBJECT-TYPE
        SYNTAX        INTEGER {
                          other(1),
                          invalid(2),
                          dynamic(3),
                          static(4)
                          }
        MAX-ACCESS    read-only
        STATUS        current
        DESCRIPTION  "Entry is typically dynamic or static."
        ::= { adGenMiniDslam3gMacEntry 4 }


    adGenMiniDslam3gMacIP OBJECT-TYPE
        SYNTAX        IpAddress
        MAX-ACCESS    read-only
        STATUS        current
        DESCRIPTION  "IP Address for this entry."
        ::= { adGenMiniDslam3gMacEntry 5 }

    adGenMiniDslam3gMacLeaseTime OBJECT-TYPE
        SYNTAX        Unsigned32
        MAX-ACCESS    read-only
        STATUS        current
        DESCRIPTION  "The expiration counter for this entry, in seconds.
                             When the count reaches 0, the entry will be removed."
        ::= { adGenMiniDslam3gMacEntry 6 }

    adGenMiniDslam3gMacGatewayMac OBJECT-TYPE
        SYNTAX        OCTET STRING
        MAX-ACCESS    read-only
        STATUS        current
        DESCRIPTION  "The gateway's MAC address."
        ::= { adGenMiniDslam3gMacEntry 7 }


    adGenMiniDslam3gMacGatewayIP OBJECT-TYPE
        SYNTAX        IpAddress
        MAX-ACCESS    read-only
        STATUS        current
        DESCRIPTION  "The gateway's IP address."
        ::= { adGenMiniDslam3gMacEntry 8 }

    adGenMiniDslam3gMacInterfaceState OBJECT-TYPE
        SYNTAX        Unsigned32
        MAX-ACCESS    read-only
        STATUS        current
        DESCRIPTION  "The interface state reflects the state
       of the current session.

        0:  PPPoEInitialize(0)
        1:  PPPoEDiscoveryInitiation(1)
        2:  PPPoEDiscoveryOffer(2)
        3:  PPPoEDiscoveryRequest(3)
        4:  PPPoEDiscoverySessionConfirmation(4)
        5:  PPPoEDiscoveryClientTerminate(5)
        6:  PPPoEDiscoveryServerTerminate(6)
        7:  PPPoET1Expired(7)
        8:  PPPoET2Expired(8)
        9:  IPoEInitialize(9)
        10: IPoEDHCPv6Invalid(10)
        11: IPoEDHCPDiscover(11)
        12: IPoEDHCPOffer(12)
        13: IPoEDHCPRequest(13)
        14: IPoEDHCPAck(14)
        15: IPoEDHCPNak(15)
        16: IPoEDHCPDecline(16)
        17: IPoEDHCPRenew(17)
        18: IPoEDHCPRelease(18)
        19: IPoEDHCPInform(19)
        20: IPoEDHCPv6Solicit(20)
        21: IPoEDHCPv6Advertise(21)
        22: IPoEDHCPv6Request(22)
        23: IPoEDHCPv6Authorized(23)
        24: IPoEDHCPv6InformationRequest(24)
        25: IPoEDHCPv6Rebind(25)
        26: IPoEDHCPv6Renew(26)
        27: IPoEDHCPv6Release(27)
        28: PPPoAInitialize(28)
        29: PPPoALCPConfigureRequest(29)
        30: PPPoAPPoEPADISent(30)
        31: PPPoAPPoEPADOReceived(31)
        32: PPPoAPPoEPADRSent(32)
        33: PPPoAPPoEPADSReceived(33)
        34: PPPoAPPoEPADTReceived(34)
        35: PPPoAPPoEPADTSent(35)
        36: PPPoALCPReceived(36)
        37: PPPoALCPConfirmation(37)
        38: IEEE8021xInitialize(38)
        39: IEEE8021xPending(39)
        40: IEEE8021xAuthorized(40)
        41: IPv6LinkLocal(41)"
        ::= { adGenMiniDslam3gMacEntry 9 }

    adGenMiniDslam3gMacXid OBJECT-TYPE
        SYNTAX        Unsigned32
        MAX-ACCESS    read-only
        STATUS        current
        DESCRIPTION  "The DHCP transaction ID, or for PPPoX sessions,
       the PPPoX session ID."
        ::= { adGenMiniDslam3gMacEntry 10 }

    adGenMiniDslam3gMacEncapsulationMode OBJECT-TYPE
        SYNTAX        Unsigned32
        MAX-ACCESS    read-only
        STATUS        current
        DESCRIPTION  "The encapsulation mode for this entry (i.e. DHCP, PPPoE, etc.)"
        ::= { adGenMiniDslam3gMacEntry 11 }

    adGenMiniDslam3gMacStartTime OBJECT-TYPE
        SYNTAX        Unsigned32
        MAX-ACCESS    read-only
        STATUS        current
        DESCRIPTION  "Timestamp for when entry was created.
                             This is given based off of system uptime, and
                             the units are seconds."
        ::= { adGenMiniDslam3gMacEntry 12 }

    adGenMiniDslam3gMacVpi OBJECT-TYPE
        SYNTAX        Unsigned32
        MAX-ACCESS    read-only
        STATUS        current
        DESCRIPTION  "VPI for this entry."
        ::= { adGenMiniDslam3gMacEntry 13 }

    adGenMiniDslam3gMacVci OBJECT-TYPE
        SYNTAX        Unsigned32
        MAX-ACCESS    read-only
        STATUS        current
        DESCRIPTION  "VCI for this entry."
        ::= { adGenMiniDslam3gMacEntry 14 }

    adGenMiniDslam3gMacCTag OBJECT-TYPE
        SYNTAX        INTEGER(0..4098)
        MAX-ACCESS    read-only
        STATUS        current
        DESCRIPTION  "C-Tag ID for this entry.
            A value of 4095 indicates that no CEVlan is present.
            A value of 4097 indicates that customer traffic can
            be tagged or untagged.
            A value of 4098 indicates that customer traffic is tagged only."
        ::= { adGenMiniDslam3gMacEntry 15 }

     adGenMiniDslam3gMacCEVlan OBJECT-TYPE
        SYNTAX        INTEGER(0..4098)
        MAX-ACCESS    read-only
        STATUS        current
        DESCRIPTION  "CE-Vlan ID for this entry.
            A value of 0 indicates priority tagged traffic
            A value of 4095 indicates that no CEVlan is present.
            A value of 4097 indicates that customer traffic can
            be tagged or untagged.
            A value of 4098 indicates that customer traffic is tagged only."
        ::= { adGenMiniDslam3gMacEntry 16 }

     adGenMiniDslam3gMacIpAddressType OBJECT-TYPE
        SYNTAX        InetAddressType
        MAX-ACCESS    read-only
        STATUS        current
        DESCRIPTION  "A value that represents a type of Internet address.

            unknown(0) An unknown address type. This value MUST
            be used if the value of the corresponding
            InetAddress object is a zero-length string.
            It may also be used to indicate an IP address
            that is not in one of the formats defined
            below.

            ipv4(1) An IPv4 address as defined by the
            InetAddressIPv4 textual convention.

            ipv6(2) An IPv6 address as defined by the
            InetAddressIPv6 textual convention.

            ipv4z(3) A non-global IPv4 address including a zone
            index as defined by the InetAddressIPv4z
            textual convention.

            ipv6z(4) A non-global IPv6 address including a zone
            index as defined by the InetAddressIPv6z
            textual convention.

            dns(16) A DNS domain name as defined by the
            InetAddressDNS textual convention."
        ::= { adGenMiniDslam3gMacEntry 17 }

     adGenMiniDslam3gMacIpAddress OBJECT-TYPE
        SYNTAX        InetAddress
        MAX-ACCESS    read-only
        STATUS        current
        DESCRIPTION  "Denotes a generic Internet address."
        ::= { adGenMiniDslam3gMacEntry 18 }

     adGenMiniDslam3gMacIpAddressPrefix OBJECT-TYPE
        SYNTAX        InetAddressPrefixLength
        MAX-ACCESS    read-only
        STATUS        current
        DESCRIPTION  "Denotes the length of a generic Internet
            network address prefix.  A value of n corresponds to
            an IP address mask that has n contiguous 1-bits from
            the most significant bit (MSB), with all other bits
            set to 0."
        ::= { adGenMiniDslam3gMacEntry 19 }

-- *************************************************************************
-- Performance Statstics Tables
-- ************************************************************************
    adGenMiniDslam3gPerf             OBJECT IDENTIFIER    ::= { adGenMiniDslam3gMib 6 }

    adGenMiniDslam3gPerf15MinCurrTable OBJECT-TYPE
        SYNTAX        SEQUENCE OF AdGenMiniDslam3gPerf15MinCurrEntry
        MAX-ACCESS    not-accessible
        STATUS        current
        DESCRIPTION
           "This table contains all the current 15-minute performance statistics
           for a given port."
        ::= { adGenMiniDslam3gPerf 1 }

    adGenMiniDslam3gPerf15MinCurrEntry OBJECT-TYPE
        SYNTAX        AdGenMiniDslam3gPerf15MinCurrEntry
        MAX-ACCESS    not-accessible
        STATUS        current
        DESCRIPTION
           "Each entry corresponds to current 15-minute performance
           interval. The ifIndex used should be the ether-like interface
           for the physical port of interest (either ethernetCsmac(6)
           or propVirtual(53)."
       INDEX { ifIndex }
        ::= { adGenMiniDslam3gPerf15MinCurrTable 1 }

    AdGenMiniDslam3gPerf15MinCurrEntry ::=
       SEQUENCE {
            adGenMiniDslam3gPerf15MinCurrIngressPackets              Counter32,
            adGenMiniDslam3gPerf15MinCurrIngressBytes                Counter32,
            adGenMiniDslam3gPerf15MinCurrEgressPackets               Counter32,
            adGenMiniDslam3gPerf15MinCurrEgressBytes                 Counter32,
            adGenMiniDslam3gPerf15MinCurrEgressOverflowPackets       Counter32,
            adGenMiniDslam3gPerf15MinCurrEgressOverflowBytes         Counter32,
            adGenMiniDslam3gPerf15MinCurrValidIntervals              Unsigned32
       }

    adGenMiniDslam3gPerf15MinCurrIngressPackets OBJECT-TYPE
        SYNTAX        Counter32
        MAX-ACCESS    read-only
        STATUS        current
        DESCRIPTION  "Ingress packets."
        ::= { adGenMiniDslam3gPerf15MinCurrEntry 1 }

    adGenMiniDslam3gPerf15MinCurrIngressBytes OBJECT-TYPE
        SYNTAX        Counter32
        MAX-ACCESS    read-only
        STATUS        current
        DESCRIPTION  "Ingress bytes."
        ::= { adGenMiniDslam3gPerf15MinCurrEntry 2 }

    adGenMiniDslam3gPerf15MinCurrEgressPackets OBJECT-TYPE
        SYNTAX        Counter32
        MAX-ACCESS    read-only
        STATUS        current
        DESCRIPTION  "Egress packets."
        ::= { adGenMiniDslam3gPerf15MinCurrEntry 3 }

    adGenMiniDslam3gPerf15MinCurrEgressBytes OBJECT-TYPE
        SYNTAX        Counter32
        MAX-ACCESS    read-only
        STATUS        current
        DESCRIPTION  "Egress bytes."
        ::= { adGenMiniDslam3gPerf15MinCurrEntry 4 }

    adGenMiniDslam3gPerf15MinCurrEgressOverflowPackets OBJECT-TYPE
        SYNTAX        Counter32
        MAX-ACCESS    read-only
        STATUS        current
        DESCRIPTION  "Egress overflow packets."
        ::= { adGenMiniDslam3gPerf15MinCurrEntry 5 }

    adGenMiniDslam3gPerf15MinCurrEgressOverflowBytes OBJECT-TYPE
        SYNTAX        Counter32
        MAX-ACCESS    read-only
        STATUS        current
        DESCRIPTION  "Egress overflow bytes."
        ::= { adGenMiniDslam3gPerf15MinCurrEntry 6 }

    adGenMiniDslam3gPerf15MinCurrValidIntervals OBJECT-TYPE
        SYNTAX        Unsigned32
        MAX-ACCESS    read-only
        STATUS        current
        DESCRIPTION  "The number of valid historical 15-minute
       intervals."
        ::= { adGenMiniDslam3gPerf15MinCurrEntry 7 }

     adGenMiniDslam3gPerf15MinIntTable OBJECT-TYPE
        SYNTAX        SEQUENCE OF AdGenMiniDslam3gPerf15MinIntEntry
        MAX-ACCESS    not-accessible
        STATUS        current
        DESCRIPTION
           "This table contains all the historical 15-minute performance statistics
           for a given port and 15-minute interval. "
        ::= { adGenMiniDslam3gPerf 2 }

    adGenMiniDslam3gPerf15MinIntEntry OBJECT-TYPE
        SYNTAX        AdGenMiniDslam3gPerf15MinIntEntry
        MAX-ACCESS    not-accessible
        STATUS        current
        DESCRIPTION
           "Each entry corresponds to a 15-minute performance interval. The ifIndex
           used should be the ether-like interface for the physical port of interest
           (either ethernetCsmac(6) or propVirtual(53)."
       INDEX { ifIndex, adGenMiniDslam3gPerf15MinIntInterval }
        ::= { adGenMiniDslam3gPerf15MinIntTable 1 }

    AdGenMiniDslam3gPerf15MinIntEntry ::=
       SEQUENCE {
            adGenMiniDslam3gPerf15MinIntInterval                     Integer32,
            adGenMiniDslam3gPerf15MinIntIngressPackets               Counter32,
            adGenMiniDslam3gPerf15MinIntIngressBytes                 Counter32,
            adGenMiniDslam3gPerf15MinIntEgressPackets                Counter32,
            adGenMiniDslam3gPerf15MinIntEgressBytes                  Counter32,
            adGenMiniDslam3gPerf15MinIntEgressOverflowPackets        Counter32,
            adGenMiniDslam3gPerf15MinIntEgressOverflowBytes          Counter32
       }

    adGenMiniDslam3gPerf15MinIntInterval OBJECT-TYPE
        SYNTAX        Integer32
        MAX-ACCESS    not-accessible
        STATUS        current
        DESCRIPTION  "Index for interval number. 1 is the most recently
       completed 15-minute interval."
        ::= { adGenMiniDslam3gPerf15MinIntEntry 1 }

    adGenMiniDslam3gPerf15MinIntIngressPackets OBJECT-TYPE
        SYNTAX        Counter32
        MAX-ACCESS    read-only
        STATUS        current
        DESCRIPTION  "Ingress packets."
        ::= { adGenMiniDslam3gPerf15MinIntEntry 2 }

    adGenMiniDslam3gPerf15MinIntIngressBytes OBJECT-TYPE
        SYNTAX        Counter32
        MAX-ACCESS    read-only
        STATUS        current
        DESCRIPTION  "Ingress bytes."
        ::= { adGenMiniDslam3gPerf15MinIntEntry 3 }

    adGenMiniDslam3gPerf15MinIntEgressPackets OBJECT-TYPE
        SYNTAX        Counter32
        MAX-ACCESS    read-only
        STATUS        current
        DESCRIPTION  "Egress packets."
        ::= { adGenMiniDslam3gPerf15MinIntEntry 4 }

    adGenMiniDslam3gPerf15MinIntEgressBytes OBJECT-TYPE
        SYNTAX        Counter32
        MAX-ACCESS    read-only
        STATUS        current
        DESCRIPTION  "Egress bytes."
        ::= { adGenMiniDslam3gPerf15MinIntEntry 5 }

    adGenMiniDslam3gPerf15MinIntEgressOverflowPackets OBJECT-TYPE
        SYNTAX        Counter32
        MAX-ACCESS    read-only
        STATUS        current
        DESCRIPTION  "Egress overflow packets."
        ::= { adGenMiniDslam3gPerf15MinIntEntry 6 }

    adGenMiniDslam3gPerf15MinIntEgressOverflowBytes OBJECT-TYPE
        SYNTAX        Counter32
        MAX-ACCESS    read-only
        STATUS        current
        DESCRIPTION  "Egress overflow bytes."
        ::= { adGenMiniDslam3gPerf15MinIntEntry 7 }


     adGenMiniDslam3gPerfDailyCurrTable OBJECT-TYPE
        SYNTAX        SEQUENCE OF AdGenMiniDslam3gPerfDailyCurrEntry
        MAX-ACCESS    not-accessible
        STATUS        current
        DESCRIPTION
           "This table contains all the current daily performance statistics
           for a given port."
        ::= { adGenMiniDslam3gPerf 3 }

    adGenMiniDslam3gPerfDailyCurrEntry OBJECT-TYPE
        SYNTAX        AdGenMiniDslam3gPerfDailyCurrEntry
        MAX-ACCESS    not-accessible
        STATUS        current
        DESCRIPTION
           "Each entry corresponds to current daily performance interval. The ifIndex
           used should be the ether-like interface for the physical port of interest
           (either ethernetCsmac(6) or propVirtual(53)."
       INDEX { ifIndex }
        ::= { adGenMiniDslam3gPerfDailyCurrTable 1 }

    AdGenMiniDslam3gPerfDailyCurrEntry ::=
       SEQUENCE {
            adGenMiniDslam3gPerfDailyCurrIngressPackets              Counter32,
            adGenMiniDslam3gPerfDailyCurrIngressBytes                Counter32,
            adGenMiniDslam3gPerfDailyCurrEgressPackets               Counter32,
            adGenMiniDslam3gPerfDailyCurrEgressBytes                 Counter32,
            adGenMiniDslam3gPerfDailyCurrEgressOverflowPackets       Counter32,
            adGenMiniDslam3gPerfDailyCurrEgressOverflowBytes         Counter32,
            adGenMiniDslam3gPerfDailyCurrValidIntervals              Unsigned32
       }

    adGenMiniDslam3gPerfDailyCurrIngressPackets OBJECT-TYPE
        SYNTAX        Counter32
        MAX-ACCESS    read-only
        STATUS        current
        DESCRIPTION  "Ingress (received) packets for the current
       day."
        ::= { adGenMiniDslam3gPerfDailyCurrEntry 1 }

    adGenMiniDslam3gPerfDailyCurrIngressBytes OBJECT-TYPE
        SYNTAX        Counter32
        MAX-ACCESS    read-only
        STATUS        current
        DESCRIPTION  "Engress (received) bytes for the current
       day."
        ::= { adGenMiniDslam3gPerfDailyCurrEntry 2 }

    adGenMiniDslam3gPerfDailyCurrEgressPackets OBJECT-TYPE
        SYNTAX        Counter32
        MAX-ACCESS    read-only
        STATUS        current
        DESCRIPTION  "Egress (transmit) packets for the
       current day."
        ::= { adGenMiniDslam3gPerfDailyCurrEntry 3 }

    adGenMiniDslam3gPerfDailyCurrEgressBytes OBJECT-TYPE
        SYNTAX        Counter32
        MAX-ACCESS    read-only
        STATUS        current
        DESCRIPTION  "Egress (transmit) bytes for the current
       day."
        ::= { adGenMiniDslam3gPerfDailyCurrEntry 4 }

    adGenMiniDslam3gPerfDailyCurrEgressOverflowPackets OBJECT-TYPE
        SYNTAX        Counter32
        MAX-ACCESS    read-only
        STATUS        current
        DESCRIPTION  "Egress (transmit) overflow packets for the current
       day."
        ::= { adGenMiniDslam3gPerfDailyCurrEntry 5 }

    adGenMiniDslam3gPerfDailyCurrEgressOverflowBytes OBJECT-TYPE
        SYNTAX        Counter32
        MAX-ACCESS    read-only
        STATUS        current
        DESCRIPTION  "Egress (transmit) overflow bytes for the current
       day."
        ::= { adGenMiniDslam3gPerfDailyCurrEntry 6 }

    adGenMiniDslam3gPerfDailyCurrValidIntervals OBJECT-TYPE
        SYNTAX        Unsigned32
        MAX-ACCESS    read-only
        STATUS        current
        DESCRIPTION  "The number of historical daily intervals that are
       available for retrieval."
        ::= { adGenMiniDslam3gPerfDailyCurrEntry 7 }

     adGenMiniDslam3gPerfDailyIntTable OBJECT-TYPE
        SYNTAX        SEQUENCE OF AdGenMiniDslam3gPerfDailyIntEntry
        MAX-ACCESS    not-accessible
        STATUS        current
        DESCRIPTION
           "This table contains all the historical daily performance statistics
           for a given port and day. "
        ::= { adGenMiniDslam3gPerf 4 }

    adGenMiniDslam3gPerfDailyIntEntry OBJECT-TYPE
        SYNTAX        AdGenMiniDslam3gPerfDailyIntEntry
        MAX-ACCESS    not-accessible
        STATUS        current
        DESCRIPTION
           "Each entry corresponds to a daily performance interval. The ifIndex
           used should be the ether-like interface for the physical port of interest
           (either ethernetCsmac(6) or propVirtual(53)."
       INDEX { ifIndex, adGenMiniDslam3gPerfDailyIntInterval }
        ::= { adGenMiniDslam3gPerfDailyIntTable 1 }

    AdGenMiniDslam3gPerfDailyIntEntry ::=
       SEQUENCE {
            adGenMiniDslam3gPerfDailyIntInterval                     Integer32,
            adGenMiniDslam3gPerfDailyIntIngressPackets               Counter32,
            adGenMiniDslam3gPerfDailyIntIngressBytes                 Counter32,
            adGenMiniDslam3gPerfDailyIntEgressPackets                Counter32,
            adGenMiniDslam3gPerfDailyIntEgressBytes                  Counter32,
            adGenMiniDslam3gPerfDailyIntEgressOverflowPackets        Counter32,
            adGenMiniDslam3gPerfDailyIntEgressOverflowBytes          Counter32
       }

    adGenMiniDslam3gPerfDailyIntInterval OBJECT-TYPE
        SYNTAX        Integer32
        MAX-ACCESS    not-accessible
        STATUS        current
        DESCRIPTION  "Index for interval number. 1 is the most recently
                        completed interval (previous day)."
        ::= { adGenMiniDslam3gPerfDailyIntEntry 1 }

    adGenMiniDslam3gPerfDailyIntIngressPackets OBJECT-TYPE
        SYNTAX        Counter32
        MAX-ACCESS    read-only
        STATUS        current
        DESCRIPTION  "The number of ingress (received) packets."
        ::= { adGenMiniDslam3gPerfDailyIntEntry 2 }

    adGenMiniDslam3gPerfDailyIntIngressBytes OBJECT-TYPE
        SYNTAX        Counter32
        MAX-ACCESS    read-only
        STATUS        current
        DESCRIPTION  "The number of ingress (received) bytes."
        ::= { adGenMiniDslam3gPerfDailyIntEntry 3 }

    adGenMiniDslam3gPerfDailyIntEgressPackets OBJECT-TYPE
        SYNTAX        Counter32
        MAX-ACCESS    read-only
        STATUS        current
        DESCRIPTION  "The number of egress (transmitted) packets."
        ::= { adGenMiniDslam3gPerfDailyIntEntry 4 }

    adGenMiniDslam3gPerfDailyIntEgressBytes OBJECT-TYPE
        SYNTAX        Counter32
        MAX-ACCESS    read-only
        STATUS        current
        DESCRIPTION  "The number of egress (transmitted) bytes."
        ::= { adGenMiniDslam3gPerfDailyIntEntry 5 }

    adGenMiniDslam3gPerfDailyIntEgressOverflowPackets OBJECT-TYPE
        SYNTAX        Counter32
        MAX-ACCESS    read-only
        STATUS        current
        DESCRIPTION  "Egress overflow packets."
        ::= { adGenMiniDslam3gPerfDailyIntEntry 6 }

    adGenMiniDslam3gPerfDailyIntEgressOverflowBytes OBJECT-TYPE
        SYNTAX        Counter32
        MAX-ACCESS    read-only
        STATUS        current
        DESCRIPTION  "Egress overflow bytes."
        ::= { adGenMiniDslam3gPerfDailyIntEntry 7 }

    -- ======================================================================
    -- Provisioning Menu Items

    adGenMiniDslam3gVlanVcMapProfileTable OBJECT-TYPE
        SYNTAX        SEQUENCE OF AdGenMiniDslam3gVlanVcMapProfileEntry
        MAX-ACCESS    not-accessible
        STATUS        current
        DESCRIPTION
           "This table contains information on the VLAN mappings
           in an ATM-oriented system (i.e., 'cross-connects'
           between VLANs and VCLs).  One entry in this
           table reflects a profile defined by a manager
           which can be used to provision a VLAN-to-VCL
           mapping."
        ::= { adGenMiniDslam3gMib 7}

    adGenMiniDslam3gVlanVcMapProfileEntry OBJECT-TYPE
        SYNTAX        AdGenMiniDslam3gVlanVcMapProfileEntry
        MAX-ACCESS    not-accessible
        STATUS        current
        DESCRIPTION
           "Each entry corresponds to an Ethernet/VLAN-to-VCL
           Mapping Profile. The ifIndex used here is the GigE ifIndex
           associated with the DSL port of interest."
       INDEX { ifIndex, adGenMiniDslam3gVlanVcVpi, adGenMiniDslam3gVlanVcVci, adGenMiniDslam3gVlanVcVid }
        ::= { adGenMiniDslam3gVlanVcMapProfileTable 1 }

    AdGenMiniDslam3gVlanVcMapProfileEntry ::=
       SEQUENCE {
            adGenMiniDslam3gVlanVcVpi                                Unsigned32,
            adGenMiniDslam3gVlanVcVci                                Unsigned32,
            adGenMiniDslam3gVlanVcVid                                Unsigned32
       }

    adGenMiniDslam3gVlanVcVpi OBJECT-TYPE
        SYNTAX        Unsigned32
        MAX-ACCESS    read-only
        STATUS        current
        DESCRIPTION
                    "The VPI for this entry"
        ::= {adGenMiniDslam3gVlanVcMapProfileEntry 1}

    adGenMiniDslam3gVlanVcVci OBJECT-TYPE
        SYNTAX        Unsigned32
        MAX-ACCESS    read-only
        STATUS        current
        DESCRIPTION
                    "The VCI for this entry"
        ::= {adGenMiniDslam3gVlanVcMapProfileEntry 2}

    adGenMiniDslam3gVlanVcVid OBJECT-TYPE
        SYNTAX        Unsigned32
        MAX-ACCESS    read-only
        STATUS        current
        DESCRIPTION
                    "The VID for this entry"
        ::= {adGenMiniDslam3gVlanVcMapProfileEntry 3}

    adGenMiniDslam3gSpanPowerTable OBJECT-TYPE
        SYNTAX        SEQUENCE OF AdGenMiniDslam3gSpanPowerEntry
        MAX-ACCESS    not-accessible
        STATUS        current
        DESCRIPTION
           "This table contains objects used to manage a
            span power supply if so equipped."
        ::= { adGenMiniDslam3gMib 8}

    adGenMiniDslam3gSpanPowerEntry OBJECT-TYPE
        SYNTAX        AdGenMiniDslam3gSpanPowerEntry
        MAX-ACCESS    not-accessible
        STATUS        current
        DESCRIPTION
           "Each entry corresponds to a particular span power channel
            to a span powered power supply. A single or multiple
            span power channels may be used by a span powered device
            in this system."
       INDEX { adGenSlotInfoIndex, adGenMiniDslam3gSpanPowerChannel }
        ::= { adGenMiniDslam3gSpanPowerTable 1 }

    AdGenMiniDslam3gSpanPowerEntry ::=
       SEQUENCE {
            adGenMiniDslam3gSpanPowerChannel                         Unsigned32,
            adGenMiniDslam3gSpanPowerAlarmEnable                     INTEGER,
            adGenMiniDslam3gSpanPowerStatus                          INTEGER
       }

    adGenMiniDslam3gSpanPowerChannel OBJECT-TYPE
        SYNTAX        Unsigned32
        MAX-ACCESS    read-only
        STATUS        current
        DESCRIPTION
           "Number of the span power channel."
        ::= {adGenMiniDslam3gSpanPowerEntry 1}

    adGenMiniDslam3gSpanPowerAlarmEnable OBJECT-TYPE
        SYNTAX        INTEGER {
                         enable(1),
                         disable(2)
                         }
        MAX-ACCESS    read-write
        STATUS        current
        DESCRIPTION
           "Used to enable or disable alarm reporting for the
            specified span power channel."
        DEFVAL { disable }
        ::= {adGenMiniDslam3gSpanPowerEntry 2}

    adGenMiniDslam3gSpanPowerStatus OBJECT-TYPE
        SYNTAX        INTEGER {
                         powered(1),
                         unPowered(2)
                         }
        MAX-ACCESS    read-only
        STATUS        current
        DESCRIPTION
           "Used to determine if span power is present on the channel."
        ::= {adGenMiniDslam3gSpanPowerEntry 3}

-- *************************************************************************
-- Gigabit Ethernet Prov
-- ************************************************************************
    adGenMiniDslam3gGigeProvTable      OBJECT-TYPE
        SYNTAX        SEQUENCE OF AdGenMiniDslam3gGigeProvEntry
        MAX-ACCESS    not-accessible
        STATUS        current
        DESCRIPTION
                 "This table contains objects for provisioning the DSLAM
                  Gigabit Ethernet Ports."
        ::= { adGenMiniDslam3gMib 9 }

    adGenMiniDslam3gGigeProvEntry   OBJECT-TYPE
        SYNTAX        AdGenMiniDslam3gGigeProvEntry
        MAX-ACCESS    not-accessible
        STATUS        current
        DESCRIPTION   "An entry in the adGenMiniDslam3gGigeProvTable."
        INDEX         { ifIndex }
        ::= { adGenMiniDslam3gGigeProvTable 1 }

    AdGenMiniDslam3gGigeProvEntry ::=
             SEQUENCE {
               adGenMiniDslam3gGigeProvRemapPbit0                  INTEGER,
               adGenMiniDslam3gGigeProvRemapPbit1                  INTEGER,
               adGenMiniDslam3gGigeProvRemapPbit2                  INTEGER,
               adGenMiniDslam3gGigeProvRemapPbit3                  INTEGER,
               adGenMiniDslam3gGigeProvRemapPbit4                  INTEGER,
               adGenMiniDslam3gGigeProvRemapPbit5                  INTEGER,
               adGenMiniDslam3gGigeProvRemapPbit6                  INTEGER,
               adGenMiniDslam3gGigeProvRemapPbit7                  INTEGER,
               adGenMiniDslam3gGigeProvRemapPbitResetAll           INTEGER
             }

    adGenMiniDslam3gGigeProvRemapPbit0 OBJECT-TYPE
        SYNTAX        INTEGER (0..7)
        MAX-ACCESS    read-write
        STATUS        current
        DESCRIPTION
                 "Remap priority 0 to the specified value. Packets are reassigned
                  at ingress. Setting this object to 0 will not modify the priority."
         ::= { adGenMiniDslam3gGigeProvEntry 1 }

    adGenMiniDslam3gGigeProvRemapPbit1 OBJECT-TYPE
        SYNTAX        INTEGER (0..7)
        MAX-ACCESS    read-write
        STATUS        current
        DESCRIPTION
                 "Remap priority 1 to the specified value. Packets are reassigned
                  at ingress. Setting this object to 1 will not modify the priority."
         ::= { adGenMiniDslam3gGigeProvEntry 2 }

    adGenMiniDslam3gGigeProvRemapPbit2 OBJECT-TYPE
        SYNTAX        INTEGER (0..7)
        MAX-ACCESS    read-write
        STATUS        current
        DESCRIPTION
                 "Remap priority 2 to the specified value. Packets are reassigned
                  at ingress. Setting this object to 2 will not modify the priority."
         ::= { adGenMiniDslam3gGigeProvEntry 3 }

    adGenMiniDslam3gGigeProvRemapPbit3 OBJECT-TYPE
        SYNTAX        INTEGER (0..7)
        MAX-ACCESS    read-write
        STATUS        current
        DESCRIPTION
                 "Remap priority 3 to the specified value. Packets are reassigned
                  at ingress. Setting this object to 3 will not modify the priority."
         ::= { adGenMiniDslam3gGigeProvEntry 4 }

    adGenMiniDslam3gGigeProvRemapPbit4 OBJECT-TYPE
        SYNTAX        INTEGER (0..7)
        MAX-ACCESS    read-write
        STATUS        current
        DESCRIPTION
                 "Remap priority 4 to the specified value. Packets are reassigned
                  at ingress. Setting this object to 4 will not modify the priority."
         ::= { adGenMiniDslam3gGigeProvEntry 5 }

    adGenMiniDslam3gGigeProvRemapPbit5 OBJECT-TYPE
        SYNTAX        INTEGER (0..7)
        MAX-ACCESS    read-write
        STATUS        current
        DESCRIPTION
                 "Remap priority 5 to the specified value. Packets are reassigned
                  at ingress. Setting this object to 5 will not modify the priority."
         ::= { adGenMiniDslam3gGigeProvEntry 6 }

    adGenMiniDslam3gGigeProvRemapPbit6 OBJECT-TYPE
        SYNTAX        INTEGER (0..7)
        MAX-ACCESS    read-write
        STATUS        current
        DESCRIPTION
                 "Remap priority 6 to the specified value. Packets are reassigned
                  at ingress. Setting this object to 6 will not modify the priority."
         ::= { adGenMiniDslam3gGigeProvEntry 7 }

    adGenMiniDslam3gGigeProvRemapPbit7 OBJECT-TYPE
        SYNTAX        INTEGER (0..7)
        MAX-ACCESS    read-write
        STATUS        current
        DESCRIPTION
                 "Remap priority 7 to the specified value. Packets are reassigned
                  at ingress. Setting this object to 7 will not modify the priority."
         ::= { adGenMiniDslam3gGigeProvEntry 8 }

    adGenMiniDslam3gGigeProvRemapPbitResetAll OBJECT-TYPE
        SYNTAX        INTEGER { reset(1) }
        MAX-ACCESS    read-write
        STATUS        current
        DESCRIPTION
                 "Resets all pbit remapping objects to the disabled states (e.g.
                  RemapPbit0 = 0, RemapPbit1 = 1, etc.). A get is meaningless and
                  will always return reset(1)."
         ::= { adGenMiniDslam3gGigeProvEntry 9 }

END

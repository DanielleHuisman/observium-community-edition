ADTRAN-TAOCTADSL2-MIB

    DEFINITIONS ::= BEGIN

    -- TITLE:     The ADTRAN TA Octal Adsl MIB 2
    -- PRODUCT:   8 PORT Adsl for TOTAL ACCESS
    -- VERSION:   1.2
    -- DATE:      05/08/04
    -- STATUS:    PRELIMINARY

    -- This MIB defines the SNMPv2 objects for object identifiers (OIDs)
    -- adTA3000OctADSL(432) and adTAOctAdslwPOTS(455).


    -- HISTORY:
       -- 02/04/01 SM. First edition (0.1). STATUS: PRELIMINARY.
       -- 02/05/21 TGC. Modified IMPORTS and modified OBJECT IDENTIFIERS to make
       --          use of the new IMPORTS. These changes were made to be compatible
       --          with older compilers while maintaining proper syntax.
       -- 02/05/22 TGC. Modified comments to reflect the fact that this MIB will be
       --          used to support multiple products. Added ServiceMode, LinkStatus,
       --          and CurrStandard variables.
       -- 02/11/13 TGC. Added adTAOctAdslConfProfileIndexApplied.
       -- 03/02/05 DSC. Added following commands to adFactGenSlotCommand in the factory genslot mib.
       --          Set Value    Action
       --              1        All LEDS set to green.
       --              2        All LEDS set to yellow.
       --              3        All LEDS set to red.
       --              4        All LEDS set to red.
       --              5        All LEDS set to off.
       --              6        All LEDS return to normal.
       --              7        Update Provisioning directly from EEPROM.
       --              8        Read Current MUX. Value returned in adFactGenSlotResults.
       --              9        Reboot system.
       -- 04/07/13 DSC. Updated service mode and bat table for adsl2+.
       -- 05/02/01 DSC. Added  adTAOctAdslAtucPhysTable
       --               Added  adTAOctAdslAtucNumParityBytes
       --               Added  adTAOctAdslAtucFramesPerCodeword
       --               Added  adTAOctAdslAtucInterleavingDepth
       --               Added  adTAOctAdslAturPhysTable
       --               Added  adTAOctAdslAturNumParityBytes
       --               Added  adTAOctAdslAturFramesPerCodeword
       --               Added  adTAOctAdslAturInterleavingDepth
       -- 05/05/02 JTZ. Added adsl1MultiMode to the adTAOctAdslConfProfileServiceMode item
       --               to allow adsl2+ line cards to be provisioned to legacy multiMode
       --               service mode.
       -- 05/05/10 GDO. Added adTAOctAdslHamBandMask and adTAOctAdslCabinetMode objects.
       -- 05/08/04 GDO. Move adTAOctAdslHamBandMask and adTAOctAdslCabinetMode objects into new table.
       -- 05/10/12 TGC. Added adTAOctAdslConfProfileName to be used by the TA11100F/1148 instead of
       --               adTAOctAdslConfProfileIndexApplied. Due to migration from previous generation
       --               TA11XX/12XX products, a profile name will work better than a profile index.
       -- 07/10/24 JEO. Added adTAOctAdslPowerThreshold object.
       -- 07/10/26 JEO. Changed filename extension from .mib to .mi2 per Phil Bergstresser.
       -- 08/08/07 JEO. Added AnnexM setting (enum 10) to ADSL service mode.
       -- 08/08/28 CLS  Added adTAOctAdslAtucCarrierMask and adTAOctAdslAturCarrierMask.
       --               Update adTAOctAdslConfProfileServiceMode to include ADSL2+ Annex M
       -- 08/08/28 CLS  Added Minimum INP to MIB
       -- 08/09/22 JEO. Added AnnexM setting (enum 10) to ADSL current standard.
       -- 08/13/2009 och added adProducts to display the ADSL cards (Sparta 57749)
       --                renamed the INTEGER values to not include "_" to help  the smicng compiler
       -- 10/30/2009 och Added adTAOctAdslAtucChanTable and adTAOctAdslAturChanTable
       --                Items: adTAOctAdslAturChanINP, adTAOctAdslAtucChanINP
       -- 11/20/2009 och Added adTAOctAdslAtucConfProfileInterleaveMinInpRev2 and adTAOctAdslAturConfProfileInterleaveMinInpRev2
       -- 06/09/2010 TAS Added adTAOctAdslAturCapabilities and adTAOctAdslAturInvProviderCode
       -- 				 Added adTAOctAdslAtmAtucCellCountTable
       --				 	adTAOctAdslAtmAtucCellCount, adTAOctAdslAtmAtucIdleCellCount, and adTAOctAdslAtmAtucHecErrorCount		
       --				 Added adTAOctAdslAtmAturCellCountTable                               
       --        			adTAOctAdslAtmAturCellCount and adTAOctAdslAtmAturIdleCellCount
       -- 07/21/2010 TAS Added adTAOctAdslAtucRelativeCap and adTAOctAdslAturRelativeCap
       --                	Changed adTAOctAdslAtucChanINP and adTAOctAdslAturChanINP descriptions from 0.1 dmt to 0.01 dmt
       -- 02/11/2011 TAS Added adTAOctAdslUsSnrMarginMap
       					    

    IMPORTS
        MODULE-IDENTITY,
        OBJECT-TYPE,
        enterprises,
        Gauge32,
	    Integer32,
	    Unsigned32
            FROM SNMPv2-SMI
        DisplayString
            FROM SNMPv2-TC
        SnmpAdminString
            FROM SNMP-FRAMEWORK-MIB
        ifIndex
            FROM IF-MIB
        adslLineConfProfileName
            FROM ADSL-LINE-MIB
        adProducts,
        adMgmt,
        adIdentity
            FROM ADTRAN-MIB         -- v2 version
        ;

-- *********************************************************************************************************
  adTAOctAdslID MODULE-IDENTITY
         LAST-UPDATED "200809221500Z"
         ORGANIZATION "ADTRAN, Inc."
         CONTACT-INFO
           "CND Tech Support
            Postal: ADTRAN, Inc.
                    901 Explorer Blvd.
                    Huntsville, AL  35806
                    Tel: +1 800 726-8663
                    Fax: +1 256 963 6217
                    E-mail: support@adtran.com"
         DESCRIPTION
              "The is the MIB module that describes
               Octal Adsl SMIv2 objects."
         ::= {  adIdentity 432 }

-- ********************************************************************************************************
    -- OBJECT IDENTIFIERS

--  adtran           OBJECT IDENTIFIER ::= { enterprises 664 }
--    adProducts       OBJECT IDENTIFIER ::= { adtran 1 }
        adTAOctAdsl      OBJECT IDENTIFIER ::= { adProducts 432 }
          adTAOctAdslalarms  OBJECT IDENTIFIER ::= { adTAOctAdsl 101 }
--          adTAOctAdslPerf    OBJECT IDENTIFIER ::= { adTAOctAdsl 102 }
        adTAOctAdslwPOTS OBJECT IDENTIFIER ::= { adProducts 455 }
        adTA5k32pADSL2           OBJECT IDENTIFIER ::= { adProducts 752 }
        adTA5k24pPOTSADSL2       OBJECT IDENTIFIER ::= { adProducts 858 }
        adTA5k32pADSL2int       OBJECT IDENTIFIER ::= { adProducts 1043 }


--    adMgmt           OBJECT IDENTIFIER ::= { adtran 2 }
        adTAOctAdslmg    OBJECT IDENTIFIER ::= { adMgmt 432 }
          adTAOctAdslProv    OBJECT IDENTIFIER ::= { adTAOctAdslmg 1 }    -- used in ADTRAN-TAOCTADSL-MIB
          adTAOctAdslProv2   OBJECT IDENTIFIER ::= { adTAOctAdslmg 2 }    -- used in ADTRAN-TAOCTADSL2-MIB
          adTAOctAdslStatus2 OBJECT IDENTIFIER ::= { adTAOctAdslmg 4 }    -- used in ADTRAN-TAOCTADSL2-MIB
--    adAdmin          OBJECT IDENTIFIER ::= { adtran 3 }
--    adPerform        OBJECT IDENTIFIER ::= { adtran 4 }
--    adShared         OBJECT IDENTIFIER ::= { adtran 5 }
--    adIdentity       OBJECT IDENTIFIER ::= { adtran 6 }

-- ********************************************************************************************************


    adTAOctAdslConfProfileExtTable   OBJECT-TYPE
        SYNTAX          SEQUENCE OF AdTAOctAdslConfProfileExtEntry
        MAX-ACCESS      not-accessible
        STATUS          current
        DESCRIPTION
            "This table contains ADSL line profile configuration
             information not defined in the adslLineConfProfileTable
             from the ADSL-LINE-MIB.  This includes the line type."
        ::= { adTAOctAdslProv2 1 }

    adTAOctAdslConfProfileExtEntry   OBJECT-TYPE
        SYNTAX          AdTAOctAdslConfProfileExtEntry
        MAX-ACCESS      not-accessible
        STATUS          current
        DESCRIPTION
            "An entry extends the adslLineConfProfileEntry
             defined in ADSL-LINE-MIB.  Each entry corresponds
             to an ADSL line profile."
        INDEX { IMPLIED adslLineConfProfileName }
        ::= { adTAOctAdslConfProfileExtTable 1 }

    AdTAOctAdslConfProfileExtEntry ::=
        SEQUENCE {
            adTAOctAdslConfProfileLineType
                INTEGER,
            adTAOctAdslConfProfileServiceMode
                INTEGER,
            adTAOctAdslConfProfileIndexApplied
                INTEGER,
            adTAOctAdslConfProfileName
                SnmpAdminString,
            adTAOctAdslAtucConfProfileInterleaveMinINP
                INTEGER,
            adTAOctAdslAturConfProfileInterleaveMinINP
                INTEGER,
            adTAOctAdslAtucConfProfileInterleaveMinInpRev2
                INTEGER,
            adTAOctAdslAturConfProfileInterleaveMinInpRev2
                INTEGER
        }

    adTAOctAdslConfProfileLineType OBJECT-TYPE
        SYNTAX      INTEGER {
                    noChannel (1),        -- no channels exist
                    fastOnly (2),         -- fast channel exists only
                    interleavedOnly (3),  -- interleaved channel exists
                                          -- only
                    fastOrInterleaved (4),-- either fast or interleaved
                                          -- channels can exist, but
                                          -- only one at any time
                    fastAndInterleaved (5)-- both fast or interleaved
                                          -- channels exist
        }
        MAX-ACCESS  read-write
        STATUS      current
        DESCRIPTION
            "This object is used to configure the ADSL physical
             line type.  The object, including enumerations, was
             taken from the ADSL Extension MIB as this was the only
             variable in the Extension MIB to be supported. Only
             enumerations (2) and (3) will be supported initially."
        ::= { adTAOctAdslConfProfileExtEntry 1 }

    adTAOctAdslConfProfileServiceMode OBJECT-TYPE
        SYNTAX      INTEGER {
                    multiMode   (1),   -- adapt to the ATUR's mode, assuming T1.413, G.dmt, or G.lite
                                              -- **NOTE**  For adsl2+ line cards, this is adsl2+ multimode
                    t1413       (2),       -- T1.413 Mode
                    gDMT        (3),       -- G.dmt Mode
                    gLite       (4),       -- G.lite Mode
                    g9923       (5),       -- ADSL2 Mode
                    g9924       (6),       -- ADSL2-lite Mode
                    g9925       (7),       -- ADSL2+ Mode
                    readsl      (8),       -- READSL Mode
                    adsl1MultiMode (9),    -- adsl legacy multimode, to be used by adsl2+ line cards to
                                           --  enable multimode equivalent to that of adsl line cards
                    g9925AnxM      (10)    -- ADSL2+ Annex M Mode
--                  vdsl_vm_vdsl1  (11),      placeholder
--                  vdsl_vm_vdsl2  (12),      placeholder
--                  vdsl_vdsl2_multi_mode (13),   placeholder
--                  vdsl_vm_xtse_multimode  (255)   placeholder

        }
        MAX-ACCESS  read-write
        STATUS      current
        DESCRIPTION
            "This object is used to provision the ADSL physical
             line service mode. If the line card is a legacy adsl
             line card, the multiMode option will allow the
             ATUC to adapt to the ATUR's mode, assuming it is T1.413,
             G.dmt, or G.lite. If the line card is adsl2+, the
             multiMode option allows the ATUC still to adapt to the
             ATUR's mode, but will attempt to connect up to adsl2+
             rates."
        ::= { adTAOctAdslConfProfileExtEntry 2 }

    adTAOctAdslConfProfileIndexApplied OBJECT-TYPE
        SYNTAX      INTEGER  (1..255)
        MAX-ACCESS  read-write
        STATUS      current
        DESCRIPTION
            "This object is used to contain the index of the ADSL
             template or profile applied to the line. This index
             is used internally to look up a name or description
             of the profile. It is NOT equivalent to:
             INDEX {IMPLIED adslLineConfProfileName}."
        ::= { adTAOctAdslConfProfileExtEntry 3 }

     adTAOctAdslConfProfileName    OBJECT-TYPE
        SYNTAX          SnmpAdminString (SIZE (1..32))
        MAX-ACCESS      read-write
        STATUS          current
        DESCRIPTION
             "This object is used to identify the ADSL template or
             profile applied to the line by name."
        ::= { adTAOctAdslConfProfileExtEntry 4 }


    adTAOctAdslAtucConfProfileInterleaveMinINP  OBJECT-TYPE
             SYNTAX INTEGER {
              zeroDMTSymbols (1),
              halfDMTSymbols (2),
              oneDMTSymbols  (3),
              twoDMTSymbols  (4)
             }
             MAX-ACCESS  read-write
             STATUS      obsolete
             DESCRIPTION
                 "The minimum amount of impulse noise protection,
                 measured in steps of 0.5 DMT symbols (250
                 microseconds per DMT symbol). This is for the
                 downstream direction.
                 NOTE: A set here applies for both upstream AND downstream."
         ::= { adTAOctAdslConfProfileExtEntry 5 }



    adTAOctAdslAturConfProfileInterleaveMinINP  OBJECT-TYPE
             SYNTAX INTEGER {
              zeroDMTSymbols (1),
              halfDMTSymbols (2),
              oneDMTSymbols  (3),
              twoDMTSymbols  (4)
             }
             UNITS       "0.5 DMT symbols"
             MAX-ACCESS  read-only
             STATUS      obsolete

             DESCRIPTION
                 "The minimum amount of impulse noise protection,
                 measured in steps of 0.5 DMT symbols (250
                 microseconds per DMT symbol). This is for the
                 upstream direction."
         ::= { adTAOctAdslConfProfileExtEntry 6 }
         
         
    adTAOctAdslAtucConfProfileInterleaveMinInpRev2     OBJECT-TYPE
             SYNTAX INTEGER {
              zeroDMTSymbols     (1),
              halfDMTSymbols     (2),
              oneDMTSymbols      (3),
              twoDMTSymbols      (4),
              threeDMTSymbols    (5),
              fourDMTSymbols     (6),
              fiveDMTSymbols     (7),
              sixDMTSymbols      (8),
              sevenDMTSymbols    (9),
              eightDMTSymbols    (10),
              nineDMTSymbols     (11),
              tenDMTSymbols      (12),
              elevenDMTSymbols   (13),
              twelveDMTSymbols   (14),
              thirteenDMTSymbols (15),
              fourteenDMTSymbols (16),
              fifteenDMTSymbols  (17),
              sixteenDMTSymbols  (18)
             }

             MAX-ACCESS  read-write
             STATUS      current
             DESCRIPTION
                 "The minimum amount of impulse noise protection,
                 measured as 0 DMT symbols, 0.5 DMT symbols (250
                 microseconds per DMT symbol), or 1-16 DMT symbols.
                 This is for the downstream direction."
         ::= { adTAOctAdslConfProfileExtEntry 7 }


    adTAOctAdslAturConfProfileInterleaveMinInpRev2  OBJECT-TYPE
             SYNTAX INTEGER {
              zeroDMTSymbols     (1),
              halfDMTSymbols     (2),
              oneDMTSymbols      (3),
              twoDMTSymbols      (4),
              threeDMTSymbols    (5),
              fourDMTSymbols     (6),
              fiveDMTSymbols     (7),
              sixDMTSymbols      (8),
              sevenDMTSymbols    (9),
              eightDMTSymbols    (10),
              nineDMTSymbols     (11),
              tenDMTSymbols      (12),
              elevenDMTSymbols   (13),
              twelveDMTSymbols   (14),
              thirteenDMTSymbols (15),
              fourteenDMTSymbols (16),
              fifteenDMTSymbols  (17),
              sixteenDMTSymbols  (18)
             }

             MAX-ACCESS  read-write
             STATUS      current
             DESCRIPTION
                 "The minimum amount of impulse noise protection,
                 measured as 0 DMT symbols, 0.5 DMT symbols (250
                 microseconds per DMT symbol), or 1-16 DMT symbols.
                 This is for the upstream direction."
         ::= { adTAOctAdslConfProfileExtEntry 8 } 
         
-- *************************
    adTAOctAdslConfLineTable   OBJECT-TYPE
        SYNTAX          SEQUENCE OF AdTAOctAdslConfLineEntry
        MAX-ACCESS      not-accessible
        STATUS          current
        DESCRIPTION
            "This table is patterned after the adslLineTable and
             includes common attributes describing
             both ends of the line.  It applies to all ADSL
             physical interfaces.  ADSL physical interfaces are
             those ifEntries where ifType is equal to adsl(94)."
        ::= { adTAOctAdslProv2 2 }

    adTAOctAdslConfLineEntry   OBJECT-TYPE
        SYNTAX          AdTAOctAdslConfLineEntry
        MAX-ACCESS      not-accessible
        STATUS          current
        DESCRIPTION     "An entry in adTAOctAdslConfLineTable."
        INDEX           { ifIndex }
        ::= { adTAOctAdslConfLineTable 1 }

    AdTAOctAdslConfLineEntry ::=
        SEQUENCE {
            adTAOctAdslHamBandMask
            INTEGER,
            adTAOctAdslCabinetMode
            INTEGER,
	    adTAOctAdslPowerThreshold
	    INTEGER,
            adTAOctAdslAtucCarrierMask
            OCTET STRING,
            adTAOctAdslAturCarrierMask
            OCTET STRING
            }

   adTAOctAdslHamBandMask OBJECT-TYPE
        SYNTAX      INTEGER {
                    enable    (1),
                    disable   (2)
                    }
        MAX-ACCESS  read-write
        STATUS      current
        DESCRIPTION
            "Used to enable/disable the hamband mask
             for the indexed ADSL port. This object is
             only valid for lines trained using ADSL2+
             service mode"
        ::= { adTAOctAdslConfLineEntry 1 }

   adTAOctAdslCabinetMode OBJECT-TYPE
        SYNTAX      INTEGER {
                    disable(1),
                    enableTone110(2),
                   	enableTone130(3),
                    enableTone250(4)
                    }
        MAX-ACCESS  read-write
        STATUS      current
        DESCRIPTION
            "Used to enable/disable cabinet mode
             for the indexed ADSL port. The different
             enable options determine which starting
             tone to use. This object is only valid
             for lines trained using ADSL2+ service
             mode."
        ::= { adTAOctAdslConfLineEntry 2 }


   adTAOctAdslPowerThreshold OBJECT-TYPE
        SYNTAX      INTEGER {
                    disable(1),
                    dBm10(2),
                    dBm12(3),
                    dBm14(4)
                    }
        MAX-ACCESS  read-write
        STATUS      current
        DESCRIPTION
            "Used to set the max ADSL tx power.
	     Disabled = no restriction,
	     dBm14 = max tx power 14 dBm,
	     dBm12 = max tx power 12 dBm,
	     dBm10 = max tx power 10 dBm"

        ::= { adTAOctAdslConfLineEntry 3 }


   adTAOctAdslAtucCarrierMask OBJECT-TYPE
       SYNTAX  OCTET STRING
       MAX-ACCESS  read-write
       STATUS  current
       DESCRIPTION
            "Per port Subcarrier Masking. In big endian order, each bit
             represents a tone from 0 to 63 in the upstream direction. Writing a 1 to a given bit
             location enables a tone. Writing a 0 disables a tone.
             Ex. Writing 0xff50 alone will enable tones 0-7,9, and 11 and disable tones 8,10, and 12-15.
             The remaining tones are implied to be enabled since they were not included in the
             write operation."
       ::= { adTAOctAdslConfLineEntry 4 }

   adTAOctAdslAturCarrierMask OBJECT-TYPE
   	   SYNTAX  OCTET STRING
   	   MAX-ACCESS  read-write
   	   STATUS  current
   	   DESCRIPTION
            "Per port Subcarrier Masking. In big endian order, each bit
             represents a tone from 0 to 511 in the downstream direction. Writing a 1 to a given bit
             location enables a tone. Writing a 0 disables a tone.
             Ex. Writing 0xff50 alone will enable tones 0-7,9, and 11 and disable tones 8,10, and 12-15.
             The remaining tones are implied to be enabled since they were not included in the
             write operation."
   	   ::= { adTAOctAdslConfLineEntry 5 }


-- *************************
    adTAOctAdslLineTable   OBJECT-TYPE
        SYNTAX          SEQUENCE OF AdTAOctAdslLineEntry
        MAX-ACCESS      not-accessible
        STATUS          current
        DESCRIPTION
            "This table is patterned after the adslLineTable and
             includes common attributes describing
             both ends of the line.  It applies to all ADSL
             physical interfaces.  ADSL physical interfaces are
             those ifEntries where ifType is equal to adsl(94)."
        ::= { adTAOctAdslStatus2 1 }

    adTAOctAdslLineEntry   OBJECT-TYPE
        SYNTAX          AdTAOctAdslLineEntry
        MAX-ACCESS      not-accessible
        STATUS          current
        DESCRIPTION     "An entry in adTAOctAdslLineTable."
        INDEX           { ifIndex }
        ::= { adTAOctAdslLineTable 1 }

    AdTAOctAdslLineEntry ::=
        SEQUENCE {
            adTAOctAdslCurrLinkStatus
            INTEGER,
            adTAOctAdslCurrStandard
            INTEGER,
            adTAOctAdslBitAllocationMap
            OCTET STRING,
            adTAOctAdslBitAllocationMapGroup2
            OCTET STRING,
            adTAOctAdslUsSnrMarginMap
            OCTET STRING
            }

    adTAOctAdslCurrLinkStatus OBJECT-TYPE
    SYNTAX      INTEGER {
                up (1),
                down (2),
                testing (3),
                training (4)
                }
    MAX-ACCESS  read-only
    STATUS      current
    DESCRIPTION
        "The current status of the line (i.e., the link
         between the ATUC and ATUR)."
         ::= { adTAOctAdslLineEntry 1 }

   adTAOctAdslCurrStandard OBJECT-TYPE
        SYNTAX      INTEGER {
                    reserved    (1),
                    t1413       (2),       -- T1.413 Mode
                    gDMT        (3),       -- G.dmt Mode
                    gLite       (4),       -- G.lite Mode
                    g9923       (5),       -- ADSL2 Mode
                    g9924       (6),       -- ADSL2-lite Mode
                    g9925       (7),       -- ADSL2+ Mode
                    readsl      (8),        -- READSL Mode
                    adsl1MultiMode (9),    -- adsl legacy multimode, to be used by adsl2+ line cards to
                                           --  enable multimode equivalent to that of adsl line cards
                    g9925AnxM      (10)    -- ADSL2+ Annex M Mode
--                  vdsl_vm_vdsl1  (11),      placeholder
--                  vdsl_vm_vdsl2  (12),      placeholder
--                  vdsl_vdsl2_multi_mode (13),   placeholder
--                  vdsl_vm_xtse_multimode  (255)   placeholder
                    }
        MAX-ACCESS  read-only
        STATUS      current
        DESCRIPTION
            "The standard governing the link
             between the ATUC and ATUR."
        ::= { adTAOctAdslLineEntry 2 }

   adTAOctAdslBitAllocationMap OBJECT-TYPE
       SYNTAX  OCTET STRING (SIZE(128))
       MAX-ACCESS  read-only
       STATUS  current
       DESCRIPTION
            "Per port Bit Allocation Table. 256 nibbles are represented.
             For each byte bits 4-7 map to the first sub-carrier, bits 0-3 map
             to the second sub-carrier."
       ::= { adTAOctAdslLineEntry 3 }

   adTAOctAdslBitAllocationMapGroup2 OBJECT-TYPE
   	   SYNTAX  OCTET STRING (SIZE(128))
   	   MAX-ACCESS  read-only
   	   STATUS  current
   	   DESCRIPTION
            "Per port Bit Allocation Table tones 256-511. 256 nibbles are represented.
   	   		 For each byte bits 4-7 map to the first sub-carrier, bits 0-3 map
   	   		 to the second sub-carrier."
   	   ::= { adTAOctAdslLineEntry 4 }     
   	      	   
   adTAOctAdslUsSnrMarginMap OBJECT-TYPE
       SYNTAX  OCTET STRING (SIZE(128))
	   UNITS       "0.1 dB"
       MAX-ACCESS  read-only
       STATUS  current
       DESCRIPTION
            "Per port Signal-to-Noise Ratio table. Each two bytes represents the 
             upstream margin in tenth dB per tone."
       ::= { adTAOctAdslLineEntry 5 }

--************************************************************

      adTAOctAdslAtucPhysTable       OBJECT-TYPE
       SYNTAX          SEQUENCE OF AdTAOctAdslAtucPhysEntry
       MAX-ACCESS      not-accessible
       STATUS          current
       DESCRIPTION
           "This table provides one row for each ATUC.
           Each row contains the Physical Layer Parameters
           table for that ATUC. ADSL physical interfaces are
           those ifEntries where ifType is equal to adsl(94)."
         ::= {  adTAOctAdslStatus2 2 }


   adTAOctAdslAtucPhysEntry       OBJECT-TYPE
       SYNTAX          AdTAOctAdslAtucPhysEntry
       MAX-ACCESS      not-accessible
       STATUS          current
       DESCRIPTION     "An entry in the adTAOctAdslAtucPhysTable."
       INDEX           { ifIndex }
         ::= { adTAOctAdslAtucPhysTable 1 }

   AdTAOctAdslAtucPhysEntry ::=
       SEQUENCE {

            adTAOctAdslAtucNumParityBytes
            Integer32,
            adTAOctAdslAtucFramesPerCodeword
            Integer32,
            adTAOctAdslAtucInterleavingDepth
            Integer32
            
       }

    adTAOctAdslAtucNumParityBytes OBJECT-TYPE
       SYNTAX      Integer32
       MAX-ACCESS  read-only
       STATUS      current
       DESCRIPTION
            "Number of Reed-Solomon parity bytes per frame. The value corresponds to the
            parameter R. This value is only valid when the link is up."
         ::= { adTAOctAdslAtucPhysEntry 2 }

    adTAOctAdslAtucFramesPerCodeword OBJECT-TYPE
       SYNTAX      Integer32
       MAX-ACCESS  read-only
       STATUS      current
       DESCRIPTION
            "Hundredth downstream frames per codeword. For G.dmt Mode and G.lite Mode
             this value corresponds to the data-frames per DMT-symbol. For ADSL2, ADSL2lite,
             and ADSL2+ modes the value corresponds to the mux data frames per codeword in a
             particular latency path. This value is only valid when the link is up."
         ::= { adTAOctAdslAtucPhysEntry 3 }

    adTAOctAdslAtucInterleavingDepth OBJECT-TYPE
       SYNTAX      Integer32
       MAX-ACCESS  read-only
       STATUS      current
       DESCRIPTION
            "Interleaving depth. The value corresponds to the parameter D.
             This value is only valid when the link is up."
         ::= { adTAOctAdslAtucPhysEntry 4 }


--************************************************************

      adTAOctAdslAturPhysTable       OBJECT-TYPE
       SYNTAX          SEQUENCE OF AdTAOctAdslAturPhysEntry
       MAX-ACCESS      not-accessible
       STATUS          current
       DESCRIPTION
           "This table provides one row for each ATUR.
           Each row contains the Physical Layer Parameters
           table for that ATUR. ADSL physical interfaces are
           those ifEntries where ifType is equal to adsl(94)."
         ::= {  adTAOctAdslStatus2 3 }


   adTAOctAdslAturPhysEntry       OBJECT-TYPE
       SYNTAX          AdTAOctAdslAturPhysEntry
       MAX-ACCESS      not-accessible
       STATUS          current
       DESCRIPTION     "An entry in the adTAOctAdslAturPhysTable."
       INDEX           { ifIndex }
         ::= { adTAOctAdslAturPhysTable 1 }

   AdTAOctAdslAturPhysEntry ::=
       SEQUENCE {

            adTAOctAdslAturNumParityBytes
            Integer32,
            adTAOctAdslAturFramesPerCodeword
            Integer32,
            adTAOctAdslAturInterleavingDepth
            Integer32,
            adTAOctAdslAturCapabilities
            Integer32,
            adTAOctAdslAturInvProviderCode
            SnmpAdminString

       }

    adTAOctAdslAturNumParityBytes OBJECT-TYPE
       SYNTAX      Integer32
       MAX-ACCESS  read-only
       STATUS      current
       DESCRIPTION
            "Number of Reed-Solomon parity bytes per frame. The value corresponds to the
            parameter R. This value is only valid when the link is up."
         ::= { adTAOctAdslAturPhysEntry 2 }

    adTAOctAdslAturFramesPerCodeword OBJECT-TYPE
       SYNTAX      Integer32
       MAX-ACCESS  read-only
       STATUS      current
       DESCRIPTION
            "Hundredth upstream frames per codeword. For G.dmt Mode and G.lite Mode
             this value corresponds to the data-frames per DMT-symbol. For ADSL2, ADSL2lite,
             and ADSL2+ modes the value corresponds to the mux data frames per codeword in a
             particular latency path. This value is only valid when the link is up."
         ::= { adTAOctAdslAturPhysEntry 3 }

    adTAOctAdslAturInterleavingDepth OBJECT-TYPE
       SYNTAX      Integer32
       MAX-ACCESS  read-only
       STATUS      current
       DESCRIPTION
            "Interleaving depth. The value corresponds to the parameter D.
             This value is only valid when the link is up."
         ::= { adTAOctAdslAturPhysEntry 4 }
    
    adTAOctAdslAturCapabilities OBJECT-TYPE
       SYNTAX      Integer32 (1..1048575)
       MAX-ACCESS  read-only
       STATUS      current
       DESCRIPTION
            "The ATUR capabilities is a listing of ADSL properties 
             on a port.  It is bit-masked (0 for disabled, 1 for 
             enabled) in the following way:
             Bit    Capability
             ---    ----------
             0      Full Rate ADSL over ISDN
             1      Full Rate ADSL over ISDN
             2      Full Rate ADSL in TCM-ISDN
             3      Lite ADSL Over POTS/ISDN
             4      Lite ADSL in TCM-ISDN
             5      SSDSL in ISDN Binder
             6      All Digital ADSL
             7      ADSL2 Over POTS
             8      ADSL2 Over ISDN
             9      All Digital ADSL2 (POTS)
             10     All Digital ADSL2 (ISDN)
             11     ADSL2 Lite Over POTS
             12     All Digital ADSL2 Lite
             13     ADSL2+ over POTS
             14     ADSL2+ over ISDN
             15     All Digital ADSL2+ (POTS)
             16     Double Upstream ADSL2
             17     All Digital ADSL2+ (ISDN)
             18     Double Upstream ADSL2+
             19     RE-ADSL2 Over POTS"  
         ::= { adTAOctAdslAturPhysEntry 5 }
         
    adTAOctAdslAturInvProviderCode OBJECT-TYPE
       SYNTAX      SnmpAdminString
       MAX-ACCESS  read-only
       STATUS      current
       DESCRIPTION
            "The provider code is a copy of the binary
             provider code field defined by the PHY[10]
             and expressed as readable characters."
         ::= { adTAOctAdslAturPhysEntry 6 }
         
--************************************************************
    adTAOctAdslAtucChanTable       OBJECT-TYPE
        SYNTAX          SEQUENCE OF AdTAOctAdslAtucChanEntry
        MAX-ACCESS      not-accessible
        STATUS          current
        DESCRIPTION
            "This table provides one row for each ATUR channel.
            ADSL channel interfaces are those ifEntries
            where ifType is equal to adslInterleave(124)
            or adslFast(125)."
    ::= { adTAOctAdslStatus2 4 }


    adTAOctAdslAtucChanEntry       OBJECT-TYPE
        SYNTAX          AdTAOctAdslAtucChanEntry
        MAX-ACCESS      not-accessible
        STATUS          current
        DESCRIPTION     "An entry in the adTAOctAdslAAtucChanTable."
        INDEX           { ifIndex }
    ::= {adTAOctAdslAtucChanTable  1 }

    AdTAOctAdslAtucChanEntry ::=
        SEQUENCE {
        adTAOctAdslAtucChanINP         Gauge32,
        adTAOctAdslAtucRelativeCap	   Gauge32
        }
        
    -- current group
    --
         adTAOctAdslAtucChanINP OBJECT-TYPE
             SYNTAX      Gauge32
             UNITS       "0.01 dmt symbols"
             MAX-ACCESS  read-only
             STATUS      current
             DESCRIPTION
                 "Current impulse noise protection on this channel,
                 measured in increments of 0.01 DMT symbols."
         ::= { adTAOctAdslAtucChanEntry 1 }
         
         adTAOctAdslAtucRelativeCap OBJECT-TYPE
             SYNTAX      Gauge32
             UNITS       "0.1 percent"
             MAX-ACCESS  read-only
             STATUS      current
             DESCRIPTION
                 "Relative capacity of the ADSL line being used measured
                  by percentage."
         ::= { adTAOctAdslAtucChanEntry 2 }



    adTAOctAdslAturChanTable       OBJECT-TYPE
        SYNTAX          SEQUENCE OF AdTAOctAdslAturChanEntry
        MAX-ACCESS      not-accessible
        STATUS          current
        DESCRIPTION
            "This table provides one row for each ATUR channel.
            ADSL channel interfaces are those ifEntries
            where ifType is equal to adslInterleave(124)
            or adslFast(125)."
    ::= { adTAOctAdslStatus2 5 }



    adTAOctAdslAturChanEntry       OBJECT-TYPE
        SYNTAX          AdTAOctAdslAturChanEntry
        MAX-ACCESS      not-accessible
        STATUS          current
        DESCRIPTION     "An entry in the adTAOctAdslAAturChanTable."
        INDEX           { ifIndex }
    ::= { adTAOctAdslAturChanTable 1 }

    AdTAOctAdslAturChanEntry ::=
        SEQUENCE {
        adTAOctAdslAturChanINP       Gauge32,
        adTAOctAdslAturRelativeCap   Gauge32
        }

    -- current group
    --
         adTAOctAdslAturChanINP OBJECT-TYPE
             SYNTAX      Gauge32
             UNITS       "0.01 dmt symbols"
             MAX-ACCESS  read-only
             STATUS      current
             DESCRIPTION
                 "Current impulse noise protection on this channel,
                 measured in increments of 0.01 DMT symbols."
         ::= { adTAOctAdslAturChanEntry 1 } 
         
         adTAOctAdslAturRelativeCap OBJECT-TYPE
             SYNTAX      Gauge32
             UNITS       "0.1 percent"
             MAX-ACCESS  read-only
             STATUS      current
             DESCRIPTION
                 "Relative capacity of the ADSL line being used measured
                  by percentage."
         ::= { adTAOctAdslAturChanEntry 2 }

            
--************************************************************
    adTAOctAdslAtmAtucCellCountTable       OBJECT-TYPE
        SYNTAX          SEQUENCE OF AdTAOctAdslAtmAtucCellCountEntry
        MAX-ACCESS      not-accessible
        STATUS          current
        DESCRIPTION
            "This table provides one row for each ATM ATUC 
             cell count."
    ::= { adTAOctAdslStatus2 6 }


    adTAOctAdslAtmAtucCellCountEntry       OBJECT-TYPE
        SYNTAX          AdTAOctAdslAtmAtucCellCountEntry
        MAX-ACCESS      not-accessible
        STATUS          current
        DESCRIPTION     "An entry in the AdTAOctAdslAtmAtucCellCountEntry."
        INDEX           { ifIndex }
    ::= {adTAOctAdslAtmAtucCellCountTable  1 }

    AdTAOctAdslAtmAtucCellCountEntry ::=
        SEQUENCE {
        adTAOctAdslAtmAtucCellCount     Unsigned32,
        adTAOctAdslAtmAtucIdleCellCount Unsigned32,
        adTAOctAdslAtmAtucHecErrorCount Unsigned32        
        }

    adTAOctAdslAtmAtucCellCount OBJECT-TYPE
        SYNTAX      Unsigned32
        MAX-ACCESS  read-only
        STATUS      current
        DESCRIPTION
            "The ATUC cell count is the sum of all ATM cells
             from all VCIs on a given port."
    ::= { adTAOctAdslAtmAtucCellCountEntry 1 }
  
    adTAOctAdslAtmAtucIdleCellCount OBJECT-TYPE
        SYNTAX      Unsigned32
        MAX-ACCESS  read-only
        STATUS      current
        DESCRIPTION
            "The ATUC idle cell count is the sum of all 
             idle ATM cells from all VCIs on a given port."
    ::= { adTAOctAdslAtmAtucCellCountEntry 2 }

    adTAOctAdslAtmAtucHecErrorCount OBJECT-TYPE
        SYNTAX      Unsigned32
        MAX-ACCESS  read-only
        STATUS      current
        DESCRIPTION
            "The ATUC HEC Error count is the sum of all HEC
             errors from all VCIs on a given port."
    ::= { adTAOctAdslAtmAtucCellCountEntry 3 }

--************************************************************
    adTAOctAdslAtmAturCellCountTable       OBJECT-TYPE
        SYNTAX          SEQUENCE OF AdTAOctAdslAtmAturCellCountEntry
        MAX-ACCESS      not-accessible
        STATUS          current
        DESCRIPTION
            "This table provides one row for each ATM ATUR 
             cell count."
    ::= { adTAOctAdslStatus2 7 }


    adTAOctAdslAtmAturCellCountEntry       OBJECT-TYPE
        SYNTAX          AdTAOctAdslAtmAturCellCountEntry
        MAX-ACCESS      not-accessible
        STATUS          current
        DESCRIPTION     "An entry in the AdTAOctAdslAtmAturCellCountEntry."
        INDEX           { ifIndex }
    ::= {adTAOctAdslAtmAturCellCountTable  1 }

    AdTAOctAdslAtmAturCellCountEntry ::=
        SEQUENCE {
        adTAOctAdslAtmAturCellCount     Unsigned32,
        adTAOctAdslAtmAturIdleCellCount Unsigned32        
        }

    adTAOctAdslAtmAturCellCount OBJECT-TYPE
        SYNTAX      Unsigned32
        MAX-ACCESS  read-only
        STATUS      current
        DESCRIPTION
            "The ATUR cell count is the sum of all ATM cells
             from all VCIs on a given port."
    ::= { adTAOctAdslAtmAturCellCountEntry 1 }
                      
    adTAOctAdslAtmAturIdleCellCount OBJECT-TYPE
        SYNTAX      Unsigned32
        MAX-ACCESS  read-only
        STATUS      current
        DESCRIPTION
            "The ATUR idle cell count is the sum of all 
             idle ATM cells from all VCIs on a given port."
    ::= { adTAOctAdslAtmAturCellCountEntry 2 }
         
    END

ADTRAN-TAeSCU-MIB

    DEFINITIONS ::= BEGIN

    -- TITLE:     The ADTRAN enhanced System Controller Unit MIB
    -- PRODUCT:   1181018L1
    -- VERSION:   2.13
    -- DATE:      10/12/07

    -- This MIB defines the object identifier (OID) for the Total Access
    -- 3000 enhanced SCU. It also defines product specific objects.

    -- MIBs supported:
    --   MIB-2 (RFC1213)
    --   Interface types (IANAifType - Internet Assigned Numbers Authority)
    --   Interfaces (RFC2863)
    --   ADTRAN standard (ADTRAN)
    --   ADTRAN textual conventions (adtrantc)
    --   ADTRAN generic chassis (genchass)
    --   ADTRAN generic slot (genslot)
    --   ADTRAN generic port (genport)
    --   ADTRAN generic eSCU (genescu)
    --   ADTRAN shelf specific OID MIB (adta3000, adta3010)
    --   ADTRAN product specific eSCU 018 (adtaescu)
    --   Proxy agent for SNMP access to all cards in TA3000 shelves.

    --  adGenSlotFaceplate (genslot)
   --  SCU 1181018L1 has single color LED
   --  The SCU 1181018L1 returns a 4 byte string.
   --  byte 1 FSE  - Red fuse LED (always off)    00 off 01 on
   --  byte 2 ALM  - Red Alarm status LED         00 off 01 on
   --  byte 3 HST  - Green LED 00 Client 01 Host  00 off 01 on
   --  byte 4 ACO  - Green LED                    00 off 01 on
   --  LED byte position description
   --  1  2
   --  3  4

    --  adGenSlotFaceplate (genslot)
   --  SCU 1181018L2 has single color LED
   --  The SCU 1181018L2 returns 7 byte string.
   --  byte 1 PWR  - Green LED (always on, green) 00 off 01 on
   --  byte 2 ENET - Green Ethernet LINK status   00 off 01 on
   --  byte 3 HOST - Green LED 00 Client 01 Host  00 off 01 on
   --  byte 4 CRI  - Red   Alarm LED CRITICAL     00 off 01 on
   --  byte 5 MAJ  - Red   Alarm LED MAJOR        00 off 01 on
   --  byte 6 MIN  - Red   Alarm LED MINOR        00 off 01 on
   --  byte 7 ACO  - Green LED                    00 off 01 on

    -- adGenSlotAlarmStatus description
   -- The various bit positions are:
   -- ==========================================================================
   --   Bit 1-16 scu alarm/status Byte 1 - 2  Details below->
   --   Bit 17-136 Card per slot Remove alams  Byte 3 - 17
   --   Bit 137 - 256 Card fuse blown alarms for each slot  Byte 18 - 32
   -- =========================================================================
   -- Bits Details for 1-16 scu alarm/status  Byte 1 -2
   -- ==========================================================================
   --   bit 1 Indicate that a alarm is present on the SCU.
   --   bit 2 "Indicates whether or not the alarm cut-off is on."
   --   bit 3 "Indicates whether or not the alarm cut-off input is active."
   --   bit 4 (adTAeSCUCtrpRmtAlm) "remote alarm input is active."
   --   bit 5 (adTAeSCUCtrpExt1Alm) "external alarm input #1 is active."
   --   bit 6 (adTAeSCUCtrpExt2Alm) "external alarm input #2 is active."
   --   bit 7 (adTAeSCUCtrpBusApowerAlm) "Iminus 48V power supply A is active."
   --   bit 8 (adTAeSCUCtrpBusBpowerAlm) "minus 48V power supply B is active."
   --   bit 9 Device comm failure.  This is not a SNMP alarm.
   --   bit 10 "Indicates whether one or more card fuses on this chassis is open."
   --   bit 11 adTAeSCUCraftLoginNotfication
   --   bit 12 adTAPowerSheddingInputAsserted
   --   bit 13 adTAPowerSheddingActivated
   --   bit 14 Empty
   --   bit 15 Empty
   --   bit 16 Empty
   -- ==========================================================================
   -- Bits Detail 17-56 Card slot blown fuses 4 bytes
   -- ==========================================================================
   --   Bits 17-24 for slot 8 - 1 card blown fuse alarm status     byte 3
   --   Bits 25-32 for slot 16 - 9 card blown fuse status    byte 4
   --   Bits 33-40 for slot 24 - 17 card blown fuse status   byte 5
   --   Bits 41-48 for slot 32 - 25 card blown fuse status   byte 6
   --   Bits 49-56 Empty
   -- ==========================================================================
   --   Bits 57-56 Empty
   -- ==========================================================================
   --   Bits 58 adTACriticalAudibleRelayActive
   --   Bits 59 adTACriticalVisualRelayActive
   --   Bits 60 adTAMajAudibleRelayActive
   --   Bits 61 adTAMajVisualRelayActive
   --   Bits 62 adTAMinorAudibleRelayActive
   --   Bits 63 adTAMinorVisualRelayActive
   --   Bits 64 adTAAux1RelayActive
   --   Bits 65 adTAAux2RelayActive
   --   ...
   --   Bits 129-136 slot 112 - 113 scu blown fuse byte 17
   -- ==========================================================================
   -- Bits Detail 137-256 represents card remove alarm present 15 bytes
   -- ==========================================================================
   --   Bits 137-144 for slot 8 - 1 card remove alarm status     byte 18
   --   Bits 145-152 for slot 16 - 9 card remove alarm status    byte 19
   --   Bits 153-160 for slot 24 - 17 card remove alarm status   byte 20
   --   Bits 161-168 for slot 32 - 25 card remove alarm status   byte 21
   --   ...
   --   Bits 249-256 for slot 120 - 113 card remove alarm status byte 32

    -- HISTORY:
       -- 14/11/01 pnb First edition.
       -- 03/05/01 pnb ad Boot Version object to this MIB for ATP.
       -- 01/22/02 ap  Added SNMP security account management support
       -- 06/13/02 ap  Add Software Configuration Archive, DNS, System Log, and
       --              other support OIDs changes.
       -- 06/14/02 RJF Change 'adTAeScuFirmwareTftpServerHostName' from read-only to read-write
       -- 06/28/02  ap add adTAeScuSCAAutoSave and adTAeScuSCAAutoSaveRetries and remove adTAeScuSCAAutoSaveInterval
       -- 07/23/02  ap Ver 2.0 MIB changes to work with SCU versions C00.18 and above:
                    --- Add objects adTAeSCUDefaultRouteInterfaceEx, adTAeSCUIpForwarding, adTAeSCURestoreNetProvFromMUX,
                    --- adTAESCUSecChangeAccountPassword and the following tables and groups:
                    --- Network Management Group            adTAeSCUNetworkMgmt
                    --- DNS related managment               adTAeSCUsDNS
                    --- Sofware/Config through TFTP         adTAeSCUFirmwareTFTPConfigMgmt
                    --- SCA () Sofware/Config related dids  adTAeSCUSystemConfigArchiveMgmt
                    --- SCA Auto Save Management            adTAeSCUSCAControl
                    --- SCA Status table                    adTAeSCUSCAOperationStatusTable
                    --- SCA Auto Save Management            adTAeSCUSCAAutoSaveMgmt
                    --- SCA Restore Management              adTAeSCUSCARestoreMgmt
                    --- System Log group                    adTAeSCUSystemLog
       -- 08/05/02  ap  Add integer limit to adTAeScuSCAAutoSaveHoursAfter and  adTAeScuSCAAutoSaveMinutesAfter.
       -- 21/02/03  ap  Change trap level NORMAL to INFORMATIONAL
       -- 08/15/03  ap  Add support adTAeScuFirmwareTftpCacheExpire and adTAeScuFirmwareTftpInvalidate
       -- 03/11/03  ap  Add adGenSlotAlarmStatus description
            -- adGenSlotAlarmStatus description
            -- The various bit positions are:
               -- ==========================================================================
               --   Bit 1-16 scu alarm/status Byte 1 - 2  Details below->
               --   Bit 17-136 Card per slot Remove alams  Byte 3 - 17
               --   Bit 137 - 256 Card fuse blown alarms for each slot  Byte 18 - 32
               -- =========================================================================
               -- Bits Details for 1-16 scu alarm/status  Byte 1 -2
               -- ==========================================================================
               --   bit 1 Indicate that a alarm is present on the SCU.
               --   bit 2 "Indicates whether or not the alarm cut-off is on."
            --   bit 3 "Indicates whether or not the alarm cut-off input is active."
            --   bit 4 (adTAeSCUCtrpRmtAlm) "remote alarm input is active."
            --   bit 5 (adTAeSCUCtrpExt1Alm) "external alarm input #1 is active."
            --   bit 6 (adTAeSCUCtrpExt2Alm) "external alarm input #2 is active."
            --   bit 7 (adTAeSCUCtrpBusApowerAlm) "Iminus 48V power supply A is active."
            --   bit 8 (adTAeSCUCtrpBusBpowerAlm) "minus 48V power supply B is active."
               --   bit 9 Device comm failure.  This is not a SNMP alarm.
            --   bit 10 "Indicates whether one or more card fuses on this chassis is open."
            --   bit 11 to 16 Nothing (Empty)
               -- ==========================================================================
               -- Bits Detail 17-136 Card slot blown fuses 15 bytes
               -- ==========================================================================
            --   Bits 17-24 for slot 8 - 1 card blown fuse alarm status     byte 3
            --   Bits 25-32 for slot 16 - 9 card blown fuse status    byte 4
            --   Bits 33-40 for slot 24 - 17 card blown fuse status   byte 5
            --   Bits 41-48 for slot 32 - 25 card blown fuse status   byte 6
            --   ...
            --   Bits 129-136 slot 112 - 113 scu blown fuse byte 17
               -- ==========================================================================
            -- Bits Detail 137-256 represents card remove alarm present 15 bytes
               -- ==========================================================================
            --   Bits 137-144 for slot 8 - 1 card remove alarm status     byte 18
            --   Bits 145-152 for slot 16 - 9 card remove alarm status    byte 19
            --   Bits 153-160 for slot 24 - 17 card remove alarm status   byte 20
            --   Bits 161-168 for slot 32 - 25 card remove alarm status   byte 21
            --   ...
            --   Bits 249-256 for slot 120 - 113 card remove alarm status byte 32
               -- ==========================================================================
               -- ==========================================================================
    -- 09/11/03   AP    Add configAccess(7) to adTAeSCUSecAccountAccessRights.
    -- 10/20/03   AP    fix syntax error on line 472.
    -- 01/19/04   AP    Add accessoryOption(4) to adTAeSCUNetworkMgmtPortComMode
    -- 01/29/04   AP    For SCA OIDs DB0 corresponds to the  Accessory Slot. (Comment change)
    -- 04/15/04   AP    Add adTAeScuTL1ActivityLog
    -- 12/28/04   AP    Add password complexity, Add Account and Password aging, Add RADIUS login options
    -- 04/20/05   AP    Add adTAeTrustedClientAccessControl
    -- 10/20/05   AP    Add adTAeSCUCraftLoginNotfication
    -- 02/03/06   KMM   Additional changes made while adding support for packed
    --                  sstate msgs. Added:
    --                     *) service state set single fail
    --                     *) service state get single fail
    --                     *) service state set all fail
    --                     *) service state get all fail
    -- 04/03/06   KMM   Removed alarms added on 02/03/06. These are auto-clearing alarms, therefore
    --                  do not have alarm status.
    -- 05/09/06   JMC   Added power shedding bit definitions to commments.
    --                  Standardized last section of these comments, it was ugly!
    -- 10/05/06   MAS   Added support for MII Ethernet and ENET interface
    -- 07/11/07   AP    Fix adTAeSCUSystemLogEntry index.  Add (adTAeSCUSystemLogIndex).
    -- 08/29/07   AP    Add adTAeSCUSecLastSixPasswordCheck and adTAeSCUSecPasswordStartEndDigitCheck
    -- 09/24/07   AP    Add adTAeSCUSecLoginStatTable.
    -- 10/12/07   AP    Add adTAeScuRADIUSFallbackMode
    -- 11/01/07   AP    Change adTAeSCUNetworkMgmtPortBaudRate description.
    -- 11/12/07   KABC  Added adTAeSCUSecAccountConnectionPort and adTAeSCUSecAccountDisconnectSession
    -- 11/13/07   KABC  Added Account Lock-out Settings Section:
    --                     adTAeScuEnableAccLoginFailureLockOut, adTAeScuEnableLockOutAlarm,
    --                     adTAeScuEnableIndefLockOut, adTAeScuNumLockOutLoginAttempts,
    --                     and adTAeScuLockOutDuration
    -- 11/16/07   KABC Added adTAeSCUSecChallengeKey, adTAeSCUSecMultiLoginAcct,and adTAeSCUSecRemoteMenuAccessRequired
    -- 11/27/07   KABC Changed adTAeSCUSecAccountDisconnectSession to read-write from read-only
    -- 01/21/08   BKP  Added osiTunnel(4), pppDCC0(5), and ethernet2(6) enum values to the adTAeSCUDefaultRouteInterfaceEx OID that I don't see any EMS support
    --                 for the OPTI, 5K, or 3K.
    -- 01/28/08   BKP  Added SNMP support for the Mount Location and the Interbank Communication Mode.
    --                 Also added adTAeSCUNetworkMgmtInterbankComModeWritable, adTAeSCULogoffCraftDTRLoss, and adTAeSCUMinMenuRefresh.
    -- 02/01/08   BKP  Removed SNMP support for the Mount Location.
    -- 02/12/08   AP   Fix adTAeSCUSystemLogIndex to be a table OID.
    -- 03/06/08   KABC Added adTAeScuSCASlotsInSCA, adTAeScuSCASlotsWithProvDataInSCA, and adTAeScuSCADateTimeNextAutoSave
    -- 03/07/08   KABC Added adTAeScuSCACardsRestoredBitmask, adTAeScuSCACardsNotRestoredBitmask, adTAeScuSCACardsExcludedBitmask,
    --                 and adTAeScuSCARestoreCardErrorsBitmask
    -- 04/14/08   PEW   Added adTAeSCUSysTACACSPlusConfig (TACACS+ Configuration)
    -- 04/24/08   AP   Add adTAeSCUSecAccountAuthenticationMethod
    -- 05/14/08   AP   Add adTAeSCUSystemLogFailureDescription
    -- 10/31/08   AP   Add adTAeScuTACACSPlusServerPort
    -- 01/29/09   KABC Added adTAeSCUSecForcePasswordReset
    -- 02/04/09   KABC Added adTAeSCUNetworkMgmtSecurityEnable
    -- 05/05/09   AP   Convert to SNMPv2
    -- 08/07/09   KABC  Added adTAeSUSecSendAcctExpAlarm, adTAeSCUSecResetAllAccountAge, and
    --                  adTAeSCUSecResetAllPasswordAge
    -- 08/12/09   KABC Added adTAeScuTACACSPlusServerName and adTAeScuTACACSPlusServerSequence
    -- 04/08/09   AP   Add adTAeSCUSecLastSessionType, adTAeSCUSecLastConnectionType, and adTAeSCUSecLastIPAddress
    --
    -- Operational notes
      -- When the SCU is addressed by IP address with scalar objects, it usually replies
      -- as a proxy for the shelf in which it is contained, providing MIB-2 system group
      -- support and ADTRAN.MIB object support. To address information on specific cards,
      -- card/port selection can be done via the ADTRAN generic MIBs, or internet standard
      -- MIBs that are indexed by ifIndex. Mapping between these indexing methods is provided
      -- in the genport MIB.
      --
      -- The exception to scalars being processed directely by the SCU are those in Internet
      -- standard MIBs that are specially identified to belong to a Multiplexor, and for which
      -- special provision has been made to direct these anonymous requests to the appropriate
      -- Mux. Otherwise scalars are not supported on line cards as there is no way to select which
      -- card is the intended target.

    IMPORTS
        OBJECT-TYPE,
        NOTIFICATION-TYPE,
        MODULE-IDENTITY,
        OBJECT-IDENTITY,
        Integer32,
        IpAddress
                  FROM SNMPv2-SMI
        DisplayString
                  FROM SNMPv2-TC
        sysName
                  FROM SNMPv2-MIB
        adProducts,
        adMgmt
            FROM ADTRAN-MIB
        adGenSlotInfoIndex
            FROM ADTRAN-GENSLOT-MIB
       adTrapInformSeqNum
            FROM ADTRAN-GENTRAPINFORM-MIB
       InetAddress,
       InetAddressType
            FROM INET-ADDRESS-MIB
    ;

    adTAeSCUmg MODULE-IDENTITY
   LAST-UPDATED "201612090000Z"
   ORGANIZATION "Adtran, Inc."
   CONTACT-INFO
     "CND Tech Support
         Postal: ADTRAN, Inc.
                 901 Explorer Blvd.
                 Huntsville, AL  35806
                 Tel: +1 800 726-8663
                 Fax: +1 256 963 6217
                 E-mail: support@adtran.com"
   DESCRIPTION
      "This MIB defines the objects for the adtranTAeScuMib MIB."
   REVISION "201612070000Z"
   DESCRIPTION "Add InetAddress OIDs to support IPv4/IPv6 addresses for Trusted Access List Clients."
   REVISION "201609200000Z"
   DESCRIPTION "Add the RadiusServerSequence and RadiusName OIDs for Radius servers."
   REVISION "201606130000Z"
   DESCRIPTION "Add support IPV6 address for SCM servers."
   REVISION "201406100000Z"
   DESCRIPTION "Added Bulk Data Export OID for the path."
      REVISION "201208141300Z"
   DESCRIPTION "Added cLI(5) to adTAeSCUNetworkMgmtPortComMode.
                Add adTAeTrustedIPClientAccessName Trusted IP Access-list name.
                Deleted all Trusted IP Clients when set to an empty string."
   REVISION "201207120000Z"
   DESCRIPTION "Added Bulk Data Export OID for the port number."
   REVISION "201204231600Z"
   DESCRIPTION "Add adTAeSCUSystemLogFailureDescription varbind to adTAeSCUSystemLogFailure   NOTIFICATION-TYPE."
   REVISION "201106270000Z"
   DESCRIPTION "Added four OIDs for Bulk Data Export."
   REVISION "200705010000Z"
   DESCRIPTION "Converted from SNMPv1 adTAeSCU.mib file."


::= { adMgmt 241 }

    -- OBJECT IDENTIFIERS

    adTAeSCU                    OBJECT IDENTIFIER ::= { adProducts 241 }
    --adTAeSCUmg                  OBJECT IDENTIFIER ::= { adMgmt 241 }


    --
    -- Configuration Information
    --

    adTAeSCUConfig  OBJECT IDENTIFIER
           ::= { adTAeSCUmg 1 }

    adTAeSCUConfigTable OBJECT-TYPE
        SYNTAX  SEQUENCE OF AdTAeSCUConfigEntry
        MAX-ACCESS  not-accessible
        STATUS  current
        DESCRIPTION
            "The enhanced System Controller Unit Config table."
       ::= { adTAeSCUConfig 1 }

    adTAeSCUConfigEntry OBJECT-TYPE
        SYNTAX  AdTAeSCUConfigEntry
        MAX-ACCESS  not-accessible
        STATUS  current
        DESCRIPTION
            "An entry in the eSCU Config table."
       INDEX   { adGenSlotInfoIndex }
       ::= { adTAeSCUConfigTable 1 }

    AdTAeSCUConfigEntry ::=
        SEQUENCE {
            adTAeSCUBootVersion
                DisplayString
        }

    adTAeSCUBootVersion OBJECT-TYPE
           SYNTAX  DisplayString
           MAX-ACCESS  read-only
           STATUS  current
           DESCRIPTION
               "Firmware version of the boot ROM."
           ::= { adTAeSCUConfigEntry 1 }

    --
    -- Card Provisioning Information
    --

    adTAeSCUCardProv  OBJECT IDENTIFIER
           ::= { adTAeSCUmg 2 }

    adTAeSCUCardProvTable OBJECT-TYPE
        SYNTAX  SEQUENCE OF AdTAeSCUCardProvEntry
        MAX-ACCESS  not-accessible
        STATUS  current
        DESCRIPTION
            "The enhanced System Controller Unit's
       (eSCU's) card-level provisioning table."
       ::= { adTAeSCUCardProv 1 }

    adTAeSCUCardProvEntry OBJECT-TYPE
        SYNTAX  AdTAeSCUCardProvEntry
        MAX-ACCESS  not-accessible
        STATUS  current
        DESCRIPTION
            "An entry in the enhanced System Controller
       Unit's (eSCU's) card-level provisioning table."
       INDEX   { adGenSlotInfoIndex }
       ::= { adTAeSCUCardProvTable 1 }

    AdTAeSCUCardProvEntry ::=
        SEQUENCE {
            adTAeSCUDefaultRouteInterface
                INTEGER,
            adTAeSCUIpForwarding
                INTEGER,
            adTAeSCURestoreNetProvFromMUX
                INTEGER,
            adTAeSCUDefaultRouteInterfaceEx
                INTEGER,
            adTAeSCULogoffCraftDTRLoss
                INTEGER,
            adTAeSCUMinMenuRefresh
                INTEGER
        }

    adTAeSCUDefaultRouteInterface OBJECT-TYPE
        SYNTAX     INTEGER {
           ethernet(1),
           in-band(2)
           }
       MAX-ACCESS  read-write
       STATUS  deprecated
       DESCRIPTION
           "Default Route Interface to be used by
       the Controller."
           ::= { adTAeSCUCardProvEntry 1 }

    adTAeSCUIpForwarding OBJECT-TYPE
        SYNTAX  INTEGER {
                enabled(1),
                disabled(2)
                }
        MAX-ACCESS  read-write
        STATUS  current
        DESCRIPTION
          "Determines wether the eSCU will perform IP forwarding."
        ::= { adTAeSCUCardProvEntry 2 }

    adTAeSCURestoreNetProvFromMUX OBJECT-TYPE
        SYNTAX  INTEGER {
                enabled(1),
                disabled(2)
                }
        MAX-ACCESS  read-write
        STATUS  current
        DESCRIPTION
          "This setting determines whether or not the eSCU will attempt to
          restore its IP network interface settings from the online MUX.
          These settings will be restored only if the eSCU has been removed
          and another eSCU inserted in it place without removal or reset
          of the online MUX.."
        ::= { adTAeSCUCardProvEntry 3}

    adTAeSCUDefaultRouteInterfaceEx OBJECT-TYPE
        SYNTAX     INTEGER {
           ethernet(1),
           in-band(2),
           local-PPP(3),
           osiTunnel(4),
           pppDCC0(5),
           ethernet2(6),
           none(999)
           }
       MAX-ACCESS  read-write
       STATUS  current
       DESCRIPTION
           "Same as adTAeSCUDefaultRouteInterface but added local-PPP(3), osiTunnel(4),
            pppDCC0(5), ethernet2(6), and none(999).  Default Route Interface to be used by
            the Controller."
           ::= { adTAeSCUCardProvEntry 4 }

    adTAeSCULogoffCraftDTRLoss OBJECT-TYPE
        SYNTAX  INTEGER {
                enabled(1),
                disabled(2)
                }
        MAX-ACCESS  read-write
        STATUS  current
        DESCRIPTION
          "When the Data Terminal Ready(DTR) signal from the connected terminal is lost,
           the controller can automatically disable the port connection."
        ::= { adTAeSCUCardProvEntry 5 }

    adTAeSCUMinMenuRefresh OBJECT-TYPE
        SYNTAX  INTEGER {
                normal(1),
                seconds1(2),
                seconds5(3),
                seconds15(4),
                seconds60(5),
                never(6)
                }
        MAX-ACCESS  read-write
        STATUS  current
        DESCRIPTION
          "The minimum terminal menu refresh rate used to limit the frequency of menu refreshing."
        ::= { adTAeSCUCardProvEntry 6 }

    --
    -- Interface Status Information
    --

    adTAeSCUInterfaceStatus  OBJECT IDENTIFIER
           ::= { adTAeSCUmg 4 }

    adTAeSCUInterfaceStatusTable OBJECT-TYPE
        SYNTAX  SEQUENCE OF AdTAeSCUInterfaceStatusEntry
        MAX-ACCESS  not-accessible
        STATUS  current
        DESCRIPTION
            "The controller's interface-level status
       table."
       ::= { adTAeSCUInterfaceStatus 1 }

    adTAeSCUInterfaceStatusEntry OBJECT-TYPE
        SYNTAX  AdTAeSCUInterfaceStatusEntry
        MAX-ACCESS  not-accessible
        STATUS  current
        DESCRIPTION
            "An entry in the controller's interface-level
       status table."
       INDEX   { adTAeSCUIfNumber }
       ::= { adTAeSCUInterfaceStatusTable 1 }

    AdTAeSCUInterfaceStatusEntry ::=
        SEQUENCE {
            adTAeSCUIfNumber
                Integer32,
            adTAeSCUIfIndex
                Integer32,
            adTAeSCUIfIPAddress
                IpAddress,
            adTAeSCUIfSubnetMask
                IpAddress,
            adTAeSCUIfDefaultGateway
                IpAddress,
            adTAeSCUIfSpeed
                INTEGER,
            adTAeSCUIfXoverCorrection
                INTEGER,
            adTAeSCUIfLEDmode
                INTEGER,
            adTAeSCUIfLinkStatus
                INTEGER,
            adTAeSCUIfLinkRate
                INTEGER
        }

    adTAeSCUIfNumber OBJECT-TYPE
        SYNTAX     Integer32
           MAX-ACCESS  read-only
           STATUS  current
           DESCRIPTION
               "Interface Number assigned by the
           Controller to it's interfaces. It is used to
           index this table. It may or may not be equal
           to the corresponding IfIndex."
           ::= { adTAeSCUInterfaceStatusEntry 1 }

    adTAeSCUIfIndex OBJECT-TYPE
        SYNTAX     Integer32
           MAX-ACCESS  read-only
           STATUS  current
           DESCRIPTION
               "This value is equal to the corresponding
           IfIndex for each interface."
           ::= { adTAeSCUInterfaceStatusEntry 2 }

    adTAeSCUIfIPAddress OBJECT-TYPE
        SYNTAX     IpAddress
           MAX-ACCESS  read-only
           STATUS  current
           DESCRIPTION
               "The IP Address assigned to this interface,
           if any."
           ::= { adTAeSCUInterfaceStatusEntry 3 }

    adTAeSCUIfSubnetMask OBJECT-TYPE
        SYNTAX     IpAddress
           MAX-ACCESS  read-only
           STATUS  current
           DESCRIPTION
               "The Subnet Mask assigned to this interface,
           if any."
           ::= { adTAeSCUInterfaceStatusEntry 4 }

    adTAeSCUIfDefaultGateway OBJECT-TYPE
        SYNTAX     IpAddress
           MAX-ACCESS  read-only
           STATUS  current
           DESCRIPTION
               "The Default Gateway assigned to this interface,
           if any."
           ::= { adTAeSCUInterfaceStatusEntry 5 }

    adTAeSCUIfSpeed OBJECT-TYPE
        SYNTAX  INTEGER {
                        auto(1),
                        bt-10(2),
                        bt-100(3)
                        }
           MAX-ACCESS  read-only
           STATUS  current
           DESCRIPTION
               "The Ethernet interface data rate"
           ::= { adTAeSCUInterfaceStatusEntry 6 }

    adTAeSCUIfXoverCorrection OBJECT-TYPE
        SYNTAX  INTEGER {
                        auto(1),
                        straight(2),
                        crossover(3)
                        }
           MAX-ACCESS  read-only
           STATUS  current
           DESCRIPTION
               "The Ethernet interface cable crossover correction"
           ::= { adTAeSCUInterfaceStatusEntry 7 }

    adTAeSCUIfLEDmode OBJECT-TYPE
        SYNTAX  INTEGER {
                        link(1),
                        blinkactivity(2)
                        }
           MAX-ACCESS  read-only
           STATUS  current
           DESCRIPTION
               "The Ethernet interface LED operation, on for link
                active only, or blink with link activity"
           ::= { adTAeSCUInterfaceStatusEntry 8 }

    adTAeSCUIfLinkStatus OBJECT-TYPE
        SYNTAX  INTEGER {
                        down(1),
                        up(2)
                        }
           MAX-ACCESS  read-only
           STATUS  current
           DESCRIPTION
               "The Ethernet interface physical layer (PHY) link
                status"
           ::= { adTAeSCUInterfaceStatusEntry 9 }

    adTAeSCUIfLinkRate OBJECT-TYPE
        SYNTAX  INTEGER {
                        unknown(1),
                        half-duplex-10bt(2),
                        half-duplex-100bt(3),
                        full-duplex-10bt(4),
                        full-duplex-100bt(5)
                        }
           MAX-ACCESS  read-only
           STATUS  current
           DESCRIPTION
               "The Ethernet interface link rate and duplex mode as
                determined by the hardware"
           ::= { adTAeSCUInterfaceStatusEntry 10 }
        --
        --
        --
        --
        --
        --
        --
        --
        --
        --
        -- Security Account Provisioning group
        --
        --
        --

        adTAeSCUSecurityAccountMg OBJECT IDENTIFIER
                                  ::= { adTAeSCUmg 5 }

        adTAeSCUSecurityAccountEnabled OBJECT-TYPE
                SYNTAX  INTEGER {
                        scuSNMPSecurityManagementEnabled(1),
                        scuSNMPSecurityManagementDisabled(2)
                        }
                MAX-ACCESS  read-only
                STATUS  current
                DESCRIPTION
                  "This indicates if SNMP security management is enabled or
                   disabled.  To enable SNMP security management go to menus
                   System Controller->Provisioning->General->Security Administration
                   using an ADMIN level account.  All security SNMP object
                   will not respond until this object is enabled."
                ::= { adTAeSCUSecurityAccountMg 1 }

      adTAeSCUSecuritySnmpAccountMgEnableDisable OBJECT-TYPE
                SYNTAX  DisplayString (SIZE(5..255))
                MAX-ACCESS  read-write
                STATUS  current
                DESCRIPTION
                  "Enable or disable SNMP Access to security management.
               Set a formatted string with [command] [backslash] [local ADMIN_account_name][backslash] [password].
               Command : 1 for Enable SNMP Access to security management.
               Command : 2 for Disable SNMP Access to security management.
               Example:
               Enable Access :  1\my_Admin_account\my_Password
               Disable access:  2\my_Admin_account\my_Password"
                ::= { adTAeSCUSecurityAccountMg 7 }


      adTAeSCUSecAccountAuthenticationMethod OBJECT-TYPE
                SYNTAX  INTEGER {
                           local                      (1),
                           rADIUS                     (2),
                           rADIUSorLocal              (3),
                           tACACS                     (4),
                           tACACSorLocal              (5),
                           tACACSorRADIUS             (6),
                           tACACSorRADIUSorLOCAL      (7)
                        }
                MAX-ACCESS  read-write
                STATUS  current
                DESCRIPTION
                  "The authentication method use to login to the controller.
                  If authentication failure occours, no other method will be used.
                  If access is granted, no other method will be used.

                   Selection with multiple methods will be used in the following maner:
                   tACACSorRADIUSorLocal
                        If TACACS server does not respond, the RADIUS server will be used.
                        If the RADIUS server does not respond then the Local accounts
                        will be used.
                   tACACSorRADIUS
                        If TACACS server does not respond, the RADIUS server will be used.
                        If the RADIUS server does not respond the controller will issue a
                        authentication failure.
                   tACACSorLocal
                        If TACACS server does not respond, then Local accounts will be used.
                   rADIUSorLocal
                        If RADIUS server does not respond, then Local accounts will be used.
                   tACACS
                        Login with TACACS server only.
                   rADIUS
                        Login with RADIUS server only.
                   local
                        Login with Local accounts only.

                   This method list will traverse the methods from TACACS+ to RADIUS,
                   and from RADIUS to the local security account database.  Each of
                   these methods, including Local, will have the ability to be disabled,
                   thus allowing a configurable method list of the following iterations:
                       T (TACACS)  R (RADIUS) L(LOCAL)
                   TRL, TR, TL, RL, T, R, L. A tech-support GR815 compliant
                   EEP (Challenge Key method) is still accepted for access into the
                   device regardless of the method list configuration (see example of
                   EEP in 61187010L1-5B, Figure 25, p.66).  "
                ::= { adTAeSCUSecurityAccountMg 8 }

        adTAeSCUSecAgingGlobalSettings OBJECT IDENTIFIER
                                  ::= { adTAeSCUSecurityAccountMg 2 }

        adTAeSCUSecAllAccountExpirationTimer OBJECT-TYPE
                SYNTAX  Integer32 (20..365)
                MAX-ACCESS  read-write
                STATUS  current
                DESCRIPTION
                  "Set all security accounts expiration timer to value."
                ::= { adTAeSCUSecAgingGlobalSettings 1 }

      adTAeSCUSecReadOnlyAccountExpirationTimer OBJECT-TYPE
                SYNTAX  Integer32 (20..365)
                MAX-ACCESS  read-write
                STATUS  current
                DESCRIPTION
                  "READONLY accounts expiration timer."
                ::= { adTAeSCUSecAgingGlobalSettings 2 }

      adTAeSCUSecReadWriteAccountExpirationTimer OBJECT-TYPE
                SYNTAX  Integer32 (20..365)
                MAX-ACCESS  read-write
                STATUS  current
                DESCRIPTION
                  "Set all READWRITEaccounts expiration timer settings value."
                ::= { adTAeSCUSecAgingGlobalSettings 3 }

      adTAeSCUSecTestAccountExpirationTimer OBJECT-TYPE
                SYNTAX  Integer32 (20..365)
                MAX-ACCESS  read-write
                STATUS  current
                DESCRIPTION
                  "Set all TEST accounts age."
                ::= { adTAeSCUSecAgingGlobalSettings 4 }

      adTAeSCUSecConfigAccountExpirationTimer OBJECT-TYPE
                SYNTAX  Integer32 (20..365)
                MAX-ACCESS  read-write
                STATUS  current
                DESCRIPTION
                  "Set all CONFIG expiration timer."
                ::= { adTAeSCUSecAgingGlobalSettings 5 }

      adTAeSCUSecAdminAccountExpirationTimer OBJECT-TYPE
                SYNTAX  Integer32 (20..365)
                MAX-ACCESS  read-write
                STATUS  current
                DESCRIPTION
                  "Set all ADMIN expiration timer."
                ::= { adTAeSCUSecAgingGlobalSettings 6 }

      adTAeSCUSecSendAcctExpAlarm OBJECT-TYPE
                SYNTAX  INTEGER {
                           enable(1),
                           disable(2)
                           }
                MAX-ACCESS  read-write
                STATUS  current
                DESCRIPTION
                  "Send Inactive Accounts Alarm Enable."
                ::= { adTAeSCUSecAgingGlobalSettings 7 }

      adTAeSCUSecResetAllAccountAge OBJECT-TYPE
                SYNTAX  INTEGER {
                           reset(1)
                           }
                MAX-ACCESS  read-write
                STATUS  current
                DESCRIPTION
                  "Resets all account expiration timers to zero."
                ::= { adTAeSCUSecAgingGlobalSettings 8 }

       adTAeSCUSecAllPasswordExpirationTimer OBJECT-TYPE
                SYNTAX  Integer32 (20..365)
                MAX-ACCESS  read-write
                STATUS  current
                DESCRIPTION
                  "Set all security password age set value."
                ::= { adTAeSCUSecAgingGlobalSettings 10 }

      adTAeSCUSecReadOnlyPasswordExpirationTimer OBJECT-TYPE
                SYNTAX  Integer32 (20..365)
                MAX-ACCESS  read-write
                STATUS  current
                DESCRIPTION
                  "Set all security READONLY accounts password expiration timer."
                ::= { adTAeSCUSecAgingGlobalSettings 11 }

      adTAeSCUSecReadWritePasswordExpirationTimer OBJECT-TYPE
                SYNTAX  Integer32 (20..365)
                MAX-ACCESS  read-write
                STATUS  current
                DESCRIPTION
                  "Set all READWRITE accounts password expiration timer settings value."
                ::= { adTAeSCUSecAgingGlobalSettings 12 }

      adTAeSCUSecTestPasswordExpirationTimer OBJECT-TYPE
                SYNTAX  Integer32 (20..365)
                MAX-ACCESS  read-write
                STATUS  current
                DESCRIPTION
                  "Set all TEST accounts password expiration timer."
                ::= { adTAeSCUSecAgingGlobalSettings 13 }

      adTAeSCUSecConfigPasswordExpirationTimer OBJECT-TYPE
                SYNTAX  Integer32 (20..365)
                MAX-ACCESS  read-write
                STATUS  current
                DESCRIPTION
                  "Set all CONFIG accounts password expiration timer."
                ::= { adTAeSCUSecAgingGlobalSettings 14 }

      adTAeSCUSecAdminPasswordExpirationTimer OBJECT-TYPE
                SYNTAX  Integer32 (20..365)
                MAX-ACCESS  read-write
                STATUS  current
                DESCRIPTION
                  "Set all ADMIN accounts password expiration timer."
                ::= { adTAeSCUSecAgingGlobalSettings 15 }

      adTAeSCUSecPasswordExpirationWarning OBJECT-TYPE
                SYNTAX  Integer32 (0..15)
                MAX-ACCESS  read-write
                STATUS  current
                DESCRIPTION
                  "Notification to users requiring them to change their passwords.
                   Number of days prior to expiration to display warning menu."
                ::= { adTAeSCUSecAgingGlobalSettings 20 }

      adTAeSCUSecResetAllPasswordAge OBJECT-TYPE
                SYNTAX  INTEGER {
                           reset(1)
                           }
                MAX-ACCESS  read-write
                STATUS  current
                DESCRIPTION
                  "Resets all password expiration timers to zero."
                ::= { adTAeSCUSecAgingGlobalSettings 21 }


      --
      --

      adTAeSCUAccountExpirationEnabled OBJECT-TYPE
                SYNTAX  INTEGER {
                        accountExpirationEnabled(1),
                        accountExpirationDisabled(2)
                        }
                MAX-ACCESS  read-write
                STATUS  current
                DESCRIPTION
                  "Enable or disable account expiration for accounts."
                ::= { adTAeSCUSecurityAccountMg 5 }

      adTAeSCUPasswordAgingEnabled OBJECT-TYPE
                SYNTAX  INTEGER {
                        passwordAgingEnabled(1),
                        passwordAgingDisabled(2)
                        }
                MAX-ACCESS  read-write
                STATUS  current
                DESCRIPTION
                  "Enable or disable password aging."
                ::= { adTAeSCUSecurityAccountMg 6 }
        --
      --
      --

        adTAeSCUSecAccountTable OBJECT-TYPE
            SYNTAX  SEQUENCE OF AdTAeSCUSecAccountEntry
            MAX-ACCESS  not-accessible
            STATUS  current
            DESCRIPTION
                "The SCU Security Account table."
           ::= { adTAeSCUSecurityAccountMg 3 }

        adTAeSCUSecAccountEntry OBJECT-TYPE
            SYNTAX  AdTAeSCUSecAccountEntry
            MAX-ACCESS  not-accessible
            STATUS  current
            DESCRIPTION
                "An entry in the SCU Security Account table.
                 Writeable objects cannot be changed while adTAeSCUSecNumAccountLogin is 1 or more."
           INDEX   { adTAeSCUSecAccountIndex}
           ::= { adTAeSCUSecAccountTable 1 }

        AdTAeSCUSecAccountEntry ::=
            SEQUENCE {
                adTAeSCUSecAccountIndex
                    Integer32,
                adTAeSCUSecAccountUserID
                     DisplayString,
                adTAeSCUSecAccountStatus
                    INTEGER,
                adTAeSCUSecNumAccountLogin
                    Integer32,
                adTAeSCUSecAccountAccessRights
                    INTEGER,
                adTAESCUSecChangeAccountPassword
                    DisplayString,
            adTAeSCUSecAccStatusExt
                    INTEGER,
            adTAeSCUSecAccExpTime
                    Integer32,
            adTAeSCUSecAccPasswordExpTime
                    Integer32,
            adTAeSCUSecAccountAge
                    Integer32,
            adTAeSCUSecAccPasswordAge
                    Integer32,
            adTAeSCUSecResetAccountAge
                    INTEGER,
            adTAeSCUSecResetAccPasswordAge
                    INTEGER,
            adTAeSCUAccExpirationEnabled
                INTEGER,
            adTAeSCUAccPasswordAccAgingEnabled
                INTEGER,
            adTAeSCUSecForcePasswordReset
                INTEGER
            }

        adTAeSCUSecAccountIndex OBJECT-TYPE
                SYNTAX  Integer32 (1..16)
                MAX-ACCESS  read-only
                STATUS  current
                DESCRIPTION
                  "Security account user Index."
                ::= { adTAeSCUSecAccountEntry 1 }

        adTAeSCUSecAccountUserID OBJECT-TYPE
                SYNTAX  DisplayString (SIZE(0..16))
                MAX-ACCESS  read-write
                STATUS  current
                DESCRIPTION
                  "Security account user ID name. If account
                  name is zero length (empty) then an account
                   name can be set.  Setting a userID name
                   creates an account with default properties.
                   Account names cannot be changed.  To change
                   an account name, the account first have
                   to be deleted by setting adTAeSCUSecNumAccountLogin
                   to deleted.  Then set to the desired name.
                   All attempts to change an account name will
                   generate a bad value error."
                ::= { adTAeSCUSecAccountEntry 2 }

        adTAeSCUSecAccountStatus OBJECT-TYPE
                SYNTAX  INTEGER {
                        createdEnabled(1),  -- This account is created and enabled
                        createdDisabled(2), -- This account is created but is disabled.  Cannot use this account to login.
                        deleted(3)          -- This account does not exist.  It is deleted.
                        }
                MAX-ACCESS  read-write
                STATUS  current
                DESCRIPTION
                    "Status of the account.  AdTAeSCUSecAccountStatus
                    cannot be changed while number of
                    adTAeSCUSecNumAccountLogin is one or more."
                DEFVAL { deleted }
                ::= { adTAeSCUSecAccountEntry 3 }

        adTAeSCUSecNumAccountLogin OBJECT-TYPE
                SYNTAX  Integer32
                MAX-ACCESS  read-only
                STATUS  current
                DESCRIPTION
                  "Number of current logins using this account.
                  Logged in status of account."
                ::= { adTAeSCUSecAccountEntry 4 }

        adTAeSCUSecAccountAccessRights OBJECT-TYPE
                SYNTAX  INTEGER{
                        readOnlyAccess(1),   -- Read Only Access.
                        readWriteAccess(2),  -- Read and Write Access.
                        testAccess(3),       -- Read, Write, and Test Access.
                        adminAccess(4),      -- Read, Write, Test, and ADMIN Access.
                        fronPanelAccess(5),  -- Front Panel Access only.
                                             -- Can only login through the front panel.
                                             -- Only for built in account. Cannot set this value.
                        techSupportAccess(6), -- Tech Support Access. Cannot set to this value.
                        configAccess(7)      -- Read and Write Access to all items except for system
                                             -- administration items.
                        }
                MAX-ACCESS  read-write
                STATUS  current
                DESCRIPTION
                  "Access rights of account."
                ::= { adTAeSCUSecAccountEntry 5 }

        -- adTAESCUSecAccountPassword OBJECT-TYPE
        --        SYNTAX  DisplayString (SIZE(0..16))
        --        MAX-ACCESS  read-write
        --        STATUS  obsolete
        --        DESCRIPTION
        --          "Account password.  A password is a 16 character
        --          alphanumeric word.  Passwords cannot be viewed.
        --           All passwords will be displayed as ******.  "
        --        DEFVAL { "*********" }
        --        ::= { adTAeSCUSecAccountEntry 6 }

        adTAESCUSecChangeAccountPassword OBJECT-TYPE
                SYNTAX  DisplayString (SIZE(0..33))
                MAX-ACCESS  read-write
                STATUS  current
                DESCRIPTION
                  "Used to change account password.  This string must contain the
                   old password and the new password separated by a \ (backslash) character.
                   Example:  password\newpassword
                   A password is a 16 character
                  alphanumeric word.  Passwords cannot be viewed.
                   All passwords will be displayed as ******.
                   A valid password may contain printable characters except for
                   the following characters: Backslash  \, Single quote ', Blank space  ."
                DEFVAL { "********" }
                ::= { adTAeSCUSecAccountEntry 7 }

      adTAeSCUSecAccStatusExt OBJECT-TYPE
                SYNTAX  INTEGER {
                        deleted(1),               -- This account does not exist.  It is deleted.
                  enabled(2),               -- This account is created and enabled
                        disabled(3),              -- This account is created but is disabled.  Cannot use this account to login.
                        enabledExpired(4),        -- This account is created, Enabled, and Expired. Cannot use this account to login.
                        disabledExpired(5),       -- This account is created, Disabled, and Expired.  Cannot use this account to login.
                        enabledLocked(6),         -- This account is created, Enabled, and Locked.  Cannot use this account to login.
                        disabledLocked(7),        -- This account is created, Disabled, and locked.  Cannot use this account to login.
                        enabledExpiredLocked(8),  -- This account is created, Enabled, Expired, and Locked.  Cannot use this account to login.
                        disabledExpiredLocked(9)  -- This account is created, Disabled, Expired, and Locked.  Cannot use this account to login.
                        }
                MAX-ACCESS  read-write
                STATUS  current
                DESCRIPTION
                    "Status of the account.  AdTAeSCUSecAccountStatus
                    cannot be changed while number of
                    adTAeSCUSecNumAccountLogin is one or more."
                DEFVAL { deleted }
                ::= { adTAeSCUSecAccountEntry 8 }

      adTAeSCUSecAccExpTime OBJECT-TYPE
                SYNTAX  Integer32 (20..365)
                MAX-ACCESS  read-write
                STATUS  current
                DESCRIPTION
                  "Security account expiration time."
                ::= { adTAeSCUSecAccountEntry 9 }

        adTAeSCUSecAccPasswordExpTime OBJECT-TYPE
                SYNTAX  Integer32 (20..365)
                MAX-ACCESS  read-write
                STATUS  current
                DESCRIPTION
                  "Security account password expiration time."
                ::= { adTAeSCUSecAccountEntry 10 }

      adTAeSCUSecAccountAge OBJECT-TYPE
                SYNTAX  Integer32
                MAX-ACCESS  read-only
                STATUS  current
                DESCRIPTION
                  "Security account age."
                ::= { adTAeSCUSecAccountEntry 11 }

      adTAeSCUSecAccPasswordAge OBJECT-TYPE
                SYNTAX  Integer32
                MAX-ACCESS  read-only
                STATUS  current
                DESCRIPTION
                  "Security account password age."
                ::= { adTAeSCUSecAccountEntry 12 }

        adTAeSCUSecResetAccountAge OBJECT-TYPE
                SYNTAX  INTEGER {
                        resetAccountAge(1)  -- Reset Account Age to zero
                        }
                MAX-ACCESS  read-write
                STATUS  current
                DESCRIPTION
                  "Reset security account age."
                ::= { adTAeSCUSecAccountEntry 13 }

        adTAeSCUSecResetAccPasswordAge OBJECT-TYPE

                SYNTAX  INTEGER {
                        resetPasswordAge(1)  -- Reset Password Age to zero

                        }
                MAX-ACCESS  read-write
                STATUS  current
                DESCRIPTION
                  "Reset security account password age."
                ::= { adTAeSCUSecAccountEntry 14 }

        adTAeSCUAccExpirationEnabled OBJECT-TYPE
                SYNTAX  INTEGER {
                        accountExpirationEnabled(1),
                        accountExpirationDisabled(2)
                        }
                MAX-ACCESS  read-write
                STATUS  current
                DESCRIPTION
                  "Enable or disable single account expiration."
                ::= { adTAeSCUSecAccountEntry 15 }

      adTAeSCUAccPasswordAccAgingEnabled OBJECT-TYPE
                SYNTAX  INTEGER {
                        passwordAgingEnabled(1),
                        passwordAgingDisabled(2)
                        }
                MAX-ACCESS  read-write
                STATUS  current
                DESCRIPTION
                  "Enable or disable single account password aging."
                ::= { adTAeSCUSecAccountEntry 16 }

        adTAeSCUSecForcePasswordReset OBJECT-TYPE
                SYNTAX  INTEGER {
                        forcedreset(1),
                        clearforcedreset(2)
                        }
                MAX-ACCESS  read-write
                STATUS  current
                DESCRIPTION
                  "Forces user to reset their password upon next login."
                ::= { adTAeSCUSecAccountEntry 17 }

        --
        -- Security Account Provisioning group
        --

        adTAeSCUSecAccountLoggedInTable OBJECT-TYPE
            SYNTAX  SEQUENCE OF AdTAeSCUSecAccountLoggedInEntry
            MAX-ACCESS  not-accessible
            STATUS  current
            DESCRIPTION
                "The SCU Security Account table."
           ::= { adTAeSCUSecurityAccountMg 4 }

        adTAeSCUSecAccountLoggedInEntry OBJECT-TYPE
            SYNTAX  AdTAeSCUSecAccountLoggedInEntry
            MAX-ACCESS  not-accessible
            STATUS  current
            DESCRIPTION
                "An entry in the SCU Security Account table."
           INDEX   { adTAeSCUSecAccountloginIndex}
           ::= { adTAeSCUSecAccountLoggedInTable 1 }

        AdTAeSCUSecAccountLoggedInEntry ::=
            SEQUENCE {
                adTAeSCUSecAccountloginIndex
                    Integer32,
                adTAeSCUSecAccountLoginUserIDIndex
                    Integer32,
                adTAeSCUSecAccountLoginUserID
                     DisplayString,
                adTAeSCUSecAccountConnectionType
                    INTEGER,
                adTAeSCUSecAccountSessionType
                    INTEGER,
                adTAeSCUSecAccountLoginConnectionSource
                     DisplayString,
                adTAeSCUSecAccountLoginDateTime
                    DisplayString,
                adTAeSCUSecAccountConnectionPort
                    Integer32,
                adTAeSCUSecAccountDisconnectSession
                    Integer32
            }
        adTAeSCUSecAccountloginIndex OBJECT-TYPE
         SYNTAX  Integer32 (1..255)
                MAX-ACCESS  read-only
                STATUS  current
                DESCRIPTION
                  "Index to indicate the order the user was logged in."
                ::= { adTAeSCUSecAccountLoggedInEntry 1 }
        adTAeSCUSecAccountLoginUserIDIndex OBJECT-TYPE
                SYNTAX  Integer32 (1..16)
                MAX-ACCESS  read-only
                STATUS  current
                DESCRIPTION
                  "Security account user Index."
                ::= { adTAeSCUSecAccountLoggedInEntry 2 }
        adTAeSCUSecAccountLoginUserID OBJECT-TYPE
                SYNTAX  DisplayString (SIZE(0..16))
                MAX-ACCESS  read-only
                STATUS  current
                DESCRIPTION
                  "Security account user ID name."
                ::= { adTAeSCUSecAccountLoggedInEntry 3 }
        adTAeSCUSecAccountConnectionType OBJECT-TYPE
                SYNTAX  INTEGER
                {
                    craft(1),
                    adminPort(2),
                    ip(3),
                    x25(4),
                    rs485(5),
                    dcc(6),
                    fcd(7),
                    invalidConnection(8)
                }
                MAX-ACCESS  read-only
                STATUS  current
                DESCRIPTION
                  "Method of connection to unit."
                ::= { adTAeSCUSecAccountLoggedInEntry 4 }
        adTAeSCUSecAccountSessionType OBJECT-TYPE
                SYNTAX  INTEGER
                {
                    menu(1),
                    tl1(2),
                    fcd(3),
                    ftp(4),
                    invalidSession(5)
                }
                MAX-ACCESS  read-only
                STATUS  current
                DESCRIPTION
                  "Connection session type."
                ::= { adTAeSCUSecAccountLoggedInEntry 5 }

        adTAeSCUSecAccountLoginConnectionSource OBJECT-TYPE
                SYNTAX  DisplayString (SIZE(0..50))
                MAX-ACCESS  read-only
                STATUS  current
                DESCRIPTION
                  "Connection source of login.  This could be an
                  IP address or some other type of address"
                ::= { adTAeSCUSecAccountLoggedInEntry 6 }

        adTAeSCUSecAccountLoginDateTime OBJECT-TYPE
                SYNTAX  DisplayString (SIZE(0..25))
                MAX-ACCESS  read-only
                STATUS  current
                DESCRIPTION
                  "String display of login date and time.
                  Formant: mm/dd/yyyy and 24 hour time string
                  in format hh:mm:ss"
                ::= { adTAeSCUSecAccountLoggedInEntry 7 }

        adTAeSCUSecAccountConnectionPort OBJECT-TYPE
         SYNTAX  Integer32
                MAX-ACCESS  read-only
                STATUS  current
                DESCRIPTION
                  "Port on which the indexed user's connection is established."
                ::= { adTAeSCUSecAccountLoggedInEntry 8 }

        adTAeSCUSecAccountDisconnectSession OBJECT-TYPE
                SYNTAX  Integer32 (1..2)
                MAX-ACCESS  read-write
                STATUS  current
                DESCRIPTION
                  "Disconnect Indexed user's session."
                ::= { adTAeSCUSecAccountLoggedInEntry 9 }

        --
        -- Security Account Login Statistics
        --

        adTAeSCUSecLoginStatTable OBJECT-TYPE
            SYNTAX  SEQUENCE OF AdTAeSCUSecLoginStatEntry
            MAX-ACCESS  not-accessible
            STATUS  current
            DESCRIPTION
                "The SCU Security Account table."
           ::= { adTAeSCUSecurityAccountMg 25 }

        adTAeSCUSecLoginStatEntry OBJECT-TYPE
            SYNTAX  AdTAeSCUSecLoginStatEntry
            MAX-ACCESS  not-accessible
            STATUS  current
            DESCRIPTION
                "An entry in the SCU Security Login Statistics table."
           INDEX   { adTAeSCUSecAccountIndex}
           ::= { adTAeSCUSecLoginStatTable 1 }

        AdTAeSCUSecLoginStatEntry ::=
            SEQUENCE {
                adTAeSCUSecLoginStatUserID
                     DisplayString,
                adTAeSCUSecNumberOfLogins
                    Integer32,
                adTAeSCUSecTotalNumLoginFailures
                    Integer32,
                adTAeSCUSecNumFailuresSinceLastLogin
                    Integer32,
                adTAeSCUSecLastLoginDateTime
                    DisplayString,
                adTAeSCUSecLastConnectionType
                    INTEGER,
                adTAeSCUSecLastSessionType
                    INTEGER,
                adTAeSCUSecLastIPAddress
                    IpAddress
            }
        adTAeSCUSecLoginStatUserID OBJECT-TYPE
                SYNTAX  DisplayString (SIZE(0..64))
                MAX-ACCESS  read-only
                STATUS  current
                DESCRIPTION
                  "Security account user ID name."
                ::= { adTAeSCUSecLoginStatEntry 3 }
        adTAeSCUSecNumberOfLogins OBJECT-TYPE
         SYNTAX  Integer32
                MAX-ACCESS  read-only
                STATUS  current
                DESCRIPTION
                  "The total number of logins recorded."
                ::= { adTAeSCUSecLoginStatEntry 5 }
        adTAeSCUSecTotalNumLoginFailures OBJECT-TYPE
         SYNTAX  Integer32
                MAX-ACCESS  read-only
                STATUS  current
                DESCRIPTION
                  "The total number of login failures recorded for the account."
                ::= { adTAeSCUSecLoginStatEntry 7 }
        adTAeSCUSecNumFailuresSinceLastLogin OBJECT-TYPE
         SYNTAX  Integer32
                MAX-ACCESS  read-only
                STATUS  current
                DESCRIPTION
                  "The total number of login failures since the last login of this account."
                ::= { adTAeSCUSecLoginStatEntry 9 }
        adTAeSCUSecLastLoginDateTime OBJECT-TYPE
                SYNTAX  DisplayString (SIZE(0..25))
                MAX-ACCESS  read-only
                STATUS  current
                DESCRIPTION
                  "String display of login date and time.
                  Formant: mm/dd/yyyy and 24 hour time string
                  in format hh:mm"
                ::= { adTAeSCUSecLoginStatEntry 13 }
        adTAeSCUSecLastConnectionType OBJECT-TYPE
                SYNTAX  INTEGER {
                  craftConnection(1),
                  adminConnection(2),
                  ntwkmgmtConnection(3),
                  ipConnection(4),
                  x25Connection(5),
                  rS485Connection(6),
                  dccConnection(7),
                  fCDConnection(8),
                  snmpConnection(9),
                  unknown1(10),
                  unknown2(11),
                  unknown3(12)
                }
                MAX-ACCESS  read-only
                STATUS  current
                DESCRIPTION
                  "The connection type of the login."
                ::= { adTAeSCUSecLoginStatEntry 14 }
        adTAeSCUSecLastSessionType OBJECT-TYPE
                SYNTAX  INTEGER {
                         menuSessionType(1),
                         tL1SessionType(2),
                         fcdSessionType(3),
                         ftpSessionType(4),
                         fsSessionType(5),  -- Terminal Server
                         webSessionType(6),
                         cliSessionType(7),
                         unknown1(8),
                         unknown2(9),
                         unknown3(10)
                        }
                MAX-ACCESS  read-only
                STATUS  current
                DESCRIPTION
                  "The Session Type of the login."
                ::= { adTAeSCUSecLoginStatEntry 15 }
        adTAeSCUSecLastIPAddress OBJECT-TYPE
                SYNTAX  IpAddress
                MAX-ACCESS  read-only
                STATUS  current
                DESCRIPTION
                  "The the IPAddress of the login."
                ::= { adTAeSCUSecLoginStatEntry 16 }

         ---
         --- Advanced Login options
         ---

         adTAeSCUSecAdvancedLoginOptions OBJECT IDENTIFIER
                                  ::= { adTAeSCUSecurityAccountMg 26 }

        adTAeSCUSecChallengeKey OBJECT-TYPE
                SYNTAX  INTEGER (1..2)
                MAX-ACCESS  read-write
                STATUS  current
                DESCRIPTION
                  "Set all security accounts expiration timer to value."
                ::= { adTAeSCUSecAdvancedLoginOptions 1 }

      adTAeSCUSecMultiLoginAcct OBJECT-TYPE
                SYNTAX  INTEGER (1..2)
                MAX-ACCESS  read-write
                STATUS  current
                DESCRIPTION
                  "READONLY accounts expiration timer."
                ::= { adTAeSCUSecAdvancedLoginOptions 2 }

      adTAeSCUSecRemoteMenuAccessRequired OBJECT-TYPE
                SYNTAX  INTEGER (1..2)
                MAX-ACCESS  read-write
                STATUS  current
                DESCRIPTION
                  "Set all READWRITEaccounts expiration timer settings value."
                ::= { adTAeSCUSecAdvancedLoginOptions 3 }

        ---
        ---  The following OIDs will only work with
        ---
        ---
        --- Network Management Group
        ---


        adTAeSCUNetworkMgmt  OBJECT IDENTIFIER
           ::= { adTAeSCUmg 6 }

       adTAeSCUNetworkMgmtPortBaudRate OBJECT-TYPE
                SYNTAX  INTEGER {
                        baud1200(1),
                        baud2400(2),
                        baud4800(3),
                        baud9600(4),
                        baud19200(5),
                        baud38400(6),
                        baud57600(7),
                        baud115200(8)
                        }
                MAX-ACCESS  read-write
                STATUS  current
                DESCRIPTION
                  "Network Interface Port Baud Rate."
                ::= { adTAeSCUNetworkMgmt 1 }

        adTAeSCUNetworkMgmtPortComMode OBJECT-TYPE
                SYNTAX  INTEGER {
                        x25(1),
                        terminalServer(2),
                        pPP(3),
                        accessoryOption(4),
                        cLI(5)
                        }
                MAX-ACCESS  read-write
                STATUS  current
                DESCRIPTION
                  "Eth2/PPP0 Network interface port operating mode.."
                ::= { adTAeSCUNetworkMgmt 2 }


        adTAeSCUNetworkMgmtPPPSerialPortMode OBJECT-TYPE
                SYNTAX  INTEGER {
                        async(1),
                        sync(2)
                        }
                MAX-ACCESS  read-write
                STATUS  current
                DESCRIPTION
                  "Determines wether the local eSCU PPP port will
                  use 'sync' or 'async' communications mode of the
                  network management port."
                ::= { adTAeSCUNetworkMgmt 3 }

        adTAeSCUNetworkMgmtInterbankComMode OBJECT-TYPE
                SYNTAX  INTEGER {
                        host(1),
                        client(2)
                        }
                MAX-ACCESS  read-write
                STATUS  current
                DESCRIPTION
                  "Communication mode when systems are wired in a daisy chained configuration.
                   When installed as a standalone chassis it can be set to either value."
                ::= { adTAeSCUNetworkMgmt 4 }

        adTAeSCUNetworkMgmtInterbankComModeWritable OBJECT-TYPE
                SYNTAX  INTEGER {
                        enabled(1),
                        disabled(2)
                        }
                MAX-ACCESS  read-only
                STATUS  current
                DESCRIPTION
                  "Communication mode is not writable for CLIENT units when a HOST is present."
                ::= { adTAeSCUNetworkMgmt 5 }

        adTAeSCUNetworkMgmtSecurityEnable OBJECT-TYPE
                SYNTAX  INTEGER {
                        enabled(1),
                        disabled(2)
                        }
                MAX-ACCESS  read-write
                STATUS  current
                DESCRIPTION
                  "Require authentication."
                ::= { adTAeSCUNetworkMgmt 6 }

        ---
        --- DNS related managment
        ---


        adTAeSCUsDNS  OBJECT IDENTIFIER
           ::= { adTAeSCUmg 7 }

       adTAeScuDNSlookupService OBJECT-TYPE
                SYNTAX  INTEGER {
                        enabled(1),
                        disabled(2)
                        }
                MAX-ACCESS  read-write
                STATUS  current
                DESCRIPTION
                  "Determines whether DNS lookup services are
                  enabled."
                ::= { adTAeSCUsDNS 1 }

        adTAeScuDNSprimaryIP OBJECT-TYPE
                SYNTAX  IpAddress
                MAX-ACCESS  read-write
                STATUS  deprecated
                DESCRIPTION
                  "Primary DNS name server IP address. Zero
                  signifies 'none'.
                  This OID is deprecated.  Use ipDNSLookupIpNetAddress.1 to configure DNS Address."
                ::= { adTAeSCUsDNS 2 }

        adTAeScuDNSsecondaryIP OBJECT-TYPE
                SYNTAX  IpAddress
                MAX-ACCESS  read-write
                STATUS  deprecated
                DESCRIPTION
                  "Secondary DNS name server IP address. Zero
                  signifies 'none'.
                  This OID is deprecated.  Use ipDNSLookupIpNetAddress.2 to configure DNS Address."
                ::= { adTAeSCUsDNS 3 }

        adTAeScuDNSsearchList OBJECT-TYPE
                SYNTAX  DisplayString (SIZE(0..40))
                MAX-ACCESS  read-write
                STATUS  current
                DESCRIPTION
                  "Domain access search list. A space separated
                  list of domain names.
                  An empty string signifies 'none'."
                ::= { adTAeSCUsDNS 4 }


        --
        -- the DNS primary and secondary Address Translation table
        --

        ipDNSLookupIpTable OBJECT-TYPE
            SYNTAX     SEQUENCE OF IpDNSLookupIpTableEntry
            MAX-ACCESS not-accessible
            STATUS     current
            DESCRIPTION
                   "The DNS primary and Secondary IP server..

                    Set primary DNS server index 1
                    Set secondary DNS server index 2"
            ::= { adTAeSCUsDNS 5  }

        ipDNSLookupIpTableEntry OBJECT-TYPE
            SYNTAX     IpDNSLookupIpTableEntry
            MAX-ACCESS not-accessible
            STATUS     current
            DESCRIPTION
                   "Each entry contains one IP address to `physical' address
                    equivalence."
            INDEX       { ipDNSLookupIpIndex}
            ::= { ipDNSLookupIpTable 1 }

        IpDNSLookupIpTableEntry ::= SEQUENCE {
                ipDNSLookupIpIndex           Integer32,
                ipDNSLookupIpInetAddressType  InetAddressType,
                ipDNSLookupIpInetAddress      InetAddress
            }
    ipDNSLookupIpIndex OBJECT-TYPE
    SYNTAX     Integer32
    MAX-ACCESS not-accessible
    STATUS     current
    DESCRIPTION
           "The index value that uniquely identifies the primary or secondary
            DNS server IP Address.
            Index 1 for Primary DNS server address.
            Index 2 for Secondary DNS server address."
    ::= { ipDNSLookupIpTableEntry 1 }

    ipDNSLookupIpInetAddressType OBJECT-TYPE
        SYNTAX InetAddressType
        MAX-ACCESS read-only
        STATUS     current
        DESCRIPTION
               "The type of ipDNSLookupIpNetAddress."
        ::= { ipDNSLookupIpTableEntry 2 }

    ipDNSLookupIpInetAddress OBJECT-TYPE
        SYNTAX InetAddress
        MAX-ACCESS read-write
        STATUS     current
        DESCRIPTION
               "The IP Address corresponding to the DNS server.
                Index 1 for Primary DNS server address.
                Index 2 for Secondary DNS server address.
                Backwards compatibility:  Setting this address to a IPv4
                address will provision old primary or secondary DNS address.
                Setting this address to an IPV6 will leave the old provision
                address as is."
        ::= { ipDNSLookupIpTableEntry 3 }

        ---
        --- Sofware/Config through TFTP
        ---

        adTAeSCUFirmwareTFTPConfigMgmt  OBJECT IDENTIFIER
           ::= { adTAeSCUmg 8 }

        adTAeScuFirmwareTftpRemoteFileName OBJECT-TYPE
                SYNTAX  DisplayString (SIZE(0..40))
                MAX-ACCESS  read-write
                STATUS  current
                DESCRIPTION
                  "Firmware TFTP remote file name"
                ::= { adTAeSCUFirmwareTFTPConfigMgmt 1 }

        adTAeScuFirmwareTftpServerHostName OBJECT-TYPE
                SYNTAX  DisplayString (SIZE(0..40))
                MAX-ACCESS  read-write
                STATUS  deprecated
                DESCRIPTION
                  "Symbolic DNS name or dotted-quad IP address of the
                   firmware TFTP server"
                ::= { adTAeSCUFirmwareTFTPConfigMgmt 2 }

        adTAeScuFirmwareTftpServerIP OBJECT-TYPE
                SYNTAX  IpAddress
                MAX-ACCESS  read-only
                STATUS  deprecated
                DESCRIPTION
                  "Firmware TFTP server IP address. Zero
                   signifies 'none'.
                   This OID is deprecated.  Use adTAeScmFirmwareTftpServerIPInetAddress
                   to configure Firmware TFTP server IP address.  adTAeScmFirmwareTftpServerIPInetAddress
                   will accept Ipv4, IPv6, and domain name address"
                ::= { adTAeSCUFirmwareTFTPConfigMgmt 3 }

        adTAeScuFirmwareTftpCacheExpire OBJECT-TYPE
                SYNTAX  Integer32 (0..1440)
                MAX-ACCESS  read-write
                STATUS  current
               DESCRIPTION
                  "The CacheExpire value specifies how many minutes a
                    flash file may be retained on the SCU before it will
                    again be retrieved from the TFTP server.  If a subsequent
                    request for the same file is made within the CacheExpire
                    time, the local copy of the file will be reused, thus
                    reducing upgrade time and network traffic.  A value of
                    zero indicates TFTP flash file caching should be disabled."
                ::= { adTAeSCUFirmwareTFTPConfigMgmt 4 }

        adTAeScuFirmwareTftpInvalidate OBJECT-TYPE
                SYNTAX  INTEGER {
                    discardCurrentConfigInfo(1)
                    }
                MAX-ACCESS  read-write
                STATUS  current
                DESCRIPTION
                  "This OID instructs the TFTP Cache system to discard any
                   information that may be currently cached.  The next TFTP
                   'get' operation will be being retrieved from the TFTP
                   host."
                ::= { adTAeSCUFirmwareTFTPConfigMgmt 5 }

        adTAeScmFirmwareTftpServerInetAddressType OBJECT-TYPE
                SYNTAX InetAddressType
                MAX-ACCESS  read-only
                STATUS  current
                DESCRIPTION
                  "Firmware TFTP server IP address type (Ipv6 or Ipv4)."
                ::= { adTAeSCUFirmwareTFTPConfigMgmt 6 }

        adTAeScmFirmwareTftpServerIPInetAddress OBJECT-TYPE
                SYNTAX InetAddress
                MAX-ACCESS  read-write
                STATUS  current
                DESCRIPTION
                  "Firmware TFTP server IP address. Ipv6 or Ipv4.
                  Backwards compatibility:  Setting this address to a IPv4
                  address will update adTAeScuFirmwareTftpServerHostName address
                  with the new value.
                  Setting this address to an IPV6 will leave adTAeScuFirmwareTftpServerHostName as is."
                ::= { adTAeSCUFirmwareTFTPConfigMgmt 7 }


        ---
        --- SCA () Sofware/Config related dids
        ---

        adTAeSCUSystemConfigArchiveMgmt  OBJECT IDENTIFIER
           ::= { adTAeSCUmg 9 }


        adTAeScuSCATftpServerHostName OBJECT-TYPE
                SYNTAX  DisplayString (SIZE(0..40))
                MAX-ACCESS  read-write
                STATUS  deprecated
                DESCRIPTION
                  "Symbolic DNS name or dotted-quad IP address of the
                   config/SCA TFTP server.
                   This OID is deprecated.  Use adTAeScuSCATftpServerHostNameInetAddress
                   to configure config/SCA TFTP server IP address."
                ::= { adTAeSCUSystemConfigArchiveMgmt 1 }

        adTAeScuSCATftpServerIP OBJECT-TYPE
                SYNTAX  IpAddress
                MAX-ACCESS  read-only
                STATUS  current
                DESCRIPTION
                  "Numeric IP address of the config/SCA TFTP server"
                ::= { adTAeSCUSystemConfigArchiveMgmt 2 }

        adTAeScuSCATftpServerIPInetAddressType OBJECT-TYPE
                SYNTAX InetAddressType
                MAX-ACCESS  read-only
                STATUS  current
                DESCRIPTION
                  "InetAddressType of IP address of the config/SCA TFTP server"
                ::= { adTAeSCUSystemConfigArchiveMgmt 3 }

        adTAeScuSCATftpServerHostNameInetAddress OBJECT-TYPE
                SYNTAX InetAddress
                MAX-ACCESS  read-write
                STATUS  current
                DESCRIPTION
                 "IP InetAddress of the config/SCA TFTP server.
                  Backwards compatibility:  Setting this address to a IPv4
                  address will update adTAeScuSCATftpServerHostName provision address
                  with the new value.
                  Setting this address to an IPV6 will leave adTAeScuSCATftpServerHostName as is."
                ::= { adTAeSCUSystemConfigArchiveMgmt 4 }

        ---
        --- SCA Auto Save Management
        ---

        adTAeSCUSCAControl  OBJECT IDENTIFIER
           ::= { adTAeSCUSystemConfigArchiveMgmt 10 }



        adTAeScuSCAFileName OBJECT-TYPE
                SYNTAX  DisplayString (SIZE(0..40))
                MAX-ACCESS  read-write
                STATUS  current
                DESCRIPTION
                  "Config/SCA file name.  SCA filename to use during
                  explicit or manual SCA save/restore operations from
                  SNMP and menu sessions.  This filename has no affect
                  on SCA autosaves"
                ::= { adTAeSCUSCAControl 1 }

        adTAeScuSCAInitiateSave OBJECT-TYPE
                SYNTAX  INTEGER {
                    initiate(1)
                    }
                MAX-ACCESS  read-write
                STATUS  current
                DESCRIPTION
                  "Initiate manual SCA Save operation to customer TFTP server."
                ::= { adTAeSCUSCAControl 2 }

        adTAeScuSCAInitiateRestore OBJECT-TYPE
                SYNTAX  INTEGER {
                    initiate(1)
                    }
                MAX-ACCESS  read-write
                STATUS  current
                DESCRIPTION
                  "Initiate Restore of SCA from customer TFTP server"
                ::= { adTAeSCUSCAControl 3 }

        adTAeScuSCAProvItemChanged OBJECT-TYPE
                SYNTAX  Integer32
                MAX-ACCESS  read-only
                STATUS  current
                DESCRIPTION
                  "Bitmap of cards with changed provisions.
                  This read-only OID will return a bitmap of slots
                  whose provisions have changed since power-up or the
                  last SCA save operation.  DB1 corresponds to slot 1,
                  DB31 corresponds to slot 31.  DB0 corresponds to the
                  Accessory Slot."
                ::= { adTAeSCUSCAControl 4 }

        adTAeScuSCAPresentCards OBJECT-TYPE
                SYNTAX  Integer32
                MAX-ACCESS  read-only
                STATUS  current
                DESCRIPTION
                  "Bitmap of card 'present' in the shelf.
                  This read-only OID will return a bitmap of
                  slots with cards installed.  DB1 corresponds
                  DB0 corresponds to the Accessory Slot."
                ::= { adTAeSCUSCAControl 5 }

        adTAeScuSCASlotsWithProvData OBJECT-TYPE
                SYNTAX  Integer32
                MAX-ACCESS  read-only
                STATUS  current
                DESCRIPTION
                  "Bitmap of slots with provision data.
                  This read-only OID will return a bitmap of slots
                  with provision information.  DB1 corresponds to
                  slot 1, DB31 corresponds to slot 31.  DB0 corresponds
                  to the Accessory Slot."
                ::= { adTAeSCUSCAControl 6 }

        adTAeScuSCASlotsInSCA OBJECT-TYPE
                SYNTAX  Integer32
                MAX-ACCESS  read-only
                STATUS  current
                DESCRIPTION
                  "Bitmap of slots in SCA.
                  This read-only OID will return a bitmap of slots
                  with provision information.  DB1 corresponds to
                  slot 1, DB31 corresponds to slot 31.  DB0 corresponds
                  to the Accessory Slot."
                ::= { adTAeSCUSCAControl 7 }

        adTAeScuSCASlotsWithProvDataInSCA OBJECT-TYPE
                SYNTAX  Integer32
                MAX-ACCESS  read-only
                STATUS  current
                DESCRIPTION
                  "Bitmap of slots with provision data in SCA.
                  This read-only OID will return a bitmap of slots
                  with provision information.  DB1 corresponds to
                  slot 1, DB31 corresponds to slot 31.  DB0 corresponds
                  to the Accessory Slot."
                ::= { adTAeSCUSCAControl 8 }

        --- Status table

        adTAeSCUSCAOperationStatusTable OBJECT-TYPE
            SYNTAX  SEQUENCE OF AdTAeSCUSCAOperationStatusEntry
            MAX-ACCESS  not-accessible
            STATUS  current
            DESCRIPTION
                "Operation status for each slot table."
           ::= { adTAeSCUSCAControl 10 }

        adTAeSCUSCAOperationStatusEntry OBJECT-TYPE
            SYNTAX  AdTAeSCUSCAOperationStatusEntry
            MAX-ACCESS  not-accessible
            STATUS  current
            DESCRIPTION
                "Operation status for each slot table."
           INDEX   { adGenSlotInfoIndex}
           ::= { adTAeSCUSCAOperationStatusTable 1 }

        AdTAeSCUSCAOperationStatusEntry ::=
            SEQUENCE {
                adTAeScuSCAOperationStatus
                    DisplayString
            }
            adTAeScuSCAOperationStatus OBJECT-TYPE
                SYNTAX  DisplayString (SIZE(0..255))
                MAX-ACCESS  read-only
                STATUS  current
                DESCRIPTION
                  "SCA system status: This read-only string will return
                  a formatted string indicating the progress or status
                  of the current or most recent SCA operation."
                ::= { adTAeSCUSCAOperationStatusEntry 1 }
        ---
        --- SCA Auto Save Management
        ---

        adTAeSCUSCAAutoSaveMgmt  OBJECT IDENTIFIER
           ::= { adTAeSCUSystemConfigArchiveMgmt 11 }


        adTAeScuSCAAutoSave OBJECT-TYPE
                SYNTAX  INTEGER {
                        enabled(1),
                        disabled(2)
                        }
                MAX-ACCESS  read-write
                STATUS  current
               DESCRIPTION
                  "Enable or disable AutoSave."
                ::= { adTAeSCUSCAAutoSaveMgmt 1 }

        adTAeScuSCAAutoSaveRetries OBJECT-TYPE
                SYNTAX  Integer32 (1..99)
                MAX-ACCESS  read-write
                STATUS  current
               DESCRIPTION
                  "AutoSave retries."
                ::= { adTAeSCUSCAAutoSaveMgmt 3 }

        adTAeScuSCAAutoSaveIfChanged OBJECT-TYPE
                SYNTAX  INTEGER {
                        enabled(1),
                        disabled(2)
                        }
                MAX-ACCESS  read-write
                STATUS  current
                DESCRIPTION
                  "This OID allows the admin to reduce the amount of
                  SCA-related network traffic by instructing the eSCU
                  to save SCA information only if provision changes
                  have been made to the eSCU, MUX, or linecards."
                ::= { adTAeSCUSCAAutoSaveMgmt 5 }

        adTAeScuSCAAutoSaveFileNamePrefix OBJECT-TYPE
                SYNTAX  DisplayString (SIZE(0..30))
                MAX-ACCESS  read-write
                STATUS  current
                DESCRIPTION
                  "This OID controls the SCA autosave filename prefix,
                  which is used to construct the full SCA autosave
                  archive filename.  The final filename will
                  consist of this prefix, a single underscore, a
                  single digit in the range 1..7 (instance) , and
                  the SCA filename suffix."
                ::= { adTAeSCUSCAAutoSaveMgmt 7 }

        adTAeScuSCAAutoSaveFileNameSuffix OBJECT-TYPE
                SYNTAX  DisplayString (SIZE(0..8))
                MAX-ACCESS  read-write
                STATUS  current
                DESCRIPTION
                  "This OID controls the SCA autosave filename suffix,
                  which is used to construct the full SCA autosave
                  archive filename.  The final filename will consist
                  of the SCA filename prefix, a single underscore, a
                  single digit in the range 1..7 (instance), and this
                  SCA filename suffix."
                ::= { adTAeSCUSCAAutoSaveMgmt 9 }


        adTAeScuSCAAutoSaveInstances OBJECT-TYPE
                SYNTAX  Integer32 (1..7)
                MAX-ACCESS  read-write
                STATUS  current
                DESCRIPTION
                  "This OID controls the maximum number of SCA filename
                  instances to save, or 'rotate' through on the SCA
                  TFTP server.  The eSCU will first save instance '1',
                  then '2', up to the value specified by this OID,
                  then cycle back to '1' on the subsequent save."
                ::= { adTAeSCUSCAAutoSaveMgmt 11 }

        adTAeScuSCAAutoSaveHoursAfter OBJECT-TYPE
                SYNTAX  Integer32 (0..23)
                MAX-ACCESS  read-write
                STATUS  current
                DESCRIPTION
                  "This OID controls how many hours after midnight autosave
                  operations should be scheduled. This allows the admin to
                  balance the SCA autosave load of many shelves so that all
                  the systems will not be attempting to contact the SCA
                  TFTP server at the same time."
                ::= { adTAeSCUSCAAutoSaveMgmt 13 }

        adTAeScuSCAAutoSaveMinutesAfter OBJECT-TYPE
                SYNTAX  Integer32 (0..59)
                MAX-ACCESS  read-write
                STATUS  current
                DESCRIPTION
                  "This OID controls how many minutes after the 'hour' oid
                  autosave operations should be scheduled.  This allows
                  the admin to balance the SCA autosave load of many
                  shelves so that all the systems will not be attempting
                  to contact the SCA TFTP server at the same time."
                ::= { adTAeSCUSCAAutoSaveMgmt 15 }

        adTAeScuSCADateTimeLastAutoSave OBJECT-TYPE
                SYNTAX  DisplayString (SIZE(0..20))
                MAX-ACCESS  read-only
                STATUS  current
                DESCRIPTION
                  "This read-only OID will return the ASCII date/time of
                  the last SCA autosave operation, or
                  an empty string if none."
                ::= { adTAeSCUSCAAutoSaveMgmt 17 }

        adTAeScuSCADateTimeNextAutoSave OBJECT-TYPE
                SYNTAX  DisplayString (SIZE(0..20))
                MAX-ACCESS  read-only
                STATUS  current
                DESCRIPTION
                  "This read-only OID will return the ASCII date/time of
                  the next SCA autosave operation, or
                  an empty string if none."
                ::= { adTAeSCUSCAAutoSaveMgmt 18 }

        ---
        --- SCA Restore Management
        ---

        adTAeSCUSCARestoreMgmt  OBJECT IDENTIFIER
           ::= { adTAeSCUSystemConfigArchiveMgmt 12 }

        adTAeScuSCAoptRestoreESCU OBJECT-TYPE
                SYNTAX  INTEGER {
                        enabled(1),
                        disabled(2)
                        }
                MAX-ACCESS  read-write
                STATUS  current
                DESCRIPTION
                  "This OID controls whether any eSCU-related
                  provisions should be restored and is a master
                  override for the restore of all eSCU-related
                  provisions.  Setting this OID to 'disable'
                  will result in all of the following eSCU-related
                  enable/disable settings being evaluated
                  as 'disabled' at the time of an SCA restore
                  operation.  Setting this value to 'enable' will
                  result in the normal evaluation of each following
                  eSCU-related enable/disable settings."
                ::= { adTAeSCUSCARestoreMgmt 1 }

        adTAeScuSCAoptRestoreSCA OBJECT-TYPE
                SYNTAX  INTEGER {
                        enabled(1),
                        disabled(2)
                        }
                MAX-ACCESS  read-write
                STATUS  current
                DESCRIPTION
                  "This OID controls whether SCA-related
                  provisions should be restored on the eSCU."
                ::= { adTAeSCUSCARestoreMgmt 2 }

        adTAeScuSCAoptRestoreNetwork OBJECT-TYPE
                SYNTAX  INTEGER {
                        enabled(1),
                        disabled(2)
                        }
                MAX-ACCESS  read-write
                STATUS  current
                DESCRIPTION
                  "This OID controls whether general IP
                  network-related provisions should be restored
                  on the eSCU.  This would include such items as
                  secondary telnet port numbers, IP-forwarding enable,
                  etc."
                ::= { adTAeSCUSCARestoreMgmt 3 }

        adTAeScuSCAoptRestoreNetworkInterface OBJECT-TYPE
                SYNTAX  INTEGER {
                        enabled(1),
                        disabled(2)
                        }
                MAX-ACCESS  read-write
                STATUS  current
                DESCRIPTION
                  "This OID controls whether IP network interface-related provisions should
                  be restored on the eSCU.  This would include such items as
                  IP/netmask/gateway/default-route settings on the IP network interfaces."
                ::= { adTAeSCUSCARestoreMgmt 4 }

        adTAeScuSCAoptRestoreSNMP OBJECT-TYPE
                SYNTAX  INTEGER {
                        enabled(1),
                        disabled(2)
                        }
                MAX-ACCESS  read-write
                STATUS  current
                DESCRIPTION
                  "This OID controls whether SNMP-related
                  provisions should be restored on the eSCU."
                ::= { adTAeSCUSCARestoreMgmt 5 }

        adTAeScuSCAoptRestoreSecurity OBJECT-TYPE
                SYNTAX  INTEGER {
                        enabled(1),
                        disabled(2)
                        }
                MAX-ACCESS  read-write
                STATUS  current
                DESCRIPTION
                  "This OID controls whether security-system
                  provisions should be restored on the eSCU.
                  This would include such items as user
                  account information."
                ::= { adTAeSCUSCARestoreMgmt 6 }

        adTAeScuSCAoptRestoreLineCard OBJECT-TYPE
                SYNTAX  INTEGER {
                        enabled(1),
                        disabled(2)
                        }
                MAX-ACCESS  read-write
                STATUS  current
                DESCRIPTION
                  "This OID controls whether provisions should
                  be restored to linecards and MUXs and is a master
                  override for the restore of all Module-related
                  provisions.  Setting this OID to 'disable'
                  will result in all of the following Module-related
                  enable/disable settings being evaluated
                  as 'disabled' at the time of an SCA restore
                  operation.  Setting this value to 'enable' will
                  result in the normal evaluation of each following
                  Module-related enable/disable settings."
                ::= { adTAeSCUSCARestoreMgmt 7 }

        adTAeScuSCAoptRestoreInServiceLineCard OBJECT-TYPE
                SYNTAX  INTEGER {
                        enabled(1),
                        disabled(2)
                        }
                MAX-ACCESS  read-write
                STATUS  current
                DESCRIPTION
                  "This OID controls whether provisions should
                  be restored to in-service linecards and MUXs."
                ::= { adTAeSCUSCARestoreMgmt 8 }

        adTAeScuSCAoptRestoreEmptySlot OBJECT-TYPE
                SYNTAX  INTEGER {
                        enabled(1),
                        disabled(2)
                        }
                MAX-ACCESS  read-write
                STATUS  current
                DESCRIPTION
                  "This OID controls whether provisions should
                  be restored to empty slots.  This operation is often
                  called pre-provisioning."
                ::= { adTAeSCUSCARestoreMgmt 9 }

        adTAeScuSCAoptRestoreCardBitmask OBJECT-TYPE
                SYNTAX  Integer32
                MAX-ACCESS  read-write
                STATUS  current
                DESCRIPTION
                  "SCA restore to linecard enable bitmask.
                   This OID accesses a enable/disable bitmap indicating which slots
                   should have their provision information restored during an SCA
                   restore operation.  Valid slots are 1..30 or 1..24, depending on
                   shelf type.  DB1 corresponds to slot 1, DB31 corresponds to slot
                   31."
                ::= { adTAeSCUSCARestoreMgmt 12 }

        adTAeScuSCADateTimeSaveInvoked OBJECT-TYPE
                SYNTAX  DisplayString (SIZE(0..20))
                MAX-ACCESS  read-only
                STATUS  current
                DESCRIPTION
                  "This read-only OID will return the ASCII date/time of the
                  last manually-invoked SCA save operation, or an empty
                  string if none."
                ::= { adTAeSCUSCARestoreMgmt 13 }

        adTAeScuSCACardsRestoredBitmask OBJECT-TYPE
                SYNTAX  Integer32
                MAX-ACCESS  read-only
                STATUS  current
                DESCRIPTION
                  "This read-only OID will return a bitmask of cards restored."
                ::= { adTAeSCUSCARestoreMgmt 14 }

        adTAeScuSCACardsNotRestoredBitmask OBJECT-TYPE
                SYNTAX  Integer32
                MAX-ACCESS  read-only
                STATUS  current
                DESCRIPTION
                  "This read-only OID will return a bitmask of cards not restored."
                ::= { adTAeSCUSCARestoreMgmt 15 }

        adTAeScuSCACardsExcludedBitmask OBJECT-TYPE
                SYNTAX  Integer32
                MAX-ACCESS  read-only
                STATUS  current
                DESCRIPTION
                  "This read-only OID will return a bitmask of cards excluding from
                  the SCA restore operation."
                ::= { adTAeSCUSCARestoreMgmt 16 }

        adTAeScuSCARestoreCardErrorsBitmask OBJECT-TYPE
                SYNTAX  Integer32
                MAX-ACCESS  read-only
                STATUS  current
                DESCRIPTION
                  "This read-only OID will return a bitmask of cards with restore errors."
                ::= { adTAeSCUSCARestoreMgmt 17 }

        --
        --
        --
        --
        --
        --
        --
        --
        --
        --
        -- System Log group
        --
        --
        --

        adTAeSCUSystemLog OBJECT IDENTIFIER
                                  ::= { adTAeSCUmg 14 }

        adTAeSCUSystemLogAlarm OBJECT-TYPE
                SYNTAX  INTEGER {
                        enabled(1),
                        disabled(2)
                        }
                MAX-ACCESS  read-write
                STATUS  current
                DESCRIPTION
                  "Enable or disable System full alaram."
                ::= { adTAeSCUSystemLog 3 }

        adTAeSCUSystemLogPercentFull OBJECT-TYPE
                SYNTAX  Integer32
                MAX-ACCESS  read-only
                STATUS  current
                DESCRIPTION
                  "Percentage of System Log buffer used.  When the
                   System Log is full it will remove the oldest half
                   of its entries.  When the System log is 70% full,
                   it will send a alarm every 5% used so an administration
                   could upload the system log."
                ::= { adTAeSCUSystemLog 5 }

        adTAeSCUSystemLogCount OBJECT-TYPE
                SYNTAX  Integer32
                MAX-ACCESS  read-only
                STATUS  current
                DESCRIPTION
                  "Number of entries in system log."
                ::= { adTAeSCUSystemLog 7 }

        adTAeSCUSystemSummReport OBJECT-TYPE
                SYNTAX  INTEGER {
                        allEvents(1),
                        loginAndLogoutEvents(2), -- all login and logouts
                        accountChangesEvents(3), -- all changes made to accounts
                        snmpProvisioning(4),     -- all provisions but not account changes
                        networkProvisioning(5),  -- all provisions but not account changes
                        tftpYmodemUpdates(6),    -- all TFTP Ymodem firmware Updates
                        scaEvents(7),            -- SCA provisioning and events
                        securityOptionsProv(8),  -- Security options provisioned
                        dateAndTimeProv(9)       -- date and time changes
                        }
                MAX-ACCESS  read-write
                STATUS  current
                DESCRIPTION
                  "Allows summary reports.."
                ::= { adTAeSCUSystemLog 8 }

        adTAeSCUSystemEnableDetail OBJECT-TYPE
                SYNTAX  INTEGER {
                        enabled(1),
                        disabled(2)
                        }
                MAX-ACCESS  read-write
                STATUS  current
                DESCRIPTION
                  "Enable or disable detail reports."
                ::= { adTAeSCUSystemLog 9 }

        adTAeSCUSystemLogFailureDescription OBJECT-TYPE
                SYNTAX  DisplayString
                MAX-ACCESS  read-only
                STATUS  current
                DESCRIPTION
                  "An string description of a system log Failure.
                   This OID is valid in a SNMP trap."
                ::= { adTAeSCUSystemLog 10 }

        adTAeSCUSystemLogTable OBJECT-TYPE
            SYNTAX  SEQUENCE OF AdTAeSCUSystemLogEntry
            MAX-ACCESS  not-accessible
            STATUS  current
            DESCRIPTION
                "The SCU System Log table."
           ::= { adTAeSCUSystemLog 15 }

        adTAeSCUSystemLogEntry OBJECT-TYPE
            SYNTAX  AdTAeSCUSystemLogEntry
            MAX-ACCESS  not-accessible
            STATUS  current
            DESCRIPTION
                "An entry in the SCU System Log table.
                 Readonly object."
           INDEX   { adTAeSCUSystemLogIndex }
           ::= { adTAeSCUSystemLogTable 1 }

        AdTAeSCUSystemLogEntry ::=
            SEQUENCE {
               adTAeSCUSystemLogIndex
                     Integer32,
                adTAeSCUSystemLogDescription
                     DisplayString
            }
        adTAeSCUSystemLogIndex OBJECT-TYPE
                SYNTAX  Integer32
                MAX-ACCESS  read-only
                STATUS  current
                DESCRIPTION
                  "An not-accessible index value. The contoller will not respond to this OID."
                ::= { adTAeSCUSystemLogEntry 1 }

        adTAeSCUSystemLogDescription OBJECT-TYPE
                SYNTAX  DisplayString
                MAX-ACCESS  read-only
                STATUS  current
                DESCRIPTION
                  "An string description of a system log entry."
                ::= { adTAeSCUSystemLogEntry 5 }



        --
        --
        --
        --
        -- adTAeScuTL1ActivityLog group
        --
        --
        --

        adTAeScuTL1ActivityLog OBJECT IDENTIFIER
                                  ::= { adTAeSCUmg 15 }


        adTAeScuResetTL1Log OBJECT-TYPE
                SYNTAX  INTEGER {
                        resetTL1Log(1)
                        }
                MAX-ACCESS  read-write
                STATUS  current
                DESCRIPTION
                  "Reset TL1 Log. "
                ::= { adTAeScuTL1ActivityLog 2 }


        adTAeScuTL1ActivityLogTable OBJECT-TYPE
            SYNTAX  SEQUENCE OF AdTAeScuTL1ActivityLogEntry
            MAX-ACCESS  not-accessible
            STATUS  current
            DESCRIPTION
                "The System TL1 Log table."
           ::= { adTAeScuTL1ActivityLog 6 }

        adTAeScuTL1ActivityLogEntry OBJECT-TYPE
            SYNTAX  AdTAeScuTL1ActivityLogEntry
            MAX-ACCESS  not-accessible
            STATUS  current
            DESCRIPTION
                "An entry in the System TL1 Log table.
                 Readonly object."
           INDEX   { adTAeSCUTL1LogIndex}
           ::= { adTAeScuTL1ActivityLogTable 1 }

        AdTAeScuTL1ActivityLogEntry ::=
            SEQUENCE {
            adTAeSCUTL1LogIndex
               Integer32,
                adTAeScuTL1ActivityLogDescription
                     DisplayString
            }

      adTAeSCUTL1LogIndex OBJECT-TYPE
         SYNTAX     Integer32
            MAX-ACCESS  read-only
            STATUS  current
            DESCRIPTION
               "An Index value to the TL1 Log.."
            ::= { adTAeScuTL1ActivityLogEntry 1 }

        adTAeScuTL1ActivityLogDescription OBJECT-TYPE
                SYNTAX  DisplayString
                MAX-ACCESS  read-only
                STATUS  current
                DESCRIPTION
                  "An string description of a system Tl1 log entry.
                   This string contains the TL1 command and response."
                ::= { adTAeScuTL1ActivityLogEntry 2 }


         --
      --
      --
      --
      -- Password Complexity Config
      --
      --

      adTAeSCUSysPasswordComplexity OBJECT IDENTIFIER
                                  ::= { adTAeSCUSecurityAccountMg 10 }

        adTAeSCUSysEnablePswdComplexity OBJECT-TYPE
                SYNTAX  INTEGER {
                        enabled(1),
                        disabled(2)
                        }
                MAX-ACCESS  read-write
                STATUS  current
                DESCRIPTION
                  "Enable or disable Password Complexity algorithms."
                ::= { adTAeSCUSysPasswordComplexity 1 }

        adTAeSCUSysMinPasswordLength OBJECT-TYPE
                SYNTAX  Integer32 (6..15)
                MAX-ACCESS  read-write
                STATUS  current
                DESCRIPTION
                  "Minimum password length required."
                ::= { adTAeSCUSysPasswordComplexity 2 }

       adTAeSCUSysUpperCaseRequired OBJECT-TYPE
                SYNTAX  INTEGER {
                        enabled(1),
                        disabled(2)
                        }
                MAX-ACCESS  read-write
                STATUS  current
                DESCRIPTION
                  "Upper case character required in password."
                ::= { adTAeSCUSysPasswordComplexity 3 }

       adTAeSCUSysLowerCaseRequired OBJECT-TYPE
                SYNTAX  INTEGER {
                        enabled(1),
                        disabled(2)
                        }
                MAX-ACCESS  read-write
                STATUS  current
                DESCRIPTION
                  "Lower case character required in password."
                ::= { adTAeSCUSysPasswordComplexity 4 }

        adTAeSCUSysDigitRequired OBJECT-TYPE
                SYNTAX  INTEGER {
                        enabled(1),
                        disabled(2)
                        }
                MAX-ACCESS  read-write
                STATUS  current
                DESCRIPTION
                  "A digit is required in password."
                ::= { adTAeSCUSysPasswordComplexity 5 }

       adTAeSCUSysSpecialCharacterRequired OBJECT-TYPE
                SYNTAX  INTEGER {
                        enabled(1),
                        disabled(2)
                        }
                MAX-ACCESS  read-write
                STATUS  current
                DESCRIPTION
                  "A special character is required in password."
                ::= { adTAeSCUSysPasswordComplexity 6 }

         adTAeSCUSysCaseSensitivePassword OBJECT-TYPE
                SYNTAX  INTEGER {
                        enabled(1),
                        disabled(2)
                        }
                MAX-ACCESS  read-write
                STATUS  current
                DESCRIPTION
                  "The system will store a case sensitive password."
                ::= { adTAeSCUSysPasswordComplexity 7 }


        adTAeSCUSysNullPasswordAccepted OBJECT-TYPE
                SYNTAX  INTEGER {
                        enabled(1),
                        disabled(2)
                        }
                MAX-ACCESS  read-write
                STATUS  deprecated
                DESCRIPTION
                  "This OID will no longer work. A NULL password is accepted."
                ::= { adTAeSCUSysPasswordComplexity 8 }

        adTAeSCUSecPasswordStartEndDigitCheck OBJECT-TYPE
                SYNTAX  INTEGER {
                        enabled(1),
                        disabled(2)
                        }
                MAX-ACCESS  read-write
                STATUS  current
                DESCRIPTION
                  "Password cannot start or end with a digit."
                ::= { adTAeSCUSysPasswordComplexity 10 }

        adTAeSCUSecLastSixPasswordCheck   OBJECT-TYPE
                SYNTAX  INTEGER {
                        enabled(1),
                        disabled(2)
                        }
                MAX-ACCESS  read-write
                STATUS  current
                DESCRIPTION
                  "Password cannot be the same as previous six passwords."
                ::= { adTAeSCUSysPasswordComplexity 12 }
        --
      --
      --
      --
      -- RADIUS Login Config
      --
      --

      adTAeSCUSysRADIUsConfig OBJECT IDENTIFIER
                                  ::= { adTAeSCUSecurityAccountMg 9 }

      adTAeScuRADIUSServAuthentication OBJECT-TYPE
         SYNTAX     INTEGER {
                        enableRADIUSAuthentication(1),       -- Use RADIUS server to login
                  enableLocalAccountAuthentication(2)  -- Use the local accounts.
                        }
            MAX-ACCESS  read-write
            STATUS  deprecated
            DESCRIPTION
               "Determine how the user Login into the system.  "
            ::= { adTAeSCUSysRADIUsConfig 2 }

       adTAeScuRadiusTL1Authentication OBJECT-TYPE
         SYNTAX     INTEGER {
                        enableRADIUSAuthentication(1),       -- Use RADIUS server to login
                  enableLocalAccountAuthentication(2)  -- Use the local accounts.
                        }
            MAX-ACCESS  read-write
            STATUS  current
            DESCRIPTION
               "Determine how the user Login into TL1.  "
            ::= { adTAeSCUSysRADIUsConfig 3 }

        adTAeScuRadiusAccountAccessLevel OBJECT-TYPE
         SYNTAX     INTEGER {
                        noneRejectLogin(1),   -- No access. Reject login
                  readOnlyAccess(2),    -- READ_ONLY Access.
                  readWriteAccess(3),   -- READ_WRITE Access
                  testAccess(4),        -- TEST access
                  configAccess(5),      -- CONFIG access
                  adminAccess(6)        -- ADMIN access
                        }
            MAX-ACCESS  read-write
            STATUS  current
            DESCRIPTION
               "Default account access previledge given to a RADIUS account
                if the RADIUS Server does not provide the Adtran level.
               Access privilege will be communicated as a Vendor Specific
               Attribute in the RADIUS Server reply packet.

                   # Values for Adtran-Telnet-Level attribute for the Total Access IADs
               # This attribute sets the Access level granted to a user for a particular
               # telnet session.
               VALUE		Adtran-IAD-Telnet-Level		Level-Full     0
               VALUE		Adtran-IAD-Telnet-Level		Level-Support  1
               VALUE		Adtran-IAD-Telnet-Level		Level-Config   2
               VALUE		Adtran-IAD-Telnet-Level		Level-Router   3
               VALUE		Adtran-IAD-Telnet-Level		Level-Voice    4
               VALUE		Adtran-IAD-Telnet-Level		Level-Status   5
               *********where*************
               -- ADMIN      - Level-Full
               -- CONFIG     - Level-Config
               -- TEST       - Level-Support
               -- READ_WRITE - Level-Router
               -- READ_ONLY  - Level-Status.
               "
            ::= { adTAeSCUSysRADIUsConfig 4 }

        adTAeScuRADIUSFallbackMode OBJECT-TYPE
         SYNTAX     INTEGER {
                        retryRADIUSAuthentication(1),       -- Use RADIUS server to login
                        fallbackToLocalAccountAuthentication(2)  -- Use the local accounts.
                        }
            MAX-ACCESS  read-write
            STATUS  deprecated
            DESCRIPTION
               "Determine how the user Login to the controller there is a failure to
                contact all four RADIUS servers.
                If fall back mode will be controlled by adTAeSCUSecAccountAuthenticationMethod.
                If adTAeSCUSecAccountAuthenticationMethod works then this OID is ignored."
            ::= { adTAeSCUSysRADIUsConfig 5 }

        adTAeScuRADIUSServerTable OBJECT-TYPE
            SYNTAX  SEQUENCE OF AdTAeScuRADIUSServerEntry
            MAX-ACCESS  not-accessible
            STATUS  current
            DESCRIPTION
                "RADIUS authentication settings."
           ::= { adTAeSCUSysRADIUsConfig 6 }


      --
      --

        adTAeScuRADIUSServerEntry OBJECT-TYPE
            SYNTAX  AdTAeScuRADIUSServerEntry
            MAX-ACCESS  not-accessible
            STATUS  current
            DESCRIPTION
                "An entry in the RADIUS settings table."
           INDEX   { adTAeScuRadiusCfgIndex}
           ::= { adTAeScuRADIUSServerTable 1 }

        AdTAeScuRADIUSServerEntry ::=
            SEQUENCE {
            adTAeScuRadiusCfgIndex
                Integer32,
            adTAeScuRadiusServerAddress
                DisplayString,
            adTAeScuRadiusServerPortNumber
                Integer32,
            adTAeScuRadiusServerSecret
                DisplayString,
            adTAeScuRADIUSServRetries
                Integer32,
            adTAeScuRADIUSServContactTimeOut
                Integer32,
            adTAeScuRadiusServerSequence
                Integer32,
            adTAeScuRadiusServerName
                DisplayString,
            adTAeScuRadiusServerAddressType
                 InetAddressType,
            adTAeScuRadiusServerInetAddress
                 InetAddress
            }

      adTAeScuRadiusCfgIndex OBJECT-TYPE
         SYNTAX     Integer32
            MAX-ACCESS  read-only
            STATUS  current
            DESCRIPTION
               "An Index to RADIUS authentication settings"
            ::= { adTAeScuRADIUSServerEntry 1 }

        adTAeScuRadiusServerAddress OBJECT-TYPE
                SYNTAX  DisplayString
                MAX-ACCESS  read-write
                STATUS  deprecated
                DESCRIPTION
                  "RADIUS Server IP address.
                  deprecated to support IPv6.  Use adTAeScuRadiusServerInetAddress."
                ::= { adTAeScuRADIUSServerEntry 2 }

      adTAeScuRadiusServerPortNumber OBJECT-TYPE
         SYNTAX     Integer32
            MAX-ACCESS  read-write
            STATUS  current
            DESCRIPTION
               "RADIUS Server IP port address."
            ::= { adTAeScuRADIUSServerEntry 3 }

      adTAeScuRadiusServerSecret OBJECT-TYPE
                SYNTAX  DisplayString
                MAX-ACCESS  read-write
                STATUS  current
                DESCRIPTION
                  "The key used in encrypting the packets passed between the
                   RADIUS Server and the client. This key must match the one
                   configured on the server."
                ::= { adTAeScuRADIUSServerEntry 4 }

      adTAeScuRADIUSServRetries OBJECT-TYPE
         SYNTAX     Integer32 (0..255)
            MAX-ACCESS  read-write
            STATUS  current
            DESCRIPTION
               "Number of retries to contact RADIUS Server.  "
            ::= { adTAeScuRADIUSServerEntry 5 }

      adTAeScuRADIUSServContactTimeOut OBJECT-TYPE
         SYNTAX     Integer32 (1000..30000)
            MAX-ACCESS  read-write
            STATUS  current
            DESCRIPTION
               "RADIUS Server responses time out in milliseconds."
            ::= { adTAeScuRADIUSServerEntry 6 }

      adTAeScuRadiusServerSequence OBJECT-TYPE
         SYNTAX     Integer32 (0..4)
            MAX-ACCESS  read-write
            STATUS  current
            DESCRIPTION
               "RADIUS Server sequence that ranks priority of each server.
               [0] if no IP is assigned at given index. 
               [1-4] for each additional server added in increasing order. The default
               sequence will match the index that each server is found at."
            ::= { adTAeScuRADIUSServerEntry 7 }
            
      adTAeScuRadiusServerName OBJECT-TYPE
         SYNTAX  DisplayString
            MAX-ACCESS  read-write
            STATUS  current
            DESCRIPTION
               "Name to be assigned to a given RADIUS server for ease of reference. 
                Can use either the given name assigned or the IP associated with 
                server to reference it."
            ::= { adTAeScuRADIUSServerEntry 8 }

      adTAeScuRadiusServerAddressType OBJECT-TYPE
        SYNTAX InetAddressType
        MAX-ACCESS read-only
        STATUS     current
        DESCRIPTION
               "The type of adTAeScuRadiusServerInetAddress."
        ::= { adTAeScuRADIUSServerEntry 9 }

      adTAeScuRadiusServerInetAddress OBJECT-TYPE
        SYNTAX InetAddress
        MAX-ACCESS read-write
        STATUS     current
        DESCRIPTION
               "RADIUS Server IP address.
                Backwards compatibility:  Setting this address to a IPv4
                address will provision old address adTAeScuRadiusServerAddress
                with the new address.
                Setting this address to an IPV6 will leave the old provision
                address adTAeScuRadiusServerAddress as is."
        ::= { adTAeScuRADIUSServerEntry 10 }
        --
        -- Account Lock-out Settings
        --

        adTAeScuAccLockOutSettings OBJECT IDENTIFIER
                  ::= { adTAeSCUSecurityAccountMg 12 }

         adTAeScuEnableAccLoginFailureLockOut OBJECT-TYPE
         SYNTAX Integer32 (1..2)
            MAX-ACCESS  read-write
            STATUS  current
            DESCRIPTION
               "Enable users to be locked-out after failed login attempts."
            ::= { adTAeScuAccLockOutSettings 1 }

         adTAeScuEnableLockOutAlarm OBJECT-TYPE
         SYNTAX Integer32 (1..2)
            MAX-ACCESS  read-write
            STATUS  current
            DESCRIPTION
               "Generate an alarm when an account triggers lock-out conditions."
            ::= { adTAeScuAccLockOutSettings 2 }

         adTAeScuEnableIndefLockOut OBJECT-TYPE
         SYNTAX Integer32 (1..2)
            MAX-ACCESS  read-write
            STATUS  current
            DESCRIPTION
               "Forces the account to be reset by an Administrator once locked.."
            ::= { adTAeScuAccLockOutSettings 3 }

         adTAeScuNumLockOutLoginAttempts OBJECT-TYPE
         SYNTAX Integer32 (2..15)
            MAX-ACCESS  read-write
            STATUS  current
            DESCRIPTION
               "Number of consecutive failed login attempts before a lockout occurs."
            ::= { adTAeScuAccLockOutSettings 4 }

         adTAeScuLockOutDuration OBJECT-TYPE
         SYNTAX Integer32 (1..60)
            MAX-ACCESS  read-write
            STATUS  current
            DESCRIPTION
               "The number of minutes the user will be locked out."
            ::= { adTAeScuAccLockOutSettings 5 }

        --
        --
        adTAeTrustedClientConfig OBJECT IDENTIFIER
                                  ::= { adTAeSCUSecurityAccountMg 13 }

       adTAeTrustedIPClientAccessControl OBJECT-TYPE
         SYNTAX     INTEGER {
                        enableTrustedClientAccessControl(1),  -- enable Trusted Client Access Control
                        disableTrustedClientAccessControl(2)  -- disable Trusted Client Access Control.
                        }
            MAX-ACCESS  read-write
            STATUS  current
            DESCRIPTION
               "Enable or disable IP Access to the controller based on the Trusted IP Client list.
                An IP address not on the list will be rejected.
                **********WARNING**********
                If there are no adTAeTrustedIPClientEntry, a SNMP wrong value error will be returned.
                ***************************
                "
            ::= { adTAeTrustedClientConfig 3 }

        adTAeTrustedIPClientAccessName OBJECT-TYPE
         SYNTAX     DisplayString (SIZE(0..49))
            MAX-ACCESS  read-write
            STATUS  current
            DESCRIPTION
               "Tursted IP Access-list name.
                Deletes all Trusted IP Clients when set to an empty string.
                Disables Trusted IP Clients feature when set to an empty string."
            ::= { adTAeTrustedClientConfig 4 }

        adTAeTrustedIPClientTable OBJECT-TYPE
            SYNTAX  SEQUENCE OF AdTAeTrustedIPClientEntry
            MAX-ACCESS  not-accessible
            STATUS  current
            DESCRIPTION
                "Trusted IP Client Table."
           ::= { adTAeTrustedClientConfig 6 }
           
        adTAeTrustedInetClientTable OBJECT-TYPE
            SYNTAX  SEQUENCE OF AdTAeTrustedInetClientEntry
            MAX-ACCESS  not-accessible
            STATUS  current
            DESCRIPTION
                "IPv4 and IPv6 Trusted IP Client Table."
           ::= { adTAeTrustedClientConfig 8 }

        adTAeTrustedIPClientEntry OBJECT-TYPE
            SYNTAX  AdTAeTrustedIPClientEntry
            MAX-ACCESS  not-accessible
            STATUS  current
            DESCRIPTION
                "An entry in theTrusted IP Client table."
           INDEX   { adTAeTrustedIPAddress,adTAeTrustedIPNetworkBits}
           ::= { adTAeTrustedIPClientTable 1 }
           
        AdTAeTrustedIPClientEntry ::=
            SEQUENCE {
                adTAeTrustedIPAddress
                    IpAddress,
                adTAeTrustedIPNetworkBits
                    Integer32,
                adTAeTrustedClientStatus
                    INTEGER,
                adTAeTrustedClientResource
                    INTEGER
            }

      adTAeTrustedClientStatus OBJECT-TYPE
         SYNTAX     INTEGER {
                        active(1),               -- Trusted IP Client is active
                     createTrustedClient(2),  -- Create a Trusted IP Client
                        deleteTrustedClient(3)   -- Delete a Trusted IP Client
                        }
            MAX-ACCESS  read-write
            STATUS  current
            DESCRIPTION
               "An Index to adTAeTrustedIPClientTable."
            ::= { adTAeTrustedIPClientEntry 1 }

        adTAeTrustedIPAddress OBJECT-TYPE
         SYNTAX     IpAddress
            MAX-ACCESS  read-only
            STATUS  current
            DESCRIPTION
               "An IPv4 address that is allowed access to the controller. "
            ::= { adTAeTrustedIPClientEntry 2 }

        adTAeTrustedIPNetworkBits OBJECT-TYPE
         SYNTAX     Integer32 (1..32)
            MAX-ACCESS  read-only
            STATUS  current
            DESCRIPTION
               "This number is used to generate a netmask.  Each connection
                    IP address is masked and compeared to a adTAeTrustedIPAddress
                    masked generated by adTAeTrustedIPNetworkBits to see if the
                    connection request is a Trusted IP Address.

                    NetMasks generated by adTAeTrustedIPNetworkBits:
                    1 0x80000000    9 0xFF800000   17 0xFFFF8000   25 0xFFFFFF80
                    2 0xC0000000   10 0xFFC00000   18 0xFFFFC000   26 0xFFFFFFC0
                    3 0xE0000000   11 0xFFE00000   19 0xFFFFE000   27 0xFFFFFFE0
                    4 0xF0000000   12 0xFFF00000   20 0xFFFFF000   28 0xFFFFFFF0
                    5 0xF8000000   13 0xFFF80000   21 0xFFFFF800   29 0xFFFFFFF8
                    6 0xFC000000   14 0xFFFC0000   22 0xFFFFFC00   30 0xFFFFFFFC
                    7 0xFE000000   15 0xFFFE0000   23 0xFFFFFE00   31 0xFFFFFFFE
                    8 0xFF000000   16 0xFFFF0000   24 0xFFFFFF00   32 0xFFFFFFFF

                    "
            ::= { adTAeTrustedIPClientEntry 3 }

        adTAeTrustedClientResource OBJECT-TYPE
         SYNTAX     INTEGER {
                        allPorts(1),         -- Trusted IP Client Unlimited Access
                  snmpPorts(2),        -- Trusted IP Client SNMP Access
                        menuPorts(3),        -- Trusted IP Client Menu Access
                        tL1Ports(4),         -- Trusted IP Client TL1 Access
                        snmpMenuPorts(5),    -- Trusted IP Client SNMP and Menu Access
                        snmpTL1Ports(6),     -- Trusted IP Client SNMP and TL1 Access
                        menuTL1Ports(7)      -- Trusted IP Client Menu and TL1 Access
                        }
            MAX-ACCESS  read-write
            STATUS  current
            DESCRIPTION
               "Indicate what type of access a trusted client has."
            ::= { adTAeTrustedIPClientEntry 4 }
            
        adTAeTrustedInetClientEntry OBJECT-TYPE
            SYNTAX  AdTAeTrustedInetClientEntry
            MAX-ACCESS  not-accessible
            STATUS  current
            DESCRIPTION
                "An entry in the IPv4 and IPv6 Trusted IP Client Table."
           INDEX   {adTAeTrustedInetAddressType,adTAeTrustedInetNetworkBits,adTAeTrustedInetAddress}
           ::= { adTAeTrustedInetClientTable 1 }
           
        AdTAeTrustedInetClientEntry ::=
            SEQUENCE {
                adTAeTrustedInetClientStatus
                    INTEGER,
                adTAeTrustedInetAddressType
                    InetAddressType,
                adTAeTrustedInetNetworkBits
                    Integer32,
                adTAeTrustedInetAddress
                    InetAddress,
                adTAeTrustedInetClientResource
                    INTEGER
            }
            
        adTAeTrustedInetClientStatus OBJECT-TYPE
         SYNTAX     INTEGER {
                        active(1),               -- Trusted IP Client is active
                        createTrustedClient(2),  -- Create a Trusted IP Client
                        deleteTrustedClient(3)   -- Delete a Trusted IP Client
                        }
            MAX-ACCESS  read-write
            STATUS  current
            DESCRIPTION
               "The status of the IPv4 and IPv6 address in the Trusted IP Client Table."
            ::= { adTAeTrustedInetClientEntry 1 }
            
        adTAeTrustedInetAddressType OBJECT-TYPE
         SYNTAX InetAddressType
            MAX-ACCESS read-only
            STATUS     current
            DESCRIPTION
               "The type of adTAeTrustedInetAddress."
              ::= { adTAeTrustedInetClientEntry 2 }
              
        adTAeTrustedInetNetworkBits OBJECT-TYPE
         SYNTAX     Integer32 (1..128)
            MAX-ACCESS  read-only
            STATUS  current
            DESCRIPTION
               "This number is used to generate a netmask.  Each connection
                    IP address is masked and compared to a adTAeTrustedInetAddress
                    masked generated by adTAeTrustedInetNetworkBits to see if the
                    connection request is a Trusted IP Address.
                    "
            ::= { adTAeTrustedInetClientEntry 3 }
             
        adTAeTrustedInetAddress OBJECT-TYPE
         SYNTAX     InetAddress
            MAX-ACCESS  read-only
            STATUS  current
            DESCRIPTION
               "An IPv4 or IPv6 address that is allowed access to the controller. "
            ::= { adTAeTrustedInetClientEntry 4 }
            
        adTAeTrustedInetClientResource OBJECT-TYPE
         SYNTAX     INTEGER {
                        allPorts(1),         -- Trusted IP Client Unlimited Access
                        snmpPorts(2),        -- Trusted IP Client SNMP Access
                        tL1Ports(3),         -- Trusted IP Client TL1 Access
                        snmpTL1Ports(4)      -- Trusted IP Client SNMP and TL1 Access
                        }
            MAX-ACCESS  read-write
            STATUS  current
            DESCRIPTION
               "Indicate what type of access a trusted client has in the 
                IPv4 and IPv6 Trusted IP Client Table.."
            ::= { adTAeTrustedInetClientEntry 5 }
        --
      --
      --
      --
      -- Advisory Warning Configuration
      --
      --

      adTAeSCUSysAdvisoryConfig OBJECT IDENTIFIER
                                  ::= { adTAeSCUSecurityAccountMg 20 }

        --
      --
        adTAeScuEnableMenuAdvisoryWarningMsg OBJECT-TYPE
         SYNTAX     INTEGER {
                  enableAdvisoryWarningMsg(1),       -- Enable AdvisoryWarning
                  disableAdvisoryWarniningMsg(2)    -- Disable Advisory Warning
                        }
            MAX-ACCESS  read-write
            STATUS  current
            DESCRIPTION
               "Enable or disable Menu Advisory Waring Message."
            ::= { adTAeSCUSysAdvisoryConfig 1 }

        adTAeScuEnableTL1AdvisoryWarningMsg OBJECT-TYPE
         SYNTAX     INTEGER {
                  enableAdvisoryWarningMsg(1),       -- Enable AdvisoryWarning
                  disableAdvisoryWarningMsg(2)    -- Disable Advisory Warning
                        }
            MAX-ACCESS  read-write
            STATUS  current
            DESCRIPTION
               "Enable or disable TL1 Advisory Warning Message."
            ::= { adTAeSCUSysAdvisoryConfig 2 }

        adTAeScuSysSavedTextJustification OBJECT-TYPE
         SYNTAX     INTEGER {
                        leftJustification(1),       -- Left Text Justification
                  rightJustification(2),      -- Center Text Justification
                        centerJustification(3)      -- Right Text Justification
                        }
            MAX-ACCESS  read-only
            STATUS  current
            DESCRIPTION
               "Set the text justification for how the Advisory Warning is displayed."
            ::= { adTAeSCUSysAdvisoryConfig 3 }

        adTAeScuSavedAdvisoryTable OBJECT-TYPE
            SYNTAX  SEQUENCE OF AdTAeScuSavedAdvisoryEntry
            MAX-ACCESS  not-accessible
            STATUS  current
            DESCRIPTION
                "Non-Volatile Saved Advisory Warning."
           ::= { adTAeSCUSysAdvisoryConfig 6 }



        adTAeScuSavedAdvisoryEntry OBJECT-TYPE
            SYNTAX  AdTAeScuSavedAdvisoryEntry
            MAX-ACCESS  not-accessible
            STATUS  current
            DESCRIPTION
                "An entry in the adTAeScuSavedAdvisoryTable."
           INDEX   { adTAeScuAdvisoryLineIndex}
           ::= { adTAeScuSavedAdvisoryTable 1 }

        AdTAeScuSavedAdvisoryEntry ::=
            SEQUENCE {
            adTAeScuAdvisoryLineIndex
               Integer32,
                adTAeScuSavedAdvisoryWarning
                     DisplayString
            }

      adTAeScuAdvisoryLineIndex OBJECT-TYPE
            SYNTAX  Integer32 (1..20)
            MAX-ACCESS  read-only
            STATUS  current
            DESCRIPTION
               "An Index to Advisory Warning line."
            ::= { adTAeScuSavedAdvisoryEntry 1 }

        adTAeScuSavedAdvisoryWarning OBJECT-TYPE
                SYNTAX  DisplayString
                MAX-ACCESS  read-only
                STATUS  current
                DESCRIPTION
                "Advisory Warning line."
                ::= { adTAeScuSavedAdvisoryEntry 2 }

        --
      --

        adTAeScuSysSaveOrResetEditAdvisoryWarning OBJECT-TYPE
         SYNTAX     INTEGER {
                        saveAdvisoryWarningChanges(1),       -- Save Edited Advisory Warning
                        resetAdvisoryWarning(2),             -- Replace Edited Advisory Warning with Saved advisory warning.
                        defaultGetValue(999)                 -- Dummy default value returned
                        }
            MAX-ACCESS  read-write
            STATUS  current
            DESCRIPTION
               "Save edit changes made to Advisory Warning.
                    saveAdvisoryWarningChanges - Save the Edited Advisory Warning
                    resetAdvisoryWarning       - Reset Edited Advisory Warning with saved one
                    defaultGetValue            - dummy value returned on a get value"
            ::= { adTAeSCUSysAdvisoryConfig 10 }

       adTAeScuSysEditTextJustification OBJECT-TYPE
         SYNTAX     INTEGER {
                        leftJustification(1),       -- Left Text Justification
                  rightJustification(2),      -- Center Text Justification
                        centerJustification(3)      -- Right Text Justification
                        }
            MAX-ACCESS  read-write
            STATUS  current
            DESCRIPTION
               "Set the text justification for how the Advisory Warning is displayed."
            ::= { adTAeSCUSysAdvisoryConfig 11 }

        adTAeScuEditedAdvisoryTable OBJECT-TYPE
            SYNTAX  SEQUENCE OF AdTAeScuEditedAdvisoryEntry
            MAX-ACCESS  not-accessible
            STATUS  current
            DESCRIPTION
                "Volatile Edited Advisory Warning."
           ::= { adTAeSCUSysAdvisoryConfig 15 }



        adTAeScuEditedAdvisoryEntry OBJECT-TYPE
            SYNTAX  AdTAeScuEditedAdvisoryEntry
            MAX-ACCESS  not-accessible
            STATUS  current
            DESCRIPTION
                "A Volatile Edited Advisory Warning line."
           INDEX   { adTAeScuAdvisoryLineIndex}
           ::= { adTAeScuEditedAdvisoryTable 1 }

        AdTAeScuEditedAdvisoryEntry ::=
            SEQUENCE {
                adTAeScuEditedAdvisoryWarning
                     DisplayString
            }

        adTAeScuEditedAdvisoryWarning OBJECT-TYPE
                SYNTAX  DisplayString
                MAX-ACCESS  read-write
                STATUS  current
                DESCRIPTION
                "Volatile Ram Edited Advisory Warning line."
                ::= { adTAeScuEditedAdvisoryEntry 2 }


              --
      --
      --
      --
      -- Bulk Data Export server Config
      --
      --

      adTAeSCUSysBulkDataExportServerConfig OBJECT IDENTIFIER
                                  ::= { adTAeSCUSecurityAccountMg 21 }


      adTAeSCUSysBulkDataExportHost OBJECT-TYPE
              SYNTAX      IpAddress
              MAX-ACCESS  read-write
              STATUS      current
              DESCRIPTION
                 "The IP address of the server to receive exported bulk data files."
              ::= { adTAeSCUSysBulkDataExportServerConfig 1 }

      adTAeSCUSysBulkDataExportUserName OBJECT-TYPE
              SYNTAX DisplayString
              MAX-ACCESS  read-write
              STATUS      current
              DESCRIPTION
               "The user name for the server to receive exported bulk data files,
                Maximum number of 30 characters for the username."
              ::= { adTAeSCUSysBulkDataExportServerConfig 2 }

      adTAeSCUSysBulkDataExportPassword OBJECT-TYPE
              SYNTAX      DisplayString
              MAX-ACCESS  read-write
              STATUS      current
              DESCRIPTION
               "The password of the server to receive exported bulk data files.
                Maximum number of 30 characters for the password."
              ::= { adTAeSCUSysBulkDataExportServerConfig 3 }

      adTAeSCUSysBulkDataExportProtocol OBJECT-TYPE
              SYNTAX INTEGER {
                       none(0),
                       tftp(1),
                       ftp(3),
                       sftp(4)
                   }
              MAX-ACCESS  read-write
              STATUS      current
              DESCRIPTION
               "The protocol used to transfer the exported bulk data files."
              ::= { adTAeSCUSysBulkDataExportServerConfig 4 }

      adTAeSCUSysBulkDataExportPort OBJECT-TYPE
              SYNTAX  Integer32
              MAX-ACCESS  read-write
              STATUS      current
              DESCRIPTION
               "The port used to transfer the exported bulk data files."
              ::= { adTAeSCUSysBulkDataExportServerConfig 5 }

      adTAeSCUSysBulkDataExportPath OBJECT-TYPE
              SYNTAX      DisplayString
              MAX-ACCESS  read-write
              STATUS      current
              DESCRIPTION
               "The destination path on the server to export bulk data files.
                Maximum number of 200 characters for the path."
              ::= { adTAeSCUSysBulkDataExportServerConfig 6 }

        --
        --
        --
        -- System Log Alarms
        --
        --
        adTAeSCUmgNotificationEvents OBJECT-IDENTITY
                STATUS current
                DESCRIPTION "The SCU/SCM controller events"
                ::= { adTAeSCU 0 }

        adTAeSCUSystemLogFull   NOTIFICATION-TYPE
                OBJECTS       {
                        adTrapInformSeqNum,
                        sysName,
                        adTAeSCUSystemLogPercentFull
                        }
                STATUS          current
                DESCRIPTION
                        "System Log is 90% full.  The System Log has a circular buffer.
                         The System Log will destroy the oldest half of its entries when
                         it is 100% full.  This alarm is used to notify Management
                         stations to download the System Log so entries may not be lost."
        --#TYPE      "Warning - System Log is full."
        --#SUMMARY   "TAeSCU 24101: System Log is %d percent full;"
        --#SUMMARY   "detected at chassis: %s"
        --#ARGUMENTS { 2, 1}
        --#SEVERITY  INFORMATIONAL
        --#GENERIC   6
        --#CATEGORY  "System Log Events"
        --#SOURCE_ID "A"
        --#TIMEINDEX 0
        ::= { adTAeSCUmgNotificationEvents 24101}

        adTAeSCUSystemLogInvalidAuthentAtt   NOTIFICATION-TYPE
                OBJECTS       {
                        adTrapInformSeqNum,
                        sysName
                        }
                STATUS          current
                DESCRIPTION
                        "Invalid user authentication attempts."
        --#TYPE      "Warning - Invalid authentication attempts surpassed."
        --#SUMMARY   "TAeSCU 24103: Invalid authentication attempts surpassed."
        --#SUMMARY   "detected at chassis: %s"
        --#ARGUMENTS { 1}
        --#SEVERITY  INFORMATIONAL
        --#GENERIC   6
        --#CATEGORY  "System Log Events"
        --#SOURCE_ID "A"
        --#TIMEINDEX 0
        ::= { adTAeSCUmgNotificationEvents 24103 }

        adTAeSCUSystemLogFailure   NOTIFICATION-TYPE
                OBJECTS       {
                        adTrapInformSeqNum,
                        sysName,
                        adTAeSCUSystemLogPercentFull,
                        adTAeSCUSystemLogCount,
                        adTAeSCUSystemLogFailureDescription
                        }
                STATUS          current
                DESCRIPTION
                        "System Log fails to record an event."
        --#TYPE      "Warning - System Log fails to record an event."
        --#SUMMARY   "TAeSCU 24105: System Log fails to record an event.;"
        --#SUMMARY   "detected at chassis: %s"
        --#ARGUMENTS { 1}
        --#SEVERITY  INFORMATIONAL
        --#GENERIC   6
        --#CATEGORY  "System Log Events"
        --#SOURCE_ID "A"
        --#TIMEINDEX 0
        ::= { adTAeSCUmgNotificationEvents 24105 }

      adTAeSCUSystemInactiveAccountExpiration   NOTIFICATION-TYPE
                OBJECTS       {
                        adTrapInformSeqNum,
                        sysName,
                        adTAeSCUSecAccountUserID,
                        adTAeSCUSecAccountAge
                        }
                STATUS          current
                DESCRIPTION
                        "Inactive account expiration notification.  Account set to expired."
        --#TYPE      "Warning - Account set to expired."
        --#SUMMARY   "TAeSCU 24163: Account %s Expired.;"
        --#SUMMARY   "detected at chassis: %s"
        --#ARGUMENTS { 2,1}
        --#SEVERITY  INFORMATIONAL
        --#GENERIC   6
        --#CATEGORY  "System Log Events"
        --#SOURCE_ID "A"
        --#TIMEINDEX 0
        ::= { adTAeSCUmgNotificationEvents 24163 }



      --
      --
      --
      -- Start of TACACSPlus Login Config
      --
      --

      adTAeSCUSysTACACSPlusConfig OBJECT IDENTIFIER
                                  ::= { adTAeSCUSecurityAccountMg 30 } -- number from the air

       adTAeScuTACACSPlusTL1Authentication OBJECT-TYPE
         SYNTAX     INTEGER {
                        enableTACACSAuthentication(1),       -- Use TACACS Plus server to login
                        disableTACACSAuthentication(2)        -- Use other methods to login.
                        }
            MAX-ACCESS  read-write
            STATUS  current
            DESCRIPTION
               "Determine how the user Login into TL1.  "
            ::= { adTAeSCUSysTACACSPlusConfig 3 }

        adTAeScuTACACSPlusServerTable OBJECT-TYPE
            SYNTAX  SEQUENCE OF AdTAeScuTACACSPlusServerEntry
            MAX-ACCESS  not-accessible
            STATUS  current
            DESCRIPTION
                "TACACS Plus authentication settings."
           ::= { adTAeSCUSysTACACSPlusConfig 6 }


      --
      --

        adTAeScuTACACSPlusServerEntry OBJECT-TYPE
            SYNTAX  AdTAeScuTACACSPlusServerEntry
            MAX-ACCESS  not-accessible
            STATUS  current
            DESCRIPTION
                "An entry in the TACACS Plus settings table."
           INDEX   { adTAeScuTACACSPlusCfgIndex}
           ::= { adTAeScuTACACSPlusServerTable 1 }

        AdTAeScuTACACSPlusServerEntry ::=
            SEQUENCE {
            adTAeScuTACACSPlusCfgIndex
               Integer32,
            adTAeScuTACACSPlusServerAddress
                DisplayString,
            adTAeScuTACACSPlusServerName
                DisplayString,
            adTAeScuTACACSPlusServerSecret
                DisplayString,
            adTAeScuTACACSPlusServerSequence
                Integer32,
            adTAeScuTACACSPlusServContactTimeOut
                Integer32,
            adTAeScuTACACSPlusServerPort
                Integer32,
            adTAeScuTACACSPlusServerAddressType
                 InetAddressType,
            adTAeScuTACACSPlusServerInetAddress
                 InetAddress
            }

      adTAeScuTACACSPlusCfgIndex OBJECT-TYPE
         SYNTAX     Integer32
            MAX-ACCESS  read-only
            STATUS  current
            DESCRIPTION
               "An Index to TACACS Plus authentication settings"
            ::= { adTAeScuTACACSPlusServerEntry 1 }

        adTAeScuTACACSPlusServerAddress OBJECT-TYPE
                SYNTAX  DisplayString
                MAX-ACCESS  read-write
                STATUS  deprecated
                DESCRIPTION
                  "TACACS Plus Server IP address.
                   deprecated to support IPv6.  Use adTAeScuTACACSPlusServerInetAddress.
                   "
                ::= { adTAeScuTACACSPlusServerEntry 2 }

        adTAeScuTACACSPlusServerName OBJECT-TYPE
                SYNTAX  DisplayString
                MAX-ACCESS  read-write
                STATUS  current
                DESCRIPTION
                  "TACACS Plus Server Name."
                ::= { adTAeScuTACACSPlusServerEntry 3 }

      adTAeScuTACACSPlusServerSecret OBJECT-TYPE
                SYNTAX  DisplayString
                MAX-ACCESS  read-write
                STATUS  current
                DESCRIPTION
                  "The key used in encrypting the packets passed between the
                   TACACS Plus Server and the client. This key must match the one
                   configured on the server."
                ::= { adTAeScuTACACSPlusServerEntry 4 }

      adTAeScuTACACSPlusServerSequence OBJECT-TYPE
         SYNTAX     Integer32 (0..4)
            MAX-ACCESS  read-write
            STATUS  current
            DESCRIPTION
               "TACACS Plus Server sequence."
            ::= { adTAeScuTACACSPlusServerEntry 5 }

      adTAeScuTACACSPlusServContactTimeOut OBJECT-TYPE
         SYNTAX     Integer32 (1000..30000)
            MAX-ACCESS  read-write
            STATUS  current
            DESCRIPTION
               "TACACS Plus Server responses time out in milliseconds."
            ::= { adTAeScuTACACSPlusServerEntry 6 }

      adTAeScuTACACSPlusServerPort OBJECT-TYPE
         SYNTAX     Integer32 (1..65535)
            MAX-ACCESS  read-write
            STATUS  current
            DESCRIPTION
               "TACACS Plus Server port number."
            ::= { adTAeScuTACACSPlusServerEntry 8 }

      adTAeScuTACACSPlusServerAddressType OBJECT-TYPE
        SYNTAX InetAddressType
        MAX-ACCESS read-only
        STATUS     current
        DESCRIPTION
               "The type of adTAeScuTACACSPlusServerInetAddress."
        ::= { adTAeScuTACACSPlusServerEntry 9 }

    adTAeScuTACACSPlusServerInetAddress OBJECT-TYPE
        SYNTAX InetAddress
        MAX-ACCESS read-write
        STATUS     current
        DESCRIPTION
               "TACACS Plus Server IP address (InetAddress).
                Backwards compatibility:  Setting this address to a IPv4
                address will provision old address adTAeScuTACACSPlusServerAddress
                with the new address.
                Setting this address to an IPV6 will leave the old provision
                address adTAeScuTACACSPlusServerAddress as is."
        ::= { adTAeScuTACACSPlusServerEntry 10 }
      --
      --
      --
      -- End of TACACSPlus Login Config
      --
      --

    END

ADTRAN-TAeSCUEXT1-MIB

      DEFINITIONS ::= BEGIN

      -- TITLE:       The ADTRAN enhanced System Controller Unit MIB Extension 1.
      -- PRODUCT:     1181018L1
      -- VERSION:     1.1
      -- DATE:        11/20/2002

      -- This MIB is an extension to the ADTRAN-TAeSCU-MIB MIB.


      -- HISTORY:
          -- 11/20/2002 ap  First edition.
          -- 03/06/2003 ap  Add adTAeSCUAlarmMg, adTAeSCUAlarmEnable and
          --                adGenSlot extention table (adGenSlotSCUext)
          -- 06/17/2003 ap  Add PCU adTAeSCUAlarmEnable description.
          -- 07/10/2003 bkp Added SCM adTAeSCUAlarmEnable description.
          -- 11/12/2003 ap  Add adGenSlotInfoStateSaveNVRAM.
          -- 04/22/2004 wfe Added support for Card Comm Fail Traps.
          -- 08/01/2004 wfe Changed name of Card Comm Fail Traps to be unique
          --                within first 20 chars.  Also, changed severities
          --                to be MAJOR.
          -- 08/01/2004 dlw Removed the range for adTAeSCUAIDIndex - it became irrelevant.
          --                Changed 'adTAeSCUmg 16' to 'adTAeSCUmg 23'.
          -- 08/24/2004 dlw Undo change - adTAeSCUmg back to '16' (that is the correct value).
          -- 02/01/2005 ap  Add adTAeFileTransferMgmt and sub items.
          -- 10/20/2005 ap  Add adTAeSCUAlarmEnable to adTAeSCUAlarmEnable comment
          -- 10/25/2005 ap  Add adAeSCU
          -- 02/02/2006 KMM Changes while adding support for packed sstate msgs. Changes to
          --                adTAeSCUAlarmEnable:
          --                *) Clean-up.
          --                *) Initial support for TA-5000.
          --                *) Added support for many OPTI-6100 alarms which were missing.
          --                *) Added support for new sstate fail alarms.
          --                *) For the OPTI:
          --                   *) Renamed:
          --                         57 DCC Link Down (adOptiMxSCMDCCAlm)
          --                      to
          --                         57 adOptiMxSCMDCCAlm
          --                   *) Renumbered:
          --                         49 adTAeSCUCraftLoginNotfication
          --                      to
          --                         50 adTAeSCUCraftLoginNotfication
          -- 04/03/2006 KMM Added support for provisioning mismatch alarm in adTAeSCUAlarmEnable:
          --                *) Added adTACleiCodeMisMatch to all projects.
          --                *) While here, added:
          --                   *) adTACriticalAudibleRelayActive
          --                   *) adTACriticalVisualRelayActive
          --                   *) adTAMajAudibleRelayActive
          --                   *) adTAMajVisualRelayActive
          --                   *) adTAMinorAudibleRelayActive
          --                   *) adTAMinorVisualRelayActive
          --                   *) adTAAux1RelayActive
          --                   *) adTAAux2RelayActive
          --                   to all projects except for the TA-1100F. Present in
          --                   g_XlateAlarmIndex but missing in adTAeSCUAlarmEnable.
          -- 04/06/2006 DLW Added adTASoftwareVerMisMatchLevel provisioning for the
          --                software version mismatch alarm.
          -- 05/09/2006 JMC Added power shedding bit definitions to commments.
          -- 06/12/2006 KMM Adding support for HFANM.
          --                *) In adTAeSCUenvAlarmsTable DESCRIPTION, removed info on each
          --                   individual alarm since it was not correct, and is different for
          --                   each project.
          --                *) Added to the OPTI section of adTAeSCUAlarmEnable:
          --                   *) adTAFanMPowerAFail
          --                   *) adTAFanMPowerBFail
          -- 06/20/2006 dlw Updated the DESCRIPTION fields:
          --                - Clean up: adTAeSCUenvAlarmDefaultName
          --                - Add description for read-only indexes Pri/Sec Clock ENV alarms:
          --                  adTAeSCUenvAlarmUserName, adTAeSCUenvAlarmInputLevel,
          --                  adTAeSCUAIDIndex, adTAeSCUConditionCode.
          -- 10/06/2006 BKP Added SRM alarms to the adTAeSCUAlarmEnable bitmask description.
          -- 01/08/2007 AP  Added IP Access Control tree (adTaIPServicePortProvMgmt)
          -- 04/12/2007 KMM Added support for adTAEquipmentFaultActive(83) in adTAeSCUAlarmEnable
          --                OPTI section.
          -- 05/02/2007 KMM Due to power shedding having it's own feature enable/disable, deprecated
          --                support for
          --                *) adTAPowerSheddingInputAsserted
          --                *) adTAPowerSheddingActivated
          --                in adTAeSCUAlarmEnable in the TA-3000, PCU, and TA-5000 projects.
          -- 05/02/2007 KGG Added SFTP as enumeration 4 on FileTransferMethod.  It wasn't listed.
          --		        Updated the comments for that oid as well too.
          --				Added LFFS as Remote File Method for OPTI 2.
          -- 06/14/2007 WFE Added the alarm bits to adTAeSCUAlarmEnable for the OSP platform.
          -- 06/28/2007 AP  Add adTaCLITelnetPortNumber, adTaCLIIPAccess, and adTaCLISSHPortNumber
          -- 01/31/2008 BKP Added the adTAeSCUAdminPort section to replace the out dated adGenESCUadminPortMode OID.
          -- 03/27/2008 WFE Added adTAeSCUAlarmEnable bits for the TA5000 HDX alarms (adTASCM5kChassisLinkStatusDown
          --                and adTASCM5kChassisRemoved).
          -- 04/17/2008 DLW Added adTASysCtrlInvalidController, adTASysCtrlInvalidControllerClear traps.
          --                Added adTAeSCUSystemInactiveAccountExpiration, adTASysCtrlSwdnldStarted,
          --                and adTASysCtrlInvalidController bits for OPTI 6100 alarms.
          -- 05/09/2008 DLW Updated the adTAeSCUAlarmEnable DESCRIPTION field for TA5000 with the correct
          --                position for 'adTAeSCUSystemInactiveAccountExpiration' and corrected the ones
          --                that follow.
          -- 08/25/2008 DLW Added adGenSlotProdName to IMPORTS, and added adTASysModuleRestart trap.
          -- 02/13/2009 KMM In adTAeSCUAlarmEnable, OPTI-6100 SCM, deprecated bit 83,
          --                adTAEquipmentFaultActive.
          -- 03/02/2009 KABC Added adTaHTTPIPAccess and adTaHTTPSIPAccess
          -- 03/06/2009 DLW Remove "Index 33 OPTI-6100 'Primary Clock Loss'" and
          --                "Index 34 OPTI-6100 'Secondary Clock Loss'" from
          --                descriptions under adTAeSCUenvAlarmsTableEntry.
          --                Index 36, Env Over Temperature Alarm, has not been fully implemented and
          --                will not be use until further notice.
          --                These three alarms will not appear in get results.
          -- 05/05/09   AP   Convert to SNMPv2
          -- 07/06/2010 JLB Added adGenSlotProdName to traps adTAeSCUCtrpCardInserted and adTAeSCUCtrpCardRemoved
          -- 09/26/2013 RJF "DO NOT MAKE HISTORY COMMENTS HERE!!!! Revision history now in REVISION/DESCRIPTION clauses below"

IMPORTS
            OBJECT-TYPE,
            NOTIFICATION-TYPE,
            MODULE-IDENTITY,
            Integer32
                  FROM SNMPv2-SMI
            DisplayString
                  FROM SNMPv2-TC
            sysName
                  FROM SNMPv2-MIB
         AdPresence
               FROM ADTRAN-TC
            adGenSlotInfoIndex, adGenSlotProdName
                  FROM ADTRAN-GENSLOT-MIB
            adTAeSCUmg,
            adTAeSCUSecAccountUserID,
            adTAeSCUNetworkMgmt,
            adTAeSCUmgNotificationEvents
                  FROM ADTRAN-TAeSCU-MIB
            adTrapInformSeqNum
                  FROM ADTRAN-GENTRAPINFORM-MIB

      ;

      adtranTAeSCUExt1MIB MODULE-IDENTITY
         LAST-UPDATED "201309191018Z"
         ORGANIZATION "Adtran, Inc."
         CONTACT-INFO
           "CND Tech Support
               Postal: ADTRAN, Inc.
                       901 Explorer Blvd.
                       Huntsville, AL  35806
                       Tel: +1 800 726-8663
                       Fax: +1 256 963 6217
                       E-mail: support@adtran.com"
         DESCRIPTION
            "This MIB defines the objects for the adtranTAeScuMib MIB."

         REVISION      "201309191018Z"
         DESCRIPTION
             "Add initial support for AutoUpgrade EOSS (End Of Software Support) Alarms.
              Update several missing adTAeSCUAlarmEnable alarm bit descriptions."

         REVISION "201208141300Z"
         DESCRIPTION "Added cLI(5) to adTAeSCUAdminPortMode."
         REVISION "200705010000Z"
         DESCRIPTION "Converted from SNMPv1 adTAeSCU.mib file."

      ::= { adTAeSCUmg 241 }

      adTAeSCUMuxModuleProv OBJECT IDENTIFIER
            ::= { adTAeSCUmg 16 }

      --
      -- See adGenESCUmoduleAutoProv and adGenESCUmuxAutoProv
      --

      adTAeSCUWriteModuleProvisioning OBJECT IDENTIFIER
            ::= { adTAeSCUMuxModuleProv 7 }

      adTAeSCUProvisioningSource OBJECT-TYPE
            SYNTAX  Integer32 (1..255)
            MAX-ACCESS  read-write
                      STATUS  current
                      DESCRIPTION
                          "This is the source slot number.  This is the slot
                           that will be copied to the destination slots.  A
                           value of zero means no slot is set.
                           adGenESCUmoduleAutoProv and adGenESCUmuxAutoProv must
                           be enabled."
                      ::= { adTAeSCUWriteModuleProvisioning 1 }



      adTAeSCUProvDestinationSlots OBJECT-TYPE
            SYNTAX  DisplayString (SIZE(1..255))
                  MAX-ACCESS  read-write
                  STATUS  current
                  DESCRIPTION
                      "Destination slots to copy to.  A valid destination slot
                       must be compatible with the source slot.  Copy provisioning
                       will be ignored if the slots are not compatible.  The
                       following format must be used.
                       **************************************************************
                       1) A slot number from 1 to 255.  Slot number greater than 0 and
                            less than 255.
                       2) A range or slot numbers (1..255)-(1..255) Example: 1-5.
                       3) A series of slot numbers separated by ',' (a comma).
                       4) A series of slot numbers separated by ',' and or range of
                            slot numbers separated by a ','.
                       5) Each slot number or range of slot numbers must be separated by
                            a ',' (comma).
                       Example 1:  '1'               Copy provisioning to slots 1.
                       Example 2:  '1,5'            Copy provisioning to slots 1 and 5.
                       Example 3:  '4-9'            Copy provisioning to slots 4 through 9.
                       Example 4:  '3,5-8,9'      Copy provisioning to slots 3,9, and 5 to 8.
                       Error Example:  '8-4'       This is an invalid range.
                       Error:  Copy from an invalid or empty slot.
                       Error:  Copy to an Empty slot.  A slot must be occupied with a
                                    compatible line card.
                       Error:  Card is incompatible."

                  ::= { adTAeSCUWriteModuleProvisioning 3 }


      adTAeSCUWriteProvInitiate OBJECT-TYPE
            SYNTAX  INTEGER {
                                initiate(1)
                            }
              MAX-ACCESS  read-write
              STATUS  current
              DESCRIPTION
                  "Command to initiate write copy provisioning."
              ::= { adTAeSCUWriteModuleProvisioning 4 }



      adTAeSCUWriteProvStatusTable OBJECT-TYPE
            SYNTAX  SEQUENCE OF AdTAeSCUWriteProvStatusTableEntry
            MAX-ACCESS  not-accessible
            STATUS  current
            DESCRIPTION
                  "Copy provision status table"
          ::= { adTAeSCUWriteModuleProvisioning 5 }


      adTAeSCUWriteProvStatusTableEntry OBJECT-TYPE
            SYNTAX  AdTAeSCUWriteProvStatusTableEntry
            MAX-ACCESS  not-accessible
            STATUS  current
            DESCRIPTION
                  "An entry in the Copy provision status table table."
          INDEX   { adGenSlotInfoIndex }
          ::= { adTAeSCUWriteProvStatusTable 1 }

      AdTAeSCUWriteProvStatusTableEntry ::=
            SEQUENCE {
                  adTAeSCUWriteProvInitiateStatus
                      DisplayString
            }

            adTAeSCUWriteProvInitiateStatus OBJECT-TYPE
            SYNTAX DisplayString (SIZE(0..255))
               MAX-ACCESS  read-only
                  STATUS  current
                  DESCRIPTION
                     "Status of adTAeSCUWriteProvInitiate command.
                      Busy(slot #,command_time),Details...
                      Idle
                      Complete; SUCCESS..... (Details)
                      Complete; ERROR: ...... (Details)
                      "
                  ::= { adTAeSCUWriteProvStatusTableEntry 1 }


     -- *******************************************************************************************************

     -- ********************************************************************************************************

     --


     adTAeSCUUserDefinableAlarm OBJECT IDENTIFIER
          ::= { adTAeSCUmg 18 }

     adTAeSCUAccModuleRemovedLevel OBJECT-TYPE
          SYNTAX  INTEGER {
                              minor(4),
                              major(5),
                              critical(6)
                          }
                  MAX-ACCESS  read-write
                  STATUS  current
                  DESCRIPTION
                     "Access Module Removed Alarm Level."
                  ::= { adTAeSCUUserDefinableAlarm 3 }

     adTAeSCUCraftLoginAlarmLevel OBJECT-TYPE
          SYNTAX INTEGER {
                               info(2),
                               alert(3),
                               minor(4),
                               major(5),
                               critical(6)
                          }
                  MAX-ACCESS  read-write
                  STATUS  current
                  DESCRIPTION
                     "Alarm Level for the adTAeSCUCraftLoginNotfication."
                  ::= { adTAeSCUUserDefinableAlarm 4 }

     adTAeSCUMUXRemovedLevel OBJECT-TYPE
          SYNTAX  INTEGER {
                               minor(4),
                               major(5),
                               critical(6)
                          }
                  MAX-ACCESS  read-write
                  STATUS  current
                  DESCRIPTION
                     "MUX Removed Alarm Level."
                  ::= { adTAeSCUUserDefinableAlarm 5 }

     adTAeSCUTrapAlarmLevel OBJECT-TYPE
          SYNTAX INTEGER {
                               info(2),
                               alert(3),
                               minor(4),
                               major(5),
                               critical(6)
                          }
                  MAX-ACCESS  read-only
                  STATUS  current
                  DESCRIPTION
                     "Alarm Level of a trap.  This value is invalid if read.
                      This will be used as a varbind in a trap to indicate
                      its alarm level."
                  ::= { adTAeSCUUserDefinableAlarm 6 }

     adTAeSCUenvAlarmsTable OBJECT-TYPE
          SYNTAX  SEQUENCE OF AdTAeSCUenvAlarmsTableEntry
          MAX-ACCESS  not-accessible
          STATUS  current
          DESCRIPTION
               "The enhanced System Controller Unit Environmental alarm table"
        ::= { adTAeSCUUserDefinableAlarm 7 }


     adTAeSCUenvAlarmsTableEntry OBJECT-TYPE
          SYNTAX  AdTAeSCUenvAlarmsTableEntry
          MAX-ACCESS  not-accessible
          STATUS  current
          DESCRIPTION
               "An entry in the Controller Unit Environmental alarm table."
        INDEX   { adTAeSCUAalarmIndex }
        ::= { adTAeSCUenvAlarmsTable 1 }

        AdTAeSCUenvAlarmsTableEntry ::=
          SEQUENCE {
               adTAeSCUAalarmIndex
                  Integer32,
               adTAeSCUenvAlarmDefaultName
                  DisplayString,
               adTAeSCUenvAlarmUserName
                  DisplayString,
               adTAeSCUenvAlarmInputLevel
                  INTEGER,
               adTAeSCUAIDIndex
                  Integer32,
               adTAeSCUConditionCode
                  DisplayString
          }
          adTAeSCUAalarmIndex OBJECT-TYPE
                SYNTAX Integer32
                MAX-ACCESS  read-only
                  STATUS  current
                  DESCRIPTION
                     "Alarm Index."
                  ::= { adTAeSCUenvAlarmsTableEntry 1 }
          adTAeSCUenvAlarmDefaultName OBJECT-TYPE
               SYNTAX DisplayString
               MAX-ACCESS  read-only
                  STATUS  current
                  DESCRIPTION
                     "Default alarm name."
                  ::= { adTAeSCUenvAlarmsTableEntry 2 }
          adTAeSCUenvAlarmUserName OBJECT-TYPE
               SYNTAX DisplayString (SIZE(1..16))
               MAX-ACCESS  read-write
                  STATUS  current
                  DESCRIPTION
                     " A user specified name.
                       adTAeSCUenvAlarmDefaultName or a user provided name.
                       Index  4 '-48V Bus A Input' read-only.
                       Index  5 '-48V Bus B Input' is read-only.
                       Index  4 and 5 will return an error."
                  ::= { adTAeSCUenvAlarmsTableEntry 3 }

          adTAeSCUenvAlarmInputLevel OBJECT-TYPE
               SYNTAX INTEGER {
                                 info(2),
                                 alert(3),
                                 minor(4),
                                 major(5),
                                 critical(6)
                              }
               MAX-ACCESS  read-write
                  STATUS  current
                  DESCRIPTION
                     "Alarm level."
                  ::= { adTAeSCUenvAlarmsTableEntry 4 }
          adTAeSCUAIDIndex OBJECT-TYPE
               SYNTAX Integer32
               MAX-ACCESS  read-write
                  STATUS  current
                  DESCRIPTION
                     "AID Index."
                  ::= { adTAeSCUenvAlarmsTableEntry 5 }
          adTAeSCUConditionCode OBJECT-TYPE
               SYNTAX DisplayString (SIZE(0..11))
               MAX-ACCESS  read-write
                  STATUS  current
                  DESCRIPTION
                     "Condition code."
                  ::= { adTAeSCUenvAlarmsTableEntry 6 }



     ---
     ---
     ---
-- *******************************************************************************************************

-- ********************************************************************************************************

-- Enable or disalble any trap in the eSCU


          adTAeSCUAlarmMg OBJECT IDENTIFIER
                        ::= { adTAeSCUmg 20 }


           adTAeSCUAlarmEnable OBJECT-TYPE
                  SYNTAX  OCTET STRING
                  MAX-ACCESS  read-write
                  STATUS  current
                  DESCRIPTION
                       "A bit encoded string representing the enabled/disabled
                       status of all alarms for the eSCU.  The bits are defined
                       in network order, that is, most significant bit first.
                       For all entries:
                          0 = DISABLE
                          1 = ENABLE
                       The various bit positions are:

                       *****************************************************
                       TA-3000 SCU:     (adTAeSCUAlarmEnable)
                       *****************************************************
                         1 adTAeSCUSystemLogFull
                         2 adTAeSCUSystemLogInvalidAuthentAtt
                         3 adTAeSCUSystemLogFailure
                         4 adTAeSCUCtrpBusApowerAlm and adTAeSCUCtrpBusApwrAlmClear
                         5 adTAeSCUCtrpBusBpowerAlm and adTAeSCUCtrpBusBpwrAlmClear
                         6 adTAeSCUCtrpCardInserted and adTAeSCUCtrpCardRemoved
                         7 adTAeSCUCtrpExt1Alm and adTAeSCUCtrpExt1AlmClear
                         8 adTAeSCUCtrpExt2Alm and adTAeSCUCtrpExt2AlmClear
                         9 adTAeSCUCtrpRmtAlm and adTAeSCUCtrpRmtAlmClear
                        10 adTAeSCUCtrpBlownFuse
                        11 DIDauthenticationFailure
                        12 DIDlinkDown
                        13 DIDlinkUp
                        14 No SNMP support - Device comm failure Active and Device comm failure Clear
                        15 Service State alarms
                        16 adTAeSCUAutoUpgradeConfigChanged
                        17 adTAeSCUAutoUpgradeInvalidConfigFile
                        18 adTAeSCUAutoUpgradeModuleUpgradeStarted
                        19 adTAeSCUAutoUpgradeModuleUpgradeCompleted
                        20 adTAeSCUAutoUpgradeModuleUpgradeFailed
                        21 adTAeSCUAutoUpgradeUnknownModule
                        22 adTAPowerSheddingInputAsserted                        (deprecated)
                        23 adTAPowerSheddingActivated                            (deprecated)
                        24 adTAeSCUCardCommFail and adTAeSCUCardCommRestored
                        25 adTAeSCUCraftLoginNotfication
                        26 adTASetSingleServiceStateMsgFail
                        27 adTAGetSingleServiceStateMsgFail
                        28 adTASetAllServiceStateMsgFail
                        29 adTAGetAllServiceStateMsgFail
                        30 adTACriticalAudibleRelayActive
                        31 adTACriticalVisualRelayActive
                        32 adTAMajAudibleRelayActive
                        33 adTAMajVisualRelayActive
                        34 adTAMinorAudibleRelayActive
                        35 adTAMinorVisualRelayActive
                        36 adTAAux1RelayActive
                        37 adTAAux2RelayActive
                        38 adTACleiCodeMisMatch
                        39 adTAAUSoftwareVerErr

                       *****************************************************
                       OPTI-6100 SCM:     (adTAeSCUAlarmEnable)
                       *****************************************************
                         1 adTAeSCUSystemLogFull
                         2 adTAeSCUSystemLogInvalidAuthentAtt
                         3 adTAeSCUSystemLogFailure
                         4 adTAeSCUCtrpBusApowerAlm and adTAeSCUCtrpBusApwrAlmClear
                         5 adTAeSCUCtrpBusBpowerAlm and adTAeSCUCtrpBusBpwrAlmClear
                         6 adTAeSCUCtrpCardInserted and adTAeSCUCtrpCardRemoved
                         7 adTAeSCUCtrpExt1Alm and adTAeSCUCtrpExt1AlmClear
                         8 adTAeSCUCtrpExt2Alm and adTAeSCUCtrpExt2AlmClear
                         9 adOptiSCMCtrpExt3Alm and adOptiMxSCMCtrpExt3AlmClear
                        10 adTAeSCUCtrpBlownFuse
                        11 DIDauthenticationFailure
                        12 DIDlinkDown
                        13 DIDlinkUp
                        14 No SNMP support - Device comm failure Active and Device comm failure Clear
                        15 Service State alarms
                        16 adTAeSCUAutoUpgradeConfigChanged
                        17 adTAeSCUAutoUpgradeInvalidConfigFile
                        18 adTAeSCUAutoUpgradeModuleUpgradeStarted
                        19 adTAeSCUAutoUpgradeModuleUpgradeCompleted
                        20 adTAeSCUAutoUpgradeModuleUpgradeFailed
                        21 adTAeSCUAutoUpgradeUnknownModule
                        22 adOptiSCMSingleFanFailureAlm and adOptiSCMSingleFanFailureAlmClear
                        23 adOptiMxSCMMultiFanFailureAlm and adOptiMxSCMMultiFanFailureAlmClear
                        24 adTAeSCUCardCommFail and adTAeSCUCardCommRestored
                        25 Enhanced Fan Auxiliary Input 1 Alarm
                        26 Enhanced Fan Auxiliary Input 2 Alarm
                        27 Enhanced Fan Auxiliary Input 3 Alarm
                        28 Enhanced Fan Auxiliary Input 4 Alarm
                        29 Enhanced Fan Auxiliary Input 5 Alarm
                        30 Enhanced Fan Auxiliary Input 6 Alarm
                        31 Enhanced Fan Auxiliary Input 7 Alarm
                        32 Enhanced Fan Auxiliary Input 8 Alarm
                        33 Enhanced Fan Auxiliary Input 9 Alarm
                        34 Enhanced Fan Auxiliary Input 10 Alarm
                        35 Enhanced Fan Auxiliary Input 11 Alarm
                        36 Enhanced Fan Auxiliary Input 12 Alarm
                        37 Enhanced Fan Auxiliary Input 13 Alarm
                        38 Enhanced Fan Auxiliary Input 14 Alarm
                        39 Enhanced Fan Auxiliary Input 15 Alarm
                        40 Enhanced Fan Auxiliary Input 16 Alarm
                        41 Auxiliary 1 Low Battery Alarm
                        42 Auxiliary 1 No Battery Alarm
                        43 Auxiliary 1 AC Failure Alarm
                        44 Auxiliary 2 Low Battery Alarm
                        45 Auxiliary 2 No Battery Alarm
                        46 Auxiliary 2 AC Failure Alarm
                        47 Auxiliary 3 Low Battery Alarm
                        48 Auxiliary 3 No Battery Alarm
                        49 Auxiliary 3 AC Failure Alarm
                        50 adTAeSCUCraftLoginNotfication
                        51 Fan Filter Alarm
                        52 Env Over Temperature Alarm
                        53 Primary Clock Failure Alarm                                     (deprecated)
                        54 Secondary Clock Failure Alarm                                   (deprecated)
                        55 Software Download Complete Alarm
                        56 Software Download Failure Alarm
                        57 adOptiMxSCMDCCAlm
                        58 adTASetSingleServiceStateMsgFail
                        59 adTAGetSingleServiceStateMsgFail
                        60 adTASetAllServiceStateMsgFail
                        61 adTAGetAllServiceStateMsgFail
                        62 adTACriticalAudibleRelayActive
                        63 adTACriticalVisualRelayActive
                        64 adTAMajAudibleRelayActive
                        65 adTAMajVisualRelayActive
                        66 adTAMinorAudibleRelayActive
                        67 adTAMinorVisualRelayActive
                        68 adTAAux1RelayActive
                        69 adTAAux2RelayActive
                        70 adTACleiCodeMisMatch
                        71 adTAAUSoftwareVerErr
                        72 adTAFanMPowerAFail
                        73 adTAFanMPowerBFail
                        74 adTASrmPrimaryRlsIncompleteActive
                        75 adTASrmSecondaryRlsIncompleteActive
                        76 adTASrmNewPrimaryRelease
                        77 adTASrmReleaseUpgradeStarted
                        78 adTASrmReleaseUpgradeCompleted
                        79 adTASrmReleaseUpgradeFailed
                        80 adTASrmPrimaryBackupStarted
                        81 adTASrmPrimaryBackupCompleted
                        82 adTASrmPrimaryBackupFailed
                        83 adTAEquipmentFaultActive                              (deprecated)
                        84 adTAeSCUSystemInactiveAccountExpiration
                        85 adTASysCtrlSwdnldStarted
                        86 adTASysCtrlInvalidController

                        *****************************************************
                        TA-3000 PCU:     (adTAeSCUAlarmEnable)
                        *****************************************************
                         1 adTAeSCUSystemLogFull
                         2 adTAeSCUSystemLogInvalidAuthentAtt
                         3 adTAeSCUSystemLogFailure
                         4 adTA3kPCUBusApowerAlm
                         5 adTAeSCUCtrpBusApowerAlm
                         6 adTAeSCUCtrpCardRemoved
                         7 adTAeSCUCtrpExt1Alm
                         8 adTAeSCUCtrpExt2Alm
                         9 adTAeSCUCtrpRmtAlm
                        10 adTAeSCUCtrpBlownFuse
                        11 DIDauthenticationFailure
                        12 DIDlinkDown
                        13 DIDLinkUp
                        14 Device comm
                        15 Service State Alarm
                        16 adTAeSCUAutoUpgradeConfigChanged
                        17 adTAeSCUAutoUpgradeInvalidConfigFile
                        18 adTAeSCUAutoUpgradeModuleUpgradeStarted
                        19 adTAeSCUAutoUpgradeModuleUpgradeCompleted
                        20 adTAeSCUAutoUpgradeModuleUpgradeFailed
                        21 adTAeSCUAutoUpgradeUnknownModule
                        22 Shelf 2 adTA3kPCUBusApowerAlm
                        23 Shelf 2 adTA3kPCUBusBpowerAlm
                        24 Shelf 2 adTA3kPCURmtAlm
                        25 Shelf 2 adTA3kPCUExt1Alm
                        26 Shelf 2 adTA3kPCUExt2Alm
                        27 Shelf 3 adTA3kPCUBusApowerAlm
                        28 Shelf 3 adTA3kPCUBusBpowerAlm
                        29 Shelf 3 adTA3kPCURmtAlm
                        30 Shelf 3 adTA3kPCUExt1Alm
                        31 Shelf 3 adTA3kPCUExt2Alm
                        32 Shelf 4 adTA3kPCUBusApowerAlm
                        33 Shelf 4 adTA3kPCUBusBpowerAlm
                        34 Shelf 4 adTA3kPCURmtAlm
                        35 Shelf 4 adTA3kPCUExt1Alm
                        36 Shelf 4 adTA3kPCUExt2Alm
                        37 Shelf 5 adTA3kPCUBusApowerAlm
                        38 Shelf 5 adTA3kPCUBusBpowerAlm
                        39 Shelf 5 adTA3kPCURmtAlm
                        40 Shelf 5 adTA3kPCUExt1Alm
                        41 Shelf 5 adTA3kPCUExt2Alm
                        42 Shelf 6 adTA3kPCUBusApowerAlm
                        43 Shelf 6 adTA3kPCUBusBpowerAlm
                        44 Shelf 6 adTA3kPCURmtAlm
                        45 Shelf 6 adTA3kPCUExt1Alm
                        46 Shelf 6 adTA3kPCUExt2Alm
                        47 Shelf 7 adTA3kPCUBusApowerAlm
                        48 Shelf 7 adTA3kPCUBusBpowerAlm
                        49 Shelf 7 adTA3kPCURmtAlm
                        50 Shelf 7 adTA3kPCUExt1Alm
                        51 Shelf 7 adTA3kPCUExt2Alm
                        52 Shelf 8 adTA3kPCUBusApowerAlm
                        53 Shelf 8 adTA3kPCUBusBpowerAlm
                        54 Shelf 8 adTA3kPCURmtAlm
                        55 Shelf 8 adTA3kPCUExt1Alm
                        56 Shelf 8 adTA3kPCUExt2Alm
                        57 adTAPCUChassisDown
                        58 adTAPCUChassisRemoved
                        59 adTAEcuRemoved
                        60 adTAAccessoryModuleRemoved and adTAAccessoryModuleInserted
                        61 adTAeSCUCardCommFail and adTAeSCUCardCommRestored
                        62 adTAeSCUCraftLoginNotfication
                        63 adTASetSingleServiceStateMsgFail
                        64 adTAGetSingleServiceStateMsgFail
                        65 adTASetAllServiceStateMsgFail
                        66 adTAGetAllServiceStateMsgFail
                        67 adTACriticalAudibleRelayActive
                        68 adTACriticalVisualRelayActive
                        69 adTAMajAudibleRelayActive
                        70 adTAMajVisualRelayActive
                        71 adTAMinorAudibleRelayActive
                        72 adTAMinorVisualRelayActive
                        73 adTAAux1RelayActive
                        74 adTAAux2RelayActive
                        75 adTACleiCodeMisMatch
                        76 adTAAUSoftwareVerErr
                        77 adTAPowerSheddingInputAsserted                        (deprecated)
                        78 adTAPowerSheddingActivated                            (deprecated)

                        *****************************************************
                        TA-1100F (OSP) SCM:     (adTAeSCUAlarmEnable)
                        *****************************************************
                        1  adTAeSCUSystemLogFull
                        2  adTAeSCUSystemLogInvalidAuthentAtt
                        3  adTAeSCUSystemLogFailure
                        4  Empty/None
                        5  Empty/None
                        6  adTADeviceInserted_Removed
                        7  Empty/None
                        8  Empty/None
                        9  Empty/None
                        10 Empty/None
                        11 DIDauthenticationFailure
                        12 Empty/None
                        13 Empty/None
                        14 Empty/None
                        15 ServiceStateAlarm
                        16 adTAeSCUAutoUpgradeConfigChanged
                        17 adTAeSCUAutoUpgradeInvalidConfigFile
                        18 adTAeSCUAutoUpgradeModuleUpgradeStarted
                        19 adTAeSCUAutoUpgradeModuleUpgradeCompleted
                        20 adTAeSCUAutoUpgradeModuleUpgradeFailed
                        21 adTAeSCUAutoUpgradeUnknownModule
                        22 Empty/None
                        23 Empty/None
                        24 adTADeviceMgmtFail / adTADeviceMgmtRestored
                        25 adTAeSCUCraftLoginNotfication
                        26 adTASetSingleServiceStateMsgFail      (Deprecated)
                        27 adTAGetSingleServiceStateMsgFail      (Deprecated)
                        28 adTASetAllServiceStateMsgFail
                        29 adTAGetAllServiceStateMsgFail
                        30 adTACleiCodeMisMatch
                        31 adTAAUSoftwareVerErr
                        32 Auxiliary Input 1 Alarm
                        33 Auxiliary Input 2 Alarm
                        34 Auxiliary Input 3 Alarm
                        35 Auxiliary Input 4 Alarm
                        36 Auxiliary Input 5 Alarm
                        37 System Alarm Severity Alarm
                        38 System Inactive Account Alarm
                        39 adTACriticalAudibleRelayActive
                        40 adTAMajAudibleRelayActive
                        41 adTAMinorAudibleRelayActive
                        42 adTaSysCtrlRebootException   (duplicated by adTASysModuleRestart)
                        43 adTAModuleProvisionChange
                        44 adTAeScmFlashDataFileError
                        68 adTACriticalVisualRelayActive
                        70 adTAMajVisualRelayActive
                        72 adTAMinorVisualRelayActive
                        73 adTaSysCtrlAutoUpgradeEOSSWarning Active/Clear
                        74 adTaSysCtrlAutoUpgradeEOSSDenied Active/Clear

                        *****************************************************
                        TA-5000 SCM:     (adTAeSCUAlarmEnable)
                        *****************************************************
                         1 adTAeSCUSystemLogFull
                         2 adTAeSCUSystemLogInvalidAuthentAtt
                         3 adTAeSCUSystemLogFailure
                         4 adTAeSCUCtrpBusApowerAlm and adTAeSCUCtrpBusApwrAlmClear
                         5 adTAeSCUCtrpBusBpowerAlm and adTAeSCUCtrpBusBpwrAlmClear
                         6 adTAeSCUCtrpCardInserted and adTAeSCUCtrpCardRemoved
                         7 adTAeSCUCtrpExt1Alm and adTAeSCUCtrpExt1AlmClear
                         8 adTAeSCUCtrpExt2Alm and adTAeSCUCtrpExt2AlmClear
                         9 adTAeSCUCtrpRmtAlm and adTAeSCUCtrpRmtAlmClear
                        10 adTAeSCUCtrpBlownFuse
                        11 DIDauthenticationFailure
                        12 DIDlinkDown
                        13 DIDlinkUp
                        14 No SNMP support - Device comm failure Active and Device comm failure Clear
                        15 Service State alarms
                        16 adTAeSCUAutoUpgradeConfigChanged
                        17 adTAeSCUAutoUpgradeInvalidConfigFile
                        18 adTAeSCUAutoUpgradeModuleUpgradeStarted
                        19 adTAeSCUAutoUpgradeModuleUpgradeCompleted
                        20 adTAeSCUAutoUpgradeModuleUpgradeFailed
                        21 adTAeSCUAutoUpgradeUnknownModule
                        22 adTAPowerSheddingInputAsserted                        (deprecated)
                        23 adTAPowerSheddingActivated                            (deprecated)
                        24 adTAeSCUCardCommFail and adTAeSCUCardCommRestored
                        25 Fan Auxiliary Input 1 Alarm
                        26 Fan Auxiliary Input 2 Alarm
                        27 Fan Auxiliary Input 3 Alarm
                        28 Fan Auxiliary Input 4 Alarm
                        29 Fan Auxiliary Input 5 Alarm
                        30 Fan Auxiliary Input 6 Alarm
                        31 Fan Auxiliary Input 7 Alarm
                        32 Fan Auxiliary Input 8 Alarm
                        33 Fan Auxiliary Input 9 Alarm
                        34 Fan Auxiliary Input 10 Alarm
                        35 Fan Auxiliary Input 11 Alarm
                        36 Fan Auxiliary Input 12 Alarm
                        37 Fan Auxiliary Input 13 Alarm
                        38 Fan Auxiliary Input 14 Alarm
                        39 Fan Auxiliary Input 15 Alarm
                        40 Fan Auxiliary Input 16 Alarm
                        41 adTAeSCUCraftLoginNotfication
                        42 adTASetSingleServiceStateMsgFail      (Deprecated)
                        43 adTAGetSingleServiceStateMsgFail      (Deprecated)
                        44 adTASetAllServiceStateMsgFail
                        45 adTAGetAllServiceStateMsgFail
                        46 adTACriticalAudibleRelayActive
                        47 adTACriticalVisualRelayActive
                        48 adTAMajAudibleRelayActive
                        49 adTAMajVisualRelayActive
                        50 adTAMinorAudibleRelayActive
                        51 adTAMinorVisualRelayActive
                        52 Empty/None
                        53 Empty/None
                        54 adTACleiCodeMisMatch
                        55 adTAAUSoftwareVerErr
                        56 adTAeSCUSystemInactiveAccountExpiration
                        57 adTASCM5kChassisLinkStatusDown
                        58 adTASCM5kChassisRemoved
                        59 adTASysModuleRestart
                        60 adTaSysCtrlRebootException
                        61 adTAeSysSystemDataError
                        62 coldStart
                        63 warmStart
                        64 adGenProcessesHeapFreeThreshCrossed
                        65 adTASysCtrlCardNotSensed
                        66 adTASysCtrlCardNotReady
                        67 adTaSysCtrlAutoUpgradeEOSSWarning Active/Clear
                        68 adTaSysCtrlAutoUpgradeEOSSDenied Active/Clear"

                      ::= { adTAeSCUAlarmMg 1 }

           adTAeSCUResendAllSnmpTraps OBJECT-TYPE
                  SYNTAX  INTEGER {
                               resendAllSnmpUnconfirmedTraps(1),-- Resend all snmp open traps
                               getResponse(2),
                               resendAllActiveAlarms(3) -- Resend all active alarms on the system
                          }
                  MAX-ACCESS  read-write
                  STATUS  current
                  DESCRIPTION
                       "resendAllSnmpUnconfirmedTrapsv(1) - Resend all unconfirmed SNMP traps in SNMP trap Chache.
                                                            See adTrapInformCache (1.3.6.1.4.1.664.5.16.2.1.1.7)
                        getResponse(2)                    - A generic value received on a get.  Means nothing.
                        resendAllActiveAlarms             - Resend all active alarms in the Chassis."

                      ::= { adTAeSCUAlarmMg 5 }

-- *******************************************************************************************************
-- Provide an extension to the adGetSlot table.
     adGenSlotExtension         OBJECT IDENTIFIER ::= { adTAeSCUmg 22 }

     adGenSlotInfoStateSaveNVRAM OBJECT-TYPE
          SYNTAX  INTEGER {
                               enable(1),
                               disable(2)
                          }
                  MAX-ACCESS  read-write
                  STATUS  current
                  DESCRIPTION
                     "Enable or disable saving the adGenSlotInfoState in NV RAM."
                  ::= { adGenSlotExtension 1 }


    adGenSlotInfoScuExtTable OBJECT-TYPE
         SYNTAX  SEQUENCE OF AdGenSlotInfoScuExtEntry
         MAX-ACCESS  not-accessible
         STATUS  current
         DESCRIPTION
               "Table of slots available for boards."
         ::= { adGenSlotExtension 3 }

      adGenSlotInfoScuExtEntry OBJECT-TYPE
         SYNTAX  AdGenSlotInfoScuExtEntry
         MAX-ACCESS  not-accessible
         STATUS  current
         DESCRIPTION
               ""
         INDEX   { adGenSlotInfoIndex }
         ::= { adGenSlotInfoScuExtTable 1 }

      AdGenSlotInfoScuExtEntry ::=
         SEQUENCE {
            adGenSlotInfoStateExtension
               AdPresence
         }

      adGenSlotInfoStateExtension OBJECT-TYPE
         SYNTAX  AdPresence
         MAX-ACCESS  read-write
         STATUS  current
         DESCRIPTION
               "Allows forcing slot with adGenSlotInfoState of virtual state to empty.
                adGenSlotInfoStateExtension will only accept a value Empty(2).  If a
               card is present but defective adGenSlotInfoState will remain Virtual."
         ::= { adGenSlotInfoScuExtEntry 1 }
-- ********************************************************************************************************
-- File Transfer Selection.
       adTAeFileTransferMgmt      OBJECT IDENTIFIER ::= { adTAeSCUmg 24 }
       adTAeSCUFileTransferMethod OBJECT-TYPE
               SYNTAX INTEGER {
                                 ftmTFTP(1),
                                 ftmFTOT(2),
                                 ftmFTP(3),
                         ftmSFTP(4),
                         ftmLFFS(5)
                              }
               MAX-ACCESS  read-write
               STATUS  current
               DESCRIPTION
                  "File transfer method to use to transfer files to and from the controller.
                   ftmTFTP(1) indicates TFTP transfer protocol.
                   ftmFTOT(2) indicates FTOT transfer protocol.
                   ftmFTP(3)  indicates FTP  transfer protocol.
                   ftmSFTP(4) indicates SFTP transfer protocol.
                   ftmLFFS(5) indicates Local Flash File System for OPTI-6100 SCM2 only."
               ::= { adTAeFileTransferMgmt 5 }


            adTAeSCUFileTransferUserID OBJECT-TYPE
               SYNTAX DisplayString (SIZE(0..40))
               MAX-ACCESS  read-write
                  STATUS  current
                  DESCRIPTION
                     "Specifies the contents of the User ID field for
                   file transfer protocols that require it, such as
                   FTP."
                  ::= { adTAeFileTransferMgmt 10 }

           adTAeSCUFileTransferPassword OBJECT-TYPE
               SYNTAX DisplayString (SIZE(0..40))
               MAX-ACCESS  read-write
                  STATUS  current
                  DESCRIPTION
                     "Specifies the contents of the password field for
                   file transfer protocols that require it, such as
                   FTP."
                  ::= { adTAeFileTransferMgmt 11 }

           adTAeSCUFileTransferFirmwarePath OBJECT-TYPE
           SYNTAX DisplayString (SIZE(0..40))
               MAX-ACCESS  read-write
                  STATUS  current
                  DESCRIPTION
                     "Specifies an optional path preceding the firmware
                   filename for file transfer protocols that may need
                   it, such as FTOT and FTP."
                  ::= { adTAeFileTransferMgmt 12 }

           adTAeSCUFileTransferReceiveStatus OBJECT-TYPE
           SYNTAX DisplayString (SIZE(0..40))
               MAX-ACCESS  read-only
                  STATUS  current
                  DESCRIPTION
                     "Status of the most recent remote file
                   get/read/receive operation."
                  ::= { adTAeFileTransferMgmt 13 }

           adTAeSCUFileTransferSendStatus  OBJECT-TYPE
           SYNTAX DisplayString (SIZE(0..40))
               MAX-ACCESS  read-only
                  STATUS  current
                  DESCRIPTION
                     "Status of the most recent remote file
                   put/write/send operation."
                  ::= { adTAeFileTransferMgmt 14 }


-- ********************************************************************************************************
-- ********************************************************************************************************
-- IP Access Control.
       --adTAeIPNetworkMgmt      OBJECT IDENTIFIER ::= { adTAeSCUNetworkMgmt 20 }

       adTaIPServicePortProvMgmt      OBJECT IDENTIFIER ::= { adTAeSCUNetworkMgmt 20 }

       adTaIPAccessPortMgmt      OBJECT IDENTIFIER ::= { adTAeSCUNetworkMgmt 22 }

            adTaSnmpIPAccess OBJECT-TYPE
               SYNTAX INTEGER {
                                 enable(1),
                                 disable(2),
                                 sSHTunnelOnly(3)
                              }
               MAX-ACCESS  read-write
               STATUS  current
               DESCRIPTION
                  "Set SNMP IP port Access mode.
                   Enable(1)        - Enable SNMP IP port access.
                   Disable(2)       - Disable SNMP IP port access.
                   SSHTunnelOnly(3) - Enabled SNMP Server IP port using a SSH tunnels."
               ::= { adTaIPAccessPortMgmt 5 }


            adTaTL1IPAccess OBJECT-TYPE
               SYNTAX INTEGER {
                                 enable(1),
                                 disable(2),
                                 sSHTunnelOnly(3)
                              }
               MAX-ACCESS  read-write
                  STATUS  current
                  DESCRIPTION
                   "Set TL1 IP port Access mode.
                   Enable(1)        - Enable TL1 IP port access.
                   Disable(2)       - Disable TL1 IP port access.
                   SSHTunnelOnly(3) - Enabled Terminal Server IP port Access using a SSH tunnels."
                  ::= { adTaIPAccessPortMgmt 7 }

           adTaMenuIPAccess OBJECT-TYPE
               SYNTAX INTEGER {
                                 enable(1),
                                 disable(2),
                                 sSHTunnelOnly(3)
                              }
               MAX-ACCESS  read-write
                  STATUS  current
                  DESCRIPTION
                   "Set Menu Server IP port Access mode.
                   Enable(1)        - Enable Menu Server IP port access.
                   Disable(2)       - Disable Menu Server IP port access.
                   SSHTunnelOnly(3) - Enabled Menu Server IP port Access using a SSH tunnels."
                  ::= { adTaIPAccessPortMgmt 9 }

           adTaTerminalServerIPAccess OBJECT-TYPE
           SYNTAX INTEGER {
                                 enable(1),
                                 disable(2),
                                 sSHTunnelOnly(3)
                              }
               MAX-ACCESS  read-write
                  STATUS  current
                  DESCRIPTION
                   "Set Terminal Server IP port Access mode.
                   Enable(1)        - Enable Terminal Server IP Access port.
                   Disable(2)       - Disable Terminal Server IP Access port.
                   SSHTunnelOnly(3) - Enabled Terminal Server IP port Access using a SSH tunnels."
                  ::= { adTaIPAccessPortMgmt 11 }

           adTaSSHIPAccess OBJECT-TYPE
           SYNTAX INTEGER {
                                 enable(1),
                                 disable(2)
                              }
               MAX-ACCESS  read-write
                  STATUS  current
                  DESCRIPTION
                   "Enable or disable SSH IP port 22.
                   Enable(1)        - Enable SSH IP port 22.
                   Disable(2)       - Disable SSH IP port 22."
                  ::= { adTaIPAccessPortMgmt 13 }

           adTaSSHIPTunnelsAccess  OBJECT-TYPE
           SYNTAX INTEGER {
                                 enable(1),
                                 disable(2)
                              }
               MAX-ACCESS  read-write
                  STATUS  current
                  DESCRIPTION
                   "Enable or disable SSH Tunnels Access.
                   Enable(1)        - Enable SSH Tunnels access.
                   Disable(2)       - Disabled SSH Tunnels access."
                  ::= { adTaIPAccessPortMgmt 15 }

          adTaCLIIPAccess OBJECT-TYPE
               SYNTAX INTEGER {
                                 enable(1),
                                 disable(2),
                                 sSHTunnelOnly(3)
                              }
               MAX-ACCESS  read-write
                  STATUS  current
                  DESCRIPTION
                   "Set CLI IP port Access mode.
                   Enable(1)        - Enable CLI IP port access.
                   Disable(2)       - Disable CLI IP port access.
                   SSHTunnelOnly(3) - Enabled Terminal Server IP port Access using a SSH tunnels."
                  ::= { adTaIPAccessPortMgmt 17 }

          adTaHTTPIPAccess OBJECT-TYPE
               SYNTAX INTEGER {
                                 enable(1),
                                 disable(2)
                              }
               MAX-ACCESS  read-write
                  STATUS  current
                  DESCRIPTION
                   "Set HTTP IP port Access mode.
                   Enable(1)        - Enable HTTP IP port access.
                   Disable(2)       - Disable HTTP IP port access."
                  ::= { adTaIPAccessPortMgmt 18 }

          adTaHTTPSIPAccess OBJECT-TYPE
               SYNTAX INTEGER {
                                 enable(1),
                                 disable(2)
                              }
               MAX-ACCESS  read-write
                  STATUS  current
                  DESCRIPTION
                   "Set HTTPS IP port Access mode.
                   Enable(1)        - Enable HTTPS IP port access.
                   Disable(2)       - Disable HTTPS IP port access."
                  ::= { adTaIPAccessPortMgmt 19 }

       --
       --
       --
       adTaTL1TelnetPortNumber OBJECT-TYPE
               SYNTAX Integer32 (1024..65535)
               MAX-ACCESS  read-write
               STATUS  current
               DESCRIPTION
                  "TL1 Telnet port number."
               ::= { adTaIPServicePortProvMgmt 1 }

       adTaTL1RawTCPPortNumber OBJECT-TYPE
               SYNTAX Integer32 (1024..65535)
               MAX-ACCESS  read-write
               STATUS  current
               DESCRIPTION
                  "TL1 Raw-TCP port number."
               ::= { adTaIPServicePortProvMgmt 3 }

       adTaSecondaryTelnetPortNumber OBJECT-TYPE
               SYNTAX Integer32 (1024..65535)
               MAX-ACCESS  read-write
               STATUS  current
               DESCRIPTION
                  "Secondary Telnet port number."
               ::= { adTaIPServicePortProvMgmt 5 }

       adTaNtwkTerminalTelnetPortNumber OBJECT-TYPE
               SYNTAX Integer32 (1024..65535)
               MAX-ACCESS  read-write
               STATUS  current
               DESCRIPTION
                  "Ntwk Terminal Server Telnet Port."
                  ::= { adTaIPServicePortProvMgmt 6 }

       adTaAdminTerminalTelnetPortNumber OBJECT-TYPE
               SYNTAX Integer32 (1024..65535)
               MAX-ACCESS  read-write
               STATUS  current
               DESCRIPTION
                  "Admin Terminal Server Telnet Port."
               ::= { adTaIPServicePortProvMgmt 7 }

       adTaCraftTerminalTelnetPortNumber OBJECT-TYPE
               SYNTAX Integer32 (1024..65535)
               MAX-ACCESS  read-write
               STATUS  current
               DESCRIPTION
                  "Craft Terminal Server Telnet Port."
               ::= { adTaIPServicePortProvMgmt 8 }

       adTaTL1SSHPortNumber OBJECT-TYPE
               SYNTAX Integer32 (1024..65535)
               MAX-ACCESS  read-write
               STATUS  current
               DESCRIPTION
                  "TL1 SSH Port."
               ::= { adTaIPServicePortProvMgmt 9 }

       adTaSecondarySSHPortNumber OBJECT-TYPE
               SYNTAX Integer32 (1024..65535)
               MAX-ACCESS  read-write
               STATUS  current
               DESCRIPTION
                  "Seconday SSH Port."
               ::= { adTaIPServicePortProvMgmt 10 }

       adTaCLITelnetPortNumber OBJECT-TYPE
               SYNTAX Integer32 (1024..65535)
               MAX-ACCESS  read-write
               STATUS  current
               DESCRIPTION
                  "CLI Telnet Port."
               ::= { adTaIPServicePortProvMgmt 11 }

       adTaCLISSHPortNumber OBJECT-TYPE
               SYNTAX Integer32 (1024..65535)
               MAX-ACCESS  read-write
               STATUS  current
               DESCRIPTION
                  "CLI SSH Port."
               ::= { adTaIPServicePortProvMgmt 12 }

       adTaSFTPPortNumber OBJECT-TYPE
               SYNTAX Integer32 (1..65535)
               MAX-ACCESS  read-write
               STATUS  current
               DESCRIPTION
                  "SFTP Port to connect to."
               ::= { adTaIPServicePortProvMgmt 13 }


       adTaTelnetDeadClientDetection OBJECT-TYPE
               SYNTAX INTEGER {
                                 enable(1),
                                 disable(2)
                              }
               MAX-ACCESS  read-write
               STATUS  current
               DESCRIPTION
                  "Telnet Dead Client Detection."
               ::= { adTaIPServicePortProvMgmt 17 }

       adTaRFC1122TCPDeadClientDetection OBJECT-TYPE
               SYNTAX INTEGER {
                                 enable(1),
                                 disable(2)
                              }
               MAX-ACCESS  read-write
               STATUS  current
               DESCRIPTION
                  "RFC1122 TCP Dead Client Detection."
               ::= { adTaIPServicePortProvMgmt 19 }

-- ********************************************************************************************************
-- ********************************************************************************************************
-- Admin Port Control.
       adTAeSCUAdminPort      OBJECT IDENTIFIER ::= { adTAeSCUNetworkMgmt 24 }

            adTAeSCUAdminPortMode OBJECT-TYPE
               SYNTAX INTEGER {
                                 menus(1),
                                 tl1(2),
                                 tl1TestAccess(3),
                                 terminalServer(4),
                                 cLI(5)
                              }
               MAX-ACCESS  read-write
               STATUS  current
               DESCRIPTION
                  "Admin port communication mode."
               ::= { adTAeSCUAdminPort 1 }

            adTAeSCUAdminPortModeOpti OBJECT-TYPE
               SYNTAX INTEGER {
                                 menus(1),
                                 tl1(2),
                                 terminalServer(3)
                              }
               MAX-ACCESS  read-write
               STATUS  current
               DESCRIPTION
                  "Admin port communication mode for systems that do NOT
                   support tl1TestAccess."
               ::= { adTAeSCUAdminPort 2 }

            adTAeSCUAdminPortUseRtsCts OBJECT-TYPE
               SYNTAX INTEGER { enable(1), disable(2) }
               MAX-ACCESS  read-write
               STATUS  current
               DESCRIPTION
                  "When enabled the controller will use the RS-232
                   Request To Send (RTS) and Clear To Send (CTS)
                   signals for Admin port communication."
               ::= { adTAeSCUAdminPort 3 }


            adTAeSCUAdminPortCarrierLoss OBJECT-TYPE
               SYNTAX INTEGER { enable(1), disable(2) }
               MAX-ACCESS  read-write
               STATUS  current
               DESCRIPTION
                  "When enabled the controller will terminate the menu session
                   on the loss of the RS-232 Data Carrier Detect (DCD) signal
                   for Admin port communication."
               ::= { adTAeSCUAdminPort 4 }

            adTAeSCUAdminPortDtrLogout OBJECT-TYPE
               SYNTAX INTEGER { enable(1), disable(2) }
               MAX-ACCESS  read-write
               STATUS  current
               DESCRIPTION
                  "When enabled the controller will De-assert/Drop the RS-232
                   Data Terminal Ready (DTR) signal on menu logouts for
                   Admin port communications."
               ::= { adTAeSCUAdminPort 5 }


-- ********************************************************************************************************
-- Generic Chassis Traps


        adTAeSCUCtrpBlownFuse    NOTIFICATION-TYPE
                OBJECTS       {
                        adTrapInformSeqNum,
                        sysName,
                        adGenSlotInfoIndex,
                        adTAeSCUTrapAlarmLevel
                        }
                STATUS          current
                DESCRIPTION
                        "Blown Fuse Alarm is active on module"
        --#TYPE      "Major - Blown Fuse Alarm is active on module"
        --#SUMMARY   "adTAeSCU 24125: Blown Fuse Alarm active;"
        --#SUMMARY   "detected at shelf: %s, slot: %d"
        --#ARGUMENTS { 1, 2 }
        --#SEVERITY  MAJOR
        --#GENERIC   6
        --#CATEGORY  "Error Events"
        --#SOURCE_ID "A"
        --#TIMEINDEX 0
        ::= { adTAeSCUmgNotificationEvents 24125 }

        adTAeSCUCtrpCardInserted   NOTIFICATION-TYPE
                OBJECTS       {
                        adTrapInformSeqNum,
                        sysName,
                        adGenSlotInfoIndex,
                        adTAeSCUTrapAlarmLevel,
                        adGenSlotProdName
                        }
                STATUS          current
                DESCRIPTION
                        "A card has been inserted into the chassis.
                         Optional unlisted varbind VARIABLES:
                         adGenSlotProdName indicate the card name that
                         was removed.  Only certain versions of
                         controller code will return this varbind.
                        "
        --#TYPE      "Informational - A card has been inserted into the chassis"
        --#SUMMARY   "TAeSCU 24126: Card inserted into chassis;"
        --#SUMMARY   "detected at chassis: %s, slot: %d"
        --#ARGUMENTS { 1, 2 }
        --#SEVERITY  INFORMATIONAL
        --#GENERIC   6
        --#CATEGORY  "Configuration Events"
        --#SOURCE_ID "A"
        --#TIMEINDEX 0
        ::= { adTAeSCUmgNotificationEvents 24126 }


        adTAeSCUCtrpCardRemoved   NOTIFICATION-TYPE
                OBJECTS       {
                        adTrapInformSeqNum,
                        sysName,
                        adGenSlotInfoIndex,
                        adTAeSCUTrapAlarmLevel,
                        adGenSlotProdName
                        }
                STATUS          current
                DESCRIPTION
                        "A card has been removed from the chassis
                         Optional unlisted varbind VARIABLES:
                         adGenSlotProdName indicate the card name that
                         was removed.  Only certain versions of
                         controller code will return this varbind.
                        "
        --#TYPE      "Warning - A card has been removed from the chassis"
        --#SUMMARY   "TAeSCU 24127: Card removed from chassis;"
        --#SUMMARY   "detected at chassis: %s, slot: %d"
        --#ARGUMENTS { 1, 2 }
        --#SEVERITY  WARNING
        --#GENERIC   6
        --#CATEGORY  "Configuration Events"
        --#SOURCE_ID "A"
        --#TIMEINDEX 0
        ::= { adTAeSCUmgNotificationEvents  24127 }


        adTAeSCUCtrpRmtAlmClear    NOTIFICATION-TYPE
                OBJECTS       {
                        adTrapInformSeqNum,
                        sysName,
                        adTAeSCUenvAlarmUserName,
                        adTAeSCUenvAlarmInputLevel
                        }
                STATUS          current
                DESCRIPTION
                        "Remote Input Alarm clear"
        --#TYPE      "Informational - Remote Input Alarm clear"
        --#SUMMARY   "TAeSCU 24128: Remote Input Alarm cleared;"
        --#SUMMARY   "detected at shelf: %s"
        --#ARGUMENTS { 1 }
        --#SEVERITY  INFORMATIONAL
        --#GENERIC   6
        --#CATEGORY  "Error Events"
        --#SOURCE_ID "A"
        --#TIMEINDEX 0
        ::= { adTAeSCUmgNotificationEvents 24128 }

        adTAeSCUCtrpRmtAlm    NOTIFICATION-TYPE
                OBJECTS       {
                        adTrapInformSeqNum,
                        sysName,
                        adTAeSCUenvAlarmUserName,
                        adTAeSCUenvAlarmInputLevel
                        }
                STATUS          current
                DESCRIPTION
                        "Remote Input Alarm active"
        --#TYPE      "Major - Remote Input Alarm active"
        --#SUMMARY   "TAeSCU 24129: Remote Input Alarm active;"
        --#SUMMARY   "detected at shelf: %s"
        --#ARGUMENTS { 1 }
        --#SEVERITY  MAJOR
        --#GENERIC   6
        --#CATEGORY  "Error Events"
        --#SOURCE_ID "A"
        --#TIMEINDEX 0
        ::= { adTAeSCUmgNotificationEvents 24129 }

        adTAeSCUCtrpExt1AlmClear    NOTIFICATION-TYPE
                OBJECTS       {
                        adTrapInformSeqNum,
                        sysName,
                        adTAeSCUenvAlarmUserName,
                        adTAeSCUenvAlarmInputLevel
                        }
                STATUS          current
                DESCRIPTION
                        "External Input #1 Alarm clear"
        --#TYPE      "Informational - External Input #1 Alarm clear"
        --#SUMMARY   "TAeSCU 24130: External Input #1 Alarm cleared;"
        --#SUMMARY   "detected at shelf: %s"
        --#ARGUMENTS { 1 }
        --#SEVERITY  INFORMATIONAL
        --#GENERIC   6
        --#CATEGORY  "Error Events"
        --#SOURCE_ID "A"
        --#TIMEINDEX 0
        ::= { adTAeSCUmgNotificationEvents 24130 }

        adTAeSCUCtrpExt1Alm    NOTIFICATION-TYPE
                OBJECTS       {
                        adTrapInformSeqNum,
                        sysName,
                        adTAeSCUenvAlarmUserName,
                        adTAeSCUenvAlarmInputLevel
                        }
                STATUS          current
                DESCRIPTION
                        "External Input #1 Alarm active"
        --#TYPE      "Major - External Input #1 Alarm active"
        --#SUMMARY   "TAeSCU 24131: External Input #1 Alarm active;"
        --#SUMMARY   "detected at shelf: %s"
        --#ARGUMENTS { 1 }
        --#SEVERITY  MAJOR
        --#GENERIC   6
        --#CATEGORY  "Error Events"
        --#SOURCE_ID "A"
        --#TIMEINDEX 0
        ::= { adTAeSCUmgNotificationEvents 24131 }

        adTAeSCUCtrpExt2AlmClear    NOTIFICATION-TYPE
                OBJECTS       {
                        adTrapInformSeqNum,
                        sysName,
                        adTAeSCUenvAlarmUserName,
                        adTAeSCUenvAlarmInputLevel
                        }
                STATUS          current
                DESCRIPTION
                        "External Input #2 Alarm clear"
        --#TYPE      "Informational - External Input #2 Alarm clear"
        --#SUMMARY   "TAeSCU 24132: External Input #2 Alarm cleared;"
        --#SUMMARY   "detected at shelf: %s"
        --#ARGUMENTS { 1 }
        --#SEVERITY  INFORMATIONAL
        --#GENERIC   6
        --#CATEGORY  "Error Events"
        --#SOURCE_ID "A"
        --#TIMEINDEX 0
        ::= { adTAeSCUmgNotificationEvents 24132 }

        adTAeSCUCtrpExt2Alm    NOTIFICATION-TYPE
                OBJECTS       {
                        adTrapInformSeqNum,
                        sysName,
                        adTAeSCUenvAlarmUserName,
                        adTAeSCUenvAlarmInputLevel
                        }
                STATUS          current
                DESCRIPTION
                        "External Input #2 Alarm active"
        --#TYPE      "Major - External Input #2 Alarm active"
        --#SUMMARY   "TAeSCU 24133: External Input #2 Alarm active;"
        --#SUMMARY   "detected at shelf: %s"
        --#ARGUMENTS { 1 }
        --#SEVERITY  MAJOR
        --#GENERIC   6
        --#CATEGORY  "Error Events"
        --#SOURCE_ID "A"
        --#TIMEINDEX 0
        ::= { adTAeSCUmgNotificationEvents 24133 }

        adTAeSCUCtrpBusApwrAlmClear    NOTIFICATION-TYPE
                OBJECTS       {
                        adTrapInformSeqNum,
                        sysName,
                        adTAeSCUenvAlarmUserName,
                        adTAeSCUenvAlarmInputLevel
                        }
                STATUS          current
                DESCRIPTION
                        "Bus A Power Failure Alarm clear"
        --#TYPE      "Informational - Bus A Power Failure Alarm clear"
        --#SUMMARY   "TAeSCU 24134: Bus A Power Failure Alarm cleared;"
        --#SUMMARY   "detected at shelf: %s"
        --#ARGUMENTS { 1 }
        --#SEVERITY  INFORMATIONAL
        --#GENERIC   6
        --#CATEGORY  "Error Events"
        --#SOURCE_ID "A"
        --#TIMEINDEX 0
        ::= { adTAeSCUmgNotificationEvents 24134 }

        adTAeSCUCtrpBusApowerAlm    NOTIFICATION-TYPE
                OBJECTS       {
                        adTrapInformSeqNum,
                        sysName,
                        adTAeSCUenvAlarmUserName,
                        adTAeSCUenvAlarmInputLevel
                        }
                STATUS          current
                DESCRIPTION
                        "Bus A Power Failure Alarm active"
        --#TYPE      "Major - Bus A Power Failure Alarm active"
        --#SUMMARY   "TAeSCU 24135: Bus A Power Failure Alarm active;"
        --#SUMMARY   "detected at shelf: %s"
        --#ARGUMENTS { 1 }
        --#SEVERITY  MAJOR
        --#GENERIC   6
        --#CATEGORY  "Error Events"
        --#SOURCE_ID "A"
        --#TIMEINDEX 0
        ::= { adTAeSCUmgNotificationEvents 24135 }

        adTAeSCUCtrpBusBpwrAlmClear    NOTIFICATION-TYPE
                OBJECTS       {
                        adTrapInformSeqNum,
                        sysName,
                        adTAeSCUenvAlarmUserName,
                        adTAeSCUenvAlarmInputLevel
                        }
                STATUS          current
                DESCRIPTION
                        "Bus B Power Failure Alarm clear"
        --#TYPE      "Informational - Bus B Power Failure Alarm clear"
        --#SUMMARY   "TAeSCU 24136: Bus B Power Failure Alarm cleared;"
        --#SUMMARY   "detected at shelf: %s"
        --#ARGUMENTS { 1 }
        --#SEVERITY  INFORMATIONAL
        --#GENERIC   6
        --#CATEGORY  "Error Events"
        --#SOURCE_ID "A"
        --#TIMEINDEX 0
        ::= { adTAeSCUmgNotificationEvents 24136 }

        adTAeSCUCtrpBusBpowerAlm    NOTIFICATION-TYPE
                OBJECTS       {
                        adTrapInformSeqNum,
                        sysName,
                        adTAeSCUenvAlarmUserName,
                        adTAeSCUenvAlarmInputLevel
                        }
                STATUS          current
                DESCRIPTION
                        "Bus B Power Failure Alarm active"
        --#TYPE      "Major - Bus B Power Failure Alarm active"
        --#SUMMARY   "TAeSCU 24137: Bus B Power Failure Alarm active;"
        --#SUMMARY   "detected at shelf: %s"
        --#ARGUMENTS { 1 }
        --#SEVERITY  MAJOR
        --#GENERIC   6
        --#CATEGORY  "Error Events"
        --#SOURCE_ID "A"
        --#TIMEINDEX 0
        ::= { adTAeSCUmgNotificationEvents 24137 }

        adTAeSCUCardCommRestored   NOTIFICATION-TYPE
                OBJECTS       {
                        adTrapInformSeqNum,
                        sysName,
                        adGenSlotInfoIndex,
                        adTAeSCUTrapAlarmLevel
                        }
                STATUS          current
                DESCRIPTION
                        "Communication with a card has been restored"
        --#TYPE      "Informational - Communication with card restored"
        --#SUMMARY   "TAeSCU 24138: Communication with card restored;"
        --#SUMMARY   "detected at chassis: %s, slot: %d"
        --#ARGUMENTS { 1, 2 }
        --#SEVERITY  MAJOR
        --#GENERIC   6
        --#CATEGORY  "Error Events"
        --#SOURCE_ID "A"
        --#TIMEINDEX 0
        ::= { adTAeSCUmgNotificationEvents 24138 }


        adTAeSCUCardCommFail   NOTIFICATION-TYPE
                OBJECTS       {
                        adTrapInformSeqNum,
                        sysName,
                        adGenSlotInfoIndex,
                        adTAeSCUTrapAlarmLevel
                        }
                STATUS          current
                DESCRIPTION
                        "Communication with a card has failed"
        --#TYPE      "Warning - Communication with card failed"
        --#SUMMARY   "TAeSCU 24139: Communication with card failed;"
        --#SUMMARY   "detected at chassis: %s, slot: %d"
        --#ARGUMENTS { 1, 2 }
        --#SEVERITY  MAJOR
        --#GENERIC   6
        --#CATEGORY  "Error Events"
        --#SOURCE_ID "A"
        --#TIMEINDEX 0
        ::= { adTAeSCUmgNotificationEvents 24139 }

      adTAeSCUCraftLoginClear   NOTIFICATION-TYPE
                OBJECTS       {
                        adTrapInformSeqNum,
                        sysName,
                        adTAeSCUSecAccountUserID,
                        adTAeSCUCraftLoginAlarmLevel
                        }
                STATUS          current
                DESCRIPTION
                        "Craft Login Clear. User Loged Out."
        --#TYPE      "Warning - Craft Account Log Out."
        --#SUMMARY   "TAeSCU 24164: Craft Log Out Account ID %d.;"
        --#SUMMARY   "detected at chassis: %s"
        --#ARGUMENTS { 1,2}
        --#SEVERITY  INFORMATIONAL
        --#GENERIC   6
        --#CATEGORY  "Log Out Event"
        --#SOURCE_ID "A"
        --#TIMEINDEX 0
        ::= { adTAeSCUmgNotificationEvents 24164 }
        adTAeSCUCraftLoginNotfication   NOTIFICATION-TYPE
                OBJECTS       {
                        adTrapInformSeqNum,
                        sysName,
                        adTAeSCUSecAccountUserID,
                        adTAeSCUCraftLoginAlarmLevel
                        }
                STATUS          current
                DESCRIPTION
                        "Craft Login notification."
        --#TYPE      "Warning - Craft Account Login."
        --#SUMMARY   "TAeSCU 24165: Craft Login Notification Account ID %d.;"
        --#SUMMARY   "detected at chassis: %s"
        --#ARGUMENTS { 1,2}
        --#SEVERITY  INFORMATIONAL
        --#GENERIC   6
        --#CATEGORY  "Login Event"
        --#SOURCE_ID "A"
        --#TIMEINDEX 0
        ::= { adTAeSCUmgNotificationEvents 24165 }

        adTASysCtrlInvalidControllerClear   NOTIFICATION-TYPE
                OBJECTS       {
                        adTrapInformSeqNum,
                        sysName,
                        adTAeSCUTrapAlarmLevel
                        }
                STATUS          current
                DESCRIPTION
                        "An invalid controller alarm cleared."
        --#TYPE      "Warning - Invalid controller installed."
        --#SUMMARY   "TAeSCU 24168: Invalid controller installed;"
        --#SUMMARY   "detected at chassis: %s, slot: %d"
        --#ARGUMENTS { 1, 2 }
        --#SEVERITY  MINOR
        --#GENERIC   6
        --#CATEGORY  "Error Events"
        --#SOURCE_ID "A"
        --#TIMEINDEX 0
        ::= { adTAeSCUmgNotificationEvents 24168 }

        adTASysCtrlInvalidController   NOTIFICATION-TYPE
                OBJECTS       {
                        adTrapInformSeqNum,
                        sysName,
                        adTAeSCUTrapAlarmLevel
                        }
                STATUS          current
                DESCRIPTION
                        "An invalid controller module has been installed."
        --#TYPE      "Warning - Invalid controller installed."
        --#SUMMARY   "TAeSCU 24169: Invalid controller installed;"
        --#SUMMARY   "detected at chassis: %s, slot: %d"
        --#ARGUMENTS { 1, 2 }
        --#SEVERITY  MINOR
        --#GENERIC   6
        --#CATEGORY  "Error Events"
        --#SOURCE_ID "A"
        --#TIMEINDEX 0
        ::= { adTAeSCUmgNotificationEvents 24169 }

        adTASysModuleRestart   NOTIFICATION-TYPE
                OBJECTS       {
                        adTrapInformSeqNum,
                        sysName,
                        adGenSlotInfoIndex,
                        adTAeSCUTrapAlarmLevel,
                        adGenSlotProdName
                        }
                STATUS          current
                DESCRIPTION
                        "The module has restarted."
        --#TYPE      "Warning - The module has restarted."
        --#SUMMARY   "Controller 24170: The module has restarted;"
        --#SUMMARY   "detected at chassis: %s, slot: %d"
        --#ARGUMENTS { 1, 2 }
        --#SEVERITY  WARNING
        --#GENERIC   6
        --#CATEGORY  "Error Events"
        --#SOURCE_ID "A"
        --#TIMEINDEX 0
        ::= { adTAeSCUmgNotificationEvents 24170 }

-- to do
-- I just added "Logoff Craft Port When DTR Lost" functionality to the
-- eSCU, and we gotta support it with snmp.

-- This value is a simple enable/disable value.

-- When set to ENABLE, this provision has the effect of closing or
-- forcing a 'logout' of any active CRAFT session when we sense an
-- absence of the RS-232 DTR signal.


      END

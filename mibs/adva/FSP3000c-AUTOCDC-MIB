FSP3000c-AUTOCDC-MIB DEFINITIONS ::= BEGIN

IMPORTS
    MODULE-COMPLIANCE, OBJECT-GROUP, NOTIFICATION-GROUP
             FROM SNMPv2-CONF
    MODULE-IDENTITY, OBJECT-TYPE, NOTIFICATION-TYPE, Integer32
             FROM SNMPv2-SMI
    TEXTUAL-CONVENTION, TruthValue
             FROM SNMPv2-TC
    ifIndex
             FROM IF-MIB
    fsp3000c, aosCommon
             FROM ADVA-MIB;

fsp3000cAutoCDCMIB MODULE-IDENTITY
    LAST-UPDATED    "201609270000Z"
    ORGANIZATION    "ADVA Optical Networking"
    CONTACT-INFO
                    "ADVA Optical Networking, Inc."
    DESCRIPTION     "This module defines the Core Facility MIB definitions
                     used by the AOS based product lines.
                     Copyright (C) ADVA Optical Networking."
    REVISION        "201609270000Z"
    DESCRIPTION     "Automatic Chromatic Dispersion Control (CDC) process
                     monitoring MIB."
    ::= {fsp3000c 1}

--
-- OID definitions
--

fsp3000cAutoCDCObjects          OBJECT IDENTIFIER ::= {fsp3000cAutoCDCMIB 1}
fsp3000cAutoCDCConformance      OBJECT IDENTIFIER ::= {fsp3000cAutoCDCMIB 2}

--
-- Textual conventions.
--

AutoCdcControlType ::= TEXTUAL-CONVENTION
    STATUS       current
    DESCRIPTION
        "Auto CDC operation status."
    SYNTAX       INTEGER {
                   none(0),
                   idle(1),
                   init(2),
                   measure(3),
                   validate(4)
                 }

AutoCdcResultType ::= TEXTUAL-CONVENTION
    STATUS       current
    DESCRIPTION
        "Auto CDC measurement and control process completion codes."
    SYNTAX       INTEGER {
                   none(0),
                   standby(1),
                   progress(2),
                   initfail(3),
                   timeout(4),
                   rngerr(5),
                   valerr(6),
                   success(7)
                 }

--
-- Scalar definitions.
--

--
-- Table definitions.
--
autoCdcStatusTable OBJECT-TYPE
    SYNTAX     SEQUENCE OF AutoCdcStatusEntry
    MAX-ACCESS not-accessible
    STATUS     current
    DESCRIPTION
            "A list of entries supporting automatic CDC measurement process."
    ::= { fsp3000cAutoCDCObjects 1 }

autoCdcStatusEntry  OBJECT-TYPE
    SYNTAX     AutoCdcStatusEntry
    MAX-ACCESS not-accessible
    STATUS     current
    DESCRIPTION
            "A table row entry representing Auto CDC status data for particular
             interface."
    INDEX { ifIndex }
    ::= { autoCdcStatusTable 1 }

AutoCdcStatusEntry ::= SEQUENCE {
    autoCdcStatusControlType      AutoCdcControlType,
    autoCdcStatusPercentComplete  Integer32,
    autoCdcStatusResultType       AutoCdcResultType,
    autoCdcStatusTodcValueSet     TruthValue,
    autoCdcStatusTodcValue        Integer32
}

autoCdcStatusControlType OBJECT-TYPE
    SYNTAX     AutoCdcControlType
    MAX-ACCESS read-only
    STATUS     current
    DESCRIPTION
         "Type of the Auto CDC control."
     ::= { autoCdcStatusEntry 1 }

autoCdcStatusPercentComplete OBJECT-TYPE
    SYNTAX     Integer32
    MAX-ACCESS read-only
    STATUS     current
    DESCRIPTION
         "Auto CDC process completion state (percentage)."
     ::= { autoCdcStatusEntry 2 }

autoCdcStatusResultType OBJECT-TYPE
    SYNTAX     AutoCdcResultType
    MAX-ACCESS read-only
    STATUS     current
    DESCRIPTION
         "Auto CDC process result type."
     ::= { autoCdcStatusEntry 3 }

autoCdcStatusTodcValueSet OBJECT-TYPE
    SYNTAX     TruthValue
    MAX-ACCESS read-only
    STATUS     current
    DESCRIPTION
         "True when the todc-value was set by the auto-cdc process, False when
          todc-value is administratively written."
     ::= { autoCdcStatusEntry 4 }

autoCdcStatusTodcValue OBJECT-TYPE
    SYNTAX     Integer32
    UNITS      "ps/nm"
    MAX-ACCESS read-only
    STATUS     current
    DESCRIPTION
         "Register setting for todc control function."
     ::= { autoCdcStatusEntry 5 }

--
-- Conformance
--
fsp3000cAutoCDCCompliances      OBJECT IDENTIFIER ::= {fsp3000cAutoCDCConformance 1}
fsp3000cAutoCDCGroups           OBJECT IDENTIFIER ::= {fsp3000cAutoCDCConformance 2}

fsp3000cAutoCDCCompliance MODULE-COMPLIANCE
    STATUS  current
    DESCRIPTION
            "Compliance status for this MIB."
    MODULE  -- this module
        MANDATORY-GROUPS {
              fsp3000cAutoCDCObjectGroup
        }
    ::= { fsp3000cAutoCDCCompliances 1 }

fsp3000cAutoCDCObjectGroup OBJECT-GROUP
    OBJECTS {
        autoCdcStatusControlType,
        autoCdcStatusPercentComplete,
        autoCdcStatusResultType,
        autoCdcStatusTodcValueSet,
        autoCdcStatusTodcValue
    }
    STATUS  current
    DESCRIPTION
            "A collection of objects used to monitor Auto CDC process."
    ::= { fsp3000cAutoCDCGroups 1 }

END

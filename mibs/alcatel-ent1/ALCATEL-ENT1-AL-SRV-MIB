ALCATEL-ENT1-AL-SRV-MIB DEFINITIONS ::= BEGIN

        IMPORTS
                Unsigned32, IpAddress,
                MODULE-IDENTITY, OBJECT-TYPE,
                NOTIFICATION-TYPE, OBJECT-IDENTITY
                                        FROM SNMPv2-SMI
                MacAddress, DisplayString, DateAndTime
                                        FROM SNMPv2-TC
                MODULE-COMPLIANCE, OBJECT-GROUP,
                NOTIFICATION-GROUP
                                        FROM SNMPv2-CONF
		InetAddress, InetAddressType
                        		FROM INET-ADDRESS-MIB
                softentIND1ActiveLeaseSrvMIB
                                        FROM ALCATEL-ENT1-BASE;


                alcatelIND1ActiveLeaseSrvMIB MODULE-IDENTITY
                LAST-UPDATED "201306050000Z"
                ORGANIZATION "Alcatel - Architects Of An Internet World"
                CONTACT-INFO
                "Please consult with Customer Service to insure the most appropriate
                version of this document is used with the products in question:

                        Alcatel Internetworking, Incorporated
                        (Division 1, Formerly XYLAN Corporation)
                        26801 West Agoura Road
                        Agoura Hills, CA  91301-5122
                        United States Of America

                        Telephone:      North America  +1 800 995 2696
                                        Latin America  +1 877 919 9526
                                        Europe         +31 23 556 0100
                                        Asia           +65 394 7933
                                        All Other      +1 818 878 4507

                Electronic Mail:         support@ind.alcatel.com
                World Wide Web:          http://www.ind.alcatel.com
                File Transfer Protocol:  ftp://ftp.ind.alcatel.com/pub/products/mibs"

                DESCRIPTION
                        "This module describes an authoritative enterprise-specific Simple
                        Network Management Protocol (SNMP) Management Information Base (MIB):

                        For the Birds Of Prey Product Line
                        Active Lease Service for DHCP Server management  

                        The right to make changes in specification and other information
                        contained in this document without prior notice is reserved.

                        No liability shall be assumed for any incidental, indirect, special, or
                        consequential damages whatsoever arising from or related to this
                        document or the information contained herein.

                        Vendors, end-users, and other interested parties are granted
                        non-exclusive license to use this specification in connection with
                        management of the products for which it is intended to be used.

                        Copyright (C) 1995-2002 Alcatel Internetworking, Incorporated
                        ALL RIGHTS RESERVED WORLDWIDE"

                REVISION      "201306050000Z"
                DESCRIPTION
                        "The QIP Active Lease Service provides a framework for components 
			such as DHCP server interact with other QIP components in the network.
                        This MIB provides the configuration information for Active Lease Service."
                ::= { softentIND1ActiveLeaseSrvMIB 1 }

-- --------------------------------------------------------------
                alcatelIND1ActiveLeaseSrvMIBNotifications OBJECT-IDENTITY
                STATUS current
                DESCRIPTION
                        "Branch For Active Lease Service Subsystem Notifications."
                ::= { alcatelIND1ActiveLeaseSrvMIB 0 }

                alcatelIND1ActiveLeaseSrvMIBObjects OBJECT-IDENTITY
                STATUS current
                DESCRIPTION
                        "Branch For Active Lease Service Subsystem Managed Objects."
                ::= { alcatelIND1ActiveLeaseSrvMIB 1 }

                alcatelIND1ActiveLeaseSrvMIBConformance OBJECT-IDENTITY
                STATUS current
                DESCRIPTION
                        "Branch for Active Lease Service Module MIB Subsystem i
		Conformance Information."
                ::= { alcatelIND1ActiveLeaseSrvMIB 2 }

                alcatelIND1ActiveLeaseSrvMIBGroups OBJECT-IDENTITY
                STATUS current
                DESCRIPTION
                        "Branch for ActiveLeaseSrv Module MIB Subsystem Units of Conformance."
                ::= { alcatelIND1ActiveLeaseSrvMIBConformance 1 }

                alcatelIND1ActiveLeaseSrvMIBCompliances OBJECT-IDENTITY
                STATUS current
                DESCRIPTION
                        "Branch for Active Lease Service Module MIB Subsystem Compliance Statements."
                ::= { alcatelIND1ActiveLeaseSrvMIBConformance 2 }

-- --------------------------------------------------------------


alaActiveLeaseSrvGlobalConfigStatus OBJECT-TYPE
        SYNTAX INTEGER
                {
                  enable(1),
                  disable(2)
                }
        MAX-ACCESS read-write
        STATUS current
        DESCRIPTION
            "This object is used to enable(1) or disable(2) QIP Active Lease Service on the switch."
	DEFVAL { disable }
::= { alcatelIND1ActiveLeaseSrvMIBObjects 1 }

alaActiveLeaseSrvGlobalRestart OBJECT-TYPE
        SYNTAX INTEGER
                {
                  inactive(1),
                  restart(2)
                }
        MAX-ACCESS read-write
        STATUS current
        DESCRIPTION
            "This object is used to restart(2) the QIP Active Lease Service on i
	the switch. Default value is inactive(1) which user can not set."
        DEFVAL { inactive }
::= { alcatelIND1ActiveLeaseSrvMIBObjects 2 }


-- -------------------------------------------------------------
-- COMPLIANCE
-- -------------------------------------------------------------
alcatelIND1ActiveLeaseSrvMIBCompliance MODULE-COMPLIANCE
        STATUS    current
        DESCRIPTION
            "Compliance statement for QIP Active Lease Service."
        MODULE
        MANDATORY-GROUPS
        {
                alaActiveLeaseSrvGlobalConfigGroup
        }
        ::= { alcatelIND1ActiveLeaseSrvMIBCompliances 1 }

-- -------------------------------------------------------------
-- UNITS OF CONFORMANCE
-- -------------------------------------------------------------
alaActiveLeaseSrvGlobalConfigGroup OBJECT-GROUP
        OBJECTS
        {
                alaActiveLeaseSrvGlobalConfigStatus,
                alaActiveLeaseSrvGlobalRestart
        }
        STATUS  current
        DESCRIPTION
            "Collection of objects for management of QIP Active Lease Service 
		Global Configuration."
        ::= { alcatelIND1ActiveLeaseSrvMIBGroups 1 }


-- -------------------------------------------------------------

END

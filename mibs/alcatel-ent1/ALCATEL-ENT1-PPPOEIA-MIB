ALCATEL-ENT1-PPPOEIA-MIB DEFINITIONS ::= BEGIN


IMPORTS
    MODULE-IDENTITY,
    OBJECT-TYPE, OBJECT-IDENTITY,
    Counter32                 FROM SNMPv2-SMI    -- [RFC2578]
    TEXTUAL-CONVENTION        FROM SNMPv2-TC
    SnmpAdminString           FROM SNMP-FRAMEWORK-MIB 
    MODULE-COMPLIANCE,
    OBJECT-GROUP              FROM SNMPv2-CONF   -- [RFC2580]
    InterfaceIndex            FROM IF-MIB        -- [RFC2863]
    softentIND1PPPoEIA        FROM ALCATEL-ENT1-BASE
   ;

alaPPPoEIAMIB   MODULE-IDENTITY
    LAST-UPDATED "201101240000Z"    -- 07/16/2014 00:00GMT
    ORGANIZATION "Alcatel - Architects Of An Internet World"
    CONTACT-INFO
    "Please consult with Customer Service to insure the most appropriate
                 version of this document is used with the products in question:

                        Alcatel Internetworking, Incorporated
                       (Division 1, Formerly XYLAN Corporation)
                               26801 West Agoura Road
                            Agoura Hills, CA  91301-5122
                              United States Of America

                Telephone:           North America  +1 800 995 2696
                                     Latin America  +1 877 919 9526
                                     Europe         +31 23 556 0100
                                     Asia           +65 394 7933
                                     All Other      +1 818 878 4507

                Electronic Mail:         support@ind.alcatel.com
                World Wide Web:          http://www.ind.alcatel.com
                File Transfer Protocol:  ftp://ftp.ind.alcatel.com/pub/products/mibs"
    DESCRIPTION 
    "This module describes an authoritative enterprise-
     specific Simple Network Management Protocol (SNMP) Management
     Information Base (MIB):

     For the Birds Of Prey Product Line
     PPPoE Intermediate Agent.

     The right to make changes in specification and other information
     contained in this document without prior notice is reserved.

     No liability shall be assumed for any incidental, indirect,
     special, or consequential damages whatsoever arising from or
     related to this document or the information contained herein.

     Vendors, end-users, and other interested parties are granted
     non-exclusive license to use this specification in connection with
     management of the products for which it is intended to be used.

     Copyright (C) 1995-2002 Alcatel Internetworking, Incorporated
                         ALL RIGHTS RESERVED WORLDWIDE"


    REVISION       "201101240000Z"    -- 01/24/2011 00:00GMT
    DESCRIPTION 
           "The mib for PPPoE Intermediate Agent module."
                ::= { softentIND1PPPoEIA 1}

-- ---------------------------------------------------------------------------------

alaPPPoEIAMIBObjects OBJECT-IDENTITY
STATUS current
DESCRIPTION
        "Branch For PPPoE Intermediate Agent Subsystem Managed Objects."
::= { alaPPPoEIAMIB 1 }

alaPPPoEIAMIBConformance OBJECT-IDENTITY
STATUS current
DESCRIPTION
        "Branch for PPPoE Intermediate Agent Module MIB Subsystem Conformance Information."
::= { alaPPPoEIAMIB 2 }

alaPPPoEIAMIBGroups OBJECT-IDENTITY
STATUS current
DESCRIPTION
        "Branch for PPPoE Intermediate Agent Module MIB Subsystem Units of Conformance."
::= { alaPPPoEIAMIBConformance 1 }

alaPPPoEIAMIBCompliances OBJECT-IDENTITY
STATUS current
DESCRIPTION
        "Branch for PPPoE Intermediate Agent Module MIB Subsystem Compliance Statements."
::= { alaPPPoEIAMIBConformance 2 }

-- ----------------------------------------------------------------------------------

PPPoEIACircuitIDFieldType ::= TEXTUAL-CONVENTION
    STATUS        current
    DESCRIPTION
       "The format for PPPoEIA Circuit Identifier ASCII field
        none(1) - This value is used when no format is specified
        base-mac(2) - base mac of the system
        system-name(3) - name of the system
        user-string(4) - user configurable string
        interface-alias(5) - the alias used for the interface
        vlan(6) - the vlan on which packets is received
        interface(7) - the interface on which packets are received
        cvlan(8) - the cvlan on which packets are received"
    SYNTAX  INTEGER {
             none(1),
             baseMac(2),
             systemName(3),
             userString(4),
             interfaceAlias(5),
             vlan(6),
             interface(7),
             cvlan(8)
            }

-- *******************************************************************
-- The PPPoE Intermediate Agent Status object
-- *******************************************************************
alaPPPoEIAGlobalConfig    OBJECT IDENTIFIER ::= { alaPPPoEIAMIBObjects 1 }

alaPPPoEIAGlobalStatus OBJECT-TYPE
    SYNTAX          INTEGER {
                    enable(1),
                    disable(2)
                    }
    MAX-ACCESS      read-write
    STATUS          current
    DESCRIPTION
       "Defines the global status for PPPoE Intermediate Agent.
        Indicates whether the PPPoE Intermediate Agent is enabled/disabled on the switch."
    DEFVAL  { disable }
    ::= { alaPPPoEIAGlobalConfig 1 }

-- *******************************************************************
-- The PPPoE Intermediate Agent Access Node Identifier object
-- *******************************************************************

alaPPPoEIAGlobalAccessNodeIDFormatType OBJECT-TYPE
    SYNTAX          INTEGER {
                    baseMac(1),
                    systemName(2),
                    mgntAddress(3),
                    userString(4)
                    }
    MAX-ACCESS      read-write
    STATUS          current
    DESCRIPTION
       "Defines the format type for Access Node Identifier."
    DEFVAL  { baseMac }
    ::= { alaPPPoEIAGlobalConfig 2 }

alaPPPoEIAGlobalAccessNodeIDStringValue OBJECT-TYPE
    SYNTAX          SnmpAdminString (SIZE (0..255)) 
    MAX-ACCESS      read-write
    STATUS          current
    DESCRIPTION
       "Defines the value of string that will be used in Access Node Identifier."
    ::= { alaPPPoEIAGlobalConfig 3 }

-- *******************************************************************
-- The PPPoE Intermediate Agent Circuit Identifier Field objects
-- *******************************************************************
alaPPPoEIAGlobalCircuitIDFormatType OBJECT-TYPE       
    SYNTAX	    INTEGER {
                    default(1),
                    ascii(2),
                    atm(3)  
                  }
    MAX-ACCESS 	    read-write
    STATUS 	    current
    DESCRIPTION
       "Defines the format type for CircuitID.
        If format is default(1), the CircuitID is encoded as 'access-node-id eth slot/port:vlan'.
        If format is ascii(2), CircuitID is encoded as all the CircuitID fields separated by 
        delimiter upto a maximum of 63 chars.
        If format is atm(3),the CircuitID is encoded as 'access-node-id atm rack/sub-rack/slot/port:svlan.cvlan'.Here rack/sub-rack will be always 0/0" 
    DEFVAL { default }
    ::= { alaPPPoEIAGlobalConfig 4 }

alaPPPoEIAGlobalCircuitIDField1 OBJECT-TYPE
    SYNTAX          PPPoEIACircuitIDFieldType 
    MAX-ACCESS      read-write
    STATUS          current
    DESCRIPTION
       "The type of the first field in the PPPoEIA CircuitID in ASCII format."
    DEFVAL { none }
    ::= { alaPPPoEIAGlobalConfig 5 }

alaPPPoEIAGlobalCircuitIDField1StrVal OBJECT-TYPE
    SYNTAX	    SnmpAdminString (SIZE (0..255))
    MAX-ACCESS 	    read-write
    STATUS 	    current
    DESCRIPTION
       "The string value of the first field in the PPPoEIA CircuitID in ASCII format."
    ::= { alaPPPoEIAGlobalConfig 6 }

alaPPPoEIAGlobalCircuitIDField2 OBJECT-TYPE
    SYNTAX          PPPoEIACircuitIDFieldType 
    MAX-ACCESS      read-write
    STATUS          current
    DESCRIPTION
       "The type of the second field in the PPPoEIA CircuitID in ASCII format."
    DEFVAL { none }
    ::= { alaPPPoEIAGlobalConfig 7 }

alaPPPoEIAGlobalCircuitIDField2StrVal OBJECT-TYPE       
    SYNTAX	    SnmpAdminString (SIZE (0..255))
    MAX-ACCESS 	    read-write
    STATUS 	    current
    DESCRIPTION
       "The string value of the second field in the PPPoEIA CircuitID in ASCII format."
    ::= { alaPPPoEIAGlobalConfig 8 }

alaPPPoEIAGlobalCircuitIDField3 OBJECT-TYPE
    SYNTAX          PPPoEIACircuitIDFieldType 
    MAX-ACCESS      read-write
    STATUS          current
    DESCRIPTION
       "The type of the third field in the PPPoEIA CircuitID in ASCII format." 
    DEFVAL { none }
    ::= { alaPPPoEIAGlobalConfig 9 }

alaPPPoEIAGlobalCircuitIDField3StrVal OBJECT-TYPE       
    SYNTAX	    SnmpAdminString (SIZE (0..255))
    MAX-ACCESS 	    read-write
    STATUS 	    current
    DESCRIPTION
       "The string value of the third field in the PPPoEIA CircuitID in ASCII format."
    ::= { alaPPPoEIAGlobalConfig 10 }

alaPPPoEIAGlobalCircuitIDField4 OBJECT-TYPE
    SYNTAX          PPPoEIACircuitIDFieldType 
    MAX-ACCESS      read-write
    STATUS          current
    DESCRIPTION
       "The type of the fourth field in the PPPoEIA CircuitID in ASCII format." 
    DEFVAL { none }
    ::= { alaPPPoEIAGlobalConfig 11 }

alaPPPoEIAGlobalCircuitIDField4StrVal OBJECT-TYPE       
    SYNTAX	    SnmpAdminString (SIZE (0..255))
    MAX-ACCESS 	    read-write
    STATUS 	    current
    DESCRIPTION
       "The string value of the fourth field in the PPPoEIA CircuitID in ASCII format."
    ::= { alaPPPoEIAGlobalConfig 12 }

alaPPPoEIAGlobalCircuitIDField5 OBJECT-TYPE
    SYNTAX          PPPoEIACircuitIDFieldType 
    MAX-ACCESS      read-write
    STATUS          current
    DESCRIPTION
       "The type of the fifth field in the PPPoEIA CircuitID in ASCII format." 
    DEFVAL { none }
    ::= { alaPPPoEIAGlobalConfig 13 }

alaPPPoEIAGlobalCircuitIDField5StrVal OBJECT-TYPE       
    SYNTAX	    SnmpAdminString (SIZE (0..255))
    MAX-ACCESS 	    read-write
    STATUS 	    current
    DESCRIPTION
       "The string value of the fifth field in the PPPoEIA CircuitID in ASCII format."
    ::= { alaPPPoEIAGlobalConfig 14 }

alaPPPoEIAGlobalCircuitIDDelimiter OBJECT-TYPE       
    SYNTAX	    OCTET STRING (SIZE (1))
    MAX-ACCESS 	    read-write
    STATUS 	    current
    DESCRIPTION
       "The value of the delimiter that is inserted between the fields in the PPPoEIA CircuitID in ASCII format. The allowed         delimiters are  ':', '|', '/', '\', '-', '_', ' ', '#', '.', ',' and ';'
        The default value of the delimiter is ':' "
    DEFVAL { ":" }
    ::= { alaPPPoEIAGlobalConfig 15 }


-- *******************************************************************
-- The PPPoE Intermediate Agent Remote Identifier object
-- *******************************************************************
alaPPPoEIAGlobalRemoteIDFormatType OBJECT-TYPE
    SYNTAX          INTEGER {
                    baseMac(1),
                    systemName(2),
                    mgntAddress(3),
                    userString(4)
                    }
    MAX-ACCESS      read-write
    STATUS          current
    DESCRIPTION
       "Defines the format type for the Remote Identifier."
    DEFVAL  { baseMac }
    ::= { alaPPPoEIAGlobalConfig 16 }

alaPPPoEIAGlobalRemoteIDStringValue OBJECT-TYPE
    SYNTAX          SnmpAdminString (SIZE (0..255))
    MAX-ACCESS      read-write
    STATUS          current
    DESCRIPTION
       "Defines the value of the string that will be used in Remote Identifier."
    ::= { alaPPPoEIAGlobalConfig 17 }

-- *******************************************************************
-- The Clear Statistics object
-- *******************************************************************

alaPPPoEIAGlobalClearStats OBJECT-TYPE
    SYNTAX          INTEGER {
                    default(1),
                    reset(2)
                    }
    MAX-ACCESS      read-write
    STATUS          current
    DESCRIPTION
       "Defines the global clear statistics control for PPPoE Intermediate Agent
        The value reset (1) indicates that clear all statistic counters."
    DEFVAL  { default }
    ::= { alaPPPoEIAGlobalConfig 18 }
	
-- ******************************************************************
-- The PPPoE Intermediate Agent Config Table
-- ******************************************************************

alaPPPoEIAPortConfigTable OBJECT-TYPE
    SYNTAX          SEQUENCE OF AlaPPPoEIAPortConfigEntry
    MAX-ACCESS      not-accessible
    STATUS          current
    DESCRIPTION
       "Defines the PPPoE Intermediate Agent port config table for providing, via SNMP, the
        capability of performing PPPoE Intermediate Agent operation."
    ::= { alaPPPoEIAMIBObjects 2 }

alaPPPoEIAPortConfigEntry OBJECT-TYPE
    SYNTAX          AlaPPPoEIAPortConfigEntry
    MAX-ACCESS      not-accessible
    STATUS          current
    DESCRIPTION
       "The Port Config table entry"
    INDEX { alaPPPoEIAPortConfigIfIndex  }
    ::= { alaPPPoEIAPortConfigTable 1 }

AlaPPPoEIAPortConfigEntry ::= SEQUENCE {
      alaPPPoEIAPortConfigIfIndex       InterfaceIndex,
      alaPPPoEIAPortConfigStatus        INTEGER,      
      alaPPPoEIAPortConfigTrustMode     INTEGER
    }

alaPPPoEIAPortConfigIfIndex OBJECT-TYPE
    SYNTAX          InterfaceIndex
    MAX-ACCESS      not-accessible
    STATUS          current
    DESCRIPTION
       "The ifIndex subindex identifying this instance."
    ::= { alaPPPoEIAPortConfigEntry 1 }

alaPPPoEIAPortConfigStatus OBJECT-TYPE
    SYNTAX          INTEGER {
                    enable(1),
                    disable(2)
                    }
    MAX-ACCESS      read-write
    STATUS          current
    DESCRIPTION
       "Indicates whether the PPPoE Intermediate Agent is enabled on the port."
    DEFVAL { disable }
    ::= { alaPPPoEIAPortConfigEntry 2 }

alaPPPoEIAPortConfigTrustMode OBJECT-TYPE
    SYNTAX          INTEGER {
                    client(1),
                    trusted(2)
                    }
    MAX-ACCESS      read-write
    STATUS          current
    DESCRIPTION
       "This allows user to configure the Trust Port."
    DEFVAL { client }
    ::= { alaPPPoEIAPortConfigEntry 3 }

-- ******************************************************************
-- PPPoE Intermediate Agent Stats Table
-- ******************************************************************

alaPPPoEIAStatsTable   OBJECT-TYPE
    SYNTAX          SEQUENCE OF AlaPPPoEIAStatsEntry
    MAX-ACCESS      not-accessible
    STATUS          current
    DESCRIPTION
       "This table contains the statistics of the tests performed for PPPoEIA."
    ::= { alaPPPoEIAMIBObjects 3 }

alaPPPoEIAStatsEntry   OBJECT-TYPE
    SYNTAX          AlaPPPoEIAStatsEntry
    MAX-ACCESS      not-accessible
    STATUS          current
    DESCRIPTION
       "The test result's stats table."
    INDEX { alaPPPoEIAStatsIfIndex }
    ::= { alaPPPoEIAStatsTable 1 }

AlaPPPoEIAStatsEntry ::= SEQUENCE {
    alaPPPoEIAStatsIfIndex                InterfaceIndex, 
    alaPPPoEIAStatsClearStats                  INTEGER,
    alaPPPoEIAStatsPADIRxCounter               Counter32,
    alaPPPoEIAStatsPADRRxCounter               Counter32,
    alaPPPoEIAStatsPADTRxCounter               Counter32,
    alaPPPoEIAStatsPADIRxDiscardCounter        Counter32,
    alaPPPoEIAStatsPADRRxDiscardCounter        Counter32,
    alaPPPoEIAStatsPADTRxDiscardCounter        Counter32,
    alaPPPoEIAStatsPADORxDiscardCounter        Counter32,
    alaPPPoEIAStatsPADSRxDiscardCounter        Counter32,
    alaPPPoEIAStatsPADSRxCounter               Counter32,
    alaPPPoEIAStatsPADORxCounter               Counter32
}

alaPPPoEIAStatsIfIndex OBJECT-TYPE
    SYNTAX          InterfaceIndex
    MAX-ACCESS      not-accessible
    STATUS          current
    DESCRIPTION
	"The ifindex of the port on which PPPoE Intermediate Agent is enabled."
    ::= { alaPPPoEIAStatsEntry 1 } 

alaPPPoEIAStatsClearStats   OBJECT-TYPE
    SYNTAX          INTEGER {
                    default(0),
                    reset(1)
                    }
    MAX-ACCESS read-write
    STATUS     current
    DESCRIPTION
        "Defines the clear statistics control for PPPoEIA for client ports.
         The value reset (1) indicates that clear all statistic counters."
    DEFVAL  { default }
    ::= { alaPPPoEIAStatsEntry 2 }

alaPPPoEIAStatsPADIRxCounter  OBJECT-TYPE
    SYNTAX          Counter32
    MAX-ACCESS      read-only
    STATUS          current
    DESCRIPTION
        "The number of the PPPoE Active Discovery Initiation Packets received on client ports."
    ::= { alaPPPoEIAStatsEntry 3 }

alaPPPoEIAStatsPADRRxCounter  OBJECT-TYPE
    SYNTAX          Counter32
    MAX-ACCESS      read-only
    STATUS          current
    DESCRIPTION
        "The number of the PPPoE Active Discovery Request Packets received on client ports."
    ::= { alaPPPoEIAStatsEntry 4 }

alaPPPoEIAStatsPADTRxCounter  OBJECT-TYPE
    SYNTAX          Counter32
    MAX-ACCESS      read-only
    STATUS          current
    DESCRIPTION
        "The number of the PPPoE Active Discovery Termination Packets received on client ports."
    ::= { alaPPPoEIAStatsEntry 5 }

alaPPPoEIAStatsPADIRxDiscardCounter  OBJECT-TYPE
    SYNTAX          Counter32
    MAX-ACCESS      read-only
    STATUS          current
    DESCRIPTION
        "The number of the PPPoE Active Discovery Initiation Packets received and discarded on client ports."
    ::= { alaPPPoEIAStatsEntry 6 }

alaPPPoEIAStatsPADRRxDiscardCounter  OBJECT-TYPE
    SYNTAX          Counter32
    MAX-ACCESS      read-only
    STATUS          current
    DESCRIPTION
        "The number of the PPPoE Active Discovery Request Packets received and discarded on client ports."
    ::= { alaPPPoEIAStatsEntry 7 }

alaPPPoEIAStatsPADTRxDiscardCounter  OBJECT-TYPE
    SYNTAX          Counter32
    MAX-ACCESS      read-only
    STATUS          current
    DESCRIPTION
        "The number of the PPPoE Active Discovery Termination Packets received and discarded on client ports."
    ::= { alaPPPoEIAStatsEntry 8 }

alaPPPoEIAStatsPADORxDiscardCounter  OBJECT-TYPE
    SYNTAX          Counter32
    MAX-ACCESS      read-only
    STATUS          current
    DESCRIPTION
        "The number of the PPPoE Active Discovery Offer Packets received and discarded on client ports."
    ::= { alaPPPoEIAStatsEntry 9 }


alaPPPoEIAStatsPADSRxDiscardCounter  OBJECT-TYPE
    SYNTAX          Counter32
    MAX-ACCESS      read-only
    STATUS          current
    DESCRIPTION
        "The number of the PPPoE Active Discovery Session Confirmation Packets received and discarded on client ports."
    ::= { alaPPPoEIAStatsEntry 10 }

alaPPPoEIAStatsPADSRxCounter  OBJECT-TYPE
    SYNTAX          Counter32
    MAX-ACCESS      read-only
    STATUS          current
    DESCRIPTION
        "The number of the PPPoE Active Discovery Session Confirmation Packets received and discarded on client ports."
    ::= { alaPPPoEIAStatsEntry 11 }


alaPPPoEIAStatsPADORxCounter  OBJECT-TYPE
    SYNTAX          Counter32
    MAX-ACCESS      read-only
    STATUS          current
    DESCRIPTION
        "The number of the PPPoE Active Discovery Session Confirmation Packets received and discarded on client ports."
    ::= { alaPPPoEIAStatsEntry 12 }

-- ******************************************************************
-- MIB Module Compliance statements
-- ****************************************************************** 

alaPPPoEIAMIBCompliance MODULE-COMPLIANCE
    STATUS          current
    DESCRIPTION
        "Compliance statement for PPPoE Intermediate Agent."
    MODULE
    MANDATORY-GROUPS
    {
         alaPPPoEIAGlobalConfigGroup,
         alaPPPoEIAPortConfigGroup,
         alaPPPoEIAStatsGroup   
    }
    ::= { alaPPPoEIAMIBCompliances 1 }

-- ******************************************************************
-- MIB Grouping - UNITS OF CONFORMANCE
-- ******************************************************************

alaPPPoEIAGlobalConfigGroup OBJECT-GROUP
    OBJECTS
    {
        alaPPPoEIAGlobalStatus,
        alaPPPoEIAGlobalAccessNodeIDFormatType,
        alaPPPoEIAGlobalAccessNodeIDStringValue,
        alaPPPoEIAGlobalCircuitIDFormatType,
        alaPPPoEIAGlobalCircuitIDField1,
        alaPPPoEIAGlobalCircuitIDField1StrVal,
        alaPPPoEIAGlobalCircuitIDField2,
        alaPPPoEIAGlobalCircuitIDField2StrVal,
        alaPPPoEIAGlobalCircuitIDField3,
        alaPPPoEIAGlobalCircuitIDField3StrVal,
        alaPPPoEIAGlobalCircuitIDField4,
        alaPPPoEIAGlobalCircuitIDField4StrVal,
        alaPPPoEIAGlobalCircuitIDField5,
        alaPPPoEIAGlobalCircuitIDField5StrVal,
        alaPPPoEIAGlobalCircuitIDDelimiter,
        alaPPPoEIAGlobalRemoteIDFormatType,
        alaPPPoEIAGlobalRemoteIDStringValue,
        alaPPPoEIAGlobalClearStats
    }
    STATUS          current
    DESCRIPTION
       "Collection of objects for the management of PPPoE Intermediate Agent Global configuration."
    ::={ alaPPPoEIAMIBGroups 1 }

alaPPPoEIAPortConfigGroup OBJECT-GROUP
    OBJECTS
    {
        alaPPPoEIAPortConfigStatus,      
        alaPPPoEIAPortConfigTrustMode
    }
    STATUS          current
    DESCRIPTION
       "Collection of objects for the PPPoE Intermediate Agent configuration."
    ::={ alaPPPoEIAMIBGroups 2 }

alaPPPoEIAStatsGroup OBJECT-GROUP
    OBJECTS
    {
        alaPPPoEIAStatsClearStats,
        alaPPPoEIAStatsPADIRxCounter,
        alaPPPoEIAStatsPADRRxCounter,
        alaPPPoEIAStatsPADTRxCounter,
        alaPPPoEIAStatsPADIRxDiscardCounter,
        alaPPPoEIAStatsPADRRxDiscardCounter,
        alaPPPoEIAStatsPADTRxDiscardCounter,
        alaPPPoEIAStatsPADORxDiscardCounter,
        alaPPPoEIAStatsPADSRxDiscardCounter,
        alaPPPoEIAStatsPADSRxCounter,
        alaPPPoEIAStatsPADORxCounter
    }
    STATUS          current
    DESCRIPTION
       "Collection of objects for the PPPoE Intermediate Agent statistics information."
    ::={ alaPPPoEIAMIBGroups 3 }
    
END

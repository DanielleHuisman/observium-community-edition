ALCATEL-IND1-IPMCAST-MIB DEFINITIONS ::= BEGIN

IMPORTS
    routingIND1Ipmrm                FROM ALCATEL-IND1-BASE
    MODULE-IDENTITY, OBJECT-TYPE,
    Unsigned32, Counter32,
    Counter64, Gauge32, TimeTicks    FROM SNMPv2-SMI
    RowStatus, StorageType,
    TimeStamp                        FROM SNMPv2-TC
    MODULE-COMPLIANCE, OBJECT-GROUP  FROM SNMPv2-CONF
    InterfaceIndexOrZero,
    InterfaceIndex                   FROM IF-MIB
    IANAipRouteProtocol,
    IANAipMRouteProtocol             FROM IANA-RTPROTO-MIB
    InetAddress, InetAddressType,
    InetAddressPrefixLength          FROM INET-ADDRESS-MIB;

alaIpMcastMIB MODULE-IDENTITY
    LAST-UPDATED "200707020000Z"
    ORGANIZATION "Alcatel - Architects of an Internet World" 
    CONTACT-INFO 
        "Please consult with Customer Service to insure the most appropriate
         version of this document is used with the products in question:

                 Alcatel-Lucent, Enterprise Solutions Division
                (Formerly Alcatel Internetworking, Incorporated)
                           26801 West Agoura Road
                        Agoura Hills, CA  91301-5122
                          United States Of America

        Telephone:               North America  +1 800 995 2696
                                 Latin America  +1 877 919 9526
                                 Europe         +31 23 556 0100
                                 Asia           +65 394 7933
                                 All Other      +1 818 878 4507

        Electronic Mail:         support@ind.alcatel.com
        World Wide Web:          http://alcatel-lucent.com/wps/portal/enterprise
        File Transfer Protocol:  ftp://ftp.ind.alcatel.com/pub/products/mibs"

    DESCRIPTION
        "This module describes an authoritative enterprise-specific Simple
         Network Management Protocol (SNMP) Management Information Base (MIB):

             This proprietary MIB contains management information for
             the IP Multicast function.  This MIB module contains information
             about IP Multicast routing, data forwarding, and data
             reception.  This MIB module is independent of the multicast
             protocol(s) and address type(s) that are in use.
             This MIB is based on the Internet Draft 
             <draft-ietf-mboned-ip-mcast-mib-02.txt> developed by
             the IETF MBONED Working Group.

         The right to make changes in specification and other information
         contained in this document without prior notice is reserved.

         No liability shall be assumed for any incidental, indirect, special, or
         consequential damages whatsoever arising from or related to this
         document or the information contained herein.

         Vendors, end-users, and other interested parties are granted
         non-exclusive license to use this specification in connection with
         management of the products for which it is intended to be used.

           Copyright (C) 1995-2007 Alcatel-Lucent
                         ALL RIGHTS RESERVED WORLDWIDE"

    REVISION     "200707020000Z" 
    DESCRIPTION
           "The latest version of this MIB Module."
    ::= { routingIND1Ipmrm 2 }

--
-- Top-level structure of the MIB
--

alaIpMcastMIBObjects OBJECT IDENTIFIER ::= { alaIpMcastMIB 1 }

alaIpMcast      OBJECT IDENTIFIER ::= { alaIpMcastMIBObjects 1 }

alaIpMcastEnable OBJECT-TYPE
    SYNTAX     INTEGER { enabled(1), disabled(2) }
    MAX-ACCESS read-write
    STATUS     current
    DESCRIPTION
            "The enabled status of IP Multicast function on this
            system."
    ::= { alaIpMcast 1 }

alaIpMcastRouteEntryCount OBJECT-TYPE
    SYNTAX     Gauge32
    MAX-ACCESS read-only
    STATUS     current
    DESCRIPTION
            "The number of rows in the alaIpMcastRouteTable.  This can be
            used to check for multicast routing activity, and to monitor
            the multicast routing table size."
    ::= { alaIpMcast 7 }

--
--  The Multicast Interface Table
--

alaIpMcastInterfaceTable OBJECT-TYPE
    SYNTAX     SEQUENCE OF IpMcastInterfaceEntry
    MAX-ACCESS not-accessible
    STATUS     current
    DESCRIPTION
            "The (conceptual) table used to manage the multicast
            protocol active on an interface."
    ::= { alaIpMcast 4 }

alaIpMcastInterfaceEntry OBJECT-TYPE
    SYNTAX     IpMcastInterfaceEntry
    MAX-ACCESS not-accessible
    STATUS     current
    DESCRIPTION
            "An entry (conceptual row) containing the multicast protocol
            information for a particular interface."
    INDEX      { alaIpMcastInterfaceIfIndex }
    ::= { alaIpMcastInterfaceTable 1 }

IpMcastInterfaceEntry ::= SEQUENCE {
    alaIpMcastInterfaceIfIndex          InterfaceIndex,
    alaIpMcastInterfaceTtl              Unsigned32,
    alaIpMcastInterfaceProtocol         IANAipMRouteProtocol,
    alaIpMcastInterfaceRateLimit        Unsigned32,
    alaIpMcastInterfaceInMcastOctets    Counter32,
    alaIpMcastInterfaceOutMcastOctets   Counter32,
    alaIpMcastInterfaceInMcastPkts      Counter32,
    alaIpMcastInterfaceOutMcastPkts     Counter32,
    alaIpMcastInterfaceHCInMcastOctets  Counter64,
    alaIpMcastInterfaceHCOutMcastOctets Counter64,
    alaIpMcastInterfaceHCInMcastPkts    Counter64,
    alaIpMcastInterfaceHCOutMcastPkts   Counter64
}

alaIpMcastInterfaceIfIndex OBJECT-TYPE
    SYNTAX     InterfaceIndex
    MAX-ACCESS not-accessible
    STATUS     current
    DESCRIPTION
            "The ifIndex value of the interface for which this entry
            contains information."
    ::= { alaIpMcastInterfaceEntry 1 }

alaIpMcastInterfaceTtl OBJECT-TYPE
    SYNTAX     Unsigned32 (0..255)
    MAX-ACCESS read-write
    STATUS     current
    DESCRIPTION
            "The datagram TTL threshold for the interface.  Any IP
            multicast datagrams with a TTL (IPv4) or Hop Limit (IPv6)
            less than this threshold will not be forwarded out the
            interface.  The default value of 0 means all multicast
            packets are forwarded out the interface."
    DEFVAL     { 0 }
    ::= { alaIpMcastInterfaceEntry 2 }

alaIpMcastInterfaceProtocol OBJECT-TYPE
    SYNTAX     IANAipMRouteProtocol
    MAX-ACCESS read-write
    STATUS     deprecated
    DESCRIPTION
            "The multicast protocol running on this interface.
            More than one multicast protocol can be used on an
            interface, so this object is ambiguous.  Use of this
            object is deprecated."
    ::= { alaIpMcastInterfaceEntry 3 }

alaIpMcastInterfaceRateLimit OBJECT-TYPE
    SYNTAX     Unsigned32 (0..2147483647)
    MAX-ACCESS read-write
    STATUS     current
    DESCRIPTION
            "The rate-limit, in kilobits per second, of forwarded
            multicast traffic on the interface.  A rate-limit of 0
            indicates that no rate limiting is done."
    DEFVAL     { 0 }
    ::= { alaIpMcastInterfaceEntry 4 }

alaIpMcastInterfaceInMcastOctets OBJECT-TYPE
    SYNTAX     Counter32
    MAX-ACCESS read-only
    STATUS     current
    DESCRIPTION
            "The number of octets of multicast packets that have arrived
            on the interface, including framing characters.  This object
            is similar to ifInOctets in the Interfaces MIB, except that
            only multicast packets are counted."
    ::= { alaIpMcastInterfaceEntry 5 }

alaIpMcastInterfaceOutMcastOctets OBJECT-TYPE
    SYNTAX     Counter32
    MAX-ACCESS read-only
    STATUS     current
    DESCRIPTION
            "The number of octets of multicast packets that have been
            sent on the interface."
    ::= { alaIpMcastInterfaceEntry 6 }

alaIpMcastInterfaceInMcastPkts OBJECT-TYPE
    SYNTAX     Counter32
    MAX-ACCESS read-only
    STATUS     current
    DESCRIPTION
            "The number of multicast packets that have arrived on the
            interface.  In many cases, this object is identical to
            ifInMulticastPkts in the Interfaces MIB.

            However, some implementations use ifXTable for Layer 2
            traffic statistics and alaIpMcastInterfaceTable at Layer 3.  In
            this case a difference between these objects probably
            indicates that some Layer 3 multicast packets are being
            transmitted as unicast at Layer 2."
    REFERENCE "RFC 2863 ifInMulticastPkts"
    ::= { alaIpMcastInterfaceEntry 7 }

alaIpMcastInterfaceOutMcastPkts OBJECT-TYPE
    SYNTAX     Counter32
    MAX-ACCESS read-only
    STATUS     current
    DESCRIPTION
            "The number of multicast packets that have been sent on the
            interface.  In many cases, this object is identical to
            ifOutMulticastPkts in the Interfaces MIB.

            However, some implementations use ifXTable for Layer 2
            traffic statistics and alaIpMcastInterfaceTable at Layer 3.  In
            this case a difference between these objects probably
            indicates that some Layer 3 multicast packets are being
            transmitted as unicast at Layer 2."
    REFERENCE "RFC 2863 ifOutMulticastPkts"
    ::= { alaIpMcastInterfaceEntry 8 }

alaIpMcastInterfaceHCInMcastOctets OBJECT-TYPE
    SYNTAX     Counter64
    MAX-ACCESS read-only
    STATUS     current
    DESCRIPTION
            "The number of octets of multicast packets that have arrived
            on the interface, including framing characters.  This object
            is a 64-bit version of alaIpMcastRouteInterfaceInMcastOctets.
            It is similar to ifHCInOctets in the Interfaces MIB, except
            that only multicast packets are counted."
    ::= { alaIpMcastInterfaceEntry 9 }

alaIpMcastInterfaceHCOutMcastOctets OBJECT-TYPE
    SYNTAX     Counter64
    MAX-ACCESS read-only
    STATUS     current
    DESCRIPTION
            "The number of octets of multicast packets that have been
            sent on the interface.  This object is a 64-bit version of
            alaIpMcastRouteInterfaceOutMcastOctets."
    ::= { alaIpMcastInterfaceEntry 10 }

alaIpMcastInterfaceHCInMcastPkts OBJECT-TYPE
    SYNTAX     Counter64
    MAX-ACCESS read-only
    STATUS     current
    DESCRIPTION
            "The number of multicast packets that have arrived on the
            interface.  In many cases, this object is identical to
            ifHCInMulticastPkts in the Interfaces MIB.

            However, some implementations use ifXTable for Layer 2
            traffic statistics and alaIpMcastInterfaceTable at Layer 3.  In
            this case a difference between these objects probably
            indicates that some Layer 3 multicast packets are being
            transmitted as unicast at Layer 2."
    REFERENCE "RFC 2863 ifHCInMulticastPkts"
    ::= { alaIpMcastInterfaceEntry 11 }

alaIpMcastInterfaceHCOutMcastPkts OBJECT-TYPE
    SYNTAX     Counter64
    MAX-ACCESS read-only
    STATUS     current
    DESCRIPTION
            "The number of multicast packets that have been sent on the
            interface.  In many cases, this object is identical to
            ifHCOutMulticastPkts in the Interfaces MIB.

            However, some implementations use ifXTable for Layer 2
            traffic statistics and alaIpMcastInterfaceTable at Layer 3.  In
            this case a difference between these objects probably
            indicates that some Layer 3 multicast packets are being
            transmitted as unicast at Layer 2."
    REFERENCE "RFC 2863 ifHCOutMulticastPkts"
    ::= { alaIpMcastInterfaceEntry 12 }

--
--  The IP Multicast Routing Table
--

alaIpMcastRouteTable OBJECT-TYPE
    SYNTAX     SEQUENCE OF IpMcastRouteEntry
    MAX-ACCESS not-accessible
    STATUS     current
    DESCRIPTION
            "The (conceptual) table containing multicast routing
            information for IP datagrams sent by particular sources to
            to the IP multicast groups known to this router."
    ::= { alaIpMcast 2 }

alaIpMcastRouteEntry OBJECT-TYPE
    SYNTAX     IpMcastRouteEntry
    MAX-ACCESS not-accessible
    STATUS     current
    DESCRIPTION
            "An entry (conceptual row) containing the multicast routing
            information for IP datagrams from a particular source and
            addressed to a particular IP multicast group address."
    INDEX      { alaIpMcastRouteGroupAddressType,
                 alaIpMcastRouteGroup,
                 alaIpMcastRouteGroupPrefixLength,
                 alaIpMcastRouteSourceAddressType,
                 alaIpMcastRouteSource,
                 alaIpMcastRouteSourcePrefixLength }
    ::= { alaIpMcastRouteTable 1 }

IpMcastRouteEntry ::= SEQUENCE {
    alaIpMcastRouteGroupAddressType      InetAddressType,
    alaIpMcastRouteGroup                 InetAddress,
    alaIpMcastRouteGroupPrefixLength     InetAddressPrefixLength,
    alaIpMcastRouteSourceAddressType     InetAddressType,
    alaIpMcastRouteSource                InetAddress,
    alaIpMcastRouteSourcePrefixLength    InetAddressPrefixLength,
    alaIpMcastRouteUpstreamNeighborType  InetAddressType,
    alaIpMcastRouteUpstreamNeighbor      InetAddress,
    alaIpMcastRouteInIfIndex             InterfaceIndexOrZero,
    alaIpMcastRouteTimeStamp             TimeStamp,
    alaIpMcastRouteExpiryTime            TimeTicks,
    alaIpMcastRoutePkts                  Counter32,
    alaIpMcastRouteDifferentInIfPackets  Counter32,
    alaIpMcastRouteOctets                Counter32,
    alaIpMcastRouteProtocol              IANAipMRouteProtocol,
    alaIpMcastRouteRtProtocol            IANAipRouteProtocol,
    alaIpMcastRouteRtAddressType         InetAddressType,
    alaIpMcastRouteRtAddress             InetAddress,
    alaIpMcastRouteRtPrefixLength        InetAddressPrefixLength,
    alaIpMcastRouteRtType                INTEGER,
    alaIpMcastRouteHCOctets              Counter64,
    alaIpMcastRouteDifferentInIfOctets   Counter32,
    alaIpMcastRouteTtlDropPackets        Counter32,
    alaIpMcastRouteTtlDropOctets         Counter32
}

alaIpMcastRouteGroupAddressType OBJECT-TYPE
    SYNTAX     InetAddressType
    MAX-ACCESS not-accessible
    STATUS     current
    DESCRIPTION
            "A value indicating the address family of the address
            contained in alaIpMcastRouteGroup.  Legal values correspond to
            the subset of address families for which multicast
            forwarding is supported."
    ::= { alaIpMcastRouteEntry 1 }

alaIpMcastRouteGroup OBJECT-TYPE
    SYNTAX     InetAddress (SIZE (0|4|8|16|20))
    MAX-ACCESS not-accessible
    STATUS     current
    DESCRIPTION
            "The IP multicast group address which, when combined with
            the corresponding value specified in
            alaIpMcastRouteGroupPrefixLength, identifies the groups for
            which this entry contains multicast routing information.

            This address object is only significant up to
            alaIpMcastRouteGroupPrefixLength bits.  The remainder of the
            address bits are zero.  This is especially important for
            this index field, which is part of the index of this entry.
            Any non-zero bits would signify an entirely different
            entry."
    ::= { alaIpMcastRouteEntry 2 }

alaIpMcastRouteGroupPrefixLength OBJECT-TYPE
    SYNTAX     InetAddressPrefixLength (4..128)
    MAX-ACCESS not-accessible
    STATUS     current
    DESCRIPTION
            "The length in bits of the mask which, when combined with
            the corresponding value of alaIpMcastRouteGroup, identifies the
            groups for which this entry contains multicast routing
            information."
    ::= { alaIpMcastRouteEntry 3 }

alaIpMcastRouteSourceAddressType OBJECT-TYPE
    SYNTAX     InetAddressType
    MAX-ACCESS not-accessible
    STATUS     current
    DESCRIPTION
            "A value indicating the address family of the address
            contained in alaIpMcastRouteSource.  The value MUST be the same
            as the value of alaIpMcastRouteGroupType."
    ::= { alaIpMcastRouteEntry 4 }

alaIpMcastRouteSource OBJECT-TYPE
    SYNTAX     InetAddress (SIZE (0|4|8|16|20))
    MAX-ACCESS not-accessible
    STATUS     current
    DESCRIPTION
            "The network address which, when combined with the
            corresponding value of alaIpMcastRouteSourcePrefixLength,
            identifies the sources for which this entry contains
            multicast routing information.

            This address object is only significant up to
            alaIpMcastRouteGroupPrefixLength bits.  The remainder of the
            address bits are zero.  This is especially important for
            this index field, which is part of the index of this entry.
            Any non-zero bits would signify an entirely different
            entry."
    ::= { alaIpMcastRouteEntry 5 }

alaIpMcastRouteSourcePrefixLength OBJECT-TYPE
    SYNTAX     InetAddressPrefixLength (4..128)
    MAX-ACCESS not-accessible
    STATUS     current
    DESCRIPTION
            "The length in bits of the mask which, when combined with
            the corresponding value of alaIpMcastRouteSource, identifies
            the sources for which this entry contains multicast routing
            information."
    ::= { alaIpMcastRouteEntry 6 }

alaIpMcastRouteUpstreamNeighborType OBJECT-TYPE
    SYNTAX     InetAddressType
    MAX-ACCESS read-only
    STATUS     current
    DESCRIPTION
            "A value indicating the address family of the address
            contained in alaIpMcastRouteUpstreamNeighbor.  The value MUST
            be the same as the value of alaIpMcastRouteGroupType."
    ::= { alaIpMcastRouteEntry 7 }

alaIpMcastRouteUpstreamNeighbor OBJECT-TYPE
    SYNTAX     InetAddress
    MAX-ACCESS read-only
    STATUS     current
    DESCRIPTION
            "The address of the upstream neighbor (for example, RPF
            neighbor) from which IP datagrams from these sources to
            this multicast address are received.  If the upstream
            neighbor is unknown, then alaIpMcastRouteUpstreamNeighbor
            will be 0.0.0.0 in the case of an IPv4 entry, and
            0:0:0:0:0:0:0:0 in the case of an IPv6 entry (for example,
            in BIDIR-PIM)."
    ::= { alaIpMcastRouteEntry 8 }

alaIpMcastRouteInIfIndex OBJECT-TYPE
    SYNTAX     InterfaceIndexOrZero
    MAX-ACCESS read-only
    STATUS     current
    DESCRIPTION
            "The value of ifIndex for the interface on which IP
            datagrams sent by these sources to this multicast address
            are received.  A value of 0 indicates that datagrams are not
            subject to an incoming interface check, but may be accepted
            on multiple interfaces (for example, in BIDIR-PIM)."
    ::= { alaIpMcastRouteEntry 9 }

alaIpMcastRouteTimeStamp OBJECT-TYPE
    SYNTAX     TimeStamp
    MAX-ACCESS read-only
    STATUS     current
    DESCRIPTION
            "The value of sysUpTime at which the multicast routing
            information represented by this entry was learned by the
            router."
    ::= { alaIpMcastRouteEntry 10 }

alaIpMcastRouteExpiryTime OBJECT-TYPE
    SYNTAX     TimeTicks
    MAX-ACCESS read-only
    STATUS     current
    DESCRIPTION
            "The minimum amount of time remaining before this entry will
            be aged out.  The value 0 indicates that the entry is not
            subject to aging.  If alaIpMcastRouteNextHopState is pruned(1),
            this object represents the remaining time until the prune
            expires. If this timer expires, state reverts to
            forwarding(2). Otherwise, this object represents the time
            until this entry is removed from the table."
    ::= { alaIpMcastRouteEntry 11 }

alaIpMcastRoutePkts OBJECT-TYPE
    SYNTAX     Counter32
    MAX-ACCESS read-only
    STATUS     current
    DESCRIPTION
            "The number of packets routed using this multicast route
            entry.

            Discontinuities in this monotonically increasing value
            occur at re-initialization of the management system.
            Discontinuities can also occur as a result of routes being
            removed and replaced, which can be detected by observing
            the value of alaIpMcastRouteTimeStamp."
    ::= { alaIpMcastRouteEntry 12 }

alaIpMcastRouteDifferentInIfPackets OBJECT-TYPE
    SYNTAX     Counter32
    MAX-ACCESS read-only
    STATUS     current
    DESCRIPTION
            "The number of packets which this router has received from
            these sources and addressed to this multicast group address,
            which were dropped because they were received on an
            unexpected interface.

            For RPF checking protocols (such as PIM-SM), these packets
            arrived on interfaces other than alaIpMcastRouteInIfIndex, and
            were dropped because of this failed RPF check.  (RPF paths
            are 'Reverse Path Forwarding' path; the unicast routes to
            the expected origin of multicast data flows).

            Other protocols may drop packets on an incoming interface
            check for different reasons (for example, BIDIR-PIM performs
            a DF check on receipt of packets).  All packets dropped as a
            result of an incoming interface check are counted here.

            If this counter increases rapidly, this indicates a problem.
            A significant quantity of multicast data is arriving at this
            router on unexpected interfaces, and is not being forwarded.
            For guidance, if the rate of increase of this counter
            exceeds 1% of the rate of increase of alaIpMcastRoutePkts, then
            there are multicast routing problems that require
            investigation.

            Discontinuities in this monotonically increasing value
            occur at re-initialization of the management system.
            Discontinuities can also occur as a result of routes being
            removed and replaced, which can be detected by observing
            the value of alaIpMcastRouteTimeStamp."
    ::= { alaIpMcastRouteEntry 13 }

alaIpMcastRouteOctets OBJECT-TYPE
    SYNTAX     Counter32
    MAX-ACCESS read-only
    STATUS     current
    DESCRIPTION
            "The number of octets contained in IP datagrams which were
            received from these sources and addressed to this multicast
            group address, and which were forwarded by this router.

            Discontinuities in this monotonically increasing value
            occur at re-initialization of the management system.
            Discontinuities can also occur as a result of routes being
            removed and replaced, which can be detected by observing
            the value of alaIpMcastRouteTimeStamp."
    ::= { alaIpMcastRouteEntry 14 }

alaIpMcastRouteProtocol OBJECT-TYPE
    SYNTAX     IANAipMRouteProtocol
    MAX-ACCESS read-only
    STATUS     current
    DESCRIPTION
            "The multicast routing protocol via which this multicast
            forwarding entry was learned."
    ::= { alaIpMcastRouteEntry 15 }

alaIpMcastRouteRtProtocol OBJECT-TYPE
    SYNTAX     IANAipRouteProtocol
    MAX-ACCESS read-only
    STATUS     current
    DESCRIPTION
            "The routing mechanism via which the route used to find the
            upstream or parent interface for this multicast forwarding
            entry was learned.  Inclusion of values for routing
            protocols is not intended to imply that those protocols need
            be supported."
    ::= { alaIpMcastRouteEntry 16 }

alaIpMcastRouteRtAddressType OBJECT-TYPE
    SYNTAX     InetAddressType
    MAX-ACCESS read-only
    STATUS     current
    DESCRIPTION
            "A value indicating the address family of the address
            contained in alaIpMcastRouteRtAddress.  The value MUST be the
            same as the value of alaIpMcastRouteGroupType."
    ::= { alaIpMcastRouteEntry 17 }

alaIpMcastRouteRtAddress OBJECT-TYPE
    SYNTAX     InetAddress
    MAX-ACCESS read-only
    STATUS     current
    DESCRIPTION
            "The address portion of the route used to find the upstream
            or parent interface for this multicast forwarding entry.

            This address object is only significant up to
            alaIpMcastRouteGroupPrefixLength bits.  The remainder of the
            address bits are zero."
    ::= { alaIpMcastRouteEntry 18 }

alaIpMcastRouteRtPrefixLength OBJECT-TYPE
    SYNTAX     InetAddressPrefixLength (4..128)
    MAX-ACCESS read-only
    STATUS     current
    DESCRIPTION
            "The length in bits of the mask associated with the route
            used to find the upstream or parent interface for this
            multicast forwarding entry."
    ::= { alaIpMcastRouteEntry 19 }

alaIpMcastRouteRtType OBJECT-TYPE
    SYNTAX     INTEGER {
                unicast (1),  -- Unicast route used in multicast RIB
                multicast (2) -- Multicast route
               }
    MAX-ACCESS read-only
    STATUS     current
    DESCRIPTION
            "The reason the given route was placed in the (logical)
            multicast Routing Information Base (RIB).  A value of
            unicast means that the route would normally be placed only
            in the unicast RIB, but was placed in the multicast RIB
            (instead or in addition) due to local configuration, such as
            when running PIM over RIP.  A value of multicast means that
            the route was explicitly added to the multicast RIB by the
            routing protocol, such as DVMRP or Multiprotocol BGP."
    ::= { alaIpMcastRouteEntry 20 }

alaIpMcastRouteHCOctets OBJECT-TYPE
    SYNTAX     Counter64
    MAX-ACCESS read-only
    STATUS     current
    DESCRIPTION
            "The number of octets contained in IP datagrams which were
            received from these sources and addressed to this multicast
            group address, and which were forwarded by this router.
            This object is a 64-bit version of alaIpMcastRouteOctets.

            Discontinuities in this monotonically increasing value
            occur at re-initialization of the management system.
            Discontinuities can also occur as a result of routes being
            removed and replaced, which can be detected by observing
            the value of alaIpMcastRouteTimeStamp."
    ::= { alaIpMcastRouteEntry 21 }

alaIpMcastRouteDifferentInIfOctets OBJECT-TYPE
    SYNTAX     Counter32
    MAX-ACCESS read-only
    STATUS     current
    DESCRIPTION
            "The number of octets contained in IP datagrams which this
            router has received from these sources and addressed to this
            multicast group address, which were dropped because they
            were received on an unexpected interface.

            For RPF checking protocols (such as PIM-SM), these packets
            arrived on interfaces other than alaIpMcastRouteInIfIndex, and
            were dropped because of this failed RPF check.  (RPF paths
            are 'Reverse Path Forwarding' path; the unicast routes to
            the expected origin of multicast data flows).

            Other protocols may drop packets on an incoming interface
            check for different reasons (for example, BIDIR-PIM performs
            a DF check on receipt of packets).  All packets dropped as a
            result of an incoming interface check are counted here.

            If this counter increases rapidly, this indicates a problem.
            A significant quantity of multicast data is arriving at this
            router on unexpected interfaces, and is not being forwarded.

            For guidance, if the rate of increase of this counter
            exceeds 1% of the rate of increase of alaIpMcastRouteOctets,
            then there are multicast routing problems that require
            investigation.

            Discontinuities in this monotonically increasing value
            occur at re-initialization of the management system.
            Discontinuities can also occur as a result of routes being
            removed and replaced, which can be detected by observing
            the value of alaIpMcastRouteTimeStamp."
    ::= { alaIpMcastRouteEntry 22 }

alaIpMcastRouteTtlDropPackets OBJECT-TYPE
    SYNTAX     Counter32
    MAX-ACCESS read-only
    STATUS     current
    DESCRIPTION
            "The number of packets which this router has received from
            these sources and addressed to this multicast group address,
            which were dropped because the TTL (IPv4) or Hop Limit
            (IPv6) was decremented to zero, or to a value less than
            alaIpMcastInterfaceTtl for all next hops.

            Discontinuities in this monotonically increasing value
            occur at re-initialization of the management system.
            Discontinuities can also occur as a result of routes being
            removed and replaced, which can be detected by observing
            the value of alaIpMcastRouteTimeStamp."
    ::= { alaIpMcastRouteEntry 23 }

alaIpMcastRouteTtlDropOctets OBJECT-TYPE
    SYNTAX     Counter32
    MAX-ACCESS read-only
    STATUS     current
    DESCRIPTION
            "The number of octets contained in IP datagrams which this
            router has received from these sources and addressed to this
            multicast group address, which were dropped because the TTL
            (IPv4) or Hop Limit (IPv6) was decremented to zero, or to a
            value less than alaIpMcastInterfaceTtl for all next hops.

            Discontinuities in this monotonically increasing value
            occur at re-initialization of the management system.
            Discontinuities can also occur as a result of routes being
            removed and replaced, which can be detected by observing
            the value of alaIpMcastRouteTimeStamp."
    ::= { alaIpMcastRouteEntry 24 }

--
--  The IP Multicast Routing Next Hop Table
--

alaIpMcastRouteNextHopTable OBJECT-TYPE
    SYNTAX     SEQUENCE OF IpMcastRouteNextHopEntry
    MAX-ACCESS not-accessible
    STATUS     current
    DESCRIPTION
            "The (conceptual) table containing information on the
            next-hops on outgoing interfaces for routing IP multicast
            datagrams.  Each entry is one of a list of next-hops on
            outgoing interfaces for particular sources sending to a
            particular multicast group address."
    ::= { alaIpMcast 3 }

alaIpMcastRouteNextHopEntry OBJECT-TYPE
    SYNTAX     IpMcastRouteNextHopEntry
    MAX-ACCESS not-accessible
    STATUS     current
    DESCRIPTION
            "An entry (conceptual row) in the list of next-hops on
            outgoing interfaces to which IP multicast datagrams from
            particular sources to an IP multicast group address are
            routed."
    INDEX      { alaIpMcastRouteNextHopGroupAddressType,
                 alaIpMcastRouteNextHopGroup,
                 alaIpMcastRouteNextHopSourceAddressType,
                 alaIpMcastRouteNextHopSource,
                 alaIpMcastRouteNextHopSourcePrefixLength,
                 alaIpMcastRouteNextHopIfIndex,
                 alaIpMcastRouteNextHopAddressType,
                 alaIpMcastRouteNextHopAddress }
    ::= { alaIpMcastRouteNextHopTable 1 }

IpMcastRouteNextHopEntry ::= SEQUENCE {
    alaIpMcastRouteNextHopGroupAddressType    InetAddressType,
    alaIpMcastRouteNextHopGroup               InetAddress,
    alaIpMcastRouteNextHopSourceAddressType   InetAddressType,
    alaIpMcastRouteNextHopSource              InetAddress,
    alaIpMcastRouteNextHopSourcePrefixLength  InetAddressPrefixLength,
    alaIpMcastRouteNextHopIfIndex             InterfaceIndex,
    alaIpMcastRouteNextHopAddressType         InetAddressType,
    alaIpMcastRouteNextHopAddress             InetAddress,
    alaIpMcastRouteNextHopState               INTEGER,
    alaIpMcastRouteNextHopTimeStamp           TimeStamp,
    alaIpMcastRouteNextHopExpiryTime          TimeTicks,
    alaIpMcastRouteNextHopClosestMemberHops   Unsigned32,
    alaIpMcastRouteNextHopProtocol            IANAipMRouteProtocol,
    alaIpMcastRouteNextHopPkts                Counter32,
    alaIpMcastRouteNextHopOctets              Counter32
}

alaIpMcastRouteNextHopGroupAddressType OBJECT-TYPE
    SYNTAX     InetAddressType
    MAX-ACCESS not-accessible
    STATUS     current
    DESCRIPTION
            "A value indicating the address family of the address
            contained in alaIpMcastRouteNextHopGroup.  Legal values
            correspond to the subset of address families for which
            multicast forwarding is supported."
    ::= { alaIpMcastRouteNextHopEntry 1 }

alaIpMcastRouteNextHopGroup OBJECT-TYPE
    SYNTAX     InetAddress (SIZE (0|4|8|16|20))
    MAX-ACCESS not-accessible
    STATUS     current
    DESCRIPTION
            "The IP multicast group for which this entry specifies a
            next-hop on an outgoing interface."
    ::= { alaIpMcastRouteNextHopEntry 2 }

alaIpMcastRouteNextHopSourceAddressType OBJECT-TYPE
    SYNTAX     InetAddressType
    MAX-ACCESS not-accessible
    STATUS     current
    DESCRIPTION
            "A value indicating the address family of the address
            contained in alaIpMcastRouteNextHopSource.  The value MUST be
            the same as the value of alaIpMcastRouteNextHopGroupType."
    ::= { alaIpMcastRouteNextHopEntry 3 }

alaIpMcastRouteNextHopSource OBJECT-TYPE
    SYNTAX     InetAddress (SIZE (0|4|8|16|20))
    MAX-ACCESS not-accessible
    STATUS     current
    DESCRIPTION
            "The network address which, when combined with the
            corresponding value of the mask specified in
            alaIpMcastRouteNextHopSourcePrefixLength, identifies the
            sources for which this entry specifies a next-hop on an
            outgoing interface.

            This address object is only significant up to
            alaIpMcastRouteNextHopSourcePrefixLength bits.  The remainder
            of the address bits are zero.  This is especially important
            for this index field, which is part of the index of this
            entry.  Any non-zero bits would signify an entirely
            different entry."
    ::= { alaIpMcastRouteNextHopEntry 4 }

alaIpMcastRouteNextHopSourcePrefixLength OBJECT-TYPE
    SYNTAX     InetAddressPrefixLength (4..128)
    MAX-ACCESS not-accessible
    STATUS     current
    DESCRIPTION
            "The length in bits of the mask which, when combined with
            the corresponding value specified in
            alaIpMcastRouteNextHopSource, identifies the sources for which
            this entry specifies a next-hop on an outgoing interface."
    ::= { alaIpMcastRouteNextHopEntry 5 }

alaIpMcastRouteNextHopIfIndex OBJECT-TYPE
    SYNTAX     InterfaceIndex
    MAX-ACCESS not-accessible
    STATUS     current
    DESCRIPTION
            "The ifIndex value of the interface for the outgoing
            interface for this next-hop."
    ::= { alaIpMcastRouteNextHopEntry 6 }

alaIpMcastRouteNextHopAddressType OBJECT-TYPE
    SYNTAX     InetAddressType
    MAX-ACCESS not-accessible
    STATUS     current
    DESCRIPTION
            "A value indicating the address family of the address
            contained in alaIpMcastRouteNextHopAddress.  The value MUST be
            the same as the value of alaIpMcastRouteNextHopGroupType."
    ::= { alaIpMcastRouteNextHopEntry 7 }

alaIpMcastRouteNextHopAddress OBJECT-TYPE
    SYNTAX     InetAddress (SIZE (0|4|8|16|20))
    MAX-ACCESS not-accessible
    STATUS     current
    DESCRIPTION
            "The address of the next-hop specific to this entry.  For
            most interfaces, this is identical to
            alaIpMcastRouteNextHopGroup.  NBMA interfaces, however, may
            have multiple next-hop addresses out a single outgoing
            interface."
    ::= { alaIpMcastRouteNextHopEntry 8 }

alaIpMcastRouteNextHopState OBJECT-TYPE
    SYNTAX     INTEGER { pruned(1), forwarding(2) }
    MAX-ACCESS read-only
    STATUS     current
    DESCRIPTION
            "An indication of whether the outgoing interface and next-
            hop represented by this entry is currently being used to
            forward IP datagrams.  The value 'forwarding' indicates it
            is currently being used; the value 'pruned' indicates it is
            not."
    ::= { alaIpMcastRouteNextHopEntry 9 }

alaIpMcastRouteNextHopTimeStamp OBJECT-TYPE
    SYNTAX     TimeStamp
    MAX-ACCESS read-only
    STATUS     current
    DESCRIPTION
            "The value of sysUpTime at which the multicast routing
            information represented by this entry was learned by the
            router."
    ::= { alaIpMcastRouteNextHopEntry 10 }

alaIpMcastRouteNextHopExpiryTime OBJECT-TYPE
    SYNTAX     TimeTicks
    MAX-ACCESS read-only
    STATUS     current
    DESCRIPTION
            "The minimum amount of time remaining before this entry will
            be aged out.  If alaIpMcastRouteNextHopState is pruned(1), the
            remaining time until the prune expires and the state reverts
            to forwarding(2).  Otherwise, the remaining time until this
            entry is removed from the table.  The time remaining may be
            copied from alaIpMcastRouteExpiryTime if the protocol in use
            for this entry does not specify next-hop timers.  The value
            0 indicates that the entry is not subject to aging."
    ::= { alaIpMcastRouteNextHopEntry 11 }

alaIpMcastRouteNextHopClosestMemberHops OBJECT-TYPE
    SYNTAX     Unsigned32 (0..255)
    MAX-ACCESS read-only
    STATUS     current
    DESCRIPTION
            "The minimum number of hops between this router and any
            member of this IP multicast group reached via this next-hop
            on this outgoing interface.  Any IP multicast datagrams for
            the group which have a TTL (IPv4) or Hop Count (IPv6) less
            than this number of hops will not be forwarded to this
            next-hop.

            This is an optimization applied by multicast routing
            protocols that explicitly track hop counts to downstream
            listeners.  Multicast protocols that are not aware of hop
            counts to downstream listeners set this object to zero."
    ::= { alaIpMcastRouteNextHopEntry 12 }

alaIpMcastRouteNextHopProtocol OBJECT-TYPE
    SYNTAX     IANAipMRouteProtocol
    MAX-ACCESS read-only
    STATUS     current
    DESCRIPTION
            "The routing mechanism via which this next-hop was learned."
    ::= { alaIpMcastRouteNextHopEntry 13 }

alaIpMcastRouteNextHopPkts OBJECT-TYPE
    SYNTAX     Counter32
    MAX-ACCESS read-only
    STATUS     current
    DESCRIPTION
            "The number of packets which have been forwarded using this
            route.

            Discontinuities in this monotonically increasing value
            occur at re-initialization of the management system.
            Discontinuities can also occur as a result of routes being
            removed and replaced, which can be detected by observing
            the value of alaIpMcastRouteNextHopTimeStamp."
    ::= { alaIpMcastRouteNextHopEntry 14 }

alaIpMcastRouteNextHopOctets OBJECT-TYPE
    SYNTAX     Counter32
    MAX-ACCESS read-only
    STATUS     current
    DESCRIPTION
            "The number of octets of multicast packets that have been
            forwarded using this route.

            Discontinuities in this monotonically increasing value
            occur at re-initialization of the management system.
            Discontinuities can also occur as a result of routes being
            removed and replaced, which can be detected by observing
            the value of alaIpMcastRouteNextHopTimeStamp."
    ::= { alaIpMcastRouteNextHopEntry 15 }

--
--  The IP Multicast Scope Boundary Table
--

alaIpMcastBoundaryTable OBJECT-TYPE
    SYNTAX     SEQUENCE OF IpMcastBoundaryEntry
    MAX-ACCESS not-accessible
    STATUS     current
    DESCRIPTION
            "The (conceptual) table listing the system's multicast scope
            zone boundaries."
    REFERENCE "RFC 4007 section 5"
    ::= { alaIpMcast 5 }

alaIpMcastBoundaryEntry OBJECT-TYPE
    SYNTAX     IpMcastBoundaryEntry
    MAX-ACCESS not-accessible
    STATUS     current
    DESCRIPTION
            "An entry (conceptual row) describing one of this device's
            multicast scope zone boundaries."
    REFERENCE "RFC 2365 section 5, RFC 4007 section 5"
    INDEX      { alaIpMcastBoundaryIfIndex,
                 alaIpMcastBoundaryAddressType,
                 alaIpMcastBoundaryAddress,
                 alaIpMcastBoundaryAddressPrefixLength }
    ::= { alaIpMcastBoundaryTable 1 }

IpMcastBoundaryEntry ::= SEQUENCE {
    alaIpMcastBoundaryIfIndex              InterfaceIndex,
    alaIpMcastBoundaryAddressType          InetAddressType,
    alaIpMcastBoundaryAddress              InetAddress,
    alaIpMcastBoundaryAddressPrefixLength  InetAddressPrefixLength,
    alaIpMcastBoundaryStatus               RowStatus,
    alaIpMcastBoundaryStorageType          StorageType,
    alaIpMcastBoundaryDroppedMcastOctets   Counter32,
    alaIpMcastBoundaryDroppedMcastPkts     Counter32,
    alaIpMcastBoundaryHCDroppedMcastOctets Counter64,
    alaIpMcastBoundaryHCDroppedMcastPkts   Counter64
}

alaIpMcastBoundaryIfIndex OBJECT-TYPE
    SYNTAX     InterfaceIndex
    MAX-ACCESS not-accessible
    STATUS     current
    DESCRIPTION
            "The IfIndex value for the interface to which this boundary
            applies.  Packets with a destination address in the
            associated address/mask range will not be forwarded over
            this interface.

            For IPv4, zone boundaries cut through links.  Therefore this
            is an external interface.  This may be either a physical or
            virtual interface (tunnel, encapsulation, and so forth.)

            For IPv6, zone boundaries cut through nodes.  Therefore this
            is a virtual interface within the node.  This is not an
            external interface, either real or virtual.  Packets
            crossing this interface neither arrive at nor leave the
            node, but only move between zones within the node."
    REFERENCE "RFC 2365 section 5, RFC 4007 section 5"
    ::= { alaIpMcastBoundaryEntry 1 }

alaIpMcastBoundaryAddressType OBJECT-TYPE
    SYNTAX     InetAddressType
    MAX-ACCESS not-accessible
    STATUS     current
    DESCRIPTION
            "A value indicating the address family of the address
            contained in alaIpMcastBoundaryAddress.  Legal values
            correspond to the subset of address families for which
            multicast forwarding is supported."
    ::= { alaIpMcastBoundaryEntry 2 }

alaIpMcastBoundaryAddress OBJECT-TYPE
    SYNTAX     InetAddress (SIZE (0|4|8|16|20))
    MAX-ACCESS not-accessible
    STATUS     current
    DESCRIPTION
            "The group address which, when combined with the
            corresponding value of alaIpMcastBoundaryAddressPrefixLength,
            identifies the group range for which the scoped boundary
            exists.  Scoped IPv4 multicast address ranges must be
            prefixed by 239.0.0.0/4.  Scoped IPv6 multicast address
            ranges are FF0x::/16, where x is a valid RFC 4291 multicast
            scope.

            An IPv6 address prefixed by FF1x::/16 is a non-permanently-
            assigned address.  An IPv6 address prefixed by FF3x::/16 is
            a unicast-prefix based multicast addresses.  A zone boundary
            for FF0x::/16 implies an identical boundary for these other
            prefixes.  No separate FF1x::/16 or FF3x::/16 entries exist
            in this table.

            This address object is only significant up to
            alaIpMcastBoundaryAddressPrefixLength bits.  The remainder of
            the address bits are zero.  This is especially important for
            this index field, which is part of the index of this entry.
            Any non-zero bits would signify an entirely different
            entry."
    REFERENCE "RFC 2365, RFC 3306 section 4, RFC 4291 section 2.7"
    ::= { alaIpMcastBoundaryEntry 3 }

alaIpMcastBoundaryAddressPrefixLength OBJECT-TYPE
    SYNTAX     InetAddressPrefixLength (4..32)
    MAX-ACCESS not-accessible
    STATUS     current
    DESCRIPTION
            "The length in bits of the mask which when, combined with
            the corresponding value of alaIpMcastBoundaryAddress,
            identifies the group range for which the scoped boundary
            exists.

            The InetAddressType is given by alaIpMcastBoundaryAddressType.
            For 'ipv4' this object must be in the range 4..32.  For
            'ipv6', this object must be 32."
    ::= { alaIpMcastBoundaryEntry 4 }

alaIpMcastBoundaryStatus OBJECT-TYPE
    SYNTAX     RowStatus
    MAX-ACCESS read-create
    STATUS     current
    DESCRIPTION
            "The status of this row, by which rows in this table can
            be created and destroyed.

            This status object can be set to active(1) without setting
            any other columnar objects in this entry.

            All writeable objects in this entry can be modified when the
            status of this entry is active(1)."
    ::= { alaIpMcastBoundaryEntry 5 }

alaIpMcastBoundaryStorageType OBJECT-TYPE
    SYNTAX      StorageType
    MAX-ACCESS  read-create
    STATUS      current
    DESCRIPTION
           "The storage type for this row.  Rows having the value
           'permanent' need not allow write-access to any columnar
           objects in the row."
       DEFVAL { nonVolatile }
    ::= { alaIpMcastBoundaryEntry 6 }

alaIpMcastBoundaryDroppedMcastOctets OBJECT-TYPE
    SYNTAX     Counter32
    MAX-ACCESS read-only
    STATUS     current
    DESCRIPTION
            "The number of octets of multicast packets that have been
            dropped as a result of this zone boundary configuration."
    ::= { alaIpMcastBoundaryEntry 7 }

alaIpMcastBoundaryDroppedMcastPkts OBJECT-TYPE
    SYNTAX     Counter32
    MAX-ACCESS read-only
    STATUS     current
    DESCRIPTION
            "The number of multicast packets that have been dropped as a
            result of this zone boundary configuration."
    ::= { alaIpMcastBoundaryEntry 8 }

alaIpMcastBoundaryHCDroppedMcastOctets OBJECT-TYPE
    SYNTAX     Counter64
    MAX-ACCESS read-only
    STATUS     current
    DESCRIPTION
            "The number of octets of multicast packets that have been
            dropped as a result of this zone boundary configuration.

            This object is a 64-bit version of
            alaIpMcastBoundaryDroppedMcastOctets."
    ::= { alaIpMcastBoundaryEntry 9 }

alaIpMcastBoundaryHCDroppedMcastPkts OBJECT-TYPE
    SYNTAX     Counter64
    MAX-ACCESS read-only
    STATUS     current
    DESCRIPTION
            "The number of multicast packets that have been dropped as a
            result of this zone boundary configuration.

            This object is a 64-bit version of
            alaIpMcastBoundaryDroppedMcastPkts."
    ::= { alaIpMcastBoundaryEntry 10 }

--
-- Conformance information
--

alaIpMcastMIBConformance
                  OBJECT IDENTIFIER ::= { alaIpMcastMIB 2 }
alaIpMcastMIBCompliances
                  OBJECT IDENTIFIER ::= { alaIpMcastMIBConformance 1 }
alaIpMcastMIBGroups  OBJECT IDENTIFIER ::= { alaIpMcastMIBConformance 2 }

--
-- Compliance statements
--

alaIpMcastMIBCompliance MODULE-COMPLIANCE
    STATUS  current
    DESCRIPTION
            "Implementations of all the mandatory MIB groups listed
            below can claim full compliance.

            This MIB contains several InetAddressType and InetAddress
            objects, but not all IP address types are supported by all
            protocol implementations.

            A MIB implementation can claim full compliance if all IP
            address types supported by the protocol implementation are
            supported by the MIB implementation."

    MODULE  -- this module
    MANDATORY-GROUPS { alaIpMcastMIBBasicGroup }

        OBJECT      alaIpMcastEnable
        MIN-ACCESS  read-only
        DESCRIPTION
           "Write access is not required."

      GROUP   alaIpMcastMIBRouteGroup
      DESCRIPTION
          "This group is mandatory if the system is a router."

        OBJECT      alaIpMcastInterfaceTtl
        MIN-ACCESS  read-only
        DESCRIPTION
           "Write access is not required."

        OBJECT      alaIpMcastInterfaceRateLimit
        MIN-ACCESS  read-only
        DESCRIPTION
           "Write access is not required."

      GROUP   alaIpMcastMIBHopCountGroup
      DESCRIPTION
          "This group is optional."

      GROUP   alaIpMcastMIBPktsOutGroup
      DESCRIPTION
          "This group is optional."

      GROUP   alaIpMcastMIBHCInterfaceGroup
      DESCRIPTION
          "This group is mandatory only for those network interfaces
          for which the value of the corresponding instance of ifSpeed
          is greater than 20,000,000 bits/second."

      GROUP   alaIpMcastMIBRouteProtoGroup
      DESCRIPTION
          "This group is mandatory if the system is a router."

      GROUP   alaIpMcastMIBBoundaryIfGroup
      DESCRIPTION
          "This group is mandatory if the system is a router that
          supports administratively-scoped multicast address
          boundaries."

        OBJECT      alaIpMcastBoundaryStatus
        MIN-ACCESS  read-only
        DESCRIPTION
            "Write access is not required."

      GROUP   alaIpMcastMIBIfPktsGroup
      DESCRIPTION
          "This group is optional."

      GROUP   alaIpMcastMIBRouteOctetsGroup
      DESCRIPTION
          "This group is optional."

    ::= { alaIpMcastMIBCompliances 1 }

alaIpMcastMIBMRouteCompliance MODULE-COMPLIANCE
    STATUS  deprecated
    DESCRIPTION
            "Implementations of this compliance statement are equivalent
            to compliance with the deprecated IPMROUTE-MIB module."

    MODULE  -- this module
    MANDATORY-GROUPS { alaIpMcastMIBMRouteBasicGroup }

    ::= { alaIpMcastMIBCompliances 2 }
--
-- Units of conformance
--
alaIpMcastMIBMRouteBasicGroup OBJECT-GROUP
    OBJECTS { alaIpMcastEnable, alaIpMcastRouteEntryCount,
              alaIpMcastRouteUpstreamNeighborType,
              alaIpMcastRouteUpstreamNeighbor, alaIpMcastRouteInIfIndex,
              alaIpMcastRouteTimeStamp, alaIpMcastRouteExpiryTime,
              alaIpMcastRouteNextHopState,
              alaIpMcastRouteNextHopTimeStamp,
              alaIpMcastRouteNextHopExpiryTime,
              alaIpMcastRouteNextHopProtocol,
              alaIpMcastRouteNextHopPkts,
              alaIpMcastInterfaceTtl,
              alaIpMcastInterfaceProtocol,
              alaIpMcastInterfaceRateLimit,
              alaIpMcastInterfaceInMcastOctets,
              alaIpMcastInterfaceOutMcastOctets
            }
    STATUS  deprecated
    DESCRIPTION
            "A collection of objects to support basic management of IP
            Multicast routing.

            This conformance group is deprecated.  It is replaced by
            alaIpMcastMIBBasicGroup and alaIpMcastMIBRouteGroup"
    ::= { alaIpMcastMIBGroups 1 }

alaIpMcastMIBHopCountGroup OBJECT-GROUP
    OBJECTS { alaIpMcastRouteNextHopClosestMemberHops }
    STATUS  current
    DESCRIPTION
            "A collection of objects to support management of the use of
            hop counts in IP Multicast routing."
    ::= { alaIpMcastMIBGroups 2 }

alaIpMcastMIBPktsOutGroup OBJECT-GROUP
    OBJECTS { alaIpMcastRouteNextHopPkts }
    STATUS  current
    DESCRIPTION
            "A collection of objects to support management of packet
            counters for each outgoing interface entry of a route."
    ::= { alaIpMcastMIBGroups 3 }

alaIpMcastMIBHCInterfaceGroup OBJECT-GROUP
    OBJECTS { alaIpMcastInterfaceHCInMcastOctets,
              alaIpMcastInterfaceHCOutMcastOctets,
              alaIpMcastInterfaceHCInMcastPkts,
              alaIpMcastInterfaceHCOutMcastPkts,
              alaIpMcastRouteHCOctets,
              alaIpMcastBoundaryHCDroppedMcastOctets,
              alaIpMcastBoundaryHCDroppedMcastPkts }
    STATUS  current
    DESCRIPTION
            "A collection of objects providing information specific to
            high speed (greater than 20,000,000 bits/second) network
            interfaces."
    ::= { alaIpMcastMIBGroups 4 }

alaIpMcastMIBRouteProtoGroup OBJECT-GROUP
    OBJECTS { alaIpMcastRouteProtocol, alaIpMcastRouteRtProtocol,
              alaIpMcastRouteRtAddressType, alaIpMcastRouteRtAddress,
              alaIpMcastRouteRtPrefixLength, alaIpMcastRouteRtType }
    STATUS  current
    DESCRIPTION
            "A collection of objects providing information on the
            relationship between multicast routing information and the
            IP Forwarding Table."
    ::= { alaIpMcastMIBGroups 5 }

alaIpMcastMIBBasicGroup OBJECT-GROUP
    OBJECTS { alaIpMcastEnable, alaIpMcastRouteEntryCount
            }
    STATUS  current
    DESCRIPTION
            "A collection of objects to support basic management of IP
            Multicast protocols."
    ::= { alaIpMcastMIBGroups 6 }

alaIpMcastMIBRouteGroup OBJECT-GROUP
    OBJECTS { alaIpMcastRouteUpstreamNeighborType,
              alaIpMcastRouteUpstreamNeighbor, alaIpMcastRouteInIfIndex,
              alaIpMcastRouteTimeStamp, alaIpMcastRouteExpiryTime,
              alaIpMcastRoutePkts,
              alaIpMcastRouteDifferentInIfPackets,
              alaIpMcastRouteOctets,
              alaIpMcastRouteNextHopState, alaIpMcastRouteNextHopTimeStamp,
              alaIpMcastRouteNextHopExpiryTime,
              alaIpMcastRouteNextHopProtocol,
              alaIpMcastRouteNextHopPkts,
              alaIpMcastInterfaceTtl,
              alaIpMcastInterfaceRateLimit,
              alaIpMcastInterfaceInMcastOctets,
              alaIpMcastInterfaceOutMcastOctets,
              alaIpMcastRouteTtlDropPackets,
              alaIpMcastRouteTtlDropOctets
            }
    STATUS  current
    DESCRIPTION
            "A collection of objects to support basic management of IP
            Multicast routing."
    ::= { alaIpMcastMIBGroups 7 }

alaIpMcastMIBBoundaryIfGroup OBJECT-GROUP
    OBJECTS { alaIpMcastBoundaryStatus,
              alaIpMcastBoundaryStorageType,
              alaIpMcastBoundaryDroppedMcastOctets,
              alaIpMcastBoundaryDroppedMcastPkts
            }
    STATUS  current
    DESCRIPTION
            "A collection of objects to support management of scoped
            multicast address boundaries."
    ::= { alaIpMcastMIBGroups 10 }

alaIpMcastMIBIfPktsGroup OBJECT-GROUP
    OBJECTS { alaIpMcastInterfaceInMcastPkts,
              alaIpMcastInterfaceOutMcastPkts }
    STATUS  current
    DESCRIPTION
            "A collection of objects to support management of packet
            counters for each interface entry."
    ::= { alaIpMcastMIBGroups 12 }

alaIpMcastMIBRouteOctetsGroup OBJECT-GROUP
    OBJECTS { alaIpMcastRouteOctets, alaIpMcastRouteNextHopOctets,
              alaIpMcastRouteDifferentInIfOctets }
    STATUS  current
    DESCRIPTION
            "A collection of objects to support management of octet
            counters for each forwarding entry."
    ::= { alaIpMcastMIBGroups 13 }

END

ALCATEL-NGOAW-DEVICES-MIB DEFINITIONS ::= BEGIN

IMPORTS
    MODULE-IDENTITY, OBJECT-IDENTITY
FROM
    SNMPv2-SMI

    hardwareNGOAWDevices
FROM
    ALCATEL-NGOAW-BASE-MIB;


alcatelNGOAWDevicesMIB MODULE-IDENTITY

    LAST-UPDATED  "201905150000Z"
    ORGANIZATION  "AL-Enterprise Inc."
    CONTACT-INFO
        "Please consult with Customer Service to ensure the most appropriate
         version of this document is used with the products in question:

                    AL-Enterprise
                   (Formerly Alcatel Internetworking, Incorporated)
                           26801 West Agoura Road
                        Agoura Hills, CA  91301-5122
                          United States Of America

        Telephone:               North America  +1 800 995 2696
                                 Latin America  +1 877 919 9526
                                 Europe         +800 00200100 (Toll Free) or +1(650)385-2193
                                 Asia Pacific: +65 6240 8484

                                 All Other      +1 818 878 4507

        Electronic Mail:         ebg_global_supportcenter@al-enterprise.com
        World Wide Web:          http://alcatel-lucent.com/wps/portal/enterprise
        File Transfer Protocol:  ftp://ftp.ind.alcatel.com/pub/products/mibs"

    DESCRIPTION
        "This module describes an authoritative enterprise-specific Simple
         Network Management Protocol (SNMP) Management Information Base (MIB):

             This module provides Object Indentifier definitions for
             Chassis and AP of the AL-Enterprise
             NGOAW Wireless Product Lines.

         The right to make changes in specification and other information
         contained in this document without prior notice is reserved.

         No liability shall be assumed for any incidental, indirect, special, or
         consequential damages whatsoever arising from or related to this
         document or the information contained herein.

         Vendors, end-users, and other interested parties are granted
         non-exclusive license to use this specification in connection with
         management of the products for which it is intended to be used.

                     Copyright (C) 2016-2019 AL-Enterprise
                         ALL RIGHTS RESERVED WORLDWIDE"

    REVISION      "201609010000Z"
    DESCRIPTION
        "Initial version of this MIB Module."

    REVISION      "201905150000Z"
    DESCRIPTION
        "Updated for new Modules like OAW-AP1201L."

    REVISION      "201908260000Z"
    DESCRIPTION
        "Updated for 6 new Modules like OAW-AP1321."

    REVISION      "202103180000Z"
    DESCRIPTION
        "Updated for new Modules like OAW-AP1301H."

    REVISION      "202203100000Z"
    DESCRIPTION
        "Updated for new Modules like OAW-AP1261."

    ::= { hardwareNGOAWDevices 1 }


familyNGOAWWirelessSwitch OBJECT-IDENTITY
    STATUS current
    DESCRIPTION
        "Branch For NGOAW Wireless Switch Product Family.
        sysObjectID: 1.3.6.1.4.1.6486.802.1.1.2.1.1 "
    ::= { alcatelNGOAWDevicesMIB 1 }


familyNGOAWWirelessAP OBJECT-IDENTITY
    STATUS current
    DESCRIPTION
        "Branch For NGOAW Wireless AP Product Family.
        sysObjectID: 1.3.6.1.4.1.6486.802.1.1.2.1.2 "
    ::= { alcatelNGOAWDevicesMIB 2 }


deviceNGOAWAp1101 OBJECT-IDENTITY
    STATUS current
    DESCRIPTION
        "OmniAccess AP1101 NexGen wireless access point. Dual radio 2x2 IEEE 802.11a/b/g/n/ac wireless
        access point with support for 802.11'B/G/N' and 802.11'A/N/AC' operation, dual-band integral antenna,
        1 x 10/100/1000Base-T (RJ-45) Ethernet Interface (Supports 802.3af Power over Ethernet),
        1 x 12V DC power interface, Console port.
        Model Name: OAW-AP1101
        Assembly:
        sysObjectID: 1.3.6.1.4.1.6486.802.1.1.2.1.2.1 "
    ::= { familyNGOAWWirelessAP 1 }


deviceNGOAWAp1221 OBJECT-IDENTITY
    STATUS current
    DESCRIPTION
        "OmniAccess AP1221 NexGen wireless access point. 802.11ac wave2 Tri radio 2.4GHz 2*2:2 + 5GHz 2*2:2 + 5Ghz 4*4:4
        wireless access point with support for 802.11'B/G/N' and 802.11'A/N/AC' operation, integral antenna,
        2 x 10/100/1000Base-T (RJ-45) Ethernet Interface (Supports 802.3at PoE), 1 x 48V DC power interface, Console port.
        Model Name: OAW-AP1221
        Assembly:
        sysObjectID: 1.3.6.1.4.1.6486.802.1.1.2.1.2.2 "
    ::= { familyNGOAWWirelessAP 2 }


deviceNGOAWAp1222 OBJECT-IDENTITY
    STATUS current
    DESCRIPTION
        "OmniAccess AP1222 NexGen wireless access point. 802.11ac wave2 Tri radio 2.4GHz 2*2:2 + 5GHz 2*2:2 + 5Ghz 4*4:4
        wireless access point with support for 802.11'B/G/N' and 802.11'A/N/AC' operation, external antenna,
        2 x 10/100/1000Base-T (RJ-45) Ethernet Interface (Supports 802.3at PoE), 1 x 48V DC power interface, Console port.
        Model Name: OAW-AP1222
        Assembly:
        sysObjectID: 1.3.6.1.4.1.6486.802.1.1.2.1.2.3 "
    ::= { familyNGOAWWirelessAP 3 }



deviceNGOAWAp1231 OBJECT-IDENTITY
    STATUS current
    DESCRIPTION
        "OmniAccess AP1231 NexGen wireless access point. 802.11ac wave2 Tri radio 2.4GHz 2*2 + 5GHz 4*4:4 + 5Ghz 4*4:4
        wireless access point with integral antenna, 1 x 10/100/1000/2500Base-T (RJ45) and 1 x 10/100/1000Base-T (RJ-45)
        Ethernet Interface (Both supports 802.3at PoE), 1 x 48V DC power interface, Console port.
        Model Name: OAW-AP1231
        Assembly:
        sysObjectID: 1.3.6.1.4.1.6486.802.1.1.2.1.2.4 "
    ::= { familyNGOAWWirelessAP 4 }


deviceNGOAWAp1232 OBJECT-IDENTITY
    STATUS current
    DESCRIPTION
        "OmniAccess AP1231 NexGen wireless access point. 802.11ac wave2 Tri radio 2.4GHz 2*2 + 5GHz 4*4:4 + 5Ghz 4*4:4
        wireless access point with external antenna, 1 x 10/100/1000/2500Base-T (RJ45) and 1 x 10/100/1000Base-T (RJ-45)
        Ethernet Interface (Both supports 802.3at PoE), 1 x 48V DC power interface, Console port
        Model Name: OAW-AP1232
        Assembly:
        sysObjectID: 1.3.6.1.4.1.6486.802.1.1.2.1.2.5 "
    ::= { familyNGOAWWirelessAP 5 }


deviceNGOAWAp1251 OBJECT-IDENTITY
    STATUS current
    DESCRIPTION
        "OmniAccess AP1251 NexGen Outdoor wireless access point. Dual radio 2x2 IEEE 802.11a/b/g/n/ac wireless access point
        with support for 802.11'B/G/N' and 802.11'A/N/AC' operation, dual-band integral antenna, 1 x 10/100/1000Base-T (RJ-45)
        Ethernet Interface (Supports 802.3af PoE), 1 x 48V DC power interface, Console port
        Model Name: OAW-AP1251
        Assembly:
        sysObjectID: 1.3.6.1.4.1.6486.802.1.1.2.1.2.6 "
    ::= { familyNGOAWWirelessAP 6 }


deviceNGOAWAp1251D OBJECT-IDENTITY
    STATUS current
    DESCRIPTION
        "OmniAccess AP1251 NexGen Outdoor wireless access point. Dual radio 2x2 IEEE 802.11a/b/g/n/ac wireless access point
        with support for 802.11'B/G/N' and 802.11'A/N/AC' operation, dual-band integral directional antenna,
        1 x 10/100/1000Base-T (RJ-45) Ethernet Interface (Supports 802.3af PoE), 1 x48V DC power interface, Console port.
        Model Name: OAW-AP1251D
        Assembly:
        sysObjectID: 1.3.6.1.4.1.6486.802.1.1.2.1.2.7 "
    ::= { familyNGOAWWirelessAP 7 }


deviceNGOAWAp1201H OBJECT-IDENTITY
    STATUS current
    DESCRIPTION
        "OmniAccess Stellar AP1201H. Dual radio 2x2:2 802.11a/b/g/n/ac MU-MIMO AP, integrated antenna,
        1x GbE uplink, 3x GbE downlink, 1x RJ45 passthrough, 1x USB (opt BLE) and 1x 48V DC power interface.
         Model Name: OAW-AP1201H
        Assembly:
        sysObjectID: 1.3.6.1.4.1.6486.802.1.1.2.1.2.8 "
    ::= { familyNGOAWWirelessAP 8 }

deviceNGOAWAp1201 OBJECT-IDENTITY
    STATUS current
    DESCRIPTION
        "OmniAccess Stellar AP1201. Dual radio 2x2:2 802.11a/b/g/n/ac MU-MIMO AP, integrated antenna,
         1x GbE, integrated BLE, 1x 48V DC power interface, 1x Console.
         Model Name: OAW-AP1201
        Assembly:
        sysObjectID: 1.3.6.1.4.1.6486.802.1.1.2.1.2.9 "
    ::= { familyNGOAWWirelessAP 9 }


deviceNGOAWAp1201L OBJECT-IDENTITY
    STATUS current
    DESCRIPTION
        "OmniAccess Stellar AP1201L. Dual radio 2x2:2 802.11a/b/g/n/ac MU-MIMO Indoor AP, with integrated
        antenna, 1x GbE, 1x 48V DC power interface, 1x Console.
        Model Name: OAW-AP1201L
        Assembly:
        sysObjectID: 1.3.6.1.4.1.6486.802.1.1.2.1.2.10 "
    ::= { familyNGOAWWirelessAP 10 }

deviceNGOAWAp1201HL OBJECT-IDENTITY
    STATUS current
    DESCRIPTION
        "OmniAccess Stellar AP1201HL. Dual radio 2x2:2 802.11a/b/g/n/ac MU-MIMO AP, integrated antenna,
        1x GbE uplink, 3x GbE downlink, 1x RJ45 passthrough and 1x 48V DC power interface.
        Model Name: OAW-AP1201HL
        Assembly:
        sysObjectID: 1.3.6.1.4.1.6486.802.1.1.2.1.2.11 "
    ::= { familyNGOAWWirelessAP 11 }


deviceNGOAWAp1321 OBJECT-IDENTITY
    STATUS current
    DESCRIPTION
        "OmniAccess Stellar AP1321. Dual radio 4x4:4 + 2x2:2 802.11ax Indoor AP, integrated Omni Directional
        Antenna. Integrated 1x1 full band scanning radio and BLE radio. Interfaces 2.5GbE, 1GbE, USB,
        48V DC Power, Console. AP mount kit to be ordered separately.
        Model Name: OAW-AP1321
        Assembly:
        sysObjectID: 1.3.6.1.4.1.6486.802.1.1.2.1.2.12 "
    ::= { familyNGOAWWirelessAP 12 }

deviceNGOAWAp1322 OBJECT-IDENTITY
    STATUS current
    DESCRIPTION
        "OmniAccess Stellar AP1322. Dual radio 4x4:4 + 2x2:2 802.11ax Indoor AP. Integrated 1x1 full band
        scanning radio and BLE radio. Interfaces 2.5GbE, 1GbE, USB, 48V DC Power, Console & 4x antenna
        connectors. AP mount kit and Antennas to be ordered separately.
        Model Name: OAW-AP1322
        Assembly:
        sysObjectID: 1.3.6.1.4.1.6486.802.1.1.2.1.2.13 "
    ::= { familyNGOAWWirelessAP 13 }

deviceNGOAWAp1361 OBJECT-IDENTITY
    STATUS current
    DESCRIPTION
        "OmniAccess Stellar AP1361. Dual radio 4x4:4 + 2x2:2 802.11ax Outdoor AP, integrated Omni Directional Antenna.
        Integrated 1x1 full band scanning radio and BLE radio. Interfaces 2.5GbE RJ-45, 1GbE RJ-45, 1GbE SFP,
        USB, 48V DC Power, Console. AP mount kit to be ordered separately.
        Model Name: OAW-AP1361
        Assembly:
        sysObjectID: 1.3.6.1.4.1.6486.802.1.1.2.1.2.14 "
    ::= { familyNGOAWWirelessAP 14 }

deviceNGOAWAp1361D OBJECT-IDENTITY
    STATUS current
    DESCRIPTION
        "OmniAccess Stellar AP1361D. Dual radio 4x4:4 + 2x2:2 802.11ax Outdoor AP, integrated Directional Antenna.
        Integrated 1x1 full band scanning radio and BLE radio. Interfaces 2.5GbE RJ-45, 1GbE RJ-45, 1GbE SFP, USB,
        48V DC Power, Console. AP mount kit to be ordered separately.
        Model Name: OAW-AP1361D
        Assembly:
        sysObjectID: 1.3.6.1.4.1.6486.802.1.1.2.1.2.15 "
    ::= { familyNGOAWWirelessAP 15 }

deviceNGOAWAp1362 OBJECT-IDENTITY
    STATUS current
    DESCRIPTION
        "OmniAccess Stellar AP1362. Dual radio 4x4:4 + 2x2:2 802.11ax Outdoor AP. Integrated 1x1 full band scanning
        radio and BLE radio. Interfaces 2.5GbE RJ-45, 1GbE RJ-45, 1GbE SFP, USB, 48V DC Power, Console & 4x antenna
        connectors. AP mount kit and antennas to be ordered separately.
        Model Name: OAW-AP1362
        Assembly:
        sysObjectID: 1.3.6.1.4.1.6486.802.1.1.2.1.2.16 "
    ::= { familyNGOAWWirelessAP 16 }

deviceNGOAWAp1201BG OBJECT-IDENTITY
    STATUS current
    DESCRIPTION
        "OmniAccess Stellar BLE GATEWAY AP1201BG. Dual radio 2x2:2 802.11a/b/g/n/ac WiFi client, integrated
        BLE GW ,integrated antenna, 1x GbE, 1x 48V DC power interface, 1x Console. Cannot be used as Access Point.
        Model Name: OAW-AP1201BG
        Assembly:
        sysObjectID: 1.3.6.1.4.1.6486.802.1.1.2.1.2.17 "
    ::= { familyNGOAWWirelessAP 17 }

deviceNGOAWAp1251RWB OBJECT-IDENTITY
    STATUS current
    DESCRIPTION
        "OmniAccess AP1251 NextGen Outdoor wireless access point. Dual radio 2x2 IEEE 802.11a/b/g/n/ac wireless access point,
        integral antenna, 1 x 10/100/1000Base-T (RJ-45) Ethernet Interface (Supports 802.3af /at PoE), Reset control.
        Model Name: OAW-AP1251-RW-B
        Assembly:
        sysObjectID: 1.3.6.1.4.1.6486.802.1.1.2.1.2.18 "
    ::= { familyNGOAWWirelessAP 18 }

deviceNGOAWAp1301 OBJECT-IDENTITY
    STATUS current
    DESCRIPTION
        "OmniAccess Stellar AP1301. Dual radio 2.4/5Ghz 2x2:2 802.11ax Indoor AP, integrated Omni Directional Antenna,
        and integrated BLE radio. Interfaces 1GbE, USB, 48V DC Power, Console. AP mount kit to be ordered separately.
        Model Name: OAW-AP1301
        Assembly:
        sysObjectID: 1.3.6.1.4.1.6486.802.1.1.2.1.2.19 "
    ::= { familyNGOAWWirelessAP 19 }

deviceNGOAWAp1311 OBJECT-IDENTITY
    STATUS current
    DESCRIPTION
        "OmniAccess Stellar AP1311. Dual radio 2.4/5Ghz 2x2:2 802.11ax Indoor AP, integrated Omni Directional Antenna.
        Integrated 1x1 full band scanning radio and BLE/Zigbee radio. Interfaces 2x 1GbE Uplink, 1GbE downlink,
        1x RJ-45 RS-232 Console/ Modbus IIOT, USB, 48V DC Power. AP mount kit to be ordered separately.
        Model Name: OAW-AP1311
        Assembly:
        sysObjectID: 1.3.6.1.4.1.6486.802.1.1.2.1.2.20 "
    ::= { familyNGOAWWirelessAP 20 }

deviceNGOAWAp1341E OBJECT-IDENTITY
    STATUS current
    DESCRIPTION
        "OmniAccess Stellar AP1341E. Tri radio 2.4/5/6Ghz 4x4:4 or Dual radio 2.4/5Ghz 4x4:4 + 8x8:8 802.11ax Indoor AP.
        Integrated 1x1 full band scanning radio and BLE/Zigbee radio. Interfaces 2x5GbE, USB, 48V DC Power, Console.
        AP mount kit to be ordered separately.
        Model Name: OAW-AP1341E
        Assembly:
        sysObjectID: 1.3.6.1.4.1.6486.802.1.1.2.1.2.21 "
    ::= { familyNGOAWWirelessAP 21 }

deviceNGOAWAp1351 OBJECT-IDENTITY
    STATUS current
    DESCRIPTION
        "OmniAccess Stellar Indoor AP1351. Tri radio AP 2.4Ghz + Dual 5Ghz 4x4+8x8+4x4 802.11ax, omni antenna.
        1x1 scanning and BLE radio. 2x 10GE up, 1x RS-232 Console, USB, 48V DC. AP mount to be ordered separately.
        Model Name: OAW-AP1351
        Assembly:
        sysObjectID: 1.3.6.1.4.1.6486.802.1.1.2.1.2.22 "
    ::= { familyNGOAWWirelessAP 22 }

deviceNGOAWAp1331 OBJECT-IDENTITY
    STATUS current
    DESCRIPTION
        "OmniAccess Stellar Indoor AP1331. Dual radio 2.4/5Ghz 4x4 802.11ax, omni antenna. 1x1 scanning and BLE radio.
        2x 2.5GE up, 1x RS-232 Console, USB, 48V DC. AP mount to be ordered separately.
        Model Name: OAW-AP1331
        Assembly:
        sysObjectID: 1.3.6.1.4.1.6486.802.1.1.2.1.2.23 "
    ::= { familyNGOAWWirelessAP 23 }

deviceNGOAWAp1301H OBJECT-IDENTITY
    STATUS current
    DESCRIPTION
        "OmniAccess Stellar Indoor AP1301H. Dual radio 2.4/5Ghz 2x2 802.11ax, integrated omni antenna, 1x GbE uplink,
        4x GbE downlink (1 PSE), RJ45 passthru pair, 1x USB (opt BLE) and 1x 48V DC power interface.
        Model Name: OAW-AP1301H
        Assembly:
        sysObjectID: 1.3.6.1.4.1.6486.802.1.1.2.1.2.24 "
    ::= { familyNGOAWWirelessAP 24 }

deviceNGOAWAp1261RWB OBJECT-IDENTITY
    STATUS current
    DESCRIPTION
        "OmniAccess Stellar Outdoor AP1261-RW-B access point. Dual radio 2x2 802.11ac MU-MIMO, integrated antenna,
        1x GbE uplink, 1x USB Console port. BBNL customized configuration
        Model Name: OAW-AP1261-RW-B
        Assembly:
        sysObjectID: 1.3.6.1.4.1.6486.802.1.1.2.1.2.25 "
    ::= { familyNGOAWWirelessAP 25 }

deviceNGOAWAp1261 OBJECT-IDENTITY
    STATUS current
    DESCRIPTION
        "OmniAccess Stellar Outdoor AP1261 access point. Dual radio 2x2 802.11ac MU-MIMO, integrated antenna,
        1x GbE uplink, 1x USB Console port.
        Model Name: OAW-AP1261
        Assembly:
        sysObjectID: 1.3.6.1.4.1.6486.802.1.1.2.1.2.26 "
    ::= { familyNGOAWWirelessAP 26 }

deviceNGOAWAp1451 OBJECT-IDENTITY
    STATUS current
    DESCRIPTION
        "OmniAccess Stellar Indoor AP1451 access point. Tri radio 2.4GHz/5GHz/6GHz 4x4+8x8+4x4 802.11ax (Wi-Fi 6E),
        with integrated omni antenna. Built in BLE/Zigbee and 1x1 scanning radio. 2x 10GE, 1x RS-232 Console, USB,
        48V DC. AP mount to be ordered separately.
        Model Name: OAW-AP1451
        Assembly:
        sysObjectID: 1.3.6.1.4.1.6486.802.1.1.2.1.2.27 "
    ::= { familyNGOAWWirelessAP 27 }

deviceNGOAWAp1431 OBJECT-IDENTITY
    STATUS current
    DESCRIPTION
        "OmniAccess Stellar Indoor AP1431 access point. Tri radio 2.4GHz/5GHz/6GHz 2x2+2x2+2x2 802.11ax (Wi-Fi 6E),
        with integrated omni antenna. Built in BLE/Zigbee and 1x1 scanning radio. 2x 2.5GE, 1x RS-232 Console, USB,
        48V DC. AP mount to be ordered separately.
        Model Name: OAW-AP1431
        Assembly:
        sysObjectID: 1.3.6.1.4.1.6486.802.1.1.2.1.2.28 "
    ::= { familyNGOAWWirelessAP 28 }

deviceNGOAWAp1362T OBJECT-IDENTITY
    STATUS current
    DESCRIPTION
        "OmniAccess Stellar rugged AP1362T access point. Dual radio 5GHz 4x4, and scanning radio. 1x GE M12 uplink,
        1x M12 110VDC power, and external antenna connectors. 1x GE and console ancillary RJ-45 ports.
        Model Name: OAW-AP1362T
        Assembly:
        sysObjectID: 1.3.6.1.4.1.6486.802.1.1.2.1.2.29 "
    ::= { familyNGOAWWirelessAP 29 }

END

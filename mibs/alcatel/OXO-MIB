-- vim: ft=mib et ts=4 sts=4 sw=4:
OXO-MIB DEFINITIONS ::= BEGIN
    IMPORTS
        MODULE-IDENTITY, enterprises
            FROM SNMPv2-SMI
        TEXTUAL-CONVENTION
            FROM SNMPv2-TC ;

    oxoMIB MODULE-IDENTITY
        LAST-UPDATED    "201503201424Z"
        ORGANIZATION    "ALE Communication"
        CONTACT-INFO    "ALE Communication
            67400 ILLKIRCH-GRAFFENSTADEN
            FRANCE"
        DESCRIPTION
            "This is ALE Communication implementation of
            enterprise specific MIB for the OmniPCX Office product."
        REVISION        "201503201424Z"
        DESCRIPTION
            "OXO R10.2"
        ::=  { aleCommunicationOXO 1 }

    aleCommunicationOXO OBJECT IDENTIFIER
        ::=  { aleCommunication 4200 }

    aleCommunication OBJECT IDENTIFIER
        ::=  { ale 64 }

    ale OBJECT IDENTIFIER
        ::=  { enterprises 6486 }


    PhysicalAddress ::= TEXTUAL-CONVENTION
        DISPLAY-HINT    "1d.1d.1d"
        STATUS          current
        DESCRIPTION
            "Physical address of an equipment in the system.
            <slot>.<half-board>.<access>"
        SYNTAX          OCTET STRING (SIZE (3))

    EventSeverity ::= TEXTUAL-CONVENTION
        STATUS          current
        DESCRIPTION
            "Perceived severity values.
            Only events with high severity generate a notification"
        SYNTAX INTEGER {
            reserved (0),
            critical (1),
            major (2),
            minor (3),
            warning (4),
            indeterminate (5),
            clear (6)
        }

    ActivationStatus ::= TEXTUAL-CONVENTION
        STATUS          current
        DESCRIPTION
            "Status active or inactive"
        SYNTAX INTEGER {
            inactive (0),
            active (1),
            unknown (2)
        }

END

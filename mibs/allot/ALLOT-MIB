ALLOT-MIB DEFINITIONS ::= BEGIN

IMPORTS
        DisplayString,
        DateAndTime,
        TimeStamp,
        VariablePointer,
        RowStatus,
        TEXTUAL-CONVENTION
                FROM SNMPv2-TC
        OBJECT-GROUP,
        NOTIFICATION-GROUP,
        MODULE-COMPLIANCE
                FROM SNMPv2-CONF
        InterfaceIndex,
        ifIndex,
        InterfaceIndexOrZero
                FROM IF-MIB
        enterprises,
        MODULE-IDENTITY,
        OBJECT-IDENTITY,
        OBJECT-TYPE,
        NOTIFICATION-TYPE,
        Counter32,
        Counter64,
        Gauge32,
        Integer32,
        IpAddress,
        Unsigned32
                FROM SNMPv2-SMI;

alRegMIB MODULE-IDENTITY
        LAST-UPDATED "201111201400Z"		-- November 20, 2011 at 14:00 GMT
        ORGANIZATION "Allot Communications"
        CONTACT-INFO
                "Allot Communications
                Telephone:  (Toll-free for US callers):  1 800 204-1364 /  1 800 204-1364
                Telephone:  (Non-US callers): 1 781 939 9355 /  1 781 939 9355
                Email:      support@allot.com"
        DESCRIPTION
                "Newly formed Allot enterprise MIB designed for
                the next generation NMS."    
                
		REVISION "201111201400Z"		-- November 20, 2011 at 14:00 GMT
			DESCRIPTION 
				"Added alCaptivePortalPassPhrase."                
		REVISION "201111171700Z"		-- November 17, 2011 at 17:00 GMT
		DESCRIPTION 
				"Added tethering support:
				1. alTetherDetectState
				2. tethering(16), under alLicenseAttrType "				
        REVISION "201109211200Z"		-- September 21, 2011 at 12:00 GMT
        DESCRIPTION 
                "Bugfix: added alSelectiveBypassActivation and alSelectiveBypassVlanGroup to the alGenericGroup OBJECT-GROUP."
				
        REVISION "201109111200Z"        -- September 11, 2011 12:00:00 PM
        DESCRIPTION
                "Add new AlSelectiveBypass"   

        REVISION "201108091100Z"        -- August 9, 2011 11:00:00 AM
        DESCRIPTION
                "Add new alIPv6State."   
	
        REVISION "201107241100Z"        -- July 24, 2011 11:00:00 PM
        DESCRIPTION
                "Updated alLicenseAttrType, added: mobileReports(14), statExport(15)"      
                
        REVISION "201107211300Z"        -- July 21, 2011 13:00:00 PM
        DESCRIPTION
                "Updated CONTACT-INFO."      
 
        REVISION "201106221100Z"        -- June 22, 2011 11:00:00 AM
        DESCRIPTION
                "Add new alVoipReportingActivation and alSPSensorActivation."   
   
        REVISION "201106211100Z"        -- June 21, 2011 11:00:00 AM
        DESCRIPTION
                "Add new alPredictiveDPI and alPDPIState."   
   
        REVISION "201106141300Z"        -- June 14, 2011 13:00:00 PM
        DESCRIPTION
                "Update alLicenseAttrType."   
   
        REVISION "201105041608Z"        -- May 4, 2011 4:08:00 PM
        DESCRIPTION
                "Add new trap definition: alURLFilteringUpdateTrap,
                Add new status for Web Safe update: alUrlFLastUpdateStatus."
   
        REVISION "201103221000Z"        -- March 22, 2011 10:00:00 AM
        DESCRIPTION
                "Add NSS NetExpand NEX-1 to alBoardType."
		REVISION "201011181000Z"        -- Nov 18, 2010 10:00:00 AM
        DESCRIPTION
                "Change 1.3.6.1.4.1.2603.5.1.8 name from alAC10K to alAC10000
                Add new products: alAC3K, alAC10K, alAC1K, alACSigmaE14, alACSigmaE6, alAC500
                Add new MIBs: alCaptivePortal & alFupProtocolVersion."
        REVISION "200912221326Z"        -- Dec 22, 2009 1:26:00 PM
        DESCRIPTION
                "1. alLicenseInfoTable is added
                2. alLicenseWarnEventTrap and alLicenseCritEventTrap are added"
        REVISION "200912011518Z"        -- Dec 1, 2009 3:18:00 PM
        DESCRIPTION
                "1. 2 new types of board are added: 10- BYP  and 11-VAS
                2. Usage capability is added to alIfXTable"
        REVISION "200910290948Z"        -- Oct 29, 2009 9:48:00 AM
        DESCRIPTION
                "1. alServiceActivation group is added to alGeneralSystem group
                2. alAsymmetricDeviceTable is changed
                3. alIfXUsage, alIfXSwitchId and alIfXSwitchPort columns are added to alIfXTable"
        REVISION "200909021333Z"        -- Sep 2, 2009 1:33:00 PM
        DESCRIPTION
                "1. alAsymmetric group added to group alGeneralSystem
                2. alAsymmetricRemoteDeviceConfTrap and alAsymmetricRemoteDeviceStatusTrap traps are added"
        REVISION "200908120959Z"        -- Aug 12, 2009 9:59:00 AM
        DESCRIPTION
                "alUserDefinedSignature OBJECT IDENTIFIER added for UDS feature support"
        REVISION "200902241135Z"        -- Feb 24, 2009 11:35:00 AM
        DESCRIPTION
                "alBoardTypes- new types are added- switch(8) dispatcher(9)
                alIfXSpeed- new speed is added - tenThousand (5)
                alStatTable -descriptions are added"
        REVISION "200711271545Z"        -- Nov 27, 2007 3:45:00 PM
        DESCRIPTION
                "Added:
                1. alWebUpdateIsEnabled and alWebUpdateExpirationDateEnable leafs are added in alActivation group.
                Changed:
                1. alSensorType is added as index in table alSensorTable.
                2. alBypass new value(4- partialBypass) is added in enumerator."
        REVISION "200709231521Z"        -- Sep 23, 2007 3:21:00 PM
        DESCRIPTION
                "New group alInternalRedundancy is added.
                alBoardTable moved to this group.
                New leafs are: alInternalDispatchMode, alInternalMinDevNum, alInternalRedundancyDevNum, alInternalActiveDevNum, AlInternalRateLimit."
        REVISION "200708200833Z"        -- Aug 20, 2007 8:33:00 AM
        DESCRIPTION
                "New leafs are added:
                alGeneralSystem/alWebUpdate/alBaseVersion
                alGeneralSystem/alWebUpdate/alCurrentVersion
                alGeneralSystem/alWebUpdate/alLastUpdateStatus

                New trap is added:
                alWebUpdateTrap"
        REVISION "200706121507Z"        -- Jun 12, 2007 3:07:00 PM
        DESCRIPTION
                "New leaf is added to alSystemCOC group: alCocRedirectionPort"
        REVISION "200705141206Z"        -- May 14, 2007 12:06:00 PM
        DESCRIPTION
                "New tables are added:
                   alBoardTable added to alGeneric/alGeneralSystem;
                   alSensorTable added to alAlerts.
                New trap is added:
                   alBoardStatusChangeTrap sent on changing any status (SW or HW) of board."
        REVISION "200702280727Z"        -- Feb 28, 2007 7:27:00 AM
        DESCRIPTION
                "New group alSystemCOC is added. It used for connection control parameters."
        REVISION "200608100853Z"        -- Aug 10, 2006 8:53:00 AM
        DESCRIPTION
                "Added new leafs:
                alObjects/alAlert/alCpuPicoUsage, alObjects/alGeneric/alGeneralSystem/alDeviceBWLimits/alDeviceBWLimitsType,
                alObjects/alGeneric/alGeneralSystem/alDeviceBWLimits/alDeviceBWLimitsOutbound, alObjects/alGeneric/alGeneralSystem/alDeviceBWLimits/alDeviceBWLimitsInbound

                Added new product type:
                alObjects/alProducts/alMediationDevice

                Added new trap:
                alApplicationInfoTrap

                Updated:
                In trap alAccessViolationTrap added VB alLastMessage

                "
        REVISION "200605311136Z"        -- May 31, 2006 11:36:00 AM
        DESCRIPTION
                "Changes:
                1. alSevereSoftwareProblem changed - added values to enum"
        REVISION "200605101150Z"        -- May 10, 2006 11:50:00 AM
        DESCRIPTION
                "Changes:
                1. alAC2500 - added (new product type)"
        REVISION "200603231055Z"        -- Mar 23, 2006 10:55:00 AM
        DESCRIPTION
                "Changes:
                1. alSevereSoftwareProblem changed - added values to enum"
        REVISION "200511141058Z"        -- Nov 14, 2005 10:58:00 AM
        DESCRIPTION
                "Added leafs:
                1.  alBypassSetting, alRemoteBypass, alBypass to Group alGeneralSystem/alSystemStatus
                2.  alRedunduncyMode, alRedundancyCap, alBypassUnit to Group alGeneralSystem
                New column in table alIfXTable:
                1.  alIfXAction
                Deleted leafs :
                1.  alRedundandStatus, alStatdby, alMirrorAction, alActiveRedundancyMode

                "
        REVISION "200508241459Z"        -- Aug 24, 2005 2:59:00 PM
        DESCRIPTION
                "llIfXActualMode is added to alIfXTable"
        REVISION "200508141249Z"        -- Aug 14, 2005 12:49:00 PM
        DESCRIPTION
                "alActivation group:
                1. alMngmtMode renamed to alLTCollectionEnabled
                2. alMngmtModel -deleted."
        REVISION "200508141213Z"        -- Aug 14, 2005 12:13:00 PM
        DESCRIPTION
                "alMngmtMode and alMngmtModel added to alActivation group."
        REVISION "200507281352Z"        -- Jul 28, 2005 1:52:00 PM
        DESCRIPTION
                "deleted leafs from alGeneric:
                alClassMode; alDOSAction; alOutOfResourceAction"
        REVISION "200507201606Z"        -- Jul 20, 2005 4:06:00 PM
        DESCRIPTION
                "alIfXSupported changed fro Octet string to UInteger32"
        REVISION "200507201225Z"        -- Jul 20, 2005 12:25:00 PM
        DESCRIPTION
                "Added:
                1. New textual convention alEnableDisableNA

                Changed:
                1. Type from AlEnableDisable to AlEnableDisableNA : alHTTPConnectionMode, alLcdConfigEnable, alLearningBridge, alSPTStatus and alDoubleSession.
                2. Added notApplicable to enumerator of: alPower, alBypass.
                3. Two new VB added to alDeviceConfChangeTrap- alGenericLastChangeStrVal and alGenericLastChangeAddrVal"
        REVISION "200507171502Z"        -- Jul 17, 2005 3:02:00 PM
        DESCRIPTION
                "In alGeneric added:
                alSshSecurity enable/disable SSH security.
                AlGenericLastChangeStrVal  and alGenericLastChangeAddrVal  same as alGenericLastChangeIntVal but saves string and ip address values.

                In table alIfXTable added:
                AlIfXSupported describes supported mode and speed options for current interface.

                "
        REVISION "200506081425Z"        -- Jun 8, 2005 2:25:00 PM
        DESCRIPTION
                "Add :
                1. alIfXLabel in alIfXTable.
                Modify:
                1. alRebootRequest (now it enumerator and can do shutdown)
                2. alPolicyModificationTag (now it enumerator)

                "
        REVISION "200505041205Z"        -- May 4, 2005 12:05:00 PM
        DESCRIPTION
                "Changes:
                1. alCpuUsage and alLastMessage  added in alAlert
                2. alMode in alGeneric is changed (no more bypass)
                3. alPolicyModificationTag is added in alProvisioning
                4. alPosIfTable index changed from ifIndex to alPosIndex
                5. alDeviceStatusUpTrap and alDeviceStatusDownTrap are added
                6. AlSoftwareProblemTrap changed - added additional VB - alLastMessage"
        REVISION "200504061208Z"        -- Apr 6, 2005 12:08:00 PM
        DESCRIPTION
                "alRedundStatus enum changed (standalone instead unknown)"
        REVISION "200503221208Z"        -- Mar 22, 2005 12:08:00 PM
        DESCRIPTION
                "Changed enumerator in for table variable alAlertConfThresholdDirection"
        REVISION "200503101121Z"        -- Mar 10, 2005 11:21:00 AM
        DESCRIPTION
                "Changes in alDataSourceEntry:
                1. New keys - alDataSourceType and alDataSourcePriorityOrder instead alDataSourceId

                "
        REVISION "200503091150Z"        -- Mar 9, 2005 11:50:00 AM
        DESCRIPTION
                "In alPosIfTable:
                1. alPosIfClocking is change:  internal(1), external0(2), external1(3)
                2. New Fields:
                    - alPosIfEncapsulation: ppp(1), chdlc(2), frameRelay(3)
                    - alPosIfMtu: (64-14336)

                In alIpXAddrTable:
                1. The index is ifIndex instead alIpXAddr.
                2. field alIpXIfIndex removed

                alIpAddrConfChangeTrap changed
                it consists alIpXAddr instead alIpXIfIndex value"
        REVISION "200503061211Z"        -- Mar 6, 2005 12:11:00 PM
        DESCRIPTION
                "Changes in enumerators."
        REVISION "200503011103Z"        -- Mar 1, 2005 11:03:00 AM
        DESCRIPTION
                "Changes:
                1. alGateway -> alInBandGateway
                2. alOutOfBandGaiteway -> alOutOfBandGateway
                Add:
                1. alActiveRedunduncy in alGeneralSystem group
                2. alBypass and alStandby in alSystemStatus group"
        REVISION "200502021859Z"        -- Feb 2, 2005 6:59:00 PM
        DESCRIPTION
                "1. Change alPolicyesStatTable and  alPoliciesStatEntry to  alPoliciesStatusTable, alPoliciesStatusEntry
                2. Change atPolicyStatus in table into doMakeActive and the description is:
                3. add  alIfXOrder into alIfXEntry

                "
        REVISION "200501231356Z"        -- Jan 23, 2005 1:56:00 PM
        DESCRIPTION
                "changed:
                alIpXVlan type from string to int32

                added:
                Table alPosIfTable
                alSaveConfigDump and alRestoreConfigDump in alLoadConfig group."
        REVISION "200501041032Z"        -- Jan 4, 2005 10:32:00 AM
        DESCRIPTION
                "alAlertConfVariable now is part of index in alAlertConfTable"
        REVISION "200412281046Z"        -- Dec 28, 2004 10:46:00 AM
        DESCRIPTION
                "minor changes: syntax and order of nodes."
        REVISION "200412271245Z"        -- Dec 27, 2004 12:45:00 PM
        DESCRIPTION
                "Identifications of nodes in alActivation and alGeneric Groups changed such as prevent holes in enumeration of elements."
        REVISION "200412271140Z"        -- Dec 27, 2004 11:40:00 AM
        DESCRIPTION
                "added
                1. alSysExpiratinDate to alActivation group
                2. alTosRemarkingEnable and alReserveOnDemandEnable to alGenericCapability group

                moved
                1. alBoxSerialNumber, alSoftwareVersion, alBackplaneVersin  from alActivation group  to alGeneralSystem group.

                "
        REVISION "200412221402Z"        -- Dec 22, 2004 2:02:00 PM
        DESCRIPTION
                "Massive changes:
                Removed:
                  1.  DOS columns from alPolicies/alLineTable
                  2.  sshAccess, RootAccess, RemoteSnapshot.
                Added:
                  1. DOS table
                  2. EnhansedTcpSecurity, Power, Fan, DoubleSession, OutOfResourceAction, ActionModel.
                Merged:
                  1. ActivityStatus and WorkingMode  to alGeneralSystem/alMode
                  2. TransClass and ApplicationClass to ClassMode
                Changed to read-only:
                  1. MACinHost, halfDuplexinQoS"
        REVISION "200412151429Z"        -- Dec 15, 2004 2:29:00 PM
        DESCRIPTION
                "Added alConnRouteTable instead all leafs in the alObject/alGeneric/alGenericConnect group.
                Added alIpXAddrTable in alObject/alGeneric group.
                Two new traps are added: alConnRouteConfChangeTrap and alIpAddrConfChangeTrap."
        REVISION "200411141119Z"        -- Nov 14, 2004 11:19:00 AM
        DESCRIPTION
                "1. alDataSourceType VB added to alDataSourceUpTrap  and alDataSourceDownTrap traps.
                2. alRebootReqest object type added."
        REVISION "200410211156Z"        -- Oct 21, 2004 11:56:00 AM
        DESCRIPTION
                "aConnCoCGateway added"
        REVISION "200409201539Z"        -- Sep 20, 2004 3:39:00 PM
        DESCRIPTION
                "alConnNatIPAddressLast and alLcdConfigEnables variables are added"
        REVISION "200408241804Z"        -- Aug 24, 2004 6:04:00 PM
        DESCRIPTION
                "alPolicyConfTrapEnable removed and alLineConfTrapEnable, alPipeConfTrapEnable, alVcConfTrapEnable added instead"
        REVISION "200408171657Z"        -- Aug 17, 2004 4:57:00 PM
        DESCRIPTION
                "Indexes in alStatTable changed - reffered to alStatCtrlTale indexes"
        REVISION "200408111637Z"        -- Aug 11, 2004 4:37:00 PM
        DESCRIPTION
                "Insert new objets to support of old NE MIBs."
        REVISION "200407252145Z"        -- Jul 25, 2004 9:45:00 PM
        DESCRIPTION
                "General clean up before CVS."
        REVISION "200405311938Z"        -- May 31, 2004 7:38:00 PM
        DESCRIPTION
                "First editing of the MIB. Many new descriptions"
        REVISION "200404132205Z"        -- Apr 13, 2004 10:05:00 PM
        DESCRIPTION
                "Initial version."
        -- 1.3.6.1.4.1.2603
        ::= { enterprises 2603 }


AlActiveStandbyStatus ::= TEXTUAL-CONVENTION
        STATUS current
        DESCRIPTION
                "Represents software status:
                (0)- notApplicable
                               (1)-bypass
                               (2)-nonBypass-active
                               (3)-standBy
                               (4)-partialBypass

                "
        SYNTAX INTEGER {
                        bypass(1),
                        nonBypass(2),
                        standBy(3),
                        partialBypass(4),
                        notApplicable(0) }


AlConfigCommand ::= TEXTUAL-CONVENTION
        STATUS current
        DESCRIPTION
                "Configuration change operations"
        SYNTAX INTEGER {
                        create(1),
                        update(2),
                        delete(3) }


AlEnableDisable ::= TEXTUAL-CONVENTION
        STATUS current
        DESCRIPTION
                "Enable/disable variable."
        SYNTAX INTEGER {
                        enabled(1),
                        disabled(2) }


AlEnableDisableNA ::= TEXTUAL-CONVENTION
        STATUS current
        DESCRIPTION
                "Enable/Disable/NA values"
        SYNTAX INTEGER {
                        enabled(1),
                        disabled(2),
                        notAplicable(3) }


AlInstanceStatus ::= TEXTUAL-CONVENTION
        STATUS current
        DESCRIPTION
                "Status of policy element entry."
        SYNTAX INTEGER {
                        active(1),
                        disabled(2),
                        removed(3) }


AlUrlOperationMode ::= TEXTUAL-CONVENTION
        STATUS current
        DESCRIPTION ""
        SYNTAX INTEGER {
                        always(1),
                        policybased(2),
                        disable(3) }


-- Notification Types
--
-- The last varbind of any notification is always trap's ID. Actually it
-- is the index of the named log entry (RFC3014). The index variable
-- name is - nlmLogIndex

alEvents OBJECT IDENTIFIER 
        -- 1.3.6.1.4.1.2603.0
        ::= { alRegMIB 0 }

alActivation OBJECT IDENTIFIER 
        -- 1.3.6.1.4.1.2603.4
        ::= { alRegMIB 4 }

alActivationKey OBJECT-TYPE
        SYNTAX  DisplayString
        MAX-ACCESS read-write
        STATUS current
        DESCRIPTION
                "Activation key for the current product."
        -- 1.3.6.1.4.1.2603.4.1
        ::= { alActivation 1 }


alActivationModel OBJECT-TYPE
        SYNTAX  DisplayString
        MAX-ACCESS read-only
        STATUS current
        DESCRIPTION
                "Product Name"
        -- 1.3.6.1.4.1.2603.4.2
        ::= { alActivation 2 }


alSysExpirationDate OBJECT-TYPE
        SYNTAX  DateAndTime
        MAX-ACCESS read-only
        STATUS current
        DESCRIPTION
                "System expiration date"
        -- 1.3.6.1.4.1.2603.4.3
        ::= { alActivation 3 }


alQoSIsEnabled OBJECT-TYPE
        SYNTAX  AlEnableDisable
        MAX-ACCESS read-only
        STATUS current
        DESCRIPTION
                "Shows whether the license enables QoS capability."
        -- 1.3.6.1.4.1.2603.4.4
        ::= { alActivation 4 }


alQoSExpirationDateEnable OBJECT-TYPE
        SYNTAX  AlEnableDisable
        MAX-ACCESS read-only
        STATUS current
        DESCRIPTION
                "QoS capability expiration date enabled or disabled.."
        -- 1.3.6.1.4.1.2603.4.5
        ::= { alActivation 5 }


alCacheIsEnabled OBJECT-TYPE
        SYNTAX  AlEnableDisable
        MAX-ACCESS read-only
        STATUS current
        DESCRIPTION
                "The redirection to proxy cache is enabled (on/off)"
        -- 1.3.6.1.4.1.2603.4.6
        ::= { alActivation 6 }


alCacheExpirationDateEnable OBJECT-TYPE
        SYNTAX  AlEnableDisable
        MAX-ACCESS read-only
        STATUS current
        DESCRIPTION
                "Enabling the expiration date for the cache redirection."
        -- 1.3.6.1.4.1.2603.4.7
        ::= { alActivation 7 }


alLoadBalancingIsEnabled OBJECT-TYPE
        SYNTAX  AlEnableDisable
        MAX-ACCESS read-only
        STATUS current
        DESCRIPTION
                "The capability of load balancing is enabled (on/off)."
        -- 1.3.6.1.4.1.2603.4.8
        ::= { alActivation 8 }


alLoadBalancingExpirationDateEnable OBJECT-TYPE
        SYNTAX  AlEnableDisable
        MAX-ACCESS read-only
        STATUS current
        DESCRIPTION
                "Enabling the expiration date for the active load balancing."
        -- 1.3.6.1.4.1.2603.4.9
        ::= { alActivation 9 }


alActivationLimits OBJECT IDENTIFIER 
        -- 1.3.6.1.4.1.2603.4.10
        ::= { alActivation 10 }

alLinePerPolicy OBJECT-TYPE
        SYNTAX  Unsigned32
        MAX-ACCESS read-only
        STATUS current
        DESCRIPTION
                "License lines limitation"
        -- 1.3.6.1.4.1.2603.4.10.1
        ::= { alActivationLimits 1 }


alPipePerPolicy OBJECT-TYPE
        SYNTAX  Unsigned32
        MAX-ACCESS read-only
        STATUS current
        DESCRIPTION
                "License pipes limitation"
        -- 1.3.6.1.4.1.2603.4.10.2
        ::= { alActivationLimits 2 }


alVcPerPolicy OBJECT-TYPE
        SYNTAX  Unsigned32
        MAX-ACCESS read-only
        STATUS current
        DESCRIPTION
                "License VCs limitation"
        -- 1.3.6.1.4.1.2603.4.10.3
        ::= { alActivationLimits 3 }


alMaxBandwidth OBJECT-TYPE
        SYNTAX  Counter64
        MAX-ACCESS read-only
        STATUS current
        DESCRIPTION
                "License bandwidth limitation in bps"
        -- 1.3.6.1.4.1.2603.4.10.4
        ::= { alActivationLimits 4 }


alMaxConnections OBJECT-TYPE
        SYNTAX  Unsigned32
        MAX-ACCESS read-only
        STATUS current
        DESCRIPTION
                "License connection limitation"
        -- 1.3.6.1.4.1.2603.4.10.5
        ::= { alActivationLimits 5 }


alLTCollectionEnabled OBJECT-TYPE
        SYNTAX  AlEnableDisable
        MAX-ACCESS read-only
        STATUS current
        DESCRIPTION
                "enables or disables long term collection in the server"
        -- 1.3.6.1.4.1.2603.4.11
        ::= { alActivation 11 }


alWebUpdateIsEnabled OBJECT-TYPE
        SYNTAX  AlEnableDisable
        MAX-ACCESS read-only
        STATUS current
        DESCRIPTION
                "Shows whether the license enables web update capability."
        -- 1.3.6.1.4.1.2603.4.12
        ::= { alActivation 12 }


alWebUpdateExpirationDateEnable OBJECT-TYPE
        SYNTAX  AlEnableDisable
        MAX-ACCESS read-only
        STATUS current
        DESCRIPTION
                "Enabling the expiration date for the web update."
        -- 1.3.6.1.4.1.2603.4.13
        ::= { alActivation 13 }


alLicenseInfoTable OBJECT-TYPE
        SYNTAX  SEQUENCE OF AlLicenseInfoEntry
        MAX-ACCESS not-accessible
        STATUS current
        DESCRIPTION
                "License information table"
        -- 1.3.6.1.4.1.2603.4.14
        ::= { alActivation 14 }


alLicenseInfoEntry OBJECT-TYPE
        SYNTAX  AlLicenseInfoEntry
        MAX-ACCESS not-accessible
        STATUS current
        DESCRIPTION ""
        INDEX {
                alLicenseAttrType,
                alLicenseLimitType }
        -- 1.3.6.1.4.1.2603.4.14.1
        ::= { alLicenseInfoTable 1 }


AlLicenseInfoEntry ::= SEQUENCE {

        alLicenseAttrType    INTEGER,
        alLicenseLimitType   INTEGER,
        alLicenseAttrName    DisplayString,
        alLimitValue         Counter64,
        alLicenseStatus      INTEGER,
        alLicenseIsCurrValue AlEnableDisable,
        alLicenseCurrValue   Counter64 }


alLicenseAttrType OBJECT-TYPE
        SYNTAX  INTEGER {
                        global(0),
                        qos(1),
                        rtReportMode(2),
                        ltReportMode(3),
                        vcNumber(4),
                        pipeNumber(5),
                        lineNumber(6),
                        apu(7),
                        websafeEnforce(8),
                        websafeUpdate(9),
                        trafficSteering(10),
                        spMitigation(11),
                        mediaSwift(12),
			spSensor(13),
			mobileReports(14),
			statExport(15),
			tethering(16),
			numOfSupportedDevices(101),
			npp(102),
			countryClassificationSubscr(103),
			netAccounting(104),
			nmsApu(105),
			tieredServices(106),
			tieredServicesGx(107),
			quotaManagement(108),
			volumeReporting(109),
			onlineCharging(110),
			offlineCharging(111) }
        MAX-ACCESS read-only
        STATUS current
        DESCRIPTION
                "Types of license statuses"
        -- 1.3.6.1.4.1.2603.4.14.1.1
        ::= { alLicenseInfoEntry 1 }


alLicenseLimitType OBJECT-TYPE
        SYNTAX  INTEGER {
                        featureState(1),
                        noOfSgcc(2),
                        bandwidth(3),
                        numberOfActiveElements(4),
                        numberOfSubscribers(5),
                        expirationDate(6),
                        activeSubscribersIp(7),
                        activeSubscribers(8) }
        MAX-ACCESS read-only
        STATUS current
        DESCRIPTION
                "Types of license limit"
        -- 1.3.6.1.4.1.2603.4.14.1.2
        ::= { alLicenseInfoEntry 2 }


alLicenseAttrName OBJECT-TYPE
        SYNTAX  DisplayString
        MAX-ACCESS read-only
        STATUS current
        DESCRIPTION ""
        -- 1.3.6.1.4.1.2603.4.14.1.3
        ::= { alLicenseInfoEntry 3 }


alLimitValue OBJECT-TYPE
        SYNTAX  Counter64
        MAX-ACCESS read-only
        STATUS current
        DESCRIPTION ""
        -- 1.3.6.1.4.1.2603.4.14.1.4
        ::= { alLicenseInfoEntry 4 }


alLicenseStatus OBJECT-TYPE
        SYNTAX  INTEGER {
                        licenseValid(1),
                        licenseExpired(2),
                        licenseAbsence(3),
                        licenseInvalid(4) }
        MAX-ACCESS read-only
        STATUS current
        DESCRIPTION "Types of license statuses"
        -- 1.3.6.1.4.1.2603.4.14.1.5
        ::= { alLicenseInfoEntry 5 }


alLicenseIsCurrValue OBJECT-TYPE
        SYNTAX  AlEnableDisable
        MAX-ACCESS read-only
        STATUS current
        DESCRIPTION ""
        -- 1.3.6.1.4.1.2603.4.14.1.6
        ::= { alLicenseInfoEntry 6 }


alLicenseCurrValue OBJECT-TYPE
        SYNTAX  Counter64
        MAX-ACCESS read-only
        STATUS current
        DESCRIPTION ""
        -- 1.3.6.1.4.1.2603.4.14.1.7
        ::= { alLicenseInfoEntry 7 }


alLicenseEventType OBJECT-TYPE
        SYNTAX  INTEGER {
                        noLicense(1),
                        licenseExpired(2),
                        licenseExprWarn(3),
                        invalidLicense(4),
                        licenseLimitBreachWarn(5),
                        licenseLimitBreachSet(6),
                        licenseLimitBreachUnSet(7) }
        MAX-ACCESS read-only
        STATUS current
        DESCRIPTION
                "Types of license statuses"
        -- 1.3.6.1.4.1.2603.4.15
        ::= { alActivation 15 }


-- Scalars and Tables
--

alObjects OBJECT IDENTIFIER 
        -- 1.3.6.1.4.1.2603.5
        ::= { alRegMIB 5 }

alProducts OBJECT IDENTIFIER 
        -- 1.3.6.1.4.1.2603.5.1
        ::= { alObjects 1 }

alAC200 OBJECT-IDENTITY
        STATUS current
        DESCRIPTION
                "AC-20x series: AC-201, AC-202, AC-204"
        -- 1.3.6.1.4.1.2603.5.1.1
        ::= { alProducts 1 }

alAC400 OBJECT-IDENTITY
        STATUS current
        DESCRIPTION
                "AC-40x series: AC-402, AC-404"
        -- 1.3.6.1.4.1.2603.5.1.2
        ::= { alProducts 2 }

alAC800 OBJECT-IDENTITY
        STATUS current
        DESCRIPTION
                "AC-80x series: AC-802, AC-804, AC-808"
        -- 1.3.6.1.4.1.2603.5.1.3
        ::= { alProducts 3 }

alAC1000 OBJECT-IDENTITY
        STATUS current
        DESCRIPTION
                "AC-1000 series: various models of AC-10x0"
        -- 1.3.6.1.4.1.2603.5.1.4
        ::= { alProducts 4 }

alAC2500 OBJECT-IDENTITY
        STATUS current
        DESCRIPTION
                "AC-2500 series: various models of AC-25x0"
        -- 1.3.6.1.4.1.2603.5.1.5
        ::= { alProducts 5 }

alMediationDevice OBJECT-IDENTITY
        STATUS current
        DESCRIPTION
                "Mediation device series: various models (currently Short Time Collector only)"
        -- 1.3.6.1.4.1.2603.5.1.6
        ::= { alProducts 6 }

alSG20 OBJECT-IDENTITY
        STATUS current
        DESCRIPTION
                "SG-20G device( ATCA complient)"
        -- 1.3.6.1.4.1.2603.5.1.7
        ::= { alProducts 7 }

alAC10000 OBJECT-IDENTITY
        STATUS current
        DESCRIPTION
                "AC10K series"
        -- 1.3.6.1.4.1.2603.5.1.8
        ::= { alProducts 8 }

alACSigma OBJECT-IDENTITY
        STATUS current
        DESCRIPTION
                "ACSigma series."
        -- 1.3.6.1.4.1.2603.5.1.9
        ::= { alProducts 9 }

alAC5K OBJECT-IDENTITY
        STATUS current
        DESCRIPTION
                "AC5K series"
        -- 1.3.6.1.4.1.2603.5.1.10
        ::= { alProducts 10 }

alAC3K OBJECT-IDENTITY
        STATUS current
        DESCRIPTION
                "AC3K series"
        -- 1.3.6.1.4.1.2603.5.1.11
        ::= { alProducts 11 }

alAC10K OBJECT-IDENTITY
        STATUS current
        DESCRIPTION
                "new AC10K series"
        -- 1.3.6.1.4.1.2603.5.1.12
        ::= { alProducts 12 }

alAC1K OBJECT-IDENTITY
        STATUS current
        DESCRIPTION
                "AC1K series"
        -- 1.3.6.1.4.1.2603.5.1.13
        ::= { alProducts 13 }

alACSigmaE14 OBJECT-IDENTITY
        STATUS current
        DESCRIPTION
                "SigmaE 14 slots series"
        -- 1.3.6.1.4.1.2603.5.1.14
        ::= { alProducts 14 }

alAC500 OBJECT-IDENTITY
        STATUS current
        DESCRIPTION
                "AC500 series"
        -- 1.3.6.1.4.1.2603.5.1.15
        ::= { alProducts 15 }

alACSigmaE6 OBJECT-IDENTITY
        STATUS current
        DESCRIPTION
                "SigmaE 6 slots series"
        -- 1.3.6.1.4.1.2603.5.1.16
        ::= { alProducts 16 }

alGeneric OBJECT IDENTIFIER 
        -- 1.3.6.1.4.1.2603.5.2
        ::= { alObjects 2 }

alConfigurationName OBJECT-TYPE
        SYNTAX  DisplayString
        MAX-ACCESS read-write
        STATUS current
        DESCRIPTION
                "The name of this configuration 'image'. Is used in case
                of save configuration command."
        -- 1.3.6.1.4.1.2603.5.2.1
        ::= { alGeneric 1 }


alDoubleSession OBJECT-TYPE
        SYNTAX  AlEnableDisableNA
        MAX-ACCESS read-write
        STATUS current
        DESCRIPTION
                "External router and internal server. Enable(1)/Disable(2)/NA(3)"
        -- 1.3.6.1.4.1.2603.5.2.3
        ::= { alGeneric 3 }


alGeneralSystem OBJECT IDENTIFIER 
        -- 1.3.6.1.4.1.2603.5.2.6
        ::= { alGeneric 6 }

alDateTime OBJECT-TYPE
        SYNTAX  DateAndTime
        MAX-ACCESS read-write
        STATUS current
        DESCRIPTION
                "The item provides the ability to synchronize the reporting
                system via SNMP"
        -- 1.3.6.1.4.1.2603.5.2.6.1
        ::= { alGeneralSystem 1 }


alTimeZone OBJECT-TYPE
        SYNTAX  DisplayString
        MAX-ACCESS read-write
        STATUS current
        DESCRIPTION
                "May be used for the reporting purposes."
        -- 1.3.6.1.4.1.2603.5.2.6.2
        ::= { alGeneralSystem 2 }


alIfXTable OBJECT-TYPE
        SYNTAX  SEQUENCE OF AlIfXEntry
        MAX-ACCESS not-accessible
        STATUS current
        DESCRIPTION
                "Allot's extansion to the interface table"
        -- 1.3.6.1.4.1.2603.5.2.6.3
        ::= { alGeneralSystem 3 }


alIfXEntry OBJECT-TYPE
        SYNTAX  AlIfXEntry
        MAX-ACCESS not-accessible
        STATUS current
        DESCRIPTION
                "Entry for the interface table extention"
        INDEX {
                ifIndex }
        -- 1.3.6.1.4.1.2603.5.2.6.3.1
        ::= { alIfXTable 1 }


AlIfXEntry ::= SEQUENCE {

        alIfXMode              INTEGER,
        alIfXType              INTEGER,
        alIfXSpeed             INTEGER,
        alIfXOrder             InterfaceIndexOrZero,
        alIfXLabel             OCTET STRING,
        alIfXSupported         Unsigned32,
        alIfXActualMode        INTEGER,
        alIfXAction            INTEGER,
        alIfXUsage             INTEGER,
        alIfXSwitchId          Unsigned32,
        alIfXSwitchPort        Unsigned32,
        alIfXUsageCapability   Unsigned32,
        alIfXThroughputTX      Counter64,
        alIfXThroughputRX      Counter64,
        alIfXPacketPerSecondTX Counter64,
        alIfXPacketPerSecondRX Counter64, 
        alIfXSTPStatus         AlEnableDisableNA,
        alIfXSTPSupport        Unsigned32 }


alIfXMode OBJECT-TYPE
        SYNTAX  INTEGER {
                        auto(1),
                        fullDuplex(2),
                        halfDuplex(3) }
        MAX-ACCESS read-write
        STATUS current
        DESCRIPTION
                "Auto/half-duplex or full duplex mode"
        DEFVAL { auto }
        -- 1.3.6.1.4.1.2603.5.2.6.3.1.1
        ::= { alIfXEntry 1 }


alIfXType OBJECT-TYPE
        SYNTAX  INTEGER {
                        internal(1),
                        external(2),
                        management(3),
                        bridgeLink(4),
                        tapLink(5),
                        cloneLink(6),
                        other(7),
                        service(8)}
        MAX-ACCESS read-write
        STATUS current
        DESCRIPTION
                "Interface 'role' (Allot specific)."
        DEFVAL { internal }
        -- 1.3.6.1.4.1.2603.5.2.6.3.1.2
        ::= { alIfXEntry 2 }


alIfXSpeed OBJECT-TYPE
        SYNTAX  INTEGER {
                        auto(1),
                        ten(2),
                        hundred(3),
                        thousand(4),
                        tenThousand(5) }
        MAX-ACCESS read-write
        STATUS current
        DESCRIPTION
                "Speed option"
        -- 1.3.6.1.4.1.2603.5.2.6.3.1.3
        ::= { alIfXEntry 3 }


alIfXOrder OBJECT-TYPE
        SYNTAX  InterfaceIndexOrZero
        MAX-ACCESS read-write
        STATUS current
        DESCRIPTION
                "defines the first (source, root) physical interface among all physical interfaces contained in virtual interfaces (e.g. mirror) based on ordered links"
        -- 1.3.6.1.4.1.2603.5.2.6.3.1.4
        ::= { alIfXEntry 4 }


alIfXLabel OBJECT-TYPE
        SYNTAX  OCTET STRING
        MAX-ACCESS read-only
        STATUS current
        DESCRIPTION
                "Administrative name of interface."
        -- 1.3.6.1.4.1.2603.5.2.6.3.1.5
        ::= { alIfXEntry 5 }


alIfXSupported OBJECT-TYPE
        SYNTAX  Unsigned32
        MAX-ACCESS read-only
        STATUS current
        DESCRIPTION
                "Bit mask that describes port options
                Bits 1-12 related to speed and duplex mode.
                   10baseT_Half    -  ( bit 1)
                   10baseT_Full    -  ( bit 2)
                   100baseT_Half   -  ( bit 3)
                   100baseT_Full - ( bit 4)
                   1000baseT_Half - ( bit 5)
                   1000baseT_Full - (bit 6)
                   AUTO - ( bit 7)
                   10000baseT_Half - ( bit 8)
                   10000baseT_Full - (bit 9)
                   FIBRE - ( bit 10)
                   MEDIA_COPPER- (bit 11)
                   STATS_64_BIT -(bit  12)"
        -- 1.3.6.1.4.1.2603.5.2.6.3.1.6
        ::= { alIfXEntry 6 }


alIfXActualMode OBJECT-TYPE
        SYNTAX  INTEGER {
                        auto(1),
                        fullDuplex(2),
                        halfDuplex(3) }
        MAX-ACCESS read-only
        STATUS current
        DESCRIPTION
                "Actual status of duplex mode"
        -- 1.3.6.1.4.1.2603.5.2.6.3.1.7
        ::= { alIfXEntry 7 }


alIfXAction OBJECT-TYPE
        SYNTAX  INTEGER {
                        none(1),
                        pair(2),
                        all(3),
                        bypass(4) }
        MAX-ACCESS read-write
        STATUS current
        DESCRIPTION
                "Defines action in case of interface link down.
                 Possible actions:
                (2) Force 'down' the peering interface
                (3) force down 'all' interfaces
                (4) move the box to the bypass"
        -- 1.3.6.1.4.1.2603.5.2.6.3.1.8
        ::= { alIfXEntry 8 }


alIfXUsage OBJECT-TYPE
        SYNTAX  INTEGER {
                        unknown(1),
                        network(2),
                        indirectRedirect(3),
                        directRedirect(4),
                        clone(5),
                        storage(6),
                        asymmetry(7),
                        management(8),
                        system(9),
                        coreControler(10),
                        flowBalancer(11),
                        host(12),
                        sfc(13),
                        byp(14) }
        MAX-ACCESS read-write
        STATUS current
        DESCRIPTION
                "Shows the current port usage type"
        -- 1.3.6.1.4.1.2603.5.2.6.3.1.9
        ::= { alIfXEntry 9 }


alIfXSwitchId OBJECT-TYPE
        SYNTAX  Unsigned32
        MAX-ACCESS read-only
        STATUS current
        DESCRIPTION
                "Identification of switch, that current interface associated with"
        -- 1.3.6.1.4.1.2603.5.2.6.3.1.10
        ::= { alIfXEntry 10 }


alIfXSwitchPort OBJECT-TYPE
        SYNTAX  Unsigned32
        MAX-ACCESS read-only
        STATUS current
        DESCRIPTION
                "Port index in switch."
        -- 1.3.6.1.4.1.2603.5.2.6.3.1.11
        ::= { alIfXEntry 11 }


alIfXUsageCapability OBJECT-TYPE
        SYNTAX  Unsigned32
        MAX-ACCESS read-only
        STATUS current
        DESCRIPTION
                "Bit mask that describes port usage options
                 network-   (bit 1)
                 indirect redirect-  (bit 2)
                 direct redirect -  (bit 3)
                 clone-     (bit 4)
                 storage-   (bit 5)
                 asymmetry- (bit 6)
                management-   (bit 7)
                system-   (bit 8)"
        -- 1.3.6.1.4.1.2603.5.2.6.3.1.12
        ::= { alIfXEntry 12 }


alIfXThroughputTX OBJECT-TYPE
        SYNTAX  Counter64
        MAX-ACCESS read-only
        STATUS current
        DESCRIPTION
                "Bytes per second for TX"
        -- 1.3.6.1.4.1.2603.5.2.6.3.1.13
        ::= { alIfXEntry 13 }


alIfXThroughputRX OBJECT-TYPE
        SYNTAX  Counter64
        MAX-ACCESS read-only
        STATUS current
        DESCRIPTION
                "Bytes per second for RX"
        -- 1.3.6.1.4.1.2603.5.2.6.3.1.14
        ::= { alIfXEntry 14 }


alIfXPacketPerSecondTX OBJECT-TYPE
        SYNTAX  Counter64
        MAX-ACCESS read-only
        STATUS current
        DESCRIPTION
                "Packet per second for TX"
        -- 1.3.6.1.4.1.2603.5.2.6.3.1.15
        ::= { alIfXEntry 15 }


alIfXPacketPerSecondRX OBJECT-TYPE
        SYNTAX  Counter64
        MAX-ACCESS read-only
        STATUS current
        DESCRIPTION
                "Packet per second for RX"
        -- 1.3.6.1.4.1.2603.5.2.6.3.1.16
        ::= { alIfXEntry 16 }


alIfXSTPStatus OBJECT-TYPE
        SYNTAX  AlEnableDisableNA
        MAX-ACCESS read-write
        STATUS current
        DESCRIPTION
                "Spanning tree status"
        -- 1.3.6.1.4.1.2603.5.2.6.3.1.17
        ::= { alIfXEntry 17 }

        
alIfXSTPSupport OBJECT-TYPE
        SYNTAX  Unsigned32
        MAX-ACCESS read-only
        STATUS current
        DESCRIPTION
                "Bit mask that describes STP options
                 enable-   (bit 1)
                 disable-  (bit 2)
                 notAplicable -  (bit 3)"
        -- 1.3.6.1.4.1.2603.5.2.6.3.1.18
        ::= { alIfXEntry 18 }

        
-- Describes connection interfaces: management interface and connection control (redirection)
-- interface. When management interface is defined as in-band, connection control uses the same 
-- IP address and will be shown equal to the management IP address. If out-of-band management
-- is defined, for connection control purposes other IP interface should be used.
-- DNS and NTP interfaces are defined in data source table  (alDataSourceTable).

alSystemNetwork OBJECT IDENTIFIER 
        -- 1.3.6.1.4.1.2603.5.2.6.4
        ::= { alGeneralSystem 4 }

alHostname OBJECT-TYPE
        SYNTAX  DisplayString
        MAX-ACCESS read-write
        STATUS current
        DESCRIPTION
                "Name of host"
        -- 1.3.6.1.4.1.2603.5.2.6.4.1
        ::= { alSystemNetwork 1 }


alDomainName OBJECT-TYPE
        SYNTAX  DisplayString
        MAX-ACCESS read-write
        STATUS current
        DESCRIPTION
                "Domain name"
        -- 1.3.6.1.4.1.2603.5.2.6.4.2
        ::= { alSystemNetwork 2 }


alInBandGateway OBJECT-TYPE
        SYNTAX  IpAddress
        MAX-ACCESS read-write
        STATUS current
        DESCRIPTION
                "For connection contol (if needed) and in-band management (not AC1000). If OOB exists, the connection control applies proprietary solution for routing."
        -- 1.3.6.1.4.1.2603.5.2.6.4.3
        ::= { alSystemNetwork 3 }


alOutOfBandGateway OBJECT-TYPE
        SYNTAX  IpAddress
        MAX-ACCESS read-write
        STATUS current
        DESCRIPTION
                "Default gateway for out-of-band."
        -- 1.3.6.1.4.1.2603.5.2.6.4.4
        ::= { alSystemNetwork 4 }


alConnRouteTable OBJECT-TYPE
        SYNTAX  SEQUENCE OF AlConnRouteEntry
        MAX-ACCESS not-accessible
        STATUS current
        DESCRIPTION
                "Static routes table"
        -- 1.3.6.1.4.1.2603.5.2.6.4.5
        ::= { alSystemNetwork 5 }


alConnRouteEntry OBJECT-TYPE
        SYNTAX  AlConnRouteEntry
        MAX-ACCESS not-accessible
        STATUS current
        DESCRIPTION ""
        INDEX {
                alConnRouteAddress }
        -- 1.3.6.1.4.1.2603.5.2.6.4.5.1
        ::= { alConnRouteTable 1 }


AlConnRouteEntry ::= SEQUENCE {

        alConnRouteAddress     IpAddress,
        alConnRouteNetMask     IpAddress,
        alConnRouteGateway     IpAddress,
        alConnRouteIfIndex     INTEGER,
        alConnRouteType        INTEGER,
        alConnRouteEntryStatus RowStatus }


alConnRouteAddress OBJECT-TYPE
        SYNTAX  IpAddress
        MAX-ACCESS not-accessible
        STATUS current
        DESCRIPTION
                "Ip address for the entry(host or subnet)"
        -- 1.3.6.1.4.1.2603.5.2.6.4.5.1.1
        ::= { alConnRouteEntry 1 }


alConnRouteNetMask OBJECT-TYPE
        SYNTAX  IpAddress
        MAX-ACCESS read-create
        STATUS current
        DESCRIPTION
                "network mask"
        -- 1.3.6.1.4.1.2603.5.2.6.4.5.1.2
        ::= { alConnRouteEntry 2 }


alConnRouteGateway OBJECT-TYPE
        SYNTAX  IpAddress
        MAX-ACCESS read-create
        STATUS current
        DESCRIPTION
                "IP address for the router of this route"
        -- 1.3.6.1.4.1.2603.5.2.6.4.5.1.3
        ::= { alConnRouteEntry 3 }


alConnRouteIfIndex OBJECT-TYPE
        SYNTAX  INTEGER (1..2147483647)
        MAX-ACCESS read-create
        STATUS current
        DESCRIPTION
                "interface index (ifTable) for the interface of this route"
        -- 1.3.6.1.4.1.2603.5.2.6.4.5.1.4
        ::= { alConnRouteEntry 4 }


alConnRouteType OBJECT-TYPE
        SYNTAX  INTEGER {
                        host(1),
                        net(2) }
        MAX-ACCESS read-create
        STATUS current
        DESCRIPTION
                "destination type (network or host) of this route"
        DEFVAL { host }
        -- 1.3.6.1.4.1.2603.5.2.6.4.5.1.5
        ::= { alConnRouteEntry 5 }


alConnRouteEntryStatus OBJECT-TYPE
        SYNTAX  RowStatus
        MAX-ACCESS read-create
        STATUS current
        DESCRIPTION
                "row status"
        DEFVAL { active }
        -- 1.3.6.1.4.1.2603.5.2.6.4.5.1.6
        ::= { alConnRouteEntry 6 }


alSystemStatus OBJECT IDENTIFIER 
        -- 1.3.6.1.4.1.2603.5.2.6.5
        ::= { alGeneralSystem 5 }

alBypassSetting OBJECT-TYPE
        SYNTAX  INTEGER {
                        standAlone(1),
                        primary(2),
                        secondary(3),
                        notConnected(4) }
        MAX-ACCESS read-only
        STATUS current
        DESCRIPTION
                "In parallel redundancy only.
                The setting is read from   the hardware."
        -- 1.3.6.1.4.1.2603.5.2.6.5.1
        ::= { alSystemStatus 1 }


alPower OBJECT-TYPE
        SYNTAX  INTEGER {
                        ok(1),
                        problem0(2),
                        problem1(3),
                        notApplicable(4) }
        MAX-ACCESS read-only
        STATUS current
        DESCRIPTION
                "Status in power suplies:
                1-OK,
                2- problem in ps0,
                3- problem in ps1
                4- not applicable"
        -- 1.3.6.1.4.1.2603.5.2.6.5.2
        ::= { alSystemStatus 2 }


alFan OBJECT-TYPE
        SYNTAX  INTEGER {
                        unknown(1),
                        ok(2),
                        problem(3) }
        MAX-ACCESS read-only
        STATUS current
        DESCRIPTION
                "Status of fans: 1- unknown, 2-OK, 3-problem."
        -- 1.3.6.1.4.1.2603.5.2.6.5.3
        ::= { alSystemStatus 3 }


alRemoteBypass OBJECT-TYPE
        SYNTAX  AlActiveStandbyStatus
        MAX-ACCESS read-only
        STATUS current
        DESCRIPTION
                "Bypass status for the remote unit"
        -- 1.3.6.1.4.1.2603.5.2.6.5.4
        ::= { alSystemStatus 4 }


alBypass OBJECT-TYPE
        SYNTAX  AlActiveStandbyStatus
        MAX-ACCESS read-only
        STATUS current
        DESCRIPTION
                "Bypass status"
        -- 1.3.6.1.4.1.2603.5.2.6.5.5
        ::= { alSystemStatus 5 }


alSystemSecurity OBJECT IDENTIFIER 
        -- 1.3.6.1.4.1.2603.5.2.6.6
        ::= { alGeneralSystem 6 }

alHTTPConnectionMode OBJECT-TYPE
        SYNTAX  AlEnableDisableNA
        MAX-ACCESS read-write
        STATUS current
        DESCRIPTION
                "Enable/ disable unsecure uaccess to HTTP
                port (enable -unsecure access, disable -secure access only, NA)"
        -- 1.3.6.1.4.1.2603.5.2.6.6.1
        ::= { alSystemSecurity 1 }


alTelnetAccess OBJECT-TYPE
        SYNTAX  AlEnableDisable
        MAX-ACCESS read-write
        STATUS current
        DESCRIPTION
                "is telnet access allowed"
        -- 1.3.6.1.4.1.2603.5.2.6.6.2
        ::= { alSystemSecurity 2 }


alPingReply OBJECT-TYPE
        SYNTAX  AlEnableDisable
        MAX-ACCESS read-write
        STATUS current
        DESCRIPTION
                "Is ping reply allowed?"
        -- 1.3.6.1.4.1.2603.5.2.6.6.3
        ::= { alSystemSecurity 3 }


alEnhancedTcpSecurity OBJECT-TYPE
        SYNTAX  AlEnableDisable
        MAX-ACCESS read-write
        STATUS current
        DESCRIPTION
                "Is enhanced TCP security allowed?

                "
        -- 1.3.6.1.4.1.2603.5.2.6.6.4
        ::= { alSystemSecurity 4 }


alLcdConfigEnable OBJECT-TYPE
        SYNTAX  AlEnableDisableNA
        MAX-ACCESS read-write
        STATUS current
        DESCRIPTION
                "Allows management from box LCD control panel.
                (Enable/Disable/NA)"
        -- 1.3.6.1.4.1.2603.5.2.6.6.5
        ::= { alSystemSecurity 5 }


alConnectionTimeout OBJECT-TYPE
        SYNTAX  Integer32
        MAX-ACCESS read-write
        STATUS current
        DESCRIPTION
                "The timeout while connected via console
                or telnet. The shells will automatically logout
                after the specified number of seconds. If 0 -
                no automatic logout"
        -- 1.3.6.1.4.1.2603.5.2.6.6.6
        ::= { alSystemSecurity 6 }


alACTable OBJECT-TYPE
        SYNTAX  SEQUENCE OF AlACEntry
        MAX-ACCESS not-accessible
        STATUS current
        DESCRIPTION
                "Access list: IP addresses that are allowed to
                connect to the box."
        -- 1.3.6.1.4.1.2603.5.2.6.6.7
        ::= { alSystemSecurity 7 }


alACEntry OBJECT-TYPE
        SYNTAX  AlACEntry
        MAX-ACCESS not-accessible
        STATUS current
        DESCRIPTION
                "Entry of the access control table"
        INDEX {
                alACIPAddr }
        -- 1.3.6.1.4.1.2603.5.2.6.6.7.1
        ::= { alACTable 1 }


AlACEntry ::= SEQUENCE {

        alACIPAddr    IpAddress,
        alACDescr     DisplayString,
        alACRowStatus RowStatus }


alACIPAddr OBJECT-TYPE
        SYNTAX  IpAddress
        MAX-ACCESS not-accessible
        STATUS current
        DESCRIPTION
                "IP address of the entry"
        -- 1.3.6.1.4.1.2603.5.2.6.6.7.1.1
        ::= { alACEntry 1 }


alACDescr OBJECT-TYPE
        SYNTAX  DisplayString
        MAX-ACCESS read-create
        STATUS current
        DESCRIPTION
                "Description"
        -- 1.3.6.1.4.1.2603.5.2.6.6.7.1.2
        ::= { alACEntry 2 }


alACRowStatus OBJECT-TYPE
        SYNTAX  RowStatus
        MAX-ACCESS read-create
        STATUS current
        DESCRIPTION
                "This variable is used for create, modify, and/or
                delete a row in this table."
        -- 1.3.6.1.4.1.2603.5.2.6.6.7.1.3
        ::= { alACEntry 3 }


alSshSecurity OBJECT-TYPE
        SYNTAX  AlEnableDisable
        MAX-ACCESS read-write
        STATUS current
        DESCRIPTION
                "Is SSH allowed?"
        -- 1.3.6.1.4.1.2603.5.2.6.6.8
        ::= { alSystemSecurity 8 }


alIpXAddrTable OBJECT-TYPE
        SYNTAX  SEQUENCE OF AlIpXAddrEntry
        MAX-ACCESS not-accessible
        STATUS current
        DESCRIPTION
                "Extension to ipIfXTable - serves for managing the IP adresses  (add/remove)
                and contains one additional parameter - VLAN tag"
        -- 1.3.6.1.4.1.2603.5.2.6.7
        ::= { alGeneralSystem 7 }


alIpXAddrEntry OBJECT-TYPE
        SYNTAX  AlIpXAddrEntry
        MAX-ACCESS not-accessible
        STATUS current
        DESCRIPTION ""
        INDEX {
                ifIndex }
        -- 1.3.6.1.4.1.2603.5.2.6.7.1
        ::= { alIpXAddrTable 1 }


AlIpXAddrEntry ::= SEQUENCE {

        alIpXAddr        IpAddress,
        alIpXNetMask     IpAddress,
        alIpXVlan        Integer32,
        alIpXEntryStatus RowStatus }


alIpXAddr OBJECT-TYPE
        SYNTAX  IpAddress
        MAX-ACCESS read-create
        STATUS current
        DESCRIPTION
                "The IP address to which this entry's addressing information
                pertains."
        -- 1.3.6.1.4.1.2603.5.2.6.7.1.1
        ::= { alIpXAddrEntry 1 }


alIpXNetMask OBJECT-TYPE
        SYNTAX  IpAddress
        MAX-ACCESS read-create
        STATUS current
        DESCRIPTION
                "The subnet mask associated with the IP address of this
                entry.  The value of the mask is an IP address with all the
                network bits set to 1 and all the hosts bits set to 0."
        -- 1.3.6.1.4.1.2603.5.2.6.7.1.2
        ::= { alIpXAddrEntry 2 }


alIpXVlan OBJECT-TYPE
        SYNTAX  Integer32
        MAX-ACCESS read-create
        STATUS current
        DESCRIPTION
                "VLAN tag"
        -- 1.3.6.1.4.1.2603.5.2.6.7.1.3
        ::= { alIpXAddrEntry 3 }


alIpXEntryStatus OBJECT-TYPE
        SYNTAX  RowStatus
        MAX-ACCESS read-create
        STATUS current
        DESCRIPTION
                "row status"
        DEFVAL { active }
        -- 1.3.6.1.4.1.2603.5.2.6.7.1.4
        ::= { alIpXAddrEntry 4 }


alMode OBJECT-TYPE
        SYNTAX  INTEGER {
                        regular(1),
                        tap(2),
                        nonApplicable(3) }
        MAX-ACCESS read-write
        STATUS current
        DESCRIPTION
                "Controls the working mode of box:
                1- regular,
                2-TAP,
                3-nonApplicable"
        -- 1.3.6.1.4.1.2603.5.2.6.8
        ::= { alGeneralSystem 8 }


alLearningBridge OBJECT-TYPE
        SYNTAX  AlEnableDisableNA
        MAX-ACCESS read-write
        STATUS current
        DESCRIPTION
                "Status of learning for the bridge function (on/off/NA)."
        -- 1.3.6.1.4.1.2603.5.2.6.9
        ::= { alGeneralSystem 9 }


alSPTStatus OBJECT-TYPE
        SYNTAX  AlEnableDisableNA
        MAX-ACCESS read-write
        STATUS current
        DESCRIPTION
                "Spanning tree status"
        -- 1.3.6.1.4.1.2603.5.2.6.10
        ::= { alGeneralSystem 10 }


alRedunduncyMode OBJECT-TYPE
        SYNTAX  INTEGER {
                        standalone(1),
                        parallel(2),
                        serial(3),
                        active(4) }
        MAX-ACCESS read-write
        STATUS current
        DESCRIPTION
                "Choice of redundancy model"
        -- 1.3.6.1.4.1.2603.5.2.6.11
        ::= { alGeneralSystem 11 }


alBoxSerialNumber OBJECT-TYPE
        SYNTAX  DisplayString
        MAX-ACCESS read-only
        STATUS current
        DESCRIPTION
                "Serial number of the box. Identifies the current
                product instance."
        -- 1.3.6.1.4.1.2603.5.2.6.12
        ::= { alGeneralSystem 12 }


alSoftwareVersion OBJECT-TYPE
        SYNTAX  DisplayString
        MAX-ACCESS read-only
        STATUS current
        DESCRIPTION
                "Identification of the software version"
        -- 1.3.6.1.4.1.2603.5.2.6.13
        ::= { alGeneralSystem 13 }


alBackplaneVersion OBJECT-TYPE
        SYNTAX  DisplayString
        MAX-ACCESS read-only
        STATUS current
        DESCRIPTION
                "Backplane (hardware) version."
        -- 1.3.6.1.4.1.2603.5.2.6.14
        ::= { alGeneralSystem 14 }


alPosIfTable OBJECT-TYPE
        SYNTAX  SEQUENCE OF AlPosIfEntry
        MAX-ACCESS not-accessible
        STATUS current
        DESCRIPTION
                "Configuration of POS."
        -- 1.3.6.1.4.1.2603.5.2.6.15
        ::= { alGeneralSystem 15 }


alPosIfEntry OBJECT-TYPE
        SYNTAX  AlPosIfEntry
        MAX-ACCESS not-accessible
        STATUS current
        DESCRIPTION ""
        INDEX {
                alPosIfIndex }
        -- 1.3.6.1.4.1.2603.5.2.6.15.1
        ::= { alPosIfTable 1 }


AlPosIfEntry ::= SEQUENCE {

        alPosIfIndex         Unsigned32,
        alPosIfType          INTEGER,
        alPosIfFraming       INTEGER,
        alPosIfCrc           INTEGER,
        alPosIfClocking      INTEGER,
        alPosIfScrambling    AlEnableDisable,
        alPosIfEncapsulation INTEGER,
        alPosIfMtu           INTEGER }


alPosIfIndex OBJECT-TYPE
        SYNTAX  Unsigned32
        MAX-ACCESS not-accessible
        STATUS current
        DESCRIPTION ""
        -- 1.3.6.1.4.1.2603.5.2.6.15.1.1
        ::= { alPosIfEntry 1 }


alPosIfType OBJECT-TYPE
        SYNTAX  INTEGER {
                        oc3(1),
                        oc12c(2),
                        oc12(3),
                        oc48c(4),
                        oc48(5) }
        MAX-ACCESS read-write
        STATUS current
        DESCRIPTION
                "Type of POS port"
        DEFVAL { oc12 }
        -- 1.3.6.1.4.1.2603.5.2.6.15.1.2
        ::= { alPosIfEntry 2 }


alPosIfFraming OBJECT-TYPE
        SYNTAX  INTEGER {
                        sdh(1),
                        sonet(2) }
        MAX-ACCESS read-write
        STATUS current
        DESCRIPTION ""
        DEFVAL { sonet }
        -- 1.3.6.1.4.1.2603.5.2.6.15.1.3
        ::= { alPosIfEntry 3 }


alPosIfCrc OBJECT-TYPE
        SYNTAX  INTEGER {
                        crc16(16),
                        crc32(32) }
        MAX-ACCESS read-write
        STATUS current
        DESCRIPTION ""
        DEFVAL { crc32 }
        -- 1.3.6.1.4.1.2603.5.2.6.15.1.4
        ::= { alPosIfEntry 4 }


alPosIfClocking OBJECT-TYPE
        SYNTAX  INTEGER {
                        internal(1),
                        external0(2),
                        external1(3) }
        MAX-ACCESS read-write
        STATUS current
        DESCRIPTION ""
        DEFVAL { external0 }
        -- 1.3.6.1.4.1.2603.5.2.6.15.1.5
        ::= { alPosIfEntry 5 }


alPosIfScrambling OBJECT-TYPE
        SYNTAX  AlEnableDisable
        MAX-ACCESS read-write
        STATUS current
        DESCRIPTION ""
        DEFVAL { enabled }
        -- 1.3.6.1.4.1.2603.5.2.6.15.1.6
        ::= { alPosIfEntry 6 }


alPosIfEncapsulation OBJECT-TYPE
        SYNTAX  INTEGER {
                        ppp(1),
                        chdlc(2),
                        frameRelay(3) }
        MAX-ACCESS read-write
        STATUS current
        DESCRIPTION ""
        -- 1.3.6.1.4.1.2603.5.2.6.15.1.7
        ::= { alPosIfEntry 7 }


alPosIfMtu OBJECT-TYPE
        SYNTAX  INTEGER (64..14336)
        MAX-ACCESS read-write
        STATUS current
        DESCRIPTION ""
        -- 1.3.6.1.4.1.2603.5.2.6.15.1.8
        ::= { alPosIfEntry 8 }


alRedundancyCap OBJECT-TYPE
        SYNTAX  Integer32
        MAX-ACCESS read-only
        STATUS current
        DESCRIPTION
                "Bit-mask of the redundancy options,
                depending of the hardware platform.
                0x1 mask- parallel;
                0x2 mask-serial;
                0x4 mask- active"
        -- 1.3.6.1.4.1.2603.5.2.6.16
        ::= { alGeneralSystem 16 }


alBypassUnit OBJECT-TYPE
        SYNTAX  AlEnableDisable
        MAX-ACCESS read-write
        STATUS current
        DESCRIPTION
                "Enable/disable the usage of the bypass unit"
        -- 1.3.6.1.4.1.2603.5.2.6.17
        ::= { alGeneralSystem 17 }


alDeviceBWLimits OBJECT IDENTIFIER 
        -- 1.3.6.1.4.1.2603.5.2.6.18
        ::= { alGeneralSystem 18 }

alDeviceBWLimitsType OBJECT-TYPE
        SYNTAX  INTEGER {
                        fullDuplexEach(1),
                        fullDuplexBoth(2),
                        halfDuplex(3) }
        MAX-ACCESS read-write
        STATUS current
        DESCRIPTION
                "Defines the working mode of the device"
        -- 1.3.6.1.4.1.2603.5.2.6.18.1
        ::= { alDeviceBWLimits 1 }


alDeviceBWLimitsOutbound OBJECT-TYPE
        SYNTAX  Integer32
        MAX-ACCESS read-write
        STATUS current
        DESCRIPTION
                "Maximum value (in Kbits/sec) for outbound (internal) direction speed
                The value has range of min=1, max=Licenesed maximum
                value of 0 (zero) stands for device maximum"
        -- 1.3.6.1.4.1.2603.5.2.6.18.2
        ::= { alDeviceBWLimits 2 }


alDeviceBWLimitsInbound OBJECT-TYPE
        SYNTAX  Integer32
        MAX-ACCESS read-write
        STATUS current
        DESCRIPTION
                "Maximum value (in Kbits/sec) for inbound (external) direction speed
                The value has range of min=1, max=Licenesed maximum
                value of 0 (zero) stands for device maximum"
        -- 1.3.6.1.4.1.2603.5.2.6.18.3
        ::= { alDeviceBWLimits 3 }


alSystemCOC OBJECT IDENTIFIER 
        -- 1.3.6.1.4.1.2603.5.2.6.19
        ::= { alGeneralSystem 19 }

alCocServerTimeOut OBJECT-TYPE
        SYNTAX  Integer32
        MAX-ACCESS read-write
        STATUS current
        DESCRIPTION
                "COC server time out"
        DEFVAL { 0 }
        -- 1.3.6.1.4.1.2603.5.2.6.19.1
        ::= { alSystemCOC 1 }


alCocServerRetries OBJECT-TYPE
        SYNTAX  Integer32
        MAX-ACCESS read-write
        STATUS current
        DESCRIPTION
                "COC server retries"
        DEFVAL { 0 }
        -- 1.3.6.1.4.1.2603.5.2.6.19.2
        ::= { alSystemCOC 2 }


alCocServerPeriod OBJECT-TYPE
        SYNTAX  Integer32
        MAX-ACCESS read-write
        STATUS current
        DESCRIPTION
                "COC server period"
        DEFVAL { 0 }
        -- 1.3.6.1.4.1.2603.5.2.6.19.3
        ::= { alSystemCOC 3 }


alCocServiceTimeOut OBJECT-TYPE
        SYNTAX  Integer32
        MAX-ACCESS read-write
        STATUS current
        DESCRIPTION
                "COC service time out"
        DEFVAL { 0 }
        -- 1.3.6.1.4.1.2603.5.2.6.19.4
        ::= { alSystemCOC 4 }


alCocServiceRetries OBJECT-TYPE
        SYNTAX  Integer32
        MAX-ACCESS read-write
        STATUS current
        DESCRIPTION
                "COC service retries"
        DEFVAL { 0 }
        -- 1.3.6.1.4.1.2603.5.2.6.19.5
        ::= { alSystemCOC 5 }


alCocServicerPeriod OBJECT-TYPE
        SYNTAX  Integer32
        MAX-ACCESS read-write
        STATUS current
        DESCRIPTION
                "COC server period"
        DEFVAL { 0 }
        -- 1.3.6.1.4.1.2603.5.2.6.19.6
        ::= { alSystemCOC 6 }


alCocTrackerMAC OBJECT-TYPE
        SYNTAX  OCTET STRING
        MAX-ACCESS read-write
        STATUS current
        DESCRIPTION
                "COC tracker MAC address"
        -- 1.3.6.1.4.1.2603.5.2.6.19.7
        ::= { alSystemCOC 7 }


alCocRedirectionMAC OBJECT-TYPE
        SYNTAX  OCTET STRING
        MAX-ACCESS read-write
        STATUS current
        DESCRIPTION
                "COC redirection MAC address"
        -- 1.3.6.1.4.1.2603.5.2.6.19.8
        ::= { alSystemCOC 8 }


alCocUseIp OBJECT-TYPE
        SYNTAX  AlEnableDisableNA
        MAX-ACCESS read-write
        STATUS current
        DESCRIPTION
                "If COC uses IP"
        DEFVAL { notAplicable }
        -- 1.3.6.1.4.1.2603.5.2.6.19.9
        ::= { alSystemCOC 9 }


alCocRedirectionPort OBJECT-TYPE
        SYNTAX  AlEnableDisable
        MAX-ACCESS read-write
        STATUS current
        DESCRIPTION
                "Coc redirection of ports"
        DEFVAL { disabled }
        -- 1.3.6.1.4.1.2603.5.2.6.19.10
        ::= { alSystemCOC 10 }


alInternalRedundancy OBJECT IDENTIFIER 
        -- 1.3.6.1.4.1.2603.5.2.6.20
        ::= { alGeneralSystem 20 }

alBoardTable OBJECT-TYPE
        SYNTAX  SEQUENCE OF AlBoardEntry
        MAX-ACCESS not-accessible
        STATUS current
        DESCRIPTION ""
        -- 1.3.6.1.4.1.2603.5.2.6.20.1
        ::= { alInternalRedundancy 1 }


alBoardEntry OBJECT-TYPE
        SYNTAX  AlBoardEntry
        MAX-ACCESS not-accessible
        STATUS current
        DESCRIPTION ""
        INDEX {
                alBoardId }
        -- 1.3.6.1.4.1.2603.5.2.6.20.1.1
        ::= { alBoardTable 1 }


AlBoardEntry ::= SEQUENCE {

        alBoardId               Unsigned32,
        alBoardType             INTEGER,
        alBoardSerialNumber     DisplayString,
        alBoardSoftwareVersion  DisplayString,
        alBoardHardwareVersion  DisplayString,
        alBoardSoftwareStatus   INTEGER,
        alBoardHWStatus         INTEGER,
        alBoardTemperatureRange INTEGER }


alBoardId OBJECT-TYPE
        SYNTAX  Unsigned32
        MAX-ACCESS not-accessible
        STATUS current
        DESCRIPTION
                "represents slot number of board"
        -- 1.3.6.1.4.1.2603.5.2.6.20.1.1.1
        ::= { alBoardEntry 1 }


alBoardType OBJECT-TYPE
        SYNTAX  INTEGER {
                        thirdParty(1),
                        apc(2),
                        dpic(3),
                        host(4),
                        byc(5),
                        spider(6),
                        scorpion(7),
                        switch(8),
                        dispatcher(9),
                        byp(10),
                        vas(11),
                        exc-cc(13),                     
                        exc-sbh(14),
                        nex-1(15)
                        }
        MAX-ACCESS read-only
        STATUS current
        DESCRIPTION
                "describes type of board:
                1- third party board
                2- APC board
                3- DPIC board
                4- Host board
                5- BYC (bypass & switch)
                6- Spider
                7- Scorpion
                8- Switch
                9- Dispatcher
                10 - BYP
                11- VAS
                13- EXC Core Controller
                14- EXC Switch Balancer Host
                15- NSS NetExpand NEX-1"
        -- 1.3.6.1.4.1.2603.5.2.6.20.1.1.2
        ::= { alBoardEntry 2 }


alBoardSerialNumber OBJECT-TYPE
        SYNTAX  DisplayString
        MAX-ACCESS read-only
        STATUS current
        DESCRIPTION
                "Serial number of board (taken from this boad)"
        -- 1.3.6.1.4.1.2603.5.2.6.20.1.1.3
        ::= { alBoardEntry 3 }


alBoardSoftwareVersion OBJECT-TYPE
        SYNTAX  DisplayString
        MAX-ACCESS read-only
        STATUS current
        DESCRIPTION
                "Version of software, which running on the board"
        -- 1.3.6.1.4.1.2603.5.2.6.20.1.1.4
        ::= { alBoardEntry 4 }


alBoardHardwareVersion OBJECT-TYPE
        SYNTAX  DisplayString
        MAX-ACCESS read-only
        STATUS current
        DESCRIPTION
                "Hardware version of board"
        -- 1.3.6.1.4.1.2603.5.2.6.20.1.1.5
        ::= { alBoardEntry 5 }


alBoardSoftwareStatus OBJECT-TYPE
        SYNTAX  INTEGER {
                notActive(1),
                active(2),
                standBy(3),
                notApplicable(4) }
        MAX-ACCESS read-only
        STATUS current
        DESCRIPTION
                "Shows status of software on the board:
                (1)-notActive (Bypass for DPIC)
                (2)-active
                (3)-standBy
                (4)-notApplicable"
        -- 1.3.6.1.4.1.2603.5.2.6.20.1.1.6
        ::= { alBoardEntry 6 }


alBoardHWStatus OBJECT-TYPE
        SYNTAX  INTEGER {
                        off(1),
                        on(2) }
        MAX-ACCESS read-only
        STATUS current
        DESCRIPTION
                "Shows physical status of card:
                (1) - off (no power or not existed)
                (2) - on (OK)"
        -- 1.3.6.1.4.1.2603.5.2.6.20.1.1.7
        ::= { alBoardEntry 7 }


alBoardTemperatureRange OBJECT-TYPE
        SYNTAX  INTEGER {
                        low(1),
                        middle(2),
                        high(3) }
        MAX-ACCESS read-only
        STATUS current
        DESCRIPTION
                "Temperature threshold ranges are defined in the following way:
                Below Non-Critical Threshold - Low range
                Between Non-Critical and Critical Threshold - Middle range
                Between Critical and Non-Recoverable Threshold - High Range"
        -- 1.3.6.1.4.1.2603.5.2.6.20.1.1.8
        ::= { alBoardEntry 8 }


alInternalDispatchMode OBJECT-TYPE
        SYNTAX  INTEGER {
                        dynamicDispatch(1),
                        staticDispatch(2) }
        MAX-ACCESS read-write
        STATUS current
        DESCRIPTION
                "Controls traffic dispatching mechanism:
                1- Dynamic dispatching mode- the system distributes the traffic automatically between the different QoS devices.
                2- Static dispatching mode- the system associates every network segment (line) with a QoS device."
        -- 1.3.6.1.4.1.2603.5.2.6.20.2
        ::= { alInternalRedundancy 2 }


alInternalMinDevNum OBJECT-TYPE
        SYNTAX  Integer32
        MAX-ACCESS read-write
        STATUS current
        DESCRIPTION
                "Minimal number of active Qos devices for activation of system."
        -- 1.3.6.1.4.1.2603.5.2.6.20.3
        ::= { alInternalRedundancy 3 }


alInternalRedundancyDevNum OBJECT-TYPE
        SYNTAX  Integer32
        MAX-ACCESS read-write
        STATUS current
        DESCRIPTION
                "Number of QoS devices in standby mode."
        -- 1.3.6.1.4.1.2603.5.2.6.20.4
        ::= { alInternalRedundancy 4 }


alInternalActiveDevNum OBJECT-TYPE
        SYNTAX  Integer32
        MAX-ACCESS read-write
        STATUS current
        DESCRIPTION
                "Number of QoS devices in ACTIVE mode in same time."
        -- 1.3.6.1.4.1.2603.5.2.6.20.5
        ::= { alInternalRedundancy 5 }


alInternalRateLimit OBJECT-TYPE
        SYNTAX  Integer32
        MAX-ACCESS read-write
        STATUS current
        DESCRIPTION
                "Maximum bandwidth for QoS device (in Kbytes/sec)."
        -- 1.3.6.1.4.1.2603.5.2.6.20.6
        ::= { alInternalRedundancy 6 }


alWebUpdate OBJECT IDENTIFIER 
        -- 1.3.6.1.4.1.2603.5.2.6.21
        ::= { alGeneralSystem 21 }

alBaseVersion OBJECT-TYPE
        SYNTAX  DisplayString
        MAX-ACCESS read-only
        STATUS current
        DESCRIPTION
                "Holds the base version of the protocols engine"
        -- 1.3.6.1.4.1.2603.5.2.6.21.1
        ::= { alWebUpdate 1 }


alCurrentVersion OBJECT-TYPE
        SYNTAX  Integer32
        MAX-ACCESS read-only
        STATUS current
        DESCRIPTION
                "The version of the current protocols engine."
        -- 1.3.6.1.4.1.2603.5.2.6.21.2
        ::= { alWebUpdate 2 }


alLastUpdateStatus OBJECT-TYPE
        SYNTAX  INTEGER {
                        success(1),
                        generalError(2),
                        wrongVersion(3),
                        wrongFormat(4),
                        binaryFileCorrupted(5),
                        aSyncSwapRequest(6),
                        requestTimeout(7) }
        MAX-ACCESS read-only
        STATUS current
        DESCRIPTION
                "The error code of the last attempted web update.
                Error codes are:
                1  Success
                2  General Error
                3  Wrong version
                4  XML file format is wrong
                5  Binary file corrupted
                6  A-Sync swap request
                7  Request Timeout"
        DEFVAL { success }
        -- 1.3.6.1.4.1.2603.5.2.6.21.3
        ::= { alWebUpdate 3 }


alUserDefinedSignature OBJECT IDENTIFIER 
        -- 1.3.6.1.4.1.2603.5.2.6.22
        ::= { alGeneralSystem 22 }

alUDSState OBJECT-TYPE
        SYNTAX  AlEnableDisable
        MAX-ACCESS read-write
        STATUS current
        DESCRIPTION
                "Condition of 'User Defined Signature' feature"
        DEFVAL { disabled }
        -- 1.3.6.1.4.1.2603.5.2.6.22.1
        ::= { alUserDefinedSignature 1 }


alAsymmetric OBJECT IDENTIFIER 
        -- 1.3.6.1.4.1.2603.5.2.6.23
        ::= { alGeneralSystem 23 }

alAsymmetricGroupId OBJECT-TYPE
        SYNTAX  Integer32 (0..7 | 255)
        MAX-ACCESS read-write
        STATUS current
        DESCRIPTION
                "Define the asymmetric group ID of the local device"
        DEFVAL { 0 }
        -- 1.3.6.1.4.1.2603.5.2.6.23.1
        ::= { alAsymmetric 1 }


alAsymmetricOwnDeviceId OBJECT-TYPE
        SYNTAX  Integer32
        MAX-ACCESS read-write
        STATUS current
        DESCRIPTION
                "Local device ID within the asymmetric group"
        -- 1.3.6.1.4.1.2603.5.2.6.23.2
        ::= { alAsymmetric 2 }


alAsymmetricHealthCheck OBJECT-TYPE
        SYNTAX  AlEnableDisable
        MAX-ACCESS read-write
        STATUS current
        DESCRIPTION
                "Enables health check of communication channel to remote devices in the asymmetric group"
        DEFVAL { disabled }
        -- 1.3.6.1.4.1.2603.5.2.6.23.3
        ::= { alAsymmetric 3 }


alAsymmetricTransportType OBJECT-TYPE
        SYNTAX  INTEGER {
                        point2point(1),
                        mac(2),
                        ip(3) }
        MAX-ACCESS read-write
        STATUS current
        DESCRIPTION
                "Transport type of communication channel to remote devices in the asymmetric group:
                -  L2 p2p (point to point)
                -  L2 Bridge (MAC forwarding)
                -  L3 (Future)"
        DEFVAL { point2point }
        -- 1.3.6.1.4.1.2603.5.2.6.23.5
        ::= { alAsymmetric 5 }


alAsymmetricEnable OBJECT-TYPE
        SYNTAX  AlEnableDisable
        MAX-ACCESS read-write
        STATUS current
        DESCRIPTION
                "Enables asymmetry capabilities on device"
        DEFVAL { disabled }
        -- 1.3.6.1.4.1.2603.5.2.6.23.6
        ::= { alAsymmetric 6 }


alAsymmetricDeviceTable OBJECT-TYPE
        SYNTAX  SEQUENCE OF AlAsymmetricDeviceEntry
        MAX-ACCESS not-accessible
        STATUS current
        DESCRIPTION
                "List of remote devices in the asymmetric group where the local device is member"
        -- 1.3.6.1.4.1.2603.5.2.6.23.7
        ::= { alAsymmetric 7 }


alAsymmetricDeviceEntry OBJECT-TYPE
        SYNTAX  AlAsymmetricDeviceEntry
        MAX-ACCESS not-accessible
        STATUS current
        DESCRIPTION ""
        INDEX {
                alAsymmetricRemoteDeviceId }
        -- 1.3.6.1.4.1.2603.5.2.6.23.7.1
        ::= { alAsymmetricDeviceTable 1 }


AlAsymmetricDeviceEntry ::= SEQUENCE {

        alAsymmetricRemoteDeviceId    Unsigned32,
        alAsymmetricControlVLAN       Integer32,
        alAsymmetricPort              Integer32,
        alAsymmetricMAC               OCTET STRING,
        alAsymmetricIP                IpAddress,
        alAsymmetricHealthCheckStatus INTEGER,
        alAsymmetricEntryStatus       RowStatus }


alAsymmetricRemoteDeviceId OBJECT-TYPE
        SYNTAX  Unsigned32
        MAX-ACCESS not-accessible
        STATUS current
        DESCRIPTION
                "Device ID (in the asymmetric group) of remote device"
        -- 1.3.6.1.4.1.2603.5.2.6.23.7.1.1
        ::= { alAsymmetricDeviceEntry 1 }


alAsymmetricControlVLAN OBJECT-TYPE
        SYNTAX  Integer32
        MAX-ACCESS read-create
        STATUS current
        DESCRIPTION
                "VLAN ID Used to carry asymmetric control traffic of flows. Use if transport type is p2p"
        -- 1.3.6.1.4.1.2603.5.2.6.23.7.1.2
        ::= { alAsymmetricDeviceEntry 2 }


alAsymmetricPort OBJECT-TYPE
        SYNTAX  Integer32
        MAX-ACCESS read-create
        STATUS current
        DESCRIPTION
                "Asymmetric control port (interface). Must be one of ifIndex."
        -- 1.3.6.1.4.1.2603.5.2.6.23.7.1.4
        ::= { alAsymmetricDeviceEntry 4 }


alAsymmetricMAC OBJECT-TYPE
        SYNTAX  OCTET STRING
        MAX-ACCESS read-create
        STATUS current
        DESCRIPTION
                "MAC address of remote device. Used to send control traffic to remote device incase transport is MAC based"
        DEFVAL { "00 00 00 00 00" }
        -- 1.3.6.1.4.1.2603.5.2.6.23.7.1.5
        ::= { alAsymmetricDeviceEntry 5 }


alAsymmetricIP OBJECT-TYPE
        SYNTAX  IpAddress
        MAX-ACCESS read-create
        STATUS current
        DESCRIPTION
                "IP address of remote device. Used to send control traffic to remote device incase transport is IP (L3)based"
        -- 1.3.6.1.4.1.2603.5.2.6.23.7.1.6
        ::= { alAsymmetricDeviceEntry 6 }


alAsymmetricHealthCheckStatus OBJECT-TYPE
        SYNTAX  INTEGER {
                        notApplicable(1),
                        up(2),
                        down(3) }
        MAX-ACCESS read-only
        STATUS current
        DESCRIPTION
                "Health check status: Up = Check enabled and ok; Down = Check enabled and failed; notApplicable = Check disabled"
        -- 1.3.6.1.4.1.2603.5.2.6.23.7.1.7
        ::= { alAsymmetricDeviceEntry 7 }


alAsymmetricEntryStatus OBJECT-TYPE
        SYNTAX  RowStatus
        MAX-ACCESS read-create
        STATUS current
        DESCRIPTION
                "Control for creating and deleting entries"
        -- 1.3.6.1.4.1.2603.5.2.6.23.7.1.8
        ::= { alAsymmetricDeviceEntry 8 }


alServiceActivation OBJECT IDENTIFIER 
        -- 1.3.6.1.4.1.2603.5.2.6.24
        ::= { alGeneralSystem 24 }

alURLFiltering OBJECT IDENTIFIER 
        -- 1.3.6.1.4.1.2603.5.2.6.24.1
        ::= { alServiceActivation 1 }

alUrlFOperationMode OBJECT-TYPE
        SYNTAX  AlUrlOperationMode
        MAX-ACCESS read-write
        STATUS current
        DESCRIPTION
                "Whether to always operate the service,
                disable the service or operate the service based on policies."
        -- 1.3.6.1.4.1.2603.5.2.6.24.1.1
        ::= { alURLFiltering 1 }


alUrlFAction OBJECT-TYPE
        SYNTAX  INTEGER {
                        reportOnly(1),
                        block(2),
                        redirect(3),
                        respond(4) }
        MAX-ACCESS read-write
        STATUS current
        DESCRIPTION
                "Whether to respond with a warning page,
                redirect the subscriber to another web site or just report the incident."
        -- 1.3.6.1.4.1.2603.5.2.6.24.1.2
        ::= { alURLFiltering 2 }


alUrlFPortal OBJECT-TYPE
        SYNTAX  OCTET STRING
        MAX-ACCESS read-write
        STATUS current
        DESCRIPTION
                "When the action is redirection, this is the URL to redirect the subscriber to."
        -- 1.3.6.1.4.1.2603.5.2.6.24.1.3
        ::= { alURLFiltering 3 }

alUrlFLastUpdateStatus OBJECT-TYPE
      SYNTAX  INTEGER {
                  success(1),
                  generalError(2),
                  wrongFormat(3),
                  binaryFileCorrupted(4),
                  requestTimeout(5), 
				  missingFiles (6)}
    MAX-ACCESS read-only
	STATUS current
	DESCRIPTION
		"The error code of the last attempted web safe update.
		Error codes are:
		1  Success
		2  General Error
		3  Wrong format
		4  Binary file corrupted
		5  Request Timeout
		6  Missing files"
	DEFVAL { success }
	-- 1.3.6.1.4.1.2603.5.2.6.24.1.4
	::= { alURLFiltering  4 }	


alURLMonitoring OBJECT IDENTIFIER 
        -- 1.3.6.1.4.1.2603.5.2.6.24.2
        ::= { alServiceActivation 2 }

alUrlMOperatonMode OBJECT-TYPE
        SYNTAX  AlUrlOperationMode
        MAX-ACCESS read-write
        STATUS current
        DESCRIPTION
                "Whether to always operate the service,
                disable the service or operate the service based on policies."
        -- 1.3.6.1.4.1.2603.5.2.6.24.2.1
        ::= { alURLMonitoring 1 }

alCaptivePortal OBJECT IDENTIFIER 
    -- 1.3.6.1.4.1.2603.5.2.6.24.3
    ::= { alServiceActivation 3 }

alCaptivePortalRedirectionTechnique OBJECT-TYPE
        SYNTAX INTEGER {
                    default(1),
                    request(2),
                    reply(3)    }
    MAX-ACCESS read-write
    STATUS current
    DESCRIPTION
                "CaptivePortal redirection execution technique"
    -- 1.3.6.1.4.1.2603.5.2.6.24.3.1
    ::= { alCaptivePortal 1 } 

-- 1.3.6.1.4.1.2603.5.2.6.24.3.2
alCaptivePortalPassPhrase OBJECT-TYPE
	SYNTAX OCTET STRING
	MAX-ACCESS read-only
	STATUS current
	DESCRIPTION
		"CaptivePortal augmented parameters encryption passphrase"
	::= { alCaptivePortal 2 }
       
alVoipReportingActivation OBJECT-TYPE
    SYNTAX  AlEnableDisable
    MAX-ACCESS read-write
    STATUS current
    DESCRIPTION
       "Condition of VOIP reporting feature"
        -- 1.3.6.1.4.1.2603.5.2.6.24.4   
        ::= { alServiceActivation 4 }
	
alSPSensorActivation OBJECT-TYPE
    SYNTAX  AlEnableDisable
    MAX-ACCESS read-write
    STATUS current
    DESCRIPTION
       "Condition of SP sensor feature"
        -- 1.3.6.1.4.1.2603.5.2.6.24.5   
        ::= { alServiceActivation 5 }
        
alFupProtocolVersion OBJECT-TYPE
    SYNTAX  Integer32
    MAX-ACCESS read-only
    STATUS current
    DESCRIPTION
       "Identification of FUP protocol version number that is supported by the device"
        -- 1.3.6.1.4.1.2603.5.2.6.25.1   
        ::= { alGeneralSystem 25 }

alPredictiveDPI OBJECT IDENTIFIER 
        -- 1.3.6.1.4.1.2603.5.2.6.26
        ::= { alGeneralSystem 26 }
		        
alPDPIState OBJECT-TYPE
    SYNTAX  AlEnableDisable
    MAX-ACCESS read-write
    STATUS current
    DESCRIPTION
       "Condition of Predictive DPI feature"
        -- 1.3.6.1.4.1.2603.5.2.6.26.1   
        ::= { alPredictiveDPI 1 }

alIPv6State OBJECT-TYPE
    SYNTAX  AlEnableDisable
    MAX-ACCESS read-write
    STATUS current
    DESCRIPTION
       "State of IPv6 support in NE"
    DEFVAL { disabled }
        -- 1.3.6.1.4.1.2603.5.2.6.27   
        ::= { alGeneralSystem 27 }

alSelectiveBypass OBJECT IDENTIFIER 
        -- 1.3.6.1.4.1.2603.5.2.6.28
        ::= { alGeneralSystem 28 }

alSelectiveBypassActivation OBJECT-TYPE
    SYNTAX  AlEnableDisable
    MAX-ACCESS read-write
    STATUS current
    DESCRIPTION
       "Activation of selective bypass function in NE"
    DEFVAL { disabled }
        -- 1.3.6.1.4.1.2603.5.2.6.28.1   
        ::= { alSelectiveBypass 1 }

alSelectiveBypassVlanGroup OBJECT-TYPE
    SYNTAX  Integer32
    MAX-ACCESS read-write
    STATUS current
    DESCRIPTION
       "VLAN group catalogue ID to be used for selective bypass"
    DEFVAL { 0 }
        -- 1.3.6.1.4.1.2603.5.2.6.28.2   
        ::= { alSelectiveBypass 2 }

alGenericLastChangeVar OBJECT-TYPE
        SYNTAX  VariablePointer
        MAX-ACCESS read-only
        STATUS current
        DESCRIPTION
                "OID of the variable that was most recently
                changed"
        -- 1.3.6.1.4.1.2603.5.2.8
        ::= { alGeneric 8 }
		
alTetherDetectState OBJECT-TYPE
		SYNTAX AlEnableDisable
		MAX-ACCESS read-write
		STATUS current
		DESCRIPTION
			"Enables tethering traffic detection in NE"     
		-- 1.3.6.1.4.1.2603.5.2.6.29
		::= { alGeneralSystem 29 }

alGenericLastChangeIntVal OBJECT-TYPE
        SYNTAX  Integer32
        MAX-ACCESS read-only
        STATUS current
        DESCRIPTION
                "Most recently changed integer value (due to previous variable).
                If value syntax is not INTEGER - the value plased in
                alGenericLastChangeStr or alGenericLastChangeAddr.
                Thus the manager should poll the previous variable
                (direct get request)."
        -- 1.3.6.1.4.1.2603.5.2.9
        ::= { alGeneric 9 }


alGenericLastChangeTimestamp OBJECT-TYPE
        SYNTAX  TimeStamp
        MAX-ACCESS read-only
        STATUS current
        DESCRIPTION
                "Timestamp for the most recent change in Generic branch.
                Not trap id because of the possibility of overflow of log file."
        -- 1.3.6.1.4.1.2603.5.2.10
        ::= { alGeneric 10 }


alGenericConfigTrapEnable OBJECT-TYPE
        SYNTAX  AlEnableDisable
        MAX-ACCESS read-write
        STATUS current
        DESCRIPTION
                "Enables or disables box configuration change traps
                for generic group: alDeviceConfChangeTrap,
                alIpAddrConfChangeTrap and alConnRouteConfChangeTrap"
        -- 1.3.6.1.4.1.2603.5.2.11
        ::= { alGeneric 11 }


alRebootRequest OBJECT-TYPE
        SYNTAX  INTEGER {
                        reboot(1),
                        shutdown(2),
                        indeterminate(3) }
        MAX-ACCESS read-write
        STATUS current
        DESCRIPTION
                "Reboot system."
        -- 1.3.6.1.4.1.2603.5.2.12
        ::= { alGeneric 12 }


alGenericLastChangeStrVal OBJECT-TYPE
        SYNTAX  OCTET STRING
        MAX-ACCESS read-only
        STATUS current
        DESCRIPTION
                "Most recently changed string value (due to variable alGenericLastChangeVar)

                "
        -- 1.3.6.1.4.1.2603.5.2.13
        ::= { alGeneric 13 }


alGenericLastChangeAddrVal OBJECT-TYPE
        SYNTAX  IpAddress
        MAX-ACCESS read-only
        STATUS current
        DESCRIPTION
                "Most recently changed ip address value (due to variable alGenericLastChangeVar)

                "
        -- 1.3.6.1.4.1.2603.5.2.14
        ::= { alGeneric 14 }


alProvisioning OBJECT IDENTIFIER 
        -- 1.3.6.1.4.1.2603.5.3
        ::= { alObjects 3 }

alCatalogs OBJECT IDENTIFIER 
        -- 1.3.6.1.4.1.2603.5.3.1
        ::= { alProvisioning 1 }

alCatalogsLastChangeTimestamp OBJECT-TYPE
        SYNTAX  TimeStamp
        MAX-ACCESS read-only
        STATUS current
        DESCRIPTION
                "The timestamp of the most recent change on
                the catalogs"
        -- 1.3.6.1.4.1.2603.5.3.1.1
        ::= { alCatalogs 1 }


alCatalogsLastChangeRequest OBJECT-TYPE
        SYNTAX  Integer32
        MAX-ACCESS read-only
        STATUS current
        DESCRIPTION
                "Request ID (identifier that came from the management facility)
                in the most recent change command. Can be used for the
                syncronization of centrally maintained catalog and its
                'shadow' on the agent."
        -- 1.3.6.1.4.1.2603.5.3.1.2
        ::= { alCatalogs 2 }


alCatalogListTable OBJECT-TYPE
        SYNTAX  SEQUENCE OF AlCatalogListEntry
        MAX-ACCESS not-accessible
        STATUS current
        DESCRIPTION
                "A complete list of all system catalogs"
        -- 1.3.6.1.4.1.2603.5.3.1.3
        ::= { alCatalogs 3 }


alCatalogListEntry OBJECT-TYPE
        SYNTAX  AlCatalogListEntry
        MAX-ACCESS not-accessible
        STATUS current
        DESCRIPTION ""
        INDEX {
                alCatalogId }
        -- 1.3.6.1.4.1.2603.5.3.1.3.1
        ::= { alCatalogListTable 1 }


AlCatalogListEntry ::= SEQUENCE {

        alCatalogId   Unsigned32,
        alCatalogName DisplayString }


alCatalogId OBJECT-TYPE
        SYNTAX  Unsigned32
        MAX-ACCESS not-accessible
        STATUS current
        DESCRIPTION
                "Catalog's identifier (number)"
        -- 1.3.6.1.4.1.2603.5.3.1.3.1.1
        ::= { alCatalogListEntry 1 }


alCatalogName OBJECT-TYPE
        SYNTAX  DisplayString
        MAX-ACCESS read-only
        STATUS current
        DESCRIPTION
                "Catalog's name"
        -- 1.3.6.1.4.1.2603.5.3.1.3.1.2
        ::= { alCatalogListEntry 2 }


alCatalogsTable OBJECT-TYPE
        SYNTAX  SEQUENCE OF AlCatalogsEntry
        MAX-ACCESS not-accessible
        STATUS current
        DESCRIPTION
                "Table of all catalogs"
        -- 1.3.6.1.4.1.2603.5.3.1.4
        ::= { alCatalogs 4 }


alCatalogsEntry OBJECT-TYPE
        SYNTAX  AlCatalogsEntry
        MAX-ACCESS not-accessible
        STATUS current
        DESCRIPTION ""
        INDEX {
                alCatalogId,
                alCatalogInstance }
        -- 1.3.6.1.4.1.2603.5.3.1.4.1
        ::= { alCatalogsTable 1 }


AlCatalogsEntry ::= SEQUENCE {

        alCatalogInstance         Unsigned32,
        alCatalogLastCommand      AlConfigCommand,
        alCatalogTimestamp        TimeStamp,
        alCatalogData             OCTET STRING,
        alCatalogCheckSum         Unsigned32,
        alCatalogInstanceStatus   AlInstanceStatus,
        alCatalogLastChangeOrigin Unsigned32 }


alCatalogInstance OBJECT-TYPE
        SYNTAX  Unsigned32
        MAX-ACCESS not-accessible
        STATUS current
        DESCRIPTION
                "This catalog entry ID. Unique inside current catalog."
        -- 1.3.6.1.4.1.2603.5.3.1.4.1.1
        ::= { alCatalogsEntry 1 }


alCatalogLastCommand OBJECT-TYPE
        SYNTAX  AlConfigCommand
        MAX-ACCESS read-only
        STATUS current
        DESCRIPTION
                "Most recent change command"
        -- 1.3.6.1.4.1.2603.5.3.1.4.1.2
        ::= { alCatalogsEntry 2 }


alCatalogTimestamp OBJECT-TYPE
        SYNTAX  TimeStamp
        MAX-ACCESS read-only
        STATUS current
        DESCRIPTION
                "Most recent update on this instance"
        -- 1.3.6.1.4.1.2603.5.3.1.4.1.3
        ::= { alCatalogsEntry 3 }


alCatalogData OBJECT-TYPE
        SYNTAX  OCTET STRING
        MAX-ACCESS read-only
        STATUS current
        DESCRIPTION
                "Data in this catalog entry (XML string)."
        -- 1.3.6.1.4.1.2603.5.3.1.4.1.4
        ::= { alCatalogsEntry 4 }


alCatalogCheckSum OBJECT-TYPE
        SYNTAX  Unsigned32
        MAX-ACCESS read-only
        STATUS current
        DESCRIPTION
                "Check Sum for the internal test"
        -- 1.3.6.1.4.1.2603.5.3.1.4.1.5
        ::= { alCatalogsEntry 5 }


alCatalogInstanceStatus OBJECT-TYPE
        SYNTAX  AlInstanceStatus
        MAX-ACCESS read-only
        STATUS current
        DESCRIPTION
                "Current status of the instance"
        -- 1.3.6.1.4.1.2603.5.3.1.4.1.6
        ::= { alCatalogsEntry 6 }


alCatalogLastChangeOrigin OBJECT-TYPE
        SYNTAX  Unsigned32
        MAX-ACCESS read-only
        STATUS current
        DESCRIPTION
                "Number that uniquely identifies the source
                of the change (AS generates the corresponding
                identifier)."
        -- 1.3.6.1.4.1.2603.5.3.1.4.1.7
        ::= { alCatalogsEntry 7 }


alPolicies OBJECT IDENTIFIER 
        -- 1.3.6.1.4.1.2603.5.3.2
        ::= { alProvisioning 2 }

alLineLastChange OBJECT-TYPE
        SYNTAX  TimeStamp
        MAX-ACCESS read-only
        STATUS current
        DESCRIPTION
                "Timestamp of most recent change on the line"
        -- 1.3.6.1.4.1.2603.5.3.2.1
        ::= { alPolicies 1 }


alLineTable OBJECT-TYPE
        SYNTAX  SEQUENCE OF AlLineEntry
        MAX-ACCESS not-accessible
        STATUS current
        DESCRIPTION
                "Table of lines"
        -- 1.3.6.1.4.1.2603.5.3.2.2
        ::= { alPolicies 2 }


alLineEntry OBJECT-TYPE
        SYNTAX  AlLineEntry
        MAX-ACCESS not-accessible
        STATUS current
        DESCRIPTION
                "Specific line entry."
        INDEX {
                alLineId }
        -- 1.3.6.1.4.1.2603.5.3.2.2.1
        ::= { alLineTable 1 }


AlLineEntry ::= SEQUENCE {

        alLineId               Unsigned32,
        alLineLastCommand      AlConfigCommand,
        alLineTimestamp        TimeStamp,
        alLineData             OCTET STRING,
        alLineCheckSum         Unsigned32,
        alLineInstanceStatus   AlInstanceStatus,
        alLineLastChangeOrigin Unsigned32 }


alLineId OBJECT-TYPE
        SYNTAX  Unsigned32
        MAX-ACCESS not-accessible
        STATUS current
        DESCRIPTION
                "Line's ID"
        -- 1.3.6.1.4.1.2603.5.3.2.2.1.1
        ::= { alLineEntry 1 }


alLineLastCommand OBJECT-TYPE
        SYNTAX  AlConfigCommand
        MAX-ACCESS read-only
        STATUS current
        DESCRIPTION
                "Most recently executed command"
        -- 1.3.6.1.4.1.2603.5.3.2.2.1.2
        ::= { alLineEntry 2 }


alLineTimestamp OBJECT-TYPE
        SYNTAX  TimeStamp
        MAX-ACCESS read-only
        STATUS current
        DESCRIPTION
                "Timestamp for the most recent change"
        -- 1.3.6.1.4.1.2603.5.3.2.2.1.3
        ::= { alLineEntry 3 }


alLineData OBJECT-TYPE
        SYNTAX  OCTET STRING
        MAX-ACCESS read-only
        STATUS current
        DESCRIPTION
                "XML data of this rule"
        -- 1.3.6.1.4.1.2603.5.3.2.2.1.4
        ::= { alLineEntry 4 }


alLineCheckSum OBJECT-TYPE
        SYNTAX  Unsigned32
        MAX-ACCESS read-only
        STATUS current
        DESCRIPTION
                "Checksum to be calculated on line's XML string
                for the testing purposes."
        -- 1.3.6.1.4.1.2603.5.3.2.2.1.5
        ::= { alLineEntry 5 }


alLineInstanceStatus OBJECT-TYPE
        SYNTAX  AlInstanceStatus
        MAX-ACCESS read-only
        STATUS current
        DESCRIPTION
                "Current status of the line."
        -- 1.3.6.1.4.1.2603.5.3.2.2.1.6
        ::= { alLineEntry 6 }


alLineLastChangeOrigin OBJECT-TYPE
        SYNTAX  Unsigned32
        MAX-ACCESS read-only
        STATUS current
        DESCRIPTION
                "Number that uniquely identifies the change
                originator"
        -- 1.3.6.1.4.1.2603.5.3.2.2.1.7
        ::= { alLineEntry 7 }


alPipeLastChange OBJECT-TYPE
        SYNTAX  TimeStamp
        MAX-ACCESS read-only
        STATUS current
        DESCRIPTION
                "Most recent configuration change timestamp on
                one of pipes"
        -- 1.3.6.1.4.1.2603.5.3.2.3
        ::= { alPolicies 3 }


alPipeTable OBJECT-TYPE
        SYNTAX  SEQUENCE OF AlPipeEntry
        MAX-ACCESS not-accessible
        STATUS current
        DESCRIPTION
                "Pipe configuration table"
        -- 1.3.6.1.4.1.2603.5.3.2.4
        ::= { alPolicies 4 }


alPipeEntry OBJECT-TYPE
        SYNTAX  AlPipeEntry
        MAX-ACCESS not-accessible
        STATUS current
        DESCRIPTION
                "Entry for the specific pipe"
        INDEX {
                alLineId,
                alPipeId }
        -- 1.3.6.1.4.1.2603.5.3.2.4.1
        ::= { alPipeTable 1 }


AlPipeEntry ::= SEQUENCE {

        alPipeId               Unsigned32,
        alPipeLastCommand      AlConfigCommand,
        alPipeTimestamp        TimeStamp,
        alPipeData             OCTET STRING,
        alPipeCheckSum         Unsigned32,
        alPipeIsTemplate       INTEGER,
        alPipeStatus           AlInstanceStatus,
        alPipeLastChangeOrigin Unsigned32 }


alPipeId OBJECT-TYPE
        SYNTAX  Unsigned32
        MAX-ACCESS not-accessible
        STATUS current
        DESCRIPTION ""
        -- 1.3.6.1.4.1.2603.5.3.2.4.1.1
        ::= { alPipeEntry 1 }


alPipeLastCommand OBJECT-TYPE
        SYNTAX  AlConfigCommand
        MAX-ACCESS read-only
        STATUS current
        DESCRIPTION ""
        -- 1.3.6.1.4.1.2603.5.3.2.4.1.2
        ::= { alPipeEntry 2 }


alPipeTimestamp OBJECT-TYPE
        SYNTAX  TimeStamp
        MAX-ACCESS read-only
        STATUS current
        DESCRIPTION ""
        -- 1.3.6.1.4.1.2603.5.3.2.4.1.3
        ::= { alPipeEntry 3 }


alPipeData OBJECT-TYPE
        SYNTAX  OCTET STRING
        MAX-ACCESS read-only
        STATUS current
        DESCRIPTION ""
        -- 1.3.6.1.4.1.2603.5.3.2.4.1.4
        ::= { alPipeEntry 4 }


alPipeCheckSum OBJECT-TYPE
        SYNTAX  Unsigned32
        MAX-ACCESS read-only
        STATUS current
        DESCRIPTION ""
        -- 1.3.6.1.4.1.2603.5.3.2.4.1.5
        ::= { alPipeEntry 5 }


alPipeIsTemplate OBJECT-TYPE
        SYNTAX  INTEGER {
                        regular(1),
                        template(2) }
        MAX-ACCESS read-only
        STATUS current
        DESCRIPTION
                "Identifies whether the current pipe is a template one."
        DEFVAL { regular }
        -- 1.3.6.1.4.1.2603.5.3.2.4.1.6
        ::= { alPipeEntry 6 }


alPipeStatus OBJECT-TYPE
        SYNTAX  AlInstanceStatus
        MAX-ACCESS read-only
        STATUS current
        DESCRIPTION ""
        -- 1.3.6.1.4.1.2603.5.3.2.4.1.7
        ::= { alPipeEntry 7 }


alPipeLastChangeOrigin OBJECT-TYPE
        SYNTAX  Unsigned32
        MAX-ACCESS read-only
        STATUS current
        DESCRIPTION
                "Number that uniquely identifies the change source"
        -- 1.3.6.1.4.1.2603.5.3.2.4.1.8
        ::= { alPipeEntry 8 }


alVCLastChange OBJECT-TYPE
        SYNTAX  TimeStamp
        MAX-ACCESS read-only
        STATUS current
        DESCRIPTION
                "The most recent configuration change timestamp on
                one of VCs"
        -- 1.3.6.1.4.1.2603.5.3.2.5
        ::= { alPolicies 5 }


alVCTable OBJECT-TYPE
        SYNTAX  SEQUENCE OF AlVCEntry
        MAX-ACCESS not-accessible
        STATUS current
        DESCRIPTION
                "Table of VC configurations"
        -- 1.3.6.1.4.1.2603.5.3.2.6
        ::= { alPolicies 6 }


alVCEntry OBJECT-TYPE
        SYNTAX  AlVCEntry
        MAX-ACCESS not-accessible
        STATUS current
        DESCRIPTION
                "A specific entry for VC"
        INDEX {
                alLineId,
                alPipeId,
                alVCId }
        -- 1.3.6.1.4.1.2603.5.3.2.6.1
        ::= { alVCTable 1 }


AlVCEntry ::= SEQUENCE {

        alVCId               Unsigned32,
        alVCLastCommand      AlConfigCommand,
        alVCTimestamp        TimeStamp,
        alVCData             OCTET STRING,
        alVCCheckSum         Unsigned32,
        alVCIsTemplate       INTEGER,
        alVCStatus           AlInstanceStatus,
        alVCLastChangeOrigin Unsigned32 }


alVCId OBJECT-TYPE
        SYNTAX  Unsigned32
        MAX-ACCESS not-accessible
        STATUS current
        DESCRIPTION ""
        -- 1.3.6.1.4.1.2603.5.3.2.6.1.1
        ::= { alVCEntry 1 }


alVCLastCommand OBJECT-TYPE
        SYNTAX  AlConfigCommand
        MAX-ACCESS read-only
        STATUS current
        DESCRIPTION ""
        -- 1.3.6.1.4.1.2603.5.3.2.6.1.2
        ::= { alVCEntry 2 }


alVCTimestamp OBJECT-TYPE
        SYNTAX  TimeStamp
        MAX-ACCESS read-only
        STATUS current
        DESCRIPTION ""
        -- 1.3.6.1.4.1.2603.5.3.2.6.1.3
        ::= { alVCEntry 3 }


alVCData OBJECT-TYPE
        SYNTAX  OCTET STRING
        MAX-ACCESS read-only
        STATUS current
        DESCRIPTION ""
        -- 1.3.6.1.4.1.2603.5.3.2.6.1.4
        ::= { alVCEntry 4 }


alVCCheckSum OBJECT-TYPE
        SYNTAX  Unsigned32
        MAX-ACCESS read-only
        STATUS current
        DESCRIPTION ""
        -- 1.3.6.1.4.1.2603.5.3.2.6.1.5
        ::= { alVCEntry 5 }


alVCIsTemplate OBJECT-TYPE
        SYNTAX  INTEGER {
                        regular(1),
                        template(2) }
        MAX-ACCESS read-only
        STATUS current
        DESCRIPTION
                "Identifies whether current VC is a template one."
        DEFVAL { regular }
        -- 1.3.6.1.4.1.2603.5.3.2.6.1.6
        ::= { alVCEntry 6 }


alVCStatus OBJECT-TYPE
        SYNTAX  AlInstanceStatus
        MAX-ACCESS read-only
        STATUS current
        DESCRIPTION ""
        -- 1.3.6.1.4.1.2603.5.3.2.6.1.7
        ::= { alVCEntry 7 }


alVCLastChangeOrigin OBJECT-TYPE
        SYNTAX  Unsigned32
        MAX-ACCESS read-only
        STATUS current
        DESCRIPTION
                "Number that uniquely identifies the last change
                command originator"
        -- 1.3.6.1.4.1.2603.5.3.2.6.1.8
        ::= { alVCEntry 8 }


alLineConfTrapEnable OBJECT-TYPE
        SYNTAX  AlEnableDisable
        MAX-ACCESS read-write
        STATUS current
        DESCRIPTION
                "Activates/deactivated line policy configuration
                change traps"
        -- 1.3.6.1.4.1.2603.5.3.2.7
        ::= { alPolicies 7 }


alPipeConfTrapEnable OBJECT-TYPE
        SYNTAX  AlEnableDisable
        MAX-ACCESS read-write
        STATUS current
        DESCRIPTION
                "Activates/deactivated Pipe policy configuration
                change traps"
        -- 1.3.6.1.4.1.2603.5.3.2.8
        ::= { alPolicies 8 }


alVcConfTrapEnable OBJECT-TYPE
        SYNTAX  AlEnableDisable
        MAX-ACCESS read-write
        STATUS current
        DESCRIPTION
                "Activates/deactivated VC policy configuration
                change traps"
        -- 1.3.6.1.4.1.2603.5.3.2.9
        ::= { alPolicies 9 }


alPolicyModificationTag OBJECT-TYPE
        SYNTAX  INTEGER {
                        inSync(1),
                        snmpNotInSync(2),
                        dataSrvNotInSync(3),
                        rescuePerformed(4),
                        unknown(5) }
        MAX-ACCESS read-only
        STATUS current
        DESCRIPTION
                "The variable reflects the synchronization status of current policy/catalogs."
        -- 1.3.6.1.4.1.2603.5.3.2.10
        ::= { alPolicies 10 }


alStatistics OBJECT IDENTIFIER 
        -- 1.3.6.1.4.1.2603.5.4
        ::= { alObjects 4 }

alStatCntlTable OBJECT-TYPE
        SYNTAX  SEQUENCE OF AlStatCntlEntry
        MAX-ACCESS not-accessible
        STATUS current
        DESCRIPTION
                "Control table of statistics"
        -- 1.3.6.1.4.1.2603.5.4.1
        ::= { alStatistics 1 }


alStatCntlEntry OBJECT-TYPE
        SYNTAX  AlStatCntlEntry
        MAX-ACCESS not-accessible
        STATUS current
        DESCRIPTION
                "Statistics control entry"
        INDEX {
                alStatCntlLine,
                alStatCntlPipe,
                alStatCntlVC,
                IMPLIED alStatCntlUserInstance }
        -- 1.3.6.1.4.1.2603.5.4.1.1
        ::= { alStatCntlTable 1 }


AlStatCntlEntry ::= SEQUENCE {

        alStatCntlLine         Unsigned32,
        alStatCntlPipe         Unsigned32,
        alStatCntlVC           Unsigned32,
        alStatCntlUserInstance DisplayString,
        alStatCntlIsTemplate   INTEGER,
        alStatCntlStartedAt    DateAndTime,
        alStatCntlIsView       AlEnableDisable,
        alStatCntlIsAlert      AlEnableDisable,
        alStatCntlStatus       RowStatus }


alStatCntlLine OBJECT-TYPE
        SYNTAX  Unsigned32
        MAX-ACCESS not-accessible
        STATUS current
        DESCRIPTION
                "Line number"
        -- 1.3.6.1.4.1.2603.5.4.1.1.1
        ::= { alStatCntlEntry 1 }


alStatCntlPipe OBJECT-TYPE
        SYNTAX  Unsigned32
        MAX-ACCESS not-accessible
        STATUS current
        DESCRIPTION
                "Pipe number inside line"
        -- 1.3.6.1.4.1.2603.5.4.1.1.2
        ::= { alStatCntlEntry 2 }


alStatCntlVC OBJECT-TYPE
        SYNTAX  Unsigned32
        MAX-ACCESS not-accessible
        STATUS current
        DESCRIPTION
                "VC number inside pipe"
        -- 1.3.6.1.4.1.2603.5.4.1.1.3
        ::= { alStatCntlEntry 3 }


alStatCntlUserInstance OBJECT-TYPE
        SYNTAX  DisplayString
        MAX-ACCESS not-accessible
        STATUS current
        DESCRIPTION
                "Some identification of the user. May be
                host name, modem ID, ip or mac address, vlan, etc.
                When not relevant (not a template rule) - zero length string."
        -- 1.3.6.1.4.1.2603.5.4.1.1.4
        ::= { alStatCntlEntry 4 }


alStatCntlIsTemplate OBJECT-TYPE
        SYNTAX  INTEGER {
                        specific(1),
                        all(2) }
        MAX-ACCESS read-create
        STATUS current
        DESCRIPTION
                "In case the statistics collection must be provided per
                each instance of template rule - (2). Otherwise
                (no template or specific instance) - (1)"
        DEFVAL { specific }
        -- 1.3.6.1.4.1.2603.5.4.1.1.5
        ::= { alStatCntlEntry 5 }


alStatCntlStartedAt OBJECT-TYPE
        SYNTAX  DateAndTime
        MAX-ACCESS read-only
        STATUS current
        DESCRIPTION
                "Collection of counters started at this date-time"
        -- 1.3.6.1.4.1.2603.5.4.1.1.6
        ::= { alStatCntlEntry 6 }


alStatCntlIsView OBJECT-TYPE
        SYNTAX  AlEnableDisable
        MAX-ACCESS read-create
        STATUS current
        DESCRIPTION
                "The current entry was created and used for viewing of the
                statistics counters."
        -- 1.3.6.1.4.1.2603.5.4.1.1.7
        ::= { alStatCntlEntry 7 }


alStatCntlIsAlert OBJECT-TYPE
        SYNTAX  AlEnableDisable
        MAX-ACCESS read-create
        STATUS current
        DESCRIPTION
                "The current entry was created and used for the alert functioning."
        -- 1.3.6.1.4.1.2603.5.4.1.1.8
        ::= { alStatCntlEntry 8 }


alStatCntlStatus OBJECT-TYPE
        SYNTAX  RowStatus
        MAX-ACCESS read-create
        STATUS current
        DESCRIPTION
                "Is used to provide create/remove of entries"
        -- 1.3.6.1.4.1.2603.5.4.1.1.9
        ::= { alStatCntlEntry 9 }


alStatTable OBJECT-TYPE
        SYNTAX  SEQUENCE OF AlStatEntry
        MAX-ACCESS not-accessible
        STATUS current
        DESCRIPTION
                "Statistics table (per rules)"
        -- 1.3.6.1.4.1.2603.5.4.2
        ::= { alStatistics 2 }


alStatEntry OBJECT-TYPE
        SYNTAX  AlStatEntry
        MAX-ACCESS not-accessible
        STATUS current
        DESCRIPTION
                "Statistics entry (for the specific rule)."
        INDEX {
                alStatCntlLine,
                alStatCntlPipe,
                alStatCntlVC,
                IMPLIED alStatCntlUserInstance }
        -- 1.3.6.1.4.1.2603.5.4.2.1
        ::= { alStatTable 1 }


AlStatEntry ::= SEQUENCE {

        alStatLiveConn     Counter32,
        alStatNewConn      Counter32,
        alStatDropConn     Counter32,
        alStatOctetsIn     Counter64,
        alStatOctetsOut    Counter64,
        alStatOctetsTotal  Counter64,
        alStatPacketsIn    Counter64,
        alStatPacketsOut   Counter64,
        alStatPacketsTotal Counter64 }


alStatLiveConn OBJECT-TYPE
        SYNTAX  Counter32
        MAX-ACCESS read-only
        STATUS current
        DESCRIPTION
                "Number of live connections"
        -- 1.3.6.1.4.1.2603.5.4.2.1.5
        ::= { alStatEntry 5 }


alStatNewConn OBJECT-TYPE
        SYNTAX  Counter32
        MAX-ACCESS read-only
        STATUS current
        DESCRIPTION
                "Number of new connections"
        -- 1.3.6.1.4.1.2603.5.4.2.1.6
        ::= { alStatEntry 6 }


alStatDropConn OBJECT-TYPE
        SYNTAX  Counter32
        MAX-ACCESS read-only
        STATUS current
        DESCRIPTION
                "Number of dropped connections"
        -- 1.3.6.1.4.1.2603.5.4.2.1.7
        ::= { alStatEntry 7 }


alStatOctetsIn OBJECT-TYPE
        SYNTAX  Counter64
        MAX-ACCESS read-only
        STATUS current
        DESCRIPTION
                "Average inbound rate (in 1024 bytes per second) during measurement interval"
        -- 1.3.6.1.4.1.2603.5.4.2.1.8
        ::= { alStatEntry 8 }


alStatOctetsOut OBJECT-TYPE
        SYNTAX  Counter64
        MAX-ACCESS read-only
        STATUS current
        DESCRIPTION
                "Average outbound rate (in 1024 bytes per second) during measurement interval"
        -- 1.3.6.1.4.1.2603.5.4.2.1.9
        ::= { alStatEntry 9 }


alStatOctetsTotal OBJECT-TYPE
        SYNTAX  Counter64
        MAX-ACCESS read-only
        STATUS current
        DESCRIPTION
                "Average total (inbound+outbound) inbound rate (in 1024 bytes per second) during measurement interval"
        -- 1.3.6.1.4.1.2603.5.4.2.1.10
        ::= { alStatEntry 10 }


alStatPacketsIn OBJECT-TYPE
        SYNTAX  Counter64
        MAX-ACCESS read-only
        STATUS current
        DESCRIPTION
                "Average inbound rate (in packets per second) during measurement interval"
        -- 1.3.6.1.4.1.2603.5.4.2.1.11
        ::= { alStatEntry 11 }


alStatPacketsOut OBJECT-TYPE
        SYNTAX  Counter64
        MAX-ACCESS read-only
        STATUS current
        DESCRIPTION
                "Average outbound rate (in packets per second) during measurement interval"
        -- 1.3.6.1.4.1.2603.5.4.2.1.12
        ::= { alStatEntry 12 }


alStatPacketsTotal OBJECT-TYPE
        SYNTAX  Counter64
        MAX-ACCESS read-only
        STATUS current
        DESCRIPTION
                "Average total (inbound+outbound) rate (in packets per second) during measurement interval"
        -- 1.3.6.1.4.1.2603.5.4.2.1.13
        ::= { alStatEntry 13 }


alStatPipes OBJECT-TYPE
        SYNTAX  Counter32
        MAX-ACCESS read-only
        STATUS current
        DESCRIPTION
                "The total number of pipes in the system (including
                template instances)"
        -- 1.3.6.1.4.1.2603.5.4.3
        ::= { alStatistics 3 }


alStatVCs OBJECT-TYPE
        SYNTAX  Counter32
        MAX-ACCESS read-only
        STATUS current
        DESCRIPTION
                "Total number of VCs in the system (including template
                instances)"
        -- 1.3.6.1.4.1.2603.5.4.4
        ::= { alStatistics 4 }


alStatLines OBJECT-TYPE
        SYNTAX  Counter32
        MAX-ACCESS read-only
        STATUS current
        DESCRIPTION
                "The total number of active lines"
        -- 1.3.6.1.4.1.2603.5.4.5
        ::= { alStatistics 5 }


alNumberEstConnections OBJECT-TYPE
        SYNTAX  Counter32
        MAX-ACCESS read-only
        STATUS current
        DESCRIPTION
                "Number of established connections"
        -- 1.3.6.1.4.1.2603.5.4.6
        ::= { alStatistics 6 }


alConnectionEstRate OBJECT-TYPE
        SYNTAX  Counter32
        MAX-ACCESS read-only
        STATUS current
        DESCRIPTION
                "Connection establishment rate"
        -- 1.3.6.1.4.1.2603.5.4.7
        ::= { alStatistics 7 }


alActiveSubscribers OBJECT-TYPE
        SYNTAX  Counter32
        MAX-ACCESS read-only
        STATUS current
        DESCRIPTION
                "The number of subscribes when interfaced with SMP"
        -- 1.3.6.1.4.1.2603.5.4.8
        ::= { alStatistics 8 }


alAlerts OBJECT IDENTIFIER 
        -- 1.3.6.1.4.1.2603.5.5
        ::= { alObjects 5 }

alDataSourceTable OBJECT-TYPE
        SYNTAX  SEQUENCE OF AlDataSourceEntry
        MAX-ACCESS not-accessible
        STATUS current
        DESCRIPTION
                "The list of data sources to be periodically
                checked"
        -- 1.3.6.1.4.1.2603.5.5.1
        ::= { alAlerts 1 }


alDataSourceEntry OBJECT-TYPE
        SYNTAX  AlDataSourceEntry
        MAX-ACCESS not-accessible
        STATUS current
        DESCRIPTION
                "Single data source server"
        INDEX {
                alDataSourceType,
                alDataSourcePriorityOrder }
        -- 1.3.6.1.4.1.2603.5.5.1.1
        ::= { alDataSourceTable 1 }


AlDataSourceEntry ::= SEQUENCE {

        alDataSourceType          INTEGER,
        alDataSourcePriorityOrder Unsigned32,
        alDataSourceIPAddr        IpAddress,
        alDataSourceDescr         DisplayString,
        alDataSourceStatus        INTEGER,
        alDataSourceRowStatus     RowStatus }


alDataSourceType OBJECT-TYPE
        SYNTAX  INTEGER {
                        dns(1),
                        dhcp(2),
                        ldap(3),
                        radius(4),
                        tftp(5),
                        ntp(6) }
        MAX-ACCESS not-accessible
        STATUS current
        DESCRIPTION
                "Data source server description"
        -- 1.3.6.1.4.1.2603.5.5.1.1.1
        ::= { alDataSourceEntry 1 }


alDataSourcePriorityOrder OBJECT-TYPE
        SYNTAX  Unsigned32
        MAX-ACCESS not-accessible
        STATUS current
        DESCRIPTION
                "Priority of source of this type"
        -- 1.3.6.1.4.1.2603.5.5.1.1.2
        ::= { alDataSourceEntry 2 }


alDataSourceIPAddr OBJECT-TYPE
        SYNTAX  IpAddress
        MAX-ACCESS read-create
        STATUS current
        DESCRIPTION
                "IP address of the corresponding server"
        -- 1.3.6.1.4.1.2603.5.5.1.1.3
        ::= { alDataSourceEntry 3 }


alDataSourceDescr OBJECT-TYPE
        SYNTAX  DisplayString
        MAX-ACCESS read-create
        STATUS current
        DESCRIPTION
                "Data source description (free text)."
        -- 1.3.6.1.4.1.2603.5.5.1.1.4
        ::= { alDataSourceEntry 4 }


alDataSourceStatus OBJECT-TYPE
        SYNTAX  INTEGER {
                        unknown(1),
                        on(2),
                        off(3) }
        MAX-ACCESS read-only
        STATUS current
        DESCRIPTION
                "Current status of the server."
        DEFVAL { unknown }
        -- 1.3.6.1.4.1.2603.5.5.1.1.5
        ::= { alDataSourceEntry 5 }


alDataSourceRowStatus OBJECT-TYPE
        SYNTAX  RowStatus
        MAX-ACCESS read-create
        STATUS current
        DESCRIPTION
                "The object for the management of data sources
                (creation, deletion)"
        -- 1.3.6.1.4.1.2603.5.5.1.1.6
        ::= { alDataSourceEntry 6 }


alDataSourceLastChange OBJECT-TYPE
        SYNTAX  TimeStamp
        MAX-ACCESS read-only
        STATUS current
        DESCRIPTION
                "The timestamp of last change on datasource
                table (add/delete/status change)"
        -- 1.3.6.1.4.1.2603.5.5.2
        ::= { alAlerts 2 }


alSevereSoftwareProblem OBJECT-TYPE
        SYNTAX  INTEGER {
                        unknown(1),
                        reboot(2),
                        processUp(3),
                        processDown(4),
                        processStuck(5),
                        picoCheckSuccess(11),
                        picoCheckFalure(12),
                        picoSaveFalure(13),
                        wrongTrapOrder(21) }
        MAX-ACCESS read-only
        STATUS current
        DESCRIPTION
                "Software problem is to be occurred. The action will be taken"
        -- 1.3.6.1.4.1.2603.5.5.3
        ::= { alAlerts 3 }


alMemoryUsage OBJECT-TYPE
        SYNTAX  Gauge32
        MAX-ACCESS read-only
        STATUS current
        DESCRIPTION
                "Device RAM usage in %"
        -- 1.3.6.1.4.1.2603.5.5.4
        ::= { alAlerts 4 }


alDiskUsage OBJECT-TYPE
        SYNTAX  Gauge32
        MAX-ACCESS read-only
        STATUS current
        DESCRIPTION
                "Device HD (or flash disk) usage level in %"
        -- 1.3.6.1.4.1.2603.5.5.5
        ::= { alAlerts 5 }


alTemperature OBJECT-TYPE
        SYNTAX  Gauge32
        MAX-ACCESS read-only
        STATUS current
        DESCRIPTION
                "The temperature gauge measurement in
                degrees centigrade"
        -- 1.3.6.1.4.1.2603.5.5.6
        ::= { alAlerts 6 }


-- Since the alerts - is a catalog, they are configured via XML interface.
-- Thus here we have only read-only entries - the copy from policy:
-- action on the specific rule.

alAlertConfTable OBJECT-TYPE
        SYNTAX  SEQUENCE OF AlAlertConfEntry
        MAX-ACCESS not-accessible
        STATUS current
        DESCRIPTION
                "Configuration table for the alerts"
        -- 1.3.6.1.4.1.2603.5.5.7
        ::= { alAlerts 7 }


alAlertConfEntry OBJECT-TYPE
        SYNTAX  AlAlertConfEntry
        MAX-ACCESS not-accessible
        STATUS current
        DESCRIPTION
                "Alert configuration entry."
        INDEX {
                alAlertConfId,
                IMPLIED alAlertConfVariable }
        -- 1.3.6.1.4.1.2603.5.5.7.1
        ::= { alAlertConfTable 1 }


AlAlertConfEntry ::= SEQUENCE {

        alAlertConfId                 Unsigned32,
        alAlertConfVariable           VariablePointer,
        alAlertConfValue              Integer32,
        alAlertConfThreshold          Integer32,
        alAlertConfNormal             Integer32,
        alAlertConfRegInterval        Integer32,
        alAlertConfUnRegInterval      Integer32,
        alAlertConfThresholdDirection INTEGER }


alAlertConfId OBJECT-TYPE
        SYNTAX  Unsigned32
        MAX-ACCESS not-accessible
        STATUS current
        DESCRIPTION
                "The identifier of alert definitions.
                All alerts with same alAlertConfId have same columns values except alAlertConfVariable and alAlertConfValue."
        -- 1.3.6.1.4.1.2603.5.5.7.1.1
        ::= { alAlertConfEntry 1 }


alAlertConfVariable OBJECT-TYPE
        SYNTAX  VariablePointer
        MAX-ACCESS read-only
        STATUS current
        DESCRIPTION
                "Points to the variable to be tested. Variable contains
                the object ID in the suffix. Thus it is possible to find
                out the with object this alarm (alert) is associated to."
        -- 1.3.6.1.4.1.2603.5.5.7.1.2
        ::= { alAlertConfEntry 2 }


alAlertConfValue OBJECT-TYPE
        SYNTAX  Integer32
        MAX-ACCESS read-only
        STATUS current
        DESCRIPTION
                "The current value of the observed variable.
                Must be integer!"
        -- 1.3.6.1.4.1.2603.5.5.7.1.3
        ::= { alAlertConfEntry 3 }


alAlertConfThreshold OBJECT-TYPE
        SYNTAX  Integer32
        MAX-ACCESS read-only
        STATUS current
        DESCRIPTION
                "Threshold value - when crossed upwards -
                the corresponding event must be issued"
        -- 1.3.6.1.4.1.2603.5.5.7.1.4
        ::= { alAlertConfEntry 4 }


alAlertConfNormal OBJECT-TYPE
        SYNTAX  Integer32
        MAX-ACCESS read-only
        STATUS current
        DESCRIPTION
                "The normal value of the variable - when
                crossed downwards - the event is deactivated"
        -- 1.3.6.1.4.1.2603.5.5.7.1.5
        ::= { alAlertConfEntry 5 }


alAlertConfRegInterval OBJECT-TYPE
        SYNTAX  Integer32
        MAX-ACCESS read-only
        STATUS current
        DESCRIPTION
                "The counter inside the sample that provides the event
                should be more then this % of time in the area defined by
                variable - alAlertConfThreshold."
        -- 1.3.6.1.4.1.2603.5.5.7.1.6
        ::= { alAlertConfEntry 6 }


alAlertConfUnRegInterval OBJECT-TYPE
        SYNTAX  Integer32
        MAX-ACCESS read-only
        STATUS current
        DESCRIPTION
                "The counter inside the sample that provides the event
                should be more then this % of time in the area defined
                defined by variable - alAlertConfNormal."
        -- 1.3.6.1.4.1.2603.5.5.7.1.7
        ::= { alAlertConfEntry 7 }


alAlertConfThresholdDirection OBJECT-TYPE
        SYNTAX  INTEGER {
                        equal(0),
                        greater(1),
                        less(2),
                        notEqual(3) }
        MAX-ACCESS read-only
        STATUS current
        DESCRIPTION
                "Defines when value crosses the threshold:
                if val > or = or <  or != threshold"
        DEFVAL { greater }
        -- 1.3.6.1.4.1.2603.5.5.7.1.8
        ::= { alAlertConfEntry 8 }


alAlertLastChange OBJECT-TYPE
        SYNTAX  TimeStamp
        MAX-ACCESS read-only
        STATUS current
        DESCRIPTION
                "Shows when the most recent alert occured.
                Covers the alerts from the alert table, memory,
                disk and temperature alerts. Not including data
                source alarms"
        -- 1.3.6.1.4.1.2603.5.5.8
        ::= { alAlerts 8 }


alLastAccessViolation OBJECT-TYPE
        SYNTAX  TimeStamp
        MAX-ACCESS read-only
        STATUS current
        DESCRIPTION
                "Most recent access violation timestamp"
        -- 1.3.6.1.4.1.2603.5.5.9
        ::= { alAlerts 9 }


alAlertsTrapsEnable OBJECT-TYPE
        SYNTAX  AlEnableDisable
        MAX-ACCESS read-write
        STATUS current
        DESCRIPTION
                "Enables/disables all alerts traps (including
                system alerts)"
        -- 1.3.6.1.4.1.2603.5.5.10
        ::= { alAlerts 10 }


alDataSourceTrapEnable OBJECT-TYPE
        SYNTAX  AlEnableDisable
        MAX-ACCESS read-write
        STATUS current
        DESCRIPTION
                "Enable/disable data source traps"
        -- 1.3.6.1.4.1.2603.5.5.11
        ::= { alAlerts 11 }


alAccessViolationTrapEnable OBJECT-TYPE
        SYNTAX  AlEnableDisable
        MAX-ACCESS read-write
        STATUS current
        DESCRIPTION
                "Enable/Disable access violation trap"
        -- 1.3.6.1.4.1.2603.5.5.12
        ::= { alAlerts 12 }


allDOSAttackTable OBJECT-TYPE
        SYNTAX  SEQUENCE OF AllDOSAttackEntry
        MAX-ACCESS not-accessible
        STATUS current
        DESCRIPTION
                "List of current DOS attacks detected on interfaces."
        -- 1.3.6.1.4.1.2603.5.5.13
        ::= { alAlerts 13 }


allDOSAttackEntry OBJECT-TYPE
        SYNTAX  AllDOSAttackEntry
        MAX-ACCESS not-accessible
        STATUS current
        DESCRIPTION ""
        INDEX {
                ifIndex,
                alDOSAttackType }
        -- 1.3.6.1.4.1.2603.5.5.13.1
        ::= { allDOSAttackTable 1 }


AllDOSAttackEntry ::= SEQUENCE {

        alDOSAttackType   INTEGER,
        alDOSAttackPort   Unsigned32,
        alDOSAttackStatus INTEGER }


alDOSAttackType OBJECT-TYPE
        SYNTAX  INTEGER {
                        tcp(1),
                        udp(2),
                        icmp(3),
                        otherIP(4),
                        nonIP(5) }
        MAX-ACCESS not-accessible
        STATUS current
        DESCRIPTION
                "Type of DOS attack"
        -- 1.3.6.1.4.1.2603.5.5.13.1.1
        ::= { allDOSAttackEntry 1 }


alDOSAttackPort OBJECT-TYPE
        SYNTAX  Unsigned32
        MAX-ACCESS read-only
        STATUS current
        DESCRIPTION
                "Port that under DOS attack"
        -- 1.3.6.1.4.1.2603.5.5.13.1.2
        ::= { allDOSAttackEntry 2 }


alDOSAttackStatus OBJECT-TYPE
        SYNTAX  INTEGER {
                        active(1),
                        finish(2) }
        MAX-ACCESS read-only
        STATUS current
        DESCRIPTION
                "Current status of DOS attack:
                1- DOS attack active
                2- DOS attack is finished"
        -- 1.3.6.1.4.1.2603.5.5.13.1.3
        ::= { allDOSAttackEntry 3 }


alDOSTrapEnable OBJECT-TYPE
        SYNTAX  AlEnableDisable
        MAX-ACCESS read-write
        STATUS current
        DESCRIPTION
                "Enable/Disable DOS attacks traps"
        DEFVAL { enabled }
        -- 1.3.6.1.4.1.2603.5.5.14
        ::= { alAlerts 14 }


alCpuUsage OBJECT-TYPE
        SYNTAX  INTEGER (0..100)
        MAX-ACCESS read-only
        STATUS current
        DESCRIPTION
                "Device average CPUs usage in %"
        -- 1.3.6.1.4.1.2603.5.5.15
        ::= { alAlerts 15 }


alLastMessage OBJECT-TYPE
        SYNTAX  OCTET STRING
        MAX-ACCESS read-only
        STATUS current
        DESCRIPTION
                "Message that describes last ALLOT system event"
        -- 1.3.6.1.4.1.2603.5.5.16
        ::= { alAlerts 16 }


alCpuPicoUsage OBJECT-TYPE
        SYNTAX  INTEGER (0..100)
        MAX-ACCESS read-only
        STATUS current
        DESCRIPTION
                "Average CPU load of Pico processors"
        DEFVAL { 0 }
        -- 1.3.6.1.4.1.2603.5.5.17
        ::= { alAlerts 17 }


alSensorTable OBJECT-TYPE
        SYNTAX  SEQUENCE OF AlSensorEntry
        MAX-ACCESS not-accessible
        STATUS current
        DESCRIPTION ""
        -- 1.3.6.1.4.1.2603.5.5.18
        ::= { alAlerts 18 }


alSensorEntry OBJECT-TYPE
        SYNTAX  AlSensorEntry
        MAX-ACCESS not-accessible
        STATUS current
        DESCRIPTION ""
        INDEX {
                alBoardId,
                alSensorId }
        -- 1.3.6.1.4.1.2603.5.5.18.1
        ::= { alSensorTable 1 }


AlSensorEntry ::= SEQUENCE {

        alSensorId       Unsigned32,
        alSensorType     INTEGER,
        alSensorRawValue Integer32 }


alSensorType OBJECT-TYPE
        SYNTAX  INTEGER {
                        temperature(1),
                        fan(2),
                        powerSupply(3),
                        cpu(4),
                        memory(5),
                        storage(6),
                        voltage(7),
                        telco(8),
                        picoCpu(9),
                        cer(10),
                        noc(11),
                        activeLines(12),
                        activePipes(13),
                        activeVcs(14),
                        registerSubscr(15) }
        MAX-ACCESS read-only
        STATUS current
        DESCRIPTION
                "Represents type of sensor.
                Possible types are:
                         temperature(1),
                                        fan(2),
                                        powerSupply(3),
                                        cpu(4),
                                        memory(5),
                                        storage(6),
                                        voltage(7),
                                        telco(8) ,
                        picoCpu(9),
                                       cer(10),
                                       noc(11),
                                       activeLines(12),
                                       activePipes(13),
                                       activeVcs(14),
                                       registerSubscribers(15)"
        -- 1.3.6.1.4.1.2603.5.5.18.1.2
        ::= { alSensorEntry 2 }


alSensorId OBJECT-TYPE
        SYNTAX  Unsigned32
        MAX-ACCESS not-accessible
        STATUS current
        DESCRIPTION ""
        -- 1.3.6.1.4.1.2603.5.5.18.1.1
        ::= { alSensorEntry 1 }


alSensorRawValue OBJECT-TYPE
        SYNTAX  Integer32
        MAX-ACCESS read-only
        STATUS current
        DESCRIPTION
                "Raw value of sensor
                (cpu load for CPU; memory usage for memory etc)"
        -- 1.3.6.1.4.1.2603.5.5.18.1.3
        ::= { alSensorEntry 3 }


alLoadConfig OBJECT IDENTIFIER 
        -- 1.3.6.1.4.1.2603.5.6
        ::= { alObjects 6 }

alSaveConfig OBJECT-TYPE
        SYNTAX  DisplayString
        MAX-ACCESS read-write
        STATUS current
        DESCRIPTION
                "Contains the name of most recent backup file or empty string. The file is located in a well-known folder.
                The set operation launches the save command which builds the new archive file with name contained
                in a var-bind value. The file is created in the same well-known directory."
        -- 1.3.6.1.4.1.2603.5.6.1
        ::= { alLoadConfig 1 }


alRestoreConfig OBJECT-TYPE
        SYNTAX  DisplayString
        MAX-ACCESS read-write
        STATUS current
        DESCRIPTION
                "Name of archive file that contains the device configuration. The get operation returns an empty string.
                Change of this node (set operation) causes the reconfiguration of the system with the new data taken from
                the given archive file (located in a well-known folder)."
        -- 1.3.6.1.4.1.2603.5.6.2
        ::= { alLoadConfig 2 }


alPoliciesStatusTable OBJECT-TYPE
        SYNTAX  SEQUENCE OF AlPoliciesStatusEntry
        MAX-ACCESS not-accessible
        STATUS current
        DESCRIPTION
                "Shows the list of policies on the
                device. Can be used for activation/deactivation of
                the policy."
        -- 1.3.6.1.4.1.2603.5.6.3
        ::= { alLoadConfig 3 }


alPoliciesStatusEntry OBJECT-TYPE
        SYNTAX  AlPoliciesStatusEntry
        MAX-ACCESS not-accessible
        STATUS current
        DESCRIPTION ""
        INDEX {
                alPolicyName }
        -- 1.3.6.1.4.1.2603.5.6.3.1
        ::= { alPoliciesStatusTable 1 }


AlPoliciesStatusEntry ::= SEQUENCE {

        alPolicyName      OCTET STRING,
        alPolicyTimestamp DateAndTime,
        alPolicyStatus    INTEGER }


alPolicyName OBJECT-TYPE
        SYNTAX  OCTET STRING
        MAX-ACCESS read-only
        STATUS current
        DESCRIPTION
                "Name of the policy"
        -- 1.3.6.1.4.1.2603.5.6.3.1.1
        ::= { alPoliciesStatusEntry 1 }


alPolicyTimestamp OBJECT-TYPE
        SYNTAX  DateAndTime
        MAX-ACCESS read-only
        STATUS current
        DESCRIPTION
                "Time when the last change happened."
        -- 1.3.6.1.4.1.2603.5.6.3.1.2
        ::= { alPoliciesStatusEntry 2 }


alPolicyStatus OBJECT-TYPE
        SYNTAX  INTEGER {
                        active(1),
                        notActive(2),
                        doMakeActive(3) }
        MAX-ACCESS read-write
        STATUS current
        DESCRIPTION
                "active - this policy (entry) is now 'active';
                nonActive - now is not in use;
                doMakeActive - setting of this value launches
                the switchover operation to make this entry (policy) active.
                In this case all other policies will be set into nonActive status"
        -- 1.3.6.1.4.1.2603.5.6.3.1.3
        ::= { alPoliciesStatusEntry 3 }



--
-- TRAPS
--

alDeviceConfChangeTrap NOTIFICATION-TYPE
        OBJECTS {
                alGenericLastChangeVar,
                alGenericLastChangeIntVal,
                alGenericLastChangeStrVal,
                alGenericLastChangeAddrVal}
        STATUS current
        DESCRIPTION
                "Is to be send when one of generic status
                variables is changed. The mentioned statuses are defined
                on the device level. The actual variable is defined via
                alGenericLastChangeVar"
        -- 1.3.6.1.4.1.2603.0.1
        ::= { alEvents 1 }


alCatalogConfChangeTrap NOTIFICATION-TYPE
        OBJECTS {
                alCatalogLastCommand,
                alCatalogLastChangeOrigin}
        STATUS current
        DESCRIPTION
                "Configuration change event on one of the catalogs"
        -- 1.3.6.1.4.1.2603.0.2
        ::= { alEvents 2 }


alLineConfChangeTrap NOTIFICATION-TYPE
        OBJECTS {
                alLineLastCommand,
                alLineLastChangeOrigin}
        STATUS current
        DESCRIPTION
                "Configuration change occurs on one of the lines"
        -- 1.3.6.1.4.1.2603.0.3
        ::= { alEvents 3 }


alPipeConfChangeTrap NOTIFICATION-TYPE
        OBJECTS {
                alPipeLastCommand,
                alPipeLastChangeOrigin}
        STATUS current
        DESCRIPTION
                "The configuration change occurs on one of the pipes"
        -- 1.3.6.1.4.1.2603.0.4
        ::= { alEvents 4 }


alVCConfChangeTrap NOTIFICATION-TYPE
        OBJECTS {
                alVCLastCommand,
                alVCLastChangeOrigin}
        STATUS current
        DESCRIPTION
                "The configuration change occurs on one of the VCs"
        -- 1.3.6.1.4.1.2603.0.5
        ::= { alEvents 5 }


alAlertRisingTrap NOTIFICATION-TYPE
        OBJECTS {
                alAlertConfVariable,
                alAlertConfValue,
                alAlertConfThreshold,
                alAlertConfRegInterval}
        STATUS current
        DESCRIPTION
                "One of the alerts crossed the threshold"
        -- 1.3.6.1.4.1.2603.0.6
        ::= { alEvents 6 }


alAlertFallingTrap NOTIFICATION-TYPE
        OBJECTS {
                alAlertConfVariable,
                alAlertConfValue,
                alAlertConfNormal,
                alAlertConfUnRegInterval}
        STATUS current
        DESCRIPTION
                "The alert' value returned to the normal level"
        -- 1.3.6.1.4.1.2603.0.7
        ::= { alEvents 7 }


alDosAttackOnTrap NOTIFICATION-TYPE
        OBJECTS {
                alDOSAttackStatus}
        STATUS current
        DESCRIPTION
                "DOS attack is identified"
        -- 1.3.6.1.4.1.2603.0.8
        ::= { alEvents 8 }


alDosAttackOffTrap NOTIFICATION-TYPE
        OBJECTS {
                alDOSAttackStatus}
        STATUS current
        DESCRIPTION
                "DOS attack is over"
        -- 1.3.6.1.4.1.2603.0.9
        ::= { alEvents 9 }


alDataSourceDownTrap NOTIFICATION-TYPE
        OBJECTS {
                alDataSourceIPAddr,
                alDataSourceType}
        STATUS current
        DESCRIPTION
                "Data source is unreachable"
        -- 1.3.6.1.4.1.2603.0.10
        ::= { alEvents 10 }


alDataSourceUpTrap NOTIFICATION-TYPE
        OBJECTS {
                alDataSourceIPAddr,
                alDataSourceType}
        STATUS current
        DESCRIPTION
                "Data source is now reachable"
        -- 1.3.6.1.4.1.2603.0.11
        ::= { alEvents 11 }


alSoftwareProblemTrap NOTIFICATION-TYPE
        OBJECTS {
                alSevereSoftwareProblem,
                alLastMessage}
        STATUS current
        DESCRIPTION
                "Severe problem occured. The trap can't be
                blocked (disabled)."
        -- 1.3.6.1.4.1.2603.0.12
        ::= { alEvents 12 }


alAccessViolationTrap NOTIFICATION-TYPE
        OBJECTS {
                alLastMessage}
        STATUS current
        DESCRIPTION
                "Access violation attempt is discovered"
        -- 1.3.6.1.4.1.2603.0.13
        ::= { alEvents 13 }


alIpAddrConfChangeTrap NOTIFICATION-TYPE
        OBJECTS {
                alIpXEntryStatus,
                alIpXAddr}
        STATUS current
        DESCRIPTION
                "Ip Address added or removed."
        -- 1.3.6.1.4.1.2603.0.14
        ::= { alEvents 14 }


alConnRouteConfChangeTrap NOTIFICATION-TYPE
        OBJECTS {
                alConnRouteEntryStatus,
                alConnRouteIfIndex}
        STATUS current
        DESCRIPTION
                "Connection routing configuration change trap"
        -- 1.3.6.1.4.1.2603.0.15
        ::= { alEvents 15 }


alDeviceStatusUpTrap NOTIFICATION-TYPE
        OBJECTS {
                alGenericLastChangeVar,
                alGenericLastChangeIntVal}
        STATUS current
        DESCRIPTION ""
        -- 1.3.6.1.4.1.2603.0.16
        ::= { alEvents 16 }


alDeviceStatusDownTrap NOTIFICATION-TYPE
        OBJECTS {
                alGenericLastChangeVar,
                alGenericLastChangeIntVal}
        STATUS current
        DESCRIPTION ""
        -- 1.3.6.1.4.1.2603.0.17
        ::= { alEvents 17 }


alApplicationInfoTrap NOTIFICATION-TYPE
        OBJECTS {
                alLastMessage}
        STATUS current
        DESCRIPTION
                "Application general information trap
                blocked (disabled)."
        -- 1.3.6.1.4.1.2603.0.18
        ::= { alEvents 18 }

-- Conformance
--

alConf OBJECT IDENTIFIER 
        -- 1.3.6.1.4.1.2603.6
        ::= { alRegMIB 6 }

-- Groups
--

alGroups OBJECT IDENTIFIER 
        -- 1.3.6.1.4.1.2603.6.1
        ::= { alConf 1 }

-- Compliance
--

alCompls OBJECT IDENTIFIER 
        -- 1.3.6.1.4.1.2603.6.2
        ::= { alConf 2 }


alBoardStatusChangeTrap NOTIFICATION-TYPE
        OBJECTS {
                alBoardType,
                alBoardSoftwareStatus,
                alBoardHWStatus}
        STATUS current
        DESCRIPTION
                "This trap is sent on changing software or hardware status of board"
        -- 1.3.6.1.4.1.2603.0.19
        ::= { alEvents 19 }


alWebUpdateTrap NOTIFICATION-TYPE
        OBJECTS {
                alCurrentVersion,
                alLastUpdateStatus}
        STATUS current
        DESCRIPTION
                "This trap will be sent for each attempted web update"
        -- 1.3.6.1.4.1.2603.0.20
        ::= { alEvents 20 }


alAsymmetricRemoteDeviceConfTrap NOTIFICATION-TYPE
        OBJECTS {
                alAsymmetricGroupId,
                alAsymmetricEntryStatus}
        STATUS current
        DESCRIPTION
                "Configuration of the asymmetric remote device is changed or device added/removed."
        -- 1.3.6.1.4.1.2603.0.21
        ::= { alEvents 21 }


alAsymmetricRemoteDeviceStatusTrap NOTIFICATION-TYPE
        OBJECTS {
                alAsymmetricGroupId,
                alAsymmetricOwnDeviceId,
                alAsymmetricHealthCheckStatus}
        STATUS current
        DESCRIPTION
                "Is to be send when health check of remote device is changed"
        -- 1.3.6.1.4.1.2603.0.22
        ::= { alEvents 22 }


alLicenseWarnEventTrap NOTIFICATION-TYPE
        OBJECTS {
                alLicenseAttrType,
                alLicenseLimitType,
                alLicenseEventType,
                alLastMessage}
        STATUS current
        DESCRIPTION
                "This trap is sent on Erroneous states of the license"
        -- 1.3.6.1.4.1.2603.0.23
        ::= { alEvents 23 }


alLicenseCritEventTrap NOTIFICATION-TYPE
        OBJECTS {
                alLicenseAttrType,
                alLicenseLimitType,
                alLicenseEventType,
                alLastMessage}
        STATUS current
        DESCRIPTION
                "This trap is sent in for critical level conditions of the license"
        -- 1.3.6.1.4.1.2603.0.24
        ::= { alEvents 24 }


alBoardTemperatureStatusTrap NOTIFICATION-TYPE
        OBJECTS {
                alBoardType,
                alBoardTemperatureRange}
        STATUS current
        DESCRIPTION
                "This trap is sent when temperature crosses range border"
        -- 1.3.6.1.4.1.2603.0.25
        ::= { alEvents 25 }

alURLFilteringUpdateTrap NOTIFICATION-TYPE
      OBJECTS {
            alUrlFLastUpdateStatus}
      STATUS current
      DESCRIPTION
            "This trap will be sent for each attempted websafe update"
      -- 1.3.6.1.4.1.2603.0.26
      ::= { alEvents 26 }
	

alGenericGroup OBJECT-GROUP
        OBJECTS {
                alBoxSerialNumber,
                alSoftwareVersion,
                alDateTime,
                alTimeZone,
                alConfigurationName,
                alMode,
                alPosIfEncapsulation,
                alSPTStatus,
                alLearningBridge,
                alHTTPConnectionMode,
                alTelnetAccess,
                alPingReply,
                alConnectionTimeout,
                alACDescr,
                alACRowStatus,
                alIfXMode,
                alIfXType,
                alGenericLastChangeVar,
                alGenericLastChangeIntVal,
                alGenericLastChangeTimestamp,
                alGenericConfigTrapEnable,
                alBackplaneVersion,
                alQoSIsEnabled,
                alQoSExpirationDateEnable,
                alCacheIsEnabled,
                alCacheExpirationDateEnable,
                alLoadBalancingIsEnabled,
                alLoadBalancingExpirationDateEnable,
                alActivationKey,
                alIfXSpeed,
                alLcdConfigEnable,
                alRebootRequest,
                alConnRouteNetMask,
                alConnRouteGateway,
                alConnRouteIfIndex,
                alConnRouteType,
                alConnRouteEntryStatus,
                alIpXNetMask,
                alIpXVlan,
                alIpXEntryStatus,
                alIfXOrder,
                alActivationModel,
                alLinePerPolicy,
                alPipePerPolicy,
                alVcPerPolicy,
                alMaxBandwidth,
                alMaxConnections,
                alHostname,
                alDomainName,
                alInBandGateway,
                alOutOfBandGateway,
                alPower,
                alFan,
                alEnhancedTcpSecurity,
                alDoubleSession,
                alSysExpirationDate,
                alPosIfCrc,
                alPosIfClocking,
                alPosIfScrambling,
                alPosIfFraming,
                alPosIfType,
                alBypass,
                alRedunduncyMode,
                alIpXAddr,
                alPosIfMtu,
                alIfXLabel,
                alIfXSupported,
                alSshSecurity,
                alGenericLastChangeStrVal,
                alGenericLastChangeAddrVal,
                alLTCollectionEnabled,
                alDeviceBWLimitsType,
                alDeviceBWLimitsOutbound,
                alDeviceBWLimitsInbound,
                alIfXActualMode,
                alIfXAction,
                alRemoteBypass,
                alRedundancyCap,
                alBypassUnit,
                alBypassSetting,
                alCocServerTimeOut,
                alCocServerRetries,
                alCocServerPeriod,
                alCocServiceTimeOut,
                alCocServiceRetries,
                alCocServicerPeriod,
                alCocTrackerMAC,
                alCocRedirectionMAC,
                alCocUseIp,
                alBoardType,
                alBoardSerialNumber,
                alBoardSoftwareVersion,
                alBoardHardwareVersion,
                alBoardSoftwareStatus,
                alBoardHWStatus,
                alCocRedirectionPort,
                alBaseVersion,
                alCurrentVersion,
                alLastUpdateStatus,
                alInternalDispatchMode,
                alInternalMinDevNum,
                alInternalRedundancyDevNum,
                alInternalActiveDevNum,
                alInternalRateLimit,
                alWebUpdateIsEnabled,
                alWebUpdateExpirationDateEnable,
                alUDSState,
                alAsymmetricGroupId,
                alAsymmetricOwnDeviceId,
                alAsymmetricHealthCheck,
                alAsymmetricTransportType,
                alAsymmetricControlVLAN,
                alAsymmetricMAC,
                alAsymmetricIP,
                alAsymmetricHealthCheckStatus,
                alAsymmetricEntryStatus,
                alAsymmetricEnable,
                alAsymmetricPort,
                alUrlFOperationMode,
                alUrlFAction,
                alUrlFPortal,
                alUrlFLastUpdateStatus,
                alUrlMOperatonMode,
				alCaptivePortalRedirectionTechnique,
				alVoipReportingActivation,
				alSPSensorActivation,
                alIfXUsage,
                alIfXSwitchId,
                alIfXSwitchPort,
                alIfXUsageCapability,
                alLicenseAttrType,
                alLicenseLimitType,
                alLicenseAttrName,
                alLimitValue,
                alLicenseStatus,
                alLicenseIsCurrValue,
                alLicenseCurrValue,
                alLicenseEventType,
                alBoardTemperatureRange,
                alIfXThroughputTX,
                alIfXThroughputRX,
                alIfXPacketPerSecondTX,
                alIfXPacketPerSecondRX,
                alIfXSTPStatus,
                alIfXSTPSupport,
                alFupProtocolVersion,
                alPDPIState,
                alIPv6State,
                alSelectiveBypassVlanGroup,
                alSelectiveBypassActivation,
                alTetherDetectState,
                alCaptivePortalPassPhrase }
        STATUS current
        DESCRIPTION
                "Group of generic objects"
        -- 1.3.6.1.4.1.2603.6.1.1
        ::= { alGroups 1 }

alProvisioningGroup OBJECT-GROUP
        OBJECTS {
                alCatalogsLastChangeTimestamp,
                alCatalogsLastChangeRequest,
                alCatalogName,
                alCatalogLastCommand,
                alCatalogTimestamp,
                alCatalogData,
                alCatalogCheckSum,
                alCatalogInstanceStatus,
                alLineLastChange,
                alLineLastCommand,
                alLineTimestamp,
                alLineData,
                alLineCheckSum,
                alLineInstanceStatus,
                alPipeLastChange,
                alPipeLastCommand,
                alPipeTimestamp,
                alPipeData,
                alPipeCheckSum,
                alPipeStatus,
                alVCLastChange,
                alVCLastCommand,
                alVCTimestamp,
                alVCData,
                alVCCheckSum,
                alVCStatus,
                alLineConfTrapEnable,
                alPipeIsTemplate,
                alVCIsTemplate,
                alCatalogLastChangeOrigin,
                alLineLastChangeOrigin,
                alPipeLastChangeOrigin,
                alVcConfTrapEnable,
                alVCLastChangeOrigin,
                alPipeConfTrapEnable,
                alPolicyModificationTag }
        STATUS current
        DESCRIPTION
                "Object related to the provisioning"
        -- 1.3.6.1.4.1.2603.6.1.2
        ::= { alGroups 2 }

alStatisticsGroup OBJECT-GROUP
        OBJECTS {
                alStatLiveConn,
                alStatNewConn,
                alStatDropConn,
                alStatOctetsIn,
                alStatOctetsOut,
                alStatOctetsTotal,
                alStatPacketsIn,
                alStatPacketsOut,
                alStatPacketsTotal,
                alStatCntlIsTemplate,
                alStatCntlStartedAt,
                alStatCntlStatus,
                alStatCntlIsView,
                alStatCntlIsAlert,
                alStatPipes,
                alStatVCs,
                alStatLines,
                alNumberEstConnections,
                alConnectionEstRate,
                alActiveSubscribers }
        STATUS current
        DESCRIPTION
                "Statistics objects"
        -- 1.3.6.1.4.1.2603.6.1.3
        ::= { alGroups 3 }

alAlertsGroup OBJECT-GROUP
        OBJECTS {
                alDataSourceIPAddr,
                alDataSourceStatus,
                alDataSourceDescr,
                alSevereSoftwareProblem,
                alDataSourceLastChange,
                alMemoryUsage,
                alDiskUsage,
                alTemperature,
                alAlertConfVariable,
                alAlertConfValue,
                alAlertConfThreshold,
                alAlertConfNormal,
                alAlertConfRegInterval,
                alAlertConfUnRegInterval,
                alAlertConfThresholdDirection,
                alAlertLastChange,
                alAlertsTrapsEnable,
                alLastAccessViolation,
                alDataSourceTrapEnable,
                alAccessViolationTrapEnable,
                alDataSourceRowStatus,
                alDOSAttackPort,
                alDOSAttackStatus,
                alDOSTrapEnable,
                alCpuUsage,
                alLastMessage,
                alCpuPicoUsage,
                alSensorRawValue,
                alSensorType }
        STATUS current
        DESCRIPTION
                "Alerts related objects"
        -- 1.3.6.1.4.1.2603.6.1.4
        ::= { alGroups 4 }

alLoadGroup OBJECT-GROUP
        OBJECTS {
                alSaveConfig,
                alPolicyName,
                alPolicyTimestamp,
                alPolicyStatus,
                alRestoreConfig }
        STATUS current
        DESCRIPTION
                "Variable related to save/restore operations"
        -- 1.3.6.1.4.1.2603.6.1.5
        ::= { alGroups 5 }

alEventsGroup NOTIFICATION-GROUP
        NOTIFICATIONS {
                alDeviceConfChangeTrap,
                alCatalogConfChangeTrap,
                alLineConfChangeTrap,
                alPipeConfChangeTrap,
                alVCConfChangeTrap,
                alAlertRisingTrap,
                alAlertFallingTrap,
                alDosAttackOnTrap,
                alDosAttackOffTrap,
                alDataSourceDownTrap,
                alDataSourceUpTrap,
                alSoftwareProblemTrap,
                alAccessViolationTrap,
                alIpAddrConfChangeTrap,
                alConnRouteConfChangeTrap,
                alDeviceStatusUpTrap,
                alDeviceStatusDownTrap,
                alApplicationInfoTrap,
                alBoardStatusChangeTrap,
                alWebUpdateTrap,
                alAsymmetricRemoteDeviceConfTrap,
                alAsymmetricRemoteDeviceStatusTrap,
                alLicenseWarnEventTrap,
                alLicenseCritEventTrap,
                alBoardTemperatureStatusTrap,
                alURLFilteringUpdateTrap}
        STATUS current
        DESCRIPTION
                "All notifications."
        -- 1.3.6.1.4.1.2603.6.1.6
        ::= { alGroups 6 }


--This module

alCompliance MODULE-COMPLIANCE
        STATUS current
        DESCRIPTION
                "The compliance statement for SNMP entities which
                implement this MIB"

        MODULE ALLOT-MIB
        MANDATORY-GROUPS {
                        alGenericGroup,
                        alProvisioningGroup,
                        alStatisticsGroup,
                        alAlertsGroup,
                        alEventsGroup,
                        alLoadGroup }

        -- 1.3.6.1.4.1.2603.6.2.1
        ::= { alCompls 1 }

END

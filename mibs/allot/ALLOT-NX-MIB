ALLOT-NX-MIB DEFINITIONS ::= BEGIN

IMPORTS
	alRegMIB
		FROM ALLOT-MIB
	MODULE-IDENTITY,
	OBJECT-TYPE,
	NOTIFICATION-TYPE,
	Counter32,
	IpAddress,
	Counter64,
	Unsigned32
		FROM SNMPv2-SMI
	OBJECT-GROUP,
	NOTIFICATION-GROUP
		FROM SNMPv2-CONF;

alNXMIB MODULE-IDENTITY
	LAST-UPDATED "200811090915Z"	-- Nov 24, 2008 9:15:00 AM
	ORGANIZATION "Allot communication Ltd"
	CONTACT-INFO
		"support@allot.com"
	DESCRIPTION
		"Allot NetExplorer Mib"
	REVISION "200812101000Z" -- Dec 10, 2008 10:00:00 AM
	DESCRIPTION
		"NetXplorer version 8.3.0"
	-- 1.3.6.1.4.1.2603.10
	::= { alRegMIB 10 }


-- Notification Types
--

alEvents OBJECT IDENTIFIER 
	-- 1.3.6.1.4.1.2603.10.0
	::= { alNXMIB 0 }

-- Scalars and Tables
--

alObjects OBJECT IDENTIFIER 
	-- 1.3.6.1.4.1.2603.10.2
	::= { alNXMIB 2 }

alAlarmTable OBJECT-TYPE
	SYNTAX  SEQUENCE OF AlEntry
	MAX-ACCESS not-accessible
	STATUS current
	DESCRIPTION
		"Alarm table"
	-- 1.3.6.1.4.1.2603.10.2.1
	::= { alObjects 1 }


alEntry OBJECT-TYPE
	SYNTAX  AlEntry
	MAX-ACCESS not-accessible
	STATUS current
	DESCRIPTION
		"Alarm table row entry"
	INDEX {
		alDeviceIp,
		alAlarmType,
		alCardId,
		alSourceId,
		alTcaId }
	-- 1.3.6.1.4.1.2603.10.2.1.1
	::= { alAlarmTable 1 }


AlEntry ::= SEQUENCE {

	alDeviceIp    IpAddress,
	alAlarmType   Unsigned32,
	alCardId      Unsigned32,
	alSourceId    Unsigned32,
	alTcaId       Unsigned32,
	alSeverity    INTEGER,
	alDescription OCTET STRING,
	alTimestamp   Counter64, 
	alIndex       OCTET STRING }


alDeviceIp OBJECT-TYPE
	SYNTAX  IpAddress
	MAX-ACCESS not-accessible
	STATUS current
	DESCRIPTION "Device IP address"
	-- 1.3.6.1.4.1.2603.10.2.1.1.1
	::= { alEntry 1 }


alCardId OBJECT-TYPE
	SYNTAX  Unsigned32
	MAX-ACCESS not-accessible
	STATUS current
	DESCRIPTION
		"Identifier of card in multicard device"
	-- 1.3.6.1.4.1.2603.10.2.1.1.3
	::= { alEntry 3 }


alAlarmType OBJECT-TYPE
	SYNTAX  Unsigned32
	MAX-ACCESS not-accessible
	STATUS current
	DESCRIPTION
		"Alarm type id defined in system as unique key for each problem occurrence"
	-- 1.3.6.1.4.1.2603.10.2.1.1.2
	::= { alEntry 2 }


alSourceId OBJECT-TYPE
	SYNTAX  Unsigned32
	MAX-ACCESS not-accessible
	STATUS current
	DESCRIPTION
		"Id of alarm source.(In same card may be several subsystem of same type such as cpu, temperature sensors and etc)"
	-- 1.3.6.1.4.1.2603.10.2.1.1.4
	::= { alEntry 4 }


alTcaId OBJECT-TYPE
	SYNTAX  Unsigned32
	MAX-ACCESS not-accessible
	STATUS current
	DESCRIPTION
		"Several alarms may be defined for each subsystem."
	-- 1.3.6.1.4.1.2603.10.2.1.1.5
	::= { alEntry 5 }


alSeverity OBJECT-TYPE
	SYNTAX  INTEGER {
		unknown(0), 
		cleared(1), 
		indeterminate(2),
		critical(3),
		major(4),
		minor(5),
		warning(6) }
	MAX-ACCESS read-only
	STATUS current
	DESCRIPTION
		"Enumeration of possible alarm severities"
	-- 1.3.6.1.4.1.2603.10.2.1.1.6
	::= { alEntry 6 }


alDescription OBJECT-TYPE
	SYNTAX  OCTET STRING
	MAX-ACCESS read-only
	STATUS current
	DESCRIPTION "Alarm description is compiled dynamically and has problem reference"
	-- 1.3.6.1.4.1.2603.10.2.1.1.7
	::= { alEntry 7 }


alTimestamp OBJECT-TYPE
	SYNTAX  Counter64
	MAX-ACCESS read-only
	STATUS current
	DESCRIPTION "Alarm timestamp in system - UTC format"
	-- 1.3.6.1.4.1.2603.10.2.1.1.8
	::= { alEntry 8 }

alIndex OBJECT-TYPE
	SYNTAX  OCTET STRING
	MAX-ACCESS read-only
	STATUS current
	DESCRIPTION "Alarm index in system"
	-- 1.3.6.1.4.1.2603.10.2.1.1.9
	::= { alEntry 9 }


alTrapCounter OBJECT-TYPE
	SYNTAX  Counter32
	MAX-ACCESS read-only
	STATUS current
	DESCRIPTION
		"Counter of sent trap"
	-- 1.3.6.1.4.1.2603.10.2.2
	::= { alObjects 2 }


-- Conformance
--

alConf OBJECT IDENTIFIER 
	-- 1.3.6.1.4.1.2603.10.3
	::= { alNXMIB 3 }

-- Groups
--

alGroups OBJECT IDENTIFIER 
	-- 1.3.6.1.4.1.2603.10.3.1
	::= { alConf 1 }

-- Compliance
--

alCompls OBJECT IDENTIFIER 
	-- 1.3.6.1.4.1.2603.10.3.2
	::= { alConf 2 }


alAlarmRisingTrap NOTIFICATION-TYPE
	OBJECTS {
		alSeverity,
		alDescription,
		alTimestamp,
		alIndex }
	STATUS current
	DESCRIPTION
		"Trap shall be sent for alarm rising"
	-- 1.3.6.1.4.1.2603.10.0.1
	::= { alEvents 1 }


alAlarmFallingTrap NOTIFICATION-TYPE
	OBJECTS {
		alSeverity,
		alDescription,
		alTimestamp,
		alIndex }
	STATUS current
	DESCRIPTION
		"Trap shall be sent for alarm clearing"
	-- 1.3.6.1.4.1.2603.10.0.2
	::= { alEvents 2 }

alBasicGroup OBJECT-GROUP
	OBJECTS {
		alSeverity,
		alDescription,
		alTrapCounter,
		alTimestamp,
		alIndex }
	STATUS current
	DESCRIPTION
		"Basic objects."
	-- 1.3.6.1.4.1.2603.10.3.1.1
	::= { alGroups 1 }

alBasicEvents NOTIFICATION-GROUP
	NOTIFICATIONS {
		alAlarmRisingTrap,
		alAlarmFallingTrap }
	STATUS current
	DESCRIPTION
		"Basic notifications."
	-- 1.3.6.1.4.1.2603.10.3.1.2
	::= { alGroups 2 }

END

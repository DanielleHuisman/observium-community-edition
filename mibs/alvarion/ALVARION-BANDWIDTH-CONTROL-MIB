-- ****************************************************************************
--  ALVARION-BANDWIDTH-CONTROL-MIB definitions
--
--  Copyright (c) 2007, Alvarion Ltd.
--  All Rights Reserved.
--
--  Alvarion Bandwidth Control MIB file.
--
-- ****************************************************************************


ALVARION-BANDWIDTH-CONTROL-MIB DEFINITIONS ::= BEGIN

IMPORTS
    MODULE-IDENTITY, OBJECT-TYPE,
    Integer32
        FROM    SNMPv2-SMI
    TruthValue
        FROM    SNMPv2-TC
    MODULE-COMPLIANCE, OBJECT-GROUP
        FROM    SNMPv2-CONF
    AlvarionPriorityQueue
        FROM    ALVARION-TC
    alvarionMgmtV2
        FROM    ALVARION-SMI
;


alvarionBandwidthControlMIB   MODULE-IDENTITY
    LAST-UPDATED    "200710310000Z"
    ORGANIZATION    "Alvarion Ltd."
    CONTACT-INFO    "Alvarion Ltd.
                     Postal: 21a HaBarzel St.
                             P.O. Box 13139
                             Tel-Aviv 69710
                             Israel
                     Phone:  +972 3 645 6262"
    DESCRIPTION     "Alvarion Bandwidth Control MIB."

    ::= { alvarionMgmtV2 14 }


-- alvarionBandwidthControlMIB definition
alvarionBandwidthControlMIBObjects OBJECT IDENTIFIER ::= { alvarionBandwidthControlMIB 1 }

-- alvarion Bandwidth Control groups
coBandwidthControlConfig    OBJECT IDENTIFIER ::= { alvarionBandwidthControlMIBObjects 1 }


-- The Bandwidth Control Address Configuration Group
coBandwidthControlEnable OBJECT-TYPE
    SYNTAX      TruthValue
    MAX-ACCESS  read-only
    STATUS      current
    DESCRIPTION "Indicates if bandwidth control is enabled or disabled on the Internet port." 
    ::= { coBandwidthControlConfig 1 }

coBandwidthControlMaxTransmitRate OBJECT-TYPE
    SYNTAX      Integer32
    MAX-ACCESS  read-only
    STATUS      current
    DESCRIPTION "Indicates the maximum rate at which data can be transmitted on the 
                 Internet port. If traffic exceeds this rate for short bursts,
                 it is buffered. Long overages will result in data being dropped."
    ::= { coBandwidthControlConfig 2 }

coBandwidthControlMaxReceiveRate OBJECT-TYPE
    SYNTAX      Integer32
    MAX-ACCESS  read-only
    STATUS      current
    DESCRIPTION "Indicates the maximum rate at which data can be received on the 
                 Internet port. If traffic exceeds this rate for short bursts
                 it is buffered. Long overages will result in data being dropped."
    ::= { coBandwidthControlConfig 3 }


coBandwidthControlLevelTable OBJECT-TYPE
    SYNTAX      SEQUENCE OF CoBandwidthControlLevelEntry
    MAX-ACCESS  not-accessible
    STATUS      current
    DESCRIPTION "A table defining the current bandwidth level settings that are
                 active on the device."
    ::= { coBandwidthControlConfig 4 }

coBandwidthControlLevelEntry OBJECT-TYPE
    SYNTAX      CoBandwidthControlLevelEntry
    MAX-ACCESS  not-accessible
    STATUS      current
    DESCRIPTION "An entry in the coBandwidthControlLevelTable.
                 coBandwidthControlLevelIndex - Uniquely access a definition for this
                                                particular bandwidth control level."
    INDEX       { coBandwidthControlLevelIndex }
    ::= { coBandwidthControlLevelTable 1 }

CoBandwidthControlLevelEntry ::= SEQUENCE
{
    coBandwidthControlLevelIndex                  AlvarionPriorityQueue,
    coBandwidthControlLevelMinTransmitRate        Integer32,
    coBandwidthControlLevelMaxTransmitRate        Integer32,
    coBandwidthControlLevelMinReceiveRate         Integer32,
    coBandwidthControlLevelMaxReceiveRate         Integer32
}

coBandwidthControlLevelIndex OBJECT-TYPE
    SYNTAX      AlvarionPriorityQueue
    MAX-ACCESS  not-accessible
    STATUS      current
    DESCRIPTION "Specifies the level index. Each index defines a bandwidth level that
                 traffic can be assigned to. Four indexes are defined (1 to 4) with 
                 the following meanings: 1-Low, 2-Normal, 3- High, 4-Very High."
    ::= { coBandwidthControlLevelEntry 1 }

coBandwidthControlLevelMinTransmitRate OBJECT-TYPE
    SYNTAX      Integer32 (0..100)
    MAX-ACCESS  read-only
    STATUS      current
    DESCRIPTION "Specify the minimum transmit rate for the level
                 as a percentage of coBandwidthControlMaxTransmitRate. This is the 
                 minimum amount of bandwidth that will be assigned to a level as 
                 soon as outgoing traffic is present on the level."
    ::= { coBandwidthControlLevelEntry 2 }

coBandwidthControlLevelMaxTransmitRate OBJECT-TYPE
    SYNTAX      Integer32 (0..100)
    MAX-ACCESS  read-only
    STATUS      current
    DESCRIPTION "Specify the maximum transmit rate for the specified level
                 as a percentage of coBandwidthControlMaxTransmitRate. This is the 
                 maximum amount of outgoing bandwidth that can be consumed by the 
                 level. Traffic in excess will be buffered for short bursts, and 
                 dropped for sustained overages"
    ::= { coBandwidthControlLevelEntry 3 }

coBandwidthControlLevelMinReceiveRate OBJECT-TYPE
    SYNTAX      Integer32 (0..100)
    MAX-ACCESS  read-only
    STATUS      current
    DESCRIPTION "Specify the minimum receive rate for the specified level 
                 as a percentage of coBandwidthControlMaxReceiveRateRate. This is the 
                 minimum amount of bandwidth that will be assigned to a level as soon 
                 as incoming traffic is present on the level." 
    ::= { coBandwidthControlLevelEntry 4 }

coBandwidthControlLevelMaxReceiveRate OBJECT-TYPE
    SYNTAX      Integer32 (0..100)
    MAX-ACCESS  read-only
    STATUS      current
    DESCRIPTION "Specify the maximum receive rate for the specified level 
                 as a percentage of coBandwidthControlMaxReceiveRateRate. This is the 
                 maximum amount of incoming bandwidth that can be consumed by the 
                 level. Traffic in excess will be buffered for short bursts, and 
                 dropped for sustained overages." 
    ::= { coBandwidthControlLevelEntry 5 }

-- conformance information
alvarionBandwidthControlMIBConformance OBJECT IDENTIFIER ::= { alvarionBandwidthControlMIB 2 }
alvarionBandwidthControlMIBCompliances OBJECT IDENTIFIER ::= { alvarionBandwidthControlMIBConformance 1 }
alvarionBandwidthControlMIBGroups      OBJECT IDENTIFIER ::= { alvarionBandwidthControlMIBConformance 2 }


-- compliance statements
alvarionBandwidthControlMIBCompliance MODULE-COMPLIANCE
    STATUS      current 
    DESCRIPTION "The compliance statement for the Bandwidth Control MIB."
    MODULE      MANDATORY-GROUPS
                    {
                        alvarionBandwidthControlMIBGroup,
                        alvarionBandwidthControlLevelMIBGroup
                    }
    ::= { alvarionBandwidthControlMIBCompliances 1 }

-- units of conformance
alvarionBandwidthControlMIBGroup OBJECT-GROUP
    OBJECTS     {
                    coBandwidthControlEnable,
                    coBandwidthControlMaxTransmitRate,
                    coBandwidthControlMaxReceiveRate
                }
    STATUS      current
    DESCRIPTION "A collection of objects for use with Bandwidth Controls."
    ::= { alvarionBandwidthControlMIBGroups 1 }

alvarionBandwidthControlLevelMIBGroup OBJECT-GROUP
    OBJECTS     {
                    coBandwidthControlLevelMinTransmitRate,
                    coBandwidthControlLevelMaxTransmitRate,
                    coBandwidthControlLevelMinReceiveRate,
                    coBandwidthControlLevelMaxReceiveRate
                }
    STATUS      current
    DESCRIPTION "A collection of objects for use with Bandwidth Controls."
    ::= { alvarionBandwidthControlMIBGroups 2 }

END

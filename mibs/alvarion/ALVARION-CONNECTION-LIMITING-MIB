-- ****************************************************************************
--  ALVARION-CONNECTION-LIMITING-MIB definitions
--
--  Copyright (c) 2007, Alvarion Ltd.
--  All Rights Reserved.
--
--  Alvarion Connection limiting MIB file.
--
-- ****************************************************************************


ALVARION-CONNECTION-LIMITING-MIB DEFINITIONS ::= BEGIN

IMPORTS
    MODULE-IDENTITY, OBJECT-TYPE, Integer32
        FROM    SNMPv2-SMI
    MODULE-COMPLIANCE, OBJECT-GROUP
        FROM    SNMPv2-CONF
    alvarionMgmtV2
        FROM    ALVARION-SMI
;


alvarionConnectionLimitingMIB MODULE-IDENTITY
    LAST-UPDATED    "200710310000Z"
    ORGANIZATION    "Alvarion Ltd."
    CONTACT-INFO    "Alvarion Ltd.
                     Postal: 21a HaBarzel St.
                             P.O. Box 13139
                             Tel-Aviv 69710
                             Israel
                     Phone:  +972 3 645 6262"
    DESCRIPTION     "Alvarion Connection limiting module."

    ::= { alvarionMgmtV2 18 }


-- alvarionConnectionLimitingMIBObjects definition
alvarionConnectionLimitingMIBObjects OBJECT IDENTIFIER ::= { alvarionConnectionLimitingMIB 1 }

-- Firmware Distribution groups
connectionLimitingConfig OBJECT IDENTIFIER ::=  { alvarionConnectionLimitingMIBObjects 1 }
connectionLimitingInfo OBJECT IDENTIFIER ::=  { alvarionConnectionLimitingMIBObjects 2 }


-- The connectionLimitingConfig group controls the process parameters

connectionLimitingMaximumUserConnections OBJECT-TYPE
    SYNTAX      Integer32 (20..2000)
    MAX-ACCESS  read-write
    STATUS      current
    DESCRIPTION "Specifies the maximum number of simultaneous connections
                 allowed for a specific user. If this amount of connections 
                 is reached, no other connections will be allowed
                 for user and a trap is generated."
    ::= { connectionLimitingConfig 1 }


-- The connectionLimitingInfo group contains information and statuses about
-- the connection limiting feature.

connectionLimitingMaximumSystemConnections OBJECT-TYPE
    SYNTAX      Integer32
    MAX-ACCESS  read-only
    STATUS      current
    DESCRIPTION "Indicates the maximum number of simultaneous connections that
                 are supported by the device. This is calculated based
                 on the device type and available memory."
    ::= { connectionLimitingInfo 1 }


-- Connection Limiting notifications
alvarionConnectionLimitingMIBNotificationPrefix OBJECT IDENTIFIER ::= { alvarionConnectionLimitingMIB 2 }
alvarionConnectionLimitingMIBNotifications OBJECT IDENTIFIER ::= { alvarionConnectionLimitingMIBNotificationPrefix 0 }


-- conformance information
alvarionConnectionLimitingMIBConformance OBJECT IDENTIFIER ::= { alvarionConnectionLimitingMIB 3 }
alvarionConnectionLimitingMIBCompliances OBJECT IDENTIFIER ::= { alvarionConnectionLimitingMIBConformance 1 }
alvarionConnectionLimitingMIBGroups      OBJECT IDENTIFIER ::= { alvarionConnectionLimitingMIBConformance 2 }

-- compliance statements
alvarionConnectionLimitingMIBCompliance MODULE-COMPLIANCE
    STATUS      current
    DESCRIPTION "The compliance statement for entities which implement
                 the Alvarion Tools MIB."
    MODULE      MANDATORY-GROUPS
                {
                    alvarionConnectionLimitingConfigMIBGroup,
                    alvarionConnectionLimitingInfoMIBGroup
                }
    ::= { alvarionConnectionLimitingMIBCompliances 1 }

-- units of conformance
alvarionConnectionLimitingConfigMIBGroup OBJECT-GROUP
    OBJECTS     {
                    connectionLimitingMaximumUserConnections
                }
    STATUS      current
    DESCRIPTION "A collection of objects providing control over the connection
                 limiting MIB capability."
    ::= { alvarionConnectionLimitingMIBGroups 1 }

alvarionConnectionLimitingInfoMIBGroup OBJECT-GROUP
    OBJECTS     {
                    connectionLimitingMaximumSystemConnections
                }
    STATUS      current
    DESCRIPTION "A collection of objects providing information over the
                 connection limiting MIB capability."
    ::= { alvarionConnectionLimitingMIBGroups 2 }

END

-- ****************************************************************************
--  ALVARION-LICENSE-MIB definitions
--
--  Copyright (c) 2007, Alvarion Ltd.
--  All Rights Reserved.
--
--  Alvarion Licensing Information MIB file.
--
-- ****************************************************************************


ALVARION-LICENSE-MIB DEFINITIONS ::= BEGIN

IMPORTS
    MODULE-IDENTITY, OBJECT-TYPE,
    Integer32
        FROM    SNMPv2-SMI
    DisplayString
        FROM    SNMPv2-TC
    MODULE-COMPLIANCE, OBJECT-GROUP
        FROM    SNMPv2-CONF
    alvarionMgmtV2
        FROM    ALVARION-SMI
;


alvarionLicenseMIB MODULE-IDENTITY
    LAST-UPDATED    "200710310000Z"
    ORGANIZATION    "Alvarion Ltd."
    CONTACT-INFO    "Alvarion Ltd.
                     Postal: 21a HaBarzel St.
                             P.O. Box 13139
                             Tel-Aviv 69710
                             Israel
                     Phone:  +972 3 645 6262"
    DESCRIPTION     "Alvarion Licensing Information MIB."

    ::= { alvarionMgmtV2 29 }


-- alvarionLicenseMIB definition
alvarionLicenseMIBObjects OBJECT IDENTIFIER ::= { alvarionLicenseMIB 1 }

-- alvarion License Information groups
coLicenseGroup OBJECT IDENTIFIER ::= { alvarionLicenseMIBObjects 1 }

-- The License Group
coLicenseFeatureTable OBJECT-TYPE
    SYNTAX      SEQUENCE OF CoLicenseFeatureEntry
    MAX-ACCESS  not-accessible
    STATUS      current
    DESCRIPTION "License information attributes."
    ::= { coLicenseGroup 1 }

coLicenseFeatureEntry OBJECT-TYPE
    SYNTAX      CoLicenseFeatureEntry
    MAX-ACCESS  not-accessible
    STATUS      current
    DESCRIPTION "An entry in the coLicenseFeatureTable.
                 coLicenseFeatureIndex - Uniquely identify a license
                                         feature in a Alvarion product."
    INDEX       { coLicenseFeatureIndex }
    ::= { coLicenseFeatureTable 1 }

CoLicenseFeatureEntry ::= SEQUENCE
{
    coLicenseFeatureIndex          Integer32,
    coLicenseFeatureName           DisplayString,
    coLicenseFeatureState          INTEGER,
    coLicenseFeatureEndingDate     OCTET STRING,
    coLicenseFeatureRemainingDays  Integer32
}

coLicenseFeatureIndex OBJECT-TYPE
    SYNTAX      Integer32 (1..2147483647)
    MAX-ACCESS  not-accessible
    STATUS      current
    DESCRIPTION "Uniquely identify a license feature in a
                 Alvarion product."
    ::= { coLicenseFeatureEntry 1 }

coLicenseFeatureName OBJECT-TYPE
    SYNTAX      DisplayString
    MAX-ACCESS  read-only
    STATUS      current
    DESCRIPTION "Friendly name of the license feature."
    ::= { coLicenseFeatureEntry 2 }

coLicenseFeatureState OBJECT-TYPE
    SYNTAX      INTEGER
                {
                    enable(1),
                    disable(2)
                }
    MAX-ACCESS  read-only
    STATUS      current
    DESCRIPTION "Indicates if the feature is enabled or disabled."
    ::= { coLicenseFeatureEntry 3 }

coLicenseFeatureEndingDate OBJECT-TYPE
    SYNTAX      OCTET STRING (SIZE (10))
    MAX-ACCESS  read-only
    STATUS      current
    DESCRIPTION "Indicates the date when the feature will be
                deactivated. The format of the date is YYYY/MM/DD."
    ::= { coLicenseFeatureEntry 4 }

coLicenseFeatureRemainingDays OBJECT-TYPE
    SYNTAX      Integer32 (0..9999)
    MAX-ACCESS  read-only
    STATUS      current
    DESCRIPTION "Indicates the number of days when the feature will be
                deactivated. If the feature is permanent, the value
                9999 is returned."
    ::= { coLicenseFeatureEntry 5 }


-- conformance information
alvarionLicenseMIBConformance OBJECT IDENTIFIER ::= { alvarionLicenseMIB 2 }
alvarionLicenseMIBCompliances OBJECT IDENTIFIER ::= { alvarionLicenseMIBConformance 1 }
alvarionLicenseMIBGroups      OBJECT IDENTIFIER ::= { alvarionLicenseMIBConformance 2 }


-- compliance statements
alvarionLicenseMIBCompliance MODULE-COMPLIANCE
    STATUS      current
    DESCRIPTION "The compliance statement for the License Information MIB."
    MODULE      MANDATORY-GROUPS
                    {
                        alvarionLicenseMIBGroup
                    }
    ::= { alvarionLicenseMIBCompliances 1 }

-- units of conformance
alvarionLicenseMIBGroup OBJECT-GROUP
    OBJECTS     {
                        coLicenseFeatureName,
                        coLicenseFeatureState,
                        coLicenseFeatureEndingDate,
                        coLicenseFeatureRemainingDays
                }
    STATUS      current
    DESCRIPTION "A collection of objects for the license information status."
    ::= { alvarionLicenseMIBGroups 1 }

END

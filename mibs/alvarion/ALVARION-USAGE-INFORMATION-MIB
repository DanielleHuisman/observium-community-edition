-- ****************************************************************************
--  ALVARION-USAGE-INFORMATION-MIB definitions
--
--  Copyright (c) 2007, Alvarion Ltd.
--  All Rights Reserved.
--
--  Alvarion Usage Information MIB file.
--
-- ****************************************************************************


ALVARION-USAGE-INFORMATION-MIB DEFINITIONS ::= BEGIN

IMPORTS
    MODULE-IDENTITY, OBJECT-TYPE, Unsigned32, TimeTicks
        FROM    SNMPv2-SMI
    MODULE-COMPLIANCE, OBJECT-GROUP
        FROM    SNMPv2-CONF
    alvarionMgmtV2
        FROM    ALVARION-SMI
;


alvarionUsageInformationMIB MODULE-IDENTITY
    LAST-UPDATED    "200710310000Z"
    ORGANIZATION    "Alvarion Ltd."
    CONTACT-INFO    "Alvarion Ltd.
                     Postal: 21a HaBarzel St.
                             P.O. Box 13139
                             Tel-Aviv 69710
                             Israel
                     Phone:  +972 3 645 6262"
    DESCRIPTION     "Alvarion Usage Information MIB."

    ::= { alvarionMgmtV2 21 }


-- alvarionUsageInformationMIB definition
alvarionUsageInformationMIBObjects OBJECT IDENTIFIER ::= { alvarionUsageInformationMIB 1 }

-- alvarion Usage groups
coUsageInformationGroup OBJECT IDENTIFIER ::= { alvarionUsageInformationMIBObjects 1 }

-- The Usage Information Group
coUsInfoUpTime OBJECT-TYPE
    SYNTAX      TimeTicks
    MAX-ACCESS  read-only
    STATUS      current
    DESCRIPTION "Elapsed time after the device boot up."
    ::= { coUsageInformationGroup 1 }

coUsInfoLoadAverage1Min OBJECT-TYPE
    SYNTAX      Unsigned32
    MAX-ACCESS  read-only
    STATUS      current
    DESCRIPTION "Average number of processes running during the last minute."
    ::= { coUsageInformationGroup 2 }

coUsInfoLoadAverage5Min OBJECT-TYPE
    SYNTAX      Unsigned32
    MAX-ACCESS  read-only
    STATUS      current
    DESCRIPTION "Average number of processes running during the last 5 minutes."
    ::= { coUsageInformationGroup 3 }

coUsInfoLoadAverage15Min OBJECT-TYPE
    SYNTAX      Unsigned32
    MAX-ACCESS  read-only
    STATUS      current
    DESCRIPTION "Average number of processes running during the last 15 minutes."
    ::= { coUsageInformationGroup 4 }

coUsInfoCpuUseNow OBJECT-TYPE
    SYNTAX      Unsigned32
    UNITS       "%"
    MAX-ACCESS  read-only
    STATUS      current
    DESCRIPTION "Current CPU usage."
    ::= { coUsageInformationGroup 5 }

coUsInfoCpuUse5Sec OBJECT-TYPE
    SYNTAX      Unsigned32
    UNITS       "%"
    MAX-ACCESS  read-only
    STATUS      current
    DESCRIPTION "Average CPU usage during the last 5 seconds."
    ::= { coUsageInformationGroup 6 }

coUsInfoCpuUse10Sec OBJECT-TYPE
    SYNTAX      Unsigned32
    UNITS       "%"
    MAX-ACCESS  read-only
    STATUS      current
    DESCRIPTION "Average CPU usage during the last 10 seconds."
    ::= { coUsageInformationGroup 7 }

coUsInfoCpuUse20Sec OBJECT-TYPE
    SYNTAX      Unsigned32
    UNITS       "%"
    MAX-ACCESS  read-only
    STATUS      current
    DESCRIPTION "Average CPU usage during the last 20 seconds."
    ::= { coUsageInformationGroup 8 }

coUsInfoRamTotal OBJECT-TYPE
    SYNTAX      Unsigned32
    UNITS       "Kb"
    MAX-ACCESS  read-only
    STATUS      current
    DESCRIPTION "Total system RAM."
    ::= { coUsageInformationGroup 9 }

coUsInfoRamFree OBJECT-TYPE
    SYNTAX      Unsigned32
    UNITS       "Kb"
    MAX-ACCESS  read-only
    STATUS      current
    DESCRIPTION "Available system RAM."
    ::= { coUsageInformationGroup 10 }

coUsInfoRamBuffer OBJECT-TYPE
    SYNTAX      Unsigned32
    UNITS       "Kb"
    MAX-ACCESS  read-only
    STATUS      current
    DESCRIPTION "Memory used by the buffers."
    ::= { coUsageInformationGroup 11 }

coUsInfoRamCached OBJECT-TYPE
    SYNTAX      Unsigned32
    UNITS       "Kb"
    MAX-ACCESS  read-only
    STATUS      current
    DESCRIPTION "Memory used by the system cache."
    ::= { coUsageInformationGroup 12 }

coUsInfoStorageUsePermanent OBJECT-TYPE
    SYNTAX      Unsigned32
    UNITS       "%"
    MAX-ACCESS  read-only
    STATUS      current
    DESCRIPTION "Percentage of permanent storage that is in use."
    ::= { coUsageInformationGroup 13 }

coUsInfoStorageUseTemporary OBJECT-TYPE
    SYNTAX      Unsigned32
    UNITS       "%"
    MAX-ACCESS  read-only
    STATUS      current
    DESCRIPTION "Percentage of temporary storage that is in use."
    ::= { coUsageInformationGroup 14 }


-- Usage Information notifications
alvarionUsageInformationMIBNotificationPrefix OBJECT IDENTIFIER ::= { alvarionUsageInformationMIB 2 }
alvarionUsageInformationMIBNotifications OBJECT IDENTIFIER ::= { alvarionUsageInformationMIBNotificationPrefix 0 }


-- conformance information
alvarionUsageInformationMIBConformance OBJECT IDENTIFIER ::= { alvarionUsageInformationMIB 3 }
alvarionUsageInformationMIBCompliances OBJECT IDENTIFIER ::= { alvarionUsageInformationMIBConformance 1 }
alvarionUsageInformationMIBGroups      OBJECT IDENTIFIER ::= { alvarionUsageInformationMIBConformance 2 }


-- compliance statements
alvarionUsageInformationMIBCompliance MODULE-COMPLIANCE
    STATUS      current
    DESCRIPTION "The compliance statement for the Usage Information MIB."
    MODULE      MANDATORY-GROUPS
                    {
                        alvarionUsageInformationMIBGroup
                    }
    ::= { alvarionUsageInformationMIBCompliances 1 }

-- units of conformance
alvarionUsageInformationMIBGroup OBJECT-GROUP
    OBJECTS     {
                    coUsInfoUpTime,
                    coUsInfoLoadAverage1Min,
                    coUsInfoLoadAverage5Min,
                    coUsInfoLoadAverage15Min,
                    coUsInfoCpuUseNow,
                    coUsInfoCpuUse5Sec,
                    coUsInfoCpuUse10Sec,
                    coUsInfoCpuUse20Sec,
                    coUsInfoRamTotal,
                    coUsInfoRamFree,
                    coUsInfoRamBuffer,
                    coUsInfoRamCached,
                    coUsInfoStorageUsePermanent,
                    coUsInfoStorageUseTemporary
                }
    STATUS      current
    DESCRIPTION "A collection of objects for CPU and memory usage."
    ::= { alvarionUsageInformationMIBGroups 1 }

END

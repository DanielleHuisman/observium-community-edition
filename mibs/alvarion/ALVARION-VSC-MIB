-- ****************************************************************************
--  ALVARION-VSC-MIB definitions
--
--  Copyright (c) 2007, Alvarion Ltd.
--  All Rights Reserved.
--
--  Alvarion Virtual Service Communities MIB file.
--
-- ****************************************************************************


ALVARION-VSC-MIB DEFINITIONS ::= BEGIN

IMPORTS
    MODULE-IDENTITY, OBJECT-TYPE,
    Integer32
        FROM    SNMPv2-SMI
    DisplayString, TruthValue
        FROM    SNMPv2-TC
    MODULE-COMPLIANCE, OBJECT-GROUP
        FROM    SNMPv2-CONF
    alvarionMgmtV2
        FROM    ALVARION-SMI
    AlvarionSSID
        FROM    ALVARION-TC
;


alvarionVscMIB MODULE-IDENTITY
    LAST-UPDATED    "200710310000Z"
    ORGANIZATION    "Alvarion Ltd."
    CONTACT-INFO    "Alvarion Ltd.
                     Postal: 21a HaBarzel St.
                             P.O. Box 13139
                             Tel-Aviv 69710
                             Israel
                     Phone:  +972 3 645 6262"
    DESCRIPTION     "Alvarion Virtual Service Communities MIB."

    ::= { alvarionMgmtV2 22 }


-- alvarionVscMIB definition
alvarionVscMIBObjects OBJECT IDENTIFIER ::= { alvarionVscMIB 1 }

-- alvarion Virtual Service Communities groups
coVscConfigGroup OBJECT IDENTIFIER ::= { alvarionVscMIBObjects 1 }

-- The Virtual Service Communities Configuration Group
coVscConfigTable OBJECT-TYPE
    SYNTAX      SEQUENCE OF CoVscConfigEntry
    MAX-ACCESS  not-accessible
    STATUS      current
    DESCRIPTION "Virtual Service Communities configuration attributes."
    ::= { coVscConfigGroup 1 }

coVscConfigEntry OBJECT-TYPE
    SYNTAX      CoVscConfigEntry
    MAX-ACCESS  not-accessible
    STATUS      current
    DESCRIPTION "An entry in the coVscConfigTable.
                 coVscCfgIndex - Uniquely identify a Virtual Service
                                 Community on an Alvarion device."
    INDEX       { coVscCfgIndex }
    ::= { coVscConfigTable 1 }

CoVscConfigEntry ::= SEQUENCE
{
    coVscCfgIndex                  Integer32,
    coVscCfgFriendlyVscName        DisplayString,
    coVscCfgSSID                   AlvarionSSID,
    coVscCfgAccessControlled       TruthValue,
    coVscCfgSecurity               INTEGER,
    coVscCfgEncryption             INTEGER,
    coVscCfg8021xAuthentication    INTEGER,
    coVscCfgMACAuthentication      TruthValue,
    coVscCfgHTMLAuthentication     TruthValue
}

coVscCfgIndex OBJECT-TYPE
    SYNTAX      Integer32 (1..2147483647)
    MAX-ACCESS  not-accessible
    STATUS      current
    DESCRIPTION "Specifies the index of a Virtual Service Community (VSC)
                 in the configuration file."
    ::= { coVscConfigEntry 1 }

coVscCfgFriendlyVscName OBJECT-TYPE
    SYNTAX      DisplayString
    MAX-ACCESS  read-only
    STATUS      current
    DESCRIPTION "The friendly name associated with the VSC."
    ::= { coVscConfigEntry 2 }

coVscCfgSSID OBJECT-TYPE
    SYNTAX      AlvarionSSID
    MAX-ACCESS  read-only
    STATUS      current
    DESCRIPTION "Service Set ID assigned to the VSC."
    ::= { coVscConfigEntry 3 }

coVscCfgAccessControlled OBJECT-TYPE
    SYNTAX      TruthValue
    MAX-ACCESS  read-only
    STATUS      current
    DESCRIPTION "Indicates if the VSC is access controlled."
    ::= { coVscConfigEntry 4 }

coVscCfgSecurity OBJECT-TYPE
    SYNTAX      INTEGER
                {
                    open(1),
                    ieee802dot1x(2),
                    wpa(3),
                    wpa2(4),
                    wpaAndWpa2(5)
                }
    MAX-ACCESS  read-only
    STATUS      current
    DESCRIPTION "Indicates the type of security used by the VSC."
    ::= { coVscConfigEntry 5 }

coVscCfgEncryption OBJECT-TYPE
    SYNTAX      INTEGER
                {
                    none(1),
                    wep(2),
                    tkip(3),
                    aes(4),
                    tkipAndAes(5)
                }
    MAX-ACCESS  read-only
    STATUS      current
    DESCRIPTION "Indicates the encryption type supported by the VSC."
    ::= { coVscConfigEntry 6 }

coVscCfg8021xAuthentication OBJECT-TYPE
    SYNTAX      INTEGER
                {
                    none(1),
                    radius(2),
                    psk(3)
                }
    MAX-ACCESS  read-only
    STATUS      current
    DESCRIPTION "Indicates the 802.1x authentication type supported by the VSC."
    ::= { coVscConfigEntry 7 }

coVscCfgMACAuthentication OBJECT-TYPE
    SYNTAX      TruthValue
    MAX-ACCESS  read-only
    STATUS      current
    DESCRIPTION "Indicates if MAC authentication is enabled on the VSC."
    ::= { coVscConfigEntry 8 }

coVscCfgHTMLAuthentication OBJECT-TYPE
    SYNTAX      TruthValue
    MAX-ACCESS  read-only
    STATUS      current
    DESCRIPTION "Indicates if HTML authentication is enabled on the
                 VSC. Always false on a satellite."
    ::= { coVscConfigEntry 9 }


-- conformance information
alvarionVscMIBConformance OBJECT IDENTIFIER ::= { alvarionVscMIB 2 }
alvarionVscMIBCompliances OBJECT IDENTIFIER ::= { alvarionVscMIBConformance 1 }
alvarionVscMIBGroups      OBJECT IDENTIFIER ::= { alvarionVscMIBConformance 2 }


-- compliance statements
alvarionVscMIBCompliance MODULE-COMPLIANCE
    STATUS      current
    DESCRIPTION "The compliance statement for the Virtual Service
                 Communities MIB."
    MODULE      MANDATORY-GROUPS
                    {
                        alvarionVscMIBGroup
                    }
    ::= { alvarionVscMIBCompliances 1 }

-- units of conformance
alvarionVscMIBGroup OBJECT-GROUP
    OBJECTS     {
                        coVscCfgFriendlyVscName,
                        coVscCfgSSID,
                        coVscCfgAccessControlled,
                        coVscCfgSecurity,
                        coVscCfgEncryption,
                        coVscCfg8021xAuthentication,
                        coVscCfgMACAuthentication,
                        coVscCfgHTMLAuthentication
                }
    STATUS      current
    DESCRIPTION "A collection of objects for the wireless interface
                 status."
    ::= { alvarionVscMIBGroups 1 }

END

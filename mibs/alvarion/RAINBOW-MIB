-- ============================================================
-- Description :
--
--                  Rainbow Management Information Base
--
--                         06/06/2006
--
-- 
-- ============================================================

RAINBOW-MIB	DEFINITIONS ::= BEGIN
	IMPORTS
                products
                        FROM ALVARION-TOP-MIB
		DisplayString, RowStatus, MacAddress, TEXTUAL-CONVENTION
			FROM SNMPv2-TC
		MODULE-IDENTITY, OBJECT-TYPE, IpAddress, TimeTicks, Unsigned32, Integer32
			FROM SNMPv2-SMI;


	rainbow	MODULE-IDENTITY
		LAST-UPDATED	"200606061500Z"
		ORGANIZATION	"Alvarion Ltd."
		CONTACT-INFO	"Alvarion Customer Service
		Postal: Alvarion Ltd.
			Barzel 21
			Tel Aviv 69710 
			ISRAEL
               	E-mail: CS_Coordinator@alvarion.com"
		DESCRIPTION		
				"Rainbow MIB"
		REVISION		"200606061500Z"
		DESCRIPTION		
				"Release 4.0"
		::=  {  products  2  }


--	alvarion	OBJECT IDENTIFIER
--		::=  {  enterprises  12394  }

--	products	OBJECT IDENTIFIER
--		::=  {  alvarion  1  }



-- TEXTUAL-CONVENTIONS --
	TrapSeverity ::= TEXTUAL-CONVENTION 
		STATUS			current
		DESCRIPTION		"Description."
		SYNTAX 			INTEGER  
		                {
						  none (0),
						  critical (1),
						  major (2),
						  minor (3),
						  warning (4),
						  info (5)
						}

	Modulation	::= TEXTUAL-CONVENTION 
		STATUS			current
		DESCRIPTION		"Description."
		SYNTAX			INTEGER	{
		                          notDefined (0),
		                          rBpsk12 (1),
		                          rBpsk34 (2),
								  rQpsk12 (3),
								  rQpsk34 (4),
								  r16Qam12 (5),
								  r16Qam34 (6),
								  r64Qam23 (7),
								  r64Qam34 (8)
								}

	LinkSpeedAndDuplex	::= TEXTUAL-CONVENTION 
		STATUS			current
		DESCRIPTION		"Description."
		SYNTAX			INTEGER	{
		                          unknown   		( 1 ),
		                          fullDuplex100Mbps ( 2 ),
		                          halfDuplex100Mbps ( 3 ),
		                          fullDuplex10Mbps  ( 4 ),
		                          halfDuplex10Mbps  ( 5 ),
								  fullDuplex1Gbps   ( 6 ),
								  halfDuplex1Gbps 	( 7	)
								 }

 	TenthdB ::= TEXTUAL-CONVENTION
        DISPLAY-HINT "d-1"
        STATUS       current
        DESCRIPTION
            "This data type represents power levels that are normally
             expressed in dB. Units are in tenths of a dB;
             for example, 5.1 dB will be represented as 51."
        SYNTAX       Integer32


--  rbNotifications			OBJECT IDENTIFIER ::=  {  rainbow  0  }
--	rbSysConfig			    OBJECT IDENTIFIER ::=  {  rainbow  1  }
--	rbChassisConfig			OBJECT IDENTIFIER ::=  {  rainbow  2  }
--  rbPerformance   		OBJECT IDENTIFIER ::=  {  rainbow  4  } (see rbPerformance.mib)
--  rbSubcriberUnitConfig	OBJECT IDENTIFIER ::=  {  rainbow  5  }
--  rbAuthorizationAndTraps	OBJECT IDENTIFIER ::=  {  rainbow  6  }
--  rbInterfaces			OBJECT IDENTIFIER ::=  {  rainbow  7  }
--  rbTesting			   	OBJECT IDENTIFIER ::=  {  rainbow  8  }
--  rbIPConfig				OBJECT IDENTIFIER ::=  {  rainbow  9  }
--  rbSwUpgrade 			OBJECT IDENTIFIER ::=  {  rainbow  10 }
--	rbBaseStation		    OBJECT IDENTIFIER ::=  {  rainbow  11  }
--	rbRadioCluster		    OBJECT IDENTIFIER ::=  {  rainbow  12  }
--	rbOduConfig			    OBJECT IDENTIFIER ::=  {  rainbow  13  }
--	rbChainConfig			OBJECT IDENTIFIER ::=  {  rainbow  14  }
--	rbGPSInfo			    OBJECT IDENTIFIER ::=  {  rainbow  15  }
--  rbLicense				OBJECT IDENTIFIER ::=  {  rainbow  50 } 
--  rbServices	    		OBJECT IDENTIFIER ::=  {  rainbow  100  } (see rbServices.mib)
--  rbRadiusClient	        OBJECT IDENTIFIER ::=  {  rainbow  150  } (see rbRadius.mib)


-- ===========================================================================
-- Base Station Parameters
-- ===========================================================================
	rbBaseStation			OBJECT IDENTIFIER		::=  {  rainbow  11  }

	rbBsAtpcParameters		OBJECT IDENTIFIER		::=  {  rbBaseStation  1  }

	rbBsATPCSupport	OBJECT-TYPE	
		SYNTAX			INTEGER	{
		                          enabled  (1),		  
								  disabled (2),
								  notDefined (3)
								 }
		MAX-ACCESS		read-write
		STATUS			current
		DESCRIPTION		
				"This parameter defines if ATPC mechanism is supported
				 by the Base Station."
		::=  {  rbBsAtpcParameters  1  }

	rbBsOptimalRSSI	 OBJECT-TYPE
		SYNTAX			Integer32 (-90..-60)  
		MAX-ACCESS		read-write
		STATUS			current
		DESCRIPTION		
				"The RSSI in dBm required from all SUs when ATPC is enabled."
		DEFVAL			{ -73 }
		::=  {  rbBsAtpcParameters 2 }


	rbBsCellParameters		OBJECT IDENTIFIER		::=  {  rbBaseStation  2  }

 	rbBSConfiguredOperatorId	 OBJECT-TYPE
		SYNTAX			OCTET STRING (SIZE(3)) 
		MAX-ACCESS		read-write
		STATUS			current
		DESCRIPTION		
				"Operator ID."
		::=  {  rbBsCellParameters 1}

    rbBSConfiguredCellId	 OBJECT-TYPE
		SYNTAX			OCTET STRING (SIZE(2)) 
		MAX-ACCESS		read-write
		STATUS			current
		DESCRIPTION		
				"Unique Cell ID."
		::=  {  rbBsCellParameters 2}


	rbBsRFModeParameters		OBJECT IDENTIFIER		::=  {  rbBaseStation  3  }

	rbBsRFConfiguredDuplexMode	OBJECT-TYPE	
		SYNTAX			INTEGER	{
		                          fdd (1),		  
								  tdd (2)
								 }
		MAX-ACCESS		read-write
		STATUS			current
		DESCRIPTION		
				"Configured Duplex Mode."
		::=  {  rbBsRFModeParameters  1  }

	rbBsRFCurrentDuplexMode	OBJECT-TYPE	
		SYNTAX			INTEGER	{
		                          fdd (1),		  
								  tdd (2)
								 }
		MAX-ACCESS		read-only
		STATUS			current
		DESCRIPTION		
				"Current Duplex Mode."
		::=  {  rbBsRFModeParameters  2  }

	rbBsRFConfiguredDlUlRatio	OBJECT-TYPE	
		SYNTAX			INTEGER	{
		                          unavailable (0),		  
								  tdd65  (1),
								  tdd60  (2),
								  tdd55  (3),
								  tdd50  (4),
								  tdd45  (5),
								  tdd40  (6),
								  tdd35  (7)
								 }
	MAX-ACCESS		    read-write
		STATUS			current
		DESCRIPTION		
				"DL-UL Ratio configurable only for TDD mode,
				 for FDD will be always unavailable (0).
                 For TDD mode the following values can be selected:
                 65-35% (1), 60-40% (2), 55-45% (3), 50-50% (4), 45-55% (5), 40-60% (6), 35-65% (7).
                 The Default value is 65-35% (1)."
		::=  {  rbBsRFModeParameters  3  }

	rbBsRFCurrentDlUlRatio	OBJECT-TYPE	
		SYNTAX			INTEGER	{
		                          unavailable (0),		  
								  tdd65  (1),
								  tdd60  (2),
								  tdd55  (3),
								  tdd50  (4),
								  tdd45  (5),
								  tdd40  (6),
								  tdd35  (7)
								 }
	MAX-ACCESS		    read-only
		STATUS			current
		DESCRIPTION		
				"Current DL-UL Ratio."
		::=  {  rbBsRFModeParameters  4  }


	rbBSClockConfigParameters		OBJECT IDENTIFIER		::=  {  rbBaseStation  4  }

	rbBSConfiguredExternalPPSClock    OBJECT-TYPE
		SYNTAX			INTEGER	{
		                           enable   ( 1 ),
		                           disable  ( 2 )
								 }
		MAX-ACCESS		read-write
		STATUS			current
		DESCRIPTION		
				"Configured option of the External 1PPS Clock parameter."
		DEFVAL			{ enable }
		::=  {  rbBSClockConfigParameters  1  }

	rbBSCurrentExternalPPSClock    OBJECT-TYPE
		SYNTAX			INTEGER	{
		                           enable   ( 1 ),
		                           disable  ( 2 )
								 }
		MAX-ACCESS		read-only
		STATUS			current
		DESCRIPTION		
				"Current option of the External 1PPS Clock parameter."
		::=  {  rbBSClockConfigParameters  2  }

	rbBSConfiguredExternal16MhzClock    OBJECT-TYPE
		SYNTAX			INTEGER	{
		                           enable   ( 1 ),
		                           disable  ( 2 )
								 }
		MAX-ACCESS		read-write
		STATUS			current
		DESCRIPTION		
				"Configured option of the External 16MHz Clock parameter."
		DEFVAL			{ disable }
		::=  {  rbBSClockConfigParameters  3  }

	rbBSCurrentExternal16MhzClock    OBJECT-TYPE
		SYNTAX			INTEGER	{
		                           enable   ( 1 ),
		                           disable  ( 2 )
								 }
		MAX-ACCESS		read-only
		STATUS			current
		DESCRIPTION		
				"Current option of the External 16MHz Clock parameter."
		::=  {  rbBSClockConfigParameters  4  }


-- ===========================================================================
-- Cluster Parameters
-- ===========================================================================
	rbRadioCluster			OBJECT IDENTIFIER		::=  {  rainbow  12  }

	rbRadioClusterTable	OBJECT-TYPE
		SYNTAX		SEQUENCE  OF  RbRadioClusterEntry
		MAX-ACCESS	not-accessible
		STATUS		current
		DESCRIPTION	
			"Table that holds Radio Clusters` parameters."
		::=  { rbRadioCluster  1 }

	rbRadioClusterEntry	OBJECT-TYPE
		SYNTAX		RbRadioClusterEntry
		MAX-ACCESS	not-accessible
		STATUS		current
		DESCRIPTION	
			"Row Description"
		INDEX		{ rbRadioClusterId }
		::=  { rbRadioClusterTable 1 }

	RbRadioClusterEntry  ::=  SEQUENCE {
		rbRadioClusterId                     Integer32,		
		rbRadioClusterName                   DisplayString,
		rbRadioClusterLocation               DisplayString,
		rbRadioClusterSectorHeading        	 Integer32,		
		rbRadioClusterSectorBeamWidth        Integer32,		
		rbRadioClusterRowStatus              RowStatus
		}

	rbRadioClusterId	OBJECT-TYPE	
		SYNTAX			Integer32 ( 1 .. 6 )  
		MAX-ACCESS		read-only
		STATUS			current
		DESCRIPTION		
				"Radio Cluster ID."
		::=  {  rbRadioClusterEntry  1  }

	rbRadioClusterName	OBJECT-TYPE	
		SYNTAX			DisplayString  ( SIZE ( 0 .. 32  ) ) 
		MAX-ACCESS		read-write
		STATUS			current
		DESCRIPTION		
				"Radio Cluster name."
		::=  {  rbRadioClusterEntry  2  }

	rbRadioClusterLocation	OBJECT-TYPE	
		SYNTAX			DisplayString  ( SIZE ( 0 .. 255  ) ) 
		MAX-ACCESS		read-write
		STATUS			current
		DESCRIPTION		
				"Radio Cluster Location."
		::=  {  rbRadioClusterEntry  3  }

	rbRadioClusterSectorHeading	OBJECT-TYPE	
		SYNTAX			Integer32  ( 0 .. 359 )
		MAX-ACCESS		read-write
		STATUS			current
		DESCRIPTION		
				"Radio Cluster Sector Heading - the angle from the north."
		::=  {  rbRadioClusterEntry  4  }

	rbRadioClusterSectorBeamWidth	OBJECT-TYPE	
		SYNTAX			Integer32  ( 0 .. 359 )
		MAX-ACCESS		read-write
		STATUS			current
		DESCRIPTION		
				"Radio Cluster Sector Antenna`s Beam Width."
		::=  {  rbRadioClusterEntry  5  }

	rbRadioClusterRowStatus	OBJECT-TYPE	
		SYNTAX			RowStatus
		MAX-ACCESS		read-write
		STATUS			current
		DESCRIPTION		
				"Control for creating and deleting entries. Entries may be modified while active.
                 active (1) - means that the entry is available for use by the managed device
                 and relevant parameters may be modified;
                 createAndGo (4) is used for creating a new entry and to have its status
                 automatically set to active;
                 destroy (6) is used for deleting an existing entry."
		::=  {  rbRadioClusterEntry  6  }


-- ===========================================================================
-- Odu Parameters
-- ===========================================================================
	rbOduConfig			OBJECT IDENTIFIER		::=  {  rainbow  13  }

	rbOduConfigTable	OBJECT-TYPE
		SYNTAX		SEQUENCE  OF  RbOduConfigEntry
		MAX-ACCESS	not-accessible
		STATUS		current
		DESCRIPTION	
			"Table that holds ODU`s parameters."
		::=  { rbOduConfig  1 }

	rbOduConfigEntry	OBJECT-TYPE
		SYNTAX		RbOduConfigEntry
		MAX-ACCESS	not-accessible
		STATUS		current
		DESCRIPTION	
			"Row Description"
		INDEX		{ rbOduConfigId }
		::=  { rbOduConfigTable 1 }

	RbOduConfigEntry  ::=  SEQUENCE {
		rbOduConfigId                     Integer32,		
		rbOduAssociatedRadioClusterId     Integer32,		
		rbOduTxPower                      DisplayString,		
		rbOduAdminStatus                  INTEGER,		
		rbOduTemperature                  Integer32,		
		rbOduHwRevision                   DisplayString,		
		rbOduHwConfigDescription          DisplayString,		
		rbOduOperationalStatus            INTEGER,		
		rbOduHwHC08Version                DisplayString,		
		rbOduCpldVersion                  DisplayString,		
		rbOduCardSerialNumber             DisplayString,
		rbOduConfigFrequencyBand          Integer32,	  	
		rbOduRowStatus                    RowStatus,
		rbOduMaxTxPower                   Integer32	  	
		}

	rbOduConfigId	OBJECT-TYPE	
		SYNTAX			Integer32  ( 1 .. 24 )   
		MAX-ACCESS		read-only
		STATUS			current
		DESCRIPTION		
				"ODU's ID."
		::=  {  rbOduConfigEntry  1  }

	rbOduAssociatedRadioClusterId	OBJECT-TYPE	
		SYNTAX			Integer32  ( 0 .. 6 )
		MAX-ACCESS		read-write
		STATUS			current
		DESCRIPTION		
				"Associated Radio Cluster ID. Valid values: 1 to 6.
				 Must be the ID of a defined Radio Cluster.
				 Agent will return 0 if Associated Radio Cluster ID is unknown."
		::=  {  rbOduConfigEntry  2  }

	rbOduTxPower	OBJECT-TYPE	
		SYNTAX			DisplayString 
		MAX-ACCESS		read-write
		STATUS			current
		DESCRIPTION		
				"The ODU's Tx Power in dBm.	Allowed range is from 13 to 50, 
				 using a resolution of 0.25dBm. 
				 Actual range is from 13 to the value defined by rbOduMaxTxPower.
				 For AUs using diversity (rbAuDiversityMode other than noDiversity),
				 this value is configurable only for the ODU associated with channel 1.
				 The Tx Power of ODUs associated with other channels will be configured
				 automatically to the value configured for the ODU associated with channel 1."
		::=  {  rbOduConfigEntry  3  }

	rbOduAdminStatus	OBJECT-TYPE	
		SYNTAX			INTEGER  { enable ( 1 ) , disable ( 2 ) } 
		MAX-ACCESS		read-write
		STATUS			current
		DESCRIPTION		
				"Odu Admin Status."
		::=  {  rbOduConfigEntry  4  }

	rbOduTemperature	OBJECT-TYPE	
		SYNTAX			Integer32 
		MAX-ACCESS		read-only
		STATUS			current
		DESCRIPTION		
				"Odu Messured Temperature.
				 Agent will return 0 if Odu Temperature is unknown."
		::=  {  rbOduConfigEntry  5  }

	rbOduHwRevision	OBJECT-TYPE	
		SYNTAX			DisplayString ( SIZE ( 0 .. 10 ) )
		MAX-ACCESS		read-only
		STATUS			current
		DESCRIPTION		
				"Odu HW Revision."
		::=  {  rbOduConfigEntry  6  }

	rbOduHwConfigDescription	OBJECT-TYPE	
		SYNTAX			DisplayString ( SIZE ( 0 .. 10 ) )
		MAX-ACCESS		read-only
		STATUS			current
		DESCRIPTION		
				"Odu HW Configuration Description."
		::=  {  rbOduConfigEntry  7  }

	rbOduOperationalStatus	OBJECT-TYPE	
		SYNTAX			INTEGER  { initFailure  ( 1 ) , 
								   down         ( 2 ) , 
								   powerOff     ( 3 ) , 
								   powerOnWait  ( 4 ) , 
								   powerOn      ( 5 ) , 
								   initializing ( 6 ) , 
								   up           ( 7 ) } 
		MAX-ACCESS		read-only
		STATUS			current
		DESCRIPTION		
				"Odu Operational Status."
		::=  {  rbOduConfigEntry  8  }

	rbOduHwHC08Version	OBJECT-TYPE	
		SYNTAX			DisplayString ( SIZE ( 0 .. 10 ) )
		MAX-ACCESS		read-only
		STATUS			current
		DESCRIPTION		
				"The version of the HC08 component in the ODU."
		::=  {  rbOduConfigEntry  9  }

	rbOduCpldVersion	OBJECT-TYPE	
		SYNTAX			DisplayString ( SIZE ( 0 .. 10 ) )
		MAX-ACCESS		read-only
		STATUS			current
		DESCRIPTION		
				"The version of the CPLD component in the ODU."
		::=  {  rbOduConfigEntry  10  }

	rbOduCardSerialNumber	OBJECT-TYPE	
		SYNTAX			DisplayString
		MAX-ACCESS		read-only
		STATUS			current
		DESCRIPTION		
				"The serial number of the ODU."
		::=  {  rbOduConfigEntry  11  }

	rbOduConfigFrequencyBand	OBJECT-TYPE	
		SYNTAX			Integer32 
		MAX-ACCESS		read-write
		STATUS			current
		DESCRIPTION		
				"Odu Configured Frequency Band ID.
				 Must be one of the Frequency Band IDs available in the Frequency Bands Table.
				 Agent will return 0 if Frequency Band is unknown."
		::=  {  rbOduConfigEntry  12  }

	rbOduRowStatus	OBJECT-TYPE	
		SYNTAX			RowStatus
		MAX-ACCESS		read-write
		STATUS			current
		DESCRIPTION		
				"Control for creating and deleting entries. Entries may be modified while active.
                 active (1) - means that the entry is available for use by the managed device
                 and relevant parameters may be modified;
                 createAndGo (4) is used for creating a new entry and to have its status
                 automatically set to active;
                 destroy (6) is used for deleting an existing entry."
		::=  {  rbOduConfigEntry  13  }

    rbOduMaxTxPower	OBJECT-TYPE	
		SYNTAX			Integer32  
		MAX-ACCESS		read-only
		STATUS			current
		DESCRIPTION		
				"The maximum Tx power supported by the ODU, in dBm units."
		::=  {  rbOduConfigEntry  14  }


-- ===========================================================================
-- System Parameters
-- ===========================================================================
	rbSysConfig				OBJECT IDENTIFIER		::=  {  rainbow  1  }
	rbSysGeneral			OBJECT IDENTIFIER		::=  {  rbSysConfig  1  }

-- ===========================================================================
-- System General Parameters
-- This group is retrieved using community NPU 
-- ===========================================================================

 	rbSysFaultStatus	OBJECT-TYPE	
		SYNTAX			INTEGER  { 
		                           noFaults ( 1 ) ,
		                           minor    ( 2 ) ,
		                           major    ( 3 ) ,
		                           critical ( 4 )
		                         } 
		MAX-ACCESS		read-only
		STATUS			current
		DESCRIPTION		
				"The summarized severity of the entire System fault status.
				 Not supported in current version."
		::=  {  rbSysGeneral  1  }

 	rbSysLastTrapSeqNumber	OBJECT-TYPE	
		SYNTAX			Unsigned32
		MAX-ACCESS		read-only
		STATUS			current
		DESCRIPTION		
				"The last trap sequence number before the reset."
		::=  {  rbSysGeneral 2  }


-- ========================================================================
-- Rainbow Chassis Configuration Parameters 
-- ========================================================================
   rbChassisConfig		OBJECT IDENTIFIER 		::=  {  rainbow  2  }

-- rbSlotConfigTable  		    {rbChassisConfig  1 }
-- rbNpuConfiguration	       OBJECT IDENTIFIER 	::  {rbChassisConfig  2	}
-- rbAuConfigTable	       	    {rbChassisConfig  3	}
-- rbAcuConfiguration		   OBJECT IDENTIFIER 	::  {rbChassisConfig  6	}
-- rbPsuConfigTable		       OBJECT IDENTIFIER  	::= {rbChassisConfig  7 }
-- rbPiuConfigTable			   OBJECT IDENTIFIER  	::= {rbChassisConfig  8 }
-- rbAuHwComponentsInfoTable   OBJECT IDENTIFIER  	::= {rbChassisConfig  9 }
-- rbChannelConfigTable        OBJECT IDENTIFIER  	::= {rbChassisConfig  11 }

--==================================================================
--Slot Configuration Table
--It is retrieved with community NPU
--==================================================================
	rbSlotConfigTable	OBJECT-TYPE
		SYNTAX		SEQUENCE  OF  RbSlotConfigEntry
		MAX-ACCESS	not-accessible
		STATUS		current
		DESCRIPTION	
			"This table provides parameters common for all cards in chassis	slots.
			It is retrieved with community NPU"
		::=  { rbChassisConfig  1 }

	rbSlotConfigEntry	OBJECT-TYPE
		SYNTAX		RbSlotConfigEntry
		MAX-ACCESS	not-accessible
		STATUS		current
		DESCRIPTION	
			"Table entry"
		INDEX		{  rbSlotNumber  }
		::=  { rbSlotConfigTable 1 }

	RbSlotConfigEntry  ::=  SEQUENCE {
		rbSlotNumber  			Integer32,
		rbSlotDetectedCard      INTEGER,
		rbSlotConfiguredCard	INTEGER,
		rbSlotAllowedCard		INTEGER,
		rbSlotLedStatus  		OCTET STRING,
		rbSlotFaultStatus  		INTEGER,
		rbSlotExtractorState    INTEGER
		}

	rbSlotNumber	OBJECT-TYPE	
		SYNTAX			Integer32  ( 1 .. 9  ) 
		MAX-ACCESS		read-only
		STATUS			current
		DESCRIPTION		
				"Physical placement of the card in the chassis (the Slot number).
				 This is the table index {1 up to 9}."
		::=  {  rbSlotConfigEntry  1  }

	rbSlotDetectedCard	OBJECT-TYPE	
		SYNTAX			INTEGER  { 
		                           notInstalled ( 1 ) ,
		                           unknown ( 2 ) ,
		                           au ( 3 ) ,
		                           npu ( 4 )
	                         } 
		MAX-ACCESS		read-only
		STATUS			current
		DESCRIPTION		
				"The auto detected card type. It also indicates whether the slot has a card
				 inserted in it or not."
		::=  {  rbSlotConfigEntry  2  }

	rbSlotConfiguredCard	OBJECT-TYPE	
		SYNTAX			INTEGER  { 
		                           notInstalled ( 1 ) ,
		                           unknown ( 2 ) ,
		                           au ( 3 ) ,
		                           npu ( 4 )
	                         } 
		MAX-ACCESS		read-write
		STATUS			current
		DESCRIPTION		
				"The card type that is configured for the slot. In current version this is read_only
				 (AU is configured for slots 1-4 and 7-9, Slot 5 is NPU, slot 6 is Not Installed)."
		::=  {  rbSlotConfigEntry  3  }

	rbSlotAllowedCard	OBJECT-TYPE	
		SYNTAX			INTEGER  { 
		                           notInstalled ( 1 ) ,
		                           unknown ( 2 ) ,
		                           au ( 3 ) ,
		                           npu ( 4 )
	                             } 
		MAX-ACCESS		read-only
		STATUS			current
		DESCRIPTION		
				"The card type that is allowed to be inserted in the specific slot.
				 In slots 1-4, 7-9 the allowed card is AU.
				 In slots 5 and the allowed card is NPU, although in the current version NPU can be used only in slot 5."
		::=  {  rbSlotConfigEntry  4  }

	rbSlotLedStatus	OBJECT-TYPE	
		SYNTAX			OCTET STRING
		MAX-ACCESS		read-only
		STATUS			current
		DESCRIPTION		
				"Not supported in current version.
				This field represents summarized information about the card leds.
				Each byte represents the single Led.
				Within each byte, bits 0-3 are the color, 4-7 are the blink rate.
				Supported color codes:
				0000 : Black (LED is off)
				0001 : Green
				0010 : Yellow
				0011 : Red
				0100 : Blue
				Supported blink rates:
				0000 : no blink
				0001 : blink
				
				The type of this field should be suitable to represent leds for all
				available cards in slot.
				------------------------------------
				Card    |   LEDs
				-------------------------------------
				NPU     |ALRM,BST ALRM,EXT ALRM,PWR,MASTER,GPS,Hot Swap
				AU      |ALRM,WLINK,TDM,PWR,WACT,IP,Hot Swap,(ODU ALRM,ODU PWR) x 4"
		::=  {  rbSlotConfigEntry 5  }

	rbSlotFaultStatus	OBJECT-TYPE	
		SYNTAX			INTEGER  { 
		                           noFaults ( 1 ) ,
		                           minor    ( 2 ) , 
		                           major    ( 3 ) ,
		                           critical ( 4 ) ,
								   disconnected (5)
		                         } 
		MAX-ACCESS		read-only
		STATUS			current
		DESCRIPTION		
				"The severity of the card fault. This is summarized information regarding the card
				healthiness in the slot. In case that there is no connection between NPU and
				the card in the slot, status is disconnected "
		::=  {  rbSlotConfigEntry  6  }

	rbSlotExtractorState	OBJECT-TYPE	
		SYNTAX			INTEGER  { 
		                           closed  ( 1 ) ,
		                           opened  ( 2 ) , 
		                           unknown ( 3 ) 
		                         } 
		MAX-ACCESS		read-only
		STATUS			current
		DESCRIPTION		
				"The current state of the card extractor - closed or opened.
				 In the current version this parameter is not supported and the status is always unknown."
		::=  {  rbSlotConfigEntry  7  }


-- ========================================================================
-- NPU configuration parameters 
-- Npu Configuration Parameters are retrieved with community NPU
-- ========================================================================

	rbNpuConfiguration	OBJECT IDENTIFIER ::=  {  rbChassisConfig  2  }

 	rbNpuConfigTable	OBJECT-TYPE
		SYNTAX		SEQUENCE  OF  RbNpuConfigEntry
		MAX-ACCESS	not-accessible
		STATUS		current
		DESCRIPTION	
			"This table provides NPU configuration parameters."
		::=  { rbNpuConfiguration  1 }

	rbNpuConfigEntry	OBJECT-TYPE
		SYNTAX		RbNpuConfigEntry
		MAX-ACCESS	not-accessible
		STATUS		current
		DESCRIPTION	
			"Table entry"
		INDEX		{  rbSlotNumber  }
		::=  { rbNpuConfigTable 1 }

	RbNpuConfigEntry  ::=  SEQUENCE {
		rbNpuSerialNo  	  			DisplayString,
	    rbNpuSysName  				DisplayString,
		rbNpuFaultStatus			INTEGER,
		rbNpuHwRevision				DisplayString,	
		rbNpuOperSwFileName			DisplayString,	
		rbNpuOperSwVersion			DisplayString,	
		rbNpuShadowSwFileName		DisplayString,	
		rbNpuShadowSwVersion		DisplayString,
		rbNpuRunningSoftware		INTEGER,
		rbNpuOperVersionValidity	INTEGER,
		rbNpuShadowVersionValidity	INTEGER,
		rbNpuRedundancyStatus       INTEGER,
		rbNpuUnitControl			INTEGER,
		rbNpuSetDefaults			INTEGER,
		rbNpuHwConfigDescription    DisplayString,
		rbNpuManagementInterface	INTEGER,
		rbNpuCreateConfigFile       DisplayString,
		rbNpuCreateBackupConfigFile INTEGER,
		rbNpuCumulativePowerOnTime  Unsigned32,
		rbNpuBootSwVersion		    DisplayString,
		rbNpuTemperature            Integer32,
		rbNpuDrapTtlRetries         Integer32,
		rbNpuRedundantCPLDVersion   Integer32
		}

	rbNpuSerialNo	OBJECT-TYPE	
		SYNTAX			DisplayString
		MAX-ACCESS		read-only
		STATUS			current
		DESCRIPTION		
				"Serial number assigned for the card during the production time."
		::=  {  rbNpuConfigEntry 1  }

	rbNpuSysName	OBJECT-TYPE	
		SYNTAX			DisplayString (SIZE (1..32))
		MAX-ACCESS		read-write
		STATUS			current
		DESCRIPTION		
				"The name of the card; like System Name in MIB-II."
		::=  {  rbNpuConfigEntry  2  }

	rbNpuFaultStatus	OBJECT-TYPE	
		SYNTAX			INTEGER  { 
		                           noFaults ( 1 ) ,
		                           minor    ( 2 ) ,
		                           major    ( 3 ) ,
		                           critical ( 4 ) ,
								   disconnected (5)
		                         } 
		MAX-ACCESS		read-only
		STATUS			current
		DESCRIPTION		
				"The severity of the card fault. This is summarized information regarding the card
				healthiness in the slot."
		::=  {  rbNpuConfigEntry 3  }

	rbNpuHwRevision	OBJECT-TYPE	
		SYNTAX			DisplayString
		MAX-ACCESS		read-only
		STATUS			current
		DESCRIPTION		
				"Hardware revision of the card."
		::=  {  rbNpuConfigEntry  4  }

	rbNpuOperSwFileName	OBJECT-TYPE	
		SYNTAX			DisplayString  ( SIZE ( 0 .. 80  ) ) 
		MAX-ACCESS		read-only
		STATUS			current
		DESCRIPTION		
				"Operational (Main) Software File Name."
		::=  {  rbNpuConfigEntry  5  }

	rbNpuOperSwVersion	OBJECT-TYPE	
		SYNTAX			DisplayString  ( SIZE ( 0..50  ) ) 
		MAX-ACCESS		read-only
		STATUS			current
		DESCRIPTION		
				"Operational (Main) Software Version."
		::=  {  rbNpuConfigEntry  6  }

	rbNpuShadowSwFileName	OBJECT-TYPE	
		SYNTAX			DisplayString  ( SIZE ( 0 .. 80  ) ) 
		MAX-ACCESS		read-only
		STATUS			current
		DESCRIPTION		
				"Shadow Software File Name."
		::=  {  rbNpuConfigEntry  7  }

	rbNpuShadowSwVersion	OBJECT-TYPE	
		SYNTAX			DisplayString  ( SIZE (0..50  ) ) 
		MAX-ACCESS		read-only
		STATUS			current
		DESCRIPTION		
				"Shadow Software Version."
		::=  {  rbNpuConfigEntry 8  }

	rbNpuRunningSoftware	OBJECT-TYPE	
		SYNTAX			INTEGER {
		                          operational (1),
		                          shadow (2)
		                        }   
		MAX-ACCESS		read-only
		STATUS			current
		DESCRIPTION		
				"Current running software."
		::=  {  rbNpuConfigEntry  9 }

	rbNpuOperVersionValidity	OBJECT-TYPE	
		SYNTAX			INTEGER {
		                          corrupted (1),
		                          valid     (2),
		                          unknown   (3)
								}
		MAX-ACCESS		read-only
		STATUS			current
		DESCRIPTION		
				"The validity of the Operational (Main) Software. Not supported in current version."
		::=  {  rbNpuConfigEntry 10 }

	rbNpuShadowVersionValidity	OBJECT-TYPE	
		SYNTAX			INTEGER {
		                          corrupted (1),
		                          valid     (2),
		                          unknown   (3)
								}
		MAX-ACCESS		read-only
		STATUS			current
		DESCRIPTION		
				"The validity of the Shadow Software. Not supported in current version."
		::=  {  rbNpuConfigEntry 11 }

	rbNpuRedundancyStatus	OBJECT-TYPE	
		SYNTAX			INTEGER {
		                          active (1),
		                          standby (2)
		                        }   
		MAX-ACCESS		read-write
		STATUS			current
		DESCRIPTION		
				"NPU redundancy status. This parameters is read only (always active) in current version."
		::=  {  rbNpuConfigEntry 12 }

   	rbNpuUnitControl	OBJECT-TYPE	
		SYNTAX			INTEGER {
 	                      none (1),
						  reset(2),
	                      resetAndRunFromShadow (4),
	                      makeRunningVersionOperational (5)
	                        }   
		MAX-ACCESS		read-write
		STATUS			current
		DESCRIPTION		
				"If resetAndRunFromShadow (4) is selected, card should perform reset and
				 boot from the shadow software image. 
				 If makeRunningVersionOperational (5) is selected and current running version is
				 marked as shadow, it should be marked as operational after the reset.
				 Get command will always return none (1). None (1) should not be used in Set commands."
		::=  {  rbNpuConfigEntry 13 }

	rbNpuSetDefaults	OBJECT-TYPE	
		SYNTAX			INTEGER  { none ( 1 ) ,
		                           factoryDefault ( 2 ) ,
		                           partialDefault ( 3 ) ,
		                           customerDefault ( 4 ) ,
		                           partialCustomerDefault ( 5 ) } 
		MAX-ACCESS		read-write
		STATUS			current
		DESCRIPTION		
				"This parameter defines the way 'Default Group' parameters are initialised
				with default values:
				1 - Default values should not be copied to the Flash Memory,
				2 - Full Factory Default configuration is copied to the Flash Memory and will be used after next reset,
				3 - Partial Factory Default is copied to the Flash Memory,
				4 - Full Customer Default is copied to the Flash Memory,
				5 - Partial Customer Default is copied to the Flash Memory
				Only Full Factory Defaults (2) is supported in the current version.
				None value (1) is available to support Get and Get Next commands. It should not be used in Set commands."
		DEFVAL			{ none }
		::=  {  rbNpuConfigEntry 14 }

    rbNpuHwConfigDescription  OBJECT-TYPE	
		SYNTAX			DisplayString  ( SIZE (0..10  ) ) 
		MAX-ACCESS		read-only
		STATUS			current
		DESCRIPTION		
				"NPU Hardware configuration description."
		::=  {  rbNpuConfigEntry 15  }

	rbNpuManagementInterface	OBJECT-TYPE	
		SYNTAX			INTEGER 
		                {
		                  managementPort(1),
		                  managementAndDataPort (2)
		                }   
		MAX-ACCESS		read-write
		STATUS			current
		DESCRIPTION		
				"The index of the NPU interface that can be used for management.
				 This parameters is read only in current version, and it is always 2 (both ports can be used for management)."
		::=  {  rbNpuConfigEntry  16  }
 
	rbNpuCreateConfigFile	OBJECT-TYPE	
		SYNTAX			DisplayString ( SIZE (0..20 ) ) 
		MAX-ACCESS		read-write
		STATUS			current
		DESCRIPTION		
				"Not applicable for Version 2 and higher.
				 This variable is used to instruct the NPU to create file containing
				 the Base Station configuration. Variable contains the name of file.
				 In version 1.0 file name is ignored by the agent. Name of the 
				 configuration file is always backup.res"
		::=  {  rbNpuConfigEntry  17  }
 
	rbNpuCreateBackupConfigFile	OBJECT-TYPE	
		SYNTAX			INTEGER  { 
		                           cfgFileNone  			( 0 ) ,
		                           cfgFileFull  			( 1 ) ,
		                           cfgFileProfiles  		( 2 ) ,
		                           cfgFileProfilesServices	( 3 ) ,
								   cfgFileFiltering  		( 4 ) ,
								   cfgFileTraps     		( 5 ) ,
								   cfgFileNmsSync  			( 6 ) ,
								   cfgFileSUSync  	        ( 7 )
		                         } 
		MAX-ACCESS		read-write
		STATUS			current
		DESCRIPTION		
				"This variable is used to instruct the NPU to create file containing
				 the Base Station configuration.
                 cfgFileFull (1) is used for creating full backup files, name of the 
				 configuration file is always backup.res;
                 cfgFileProfiles (2) is used for creating profiles backup files, name of the 
				 configuration file is always profiles.res;
                 cfgFileProfilesServices (3) is used for creating profiles and services backup files,
                 name of the configuration file is always profiles_srvcs.res;
				 cfgFileFiltering (4) is used for creating filtering backup files, name of the 
				 configuration file is always filtering.res;
				 cfgFileTraps (5) is used for creating traps backup files, name of the 
				 configuration file is always Traps_Config.res;
				 cfgFileNmsSync (6) is used for creating a file that contains the entire Base Station configuration.
				 This file is created for the use of the NMS for database synchronization purposes.
				 It includes also the initialization stamp and the last trap sequential number at the file creation time.
				 The name of the file is always Nms_Sync.res;
				 cfgFileSUSync (7) is used for creating a file that contains the SUs inventory configuration.
				 This file is created for the use of the NMS for database synchronization purposes.
				 The name of the file is always SU_Sync.res."
		::=  {  rbNpuConfigEntry  18  }

	rbNpuCumulativePowerOnTime		OBJECT-TYPE	
		SYNTAX			Unsigned32
		MAX-ACCESS		read-only
		STATUS			current
		DESCRIPTION		
				"Cumulative Power On Time (minutes). 
				 Agent will return 0 if Cumulative Power On Time is unknown." 
		::=  {  rbNpuConfigEntry  19  }
	
	rbNpuBootSwVersion	OBJECT-TYPE	
		SYNTAX			DisplayString  ( SIZE ( 0..50  ) ) 
		MAX-ACCESS		read-only
		STATUS			current
		DESCRIPTION		
				"Boot Software Version."
		::=  {  rbNpuConfigEntry  20  }

	rbNpuTemperature	OBJECT-TYPE	
		SYNTAX			Integer32 
		MAX-ACCESS		read-only
		STATUS			current
		DESCRIPTION		
				"NPU Messured Temperature."
		::=  {  rbNpuConfigEntry  21  }

	rbNpuDrapTtlRetries	OBJECT-TYPE	
		SYNTAX			Integer32 ( 1 .. 100 )
		MAX-ACCESS		read-write
		STATUS			current
		DESCRIPTION		
				"NPU DRAP TTL Retries.
				 Sets the limit of TTL retries for gateways that support the DRAP protocol
				 before concluding that the gateway is no longer active and removing it from the database."
		::=  {  rbNpuConfigEntry  22  }

	rbNpuRedundantCPLDVersion	OBJECT-TYPE	
		SYNTAX			Integer32 ( 0 .. 255 )
		MAX-ACCESS		read-only
		STATUS			current
		DESCRIPTION		
				"NPU Redundant CPLD Version. The Redundant CPLD is needed to enable GPS support."
		::=  {  rbNpuConfigEntry  23  }


--==================================================================
--          NPU Bridging Parameters
--==================================================================
	rbNpuBridgingParameters	OBJECT IDENTIFIER ::=  {  rbNpuConfiguration  2  }

	rbNpuBridgeAgingTime	OBJECT-TYPE	
		SYNTAX			Integer32 (0..1440)
		MAX-ACCESS		read-write
		STATUS			current
		DESCRIPTION		
				"The Aging Time for the NPU Bridging tables in minutes.
				 0 is for No Aging."
		::=  {  rbNpuBridgingParameters  1  }
	

--==================================================================
--          Frequency Bands Parameters
--==================================================================
	rbNpuFrequencyBandsParameters	OBJECT IDENTIFIER ::=  {  rbNpuConfiguration  3  }

	rbFrequencyBandsFileVersion	OBJECT-TYPE	
		SYNTAX			Unsigned32 
		MAX-ACCESS		read-only
		STATUS			current
		DESCRIPTION		
				"The version of the Frequency Bands File."
		::=  {  rbNpuFrequencyBandsParameters 1  }


	rbFrequencyBandsTable	OBJECT-TYPE
		SYNTAX		SEQUENCE  OF  RbFrequencyBandsEntry
		MAX-ACCESS	not-accessible
		STATUS		current
		DESCRIPTION	
			"A table that holds the main details of the bands in the current Frequency Bands File."
		::=  { rbNpuFrequencyBandsParameters  2 }

	rbFrequencyBandsEntry	OBJECT-TYPE
		SYNTAX		RbFrequencyBandsEntry
		MAX-ACCESS	not-accessible
		STATUS		current
		DESCRIPTION	
			"Table entry"
		INDEX		{ rbFrequencyBandId  }
		::=  { rbFrequencyBandsTable 1 }

	RbFrequencyBandsEntry  ::=  SEQUENCE {
		rbFrequencyBandId				Unsigned32,
		rbFrequencyBandName				DisplayString,
		rbFrequencyBandRevision			DisplayString,
		rbFrequencyBandGroupId			Unsigned32,
		rbFrequencyBandStartFrequency	Unsigned32,
		rbFrequencyBandStopFrequency	Unsigned32,
		rbFrequencyBandStep				Unsigned32,
		rbFrequencyBandDuplexSeparation	Integer32
		}

	rbFrequencyBandId	OBJECT-TYPE	
		SYNTAX			Unsigned32    
		MAX-ACCESS		read-only
		STATUS			current
		DESCRIPTION		
				"The ID of the Frequency Band."
		::=  {  rbFrequencyBandsEntry  1  }

	rbFrequencyBandName	OBJECT-TYPE	
		SYNTAX			DisplayString  ( SIZE ( 1 .. 32  ) ) 
		MAX-ACCESS		read-only
		STATUS			current
		DESCRIPTION		
				"The name of the Frequency Band."
		::=  {  rbFrequencyBandsEntry  2  }

	rbFrequencyBandRevision	OBJECT-TYPE	
		SYNTAX			DisplayString  ( SIZE ( 0 .. 32  ) ) 
		MAX-ACCESS		read-only
		STATUS			current
		DESCRIPTION		
				"The revision of the Frequency Band."
		::=  {  rbFrequencyBandsEntry  3  }

	rbFrequencyBandGroupId	OBJECT-TYPE	
		SYNTAX			Unsigned32    
		MAX-ACCESS		read-only
		STATUS			current
		DESCRIPTION		
				"The Group ID of the Frequency Band."
		::=  {  rbFrequencyBandsEntry  4  }

	rbFrequencyBandStartFrequency	OBJECT-TYPE	
		SYNTAX			Unsigned32    
		MAX-ACCESS		read-only
		STATUS			current
		DESCRIPTION		
				"Downlink Start Frequency [MHz]."
		::=  {  rbFrequencyBandsEntry  5  }

	rbFrequencyBandStopFrequency	OBJECT-TYPE	
		SYNTAX			Unsigned32    
		MAX-ACCESS		read-only
		STATUS			current
		DESCRIPTION		
				"Downlink Stop Frequency [MHz]."
		::=  {  rbFrequencyBandsEntry  6  }

	rbFrequencyBandStep	OBJECT-TYPE	
		SYNTAX			Unsigned32    
		MAX-ACCESS		read-only
		STATUS			current
		DESCRIPTION		
				"The Frequency resolution [MHz]."
		::=  {  rbFrequencyBandsEntry  7  }

	rbFrequencyBandDuplexSeparation	OBJECT-TYPE	
		SYNTAX			Integer32    
		MAX-ACCESS		read-only
		STATUS			current
		DESCRIPTION		
				"Duplex Frequency Separation [MHz]."
		::=  {  rbFrequencyBandsEntry  8  }


--==================================================================
--          AU Configuration Parameters
--==================================================================

	rbAuConfigTable	OBJECT-TYPE
		SYNTAX		SEQUENCE  OF  RbAuConfigEntry
		MAX-ACCESS	not-accessible
		STATUS		current
		DESCRIPTION	
			"This table provides Access Unit configuration parameters."
		::=  { rbChassisConfig  3 }

	rbAuConfigEntry	OBJECT-TYPE
		SYNTAX		RbAuConfigEntry
		MAX-ACCESS	not-accessible
		STATUS		current
		DESCRIPTION	
			"Table entry"
		INDEX		{  rbSlotNumber  }
		::=  { rbAuConfigTable 1 }

	RbAuConfigEntry  ::=  SEQUENCE {
		rbAuSerialNo  	  			DisplayString,
	    rbAuSysName  				DisplayString,
		rbAuFaultStatus				INTEGER,
		rbAuIduTemperature			Integer32,
		rbAuIduHwRevision			DisplayString,	
		rbAuOperSwFileName			DisplayString,	
		rbAuOperSwVersion			DisplayString,	
		rbAuShadowSwFileName		DisplayString,	
		rbAuShadowSwVersion			DisplayString,
		rbAuRunningSoftware			INTEGER,
		rbAuUnitControl				INTEGER,
		rbAuOperVersionValidity     INTEGER,
		rbAuShadowVersionValidity	INTEGER,
		rbAuSetDefaults				INTEGER,
		rbAuIduHwConfigDescription	DisplayString,
		rbAuOduHwConfigDescription	DisplayString,
		rbAuUpgradeSwFileName		DisplayString,
		rbAuOduHwRevision			DisplayString,
		rbAuMaxNumberOfCalls		Integer32,
		rbAuNumberOfRegisteredSUs	Integer32,
		rbAuAirInterfaceType		INTEGER,
		rbAuCumulativePowerOnTime   Unsigned32,
		rbAuBeStarvationProtectLevelCurrent	 Integer32,
		rbAuBeStarvationProtectLevelConfig	 Integer32,
		rbAuNrtStarvationProtectLevelCurrent Integer32,
		rbAuNrtStarvationProtectLevelConfig	 Integer32,
		rbAuActiveVoiceCalls		Integer32,
		rbAuSuUpgradeSwFileName     DisplayString,
		rbAuSuUpgradeSwAction       INTEGER,
		rbAuClearAllSuSwUpgradeParams	     INTEGER,
		rbAuDiversityMode 	        INTEGER
		} 

	rbAuSerialNo	OBJECT-TYPE	
		SYNTAX			DisplayString
		MAX-ACCESS		read-only
		STATUS			current
		DESCRIPTION		
				"Serial number assigned for the card during the production time."
		::=  {  rbAuConfigEntry 1  }

	rbAuSysName	OBJECT-TYPE	
		SYNTAX			DisplayString (SIZE (0..32))
		MAX-ACCESS		read-write
		STATUS			current
		DESCRIPTION		
				"Logical card ID, providing unique identification of the card.
				 Note that SysName for AU is not supported by MIB II (as well as SysLocation and SysContact)."
		::=  {  rbAuConfigEntry  2  }

	rbAuFaultStatus	OBJECT-TYPE	
		SYNTAX			INTEGER  { 
		                           noFaults ( 1 ) ,
		                           minor    ( 2 ) ,
		                           major    ( 3 ) ,
		                           critical ( 4 ) ,
								   disconnected (5)
	                         } 
		MAX-ACCESS		read-only
		STATUS			current
		DESCRIPTION		
				"The severity of the card fault. This is summarized information regarding the card
				healthiness in the slot."
		::=  {  rbAuConfigEntry  3  }

	rbAuIduTemperature	OBJECT-TYPE	
		SYNTAX			Integer32 
		MAX-ACCESS		read-only
		STATUS			current
		DESCRIPTION		
				"AU-IDU Temperature (Celsius)."
		::=  {  rbAuConfigEntry  4  }

	rbAuIduHwRevision	OBJECT-TYPE	
		SYNTAX			DisplayString
		MAX-ACCESS		read-only
		STATUS			current
		DESCRIPTION		
				"Hardware revision of the AU-IDU card."
		::=  {  rbAuConfigEntry  5  }

	rbAuOperSwFileName	OBJECT-TYPE	
		SYNTAX			DisplayString  ( SIZE ( 0 .. 80  ) ) 
		MAX-ACCESS		read-only
		STATUS			current
		DESCRIPTION		
				"Operational (Main) Software File Name."
		::=  {  rbAuConfigEntry  6  }

	rbAuOperSwVersion	OBJECT-TYPE	
		SYNTAX			DisplayString  ( SIZE ( 0..50  ) ) 
		MAX-ACCESS		read-only
		STATUS			current
		DESCRIPTION		
				"Operational (Main) Software Version."
		::=  {  rbAuConfigEntry  7  }

	rbAuShadowSwFileName	OBJECT-TYPE	
		SYNTAX			DisplayString  ( SIZE ( 0 .. 80  ) ) 
		MAX-ACCESS		read-only
		STATUS			current
		DESCRIPTION		
				"Shadow Software File Name."
		::=  {  rbAuConfigEntry  8  }

	rbAuShadowSwVersion	OBJECT-TYPE	
		SYNTAX			DisplayString  ( SIZE (0..50  ) ) 
		MAX-ACCESS		read-only
		STATUS			current
		DESCRIPTION		
				"Shadow Software Version."
		::=  {  rbAuConfigEntry 9  }

	rbAuRunningSoftware	OBJECT-TYPE	
		SYNTAX			INTEGER {
		                          operational (1),
		                          shadow (2),
								  unknown (3)
		                        }   
		MAX-ACCESS		read-only
		STATUS			current
		DESCRIPTION		
				"Current running software."
		::=  {  rbAuConfigEntry  10 }

	rbAuUnitControl	OBJECT-TYPE	
		SYNTAX			INTEGER {
		                          none (1),
								  reset (2),
								  putToShadow (3),
		                          resetAndRunFromShadow (4),
		                          makeRunningVersionOperational (5)
		                        }   
		MAX-ACCESS		read-write
		STATUS			current
		DESCRIPTION		
				"If reset (2) is selected, the AU should perform reset 
				 and resume running from the current version.
				 Reset is applicable only for an installed AU, and it does not affect the database
				 (Get will return the previously selected option).
                 putToShadow (3), resetAndRunFromShadow (4) and makeRunningVersionOperational (5)
                 are applicable also for AUs that are not installed: they define the action
                 that should take place upon installing the AU.
                 If putToShadow (3) is selected, the file specified in rbAuUpgradeSwFileName
                 will be loaded as the Shadow file (unless it already exists in the AU).
                 If resetAndRunFromShadow (4) is selected, the file specified in rbAuUpgradeSwFileName
                 will be loaded as the Shadow file (unless it already exists as the Shadow),
                 the AU should perform reset and boot from the Shadow software.
                 If the specified file already exists as the Main version, no action will take place.
                 If makeRunningVersionOperational (5) is selected, the file specified in
                 rbAuUpgradeSwFileName will be loaded as the Shadow file, the AU should perform reset
                 and boot from the Shadow software, and then swap the Main and Shadow SW Version,
                 so that the running version (which was previously the Shadow version)
                 will become the Main version, to be used after next reset.
                 If no file is specified, the AU should perform the described operations
                 using the current Shadow file."
		::=  {  rbAuConfigEntry 11 }

	rbAuOperVersionValidity	OBJECT-TYPE	
		SYNTAX			INTEGER {
		                          corrupted (1),
		                          valid     (2),
		                          unknown   (3)
								}
		MAX-ACCESS		read-only
		STATUS			current
		DESCRIPTION		
				"The validity of the Operational (Main) Software. Not supported in current version."
		::=  {  rbAuConfigEntry 12 }

	rbAuShadowVersionValidity	OBJECT-TYPE	
		SYNTAX			INTEGER {
		                          corrupted (1),
		                          valid     (2),
		                          unknown   (3)
								}
		MAX-ACCESS		read-only
		STATUS			current
		DESCRIPTION		
				"The validity of the Shadow Software. Not supported in current version."
		::=  {  rbAuConfigEntry 13 }

	rbAuSetDefaults	OBJECT-TYPE	
		SYNTAX			INTEGER  { none ( 1 ) ,
		                           factoryDefault ( 2 ) ,
		                           partialDefault ( 3 ) ,
		                           customerDefault ( 4 ) ,
		                           partialCustomerDefault ( 5 ) } 
		MAX-ACCESS		read-write
		STATUS			current
		DESCRIPTION		
				"This parameter defines the way 'Default Group' parameters are initialised
				with default values:
				1 - Default values should not be copied to the Flash Memory,
				2 - Full Factory Default configuration is copied to the Flash Memory and will be used after next reset,
				3 - Partial Factory Default is copied to the Flash Memory,
				4 - Full Customer Default is copied to the Flash Memory,
				5 - Partial Customer Default is copied to the Flash Memory
				Only Full Factory Defaults (2) is supported in the current version.
				None value (1) is available to support Get and Get Next commands. It should not be used in Set commands."
		DEFVAL			{ none }
		::=  {  rbAuConfigEntry 14 }

	rbAuIduHwConfigDescription	 OBJECT-TYPE		
		SYNTAX			DisplayString  ( SIZE (0..10  ) ) 
		MAX-ACCESS		read-only
		STATUS			current
		DESCRIPTION		
				"AU IDU Hardware configuration description"
		::=  {  rbAuConfigEntry 15  }

	rbAuOduHwConfigDescription	   OBJECT-TYPE		
		SYNTAX			DisplayString  ( SIZE (0..10  ) ) 
		MAX-ACCESS		read-only
		STATUS			current
		DESCRIPTION		
				"AU ODU Hardware configuration description.
				 Not applicable for Version 2 and higher.
				 For Version 2 it should return the value for the ODU connected to Channel 1."
		::=  {  rbAuConfigEntry 16  }
	
	rbAuUpgradeSwFileName	   OBJECT-TYPE		
		SYNTAX			DisplayString ( SIZE ( 0 .. 255  ) )   
		MAX-ACCESS		read-write
		STATUS			current
		DESCRIPTION		
				"The name of the software file that should be used to upgrade AU software"
 		::=  {  rbAuConfigEntry 17  }
	
	rbAuOduHwRevision	   OBJECT-TYPE		
		SYNTAX			DisplayString  ( SIZE (0..10  ) ) 
		MAX-ACCESS		read-only
		STATUS			current
		DESCRIPTION		
				"AU ODU Hardware revision. Not applicable for Version 2 and higher.
				 For Version 2 it should return the value for the ODU connected to Channel 1."
		::=  {  rbAuConfigEntry 18  }

	rbAuMaxNumberOfCalls	   OBJECT-TYPE		
		SYNTAX			Integer32 (0..300)
		MAX-ACCESS		read-write
		STATUS			current
		DESCRIPTION		
				"The maximum number of voice calls supported by AU."
		::=  {  rbAuConfigEntry 19  }

	rbAuNumberOfRegisteredSUs	   OBJECT-TYPE		
		SYNTAX			Integer32
		MAX-ACCESS		read-only
		STATUS			current
		DESCRIPTION		
				"The number of registered SUs currently connected to this AU."
		::=  {  rbAuConfigEntry 20  }

	rbAuAirInterfaceType	OBJECT-TYPE	
		SYNTAX			INTEGER {
								  unknown (0),
		                          typeA  (1),
		                          typeSi (2)
		                        }    
		MAX-ACCESS		read-only
		STATUS			current
		DESCRIPTION		
				"AU Operation Mode.
				 typeA (1) - Standard Operation Mode, typeSi (2) - Advance Si Operation Mode."
		::=  {  rbAuConfigEntry 21  }

	rbAuCumulativePowerOnTime		OBJECT-TYPE	
		SYNTAX			Unsigned32
		MAX-ACCESS		read-only
		STATUS			current
		DESCRIPTION		
				"Cumulative Power On Time (minutes).
				 Agent will return 0 if Cumulative Power On Time is unknown." 
		::=  {  rbAuConfigEntry  22  }

	rbAuBeStarvationProtectLevelCurrent	   OBJECT-TYPE		
		SYNTAX			Integer32 (0..250)
		MAX-ACCESS		read-only
		STATUS			deprecated
		DESCRIPTION		
				"Not supported in current version.
				 The Starvation Protection Level in Kbps for Best Effort connections.
				 The system will maintain the throughput of all BE connections at 
				 least to this level (or to the MIR value if lower than this level),
				 even at the expense of degrading QoS to classes of service of higher priority.
				 The AU will distribute the parameter to all SUs in the sector."
		::=  {  rbAuConfigEntry  23  }

	rbAuBeStarvationProtectLevelConfig	   OBJECT-TYPE		
		SYNTAX			Integer32 (0..250)
		MAX-ACCESS		read-write
		STATUS			deprecated
		DESCRIPTION		
				"Not supported in current version.
				 The configured Starvation Protection Level in Kbps for Best Effort connections.
				 Will take effect (become current) after next reset."
		::=  {  rbAuConfigEntry  24  }

	rbAuNrtStarvationProtectLevelCurrent	   OBJECT-TYPE		
		SYNTAX			Integer32 (0..100)
		MAX-ACCESS		read-only
		STATUS			deprecated
		DESCRIPTION		
				"Not supported in current version.
				 The Starvation Protection Level in Kbps for Non Real Time connections.
				 The system will maintain the throughput of all NRT connections at 
				 least to this level (or to the CIR value if lower than this level),
				 even at the expense of degrading QoS to classes of service of higher priority.
				 The AU will distribute the parameter to all SUs in the sector."
		::=  {  rbAuConfigEntry 25  }

	rbAuNrtStarvationProtectLevelConfig	   OBJECT-TYPE	  	
		SYNTAX			Integer32 (0..100)
		MAX-ACCESS		read-write
		STATUS			deprecated
		DESCRIPTION		
				"Not supported in current version.
				 The configured Starvation Protection Level in Kbps for Best Effort connections.
				 Will take effect (become current) after next reset."
		::=  {  rbAuConfigEntry 26  }

	rbAuActiveVoiceCalls	   OBJECT-TYPE	
		SYNTAX			Integer32 (0..300)
		MAX-ACCESS		read-only
		STATUS			current
		DESCRIPTION		
				"The number of active voice calls in the sector.
				 Actual range is from 0 to the value defined by rbAuMaxNumberOfCalls."
		::=  {  rbAuConfigEntry 27  }

	rbAuSuUpgradeSwFileName	   OBJECT-TYPE		
		SYNTAX			DisplayString ( SIZE ( 0 .. 255  ) )   
		MAX-ACCESS		read-write
		STATUS			current
		DESCRIPTION		
				"The name of the software file that should be used to upgrade SU software upon network entry
				 for all SUs in this sector. Not applicable for any SU whose rbSuUpgradeSwFileName is not empty."
 		::=  {  rbAuConfigEntry 28  }

	rbAuSuUpgradeSwAction	OBJECT-TYPE	
		SYNTAX			INTEGER
		                {
						  none (1),
						  putToShadow (3),
						  runFromShadow (4),
						  makeShadowOperational(5)
						}
		MAX-ACCESS		read-write
		STATUS			current
		DESCRIPTION		
				"The Action that should be performed by SUs in this sector upon
				 the Network Entry. Action should be performed using the rbAuSuUpgradeSwFileName.
				 Not applicable for any SU whose rbSuUnitControl is other than none (1)."
		::=  {  rbAuConfigEntry 29 }

	rbAuClearAllSuSwUpgradeParams	OBJECT-TYPE	
		SYNTAX			INTEGER  { none ( 1 ), clearAllSuSwUpgradeParams ( 2 ) } 
		MAX-ACCESS		read-write
		STATUS			current
		DESCRIPTION		
				"Clears the SW Upgrade parameters for all SUs in the sector:
				 For all SUs, rbSuUpgradeSwFileName will be set to an empty string,
				 and rbSuUnitControl will be set to none (1).
				 none (1) value is available to support Get and Get Next commands.
				 It should not be used in Set commands."
		::=  {  rbAuConfigEntry 30  }

	rbAuDiversityMode	OBJECT-TYPE	
		SYNTAX			INTEGER  { noDiversity         ( 1 ),
								   secondOrder         ( 2 ),
								   fourthOrder         ( 3 )
					    } 
		MAX-ACCESS		read-write
		STATUS			current
		DESCRIPTION		
				"The diversity mode used by the AU:
                 noDiversity (1): No diversity (multi-channels).
                 secondOrder (2): Second order diversity using channels 1 and 2.
                 fourthOrder (3): Fourth order diversity, using all 4 channels.
				 Change of this variable will cause the AU reset."
		::=  {  rbAuConfigEntry 31  }


-- =================================================================================
--          ACU Configuration   
-- =================================================================================
   rbAcuConfiguration		   OBJECT IDENTIFIER 	::=  {rbChassisConfig  6	}

   rbAcuOperStatus	OBJECT-TYPE	
		SYNTAX			INTEGER 
		                {
		                  ok (1),
		                  failed (2),
		                  notInstalled (3)
		                }     
		MAX-ACCESS		read-only
		STATUS			current
		DESCRIPTION		
				"Air Ventilation Unit operational status."
		::=  {  rbAcuConfiguration  1  }

   rbAcuFaultStatus	OBJECT-TYPE	
		SYNTAX			OCTET STRING (SIZE (10)) 
		MAX-ACCESS		read-only
		STATUS			current
		DESCRIPTION		
				"Air Ventilation Unit fault status : each octet is representing
				 one of 10 AVU fans: 
				 1 - unit is OK,
				 2 - unit failed,
				 3 - unit is not installed "
		::=  {  rbAcuConfiguration  2  }

   rbAcuLedStatus	OBJECT-TYPE	
		SYNTAX			OCTET STRING 
		MAX-ACCESS		read-only
		STATUS			current
		DESCRIPTION		
				"Air Ventilation Unit Leds Status:
				 Each byte represents the single Led.
				 Within each byte, bits 0-3 are the color, 4-7 are the blink rate.
				 Supported color codes:
				 0000 : Black (LED is off)
				 0001 : Green
				 0010 : Yellow
				 0011 : Red
				 0100 : Blue
				 Supported blink rates:
				 0000 : no blink
				 0001 : blink
                 The order of bytes is as following :
				 FAN, Power "
		::=  {  rbAcuConfiguration  3 }


-- =================================================================================
--          PSU Configuration Table  
-- =================================================================================
	rbPsuConfigTable	OBJECT-TYPE
		SYNTAX		SEQUENCE  OF  RbPsuConfigEntry
		MAX-ACCESS	not-accessible
		STATUS		current
		DESCRIPTION	
			"This table provides Power Supply Unit configuration parameters"
		::=  { rbChassisConfig  7 }

	rbPsuConfigEntry	OBJECT-TYPE
		SYNTAX		RbPsuConfigEntry
		MAX-ACCESS	not-accessible
		STATUS		current
		DESCRIPTION	
			"Table entry"
		INDEX		{  rbPsuNumber  }
		::=  { rbPsuConfigTable 1 }

	RbPsuConfigEntry  ::=  SEQUENCE {
		rbPsuNumber  	  	Integer32,
	    rbPsuStatus  		INTEGER
		}


	rbPsuNumber	OBJECT-TYPE	
		SYNTAX			Integer32  ( 1 .. 4  ) 
		MAX-ACCESS		read-only
		STATUS			current
		DESCRIPTION		
				"Physical placement of the PSU."
		::=  {  rbPsuConfigEntry  1  }

	rbPsuStatus	OBJECT-TYPE	
		SYNTAX			INTEGER {
		                          ok    (1),
		                          fault (2),
								  notInstalled (3)
		                        }    
		MAX-ACCESS		read-only
		STATUS			current
		DESCRIPTION		
				"PSU fault status."
		::=  {  rbPsuConfigEntry 2  }


-- =================================================================================
--          PIU Configuration Table  
-- =================================================================================

	rbPiuConfigTable	OBJECT-TYPE
		SYNTAX		SEQUENCE  OF  RbPiuConfigEntry
		MAX-ACCESS	not-accessible
		STATUS		current
		DESCRIPTION	
			"This table provides Power Interface Unit configuration parameters."
		::=  { rbChassisConfig  8 }

	rbPiuConfigEntry	OBJECT-TYPE
		SYNTAX		RbPiuConfigEntry
		MAX-ACCESS	not-accessible
		STATUS		current
		DESCRIPTION	
			"Table entry"
		INDEX		{  rbPiuNumber  }
		::=  { rbPiuConfigTable 1 }

	RbPiuConfigEntry  ::=  SEQUENCE {
		rbPiuNumber  	  	Integer32,
	    rbPiuStatus  		INTEGER,
	    rbPiuMode  		    INTEGER
		}


	rbPiuNumber	OBJECT-TYPE	
		SYNTAX			Integer32  ( 1 .. 2  ) 
		MAX-ACCESS		read-only
		STATUS			current
		DESCRIPTION		
				"Physical placement of the PIU."
		::=  {  rbPiuConfigEntry  1  }

	rbPiuStatus	OBJECT-TYPE	
		SYNTAX			INTEGER {
		                          ok    (1),
		                          fault (2),
								  unknown (3)
		                        }    
		MAX-ACCESS		read-only
		STATUS			current
		DESCRIPTION		
				"PIU fault status."
		::=  {  rbPiuConfigEntry 2  }

	rbPiuMode	OBJECT-TYPE	
		SYNTAX			INTEGER {
		                          master       (1),
		                          redundant    (2),
								  notInstalled (3)
		                        }    
		MAX-ACCESS		read-only
		STATUS			current
		DESCRIPTION		
				"PIU mode."
		::=  {  rbPiuConfigEntry 3  }


-- =================================================================================
--          AU Hardware Components Info Table  
-- =================================================================================
	rbAuHwComponentsInfoTable	OBJECT-TYPE
		SYNTAX		SEQUENCE  OF  RbAuHwComponentsInfoEntry
		MAX-ACCESS	not-accessible
		STATUS		current
		DESCRIPTION	
			"This table provides parameters information regarding the AU Hardware components."
		::=  { rbChassisConfig  9 }

	rbAuHwComponentsInfoEntry 	OBJECT-TYPE
		SYNTAX		RbAuHwComponentsInfoEntry
		MAX-ACCESS	not-accessible
		STATUS		current
		DESCRIPTION	
			"Table entry"
		INDEX		{  rbSlotNumber  }
		::=  { rbAuHwComponentsInfoTable 1 }

	RbAuHwComponentsInfoEntry  ::=  SEQUENCE {
		rbAuIduIfCardRevision   	DisplayString,
		rbAuIduIfCardConfiguration	DisplayString,
		rbAuIduBootVersion			DisplayString,
		rbAuOduHC08Version  		DisplayString,
		rbAuOduCpldVersion  		DisplayString,
		rbAuOduCardSerialNumber     DisplayString,
		rbAuIduType  		        INTEGER
		}


	rbAuIduIfCardRevision	OBJECT-TYPE	
		SYNTAX			DisplayString 
		MAX-ACCESS		read-only
		STATUS			current
		DESCRIPTION		
				"AU-IDU IF Card Revision."
		::=  {  rbAuHwComponentsInfoEntry  1  }

	rbAuIduIfCardConfiguration	OBJECT-TYPE	
		SYNTAX			DisplayString 
		MAX-ACCESS		read-only
		STATUS			current
		DESCRIPTION		
				"AU-IDU IF Card Configuration description."
		::=  {  rbAuHwComponentsInfoEntry  2  }

	rbAuIduBootVersion	OBJECT-TYPE	
		SYNTAX			DisplayString 
		MAX-ACCESS		read-only
		STATUS			current
		DESCRIPTION		
				"AU-IDU Boot Version."
		::=  {  rbAuHwComponentsInfoEntry  3  }

	rbAuOduHC08Version	OBJECT-TYPE	
		SYNTAX			DisplayString 
		MAX-ACCESS		read-only
		STATUS			current
		DESCRIPTION		
				"AU ODU HC08 Version. Not applicable for Version 2 and higher.
				 For Version 2 it should return the value for the ODU connected to Channel 1."
		::=  {  rbAuHwComponentsInfoEntry 4  }

	rbAuOduCpldVersion	OBJECT-TYPE	
		SYNTAX			DisplayString 
		MAX-ACCESS		read-only
		STATUS			current
		DESCRIPTION		
				"AU ODU Cpld Version. Not applicable for Version 2 and higher.
				 For Version 2 it should return the value for the ODU connected to Channel 1."
		::=  {  rbAuHwComponentsInfoEntry 5  }
	
	rbAuOduCardSerialNumber	OBJECT-TYPE	
		SYNTAX			DisplayString 
		MAX-ACCESS		read-only
		STATUS			current
		DESCRIPTION		
				"AU ODU serial number. Not applicable for Version 2 and higher.
				 For Version 2 it should return the value for the ODU connected to Channel 1."
		::=  {  rbAuHwComponentsInfoEntry 6  }

	rbAuIduType	OBJECT-TYPE	
		SYNTAX			INTEGER {
                                          unknown         (0),
		                          twoChannels     (1),
		                          fourChannels    (2),
		                          twoChannels-HP  (3),
		                          fourChannels-HP (4)
		                        }    
		MAX-ACCESS		read-only
		STATUS			current
		DESCRIPTION		
				"AU-IDU Type. fourChannels and twoChannels-HP are not applicable in the current version."
		::=  {  rbAuHwComponentsInfoEntry 7  }


--==================================================================
--          Channel Configuration Parameters
--==================================================================

	rbChannelConfigTable	OBJECT-TYPE
		SYNTAX		SEQUENCE  OF  RbChannelConfigEntry
		MAX-ACCESS	not-accessible
		STATUS		current
		DESCRIPTION	
			"This table provides Channel configuration parameters. 
			 This is a static Table. Only Update allowed."
		::=  { rbChassisConfig  11 }

	rbChannelConfigEntry	OBJECT-TYPE
		SYNTAX		RbChannelConfigEntry
		MAX-ACCESS	not-accessible
		STATUS		current
		DESCRIPTION	
			"Table entry"
		INDEX		{  rbSlotNumber, rbChannelId  }
		::=  { rbChannelConfigTable 1 }

	RbChannelConfigEntry  ::=  SEQUENCE {
		rbChannelId                       Integer32,
		rbChannelAssociatedRadioClusterId Integer32,
		rbChannelAssociatedOduId          Integer32,
		rbChannelTxFrequency              DisplayString,
		rbChannelRxFrequency              DisplayString,
		rbChannelAdminStatus              INTEGER,
		rbChannelConfiguredTxFrequency    DisplayString,
		rbChannelOduActualFrequencyBand   Integer32,	  	
		rbChannelOperStatus               INTEGER
		}

	rbChannelId	   OBJECT-TYPE		
		SYNTAX			Integer32 ( 1 .. 4 )
		MAX-ACCESS		read-only
		STATUS			current
		DESCRIPTION		
				"Channel ID. For two-channels AU-IDU only Channel ID 1-2 are supported."
		::=  {  rbChannelConfigEntry 1  }

	rbChannelAssociatedRadioClusterId	   OBJECT-TYPE		
		SYNTAX			Integer32 ( 0 .. 6 )
		MAX-ACCESS		read-only
		STATUS			current
		DESCRIPTION		
				"Channel Associated Radio Cluster ID, as defined in the Associated ODU.
				 Agent will return 0 if Associated Radio Cluster ID is unknown."
		::=  {  rbChannelConfigEntry 2  }

	rbChannelAssociatedOduId	   OBJECT-TYPE		
		SYNTAX			Integer32 ( 0 .. 24 )
		MAX-ACCESS		read-write
		STATUS			current
		DESCRIPTION		
				"Channel Associated ODU ID. Valid values: 1 to 24 or 0 to disassociate.
				 Agent will return 0 if Associated ODU ID is unknown."
		::=  {  rbChannelConfigEntry 3  }

	rbChannelTxFrequency	OBJECT-TYPE	
		SYNTAX			DisplayString 
		MAX-ACCESS		read-only
		STATUS			current
		DESCRIPTION		
				"The current Channel Tx Frequency (MHz).
				 Agent will return 0 if Tx Frequency is unknown."
		::=  {  rbChannelConfigEntry  4  }

	rbChannelRxFrequency	OBJECT-TYPE	
		SYNTAX			DisplayString 
		MAX-ACCESS		read-only
		STATUS			current
		DESCRIPTION		
				"Channel Rx Frequency (MHz). Calculated from the Tx Frequency according to
				 the parameters of the Configured Frequency Band in the Associated ODU.
				 Agent will return 0 if Rx Frequency is unknown."
		::=  {  rbChannelConfigEntry  5  }

	rbChannelAdminStatus	OBJECT-TYPE	
		SYNTAX			INTEGER  { unknown ( 0 ), enable ( 1 ) , disable ( 2 ) } 
		MAX-ACCESS		read-write
		STATUS			current
		DESCRIPTION		
				"Channel Administrative Status.	Valid values: 1 to 2
				 Agent will return 0 if Admin Status is unknown.
				 For AUs using diversity (rbAuDiversityMode other than noDiversity), 
				 this parameter is read-write only for Channel 1.
				 The status for other relevant channels (channel 2 for secondOrderDiversity,
				 channels 2 to 4 for fourthOrderDiversity) is read-only, and is configured automatically
				 to the same value configured for channel 1."
		::=  {  rbChannelConfigEntry  6  }

	rbChannelConfiguredTxFrequency	OBJECT-TYPE	
		SYNTAX			DisplayString 
		MAX-ACCESS		read-write
		STATUS			current
		DESCRIPTION		
				"The configured Channel Tx Frequency (MHz).
				 Available values depend on Bandwidth and parameters of the Configured
				 Frequency Band in the Associated ODU.
				 For AUs that do not use diversity (rbAuDiversityMode is set to noDiversity),
				 if the Tx Frequency of one Channel is already configured,
				 the available values depend on the Bandwidth,
				 on the Tx Frequency defined for the already configured Channel,
				 and on the Frequency Bands included in the applicable Frequency Bands Group.
				 For AUs using diversity (rbAuDiversityMode other than noDiversity),
				 this value is configurable only for channel 1.
				 The Tx Frequency of other relevant channels (channel 2 for secondOrderDiversity,
				 channels 2 to 4 for fourthOrderDiversity) will be configured automatically to the value
				 configured for channel 1.
				 Will be applied after reset."
		::=  {  rbChannelConfigEntry  7  }

	rbChannelOduActualFrequencyBand	OBJECT-TYPE	
		SYNTAX			Integer32 
		MAX-ACCESS		read-only
		STATUS			current
		DESCRIPTION		
				"Odu Actual Frequency Band ID.
				 Must be one of the Frequency Band IDs available in the Frequency Bands Table.
				 Agent will return 0 if Frequency Band is unknown."
		::=  {  rbChannelConfigEntry  8  }

	rbChannelOperStatus	OBJECT-TYPE	
		SYNTAX			INTEGER  { unknown ( 0 ), up ( 1 ) , down ( 2 ) } 
		MAX-ACCESS		read-only
		STATUS			current
		DESCRIPTION		
				"Channel Operational Status.
				 Agent will return 0 if Oper Status is unknown."
		::=  {  rbChannelConfigEntry  9  }


--==================================================================
--          Subscriber Unit Configuration   
--==================================================================
    rbSubcriberUnitConfig	   OBJECT IDENTIFIER ::=  {  rainbow  5  }
--	rbRegisteredSuTable		   OBJECT IDENTIFIER ::=  {  rbSubcriberUnitConfig  1  }
--  rbSuSubDevicesTable        OBJECT IDENTIFIER ::=  {  rbSubcriberUnitConfig  2  }
--  rbSuHwComponentsInfoTable  OBJECT IDENTIFIER ::=  {  rbSubcriberUnitConfig  3  }
--  suBridgingParameters       OBJECT IDENTIFIER ::=  {  rbSubcriberUnitConfig  4  }
--  rbMACBehindSUList          OBJECT IDENTIFIER ::=  {  rbSubcriberUnitConfig  5  }
--  rbSiSuInfo                 OBJECT IDENTIFIER ::=  {  rbSubcriberUnitConfig  6  }
--  rbSuLicenses               OBJECT IDENTIFIER ::=  {  rbSubcriberUnitConfig  7  }


--==================================================================
--          SU General Configuration Parameters  
--==================================================================

--========================================================================
--     Registered SU table
--     Contains all SUs defined in the system 
--========================================================================
	rbRegisteredSuTable	OBJECT-TYPE
		SYNTAX		SEQUENCE  OF  RbRegisteredSuEntry
		MAX-ACCESS	not-accessible
		STATUS		current
		DESCRIPTION	
			"This table contains information on SUs registered in the system.
			 It includes also SUs that are defined but are not registered currently.
			 It can also be used to define new SUs."
		::=  { rbSubcriberUnitConfig  1 }

	rbRegisteredSuEntry	OBJECT-TYPE
		SYNTAX		RbRegisteredSuEntry
		MAX-ACCESS	not-accessible
		STATUS		current
		DESCRIPTION	
			"Table entry"
		INDEX		{ rbSuMacAddr }
		::=  { rbRegisteredSuTable 1 }

	RbRegisteredSuEntry  ::=  SEQUENCE {
		rbAuId			  			Integer32,
		rbSuMacAddr  		  		MacAddress,
		rbSuID               		Integer32,
		rbSuRegistrationState		INTEGER,
		rbSuPersistence				INTEGER,
 		rbSuSerialNo  	  			DisplayString,
	    rbSuSysName  				DisplayString,
		rbSuFaultStatus				INTEGER,
		rbSuHwRevision				DisplayString,	
		rbSuOperSwFileName			DisplayString,	
		rbSuOperSwVersion			DisplayString,	
		rbSuShadowSwFileName		DisplayString,	
		rbSuShadowSwVersion			DisplayString,
		rbSuRunningSoftware			INTEGER,
		rbSuOperVersionValidity		INTEGER,
		rbSuShadowVersionValidity	INTEGER, 
		rbSuUnitControl				INTEGER,
		rbSuSetDefaults				INTEGER,
		rbSuAllowedUsersType		INTEGER,
		rbSuAllowedQoS				INTEGER,
		rbSuAllowedService			OCTET STRING,
		rbSuRowStatus       		RowStatus,
		rbSuInstallerPassword		DisplayString,
		rbSuHwConfigDescription     DisplayString,
		rbSuUpgradeSwFileName		DisplayString,
		rbSuServiceType				INTEGER,
		rbSuIduType					INTEGER,
		rbSuExternalDevNumber       Integer32,
		rbSuServiceFaultBitMap		OCTET STRING,
		rbSuCumulativePowerOnTime   Unsigned32,
		rbSuOrganizationName        DisplayString,
		rbSuAddress                 DisplayString,
		rbSuCountry                 DisplayString,
		rbSuMACControlNumber        Integer32,
		rbSuAirInterfaceType        INTEGER
 	}

	rbAuId	OBJECT-TYPE	
		SYNTAX			Integer32
		MAX-ACCESS		read-only
		STATUS			current
		DESCRIPTION		
				"The slot number of the AU to which the SU is connected.
				 For a Micro Base Station AU ID is 1.
				 If the SU is still not registered - AU ID is 255." 
		::=  {  rbRegisteredSuEntry  1  }

	rbSuMacAddr	OBJECT-TYPE	
		SYNTAX			MacAddress
		MAX-ACCESS		read-only
		STATUS			current
		DESCRIPTION		
				"The MAC address of the SU.
				 For registered SUs this parameter is read-only.
				 The MAC address is read-write for SUs that are not registered,
				 enabling pre-definition of new SUs." 
		::=  {  rbRegisteredSuEntry  2  }

	rbSuID	OBJECT-TYPE	
		SYNTAX			Integer32
		MAX-ACCESS		read-only
		STATUS			current
		DESCRIPTION		
				"SU ID. An index assigned by the serving device." 
		::=  {  rbRegisteredSuEntry  3  }

	rbSuRegistrationState	OBJECT-TYPE	
		SYNTAX			INTEGER {
		                          notRegistered (1),
								  registered    (2),
								  authenticated (3)
								}
		MAX-ACCESS		read-only
		STATUS			current
		DESCRIPTION		
				"The registration state of the SU." 
		::=  {  rbRegisteredSuEntry  4  }

    rbSuPersistence	OBJECT-TYPE	
		SYNTAX			INTEGER {
		                          temporary  (1),
								  permanent (2)
								}
		MAX-ACCESS		read-write
		STATUS			current
		DESCRIPTION		
				"The permanence status of the SU.
				 A new SU that becomes registered at the Device, is automatically added to 
				 the database with a Temporary status. If the Device uses Advanced (professional)
				 Service Working Mode, and the SU uses Standard Operation Mode (Air Interface type a),
				 then as long as the status remains Temporary the Subscriber(s) behind the SUs
				 will not get any service. If the SU uses Advanced Si Operation Mode (Air Interface type si),
				 it will be authenticated and provisioned with Service(s) by the RADIUS server.
				 If the Device uses Quick (lightMode) Service Working Mode,
				 then Subscribers behind a Temporary SU using Standard Operation Mode (Air Interface type a)
				 will get Services based on	the defined Default Service Template(s).
				 Subscribers behind an SU that uses Advanced Si Operation Mode (Air Interface type si)
				 will get Services based on the defined Default Service Template(s)
				 only if the configured SU's Password is either quickynikynyoky or blank.
				 A Temporary SU will be deleted from the database if it will be disconnected." 
		::=  {  rbRegisteredSuEntry  5  }

	rbSuSerialNo	OBJECT-TYPE	
		SYNTAX			DisplayString
		MAX-ACCESS		read-only
		STATUS			current
		DESCRIPTION		
				"Serial number assigned for the SU during the production time."
		::=  {  rbRegisteredSuEntry 6  }

	rbSuSysName	OBJECT-TYPE	
		SYNTAX			DisplayString (SIZE (0..32))
		MAX-ACCESS		read-write
		STATUS			current
		DESCRIPTION		
				"The SU's name. User Name in SUs using Advanced Si Operation Mode (Air Interface type Si)).
				 Configurable (write) only for SUs running SW version 2.0 or higher and using Standard Operation Mode (Air Interface type A).
				 Note that SysName for SU is not supported by MIB II (as well as SysLocation and SysContact)."
		::=  {  rbRegisteredSuEntry  7  }

	rbSuFaultStatus	OBJECT-TYPE	
		SYNTAX			INTEGER  { 
		                           noFaults ( 1 ) ,
		                           minor    ( 2 ) ,
		                           major    ( 3 ) ,
		                           critical ( 4 ) ,
								   disconnected (5)
		                         } 
		MAX-ACCESS		read-only
		STATUS			current
		DESCRIPTION		
				"The severity of the SU's fault.
				 This is summarized information regarding the unit's healthiness."
		::=  {  rbRegisteredSuEntry  8  }

	rbSuHwRevision	OBJECT-TYPE	
		SYNTAX			DisplayString
		MAX-ACCESS		read-only
		STATUS			current
		DESCRIPTION		
				"Hardware version of the SU's Main card."
		::=  {  rbRegisteredSuEntry  9  }

	rbSuOperSwFileName	OBJECT-TYPE	
		SYNTAX			DisplayString  ( SIZE ( 0 .. 80  ) ) 
		MAX-ACCESS		read-only
		STATUS			current
		DESCRIPTION		
				"Operational (Main) Software File Name."
		::=  {  rbRegisteredSuEntry  10  }

	rbSuOperSwVersion	OBJECT-TYPE	
		SYNTAX			DisplayString  ( SIZE ( 0..50  ) ) 
		MAX-ACCESS		read-only
		STATUS			current
		DESCRIPTION		
				"Operational (Main) Software Version."
		::=  {  rbRegisteredSuEntry  11  }

	rbSuShadowSwFileName	OBJECT-TYPE	
		SYNTAX			DisplayString  ( SIZE ( 0 .. 80  ) ) 
		MAX-ACCESS		read-only
		STATUS			current
		DESCRIPTION		
				"Shadow Software File name."
		::=  {  rbRegisteredSuEntry  12  }

	rbSuShadowSwVersion	OBJECT-TYPE	
		SYNTAX			DisplayString  ( SIZE (0..50  ) ) 
		MAX-ACCESS		read-only
		STATUS			current
		DESCRIPTION		
				"Shadow Software Version."
		::=  {  rbRegisteredSuEntry 13  }

	rbSuRunningSoftware	OBJECT-TYPE	
		SYNTAX			INTEGER {
		                          operational (1),
		                          shadow (2),
								  unknown (3)
		                        }   
		MAX-ACCESS		read-only
		STATUS			current
		DESCRIPTION		
				"Current running software."
		::=  {  rbRegisteredSuEntry  14 }

	rbSuOperVersionValidity	OBJECT-TYPE	
		SYNTAX			INTEGER {
		                          corrupted (1),
		                          valid     (2),
		                          unknown   (3)
								}
		MAX-ACCESS		read-only
		STATUS			current
		DESCRIPTION		
				"The validity of the Operational (Main) Software."
		::=  {  rbRegisteredSuEntry 15 }

	rbSuShadowVersionValidity	OBJECT-TYPE	
		SYNTAX			INTEGER {
		                          corrupted (1),
		                          valid     (2),
		                          unknown   (3)
								}
		MAX-ACCESS		read-only
		STATUS			current
		DESCRIPTION		
				"The validity of the Shadow Software. Not supported in current version."
		::=  {  rbRegisteredSuEntry 16 }

	rbSuUnitControl	OBJECT-TYPE	
		SYNTAX			INTEGER {
		                          none (1),
								  reset (2),
								  putToShadow (3),
		                          resetAndRunFromShadow (4),
		                          makeRunningVersionOperational (5)
		                        }   
		MAX-ACCESS		read-write
		STATUS			current
		DESCRIPTION		
				"If reset (2) is selected, the SU should perform reset
				 and resume running from the current version.
				 Reset is applicable only for a connected SU, and it does not affect the database
				 (Get will return the previously selected option).
                 putToShadow (3), resetAndRunFromShadow (4) and makeRunningVersionOperational (5)
                 are applicable also for SUs that are not connected: they define the action
                 that should take place upon network entry of the SU.
                 If putToShadow (3) is selected, the file specified in rbSuUpgradeSwFileName
                 will be loaded as the Shadow file (unless it already exists in the SU). 
                 If resetAndRunFromShadow (4) is selected, the file specified in rbSuUpgradeSwFileName
                 will be loaded as the Shadow file (unless it already exists as the Shadow),
                 the SU should perform reset and boot from the Shadow software.
                 If the specified file already exists as the Main version, no action will take place.
                 If makeRunningVersionOperational (5) is selected, the file specified in
                 rbSuUpgradeSwFileName will be loaded as the Shadow file, the SU should perform reset
                 and boot from the Shadow software, and then swap the Main and Shadow SW Version,
                 so that the running version (which was previously the Shadow version)
                 will become the Main version, to be used after next reset.
                 If no file is specified, the SU should perform the described operations
                 using the current Shadow file."
		::=  {  rbRegisteredSuEntry 17 }

	rbSuSetDefaults	OBJECT-TYPE	
		SYNTAX			INTEGER  { none ( 1 ) ,
		                           factoryDefault ( 2 ) ,
		                           partialDefault ( 3 ) ,
		                           customerDefault ( 4 ) ,
		                           partialCustomerDefault ( 5 ) } 
		MAX-ACCESS		read-write
		STATUS			current
		DESCRIPTION		
				"This parameter defines the way 'Default Group' parameters are initialised
				with default values:
				1 - Default values should not be copied to the Flash Memory,
				2 - Full Factory Default configuration is copied to the Flash Memory and will be used after next reset,
				3 - Partial Factory Default is copied to the Flash Memory,
				4 - Full Customer Default is copied to the Flash Memory,
				5 - Partial Customer Default is copied to the Flash Memory
				Only Full Factory Defaults (2) is supported in the current version.
				None value (1) is available to support Get and Get Next commands. It should not be used in Set commands."
		DEFVAL			{ none }
		::=  {  rbRegisteredSuEntry 18 }

	rbSuAllowedUsersType	OBJECT-TYPE	
		SYNTAX			INTEGER  { 
								   residentional ( 1 ) ,
		                           unknown		 ( 2 ) 
								 }
 		MAX-ACCESS		read-write
		STATUS			deprecated
		DESCRIPTION		
				"Not supported in current version."
		::=  {  rbRegisteredSuEntry 19 }

	rbSuAllowedQoS	OBJECT-TYPE	
		SYNTAX			INTEGER  { 
								   residentional ( 1 ) ,
		                           unknown		 ( 2 ) 
								 }
 		MAX-ACCESS		read-write
		STATUS			deprecated
		DESCRIPTION		
				"Not supported in current version."
		::=  {  rbRegisteredSuEntry 20 }

	rbSuAllowedService	OBJECT-TYPE	
		SYNTAX			OCTET STRING			
		MAX-ACCESS		read-write
		STATUS			deprecated
		DESCRIPTION		
				"Not supported in current version."
		::=  {  rbRegisteredSuEntry 21 }

	rbSuRowStatus	OBJECT-TYPE	
		SYNTAX			RowStatus
		MAX-ACCESS		read-write
		STATUS			current
		DESCRIPTION		
				"Control for creating and deleting entries.  Entries may be modified while active.
                 active (1) - means that the entry is available for use by the managed device and
                 relevant parameters may be modified;
                 createAndGo (4) is used for creating a new entry and to have its status
                 automatically set to active.
                 destroy (6) is used for deleting an existing entry." 
		::=  {  rbRegisteredSuEntry  22  }

  	rbSuInstallerPassword	 OBJECT-TYPE		
		SYNTAX			DisplayString  ( SIZE (0..20  ) ) 
		MAX-ACCESS		read-write
		STATUS			current
		DESCRIPTION		
				"The password that should be used when accessing the SU's Monitor program
				 using Telnet via its Ethernet port."
		::=  {  rbRegisteredSuEntry 23  }

	rbSuHwConfigDescription	   OBJECT-TYPE		
		SYNTAX			DisplayString  ( SIZE (0..10  ) ) 
		MAX-ACCESS		read-only
		STATUS			current
		DESCRIPTION		
				"The Hardware configuration description of the SU's Main card."
		::=  {  rbRegisteredSuEntry 24  }

	rbSuUpgradeSwFileName	   OBJECT-TYPE		
		SYNTAX			DisplayString  ( SIZE ( 0 .. 255  ) ) 
		MAX-ACCESS		read-write
		STATUS			current
		DESCRIPTION		
				"The name of the software file that should be used to upgrade SU software."
 		::=  {  rbRegisteredSuEntry 25  }

	rbSuServiceType	   OBJECT-TYPE		
		SYNTAX			INTEGER 
		                { 
		                  suData (1),
						  suVoice(2)
						}
		MAX-ACCESS		read-write
		STATUS			deprecated
		DESCRIPTION		
				"Not supported in current version."
 		::=  {  rbRegisteredSuEntry 26  }

	rbSuIduType	   OBJECT-TYPE		
		SYNTAX			INTEGER 
		                { 
		                  basic (0),
						  vgData4Voice2 (6),
						  ngData4Wireless (11)
						}
		MAX-ACCESS		read-only
		STATUS			current
		DESCRIPTION		
				"The type of SU IDU. In current version only basic (0) and ngData4Wireless (11) are supported."
 		::=  {  rbRegisteredSuEntry 27  }

	rbSuExternalDevNumber	   OBJECT-TYPE		
		SYNTAX			Integer32 
		MAX-ACCESS		read-only
		STATUS			current
		DESCRIPTION		
				"The number of gateways (including ngData4Wireless IDU) connected to SU.
				 This includes only devices that support the DRAP protocol for registration
				 at the Base Station/Micro Base Station."
 		::=  {  rbRegisteredSuEntry 28  }

	rbSuServiceFaultBitMap	OBJECT-TYPE	
		SYNTAX			OCTET STRING  ( SIZE ( 4 ) ) 
		MAX-ACCESS		read-only
		STATUS			current
		DESCRIPTION		
				"The reason for denying services to the SU.  
				 Bit 1: Loop problem. A loop was detected on the Ethernet side of the SU.
				 rbNetworkingError Trap will be sent, and services to this SU will be denied
				 until resetting the SU from the network (NPU) side
				 (provided the problem does not exist any more)
				 Bit 2: Duplicate SU Name. The SU Name is already in use by another SU.
				 rbSuDuplicateName Trap will be sent and services to the SU will be denied
				 until another, unique name is configured for the SU."
		::=  {  rbRegisteredSuEntry  29  }

	rbSuCumulativePowerOnTime	OBJECT-TYPE	
		SYNTAX			Unsigned32
		MAX-ACCESS		read-only
		STATUS			current
		DESCRIPTION		
				"Cumulative Power On Time (minutes).
				 Agent will return 0 if Cumulative Power On Time is unknown." 
		::=  {  rbRegisteredSuEntry  30  }
	
	rbSuOrganizationName	OBJECT-TYPE	
		SYNTAX			DisplayString (SIZE (0..32))
		MAX-ACCESS		read-only
		STATUS			current
		DESCRIPTION		
				"SU's organization name as defined in the SU."
		::=  {  rbRegisteredSuEntry  31  }

	rbSuAddress	OBJECT-TYPE	
		SYNTAX			DisplayString (SIZE (0..32))
		MAX-ACCESS		read-only
		STATUS			current
		DESCRIPTION		
				"The SU's address as defined in the SU."
		::=  {  rbRegisteredSuEntry  32  }

	rbSuCountry	OBJECT-TYPE	
		SYNTAX			DisplayString (SIZE (0..12))
		MAX-ACCESS		read-only
		STATUS			current
		DESCRIPTION		
				"The SU's country as defined in the SU."
		::=  {  rbRegisteredSuEntry  33  }

	rbSuMACControlNumber	OBJECT-TYPE	
		SYNTAX			Integer32
		MAX-ACCESS		read-only
		STATUS			current
		DESCRIPTION		
				"Least Significant Byte of the Integer computed by summarizing the
				 values of the 12 hexadecimal digits of the MAC Address." 
		::=  {  rbRegisteredSuEntry  34  }

	rbSuAirInterfaceType	OBJECT-TYPE	
		SYNTAX			INTEGER {
								  unknown (0),
		                          typeA  (1),
		                          typeSi (2)
		                        }    
		MAX-ACCESS		read-only
		STATUS			current
		DESCRIPTION		
				"SU Operation Mode.
				 typeA (1) - Standard Operation Mode, typeSi (2) - Advance Si Operation Mode."
		::=  {  rbRegisteredSuEntry  35  }


--========================================================================
--     SU External devices table 
--========================================================================
	rbSuSubDevicesTable	OBJECT-TYPE
		SYNTAX		SEQUENCE OF  RbSuSubDevicesEntry
		MAX-ACCESS	not-accessible
		STATUS		current
		DESCRIPTION	
			"This table contains IP Addresse of Gateways that support DRAP
			 that are connected to SUs.
			 To receive the Gateways connected to a specific SU, community 
			 <com>@SU.<MacAddress> should be used in Get Next command."
		::=  { rbSubcriberUnitConfig  2 }

	rbSuSubDevicesEntry	OBJECT-TYPE
		SYNTAX		RbSuSubDevicesEntry
		MAX-ACCESS	not-accessible
		STATUS		current
		DESCRIPTION	
			"Table entry"
		INDEX		{ rbSubDeviceIpAddress }
		::=  { rbSuSubDevicesTable 1 }

	RbSuSubDevicesEntry  ::=  SEQUENCE {
	    rbSubDeviceIpAddress    IpAddress,
		rbSuMacAddress          MacAddress,
		rbSubDeviceType		    INTEGER,
		rbSubDeviceVlanID		Integer32
		}


   	rbSubDeviceIpAddress	OBJECT-TYPE	
		SYNTAX			IpAddress
		MAX-ACCESS		read-only
		STATUS			current
		DESCRIPTION		
				"IP Address of the Gateway connected to an SU."
		::=  {  rbSuSubDevicesEntry  1  }

   	rbSuMacAddress	OBJECT-TYPE	
		SYNTAX			MacAddress
		MAX-ACCESS		read-only
		STATUS			current
		DESCRIPTION		
				"MAC Address of the SU."
		::=  {  rbSuSubDevicesEntry  2  }

   	rbSubDeviceType	OBJECT-TYPE	
		SYNTAX			INTEGER
		                {
						  unknown (0),
						  vgDataVoice (4),
						  vgData1Voice1 (5),
						  vgData4Voice2 (6),
						  vgDataVoice2(7),
						  ngData4Wireless (11),
						  winetworksMSG (23)
						}
		MAX-ACCESS		read-only
		STATUS			current
		DESCRIPTION		
				"The type of Gateway."
		::=  {  rbSuSubDevicesEntry  3  }
		
   	rbSubDeviceVlanID	OBJECT-TYPE	
		SYNTAX			Integer32
	    MAX-ACCESS		read-only
		STATUS			current
		DESCRIPTION		
				"The management VLAN ID used by the Gateway."
		::=  {  rbSuSubDevicesEntry  4  }
	
	
--========================================================================
--     SU Bridging Parameters  
-- SU Bridging Parameters are retrieved with community <com>@SU.<MacAddress>
--========================================================================
    suBridgingParameters    OBJECT IDENTIFIER ::=  {  rbSubcriberUnitConfig 4  }

	rbSuSupportDevicesLimit 	OBJECT-TYPE	
		SYNTAX			INTEGER
		                {
		                  enable (1),
		                  disable (2),
						  unknown (3)
		                }    
		MAX-ACCESS		read-write
		STATUS			current
		DESCRIPTION		
				"Enable\disable the limitation on the maximum number
				 of Ethernet devices (MAC addresses) that can be supported by the SU.
				 If disabled, then the maximum number is set to 512."
		::=  {  suBridgingParameters  1  }

	rbSuMaxNumberOfSupportedDevices 	OBJECT-TYPE	
		SYNTAX			Integer32 (1..512)
		MAX-ACCESS		read-write
		STATUS			current
		DESCRIPTION		
				"Maximum number of devices supported by SU. This parameter can be changed only if
				rbSuSupportDevicesLimit is enabled."
		::=  {  suBridgingParameters  2  }

	rbSuBridgeAgingTime 	OBJECT-TYPE	
		SYNTAX			Integer32 (1..1440)
		MAX-ACCESS		read-write
		STATUS			current
		DESCRIPTION		
				"The MAC Address aging time in minutes."
		::=  {  suBridgingParameters  3  }


-- =================================================================================
--     SU Hardware Components Info Table  
-- =================================================================================
	rbSuHwComponentsInfoTable	OBJECT-TYPE
		SYNTAX		SEQUENCE  OF  RbSuHwComponentsInfoEntry
		MAX-ACCESS	not-accessible
		STATUS		current
		DESCRIPTION	
			"This table provides parameters information regarding the SU Hardware components."
		::=  { rbSubcriberUnitConfig 3 }

	rbSuHwComponentsInfoEntry 	OBJECT-TYPE
		SYNTAX		RbSuHwComponentsInfoEntry
		MAX-ACCESS	not-accessible
		STATUS		current
		DESCRIPTION	
			"Table entry"
		INDEX		{  rbSuMacAddr  }
		::=  { rbSuHwComponentsInfoTable 1 }

	RbSuHwComponentsInfoEntry  ::=  SEQUENCE {
		rbSuRfCardRevision   		DisplayString,
		rbSuRfCardConfiguration		DisplayString,
		rbSuBootVersion				DisplayString,
		rbSuType    				INTEGER
	}


	rbSuRfCardRevision	OBJECT-TYPE	
		SYNTAX			DisplayString 
		MAX-ACCESS		read-only
		STATUS			current
		DESCRIPTION		
				"SU RF Card Revision."
		::=  {  rbSuHwComponentsInfoEntry  1  }

	rbSuRfCardConfiguration	OBJECT-TYPE	
		SYNTAX			DisplayString 
		MAX-ACCESS		read-only
		STATUS			deprecated
		DESCRIPTION		
				"SU RF Card Configuration description. Not supported in current version."
		::=  {  rbSuHwComponentsInfoEntry  2  }

	rbSuBootVersion	OBJECT-TYPE	
		SYNTAX			DisplayString 
		MAX-ACCESS		read-only
		STATUS			current
		DESCRIPTION		
				"SU Boot Version."
		::=  {  rbSuHwComponentsInfoEntry  3  }

	rbSuType	OBJECT-TYPE	
		SYNTAX        INTEGER    { unknown  ( 0 ) ,
		                           cpe      ( 1 ) ,
		                           cpePro   ( 2 ) ,
		                           cpeSi    ( 3 ) ,
		                           cpeProL  ( 4 ) ,
		                           cpeSiL   ( 5 ) ,
		                           cpe2Pro  ( 6 ) ,
		                           cpe2Si   ( 7 ) ,
		                           cpe2ProL ( 8 ) ,
		                           cpe2SiL  ( 9 )
		                         }
		MAX-ACCESS		read-only
		STATUS			current
		DESCRIPTION		
				"SU Type."
		::=  {  rbSuHwComponentsInfoEntry  4  }


--========================================================================
--     MAC Behind SU Table  
--========================================================================
    rbMACBehindSUList    OBJECT IDENTIFIER ::=  {  rbSubcriberUnitConfig 5  }

	rbMACBehindSUListTable	OBJECT-TYPE
		SYNTAX		SEQUENCE  OF  RbMACBehindSUListEntry
		MAX-ACCESS	not-accessible
		STATUS		current
		DESCRIPTION	
			"This table provides information regarding the MAC Addresses and VLAN IDs of devices behind the SU."
		::=  { rbMACBehindSUList 1 }

	rbMACBehindSUListEntry 	OBJECT-TYPE
		SYNTAX		RbMACBehindSUListEntry
		MAX-ACCESS	not-accessible
		STATUS		current
		DESCRIPTION	
			"Table entry"
		INDEX		{  rbSuMacAddr, rbMacBehindSuAddr  }
		::=  { rbMACBehindSUListTable 1 }

	RbMACBehindSUListEntry  ::=  SEQUENCE {
		rbMacBehindSuAddr  		  	MacAddress,
		rbMacBehindSuVlan			Integer32
	}

		
	rbMacBehindSuAddr	OBJECT-TYPE	
		SYNTAX			MacAddress
		MAX-ACCESS		read-only
		STATUS			current
		DESCRIPTION		
				"MAC Address of a device behind the SU." 
		::=  {  rbMACBehindSUListEntry  1  }

   	rbMacBehindSuVlan	OBJECT-TYPE	
		SYNTAX			Integer32
	    MAX-ACCESS		read-only
		STATUS			current
		DESCRIPTION		
				"The VLAN ID used by the device (a device may use more than one VLAN ID, or none.
				 If more than one VLAN ID is used, this will be the first identified VLAN ID)."
		::=  {  rbMACBehindSUListEntry  2  }


--========================================================================
--     Self-Installed SU Table  
--========================================================================
    rbSiSuInfo    OBJECT IDENTIFIER ::=  {  rbSubcriberUnitConfig 6  }

	rbSiSuInfoTable	OBJECT-TYPE
		SYNTAX		SEQUENCE  OF  RbSiSuInfoEntry
		MAX-ACCESS	not-accessible
		STATUS		current
		DESCRIPTION	
			"This table provides parameters information regarding the Self-Install SU."
		::=  { rbSiSuInfo 1 }

	rbSiSuInfoEntry 	OBJECT-TYPE
		SYNTAX		RbSiSuInfoEntry
		MAX-ACCESS	not-accessible
		STATUS		current
		DESCRIPTION	
			"Table entry"
		INDEX		{  rbSuMacAddr  }
		::=  { rbSiSuInfoTable 1 }

	RbSiSuInfoEntry  ::=  SEQUENCE {
		rbSiSuAntennaSelection	    INTEGER,
		rbSiSuSmartCardStatus    	INTEGER,
		rbSiSuInterfaceType         INTEGER
	}


	rbSiSuAntennaSelection	OBJECT-TYPE	
		SYNTAX			INTEGER  { unknown   ( 0 ) ,
                                   internal1 ( 1 ) ,
                                   internal2 ( 2 ) ,
								   internal3 ( 3 ) ,
                                   internal4 ( 4 ) ,
                                   internal5 ( 5 ) ,
								   internal6 ( 6 ) ,
                                   external  ( 7 ) ,
                                   automatic ( 8 ) 
		                         } 
		MAX-ACCESS		read-only
		STATUS			current
		DESCRIPTION		
				"The antenna(s) that can be used in the SI CPE." 
		DEFVAL			{ internal3 }
		::=  {  rbSiSuInfoEntry  1 }

	rbSiSuSmartCardStatus	OBJECT-TYPE	
		SYNTAX			INTEGER  { unknown      ( 0 ) ,
		                           installed    ( 1 ) ,
		                           notInstalled ( 2 ) ,
		                           fault        ( 3 )
		                         } 
		MAX-ACCESS		read-only
		STATUS			current
		DESCRIPTION		
				"The Smart card status."
		::=  {  rbSiSuInfoEntry  2 }

	rbSiSuInterfaceType	OBJECT-TYPE	
		SYNTAX			INTEGER  { unknown  ( 0 ) ,
		                           ethernet ( 1 ) ,
		                           usb      ( 2 ) 
		                         } 
		MAX-ACCESS		read-only
		STATUS			current
		DESCRIPTION		
				"The interface type."
		::=  {  rbSiSuInfoEntry  3 }


--========================================================================
--     SU Licenses Table
--========================================================================
    rbSuLicenses    OBJECT IDENTIFIER ::=  {  rbSubcriberUnitConfig 7  }

    rbSuLicensesTable	OBJECT-TYPE
		SYNTAX		SEQUENCE  OF  RbSuLicensesEntry
		MAX-ACCESS	not-accessible
		STATUS		current
		DESCRIPTION	
			"This table provides information about License(s) registered for the SU.
			 It will include up to 5 entries - Maximum License Count per SU. 
			 This table will only be applicable for L(Limitted Capabilities) model units."
		::=  { rbSuLicenses 1 }

	rbSuLicensesEntry	OBJECT-TYPE
		SYNTAX		RbSuLicensesEntry
		MAX-ACCESS	not-accessible
		STATUS		current
		DESCRIPTION	
			"Table entry."
		INDEX		{ rbSuMacAddr, rbSuLicenseIdx }
		::=  { rbSuLicensesTable 1 }

	RbSuLicensesEntry  ::=  SEQUENCE {
		rbSuLicenseIdx 	         Integer32, 
		rbSuLicenseId		     INTEGER,
		rbSuLicenseValue 	     Unsigned32
		}

	rbSuLicenseIdx	OBJECT-TYPE	
		SYNTAX			Integer32 ( 1 .. 5 )
		MAX-ACCESS		read-only
		STATUS			current
		DESCRIPTION		
				"SU License Table Index."
		::=  {  rbSuLicensesEntry  1  }

	rbSuLicenseId 	OBJECT-TYPE	
		SYNTAX			INTEGER
		                { 
		                  bandwidth  (1)
						}
		MAX-ACCESS		read-write
		STATUS			current
		DESCRIPTION		
				"SU License ID. Currently the only supported value is 1 for Bandwidth."
		::=  {  rbSuLicensesEntry  2  }

	rbSuLicenseValue	OBJECT-TYPE	
		SYNTAX			Unsigned32
		MAX-ACCESS		read-write
		STATUS			current
		DESCRIPTION		
				"SU License Value. Currently the only supported value is 0 for Unlimited Bandwidth."
		::=  {  rbSuLicensesEntry  3  }


--========================================================================
--     Authorization and Traps parameters 
--========================================================================

	rbAuthorizationAndTraps   OBJECT IDENTIFIER ::= {  rainbow 6 }

	rbAuthorizedManagersTable	OBJECT-TYPE
		SYNTAX		SEQUENCE  OF  RbAuthorizedManagersEntry
		MAX-ACCESS	not-accessible
		STATUS		current
		DESCRIPTION	
			"This table defines the stations that are authorized to manage the device.
			 Up to 10 Authorized Managers can be defined."
		::=  { rbAuthorizationAndTraps 1 }

	rbAuthorizedManagersEntry	OBJECT-TYPE
		SYNTAX		RbAuthorizedManagersEntry
		MAX-ACCESS	not-accessible
		STATUS		current
		DESCRIPTION	
			"Table entry"
		INDEX		{ authMngrIpAddr }
		::=  { rbAuthorizedManagersTable 1 }

	RbAuthorizedManagersEntry  ::=  SEQUENCE {
		authMngrIpAddr  			IpAddress,
		authMngrReadCommunity   	DisplayString, 
		authMngrWriteCommunity   	DisplayString, 
		authMngrTrapEnable  		INTEGER,
		authMngrRowStatus       	RowStatus 
		}


	authMngrIpAddr	OBJECT-TYPE	
		SYNTAX			IpAddress
		MAX-ACCESS		read-write
		STATUS			current
		DESCRIPTION		
				"IP address of the Authorized Management Station" 
		::=  {  rbAuthorizedManagersEntry  1  }


	authMngrReadCommunity	OBJECT-TYPE	
		SYNTAX			DisplayString  ( SIZE ( 0 .. 23 ) ) 
		MAX-ACCESS		read-write
		STATUS			current
		DESCRIPTION		
				"Authorized Management Station Community for Read operations.
				 In case that trap transmission is enabled, trap message is send
				 with this community."
		::=  {  rbAuthorizedManagersEntry  2  }

	authMngrWriteCommunity	OBJECT-TYPE	
		SYNTAX			DisplayString  ( SIZE ( 0 .. 23 ) ) 
		MAX-ACCESS		read-write
		STATUS			current
		DESCRIPTION		
				"Authorized Management Station Community for Write operations."
		::=  {  rbAuthorizedManagersEntry  3  }

	authMngrTrapEnable	OBJECT-TYPE	
		SYNTAX			INTEGER  {
		                           enable ( 1 ) ,
		                           disable  ( 2 )
		                         } 
		MAX-ACCESS		read-write
		STATUS			current
		DESCRIPTION		
				"When set to enable, device transmits trap to the Authorized Manager."
		::=  {  rbAuthorizedManagersEntry  4 }

	authMngrRowStatus	OBJECT-TYPE	
		SYNTAX			RowStatus
		MAX-ACCESS		read-write
		STATUS			current
		DESCRIPTION		
				"Control for creating and deleting entries. Entries may be modified while active.
                 active (1) - means that the entry is available for use by the managed device and
                 relevant parameters may be modified;
                 createAndGo (4) is used for creating a new entry and to have its status 
                 automatically set to active.
                 destroy (6) is used for deleting an existing entry."
		::=  {  rbAuthorizedManagersEntry  5  }


	rbTrapConfigTable	OBJECT-TYPE
		SYNTAX		SEQUENCE  OF  RbTrapConfigEntry
		MAX-ACCESS	not-accessible
		STATUS		current
		DESCRIPTION	
			"This table defines configuration parameters for each trap supported by device."
		::=  { rbAuthorizationAndTraps 2 }

	rbTrapConfigEntry	OBJECT-TYPE
		SYNTAX		RbTrapConfigEntry
		MAX-ACCESS	not-accessible
		STATUS		current
		DESCRIPTION	
			"Table entry"
		INDEX		{  trapEnterprizeId, trapId }
		::=  { rbTrapConfigTable 1 }

	RbTrapConfigEntry  ::=  SEQUENCE {
		trapEnterprizeId  			INTEGER,
		trapId  					Integer32,
		trapEnable  				INTEGER,
		trapSeverity				TrapSeverity,
		trapSuppressionInterval  	Integer32
		}


	trapEnterprizeId	OBJECT-TYPE	
		SYNTAX			INTEGER {
		                          snmp    (1),
								  rainbow (2),
								  other   (3)
								}
		MAX-ACCESS		read-only
		STATUS			current
		DESCRIPTION		
				"Identification of the MIB where the trap is defined." 
		::=  {  rbTrapConfigEntry  1  }

	trapId	OBJECT-TYPE	
		SYNTAX			Integer32 ( 0 .. 256 ) 
		MAX-ACCESS		read-only
		STATUS			current
		DESCRIPTION		
				"Trap ID defined in the TRAP-TYPE macro in the corresponding MIB.
				 For snmp trapEnterprizedId:
				 1 - coldStart ,
				 2 - warmStart ,
			     3 - linkDown  ,
			     4 - linkUp    ,
				 5 - authenticationFailure,
				 6 - egpNeighborLoss" 
		::=  {  rbTrapConfigEntry  2  }

	trapEnable	OBJECT-TYPE	
		SYNTAX			INTEGER { 
		                           enable	( 1 ) ,
		                           disable  ( 2 )
								}
		MAX-ACCESS		read-write
		STATUS			current
		DESCRIPTION		
				"Enable/disable transmission of the trap." 
		::=  {  rbTrapConfigEntry  3  }

	trapSeverity	OBJECT-TYPE	
		SYNTAX			TrapSeverity
		MAX-ACCESS		read-write
		STATUS			current
		DESCRIPTION		
				"Trap severity." 
		::=  {  rbTrapConfigEntry  4  }

	trapSuppressionInterval	OBJECT-TYPE	
		SYNTAX			Integer32 ( 0 .. 86400 )  
		MAX-ACCESS		read-write
		STATUS			current
		DESCRIPTION		
				"The interval in seconds during which transmission of identical traps should
				 be supressed by the device. 0 means trap suppression is disabled." 
		::=  {  rbTrapConfigEntry  5  }


	rbTrapGetActive	OBJECT-TYPE	
		SYNTAX			INTEGER { 
		                           enable   ( 1 ) ,
		                           disable  ( 2 )
								}
		MAX-ACCESS		read-write
		STATUS			current
		DESCRIPTION		
				"This parameter is used to obtain active alarms from device.
				 When set to enable, the device respond by transmitting all currently active alarms." 
		::=  {  rbAuthorizationAndTraps  3  }

	rbTrapSeqNumber	OBJECT-TYPE	
		SYNTAX			Unsigned32 
		MAX-ACCESS		read-write
		STATUS			current
		DESCRIPTION		
				"This parameter is used as trap variable binding and contains the sequential trap number.
				 Get of this variable should return the number of the last trap transmitted by the device.
				 Set is not supported in the current version."
		::=  {  rbAuthorizationAndTraps  4  }
    
	rbTrapSeverity	OBJECT-TYPE	
		SYNTAX			TrapSeverity 
		MAX-ACCESS		read-only
		STATUS			current
		DESCRIPTION		
				"This parameter is used as trap variable binding and contains the severity
				 of the trap."
		::=  {  rbAuthorizationAndTraps  5  }

	rbTrapSource	OBJECT-TYPE	
		SYNTAX			DisplayString 
		MAX-ACCESS		read-only
		STATUS			current
		DESCRIPTION		
				"This parameter is used as trap variable binding and contains the trap source 
				 entity : <NPU.Slot#>,
				          <AU.Slot#>,
				          <SU.MacAddress>,
				          <BS>,
				          <PSU#>,
				          <PIU#>,
				          <ACU#>,
		                  <ACU-FAN.Slot#>,
				          <RC.RadioClusterId#>,
				          <ODU.OduConfigId#>,
				          <CHNL.AuSlot#.ChannelId#>,
   			              <SBSCR.SubscriberIdx#>,
	                      <SRVC.PipeIdx#>,
                          <POLICY.RuleIdx#>,
                          <QOS.ProfileIdx#>,
	                      <FRWRD.RuleIdx#>,
	                      <TMPL.ProfileIdx#>,
	                      <FLTR2.RuleIdx#>,
	                      <FLTR3.RuleIdx#>,
	                      <FLTRIFC.FilteringIdx#>,
	                      <FLTR.RuleIdx#>,
	                      <DENY.MacAddress>,
	                      <AUTH-MNG.IpAddress>,
	                      <TRAP.TrapId#>,
	                      <AUTH-SERV.IpAddress>,
	                      <ACCT-SERV.IpAddress>"
		::=  {  rbAuthorizationAndTraps  6  }

	rbTrapAdditionalInfo	OBJECT-TYPE	
		SYNTAX			INTEGER {
		                noInfo (0),
		                externalReset (1),
						internalFaultReset(2),
		                
-- SU HW Fault
		                mantaPllNotLockedOnInit(3),             -- MantaPLL is not locked for more than 5mSec
		                mantaPllNotLockedOnSteadyState(4),      -- Manta PLL is not locked in steady state
		                mantaSWDownloadError(5),	            -- Host fails to download Manta's firmware (C with CRC errors, or handshake error).
		                radioPLLNotLockedAfterPowerUP(6),	    -- Radio PLL's lock indication not locked after power up sequence.
		                radioPLLNotLockedOnSteadyState(7),      -- Radio PLL's lock indication not locked on steady state.
		                bitTestFailed(8),						-- One of the Built in tests Failed.

-- Networking faults    
                        suEthernetPortLoop (10),				-- Loop was detected on SU Ethernet port

-- AU HW Fault
                        powerExPmaxTimeTooLong(23),      	    -- When power exceeds PMAX+5dB for more than 5 minutes
                        phyIDUburnFailed(24),	                -- When a process to burn IDU table fails (CRC check on finish fails, FTP session failed, no place in FFS).
                        ifFailLock(25),	                        -- IF synthesizer failed to lock on the frequency set on the synthesizer
                        oduTableDnldError(26), 	                -- AU detects an error while downloading the ODU table. The string should include also the byte number of the ODU table were the error was detected.
                        oduConnLost(27),	                    -- Connection between AU and ODU is lost
		                
-- Configuration Changed
                        configElementAdded (30),				-- NPU configuration changed - element added event
                        configElementDeleted (31),				-- NPU configuration changed - element deleted event
                        configElementUpdated (32),				-- NPU configuration changed - element modified  event
                        managementPortConfig (33),				-- NPU Management Port configuration changed
		                
-- Shelf Peripherals Fault
					    powerSupplyFault(53),	                -- NPU detected a fault in one of the Power Supply Units
						powerInterfaceUnitsFault(54),			-- NPU detected a fault in one of the Power Interface Units 
						acuFault(55),							-- NPU detected a fault in the ACU unit
		                
-- Shelf Environment Fault
						dryContactsFault(73),					-- NPU detected a fault in the dry contacts
						npuTemperatureFault (74),				-- NPU detected temperature fault
						auIduTemperatureFault(75),		        -- AU IDU temperature fault detected
						auOduTemperatureFault (76),				-- AU ODU temperature fault detected

-- Software Download Fault
                        sdlBadVersion(100),                     -- Unsupported Software version is detected. 
                                                                -- This trap is generated in NPU when there is no compatibility between versions (NPU, AU or SU)in AU and SU is generated when no compatibility is detected with corresponding SU or AU versions.
                        sdlVerNotAvailable(101),                -- Software version requested is not available at NPU site. This trap is generated in NPU only.
                        sdlFailed(102),                         -- Software download process has failed. 
                        noDiskSpace(103),                       -- There are already 3 SW versions in NPU for AU and SU, and another version is being downloaded
						actionRunFromShadow (104),				
						actionMakeRunningVerOperational (105),
		                
-- Services related messages.
						maxSubscribers(111),					-- Maximum number of allowed subscribers has been reached
						maxServPipes(112),						-- Maximum number of allowed service pipe configurations has been reached
						maxServProfiles(113),					-- Maximum number of allowed service profile configurations has been reached
						maxForwRules(114),				    	-- Maximum number of allowed forwarding rules profile configuration has been reached
						maxPolicyRules(115),			        -- Maximum number of allowed policy rules profile configuration has been reached
						maxQoSProfiles(116),    				-- Maximum number of allowed quality of service profile configuration has been reached
						maxNumOfCalls(117),					    -- Maximum number of calls has been reached
						noBWforVOIP(118),						-- No available bandwidth to allocate a new VoIP call
                        serviceAdminStatusChanged (119),        -- Service Admin Status has been changed
                        serviceSuMacChanged (120),              -- Service SU Mac Address has been changed
                        serviceVlanListChanged(121),	        -- Service Subscriber Site VLAN List has been changed
                        serviceProfileChanged(122),	            -- Service Profile has been changed (implies that another Service Profile has been set)

-- LinkUP/Down Traps
					    mainBackbonePort(127),				    -- Ethernet connection to backbone.			    
						managementPort(128),                    -- Management connection is found to be downGenerated in NPU
                        connection2AU(129),                     -- Communication to AU 
                        radioLinkAU(130),                       -- Radio Link fails (all SU's are lost)Generated in AU
                        radioLinkAU2SU(131),                    -- Link to specific SU

-- SU/AU Network Entries States
                        authenticationProcessFailed (132),  	-- Authentication process failed								
 					    registrationProcessFailed (133),		-- Registration process failed
						registrationProcessSucceed (134),       -- Registration process succeed
						auDhcpProcessFailed (135),				-- AU DHCP process failed
						auConfigurationDownloadFailed (136),	-- AU configuration download failed
						auSetParametersFailed (137),			-- AU set parameters failed
						auFirmwareDownloadFailed (138),			-- AU firmware download failed
						auInService (139),						-- AU is in service
		                
-- General
						lciConnection  (140),					-- LCI access detected
						telnetConnection (141),					-- Telnet access detected
						telnetAuthenticationFailure (142),		-- Telnet Authentication Failure
						lciAuthenticationFailure (143),		    -- LCI Authentication Failure
		                
-- AU/SU Mode Conflict
						diversityModeMismatch  (144),		    -- Diversity Mode definition for old AU card
						wrongBandwidth         (145),			-- Wrong BW Configuration (AU/SU)
						wrongFDDConfig         (146),		    -- Wrong FDD Configuration for AU PV card
						wrongTDDConfig         (147),		    -- Wrong TDD Configuration for old AU card
						wrongMaxCellRadius     (148),		    -- Wrong MaxCellRadius Configuration for AU PV card
						wrongMinCellRadius     (149),		    -- Wrong MinCellRadius Configuration for old AU card
		                
-- AU/SU Sw Download fault reasons
						downloadAborted	(150),						-- Download is aborted by external event	
						incompatibleHWRevisionDetected (151),		-- Header's "HW Version" is not compatible with the real unit's HW	
						incompatibleHWConfigurationDetected (152), 	-- Header's "NW Config" is not compatible with the real unit's HW	
						createFileFailed (153),						-- Fail to create new file on Flash	
						openFileFailed (154),						-- Fail to open file on Flash	
						fstatFailed (155),							-- Fail to get file statistics (size ...)	
						readFileFailed (156),						-- Fail to read from file	
						writeFileFailed	(157),						-- Fail to write to file	
						writeInfoFailed	(158),						-- Fail to write information about SW file to the "Info" file	
						flashAccessFailed (159),					-- Can not Access Flash using File System	
						shadowFileAccessFailed (160),	 			-- Old Shadow file is not accessible and can not be removed	
						wrongSignature (161),						-- NPU File Signature is not recognized	
						fileWithoutHeader (162),					-- File does not contain header	
						headerTooLong (163),						-- File's header is too long	
						mismatchInHeader (164),						-- Some header's field title or format is not recognized 	
						invalidUnitType	(165),						-- Header's "Unit Type" field does not match current Unit (Trying to Download wrong SW)	
						noRFVersionInHeader	(166),					-- RF Version should be checked but is not found in header	
						incompatibleRFRevision (167),				-- Header's "RF Revision" is not compatible with the real unit's RF	
						calcCRCFailed (168),						-- CRC calculation failed	
						wrongCRC (169),								-- Calculated CRC does not match CRC in the header	
						wrongFileSize (170),						-- Calculated file size does not match file size in the header	
						tFTPStartFailed	(171),						-- Fail to start TFTP client	
						errorDuringTFTP	(172),						-- Error is received during TFTP	
						readSocketError	(173),						-- Fail to read received data from TFTP data socket	
						noReadBytes	(174),							-- TFTP data socket is empty	
						inProcess (175),							-- Another TFTP session is already in process	
						noFilename (176),							-- File name is not set properly	
						fileSizeTooBig  (177),						-- File size exceeds maximum that can be downloaded to AU/SU	
						wrongFileExt (178),							-- Files with extension differ than ".bz" can not be downloaded to AU/SU	
						fileIsMain (179),							-- File exists as Main and can not be removed	
						fileNotAvailable (180 ),					-- File is not available
						timeout (181),								-- Communication timeout

-- License Related Traps
                        tempGracePeriodStarted (182),  	            -- Temp Grace License Started.	
                        tempGracePeriodStopped (183),  	            -- Temp Grace License Expired.	
                        gracePeriodStarted     (184),  		        -- Grace License Started.	
                        gracePeriodExpired     (185),  		        -- Grace License Expired.	
                        gracePeriodExpiresIn3days (186),            -- Grace License Expires in 3 days.
						macInLicenseFileConflict  (187),            -- License file loaded to wrong MicroBST.
                        wrongFileSignature     (188),  		        -- License File Signature is not recognized.
						wrongFileSyntax        (189),			    -- License File syntax error.	
						wrongFileCPEsNumber    (190),		        -- MicroBST License File wrong CPEs number.	
						fileExists             (191),			    -- License File already exists in DB
							
-- RADIUS
                        serviceProfileDoesNotExist (200),           -- Service Profile does not exist
						tooManyVlansPerService     (201),           -- Too many VLAN IDs defined for the service
						tooManyVlansPerSU          (202),           -- Too many VLAN IDs on one SU
						wrongVlanID                (203),           -- Wrong VLAN ID (0 To 4094 expected)
						transparentVlanAndVplMismatch    (204),     -- Transparent VLAN ID and VPL mismatch
						vlanMismatch               (205),           -- Can't allocate for the same SU services with and without VLANs
						sameServiceTypeOnVlan      (206),           -- Can't create 2 services with either the same type of service, or L2 and Voice services with the same VLAN ID
                        oneVlanPermittedForVlanClassMode (207),     -- Only one VLAN permitted when VLAN classification mode is ON
                        accessVlanMismatch         (208),           -- Access VLAN permitted only for empty VLAN list or for Hybrid mode ON with VLAN list
                        accessVlanDuplicate        (209),           -- Access VLAN can not be equal to any VLAN in the SU VLAN list
                        oneAccessVlanPerSU         (210),           -- Only one Access VLAN allowed per SU
                        userAuthTimeOut            (211),           -- No connection between NPU and Authentication Server during authentication or re-authentication
                        userAccStartTimeOut        (212),           -- User Accounting Server start time out
                        userAccStopTimeOut         (213),           -- User Accounting Server stop time out
                        tableIsFull                (214),           -- Service Pipe Table is full

-- File Download Related Traps
                        fileDownloadStarted        (220),  	        -- File Download Started	
                        fileDownloadCompleted      (221),  	        -- File Download Completed	
                        fileMD5Failure             (222),  		    -- File MD5 Failure	
                        fileParsingFailure         (223),  		    -- File Parsing Failure	
                        fileDownloadFailure        (224), 		    -- File Download Failure

-- ODU Related Traps
                        overCurrent                (225),  	        -- ODU shut down as a result of the over current	
                        synthesizerUnlock          (226),  	        -- ODU shut down as a result of the synthesizer unlock	
                        highReflectedPower         (227),  		    -- ODU shut down as a result of the high reflected power	
                        overTemperature            (228)  		    -- ODU shut down as a result of the over temperature

		                } 
		MAX-ACCESS		read-only
		STATUS			current
		DESCRIPTION		
				"This parameter is used as trap variable binding and contains the 
				 additional info, transmitted with the trap."
		::=  {  rbAuthorizationAndTraps  7  }

    rbTrapCategory	OBJECT-TYPE	
		SYNTAX			INTEGER
		                {
			             none (0),
			             communications (1),
			             qualityOfService (2),
			             processingError (3),
			             equipment (4),
			             environmental (5)			  
						}
		MAX-ACCESS		read-only
		STATUS			current
		DESCRIPTION		
				"The trap category according to the X.733." 
		::=  {  rbAuthorizationAndTraps 8  }

 	rbTrapMinSeverity	OBJECT-TYPE	
		SYNTAX			TrapSeverity
		MAX-ACCESS		read-only
		STATUS			current
		DESCRIPTION		
				"This parameter defines the minimum severity of traps to be transmitted by device.
				 Not supported in current version." 
		::=  {  rbAuthorizationAndTraps 9  }

 	rbTrapLedStatus	OBJECT-TYPE	
		SYNTAX			OCTET STRING
		MAX-ACCESS		read-only
		STATUS			current
		DESCRIPTION		
				"This parameter defines status of the leds of corresponding device.
				 Not supported in current version."
		::=  {  rbAuthorizationAndTraps 10  }

 	rbTrapIpAddress	OBJECT-TYPE	
		SYNTAX			IpAddress
		MAX-ACCESS		read-only
		STATUS			current
		DESCRIPTION		
				"This parameter is used as a trap variable binding in case that IP Address
				 should be transmitted."
		::=  {  rbAuthorizationAndTraps 11  }

 	rbTrapSetFailureReason	OBJECT-TYPE	
		SYNTAX			INTEGER
		                {
						 unknown(0),         			    -- Unknown
						 generalError(1),         			-- General Error
						 updateCRCFailed (2),	  			-- Failed to update parameters CRC
						 wrongDefaultsValue (3),  			-- Set defaults to unknown type (internal error) 
						 setDefaultsFailed (4),	  			-- Failed to set defaults	(internal error)
						 logPreffixTooLong (5),	  			-- Log preffix is too long
						 setLogPreffixFailed (6), 			-- Failed to set Log Preffix (internal error)
						 invalidCellRadius (7),   			-- Cell Radius is invalid
						 setCellRadiusFailed (8), 			-- Failed to set Cell Radius
						 setBsIDFailed (9),		  			-- Failed to set Base Station ID (internal error)
						 setBsMaskFailed (10),    			-- Failed to set Base Station Mask (internal error)
						 setArqModeFailed (11),   			-- Failed to set ARQ mode (internal error)
						 setBandTypeFailed (12),  			-- Failed to set Band (internal error)
						 txFrequencyOutOfLimitedRange (13), -- Tx Frequency is out of calculated limited range
						 invalidTxFrequency (14), 			-- Tx frequency is invalid
						 txFrequencyOutOfRange (15),        -- Tx frequency is out of maximum permited range
						 setTxFrequencyFailed (16),         -- Tx Frequency set failed (internal error)
						 invalidTxPower (17),               -- Tx Power value is invalid
						 setTxPowerFailed (18),             -- Set Tx Power Failed (internal error)
						 invalidUplinkBasicRate (19),       -- UL Basic rate is invalid
						 setUplinkBasicRateFailed (20),     -- Failed to set Uplink Basic Rate (internal error)
	                     invalidDownlinkBasicRate (21),     -- DL Basic rate is invalid
						 setDownlinkBasicRateFailed (22),   -- Failed to set Downlink Basic Rate (internal error)
						 setSuRateWhileMrtEnabled (23),     -- It is forbidden to set SU rate while Multirate is enabled
						 invalidDownLinkRate (24),          -- Invalid Downlink rate
						 invalidUplinkRate (25),            -- Invalid Uplink rate
						 invalidOptimalRSSI (26),           -- Invalid Optimal RSSI
						 setOptimalRSSIFailed (27),         -- set Optimal RSSI failed (internal error)
						 berTestDataSizeUnderMin (28),      -- BER Test data size is less then minimum allowed
						 berTestDataSizeOverMax (29),       -- BER Test data size is greater then maximum allowed
						 berTestIsAlreadyRunning (30),      -- BER Test is already running
						 invalidBerTestRate (31),           -- Invalid BER Test rate
						 invalidBerTestSLA (32),			-- Invalid BER Test SLA
						 setBerTestSlaFailed (33),          -- Failed to set SLA for BER Test (internal error)
						 invalidBerTestMaxPacketSize (34),  -- Invalid BER Test maximum packet size
						 setBerTestMaxPacketSizeFailed(35), -- Failed to set BER Test maximum packet size (internal error)
						 berTestCreateConnectionFailed(36), -- Failed to create connection for the BER test
						 telnetDisconnectFailed (37),       -- Failed to disconnect Telnet session
						 invalidEthernetMode (38),          -- Invalid Ethernet configuration mode
						 setEthernetModeFailed (39),   		-- Set Ethernet mode failed (internal error)
						 installerPasswordTooLong (40),     -- SU Installer password too long
						 setInstallerPasswordFailed (41),   -- Set SU Installer password failed (internal error) 
						 invalidBand (42),                  -- Invalid band  
						 invalidAgingTime (43),	            -- Invalid Aging Time or internal error  
                         invalidLimitDevicesNum (44),	    -- Invalid Limit of Supported devices or internal error  
                         invalidLimitMaxDevicesEnable (45), -- Failed to set limit mode - invalid value or or internal error  
                         maxCellRadiusConflict        (46)  -- Failed to set cell radius - conflict with TDD ratio  

                        }
		MAX-ACCESS		read-only
		STATUS			current
		DESCRIPTION		
				"This parameter contains the reason the Set parameter command was rejected
				 by device"
		::=  {  rbAuthorizationAndTraps 12  }

    rbTrapRestoreDefaults	OBJECT-TYPE	
		SYNTAX			INTEGER
		                {
			             noAction            (0),
			             restoreTrapEnable   (1),
			             restoreTrapSeverity (2),
			             restoreTrapSuppressionInterval (3)
						}
		MAX-ACCESS		read-write
		STATUS			current
		DESCRIPTION		
				"This parameter is used to restore the default values of the configuration parameters
				 for each trap supported by device:
                 restoreTrapEnable (1) - means that the Trap Admin Status will be restored to Enable;
                 restoreTrapSeverity (2) - means that the Trap Severity will be restored to the default severity;
                 restoreTrapSuppressionInterval (3) - means that the Trap Suppression will be restored to 0 (no suppression)." 
		::=  {  rbAuthorizationAndTraps 13  }


------------------------------
	rbTrapThresholdsTable	OBJECT-TYPE
		SYNTAX		SEQUENCE  OF  RbTrapThresholdsEntry
		MAX-ACCESS	not-accessible
		STATUS		current
		DESCRIPTION	
			"This table defines thresholds for specific counters. Trap is transmitted
			 if counter passes the threshold. Not supported in current version."
		::=  { rbAuthorizationAndTraps 20 }

	rbTrapThresholdsEntry	OBJECT-TYPE
		SYNTAX		RbTrapThresholdsEntry
		MAX-ACCESS	not-accessible
		STATUS		current
		DESCRIPTION	
			"Table entry"
		INDEX		{ counterId  }
		::=  { rbTrapThresholdsTable 1 }

	RbTrapThresholdsEntry  ::=  SEQUENCE {
		counterId  			Integer32,
		counterName			DisplayString,
		counterType  		INTEGER,
		counterIntValue		Integer32,
		counterStringValue	DisplayString
		}

	counterId	OBJECT-TYPE	
		SYNTAX			Integer32 ( 1 .. 100 )
		MAX-ACCESS		read-write
		STATUS			current
		DESCRIPTION		
				"Identification of the counter" 
		::=  {  rbTrapThresholdsEntry  1  }

	counterName	OBJECT-TYPE	
		SYNTAX			DisplayString
		MAX-ACCESS		read-write
		STATUS			current
		DESCRIPTION		
				"String representing the name of the counter, as it is defined in the MIB" 
		::=  {  rbTrapThresholdsEntry  2  }

	counterType	OBJECT-TYPE	
		SYNTAX			INTEGER
		                {
						  integer (1),
						  string  (2) 
						}
		MAX-ACCESS		read-write
		STATUS			current
		DESCRIPTION		
				"Type of the counter" 
		::=  {  rbTrapThresholdsEntry  3  }

	counterIntValue	OBJECT-TYPE	
		SYNTAX			Integer32
		MAX-ACCESS		read-write
		STATUS			current
		DESCRIPTION		
				"Counter value in Integer format" 
		::=  {  rbTrapThresholdsEntry  4  }

	counterStringValue	OBJECT-TYPE	
		SYNTAX			DisplayString
		MAX-ACCESS		read-write
		STATUS			current
		DESCRIPTION		
				"Counter value in String format" 
		::=  {  rbTrapThresholdsEntry  5  }


	rbTrapEventLogTable	OBJECT-TYPE
		SYNTAX		SEQUENCE  OF  RbTrapEventLogEntry
		MAX-ACCESS	not-accessible
		STATUS		current
		DESCRIPTION	
			"This table containes trap information for the last 1000 traps."
		::=  { rbAuthorizationAndTraps 21 }

	rbTrapEventLogEntry	OBJECT-TYPE
		SYNTAX		RbTrapEventLogEntry
		MAX-ACCESS	not-accessible
		STATUS		current
		DESCRIPTION	
			"Table entry"
		INDEX		{  trapEventLogSeqNum  }
		::=  { rbTrapEventLogTable 1 }

	RbTrapEventLogEntry  ::=  SEQUENCE {
		trapEventLogSeqNum  	     Unsigned32,
		trapEventLogId 			     Integer32,
		trapEventLogSeverity         TrapSeverity,
		trapEventLogType 		     INTEGER,
		trapEventLogCategory 	     INTEGER,
		trapEventLogSource 		     DisplayString,
		trapEventLogVarBindNumber    Integer32,
		trapEventLogVarBindSize		 Integer32,
		trapEventLogAddVarAttributes DisplayString,
		trapEventLogDateAndTime      DisplayString
		}

	trapEventLogSeqNum	OBJECT-TYPE	
		SYNTAX			Unsigned32 
		MAX-ACCESS		read-only
		STATUS			current
		DESCRIPTION		
				"The trap sequential number."
		::=  {  rbTrapEventLogEntry  1  }

	trapEventLogId	OBJECT-TYPE	
		SYNTAX			Integer32 
		MAX-ACCESS		read-only
		STATUS			current
		DESCRIPTION		
				"The trap ID defined in the TRAP-TYPE macro." 
		::=  {  rbTrapEventLogEntry  2  }
    
	trapEventLogSeverity	OBJECT-TYPE	
		SYNTAX			TrapSeverity 
		MAX-ACCESS		read-only
		STATUS			current
		DESCRIPTION		
				"The trap severity."
		::=  {  rbTrapEventLogEntry  3  }

    trapEventLogType	OBJECT-TYPE	
		SYNTAX			INTEGER
		                {
			             coldStart       (0),
			             warmStart       (1),
			             linkDown        (2),
			             linkUp          (3),
			             authenticationFailure (4),
			             egpNeighborLoss       (5),
			             enterpriseSpecific    (6)			  
						}
		MAX-ACCESS		read-only
		STATUS			current
		DESCRIPTION		
				"Trap ID defined in the TRAP-TYPE macro: 0 to 5 for the snmp MIB or 6 for other MIBs." 
		::=  {  rbTrapEventLogEntry  4  }

    trapEventLogCategory	OBJECT-TYPE	
		SYNTAX			INTEGER
		                {
			             none             (0),
			             communications   (1),
			             qualityOfService (2),
			             processingError  (3),
			             equipment        (4),
			             environmental    (5)			  
						}
		MAX-ACCESS		read-only
		STATUS			current
		DESCRIPTION		
				"The trap category according to the X.733." 
		::=  {  rbTrapEventLogEntry  5  }

	trapEventLogSource	OBJECT-TYPE	
		SYNTAX			DisplayString 
		MAX-ACCESS		read-only
		STATUS			current
		DESCRIPTION		
				"Trap source entity :
				          <NPU.Slot#>,
				          <AU.Slot#>,
				          <SU.MacAddress>,
				          <BS>,
				          <PSU#>,
				          <PIU#>,
				          <ACU#>,
		                  <ACU-FAN.Slot#>,
				          <RC.RadioClusterId#>,
				          <ODU.OduConfigId#>,
				          <CHNL.AuSlot#.ChannelId#>,
   			              <SBSCR.SubscriberIdx#>,
	                      <SRVC.PipeIdx#>,
                          <POLICY.RuleIdx#>,
                          <QOS.ProfileIdx#>,
	                      <FRWRD.RuleIdx#>,
	                      <TMPL.ProfileIdx#>,
	                      <FLTR2.RuleIdx#>,
	                      <FLTR3.RuleIdx#>,
	                      <FLTRIFC.FilteringIdx#>,
	                      <FLTR.RuleIdx#>,
	                      <DENY.MacAddress>,
	                      <AUTH-MNG.IpAddress>,
	                      <TRAP.TrapId#>,
	                      <AUTH-SERV.IpAddress>,
	                      <ACCT-SERV.IpAddress>"
		::=  {  rbTrapEventLogEntry  6  }
    
	trapEventLogVarBindNumber	OBJECT-TYPE	
		SYNTAX			Integer32 
		MAX-ACCESS		read-only
		STATUS			current
		DESCRIPTION		
				"The trap Variable Bind Number."
		::=  {  rbTrapEventLogEntry  7  }
    
	trapEventLogVarBindSize	OBJECT-TYPE	
		SYNTAX			Integer32 
		MAX-ACCESS		read-only
		STATUS			current
		DESCRIPTION		
				"The trap Variable Bind Size."
		::=  {  rbTrapEventLogEntry  8  }

	trapEventLogAddVarAttributes	OBJECT-TYPE	
		SYNTAX			DisplayString 
		MAX-ACCESS		read-only
		STATUS			current
		DESCRIPTION		
				"The trap Variable Attributes Additional information."
		::=  {  rbTrapEventLogEntry  9  }

	trapEventLogDateAndTime	OBJECT-TYPE	
		SYNTAX			DisplayString 
		MAX-ACCESS		read-only
		STATUS			current
		DESCRIPTION		
				"The trap Date And Time."
		::=  {  rbTrapEventLogEntry  10  }


	rbTrapAlarmLogTable	OBJECT-TYPE
		SYNTAX		SEQUENCE  OF  RbTrapAlarmLogEntry
		MAX-ACCESS	not-accessible
		STATUS		current
		DESCRIPTION	
			"This table containes trap information for all alarms.
			 For traps that are not active the trapAlarmLogAddVarAttributes is NA."
		::=  { rbAuthorizationAndTraps 22 }

	rbTrapAlarmLogEntry	OBJECT-TYPE
		SYNTAX		RbTrapAlarmLogEntry
		MAX-ACCESS	not-accessible
		STATUS		current
		DESCRIPTION	
			"Table entry"
		INDEX		{  trapAlarmLogAlarmId, trapAlarmLogSource, trapAlarmLogSlotId  }
		::=  { rbTrapAlarmLogTable 1 }

	RbTrapAlarmLogEntry  ::=  SEQUENCE {
		trapAlarmLogAlarmId  	     INTEGER,
		trapAlarmLogSource  	     INTEGER,
		trapAlarmLogSlotId  	     Integer32,
		trapAlarmLogEventId 	     Integer32,
		trapAlarmLogName             DisplayString,
		trapAlarmLogSeverity         TrapSeverity,
		trapAlarmLogCategory 	     INTEGER,
		trapAlarmLogStrOn 		     DisplayString,
		trapAlarmLogVarBindNumber    Integer32,
		trapAlarmLogVarBindSize		 Integer32,
		trapAlarmLogAddVarAttributes DisplayString,
		trapAlarmLogLed              INTEGER
		}

	trapAlarmLogAlarmId	OBJECT-TYPE	
		SYNTAX			INTEGER
		                {
			             npuEthConn          (1),
			             npuMngConn          (2),
			             npuAuConn           (3),
			             auRlinkLoss         (4),
			             npuLciUnauthAcc     (5),
			             npuTelnetUnauthAcc  (6),
			             bitFailed           (7),
			             npuLciAccess        (8),
			             npuTelnetAccess     (9),
			             npuReset            (10),
			             swDnl               (11),
			             swDnlFail           (12),
			             swDnlSwitch         (13),
			             bstCard             (14),
			             bstPerFault         (15),
			             bstEnvFault         (16),
			             service             (17),			  
			             bstExt1PPSFault     (18),			  
			             bstInt1PPSFault     (19),			  
			             bstExt16MHzFault    (20),			  
			             bstInt16MHzFault    (21),			  
			             bstGpsComFault      (22),			  
			             bstGpsHealthFault   (23),			  
			             bstGpsNumSatsFault  (24),			  
			             authSrvKeepAliveFault (25),			  
			             acctSrvKeepAliveFault (26),			  
			             auModeConflict      (27),			  
			             auOduComError       (28),			  
			             auOduBandMismatch   (29),			  
			             auExt1PPSFault      (30),			  
			             auHoldOverEntered   (31),			  
			             auHoldOverTOPassed  (32)			  
						}
	
		MAX-ACCESS		read-only
		STATUS			current
		DESCRIPTION		
				"The alarm type."
		::=  {  rbTrapAlarmLogEntry  1  }

	trapAlarmLogSource	OBJECT-TYPE	
		SYNTAX			INTEGER
		                {
			             npu     (1),
			             au      (2),
			             su      (3),
			             bs      (4),
			             psu     (5),
			             piu     (6),
			             acu     (7),
			             service (8)			  
						}
		MAX-ACCESS		read-only
		STATUS			current
		DESCRIPTION		
				"The alarm source."
		::=  {  rbTrapAlarmLogEntry  2  }

	trapAlarmLogSlotId	OBJECT-TYPE	
		SYNTAX			Integer32 ( 1..9 )
		MAX-ACCESS		read-only
		STATUS			current
		DESCRIPTION		
				"The alarm card slot id.
				 Slot 5-6 are allowed for NPU card, although in the current version NPU can be used only in slot 5.
				 Slots 1-4, 7-9 are allowed for AU card.
				 Slots 1-4 are allowed for PSU card.
				 Slots 1-2 are allowed for PIU card.
				 Slot 1 is allowed for ACU card." 
		::=  {  rbTrapAlarmLogEntry  3  }

	trapAlarmLogEventId	OBJECT-TYPE	
		SYNTAX			Integer32 
		MAX-ACCESS		read-only
		STATUS			current
		DESCRIPTION		
				"The trap ID defined in the TRAP-TYPE macro.
				 For standard SNMP traps, the proprietary trap IDs are:
                 ColdStart - 128
                 WarmStart - 129
                 LinkDown  - 130
                 LinkUp    - 131
                 AuthenticationFailure - 132." 
		::=  {  rbTrapAlarmLogEntry  4  }

	trapAlarmLogName	OBJECT-TYPE	
		SYNTAX			DisplayString 
		MAX-ACCESS		read-only
		STATUS			current
		DESCRIPTION		
				"The representing trap name."
		::=  {  rbTrapAlarmLogEntry  5  }
    
	trapAlarmLogSeverity	OBJECT-TYPE	
		SYNTAX			TrapSeverity 
		MAX-ACCESS		read-only
		STATUS			current
		DESCRIPTION		
				"The trap severity."
		::=  {  rbTrapAlarmLogEntry  6  }

    trapAlarmLogCategory	OBJECT-TYPE	
		SYNTAX			INTEGER
		                {
			             none             (0),
			             communications   (1),
			             qualityOfService (2),
			             processingError  (3),
			             equipment        (4),
			             environmental    (5)			  
						}
		MAX-ACCESS		read-only
		STATUS			current
		DESCRIPTION		
				"The trap category according to the X.733." 
		::=  {  rbTrapAlarmLogEntry  7  }

	trapAlarmLogStrOn	OBJECT-TYPE	
		SYNTAX			DisplayString 
		MAX-ACCESS		read-only
		STATUS			current
		DESCRIPTION		
				"The representing trap string."
		::=  {  rbTrapAlarmLogEntry  8  }
    
	trapAlarmLogVarBindNumber	OBJECT-TYPE	
		SYNTAX			Integer32 
		MAX-ACCESS		read-only
		STATUS			current
		DESCRIPTION		
				"The trap Variable Bind Number."
		::=  {  rbTrapAlarmLogEntry  9  }
    
	trapAlarmLogVarBindSize	OBJECT-TYPE	
		SYNTAX			Integer32 
		MAX-ACCESS		read-only
		STATUS			current
		DESCRIPTION		
				"The trap Variable Bind Size."
		::=  {  rbTrapAlarmLogEntry  10  }

	trapAlarmLogAddVarAttributes	OBJECT-TYPE	
		SYNTAX			DisplayString 
		MAX-ACCESS		read-only
		STATUS			current
		DESCRIPTION		
				"The trap Variable Attributes Additional information.
				 NA is used for inactive Alarms."
		::=  {  rbTrapAlarmLogEntry  11  }

	trapAlarmLogLed	OBJECT-TYPE	
		SYNTAX			INTEGER
		                {
			             none      (0),
			             led	   (1),
			             ledBst    (2)			  
						}
		MAX-ACCESS		read-only
		STATUS			current
		DESCRIPTION		
				"The NPU LEDs associated with alarm. Not applicable for current version."
		::=  {  rbTrapAlarmLogEntry  12  }


--========================================================================
--     Interfaces  
--========================================================================
    rbInterfaces			OBJECT IDENTIFIER ::=  {  rainbow  7  }
    rbEthernetInterface		OBJECT IDENTIFIER ::=  {  rbInterfaces  1 }
	rbAirInterface			OBJECT IDENTIFIER ::=  {  rbInterfaces  2 }

--========================================================================
--     Ethernet Interface  
--========================================================================

	rbEthIfConfigTable	OBJECT-TYPE
		SYNTAX		SEQUENCE  OF  RbEthIfConfigEntry
		MAX-ACCESS	not-accessible
		STATUS		current
		DESCRIPTION	
			"This table contains Ethernet interface configuration parameters.
			 To receive the Ethernet Interface configuration to a specific SU, community 
			 <com>@SU.<MacAddress> should be used."
		::=  { rbEthernetInterface 1 }

	rbEthIfConfigEntry	OBJECT-TYPE
		SYNTAX		RbEthIfConfigEntry
		MAX-ACCESS	not-accessible
		STATUS		current
		DESCRIPTION	
			"Table entry"
		INDEX		{  ethConfigIfIndex  }
		::=  { rbEthIfConfigTable 1 }

	RbEthIfConfigEntry  ::=  SEQUENCE {
		ethConfigIfIndex  	  				Integer32,
		ethConfigAutoNegotiation			INTEGER,	
		ethConfigLinkSpeedAndDuplex     	LinkSpeedAndDuplex,
		ethConfigCurrentdAutoNegotiation   	INTEGER,
		ethConfigCurrentLinkSpeedAndDuplex	LinkSpeedAndDuplex
		}


	ethConfigIfIndex	OBJECT-TYPE	
		SYNTAX			Integer32 ( 1 .. 2 )
		MAX-ACCESS		read-only
		STATUS			current
		DESCRIPTION		
				"Index of Ethernet Interface. In NPU and Micro Base Station,
				 1 is for the DATA port and 2 is for the MGMT port.
				 In SU, 1 is for the ETHERNET port and 2 is not applicable." 
		::=  {  rbEthIfConfigEntry  1  }

	ethConfigAutoNegotiation	OBJECT-TYPE	
		SYNTAX			INTEGER {
		                          enable  (1),
		                          disable (2)
		                        }    
		MAX-ACCESS		read-write
		STATUS			current
		DESCRIPTION		
				"The Auto Negotiation mode that will be active after the reset.
				 Not applicable for NPU ports." 
		::=  {  rbEthIfConfigEntry  2  }

	ethConfigLinkSpeedAndDuplex	OBJECT-TYPE	
		SYNTAX			LinkSpeedAndDuplex 
		MAX-ACCESS		read-write
		STATUS			current
		DESCRIPTION		
                "The configured Speed and Duplex that will be in effect after the next reset.
                 Applicable only if Auto Negotiation is Disabled. The applicable options are:
                 In NPU Data port - 100 Mbps Full Duplex, 1 Gbps Full Duplex.
                 In NPU Management port - Not Applicable (Auto Negotiation always Enabled).
                 In Micro Base Station Data and Management ports - 10 Mbps Half Duplex,
                 10 Mbps Full Duplex, 100 Mbps Half Duplex, 100 Mbps Full Duplex."
	::=  {  rbEthIfConfigEntry 3  }

	ethConfigCurrentdAutoNegotiation	OBJECT-TYPE	
		SYNTAX			INTEGER {
		                          enable  (1),
		                          disable (2)
		                        }    
		MAX-ACCESS		read-only
		STATUS			current
		DESCRIPTION		
				"The current Auto Negotiation mode (enabled/disabled).
				 In NPU, DATA port is always disabled, MGMT port is always enabled." 
		::=  {  rbEthIfConfigEntry 4  }

	ethConfigCurrentLinkSpeedAndDuplex	OBJECT-TYPE	
		SYNTAX			LinkSpeedAndDuplex 
		MAX-ACCESS		read-only
		STATUS			current
		DESCRIPTION		
				"When Auto Negotiation is disabled, this is the current Speed and Duplex.
				 When Auto Negotiation is enabled, this is the detected Speed and Duplex."
	  	::=  {  rbEthIfConfigEntry 5  }


--========================================================================
--     Air Interface  
--========================================================================
  rbAuMacParameters        OBJECT IDENTIFIER ::=  { rbAirInterface 1 }
  rbSuMacParameters	       OBJECT IDENTIFIER ::=  { rbAirInterface 2 }
  rbAuMultirateParameters  OBJECT IDENTIFIER ::=  { rbAirInterface 3 }
  rbAuATPCParameters       OBJECT IDENTIFIER ::=  { rbAirInterface 4 }
  rbSuMultirateParameters  OBJECT IDENTIFIER ::=  { rbAirInterface 5 }
  rbSuATPCParameters       OBJECT IDENTIFIER ::=  { rbAirInterface 6 }
  rbAuPhyParameters	       OBJECT IDENTIFIER ::=  { rbAirInterface 7 }
  rbSuPhyParameters	       OBJECT IDENTIFIER ::=  { rbAirInterface 9 }
  rbSuBestBstAuParams      OBJECT IDENTIFIER ::=  { rbAirInterface 10 }
  rbSuRadioParameters      OBJECT IDENTIFIER ::=  { rbAirInterface 11 }

--==================================================================
--     AU MAC Parameters  
-- AU MAC Parameters are retrieved using community <com>@AU.<slot #>
--==================================================================

    rbAuBaseStationId	 OBJECT-TYPE
		SYNTAX			OCTET STRING (SIZE(6)) 
		MAX-ACCESS		read-only
		STATUS			current
		DESCRIPTION		
				"The current Base Station ID. The Base Station ID consists of 6 octets.
				 The first 3 octets are the Operator ID, the next two octets are 
				 the Cell ID and the sixth octet is the AU/Micro Base Station ID."
		::=  {  rbAuMacParameters 1}

	rbAuMaxCellRadius	OBJECT-TYPE	
		SYNTAX			Integer32 (5..110)
		MAX-ACCESS		read-write
		STATUS			current
		DESCRIPTION		
				"The maximum cell radius (the distance of the farthest SU that should be served by the base station)in km.
				 The defaults are
				 BW=1.75MHz, Max Cell Radius = 10 to 110Km (FDD mode).
                 BW=3.5MHz,  Max Cell Radius = 10 to 110Km (FDD mode). 
				 BW=1.75MHz, Max Cell Radius = 10 to 50Km  (TDD mode).
                 BW=3.5MHz,  Max Cell Radius = 10 to 50Km  (TDD mode). 
                 BW=5MHz,    Max Cell Radius = 7 to 45Km   (TDD mode).  
                 BW=7MHz,    Max Cell Radius = 5 to 55Km   (TDD mode).
                 BW=10MHz,   Max Cell Radius = 7 to 45Km   (TDD mode).   
				 The range is from Min Cell Radius up to Max Cell Radius allowed for each band with 1Km selection granularity."
        DEFVAL {20}
		::=  {  rbAuMacParameters 2  }

    rbAuConfiguredBaseStationId	 OBJECT-TYPE
		SYNTAX			OCTET STRING (SIZE(6)) 
		MAX-ACCESS		read-write
		STATUS			current
		DESCRIPTION		
				"Unique Base Station ID that will be in use after the reset.
				 For version 2.0 and higher this is a read only parameter."
		::=  {  rbAuMacParameters 3}

    rbAuARQState 	 OBJECT-TYPE
		SYNTAX			INTEGER
		                {
						  enable  (1),
						  disable (2)
		                } 
		MAX-ACCESS		read-only
		STATUS			current
		DESCRIPTION		
				"Current ARQ state."
		::=  {  rbAuMacParameters 4 }

    rbAuConfiguredARQState 	 OBJECT-TYPE
		SYNTAX			INTEGER
		                {
						  enable  (1),
						  disable (2)
		                } 
		MAX-ACCESS		read-write
		STATUS			current
		DESCRIPTION		
				"ARQ state that will be in effect after the next reset."
		::=  {  rbAuMacParameters 5 }

    rbAuConfiguredSectorId	 OBJECT-TYPE
		SYNTAX			OCTET STRING (SIZE(1)) 
		MAX-ACCESS		read-write
		STATUS			current
		DESCRIPTION		
				"Unique AU Sector ID."
		::=  {  rbAuMacParameters 6 }

	rbAuCurrentMaxCellRadius	OBJECT-TYPE	
		SYNTAX			Integer32 (5..110)
		MAX-ACCESS		read-only
		STATUS			current
		DESCRIPTION		
				"The maximum cell radius supported by the AU, in km."
		::=  {  rbAuMacParameters 7 }


--==================================================================
--     SU MAC Parameters  
-- SU MAC Parameters are retrieved using community <com>@SU.<MacAddress>
-- Available only for SUs using Standard Operation Mode (Air Interface type a)
--==================================================================
    rbSuBaseStationId	 OBJECT-TYPE
		SYNTAX			OCTET STRING (SIZE(6)) 
		MAX-ACCESS		read-only
		STATUS			current
		DESCRIPTION		
				"The current Base Station ID.
				 Together with rbSuBaseStationIdMask it defines the AUs to which the SU is allowed to connect."
		::=  {  rbSuMacParameters 1 }

    rbSuBaseStationIdMask	 OBJECT-TYPE
		SYNTAX			OCTET STRING (SIZE(6)) 
		MAX-ACCESS		read-only
		STATUS			current
		DESCRIPTION		
				"The matching criteria for the define Base Station Id."
		::=  {  rbSuMacParameters 2 }

    rbSuConfiguredBaseStationId	 OBJECT-TYPE
		SYNTAX			OCTET STRING (SIZE(6)) 
		MAX-ACCESS		read-write
		STATUS			current
		DESCRIPTION		
				"The Base Station ID that will be in use after the next reset."
		::=  {  rbSuMacParameters 3 }

    rbSuConfiguredBaseStationIdMask	 OBJECT-TYPE
		SYNTAX			OCTET STRING (SIZE(6)) 
		MAX-ACCESS		read-write
		STATUS			current
		DESCRIPTION		
				"The matching criteria for the define Base Station Id that will be in use
				 after the next reset."
		::=  {  rbSuMacParameters 4 }


--==================================================================
--     AU Multi-rate parameters  
-- AU Multi-rate parameters are retrieved using community <com>@AU.<slot #>
--==================================================================
	rbAuMultirateSupport	OBJECT-TYPE	
		SYNTAX			INTEGER	{
		                          enabled  (1),	
		                          disabled (2),
		                          notDefined (3)
								 }
		MAX-ACCESS		read-write
		STATUS			current
		DESCRIPTION		
				"This parameter defines if Multi-rate mechanism is supported
				 by AU. After each reset AU boots with Multirate Support enabled."
		::=  {  rbAuMultirateParameters  1  }

	rbAuUlBasicRate	 OBJECT-TYPE
		SYNTAX			Modulation 
		MAX-ACCESS		read-write
		STATUS			current
		DESCRIPTION		
				"The lowest modulation SU will use."
		DEFVAL			{ 1 }
		::=  {  rbAuMultirateParameters  2  }

	rbAuDlBasicRate	 OBJECT-TYPE
		SYNTAX			Modulation 
		MAX-ACCESS		read-write
		STATUS			current
		DESCRIPTION		
				"The lowest modulation AU will use."
		DEFVAL			{ 1 }
		::=  {  rbAuMultirateParameters  3  }

	rbAuUlMinNoOfSubChannels	OBJECT-TYPE	
		SYNTAX			Integer32 ( 1 .. 16 )
		MAX-ACCESS		read-write
		STATUS			current
		DESCRIPTION		
				"Applicable only if the Uplink Basic Rate is BPSK 1/2 (rbAuUlBasicRate is 1).
				 The Minimum Number of Subchannels to be used by the Multi Rate algorithm in the Uplink.
				 This is also the number of Sub Channels to be used in the Uplink for non-scheduled
				 transmissions (if the Basic Uplink Rate is BPSK 1/2). Options: 1, 2, 4, 8, 16 Sub-Channels."
		DEFVAL			{ 16 }
		::=  {  rbAuMultirateParameters  4  }


--==================================================================
--     AU ATPC Parameters  
-- AU ATPC Parameters are retrieved using community <com>@AU.<slot #>
--==================================================================

	rbAuATPCSupport	OBJECT-TYPE	
		SYNTAX			INTEGER	{
		                          enabled  (1),		  
								  disabled (2),
								  notDefined (3)
								 }
		MAX-ACCESS		read-write
		STATUS			current
		DESCRIPTION		
				"This parameter defines if ATPC mechanism is supported
				 by AU. After each reset AU boots with ATPC enabled.
				 For version 2.0 and higher this is a read-only parameter."
		::=  {  rbAuATPCParameters  1  }
    
	rbAuOptimalRSSI	 OBJECT-TYPE
		SYNTAX			Integer32 (-90..-60)  
		MAX-ACCESS		read-write
		STATUS			current
		DESCRIPTION		
				"The RSSI in dBm required from all SUs.
				 For version 2.0 and higher this is a read-only parameter."
		::=  {  rbAuATPCParameters 2 }


--==================================================================
--     SU Multi-rate parameters  
-- SU Multi-rate parameters are retrieved using community <com>@SU.<MacAddress>
--==================================================================
	rbSuTxPower	 OBJECT-TYPE
		SYNTAX			DisplayString  
		MAX-ACCESS		read-only
		STATUS			current
		DESCRIPTION		
				"The last transmit power in dBm."
		::=  {  rbSuMultirateParameters 1 }

    rbSuUlSNR	 OBJECT-TYPE
		SYNTAX			DisplayString 
		MAX-ACCESS		read-only
		STATUS			current
		DESCRIPTION		
				"The SNR in dB of the last burst received from the SU."
		::=  {  rbSuMultirateParameters 3 }

    rbSuUlRSSI	 OBJECT-TYPE
		SYNTAX			DisplayString 
		MAX-ACCESS		read-only
		STATUS			current
		DESCRIPTION		
				"The RSSI in dBm of the last burst received from the SU."
		::=  {  rbSuMultirateParameters 4 }

    rbSuUlCurrentRate	 OBJECT-TYPE
		SYNTAX			Modulation
		MAX-ACCESS		read-write
		STATUS			current
		DESCRIPTION		
				"The last uplink rate used by the Multirate mechanism.
				 When Multirate is enabled, this parameter is read-only.
				 If Multirate in the AU is disabled, this parameter becomes read-write,
				 enabling to set a fixed rate in the uplink."
		::=  {  rbSuMultirateParameters 5 }

    rbSuDlSNR	 OBJECT-TYPE
		SYNTAX			DisplayString 
		MAX-ACCESS		read-only
		STATUS			current
		DESCRIPTION		
				"The SNR in dB of the last burst received by the SU."
		::=  {  rbSuMultirateParameters 6 }

    rbSuDlRSSI	 OBJECT-TYPE
		SYNTAX			DisplayString 
		MAX-ACCESS		read-only
		STATUS			current
		DESCRIPTION		
				"The RSSI in dBm of the last burst received by the SU."
		::=  {  rbSuMultirateParameters 7 }

    rbSuDlCurrentRate	 OBJECT-TYPE
		SYNTAX			Modulation
		MAX-ACCESS		read-write
		STATUS			current
		DESCRIPTION		
				"The last downlink rate used by the Multirate mechanism.
				 When Multirate is enabled, this parameter is read-only.
				 If Multirate in the AU is disabled, this parameter becomes read-write,
				 enabling to set a fixed rate in the downlink."
		::=  {  rbSuMultirateParameters 8 }

    rbSuMultirateSupport	 OBJECT-TYPE
		SYNTAX			INTEGER	{
		                          enabled  (1),	
								  disabled (2),
								  notDefined (3)
								 }
		MAX-ACCESS		read-only
		STATUS			current
		DESCRIPTION		
				"This parameter indicates if Multi-rate mechanism is used
				 by associated AU."
		::=  {  rbSuMultirateParameters 9 }

	rbSuEstDistance	OBJECT-TYPE	
		SYNTAX			Unsigned32 
		MAX-ACCESS		read-only
		STATUS			current
		DESCRIPTION		
				"The estimated distance in meters from the Base Station (rounded to 100 meters).
				 Agent will return 0 if distance is unknown."
		::=  {  rbSuMultirateParameters  10  }

    rbSuUlSNRValue	 OBJECT-TYPE
		SYNTAX			TenthdB
		MAX-ACCESS		read-only
		STATUS			current
		DESCRIPTION		
				"The SNR in tenth dB units of the last burst received from the SU."
		::=  {  rbSuMultirateParameters 11 }

    rbSuUlRSSIValue	 OBJECT-TYPE
		SYNTAX			TenthdB 
		MAX-ACCESS		read-only
		STATUS			current
		DESCRIPTION		
				"The RSSI in tenth dBm units of the last burst received from the SU."
		::=  {  rbSuMultirateParameters 12 }

    rbSuDlSNRValue	 OBJECT-TYPE
		SYNTAX			TenthdB 
		MAX-ACCESS		read-only
		STATUS			current
		DESCRIPTION		
				"The SNR in thenth dB units of the last burst received by the SU."
		::=  {  rbSuMultirateParameters 13 }

    rbSuDlRSSIValue	 OBJECT-TYPE
		SYNTAX			TenthdB 
		MAX-ACCESS		read-only
		STATUS			current
		DESCRIPTION		
				"The RSSI in tenth dBm units of the last burst received by the SU."
		::=  {  rbSuMultirateParameters 14 }


--==================================================================
--     SU ATPC parameters  
-- SU ATPC parameters are retrieved using community <com>@SU.<MacAddress>
--==================================================================
	rbSuATPCSupport	OBJECT-TYPE	
		SYNTAX			INTEGER	{
		                          enabled  (1),
								  disabled (2),
								  notDefined (3)
								 }
		MAX-ACCESS		read-only
		STATUS			current
		DESCRIPTION		
				"Indicates whether ATPC is used by the SU. 
				 Typically this is controlled by the AU/Micro Base Station. 
				 ATPC can be disabled locally (via the Ethernet port of the SU, using the SU Installer Monitor)."
		::=  {  rbSuATPCParameters  1  }
    

--==================================================================
--     AU PHY Parameters 
-- AU PHY Parameters are retrieved using community <com>@AU.<slot #>
--==================================================================
	rbAuCurrentPhyBandwidth	OBJECT-TYPE	
		SYNTAX			INTEGER  { 
		                           b175 ( 1 ) ,
		                           b35  ( 2 ) , 
		                           b50  ( 3 ) , 
		                           b70  ( 4 ) , 
		                           b100 ( 5 )  
		                         } 
		MAX-ACCESS		read-only
		STATUS			current
		DESCRIPTION		
				"This parameter defines the current operating bandwidth."
		::=  {  rbAuPhyParameters  1  }

	rbAuPhyTxFrequencyChannel	OBJECT-TYPE	
		SYNTAX			DisplayString
		MAX-ACCESS		read-only
		STATUS			current
		DESCRIPTION		
				"Not applicable for Version 2 and higher.
			     This parameter defines central channel frequency in MHz."
		::=  {  rbAuPhyParameters 2  }

	rbAuPhyTxConfiguredFrequencyChannel	OBJECT-TYPE	
		SYNTAX			DisplayString
		MAX-ACCESS		read-write
		STATUS			current
		DESCRIPTION		
				"Not applicable for Version 2 and higher.
				 This parameter defines central channel frequency in MHz."
		::=  {  rbAuPhyParameters 3  }

	rbAuConfiguredPhyBandwidth	OBJECT-TYPE	
		SYNTAX			INTEGER  { 
		                           b175 ( 1 ) ,
		                           b35  ( 2 ) , 
		                           b50  ( 3 ) , 
		                           b70  ( 4 ) , 
		                           b100 ( 5 )  
		                         } 
		MAX-ACCESS		read-write
		STATUS			current
		DESCRIPTION		
				"b175 (1): 1.75 MHz
                 b35  (2): 3.5  MHz
                 b50  (3): 5    MHz
                 b70  (4): 7    MHz
                 b100 (5): 10   MHz
                 The actually available bandwidths depend on the AU's hardware and SW version.
                 A bandwidth that is not supported by the hardware and SW version will be rejected."
		::=  {  rbAuPhyParameters  4  }


	rbAuOutdoorConfigTable	OBJECT-TYPE
		SYNTAX		SEQUENCE  OF  RbAuOutdoorConfigEntry
		MAX-ACCESS	not-accessible
		STATUS		deprecated
		DESCRIPTION	
			"This table is deprecated from version 2.0.
			 This table contains AU PHY Configuration Parameters per Outdoor unit."
		::=  { rbAirInterface 8 }

	rbAuOutdoorConfigEntry	OBJECT-TYPE
		SYNTAX		RbAuOutdoorConfigEntry
		MAX-ACCESS	not-accessible
		STATUS		deprecated
		DESCRIPTION	
			"Table entry"
		INDEX		{  auOutdoorUnitIndex  }
		::=  { rbAuOutdoorConfigTable 1 }

	RbAuOutdoorConfigEntry  ::=  SEQUENCE {
		auOutdoorUnitIndex	 Integer32,
		auFrequencyBand		 INTEGER,
 	    auTxPower            DisplayString
		}

    auOutdoorUnitIndex	 OBJECT-TYPE
		SYNTAX			Integer32 (1..4)
		MAX-ACCESS		read-only
		STATUS			deprecated
		DESCRIPTION		
				"Index of outdoor unit."
		::=  {  rbAuOutdoorConfigEntry 1 }

	auFrequencyBand	OBJECT-TYPE	
		SYNTAX			INTEGER  { 
		                           bandA1  ( 1 ) ,
		                           bandB   ( 2 ) ,
		                           bandF   ( 3 ) ,
		                           bandD   ( 4 ) ,
		                           bandE   ( 5 ) ,
		                           band23  ( 12 ),
		                           band25A ( 13 ),
		                           band25B ( 14 )
	                         } 
		MAX-ACCESS		read-only
		STATUS			deprecated
		DESCRIPTION		
				"This parameter defines frequency band."
		::=  {  rbAuOutdoorConfigEntry  2  }

	auTxPower	OBJECT-TYPE	
		SYNTAX			DisplayString
		MAX-ACCESS		read-write
		STATUS			deprecated
		DESCRIPTION		
				"Working Transmit Power in dBm. The Min is 13 dBm, the Max is 28 dBm."
		::=  {  rbAuOutdoorConfigEntry  3  }


--==================================================================
--     SU PHY Parameters 
-- SU PHY Parameters are retrieved using community <com>@SU.<MacAddress>
-- Available only for SUs using Standard Operation Mode (Air Interface type a)
--==================================================================
	suPhyCurrentBandwidth	OBJECT-TYPE	
		SYNTAX			INTEGER  { 
		                           b175 ( 1 ) ,
		                           b35  ( 2 ) , 
		                           b50  ( 3 ) , 
		                           b70  ( 4 ) , 
		                           b100 ( 5 )  
		                         } 
		MAX-ACCESS		read-only
		STATUS			current
		DESCRIPTION		
				"b175 (1): 1.75 MHz
                 b35  (2): 3.5  MHz
                 b50  (3): 5    MHz
                 b70  (4): 7    MHz
                 b100 (5): 10   MHz
                 The actually available bandwidths depend on the SU's hardware and SW version.
                 A bandwidth that is not supported by the hardware and SW version will be rejected."
		::=  {  rbSuPhyParameters  1  }

	suPhyCurrentTxFrequencyChannel	OBJECT-TYPE	
		SYNTAX			DisplayString
		MAX-ACCESS		read-only
		STATUS			current
		DESCRIPTION		
				"This parameter defines the current central channel frequency in MHz."
		::=  {  rbSuPhyParameters  2 }

	suPhyConfiguredBandwidth	OBJECT-TYPE	
		SYNTAX			INTEGER  { 
		                           b175 ( 1 ) ,
		                           b35  ( 2 ) , 
		                           b50  ( 3 ) , 
		                           b70  ( 4 ) , 
		                           b100 ( 5 )  
		                         } 
		MAX-ACCESS		read-write
		STATUS			current
		DESCRIPTION		
				"This parameter defines the configured bandwidth,
				 that will be in effect	after the next reset."
		::=  {  rbSuPhyParameters  3  }

	suPhyConfiguredTxFrequencyChannel	OBJECT-TYPE	
		SYNTAX			DisplayString
		MAX-ACCESS		read-write
		STATUS			current
		DESCRIPTION		
				"This parameter defines central channel frequency in MHz.
				 In version 2.0 and higher the available values depend on 
				 the Bandwidth and on the applicable Frequency Bands Group.
				 Becomes applicable only when the SU operates using Standard Operation Mode (Air Interface type a)."
	::=  {  rbSuPhyParameters  4 }


--========================================================================
--     SU: Best BST/AU Support  (PRO CPE and SI CPE)  
-- Available only for SUs using Advanced Si Operation Mode (Air Interface type si)
--========================================================================
	rbSuBestBstAuParamsTable	OBJECT-TYPE
		SYNTAX		SEQUENCE  OF  RbSuBestBstAuParamsEntry
		MAX-ACCESS	not-accessible
		STATUS		current
		DESCRIPTION	
			"This table provides parameters information regarding the Best BST/AU Configuration and Status."
		::=  { rbSuBestBstAuParams 1 }

	rbSuBestBstAuParamsEntry 	OBJECT-TYPE
		SYNTAX		RbSuBestBstAuParamsEntry
		MAX-ACCESS	not-accessible
		STATUS		current
		DESCRIPTION	
			"Table entry"
		INDEX		{  rbSuMacAddr  }
		::=  { rbSuBestBstAuParamsTable 1 }

	RbSuBestBstAuParamsEntry  ::=  SEQUENCE {
		rbSuCurrentBestBstAuSupport  	   INTEGER,
		rbSuConfiguredBestBstAuSupport     INTEGER,
		rbSuCurrentPreferredBstAuId	   OCTET STRING,
		rbSuConfiguredPreferredBstAuId	   OCTET STRING,
		rbSuCurrentPreferredBstAuMask	   OCTET STRING,
		rbSuConfiguredPreferredBstAuMask   OCTET STRING,
		rbSuSelectedBstAu      	           OCTET STRING,
		rbSuSelectedRxFrequency      	   DisplayString,
		rbSuSelectedTxFrequency      	   DisplayString,
		rbSuCurrentBstAuId	           OCTET STRING,
		rbSuConfiguredBstAuId	           OCTET STRING,
		rbSuCurrentBstAuMask	           OCTET STRING,
		rbSuConfiguredBstAuMask            OCTET STRING
	}


	rbSuCurrentBestBstAuSupport	OBJECT-TYPE	
		SYNTAX			INTEGER  { notDefined (0) , enable ( 1 ) , disable ( 2 ) } 
		MAX-ACCESS		read-only
		STATUS			current
		DESCRIPTION		
				"Enable/Disable the feature - current value."
		::=  {  rbSuBestBstAuParamsEntry  1 }

	rbSuConfiguredBestBstAuSupport	OBJECT-TYPE	
		SYNTAX			INTEGER  { notDefined (0) , enable ( 1 ) , disable ( 2 ) } 
		MAX-ACCESS		read-write
		STATUS			current
		DESCRIPTION		
				"Enable/Disable the feature - configured value."
		::=  {  rbSuBestBstAuParamsEntry  2 }

	rbSuCurrentPreferredBstAuId	OBJECT-TYPE	
		SYNTAX			OCTET STRING (SIZE(6)) 
		MAX-ACCESS		read-only
		STATUS			current
		DESCRIPTION		
				"Define the base ID for the preferred BST/AU - current value."
		::=  {  rbSuBestBstAuParamsEntry  3 }

	rbSuConfiguredPreferredBstAuId	OBJECT-TYPE	
		SYNTAX			OCTET STRING (SIZE(6)) 
		MAX-ACCESS		read-write
		STATUS			current
		DESCRIPTION		
				"Define the base ID for the preferred BST/AU - configured value."
		::=  {  rbSuBestBstAuParamsEntry  4 }

	rbSuCurrentPreferredBstAuMask	OBJECT-TYPE	
		SYNTAX			OCTET STRING (SIZE(6)) 
		MAX-ACCESS		read-only
		STATUS			current
		DESCRIPTION		
				"The ID mask that together with the Preferred BST/AU ID defines
				 a range of preferred BST/AUs - current value."
		::=  {  rbSuBestBstAuParamsEntry  5 }

	rbSuConfiguredPreferredBstAuMask	OBJECT-TYPE	
		SYNTAX			OCTET STRING (SIZE(6)) 
		MAX-ACCESS		read-write
		STATUS			current
		DESCRIPTION		
				"The ID mask that together with the Preferred BST/AU ID defines
				 a range of preferred BST/AUs - configured value."
		::=  {  rbSuBestBstAuParamsEntry  6 }

	rbSuSelectedBstAu	OBJECT-TYPE	
		SYNTAX			OCTET STRING (SIZE(6)) 
		MAX-ACCESS		read-only
		STATUS			current
		DESCRIPTION		
				"The selected BST/AU ID."
		::=  {  rbSuBestBstAuParamsEntry  7 }

	rbSuSelectedRxFrequency	OBJECT-TYPE	
		SYNTAX			DisplayString 
		MAX-ACCESS		read-only
		STATUS			current
		DESCRIPTION		
				"The selected Rx Frequency, in MHz."
		::=  {  rbSuBestBstAuParamsEntry  8 }

	rbSuSelectedTxFrequency	OBJECT-TYPE	
		SYNTAX			DisplayString 
		MAX-ACCESS		read-only
		STATUS			current
		DESCRIPTION		
				"The selected Tx Frequency, in MHz."
		::=  {  rbSuBestBstAuParamsEntry 9 }

	rbSuCurrentBstAuId	OBJECT-TYPE	
		SYNTAX			OCTET STRING (SIZE(6)) 
		MAX-ACCESS		read-only
		STATUS			current
		DESCRIPTION		
				"Define the base ID for the BST/AU - current value."
		::=  {  rbSuBestBstAuParamsEntry  10 }

	rbSuConfiguredBstAuId	OBJECT-TYPE	
		SYNTAX			OCTET STRING (SIZE(6)) 
		MAX-ACCESS		read-write
		STATUS			current
		DESCRIPTION		
				"Define the base ID for the BST/AU - configured value."
		::=  {  rbSuBestBstAuParamsEntry  11 }

	rbSuCurrentBstAuMask	OBJECT-TYPE	
		SYNTAX			OCTET STRING (SIZE(6)) 
		MAX-ACCESS		read-only
		STATUS			current
		DESCRIPTION		
				"The ID mask that together with the BST/AU ID defines
				 a range of BST/AUs - current value."
		::=  {  rbSuBestBstAuParamsEntry  12 }

	rbSuConfiguredBstAuMask	OBJECT-TYPE	
		SYNTAX			OCTET STRING (SIZE(6)) 
		MAX-ACCESS		read-write
		STATUS			current
		DESCRIPTION		
				"The ID mask that together with the BST/AU ID defines
				 a range of BST/AUs - configured value."
		::=  {  rbSuBestBstAuParamsEntry  13 }


--========================================================================

	rbSuBestBstAuDataTable	OBJECT-TYPE
		SYNTAX		SEQUENCE  OF  RbSuBestBstAuDataEntry
		MAX-ACCESS	not-accessible
		STATUS		current
		DESCRIPTION	
			"This table provides parameters information regarding the Best BST/AU Scanning Results.
			 Includes parameters for all relevant AUs that were found in the scanning process."
		::=  { rbSuBestBstAuParams 2 }

	rbSuBestBstAuDataEntry 	OBJECT-TYPE
		SYNTAX		RbSuBestBstAuDataEntry
		MAX-ACCESS	not-accessible
		STATUS		current
		DESCRIPTION	
			"Table entry"
		INDEX		{  rbSuMacAddr, rbBstAuIndx  }
		::=  { rbSuBestBstAuDataTable 1 }

	RbSuBestBstAuDataEntry  ::=  SEQUENCE {
		rbBstAuIndx					Integer32,
		rbBstAuId  		            OCTET STRING,
		rbBstAuRxFrequency	  	    DisplayString,
		rbBstAuSNR	  	            TenthdB,
		rbBstAuRxAntennaNumber      INTEGER
	}


	rbBstAuIndx	OBJECT-TYPE	
		SYNTAX			Integer32  ( 1 .. 6 )   
		MAX-ACCESS		read-only
		STATUS			current
		DESCRIPTION		
				"The table index"
		::=  {  rbSuBestBstAuDataEntry  1 }

	rbBstAuId	OBJECT-TYPE	
		SYNTAX			OCTET STRING (SIZE(6)) 
		MAX-ACCESS		read-only
		STATUS			current
		DESCRIPTION		
				"The BST/AU ID."
		::=  {  rbSuBestBstAuDataEntry  2 }

	rbBstAuRxFrequency	OBJECT-TYPE	
		SYNTAX			DisplayString 
		MAX-ACCESS		read-only
		STATUS			current
		DESCRIPTION		
				"The BST/AU's downlink frequency."
		::=  {  rbSuBestBstAuDataEntry  3 }

	rbBstAuSNR	OBJECT-TYPE	
		SYNTAX			TenthdB 
		MAX-ACCESS		read-only
		STATUS			current
		DESCRIPTION		
				"The SNR of the signal that was received at the SU side."
		::=  {  rbSuBestBstAuDataEntry  4 }

	rbBstAuRxAntennaNumber	OBJECT-TYPE	
		SYNTAX			INTEGER  { unknown   ( 0 ) ,
                                   internal1 ( 1 ) ,
                                   internal2 ( 2 ) ,
								   internal3 ( 3 ) ,
                                   internal4 ( 4 ) ,
                                   internal5 ( 5 ) ,
								   internal6 ( 6 ) ,
                                   external  ( 7 ) ,
                                   automatic ( 8 ) 
		                         } 
		MAX-ACCESS		read-only
		STATUS			current
		DESCRIPTION		
				"The Rx Antenna Number."
		::=  {  rbSuBestBstAuDataEntry 5  }


--========================================================================
--     SU: Radio Parameters  (PRO CPE and SI CPE)  
-- Available only for SUs using Advanced Si Operation Mode (Air Interface type si)
--========================================================================
    rbSuRadioParametersTable	OBJECT-TYPE 
		SYNTAX		SEQUENCE  OF  RbSuRadioParametersEntry
		MAX-ACCESS	not-accessible
		STATUS		current
		DESCRIPTION	
			"This table provides parameters information regarding the Best BST/AU Frequency Scanning Parameters."
		::=  { rbSuRadioParameters 1 }

	rbSuRadioParametersEntry 	OBJECT-TYPE
		SYNTAX		RbSuRadioParametersEntry
		MAX-ACCESS	not-accessible
		STATUS		current
		DESCRIPTION	
			"Table entry"
		INDEX		{  rbSuMacAddr  }
		::=  { rbSuRadioParametersTable 1 }

	RbSuRadioParametersEntry  ::=  SEQUENCE {
		rbSuCurrentScanStartFreq      DisplayString,
		rbSuConfiguredScanStartFreq   DisplayString,
		rbSuCurrentScanEndFreq        DisplayString,
		rbSuConfiguredScanEndFreq     DisplayString,
		rbSuCurrentScanStep 	      DisplayString,
		rbSuConfiguredScanStep 	      DisplayString,
		rbSuCurrentScanMask           OCTET STRING,
		rbSuConfiguredScanMask        OCTET STRING,
		rbSuDiscreteF1                DisplayString,
		rbSuDiscreteF2                DisplayString,
		rbSuDiscreteF3                DisplayString,
		rbSuDiscreteF4                DisplayString,
		rbSuDiscreteF5                DisplayString,
		rbSuDiscreteF6                DisplayString,
		rbSuDiscreteF7                DisplayString,
		rbSuDiscreteF8                DisplayString,
		rbSuDiscreteF9                DisplayString,
		rbSuDiscreteF10               DisplayString,
		rbSuCurrentBandwidth          INTEGER,
		rbSuConfiguredBandwidth       INTEGER
	}


	rbSuCurrentScanStartFreq	OBJECT-TYPE	
		SYNTAX			DisplayString ( SIZE ( 0 .. 10 ) )
		MAX-ACCESS		read-only
		STATUS			current
		DESCRIPTION		
				"First frequency to be used by the scanning process - current value."
		::=  {  rbSuRadioParametersEntry  1 }

	rbSuConfiguredScanStartFreq	OBJECT-TYPE	
		SYNTAX			DisplayString ( SIZE ( 0 .. 10 ) )
		MAX-ACCESS		read-write
		STATUS			current
		DESCRIPTION		
				"First frequency to be used by the scanning process - configured value."
		::=  {  rbSuRadioParametersEntry  2 }

	rbSuCurrentScanEndFreq	OBJECT-TYPE	
		SYNTAX			DisplayString ( SIZE ( 0 .. 10 ) )
		MAX-ACCESS		read-only
		STATUS			current
		DESCRIPTION		
				"End frequency to be used by the scanning process - current value."
		::=  {  rbSuRadioParametersEntry  3 }

	rbSuConfiguredScanEndFreq	OBJECT-TYPE	
		SYNTAX			DisplayString ( SIZE ( 0 .. 10 ) )
		MAX-ACCESS		read-write
		STATUS			current
		DESCRIPTION		
				"End frequency to be used by the scanning process - configured value."
		::=  {  rbSuRadioParametersEntry  4 }

	rbSuCurrentScanStep	OBJECT-TYPE	
		SYNTAX			DisplayString ( SIZE ( 0 .. 10 ) )
		MAX-ACCESS		read-only
		STATUS			current
		DESCRIPTION		
				"The scanning step in MHz- current value."
		::=  {  rbSuRadioParametersEntry  5 }

	rbSuConfiguredScanStep	OBJECT-TYPE	
		SYNTAX			DisplayString ( SIZE ( 0 .. 10 ) )
		MAX-ACCESS		read-write
		STATUS			current
		DESCRIPTION		
				"The scanning step in MHz- configured value.
				 Resolution: 125 KHz step up to 1.75MHz for bandwith multiple of 1.75 and
				 up to 5MHz for bandwith multiple of 2.5.
				 Default for bandwith multiple of 1.75: 875 KHz.
				 Default for bandwith multiple of 2.5: 2.5 MHz."
		::=  {  rbSuRadioParametersEntry  6 }

	rbSuCurrentScanMask	OBJECT-TYPE	
		SYNTAX			OCTET STRING (SIZE(1)) 
		MAX-ACCESS		read-only
		STATUS			current
		DESCRIPTION		
				"This is a bit-mask field: 00-FF. 
				 Allow scanning none standard frequencies that cannot be found by original Scan Steps - current value."
		::=  {  rbSuRadioParametersEntry  7 }

	rbSuConfiguredScanMask	OBJECT-TYPE	
		SYNTAX			OCTET STRING (SIZE(1)) 
		MAX-ACCESS		read-write
		STATUS			current
		DESCRIPTION		
				"This is a bit-mask field: 00-FF.
				 Allow scanning none standard frequencies that cannot be found by original Scan Steps - configured value.
                 Bit 0: Steps of 0 MHz (Start Frequency only).
                 Bit 1: Steps of 0.125 MHz.
                 Bit 2: Steps of 0.250 MHz.
                 Bit 3: Steps of 0.375 MHz.
                 Bit 4: Steps of 0.500 MHz.
                 Bit 5: Steps of 0.625 MHz.
                 Bit 6: Steps of 0.750 MHz.
				 Bit 7: Steps of 0.875 MHz for bandwidth multiple of 1.75. 
				 Bit 7: Steps of 1.250 MHz for bandwidth multiple of 2.5."
		::=  {  rbSuRadioParametersEntry  8 }

	rbSuDiscreteF1	OBJECT-TYPE	
		SYNTAX			DisplayString ( SIZE ( 0 .. 10 ) )
		MAX-ACCESS		read-only
		STATUS			current
		DESCRIPTION		
				"Su Discrete 1st Frequency. 0(Null) means frequency is not configured."
		::=  {  rbSuRadioParametersEntry  9 }

	rbSuDiscreteF2	OBJECT-TYPE	
		SYNTAX			DisplayString ( SIZE ( 0 .. 10 ) )
		MAX-ACCESS		read-only
		STATUS			current
		DESCRIPTION		
				"Su Discrete 2nd Frequency. 0(Null) means frequency is not configured."
		::=  {  rbSuRadioParametersEntry  10 }

	rbSuDiscreteF3	OBJECT-TYPE	
		SYNTAX			DisplayString ( SIZE ( 0 .. 10 ) )
		MAX-ACCESS		read-only
		STATUS			current
		DESCRIPTION		
				"Su Discrete 3rd Frequency. 0(Null) means frequency is not configured."
		::=  {  rbSuRadioParametersEntry  11 }

	rbSuDiscreteF4	OBJECT-TYPE	
		SYNTAX			DisplayString ( SIZE ( 0 .. 10 ) )
		MAX-ACCESS		read-only
		STATUS			current
		DESCRIPTION		
				"Su Discrete 4th Frequency. 0(Null) means frequency is not configured."
		::=  {  rbSuRadioParametersEntry  12 }

	rbSuDiscreteF5	OBJECT-TYPE	
		SYNTAX			DisplayString ( SIZE ( 0 .. 10 ) )
		MAX-ACCESS		read-only
		STATUS			current
		DESCRIPTION		
				"Su Discrete 5th Frequency. 0(Null) means frequency is not configured."
		::=  {  rbSuRadioParametersEntry  13 }

	rbSuDiscreteF6	OBJECT-TYPE	
		SYNTAX			DisplayString ( SIZE ( 0 .. 10 ) )
		MAX-ACCESS		read-only
		STATUS			current
		DESCRIPTION		
				"Su Discrete 6th Frequency. 0(Null) means frequency is not configured."
		::=  {  rbSuRadioParametersEntry  14 }

	rbSuDiscreteF7	OBJECT-TYPE	
		SYNTAX			DisplayString ( SIZE ( 0 .. 10 ) )
		MAX-ACCESS		read-only
		STATUS			current
		DESCRIPTION		
				"Su Discrete 7th Frequency. 0(Null) means frequency is not configured."
		::=  {  rbSuRadioParametersEntry  15 }

	rbSuDiscreteF8	OBJECT-TYPE	
		SYNTAX			DisplayString ( SIZE ( 0 .. 10 ) )
		MAX-ACCESS		read-only
		STATUS			current
		DESCRIPTION		
				"Su Discrete 8th Frequency. 0(Null) means frequency is not configured."
		::=  {  rbSuRadioParametersEntry  16 }

	rbSuDiscreteF9	OBJECT-TYPE	
		SYNTAX			DisplayString ( SIZE ( 0 .. 10 ) )
		MAX-ACCESS		read-only
		STATUS			current
		DESCRIPTION		
				"Su Discrete 9th Frequency. 0(Null) means frequency is not configured."
		::=  {  rbSuRadioParametersEntry  17 }

	rbSuDiscreteF10	OBJECT-TYPE	
		SYNTAX			DisplayString ( SIZE ( 0 .. 10 ) )
		MAX-ACCESS		read-only
		STATUS			current
		DESCRIPTION		
				"Su Discrete 10th Frequency. 0(Null) means frequency is not configured."
		::=  {  rbSuRadioParametersEntry  18 }

	rbSuCurrentBandwidth	OBJECT-TYPE	
		SYNTAX			INTEGER  { 
		                           b175 ( 1 ) ,
		                           b35  ( 2 ) , 
		                           b50  ( 3 ) , 
		                           b70  ( 4 ) , 
		                           b100 ( 5 )  
		                         } 
		MAX-ACCESS		read-only
		STATUS			current
		DESCRIPTION		
				"b175 (1): 1.75 MHz
                 b35  (2): 3.5  MHz
                 b50  (3): 5    MHz
                 b70  (4): 7    MHz
                 b100 (5): 10   MHz
                 The actually available bandwidths depend on the SU's hardware and SW version.
                 A bandwidth that is not supported by the hardware and SW version will be rejected."
		::=  {  rbSuRadioParametersEntry  19  }

	rbSuConfiguredBandwidth	OBJECT-TYPE	
		SYNTAX			INTEGER  { 
		                           b175 ( 1 ) ,
		                           b35  ( 2 ) , 
		                           b50  ( 3 ) , 
		                           b70  ( 4 ) , 
		                           b100 ( 5 )  
		                         } 
		MAX-ACCESS		read-write
		STATUS			current
		DESCRIPTION		
				"This parameter defines the configured bandwidth,
                 that will be in effect after the next reset."
		::=  {  rbSuRadioParametersEntry  20  }


--========================================================================
--     Testing  
--========================================================================
    rbTesting		OBJECT IDENTIFIER ::=  {  rainbow    8  }
	rbBerTest		OBJECT IDENTIFIER ::=  {  rbTesting  1  }

--========================================================================
--     BER Test Setup  
-- Not supported in current version. 
-- SU BER Test Setup is retrieved using community <com>@SU.<MacAddress>
--========================================================================
	rbBerTestSetup		OBJECT IDENTIFIER ::=  {  rbBerTest  1  }

	rbBerTestDataSize	OBJECT-TYPE	
		SYNTAX			Integer32	(1000..100000000)
		MAX-ACCESS		read-write
		STATUS			current
		DESCRIPTION		
				"Not supported in current version.
				 The total number of BER test bytes to be transmitted.
				 When starting a BER test, this parameter must be sent in together
				 with all other test parameters, and rbBerTestAction start (1)." 
		::=  {  rbBerTestSetup  1  }

	rbBerTestModulation		OBJECT-TYPE	
		SYNTAX			INTEGER	{
		                          notDefined (0),
		                          rBpsk12 (1),
		                          rBpsk34 (2),
								  rQpsk12 (3),
								  rQpsk34 (4),
								  r16Qam12 (5),
								  r16Qam34 (6),
								  r64Qam23 (7),
								  r64Qam34 (8)
								}
	MAX-ACCESS		read-write
		STATUS			current
		DESCRIPTION		
				"Not supported in current version.
				 Modulation and Forwarding Error Correction Rate 
				 to be used during the BER test.
				 When starting a BER test, this parameter must be sent in together
				 with all other test parameters, and rbBerTestAction start (1)."  
		::=  {  rbBerTestSetup  2  }

	rbBerTestAction		OBJECT-TYPE	
		SYNTAX			INTEGER	{
		                          start  (1),
		                          abort  (2),
								  none   (3)
							    }
	MAX-ACCESS		read-write
		STATUS			current
		DESCRIPTION		
				"Not supported in current version.
				 Initiating/terminating the test.
				 When starting a BER test, rbBerTestAction start (1) must be sent in
				 together with all other test parameters.
				 The test will be normally be finished after completion 
				 (all test bytes as defined by rbBerTestDataSize were sent). 
				 It can also be aborted before completion." 
		::=  {  rbBerTestSetup  3  }

	rbBerTestStatus		OBJECT-TYPE	
		SYNTAX			INTEGER	{
		                          inactive (1),
		                          active   (2),
								  finished (3),
								  failed   (4),
								  suDisconnected (5)
							    }
	MAX-ACCESS		read-only
		STATUS			current
		DESCRIPTION		
				"Not supported in current version.
				 The status of the test." 
		::=  {  rbBerTestSetup  4  }

	rbBerTestSU		OBJECT-TYPE	
		SYNTAX			MacAddress	
		MAX-ACCESS		read-only
		STATUS			current
		DESCRIPTION		
				"Not supported in current version.
				 The MAC address of SU to be tested during the BER test." 
		::=  {  rbBerTestSetup  5  }

	rbBerTestTrafficPriority		OBJECT-TYPE	
		SYNTAX			INTEGER
		                {
						   notDefined (0),
						   realTime (1),
						   notRealTime (2),
						   bestEffort (3)
		                }	
		MAX-ACCESS		read-write
		STATUS			current
		DESCRIPTION		
				"Not supported in current version.
				 The service priority of the BER test traffic.
				 When starting a BER test, this parameter must be sent in together
				 with all other test parameters, and rbBerTestAction start (1)." 
		::=  {  rbBerTestSetup  6  }

	rbBerTestMaxPacketSize		OBJECT-TYPE	
		SYNTAX			Integer32	(500..4000)
		MAX-ACCESS		read-write
		STATUS			current
		DESCRIPTION		
				"Not supported in current version.
				 The packet size in bytes.
				 When starting a BER test, this parameter must be sent in together
				 with all other test parameters, and rbBerTestAction start (1)." 
		::=  {  rbBerTestSetup  7  }


--========================================================================
--     BER Test Results  
-- Not supported in current version.  
-- SU BER Test Results are retrieved using community <com>@SU.<MacAddress>
--========================================================================
	rbBerTestResults		OBJECT IDENTIFIER ::=  {  rbBerTest  2  }

	rbBerTestULReceivedBits	OBJECT-TYPE	
		SYNTAX			Integer32	
		MAX-ACCESS		read-only
		STATUS			current
		DESCRIPTION		
				"Not supported in current version.
				 Number of bits received during the last BER test in the UpLink direction." 
		::=  {  rbBerTestResults  1  }

	rbBerTestULReceivedErrorBits	OBJECT-TYPE	
		SYNTAX			Integer32	
		MAX-ACCESS		read-only
		STATUS			current
		DESCRIPTION		
				"Not supported in current version.
				 Number of error bits received during the last BER test in the UpLink direction." 
		::=  {  rbBerTestResults  2  }

	rbBerTestDLReceivedBits	OBJECT-TYPE	
		SYNTAX			Integer32	
		MAX-ACCESS		read-only
		STATUS			current
		DESCRIPTION		
				"Not supported in current version.
				 Number of bits received during the last BER test in the DownLink direction." 
		::=  {  rbBerTestResults  3  }

	rbBerTestDLReceivedErrorBits	OBJECT-TYPE	
		SYNTAX			Integer32	
		MAX-ACCESS		read-only
		STATUS			current
		DESCRIPTION		
				"Not supported in current version.
				 Number of error bits received in the DownLink direction during the last BER test." 
		::=  {  rbBerTestResults  4  }

	rbBerTestDLMapLost	OBJECT-TYPE	
		SYNTAX			Integer32	
		MAX-ACCESS		read-only
		STATUS			current
		DESCRIPTION		
				"Not supported in current version.
				 Number of times MAP was lost during the last BER test in the DownLink direction." 
		::=  {  rbBerTestResults  5  }

	rbBerTestResultsSU		OBJECT-TYPE	
		SYNTAX			MacAddress	
		MAX-ACCESS		read-only
		STATUS			current
		DESCRIPTION		
				"Not supported in current version.
				 The MAC address of the SU." 
		::=  {  rbBerTestResults  6  }

	rbBerTestUplinkBER		OBJECT-TYPE	
		SYNTAX			DisplayString	
		MAX-ACCESS		read-only
		STATUS			current
		DESCRIPTION		
				"Not supported in current version.
				 The BER in the Uplink Direction." 
		::=  {  rbBerTestResults  7  }

	rbBerTestDownlinkBER		OBJECT-TYPE	
		SYNTAX			DisplayString	
		MAX-ACCESS		read-only
		STATUS			current
		DESCRIPTION		
				"Not supported in current version.
				 The BER in the Downlink Direction." 
		::=  {  rbBerTestResults  8  }


--========================================================================
--     IP Config  
--========================================================================
   rbIPConfig				OBJECT IDENTIFIER ::=  {  rainbow  9  }

   rbIpIfConfigTable	OBJECT-TYPE
		SYNTAX		SEQUENCE  OF  RbIpIfConfigEntry
		MAX-ACCESS	not-accessible
		STATUS		current
		DESCRIPTION	
			"This table contains IP configuration parameters per interface."
		::=  { rbIPConfig 1 }

	rbIpIfConfigEntry	OBJECT-TYPE
		SYNTAX		RbIpIfConfigEntry
		MAX-ACCESS	not-accessible
		STATUS		current
		DESCRIPTION	
			"Table entry"
		INDEX		{  ipIfConfigIfIndex  }
		::=  { rbIpIfConfigTable 1 }

	RbIpIfConfigEntry  ::=  SEQUENCE {
		ipIfConfigIfIndex  	  			Integer32,
		ipIfConfigVlanId				Integer32,
		ipIfConfigIpAddress				IpAddress,
		ipIfConfigNetworkMask			IpAddress,
		ipIfConfigDefaultGateway		IpAddress,
		ipIfStaticRouteSubnet 			IpAddress,
		ipIfStaticRouteSubnetMask 		IpAddress

		}

	ipIfConfigIfIndex	OBJECT-TYPE	
		SYNTAX			Integer32 ( 1..2 )
		MAX-ACCESS		read-only
		STATUS			current
		DESCRIPTION		
				"Index of Ethernet Interface.
				 In NPU and Micro Base Station, 1 is for the DATA port and 2 is for the MGMT port.
				 In SU, 1 is for the ETHERNET port and 2 is not applicable." 
		::=  {  rbIpIfConfigEntry  1  }

	ipIfConfigVlanId	OBJECT-TYPE	
		SYNTAX			Integer32 (0..4095) 
		MAX-ACCESS		read-write
		STATUS			current
		DESCRIPTION		
				"The management VLAN ID associated with the specific interface. 
				 Applicable only for the DATA port of NPU/Micro Base Station. 
				 The range is from 0 to 4095, where 4095 means that no management VLAN ID is defined." 
		::=  {  rbIpIfConfigEntry 2  }

	ipIfConfigIpAddress	OBJECT-TYPE	
		SYNTAX			IpAddress  
		MAX-ACCESS		read-write
		STATUS			current
		DESCRIPTION		
				"IP Address of the interface." 
		::=  {  rbIpIfConfigEntry 3  }

	ipIfConfigNetworkMask	OBJECT-TYPE	
		SYNTAX			IpAddress  
		MAX-ACCESS		read-write
		STATUS			current
		DESCRIPTION		
				"The Subnet Mask of the interface." 
		::=  {  rbIpIfConfigEntry 4  }

	ipIfConfigDefaultGateway	OBJECT-TYPE	
		SYNTAX			IpAddress  
		MAX-ACCESS		read-write
		STATUS			current
		DESCRIPTION		
				"Default Gateway IP Address of the interface." 
		::=  {  rbIpIfConfigEntry 5  }

	ipIfStaticRouteSubnet	OBJECT-TYPE	
		SYNTAX			IpAddress  
		MAX-ACCESS		read-write
		STATUS			current
		DESCRIPTION		
				"Applicable only to the MGMT port of NPU/Micro Base Station. 
				 The Destination Subnet (base IP address of the subnet) 
				 of the stations that can manage the device when connected via a router to the MGMT port. 
				 All management frames destined for addresses belonging to this group will be 
				 routed via the MGMT port. All management frames that are not destined for these addresses, 
				 or to addresses belonging to the MGMT port local subnet, will be routed via the DATA port." 
		::=  {  rbIpIfConfigEntry 6  }

	ipIfStaticRouteSubnetMask	OBJECT-TYPE	
		SYNTAX			IpAddress  
		MAX-ACCESS		read-write
		STATUS			current
		DESCRIPTION		
				"Applicable only to the MGMT port of NPU/Micro Base Station. 
				 The Destination Subnet Mask associated with the Destination Subnet (ipIfStaticRouteSubnet)." 
		::=  {  rbIpIfConfigEntry 7  }


--========================================================================
--     Software Upgrade  
--========================================================================
    rbSwUpgrade    OBJECT IDENTIFIER ::=  {  rainbow  10 }

	rbSwAuFiles	OBJECT-TYPE	
		SYNTAX			DisplayString 
		MAX-ACCESS		read-only
		STATUS			current
		DESCRIPTION		
				"String that contains the names of AU software files in the NPU (up to 4), separated by ;"
		::=  {  rbSwUpgrade 1  }

	rbSwSuFiles	OBJECT-TYPE	
		SYNTAX			DisplayString 
		MAX-ACCESS		read-only
		STATUS			current
		DESCRIPTION		
				"String that contains names of SU software files in NPU/Micro Base Station (up to 4), separated by ;"
		::=  {  rbSwUpgrade 2  }

	rbSwDeleteFiles	OBJECT-TYPE	
		SYNTAX			DisplayString
		MAX-ACCESS		read-write
		STATUS			current
		DESCRIPTION		
				"String that contains names, separated by ;, of the AU/SU software files to deleted."
		::=  {  rbSwUpgrade 3  }

	rbSwSuDefaultFile	OBJECT-TYPE	
		SYNTAX			DisplayString
		MAX-ACCESS		read-write
		STATUS			current
		DESCRIPTION		
				"In SUs using SW version below 2.5: The name of the software file that should be used
				 by Temporary SU upon the Network Entry. 
                 In SUs using SW version 2.5 and higher: The SW file that should be used upon network entry
                 by all SUs using Air Interface type a.
                 Not applicable if either rbAuSuUpgradeSwFileName in the AU serving the SU,
                 or rbSuUpgradeSwFileName for this SU, are not empty."
		::=  {  rbSwUpgrade 4  }

	rbSwSuDefaultAction	OBJECT-TYPE	
		SYNTAX			INTEGER
		                {
						  none (1),
						  putToShadow (3),
						  runFromShadow (4),
						  makeShadowOperational(5)
						}
		MAX-ACCESS		read-write
		STATUS			current
		DESCRIPTION		
				"In SUs using SW version below 2.5: The Action that should be performed
				 by Temporary SU upon the Network Entry.
				 Action should be performed using the rbSwSuDefaultFile.
                 In SUs using SW version 2.5 and higher: The action to be taken with the rbSwSuDefaultFile
                 upon network entry by all SUs using Air Interface type a.
                 Not applicable if either the rbAuSuUpgradeSwAction in the AU serving this SU,
                 or rbSuUnitControl for this SU, are other than none (1)."
		::=  {  rbSwUpgrade 5  }


    rbSwUpgradeLogTable	OBJECT-TYPE
		SYNTAX		SEQUENCE  OF  RbSwUpgradeLogEntry
		MAX-ACCESS	not-accessible
		STATUS		current
		DESCRIPTION	
			"This table contains the status of the last software upgrade performed for 
			 specific AUs or SUs."
		::=  { rbSwUpgrade 6 }

	rbSwUpgradeLogEntry	OBJECT-TYPE
		SYNTAX		RbSwUpgradeLogEntry
		MAX-ACCESS	not-accessible
		STATUS		current
		DESCRIPTION	
			"Table entry"
		INDEX		{rbSwDeviceType,rbSwDeviceId }
		::=  { rbSwUpgradeLogTable 1 }

	RbSwUpgradeLogEntry  ::=  SEQUENCE {
		rbSwDeviceType				INTEGER,
		rbSwDeviceId  	  			OCTET STRING,
		rbSwUpgradeFileName			DisplayString,
		rbSwUpgradeAction			INTEGER,
		rbSwUpgradeStartTime		TimeTicks,
		rbSwUpgradeEndTime			TimeTicks,
		rbSwUpgradeStatus			INTEGER
		}


	rbSwDeviceType	OBJECT-TYPE	
		SYNTAX			INTEGER
		                {
		                  au (1),
		                  su (2)
		                }   
		MAX-ACCESS		read-only
		STATUS			current
		DESCRIPTION		
				"Type of device participating in the software upgrade process." 
		::=  {  rbSwUpgradeLogEntry  1  }

	rbSwDeviceId	OBJECT-TYPE	
		SYNTAX			OCTET STRING (SIZE (1..6))
		MAX-ACCESS		read-only
		STATUS			current
		DESCRIPTION		
				"Identification of device. For AU - slot number , for SU - MAC Address." 
		::=  {  rbSwUpgradeLogEntry  2  }

	rbSwUpgradeFileName	OBJECT-TYPE	
		SYNTAX			DisplayString
		MAX-ACCESS		read-only
		STATUS			current
		DESCRIPTION		
				"The name of the software file that was used for upgrade." 
		::=  {  rbSwUpgradeLogEntry  3  }

	rbSwUpgradeAction	OBJECT-TYPE	
		SYNTAX			INTEGER
		                {
	                      none (1),
						  putToShadow (3),
	                      resetAndRunFromShadow (4),
	                      makeRunningVersionOperational (5),
						  startRegistration ( 6 )
						}
		MAX-ACCESS		read-only
		STATUS			current
		DESCRIPTION		
				"The last performed software upgrade action." 
		::=  {  rbSwUpgradeLogEntry  4  }

	rbSwUpgradeStartTime	OBJECT-TYPE	
		SYNTAX			TimeTicks
		MAX-ACCESS		read-only
		STATUS			current
		DESCRIPTION		
				"The time when the software upgrade process was started. 
				 Not supported in current version." 
		::=  {  rbSwUpgradeLogEntry  5  }
	
	rbSwUpgradeEndTime	OBJECT-TYPE	
		SYNTAX			TimeTicks
		MAX-ACCESS		read-only
		STATUS			current
		DESCRIPTION		
				"The time when the software upgrade process was finished.
				 Not supported in current version." 
		::=  {  rbSwUpgradeLogEntry  6  }

	rbSwUpgradeStatus	OBJECT-TYPE	
		SYNTAX			INTEGER
		                { 
		                  none (1),
						  success (2),
						  inProgress (3),
						  failed (4),
						  pending (5)
						}
		MAX-ACCESS		read-only
		STATUS			current
		DESCRIPTION		
				"The status of the software upgrade process."
		::=  {  rbSwUpgradeLogEntry  7  }


	rbSwSuSiDefaultFile	OBJECT-TYPE	
		SYNTAX			DisplayString
		MAX-ACCESS		read-write
		STATUS			current
		DESCRIPTION		
				"The SW file that should be used upon network entry by all SUs using Air Interface type si.
				 Not applicable if either rbAuSuUpgradeSwFileName in the AU serving the SU,
				 or rbSuUpgradeSwFileName for this SU, are not empty."
		::=  {  rbSwUpgrade 7  }

	rbSwSuSiDefaultAction	OBJECT-TYPE	
		SYNTAX			INTEGER
		                {
						  none (1),
						  putToShadow (3),
						  runFromShadow (4),
						  makeShadowOperational(5)
						}
		MAX-ACCESS		read-write
		STATUS			current
		DESCRIPTION		
				"The action to be taken with the rbSwSuSiDefaultFile upon network entry	
				 by all SUs using Air Interface type si.
				 Not applicable if either the rbAuSuUpgradeSwAction in the AU serving this SU,
				 or rbSuUnitControl for this SU, are other than none (1)."
		::=  {  rbSwUpgrade 8  }

	rbSwAuDefaultFile	OBJECT-TYPE	
		SYNTAX			DisplayString
		MAX-ACCESS		read-write
		STATUS			current
		DESCRIPTION		
				"The name of the software file that should be used by an AU using Air Interface type a
				 upon the Network Entry. Not applicable if rbAuUpgradeSwFileName for the AU is not empty."
		::=  {  rbSwUpgrade 9  }

	rbSwAuDefaultAction	OBJECT-TYPE	
		SYNTAX			INTEGER
		                {
						  none (1),
						  putToShadow (3),
						  runFromShadow (4),
						  makeShadowOperational(5)
						}
		MAX-ACCESS		read-write
		STATUS			current
		DESCRIPTION		
				"The Action that should be performed by an AU using Air Interface type a upon the Network Entry. 
				 Action should be performed using the rbSwAuDefaultFile.
				 Not applicable if rbAuUnitControl for the AU is other than None."
		::=  {  rbSwUpgrade 10  }

	rbSwAuSiDefaultFile	OBJECT-TYPE	
		SYNTAX			DisplayString
		MAX-ACCESS		read-write
		STATUS			current
		DESCRIPTION		
				"The name of the software file that should be used by an AU using Air Interface type si
				 upon the Network Entry. Not applicable if rbAuUpgradeSwFileName for the AU is not empty."
		::=  {  rbSwUpgrade 11  }

	rbSwAuSiDefaultAction	OBJECT-TYPE	
		SYNTAX			INTEGER
		                {
						  none (1),
						  putToShadow (3),
						  runFromShadow (4),
						  makeShadowOperational(5)
						}
		MAX-ACCESS		read-write
		STATUS			current
		DESCRIPTION		
				"The Action that should be performed by an AU using Air Interface type si upon the Network Entry. 
				 Action should be performed using the rbSwAuSiDefaultFile.
				 Not applicable if rbAuUnitControl for the AU is other than None."
		::=  {  rbSwUpgrade 12  }

	rbBstClearAllSuSwUpgradeParams	OBJECT-TYPE	
		SYNTAX			INTEGER  { none ( 1 ), clearAllSuSwUpgradeParams ( 2 ) } 
		MAX-ACCESS		read-write
		STATUS			current
		DESCRIPTION		
				"Clears the SW Upgrade parameters for all SUs served by the Base Station:
				 For all SUs, rbSuUpgradeSwFileName will be set to an empty string,
				 and rbSuUnitControl will be set to none (1).
				 none (1) value is available to support Get and Get Next commands.
				 It should not be used in Set commands."
		::=  {  rbSwUpgrade 13  }

	rbBstClearAllAuSwUpgradeParams	OBJECT-TYPE	
		SYNTAX			INTEGER  { none ( 1 ), clearAllAuSwUpgradeParams ( 2 ) } 
		MAX-ACCESS		read-write
		STATUS			current
		DESCRIPTION		
				"Clears the SW Upgrade parameters for all AUs in the Base Station:
				 For all AUs, rbAuUpgradeSwFileName will be set to an empty string,
				 and rbAuUnitControl will be set to none (1).
				 none (1) value is available to support Get and Get Next commands.
				 It should not be used in Set commands."
		::=  {  rbSwUpgrade 14  }


-- ===========================================================================
-- Chain Configuration Parameters
-- ===========================================================================

	rbChainConfig    OBJECT IDENTIFIER    ::=  {  rainbow  14  }

	rbGPSSupported    OBJECT-TYPE	
		SYNTAX			INTEGER	{
								   supported     ( 1 ),
		                           notSupported  ( 2 )
								 }
		MAX-ACCESS		read-only
		STATUS			current
		DESCRIPTION		
				"The GPS support status."
		::=  {  rbChainConfig  1  }

	rbConfiguredChainNumber    OBJECT-TYPE	
		SYNTAX			Unsigned32 ( 0 .. 1500 )  
		MAX-ACCESS		read-write
		STATUS			current
		DESCRIPTION		
				"The Configured GPS Chain number. Allowed range is from 1 to 1500.
				 0 is only init value that need to be modified in order to have possibility
				 to change other chain parameters."
		DEFVAL			{ 0 }
		::=  {  rbChainConfig  2  }

	rbCurrentChainNumber    OBJECT-TYPE	
		SYNTAX			Unsigned32 ( 0 .. 1500 )  
		MAX-ACCESS		read-only
		STATUS			current
		DESCRIPTION		
				"The Current GPS Chain number."
		::=  {  rbChainConfig  3  }

	rbGPSConfiguredType    OBJECT-TYPE	
		SYNTAX			INTEGER	{
		                           none        ( 0 ),
								   trimble     ( 1 ),
		                           symmetricom ( 2 )
								 }
	    MAX-ACCESS		read-write
		STATUS			current
		DESCRIPTION		
				"The Configured GPS Protocol."
		DEFVAL			{ trimble }
		::=  {  rbChainConfig  4  }

	rbGPSCurrentType    OBJECT-TYPE	
		SYNTAX			INTEGER	{
		                           none        ( 0 ),
								   trimble     ( 1 ),
		                           symmetricom ( 2 )
								 }
	    MAX-ACCESS		read-only
		STATUS			current
		DESCRIPTION		
				"The Current GPS Protocol."
		::=  {  rbChainConfig  5  }

	rbTimeZoneOffsetFromUTC    OBJECT-TYPE
		SYNTAX			DisplayString  ( SIZE ( 6 ) ) 
		MAX-ACCESS		read-write
		STATUS			current
		DESCRIPTION		
				"Local Time Zone offset from UTC.
				 The range is -12:00 up to +13:00 in 30 minutes resolution."
		::=  {  rbChainConfig  6  }

	rbStopTxAfterHoldOverTimeout    OBJECT-TYPE	
		SYNTAX			INTEGER	{
		                           enable   ( 1 ),
		                           disable  ( 2 )
								 }
		MAX-ACCESS		read-write
		STATUS			current
		DESCRIPTION		
				"Defines whether to stop transmitting after Hold Over Timeout.
				 Disable means not to stop transmissions. Enable means stop transmissions after Timeout."
		DEFVAL          { disable }
		::=  {  rbChainConfig  7  }

	rbHoldOverPassedTimeout    OBJECT-TYPE
		SYNTAX			Unsigned32 ( 0 .. 2880 )  
		MAX-ACCESS		read-write
		STATUS			current
		DESCRIPTION		
				"Hold Over Timeout in minutes. 
				 AUs will enter Hold Over mode when receiving less than two satellites."
		DEFVAL          { 30 }
		::=  {  rbChainConfig  8  }


-- ===========================================================================
-- GPS Info Parameters
-- ===========================================================================

	rbGPSInfo    OBJECT IDENTIFIER    ::=  {  rainbow  15  }

	rbGPSNumberOfRxSatellites    OBJECT-TYPE	
		SYNTAX			Unsigned32 ( 1 .. 255 )  
		MAX-ACCESS		read-only
		STATUS			current
		DESCRIPTION		
				"Number of received satellites."
		::=  {  rbGPSInfo  1  }
	
	rbGPSLongitude    OBJECT-TYPE	
		SYNTAX			DisplayString  
		MAX-ACCESS		read-only
		STATUS			current
		DESCRIPTION		
				"GPS Longitude.
				 Format is llll.lll,a: llll.lll is longitude in degrees; a - is E(east) or W(west)."
		::=  {  rbGPSInfo  2  }

	rbGPSLatitude    OBJECT-TYPE	
		SYNTAX			DisplayString  
		MAX-ACCESS		read-only
		STATUS			current
		DESCRIPTION		
				"GPS Latitude.
				 Format is llll.lll,a: llll.lll is latitude in degrees; a - is N(North) or S(South)."
		::=  {  rbGPSInfo  3  }

	rbGPSAltitude    OBJECT-TYPE	
		SYNTAX			DisplayString  
		MAX-ACCESS		read-only
		STATUS			current
		DESCRIPTION		
				"GPS Antenna Altitude in meters.
				 Format is a.a,M: a.a is altitude; M - is Meters."
		::=  {  rbGPSInfo  4 }

	rbGPSLocalDateAndTime    OBJECT-TYPE	
		SYNTAX			DisplayString  ( SIZE ( 20 ) ) 
		MAX-ACCESS		read-only
		STATUS			current
		DESCRIPTION		
				"Calculated local Date and time.
				 The format is hh:mm:ss, dd/mm/yyyy. For example: 23:22:04, 25/12/2006."
		::=  {  rbGPSInfo  5  }

	rbGPSNavigationProcessorSWVersion    OBJECT-TYPE
		SYNTAX			DisplayString  ( SIZE ( 0 .. 32 ) ) 
		MAX-ACCESS		read-only
		STATUS			current
		DESCRIPTION		
				"Navigation Processor SW version.
				 Format is Major Version Number, Minor Version Number, Month, Day and Year+1900."
		::=  {  rbGPSInfo  6  }

	rbGPSSignalProcessorSWVersion    OBJECT-TYPE
		SYNTAX			DisplayString  ( SIZE ( 0 .. 32 ) ) 
		MAX-ACCESS		read-only
		STATUS			current
		DESCRIPTION		
				"Signal Processor SW version.
				 Format is Major Version Number, Minor Version Number, Month, Day and Year+1900."
		::=  {  rbGPSInfo  7  }


--========================================================================
--     License  
--========================================================================

 rbLicense 			OBJECT IDENTIFIER ::=  {  rainbow  50 }

--========================================================================
--     CPEs License Bank Status
--========================================================================

    rbLicenseBankTable	OBJECT-TYPE
		SYNTAX		SEQUENCE  OF  RbLicenseBankEntry
		MAX-ACCESS	not-accessible
		STATUS		current
		DESCRIPTION	
			"A Table of CPE Licenses."
		::=  { rbLicense 1 }

	rbLicenseBankEntry	OBJECT-TYPE
		SYNTAX		RbLicenseBankEntry
		MAX-ACCESS	not-accessible
		STATUS		current
		DESCRIPTION	
			"Table entry."
		INDEX		{ rbLicenseId, rbLicenseValue }
		::=  { rbLicenseBankTable 1 }

	RbLicenseBankEntry  ::=  SEQUENCE {
		rbLicenseId		INTEGER,
		rbLicenseValue 	        Unsigned32,
		rbLicenseCount	        Unsigned32,
		rbLicenseDescription    DisplayString
		}

	rbLicenseId 	OBJECT-TYPE	
		SYNTAX			INTEGER
		                { 
		                  bandwidth  (1)
						}
		MAX-ACCESS		read-only
		STATUS			current
		DESCRIPTION		
				"Type of Licenses: bandwidth (1) - Bandwidth License."
		::=  {  rbLicenseBankEntry  1  }

	rbLicenseValue	OBJECT-TYPE	
		SYNTAX			Unsigned32
		MAX-ACCESS		read-only
		STATUS			current
		DESCRIPTION		
				"For Bandwidth Limitation License the current valid value is 0 for Unlimited Bandwidth."
		::=  {  rbLicenseBankEntry  2  }

	rbLicenseCount	OBJECT-TYPE	
		SYNTAX			Unsigned32
		MAX-ACCESS		read-only
		STATUS			current
		DESCRIPTION		
				"The number of applicable Licenses that are available in the CPEs License Bank."
		::=  {  rbLicenseBankEntry  3  }

	rbLicenseDescription    OBJECT-TYPE	
		SYNTAX			DisplayString  ( SIZE ( 0 .. 32  ) ) 
		MAX-ACCESS		read-only
		STATUS			current
		DESCRIPTION		
				"The Licenses Description."
		::=  {  rbLicenseBankEntry  4  }


--========================================================================
--     Base Station License	Table
--========================================================================
    rbLicenseBst 			OBJECT IDENTIFIER ::=  {  rbLicense  2  }

    rbLicenseBstTable	OBJECT-TYPE
		SYNTAX		SEQUENCE  OF  RbLicenseBstEntry
		MAX-ACCESS	not-accessible
		STATUS		current
		DESCRIPTION	
			"A Table of Base Station/Micro Base Station Licenses."
		::=  { rbLicenseBst 1 }

	rbLicenseBstEntry	OBJECT-TYPE
		SYNTAX		RbLicenseBstEntry
		MAX-ACCESS	not-accessible
		STATUS		current
		DESCRIPTION	
			"Table entry."
		INDEX		{ rbBstLicenseId }
		::=  { rbLicenseBstTable 1 }

	RbLicenseBstEntry  ::=  SEQUENCE {
		rbBstLicenseId		   INTEGER,
		rbBstLicenseValue 	   Unsigned32,
		rbBstLicenseDescription    DisplayString
		}

	rbBstLicenseId 	OBJECT-TYPE	
		SYNTAX			INTEGER
		                { 
		                  bandwidth       (1),
						  maxNumberOfSUs  (2)
						}
		MAX-ACCESS		read-only
		STATUS			current
		DESCRIPTION		
				"Type of Licenses:
				 bandwidth (1) - Bandwidth limitation for all PRO-L SUs served by the Base Station/Micro Base Station,
				 maxNumberOfSUs (2) - Maximum Number of SU's is relevant only for Micro Base Station."
		::=  {  rbLicenseBstEntry  1  }

	rbBstLicenseValue	OBJECT-TYPE	
		SYNTAX			Unsigned32
		MAX-ACCESS		read-only
		STATUS			current
		DESCRIPTION		
				"For Bandwidth Limitation License the current valid value is 0 for Unlimited Bandwidth.
				 For Maximum Number of SUs License the valid values are 50, 150, 250."
		::=  {  rbLicenseBstEntry  2  }

	rbBstLicenseDescription    OBJECT-TYPE	
		SYNTAX			DisplayString  ( SIZE ( 0 .. 32  ) ) 
		MAX-ACCESS		read-only
		STATUS			current
		DESCRIPTION		
				"The Licenses Description."
		::=  {  rbLicenseBstEntry  3  }

	rbNumberOfSUsGraceEndDate 	OBJECT-TYPE	
		SYNTAX			DisplayString
		MAX-ACCESS		read-only
		STATUS			current
		DESCRIPTION		
				"Applicable only to a Micro Base Station that was upgraded from SW version 2.0 or lower
				 and does not have any Maximum Number of SUs License.
				 The Grace Period will be activated automatically upon the first time that the Micro Base Station
				 starts to serve more than 20 SUs.
				 Indicates the Grace Period End Date. Until the End Date the Micro Base Station can serve up to 250 SUs.
				 If it is empty it means Not Applicable."
		::=  {  rbLicenseBst  2  }


--========================================================================
--     SU Temporary Grace Period License Table
--========================================================================

    rbSUTempGracePeriodLicenseTable	OBJECT-TYPE
		SYNTAX		SEQUENCE  OF  RbSUTempGracePeriodLicenseEntry
		MAX-ACCESS	not-accessible
		STATUS		current
		DESCRIPTION	
			"SU Temporary Grace Period License Table."
		::=  { rbLicense 3 }

	rbSUTempGracePeriodLicenseEntry	OBJECT-TYPE
		SYNTAX		RbSUTempGracePeriodLicenseEntry
		MAX-ACCESS	not-accessible
		STATUS		current
		DESCRIPTION	
			"Table entry."
		INDEX		{ rbSUTempGracePeriodIndex }
		::=  { rbSUTempGracePeriodLicenseTable 1 }

	RbSUTempGracePeriodLicenseEntry  ::=  SEQUENCE {
		rbSUTempGracePeriodIndex		     Unsigned32,
		rbSUTempGracePeriodSuMacAddr		 MacAddress,
		rbSUTempGracePeriodLicenseId		 INTEGER,
		rbSUTempGracePeriodLicenseEndDate    DisplayString
		}


	rbSUTempGracePeriodIndex	OBJECT-TYPE	
		SYNTAX			Unsigned32    
		MAX-ACCESS		read-only
		STATUS			current
		DESCRIPTION		
				"The INDEX of the SU Temporary Grace Period License Table."
		::=  {  rbSUTempGracePeriodLicenseEntry  1  }

	rbSUTempGracePeriodSuMacAddr	OBJECT-TYPE	
		SYNTAX			MacAddress
		MAX-ACCESS		read-only
		STATUS			current
		DESCRIPTION		
				"The MAC address of the SU." 
		::=  {  rbSUTempGracePeriodLicenseEntry  2  }

	rbSUTempGracePeriodLicenseId 	OBJECT-TYPE	
		SYNTAX			INTEGER
		                { 
		                  bandwidth  (1)
						}
		MAX-ACCESS		read-only
		STATUS			current
		DESCRIPTION		
				"Type of Licenses: bandwidth (1) - Bandwidth License."
		::=  {  rbSUTempGracePeriodLicenseEntry  3  }

	rbSUTempGracePeriodLicenseEndDate	OBJECT-TYPE	
		SYNTAX			DisplayString
		MAX-ACCESS		read-only
		STATUS			current
		DESCRIPTION		
				"SU Temporary Grace Period Date."
		::=  {  rbSUTempGracePeriodLicenseEntry  4  }


--========================================================================
--     SU Grace Period Table  
--========================================================================

    rbSUGracePeriodLicenseTable	OBJECT-TYPE
		SYNTAX		SEQUENCE  OF  RbSUGracePeriodLicenseEntry
		MAX-ACCESS	not-accessible
		STATUS		current
		DESCRIPTION	
			"SU Grace Period Table."
		::=  { rbLicense 4 }

	rbSUGracePeriodLicenseEntry	OBJECT-TYPE
		SYNTAX		RbSUGracePeriodLicenseEntry
		MAX-ACCESS	not-accessible
		STATUS		current
		DESCRIPTION	
			"Table entry."
		INDEX		{ rbSUGracePeriodIndex }
		::=  { rbSUGracePeriodLicenseTable 1 }

	RbSUGracePeriodLicenseEntry  ::=  SEQUENCE {
		rbSUGracePeriodIndex		     Unsigned32,
		rbSUGracePeriodSuMacAddr		 MacAddress,
		rbSUGracePeriodLicenseId		 INTEGER,
		rbSUGracePeriodLicenseEndDate    DisplayString,
		rbSUGracePeriodLicenseStatus     INTEGER
		}


	rbSUGracePeriodIndex	OBJECT-TYPE	
		SYNTAX			Unsigned32    
		MAX-ACCESS		read-only
		STATUS			current
		DESCRIPTION		
				"The INDEX of the SU Grace Period License Table."
		::=  {  rbSUGracePeriodLicenseEntry  1  }

	rbSUGracePeriodSuMacAddr	OBJECT-TYPE	
		SYNTAX			MacAddress
		MAX-ACCESS		read-only
		STATUS			current
		DESCRIPTION		
				"The MAC address of the SU." 
		::=  {  rbSUGracePeriodLicenseEntry  2  }

	rbSUGracePeriodLicenseId 	OBJECT-TYPE	
		SYNTAX			INTEGER
		                { 
		                  bandwidth  (1)
						}
		MAX-ACCESS		read-only
		STATUS			current
		DESCRIPTION		
				"Type of Licenses: bandwidth (1) - Bandwidth License."
		::=  {  rbSUGracePeriodLicenseEntry  3  }

	rbSUGracePeriodLicenseEndDate	OBJECT-TYPE	
		SYNTAX			DisplayString
		MAX-ACCESS		read-only
		STATUS			current
		DESCRIPTION		
				"SU Grace Period End Date."
		::=  {  rbSUGracePeriodLicenseEntry  4  }

	rbSUGracePeriodLicenseStatus	OBJECT-TYPE	
		SYNTAX			INTEGER
		                { 
		                  licenseNone      (1),
						  licenseActivated (2),
						  licenseActiveWarnIssued (3),
						  licenseUsed      (4)
						}
		MAX-ACCESS		read-only
		STATUS			current
		DESCRIPTION		
				"License SU Grace Period Admin Status."
		::=  {  rbSUGracePeriodLicenseEntry  5  }



 endOfMib       OBJECT-TYPE
                SYNTAX                    INTEGER  { endOfMib ( 1 ) }
                MAX-ACCESS                read-only
                STATUS                    current
                DESCRIPTION
                                "This leaf is intended to solve getNext problem when the end of the MIB is reached."
                DEFVAL                        { endOfMib }
                ::=  {  rainbow  300  }

END

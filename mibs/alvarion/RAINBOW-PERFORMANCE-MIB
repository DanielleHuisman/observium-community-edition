--
-- 
--                  Rainbow Performance Management Information Base
--
--                          06/06/2006
--
-- 
RAINBOW-PERFORMANCE-MIB	DEFINITIONS ::= BEGIN
	IMPORTS
		rainbow, Modulation
			FROM RAINBOW-MIB
		rbServiceID	 
		    FROM RAINBOW-SERVICES-MIB
		MODULE-IDENTITY, OBJECT-TYPE, Counter32, Unsigned32, Gauge32, Integer32
			FROM SNMPv2-SMI
		DisplayString, MacAddress
			FROM SNMPv2-TC
		ifIndex
		    FROM RFC1213-MIB;

--  enterprises  OBJECT IDENTIFIER ::=
--  { iso org(3) dod(6) internet(1) private(4) 1 }
--  alvarion     OBJECT IDENTIFIER ::=  { enterprises 12394 }
--  products     OBJECT IDENTIFIER ::=  { alvarion 1 }
--  rainbow      OBJECT IDENTIFIER ::=  { products 2 }


	rbPerformance	MODULE-IDENTITY
		LAST-UPDATED	"200606061500Z"
		ORGANIZATION	"Alvarion Ltd."
		CONTACT-INFO	"Alvarion Customer Service
		Postal: Alvarion Ltd.
			Barzel 21
			Tel Aviv 69710 
			ISRAEL
               	E-mail: CS_Coordinator@alvarion.com"
		DESCRIPTION		
				"Rainbow Performance monitoring MIB Definitions"
		REVISION		"200606061500Z"
		DESCRIPTION		
				"Revision 2.5"
		::=  {  rainbow  4  }
	  

-- ####################################################################
--	Service Specific Performance Indicators
-- ####################################################################


rbPMServ OBJECT IDENTIFIER ::=  {  rbPerformance  1  }

-- #######################################################################
-- Performance Indicators of Connection Table for CG (VoIP) Services 
-- #######################################################################

   rbPMCGServConnTable	OBJECT-TYPE
		SYNTAX		SEQUENCE  OF  RbPMCGServConnEntry
		MAX-ACCESS	not-accessible
		STATUS		deprecated
		DESCRIPTION	
			"This table is deprecated from NPU version 1.5
			This table contains cumulative parameters per each CG (VoIP) Service
			defined for the system.
			All Statistics counters are accumulated since last reset "
		::=  { rbPMServ  1 }

	rbPMCGServConnEntry	OBJECT-TYPE
		SYNTAX		RbPMCGServConnEntry
		MAX-ACCESS	not-accessible
		STATUS		deprecated
		DESCRIPTION	
			"Entry in the rbPMCGServConnTable "
		INDEX		{  rbServiceID , rbPMCGConnDirection }
		::=  { rbPMCGServConnTable 1 }

	RbPMCGServConnEntry  ::=  SEQUENCE {
		rbPMCGConnDirection		INTEGER,
		rbPMCGConnByteReq    	Counter32,
		rbPMCGConnByteTx	   	Counter32,
		rbPMCGConnByteRetTx	   	Counter32,
		rbPMCGConnByteDropped  	Counter32,
		rbPMCGConnByteDiscarded Counter32,
		rbPMCGConnPktsReq  	    Counter32,
		rbPMCGConnPktsTx 	    Counter32,
		rbPMCGConnPktsDropped 	Counter32,
		rbPMCGConnPktsDiscarded Counter32,
		rbPMCGConnAvarageDelay 	Integer32,
		rbPMCGConnStandardDeviationDelay 	Integer32,
		rbPMCGConnMaxDelay 	        Integer32,
		rbPMCGConnPerSucsGrant 	    Counter32,
		rbPMCGConnAvgGrantInt 	    Counter32,
		rbPMCGConnMaxGrantInt 	    Counter32,
		rbPMCGConnAvgIntArvTime 	Counter32,
		rbPMCGConnMaxIntArvTime 	Counter32,
		rbPMCGConnMinIntArvTime 	Counter32,
		rbPMCGConnAvgSDUDropRate 	Counter32,
		rbPMCGConnResetCounters     Integer32
        }

	rbPMCGConnDirection   OBJECT-TYPE
		SYNTAX		    INTEGER 
		  				{
						  downLink (1),
						  upLink   (2)
						}
		MAX-ACCESS		read-only
		STATUS			deprecated
		DESCRIPTION		
				"The direction in which counters were measured . "
		::=  {  rbPMCGServConnEntry  1  }

	rbPMCGConnByteReq   OBJECT-TYPE
		SYNTAX		    Counter32 
		MAX-ACCESS		read-only
		STATUS			deprecated
		DESCRIPTION		
				"The number of bytes submitted by upper layers to this connection"
		::=  {  rbPMCGServConnEntry  2  }
		
	rbPMCGConnByteTx   OBJECT-TYPE
		SYNTAX		    Counter32 
		MAX-ACCESS		read-only
		STATUS			deprecated
		DESCRIPTION		
				"The number of bytes transmitted to WL port through this
				 connection including retransmissions."
		::=  {  rbPMCGServConnEntry  3 }
		
	rbPMCGConnByteRetTx   OBJECT-TYPE
		SYNTAX		    Counter32 
		MAX-ACCESS		read-only
		STATUS			deprecated
		DESCRIPTION		
				"The number of bytes retransmitted to WL port through this connection."
		::=  {  rbPMCGServConnEntry  4 }
		
	rbPMCGConnByteDropped   OBJECT-TYPE
		SYNTAX		    Counter32 
		MAX-ACCESS		read-only
		STATUS			deprecated
		DESCRIPTION		
				"The number of bytes dropped from this connection."
		::=  {  rbPMCGServConnEntry  5 }
		
	rbPMCGConnByteDiscarded   OBJECT-TYPE
		SYNTAX		    Counter32 
		MAX-ACCESS		read-only
		STATUS			deprecated
		DESCRIPTION		
				"The number of bytes discarded from this connection"
		::=  {  rbPMCGServConnEntry  6 }  
		
	rbPMCGConnPktsReq   OBJECT-TYPE
		SYNTAX		    Counter32 
		MAX-ACCESS		read-only
		STATUS			deprecated
		DESCRIPTION		
				"The number of packets submitted by upper layers to this connection"
		::=  {  rbPMCGServConnEntry  7 } 
		
	rbPMCGConnPktsTx   OBJECT-TYPE
		SYNTAX		    Counter32 
		MAX-ACCESS		read-only
		STATUS			deprecated
		DESCRIPTION		
				"The number of packets transmitted to WL through this connection 
				not including retransmissions."
		::=  {  rbPMCGServConnEntry  8 }
		
	rbPMCGConnPktsDropped   OBJECT-TYPE
		SYNTAX		    Counter32 
		MAX-ACCESS		read-only
		STATUS			deprecated
		DESCRIPTION		
				"The number of packets dropped by the transmitter for this connection"
		::=  {  rbPMCGServConnEntry  9 } 
		
	rbPMCGConnPktsDiscarded   OBJECT-TYPE
		SYNTAX		    Counter32 
		MAX-ACCESS		read-only
		STATUS			deprecated
		DESCRIPTION		
				"The number of packets discarded by the transmitter for this connection."
		::=  {  rbPMCGServConnEntry  10 }
		
	rbPMCGConnAvarageDelay   OBJECT-TYPE
		SYNTAX		    Integer32 
		MAX-ACCESS		read-only
		STATUS			deprecated
		DESCRIPTION		
				"Average packet delay in milliseconds, measured for this connection over the last 15 seconds."
		::=  {  rbPMCGServConnEntry  11 }						 		 		  								

	rbPMCGConnStandardDeviationDelay   OBJECT-TYPE
		SYNTAX		    Integer32 
		MAX-ACCESS		read-only
		STATUS			deprecated
		DESCRIPTION		
				"The variance of the packet delay, in milliseconds~2, 
				measured for this connection over the last 15 seconds."
		::=  {  rbPMCGServConnEntry  12 }						 		 		  								
		
	rbPMCGConnMaxDelay   OBJECT-TYPE
		SYNTAX		    Integer32 
		MAX-ACCESS		read-only
		STATUS			deprecated
		DESCRIPTION		
				"The maximum packet delay in milliseconds, 
				 measured for this connection over the last 15 seconds."
		::=  {  rbPMCGServConnEntry  13 }
				
	rbPMCGConnPerSucsGrant   OBJECT-TYPE
		SYNTAX		    Counter32 
		MAX-ACCESS		read-only
		STATUS			deprecated
		DESCRIPTION		
				"Percentage of successes in granting the transmission, 
				 measured for this Continuing Grant CONN over the last 15 seconds."
		::=  {  rbPMCGServConnEntry  14 }
		
	rbPMCGConnAvgGrantInt   OBJECT-TYPE
		SYNTAX		    Counter32 
		MAX-ACCESS		read-only
		STATUS			deprecated
		DESCRIPTION		
				"Average Grant Interval, in microseconds, 
				measured for this Continuing Grant CONN over the last 15 seconds."
		::=  {  rbPMCGServConnEntry  15 }
		
	rbPMCGConnMaxGrantInt   OBJECT-TYPE
		SYNTAX		    Counter32 
		MAX-ACCESS		read-only
		STATUS			deprecated
		DESCRIPTION		
				"Maximum Grant Interval, in microseconds, 
				measured for this Continuing Grant CONN over the last 15 seconds."
		::=  {  rbPMCGServConnEntry  16 }				

	rbPMCGConnAvgIntArvTime   OBJECT-TYPE
		SYNTAX		    Counter32 
		MAX-ACCESS		read-only
		STATUS			deprecated
		DESCRIPTION		
				"Average of the SDU Inter-Arrival Time Interval measured 
				 for this Continuing Grant CONN in the last 15 seconds."
		::=  {  rbPMCGServConnEntry  17 }
		
	rbPMCGConnMaxIntArvTime   OBJECT-TYPE
		SYNTAX		    Counter32 
		MAX-ACCESS		read-only
		STATUS			deprecated
		DESCRIPTION		
				"Maximum of the SDU Inter-Arrival Time Interval, 
				in microseconds, measured for this Continuing Grant CONN over the last 15 seconds."
		::=  {  rbPMCGServConnEntry  18 }
		
	rbPMCGConnMinIntArvTime   OBJECT-TYPE
		SYNTAX		    Counter32 
		MAX-ACCESS		read-only
		STATUS			deprecated
		DESCRIPTION		
				"Minimum of the SDU Inter-Arrival Time Interval, 
				 in microseconds, measured for this Continuing Grant CONN over the last 15 seconds."
		::=  {  rbPMCGServConnEntry  19 }
		
	rbPMCGConnAvgSDUDropRate   OBJECT-TYPE
		SYNTAX		    Counter32 
		MAX-ACCESS		read-only
		STATUS			deprecated
		DESCRIPTION		
				"Number of packets dropped per second for this connection, averaged over the last 15 seconds."
		::=  {  rbPMCGServConnEntry  20 }	
		
	rbPMCGConnResetCounters       	 OBJECT-TYPE
		SYNTAX		    Integer32 
		MAX-ACCESS		read-write
		STATUS			deprecated
		DESCRIPTION		
				"Resets the connection counters in this table entry"
		::=  {  rbPMCGServConnEntry  21 }
				
				
-- ###############################################################################
-- Per Connection Service Performance Indicators 
-- ###############################################################################

  rbPMServConnTable	OBJECT-TYPE
		SYNTAX		SEQUENCE  OF  RbPMServConnEntry
		MAX-ACCESS	not-accessible
		STATUS		current
		DESCRIPTION	
			"This table contains performance indication parameters per each connection
			 in the currently active services. All Statistics counters for BE, RT and NRT connections
			 are accumulated since last reset. Counters for active CG connections
			 are accumulated from session start time."
		::=  { rbPMServ  2 }

	rbPMServConnEntry	OBJECT-TYPE
		SYNTAX		RbPMServConnEntry
		MAX-ACCESS	not-accessible
		STATUS		current
		DESCRIPTION	
			"Entry in the rbPMServConnTable "
		INDEX		{rbServiceID, rbPMConnDirection, rbPMConnQoSPipeIdx}
		::=  { rbPMServConnTable 1 }

	RbPMServConnEntry  ::=  SEQUENCE {
		rbPMConnDirection			    INTEGER,
		rbPMConnQoSPipeIdx              Integer32,		
		rbPMConnByteReq     			Counter32,
		rbPMConnByteTx          		Counter32,
		rbPMConnByteRetTx       		Counter32,
		rbPMConnByteDropped       		Counter32,
		rbPMConnByteDiscarded       	Counter32,
		rbPMConnPktsReq       		    Counter32,
		rbPMConnPktsTx       		    Counter32,
		rbPMConnPktsDropped       		Counter32,
		rbPMConnPktsDiscarded       	Counter32,
		rbPMConnAvarageDelay       		Integer32,
		rbPMConnStandardDeviationDelay  Integer32,
		rbPMConnMaxDelay       		    Integer32,
		rbPMConnCBP       		        Gauge32,
		rbPMConnDLI       		        Gauge32,
		rbPMConnExBurst       		    Gauge32,
		rbPMConnAvgThroughput       	Gauge32,
		rbPMConnResetCounters       	INTEGER,
		rbPMConnServiceIdx              Unsigned32,
		rbPMConnQoSType					INTEGER,
		rbPMConnQosParam1				Unsigned32,
		rbPMConnQosParam2				Unsigned32,
		rbPMConnQosParamTime   			INTEGER
	 }

		
	rbPMConnDirection   OBJECT-TYPE
		SYNTAX		    INTEGER 
		  				{
						  downLink (1),
						  upLink   (2)
						}
		MAX-ACCESS		read-only
		STATUS			current
		DESCRIPTION		
				"The direction of the connection."
		::=  {  rbPMServConnEntry  1  }
				
	rbPMConnQoSPipeIdx   OBJECT-TYPE
		SYNTAX			Integer32 ( 1 .. 4 )
		MAX-ACCESS		read-only
		STATUS			current
		DESCRIPTION		
				"The index of the connection (up to 4) established for the Service."
		::=  {  rbPMServConnEntry  2  }		

	rbPMConnByteReq	  OBJECT-TYPE
		SYNTAX		 	Counter32   
		MAX-ACCESS		read-only
		STATUS			current
		DESCRIPTION		
				"The number of bytes submitted by upper layers to this connection."
		::=  {  rbPMServConnEntry  3  }

	rbPMConnByteTx     OBJECT-TYPE
		SYNTAX		 	Counter32   
		MAX-ACCESS		read-only
		STATUS			current
		DESCRIPTION		
				"The number of bytes transmitted to the wireless port through this connection,
				 including retransmissions."
		::=  {  rbPMServConnEntry  4  }

	rbPMConnByteRetTx  OBJECT-TYPE
		SYNTAX		 	Counter32   
		MAX-ACCESS		read-only
		STATUS			current
		DESCRIPTION		
				"The number of bytes retransmitted to the wireless port through this connection."
		::=  {  rbPMServConnEntry  5  }

	rbPMConnByteDropped  OBJECT-TYPE
		SYNTAX		 	Counter32   
		MAX-ACCESS		read-only
		STATUS			current
		DESCRIPTION		
				"The number of bytes dropped from this connection due to congestion in the wireless link.
				 Identical to rbPMConnByteDiscarded."
		::=  {  rbPMServConnEntry  6  }
		
	rbPMConnByteDiscarded  OBJECT-TYPE
		SYNTAX		 	Counter32   
		MAX-ACCESS		read-only
		STATUS			current
		DESCRIPTION		
				"The number of bytes discarded from this connection due to congestion in the wireless link.
				 Identical to rbPMConnByteDropped."
		::=  {  rbPMServConnEntry  7  }	
		
	rbPMConnPktsReq  OBJECT-TYPE
		SYNTAX		 	Counter32   
		MAX-ACCESS		read-only
		STATUS			current
		DESCRIPTION		
				"The number of packets submitted by upper layers to this connection."
		::=  {  rbPMServConnEntry  8  }	
		
	rbPMConnPktsTx  OBJECT-TYPE
		SYNTAX		 	Counter32   
		MAX-ACCESS		read-only
		STATUS			current
		DESCRIPTION		
				"The number of packets transmitted to the wireless port through this connection
				 not including retransmissions."
		::=  {  rbPMServConnEntry  9  }	

	rbPMConnPktsDropped  OBJECT-TYPE
		SYNTAX		 	Counter32   
		MAX-ACCESS		read-only
		STATUS			current
		DESCRIPTION		
				"The number of packets dropped by the transmitter for this connection due to
				 congestion in the wireless link. Identical to rbPMConnPktsDiscarded."
		::=  {  rbPMServConnEntry  10  }
		
	rbPMConnPktsDiscarded  OBJECT-TYPE
		SYNTAX		 	Counter32   
		MAX-ACCESS		read-only
		STATUS			current
		DESCRIPTION		
				"The number of packets discarded by the transmitter for this connection due to
				 congestion in the wireless link. Identical to rbPMConnPktsDropped."
		::=  {  rbPMServConnEntry  11  }
		
	rbPMConnAvarageDelay  OBJECT-TYPE
		SYNTAX		 	Integer32   
		MAX-ACCESS		read-only
		STATUS			current
		DESCRIPTION		
				"Average packet delay in milliseconds, measured for this connection
				 over the last 15 seconds. The value is updated every 15 seconds."
		::=  {  rbPMServConnEntry  12  }
		
	rbPMConnStandardDeviationDelay  OBJECT-TYPE
		SYNTAX		 	Integer32   
		MAX-ACCESS		read-only
		STATUS			current
		DESCRIPTION		
				"The variance (the standard deviation squared) of the packet delay,
				 in milliseconds square, measured for this connection over the last 15 seconds.
                 The value is updated every 15 seconds."
		::=  {  rbPMServConnEntry  13  }													
		
	rbPMConnMaxDelay  OBJECT-TYPE
		SYNTAX		 	Integer32   
		MAX-ACCESS		read-only
		STATUS			current
		DESCRIPTION		
				"The maximum packet delay in milliseconds, measured for this connection
				 over the last 15 seconds. The value is updated every 15 seconds."
		::=  {  rbPMServConnEntry  14  }
		
	rbPMConnCBP  OBJECT-TYPE
		SYNTAX		 	Gauge32   
		MAX-ACCESS		read-only
		STATUS			current
		DESCRIPTION		
				"The CIR utilization measured for an RT or NRT connection over the last 15 seconds.
				 Not applicable for BE and CG connections.
                 k = 100 x (the minimum between bytes transferred and CIR)/CIR is calculated for each
                 1 second interval. CIR Utilization equals the average of k over the last 15 seconds,
                 and may vary from 0 to 100. The value is updated every 15 seconds."
		::=  {  rbPMServConnEntry  15  }
		
	rbPMConnDLI  OBJECT-TYPE
		SYNTAX		 	Gauge32   
		MAX-ACCESS		read-only
		STATUS			current
		DESCRIPTION		
				"The percentage of dropped packets, out of the total demand,
				 measured for this connection over the last 15 seconds.
				 DLI (%) = 100*(Packets Dropped)/(Packets Submitted).
                 The value is updated every 15 seconds."
		::=  {  rbPMServConnEntry  16  }
		
	rbPMConnExBurst  OBJECT-TYPE
		SYNTAX		 	Gauge32   
		MAX-ACCESS		read-only
		STATUS			current
		DESCRIPTION		
				"Excess Information Rate utilization measured for a BE or NRT connection over the last 15 seconds.
				 Not applicable for RT and CG connections. 
                 k=100 x (bytes transferred-CIR)/(MIR-CIR) is calculated for each 1 second interval.
                 In BE CIR = 0. The EIR Utilization equals the average of k over the last 15 seconds,
                 and may range from 0 to 100. The value is updated every 15 seconds."
		::=  {  rbPMServConnEntry  17  }
		
	rbPMConnAvgThroughput  OBJECT-TYPE
		SYNTAX		 	Gauge32   
		MAX-ACCESS		read-only
		STATUS			current
		DESCRIPTION		
				"The average throughput, in bits/second, measured for this connection
				for the last 15 seconds. The value is updated every 15 seconds."
		::=  {  rbPMServConnEntry  18  }
	
	rbPMConnResetCounters  OBJECT-TYPE
		SYNTAX		 	INTEGER
		                {
                          noAction (0),
		                  reset (1)
	                    }   
		MAX-ACCESS		read-write
		STATUS			current
		DESCRIPTION		
				"When set to reset (1), the Service counters will be initialized to 0.
				 noAction (0) value is available to support Get and Get Next commands.
				 It should not be used in Set commands."
		::=  {  rbPMServConnEntry  19  }								
														
	rbPMConnServiceIdx	OBJECT-TYPE	
		SYNTAX			Unsigned32
		MAX-ACCESS		read-only
		STATUS			current
		DESCRIPTION		
				"The index of the relevant Service Entry."
		::=  {  rbPMServConnEntry  20  }
	
	rbPMConnQoSType	OBJECT-TYPE
	    SYNTAX   INTEGER  { rbCG (1),  rbRT ( 2 ) , rbNRT ( 3 ) , rbBE ( 4 ) }
		MAX-ACCESS		read-only
		STATUS			current
		DESCRIPTION		
				"The QoS Type used in the connection."
		::=  {  rbPMServConnEntry  21  }								
	
	rbPMConnQosParam1  OBJECT-TYPE
		SYNTAX		 	Unsigned32   
		MAX-ACCESS		read-only
		STATUS			current
		DESCRIPTION		
				"The value of rbQoSProfileParam1 of the QoS Profile used in the connection.
				 For RT and NRT connections, this parameter is the CIR (Kbps).
				 For CG connections this is the Packet Size (bytes).
				 For BE connection this parameter is not applicable."
		::=  {  rbPMServConnEntry  22  }								
	
	rbPMConnQosParam2  OBJECT-TYPE
		SYNTAX		 	Unsigned32   
		MAX-ACCESS		read-only
		STATUS			current
		DESCRIPTION		
				"The value of rbQoSProfileParam2 of the QoS Profile used in the connection.
				 For BE and NRT connections, this parameter is the MIR (Kbps).
				 For CG connections this is the Sample Interval (milliseconds).
				 For RT connections this parameter is not applicable."
		::=  {  rbPMServConnEntry  23  }								
	
	rbPMConnQosParamTime  OBJECT-TYPE
		SYNTAX			INTEGER { short ( 1 ) , medium ( 2 ) , long ( 3 ) } 
		MAX-ACCESS		read-only
		STATUS			current
		DESCRIPTION		
				"The value of rbQoSProfileParamTime of the QoS Profile used in the connection.
				 This is the CT (Committed Time) parameter that defines the time window over
				 which the information rate is averaged to ensure compliance with
				 the CIR and/or MIR parameter for BE, NRT and RT connections.
				 For CG connections this parameter is not applicable."
		::=  {  rbPMServConnEntry  24  }								
				

-- ####################################################################################
-- Packet Error Rate Counters 
-- PER counters are collected per SU and are retrieved using community SU.<MAC Address>
-- ####################################################################################
    rbPMPacketErrorRateTable OBJECT-TYPE
              SYNTAX  SEQUENCE OF RbPMPacketErrorRateEntry
              MAX-ACCESS  not-accessible
              STATUS  deprecated
              DESCRIPTION
                      "Deprecated. A table that contains Packet Error Rate (PER) Counters" 
              ::= { rbPerformance 4 }

    rbPMPacketErrorRateEntry OBJECT-TYPE
              SYNTAX  RbPMPacketErrorRateEntry
              MAX-ACCESS  not-accessible
              STATUS      deprecated
              DESCRIPTION
                      "Entry in the Packet Error Rate Table."
              INDEX   {rbPMDirection }
              ::= { rbPMPacketErrorRateTable 1 }

	RbPMPacketErrorRateEntry  ::=  SEQUENCE {
		rbPMDirection        	INTEGER,
		rbPMTotalBursts		 	Counter32,
		rbPMErrorBursts			Counter32,
		rbPMResetCounters		INTEGER
  		}


	rbPMDirection   OBJECT-TYPE
		SYNTAX		 	INTEGER
		                {
		                  downLink (1),
		                  upLink   (2)
		                }   
		MAX-ACCESS		read-only
		STATUS			deprecated
		DESCRIPTION		
				"The direction in which counters were measured."
		::=  {  rbPMPacketErrorRateEntry  1  }

	rbPMTotalBursts   OBJECT-TYPE
		SYNTAX		 	Counter32 
		MAX-ACCESS		read-only
		STATUS			deprecated
		DESCRIPTION		
				"The total number of bursts received by SU since the last reset of counters."
		::=  {  rbPMPacketErrorRateEntry  2  }

	rbPMErrorBursts   OBJECT-TYPE
		SYNTAX		 	Counter32 
		MAX-ACCESS		read-only
		STATUS			deprecated
		DESCRIPTION		
				"The total number of error bursts received by SU since the last reset of counters."
		::=  {  rbPMPacketErrorRateEntry  3  }

	rbPMResetCounters   OBJECT-TYPE
		SYNTAX		 	INTEGER {
		                          noAction (0),
		                          reset (1)
								}
		MAX-ACCESS		read-write
		STATUS			deprecated
		DESCRIPTION		
				"When Set to reset (1) PER Modulation Table counters are reset to 0."
		::=  {  rbPMPacketErrorRateEntry  4  }


-- ####################################################################################
-- Reset ifTable Counters 
-- For AU - <community>@AU.<Slot Number> is used.
-- For SU - <community>@SU.<MAC Address> is used
-- ####################################################################################
    rbPMIfCountersTable OBJECT-TYPE
              SYNTAX  SEQUENCE OF RbPMIfCountersEntry
              MAX-ACCESS  not-accessible
              STATUS  deprecated
              DESCRIPTION
                      "Deprecated from version 2.1. A table of interface Counters.
                       It is recommended to use the rbPMIfCounters (rbNPUDataPortCounters, rbManagementPortCounters,
					   rbSUEthernetCounters, rbSUWirelessCounters, rbAUBackplaneCounters, rbAUWirelessCounters)
                       rather than these counters." 
              ::= { rbPerformance 5 }

    rbPMIfCountersEntry OBJECT-TYPE
              SYNTAX  RbPMIfCountersEntry
              MAX-ACCESS  not-accessible
              STATUS      deprecated
              DESCRIPTION
                      "Entry in the rbPMIfCountersTable."
              INDEX   { ifIndex }
              ::= { rbPMIfCountersTable 1 }

	RbPMIfCountersEntry  ::=  SEQUENCE {
		rbPMIfInResetCounters       INTEGER,
		rbPMIfInForwardedBytes		Counter32,
		rbPMIfInInternalBytes		Counter32,
		rbPMIfInDiscardedBytes		Counter32,
     	rbPMIfOutInternalPackets 	Counter32,
		rbPMIfOutResetCounters      INTEGER,
		rbPMIfOutSubmittedBytes		Counter32,
		rbPMIfOutInternalBytes		Counter32,
		rbPMIfOutDiscardedBytes		Counter32
 		}


	rbPMIfInResetCounters   OBJECT-TYPE
		SYNTAX		 	INTEGER
		                {
                          noAction (0),
		                  reset (1)
	                    }   
		MAX-ACCESS		read-write
		STATUS			deprecated
		DESCRIPTION		
				"When set to reset (1), In counters of the specified interface on the specified
				 device will be initialised to 0."
		::=  {  rbPMIfCountersEntry  1  }

	rbPMIfInForwardedBytes   OBJECT-TYPE
		SYNTAX		 	Counter32
		MAX-ACCESS		read-only
		STATUS			deprecated
		DESCRIPTION		
				"Number of bytes submitted to interface."
		::=  {  rbPMIfCountersEntry 2  }

	rbPMIfInInternalBytes   OBJECT-TYPE
		SYNTAX		 	Counter32
		MAX-ACCESS		read-only
		STATUS			deprecated
		DESCRIPTION		
				"Number of bytes submitted to Internal Port."
		::=  {  rbPMIfCountersEntry 3  }

	rbPMIfInDiscardedBytes   OBJECT-TYPE
		SYNTAX		 	Counter32
		MAX-ACCESS		read-only
		STATUS			deprecated
		DESCRIPTION		
				"Number of bytes discarded when received from the interface."
		::=  {  rbPMIfCountersEntry 4  }

	rbPMIfOutInternalPackets   OBJECT-TYPE
		SYNTAX		 	Counter32
		MAX-ACCESS		read-only
		STATUS			deprecated
		DESCRIPTION		
				"Number of packets, created internally by device and transmitted through the
				 wireless interface. Value 0 should be returned for the Ethernet Interface."
		::=  {  rbPMIfCountersEntry 5  }
		
	rbPMIfOutResetCounters   OBJECT-TYPE
		SYNTAX		 	INTEGER
		                {
                          noAction (0),
		                  reset (1)
	                    }   
		MAX-ACCESS		read-write
		STATUS			deprecated
		DESCRIPTION		
				"When set to reset (1), Out counters of the specified interface on the specified
				 device will be initialised to 0."
		::=  {  rbPMIfCountersEntry  6  }		

	rbPMIfOutSubmittedBytes   OBJECT-TYPE
		SYNTAX		 	Counter32
		MAX-ACCESS		read-only
		STATUS			deprecated
		DESCRIPTION		
				"Number of bytes submitted from intetface."
		::=  {  rbPMIfCountersEntry 7  }

	rbPMIfOutInternalBytes   OBJECT-TYPE
		SYNTAX		 	Counter32
		MAX-ACCESS		read-only
		STATUS			deprecated
		DESCRIPTION		
				"Number of bytes submitted from Internal Port."
		::=  {  rbPMIfCountersEntry 8  }

	rbPMIfOutDiscardedBytes   OBJECT-TYPE
		SYNTAX		 	Counter32
		MAX-ACCESS		read-only
		STATUS			deprecated
		DESCRIPTION		
				"Number of bytes discarded during the transmit through the interface."
		::=  {  rbPMIfCountersEntry 9  }


-- ####################################################################################
-- Burst Error Rate Counters 
-- ####################################################################################

	rbPMBurstErrRateCounters	OBJECT IDENTIFIER
		::=  {  rbPerformance  6  }

    rbPMBurstErrorRateTable OBJECT-TYPE
              SYNTAX  SEQUENCE OF RbPMBurstErrorRateEntry
              MAX-ACCESS  not-accessible
              STATUS  current
              DESCRIPTION
                      "A table that contains Burst Error Rate (BER) Counters for each Rate
                       in the Uplink and Downlink of each SU." 
              ::= { rbPMBurstErrRateCounters 1 }

    rbPMBurstErrorRateEntry OBJECT-TYPE
              SYNTAX  RbPMBurstErrorRateEntry
              MAX-ACCESS  not-accessible
              STATUS      current
              DESCRIPTION
                      "Entry in the Burst Error Rate Table."
              INDEX   {rbPMBurstSuMacAddr, rbPMBurstDirection, rbPMBurstRate}
              ::= { rbPMBurstErrorRateTable 1 }

	RbPMBurstErrorRateEntry  ::=  SEQUENCE {
	    rbPMBurstSuMacAddr 	    MacAddress,
		rbPMBurstDirection      INTEGER,
		rbPMBurstRate           Modulation,
		rbPMBurstCountersReset	INTEGER,
		rbPMBurstTotal		 	Counter32,
		rbPMBurstError			Counter32,
		rbPMBurstErrorRate		DisplayString
  		}


	rbPMBurstSuMacAddr	OBJECT-TYPE	
		SYNTAX			MacAddress
		MAX-ACCESS		read-only
		STATUS			current
		DESCRIPTION		
				"MAC Address of SU." 
		::=  {  rbPMBurstErrorRateEntry  1  }

	rbPMBurstDirection   OBJECT-TYPE
		SYNTAX		 	INTEGER
		                {
		                  downLink (1),
		                  upLink   (2)
		                }   
		MAX-ACCESS		read-only
		STATUS			current
		DESCRIPTION		
				"The direction in which counters were measured."
		::=  {  rbPMBurstErrorRateEntry  2  }

	rbPMBurstRate	 OBJECT-TYPE
		SYNTAX			Modulation 
		MAX-ACCESS		read-only
		STATUS			current
		DESCRIPTION		
				"The Modulation and Coding Rate of the entry."
		DEFVAL			{ 1 }
		::=  {  rbPMBurstErrorRateEntry 3 }
		
	rbPMBurstCountersReset   OBJECT-TYPE
		SYNTAX		 	INTEGER
		                {
                          noAction (0),
		                  reset (1)
	                    }   
		MAX-ACCESS		read-write
		STATUS			current
		DESCRIPTION		
				"Reset the BER Counters for the selected SU, for all rates in the relevant direction.
				 noAction (0) value is available to support Get and Get Next commands.
				 It should not be used in Set commands."
		::=  {  rbPMBurstErrorRateEntry  4  }		

	rbPMBurstTotal   OBJECT-TYPE
		SYNTAX		 	Counter32
		MAX-ACCESS		read-only
		STATUS			current
		DESCRIPTION		
				"Number of Bursts transmitted to/from the SU at the relevant rate and direction."
		::=  {  rbPMBurstErrorRateEntry 5  }

	rbPMBurstError   OBJECT-TYPE
		SYNTAX		 	Counter32
		MAX-ACCESS		read-only
		STATUS			current
		DESCRIPTION		
				"Number of Error Bursts at the relevant rate and direction."
		::=  {  rbPMBurstErrorRateEntry 6  }

    rbPMBurstErrorRate	 OBJECT-TYPE
		SYNTAX			DisplayString 
		MAX-ACCESS		read-only
		STATUS			current
		DESCRIPTION		
				"The Burst Error Rate for the relevant rate and direction (100*Burst Error/Burst Total)."
		::=  {  rbPMBurstErrorRateEntry 7 }


-- ####################################################################################
-- ifTable Counters 
-- For NPU .
-- For AU .
-- For SU .
-- ####################################################################################

	rbPMIfCounters	OBJECT IDENTIFIER
		::=  {  rbPerformance  7  }

	rbNPUDataPortCounters	OBJECT IDENTIFIER
		::=  {  rbPMIfCounters  1  }

	rbMBSTDataPortCounters	OBJECT IDENTIFIER
		::=  {  rbPMIfCounters  2  }

	rbManagementPortCounters	OBJECT IDENTIFIER
		::=  {  rbPMIfCounters  10  }

	rbSUEthernetCounters	OBJECT IDENTIFIER
		::=  {  rbPMIfCounters  20  }

	rbSUWirelessCounters	OBJECT IDENTIFIER
		::=  {  rbPMIfCounters  21  }

	rbAUBackplaneCounters	OBJECT IDENTIFIER
		::=  {  rbPMIfCounters  30  }

	rbAUWirelessCounters	OBJECT IDENTIFIER
		::=  {  rbPMIfCounters  31  }


-- ####################################################################################
    rbNPUDataPortCountersTable OBJECT-TYPE
              SYNTAX  SEQUENCE OF RbNPUDataPortCountersEntry
              MAX-ACCESS  not-accessible
              STATUS  current
              DESCRIPTION
                      "A table of NPU Data port counters." 
              ::= { rbNPUDataPortCounters 1 }

    rbNPUDataPortCountersEntry OBJECT-TYPE
              SYNTAX  RbNPUDataPortCountersEntry
              MAX-ACCESS  not-accessible
              STATUS      current
              DESCRIPTION
                      "Entry in the rbNPUDataPortCountersTable."
              INDEX   { rbPMIfSlot }
              ::= { rbNPUDataPortCountersTable 1 }

	RbNPUDataPortCountersEntry  ::=  SEQUENCE {
	    rbPMIfSlot 	                    Integer32,
		rbNpuDataPortResetCounters      INTEGER,
		rbNpuDataPortTotalPacketsRx     Counter32,
		rbNpuDataPortMangementPacketsFw Counter32,
		rbNpuDataPortPacketsFwToSlot1   Counter32,
		rbNpuDataPortPacketsFwToSlot2   Counter32,
		rbNpuDataPortPacketsFwToSlot3   Counter32,
		rbNpuDataPortPacketsFwToSlot4   Counter32,
		rbNpuDataPortPacketsFwToSlot7   Counter32,
		rbNpuDataPortPacketsFwToSlot8   Counter32,
		rbNpuDataPortPacketsFwToSlot9   Counter32,
		rbNpuDataPortPacketsDiscardedOnRx   Counter32,
		rbNpuDataPortTotalPacketsTx         Counter32,
		rbNpuDataPortMangementPacketsSbmt   Counter32,
		rbNpuDataPortPacketsSbmtFromSlot1   Counter32,
		rbNpuDataPortPacketsSbmtFromSlot2   Counter32,
		rbNpuDataPortPacketsSbmtFromSlot3   Counter32,
		rbNpuDataPortPacketsSbmtFromSlot4   Counter32,
		rbNpuDataPortPacketsSbmtFromSlot7   Counter32,
		rbNpuDataPortPacketsSbmtFromSlot8   Counter32,
		rbNpuDataPortPacketsSbmtFromSlot9   Counter32,
		rbNpuDataPortPacketsDiscardedOnTx   Counter32
 		}


	rbPMIfSlot	OBJECT-TYPE	
		SYNTAX			Integer32 ( 5 .. 6 )
		MAX-ACCESS		read-only
		STATUS			current
		DESCRIPTION		
				"The NPU's slot number: 5 or 6. In current version only 5 is applicable." 
		::=  {  rbNPUDataPortCountersEntry  1  }

	rbNpuDataPortResetCounters   OBJECT-TYPE
		SYNTAX		 	INTEGER
		                {
                          noAction (0),
		                  reset (1)
	                    }   
		MAX-ACCESS		read-write
		STATUS			current
		DESCRIPTION		
				"When set to reset (1), the Data port counters will be initialized to 0.
				 noAction (0) value is available to support Get and Get Next commands.
				 It should not be used in Set commands."
		::=  {  rbNPUDataPortCountersEntry  2  }

	rbNpuDataPortTotalPacketsRx   OBJECT-TYPE
		SYNTAX		 	Counter32
		MAX-ACCESS		read-only
		STATUS			current
		DESCRIPTION		
				"The total number of packets received on the interface.
				 Packets with errors are not counted."
		::=  {  rbNPUDataPortCountersEntry 3  }

	rbNpuDataPortMangementPacketsFw   OBJECT-TYPE
		SYNTAX		 	Counter32
		MAX-ACCESS		read-only
		STATUS			current
		DESCRIPTION		
				"The total number of management packets
				 (packets whose destination is the NPU, and broadcasts)
				 received on the Data port and forwarded to the NPU's internal management."
		::=  {  rbNPUDataPortCountersEntry 4  }

	rbNpuDataPortPacketsFwToSlot1   OBJECT-TYPE
		SYNTAX		 	Counter32
		MAX-ACCESS		read-only
		STATUS			current
		DESCRIPTION		
				"The total number of packets received from the Data port and forwarded
				 by the NPU to AU Slot 1."
		::=  {  rbNPUDataPortCountersEntry 5  }

	rbNpuDataPortPacketsFwToSlot2   OBJECT-TYPE
		SYNTAX		 	Counter32
		MAX-ACCESS		read-only
		STATUS			current
		DESCRIPTION		
				"The total number of packets received from the Data port and forwarded
				 by the NPU to AU Slot 2."
		::=  {  rbNPUDataPortCountersEntry 6  }

	rbNpuDataPortPacketsFwToSlot3   OBJECT-TYPE
		SYNTAX		 	Counter32
		MAX-ACCESS		read-only
		STATUS			current
		DESCRIPTION		
				"The total number of packets received from the Data port and forwarded
				 by the NPU to AU Slot 3."
		::=  {  rbNPUDataPortCountersEntry 7  }

	rbNpuDataPortPacketsFwToSlot4   OBJECT-TYPE
		SYNTAX		 	Counter32
		MAX-ACCESS		read-only
		STATUS			current
		DESCRIPTION		
				"The total number of packets received from the Data port and forwarded
				 by the NPU to AU Slot 4."
		::=  {  rbNPUDataPortCountersEntry 8  }

	rbNpuDataPortPacketsFwToSlot7   OBJECT-TYPE
		SYNTAX		 	Counter32
		MAX-ACCESS		read-only
		STATUS			current
		DESCRIPTION		
				"The total number of packets received from the Data port and forwarded
				 by the NPU to AU Slot 7."
		::=  {  rbNPUDataPortCountersEntry 9  }

	rbNpuDataPortPacketsFwToSlot8   OBJECT-TYPE
		SYNTAX		 	Counter32
		MAX-ACCESS		read-only
		STATUS			current
		DESCRIPTION		
				"The total number of packets received from the Data port and forwarded
				 by the NPU to AU Slot 8."
		::=  {  rbNPUDataPortCountersEntry 10  }

	rbNpuDataPortPacketsFwToSlot9   OBJECT-TYPE
		SYNTAX		 	Counter32
		MAX-ACCESS		read-only
		STATUS			current
		DESCRIPTION		
				"The total number of packets received from the Data port and forwarded
				 by the NPU to AU Slot 9."
		::=  {  rbNPUDataPortCountersEntry 11  }

	rbNpuDataPortPacketsDiscardedOnRx   OBJECT-TYPE
		SYNTAX		 	Counter32
		MAX-ACCESS		read-only
		STATUS			current
		DESCRIPTION		
				"The total number of packets received from the Data port that were discarded
				 due to switching and classification failures."
		::=  {  rbNPUDataPortCountersEntry 12  }

	rbNpuDataPortTotalPacketsTx   OBJECT-TYPE
		SYNTAX		 	Counter32
		MAX-ACCESS		read-only
		STATUS			current
		DESCRIPTION		
				"The total number of packets transmitted to the interface.
				 Packets with errors are not counted.."
		::=  {  rbNPUDataPortCountersEntry 13  }

	rbNpuDataPortMangementPacketsSbmt   OBJECT-TYPE
		SYNTAX		 	Counter32
		MAX-ACCESS		read-only
		STATUS			current
		DESCRIPTION		
				"The total number of management packets submitted by the NPU to the Data port."
		::=  {  rbNPUDataPortCountersEntry 14  }

	rbNpuDataPortPacketsSbmtFromSlot1   OBJECT-TYPE
		SYNTAX		 	Counter32
		MAX-ACCESS		read-only
		STATUS			current
		DESCRIPTION		
				"The total number of packets received by the NPU from the AU in Slot 1
				 and submitted to the Data port."
		::=  {  rbNPUDataPortCountersEntry 15  }

	rbNpuDataPortPacketsSbmtFromSlot2   OBJECT-TYPE
		SYNTAX		 	Counter32
		MAX-ACCESS		read-only
		STATUS			current
		DESCRIPTION		
				"The total number of packets received by the NPU from the AU in Slot 2
				 and submitted to the Data port."
		::=  {  rbNPUDataPortCountersEntry 16  }

	rbNpuDataPortPacketsSbmtFromSlot3   OBJECT-TYPE
		SYNTAX		 	Counter32
		MAX-ACCESS		read-only
		STATUS			current
		DESCRIPTION		
				"The total number of packets received by the NPU from the AU in Slot 3
				 and submitted to the Data port."
		::=  {  rbNPUDataPortCountersEntry 17  }

	rbNpuDataPortPacketsSbmtFromSlot4   OBJECT-TYPE
		SYNTAX		 	Counter32
		MAX-ACCESS		read-only
		STATUS			current
		DESCRIPTION		
				"The total number of packets received by the NPU from the AU in Slot 4
				 and submitted to the Data port."
		::=  {  rbNPUDataPortCountersEntry 18  }

	rbNpuDataPortPacketsSbmtFromSlot7   OBJECT-TYPE
		SYNTAX		 	Counter32
		MAX-ACCESS		read-only
		STATUS			current
		DESCRIPTION		
				"The total number of packets received by the NPU from the AU in Slot 7
				 and submitted to the Data port."
		::=  {  rbNPUDataPortCountersEntry 19  }

	rbNpuDataPortPacketsSbmtFromSlot8   OBJECT-TYPE
		SYNTAX		 	Counter32
		MAX-ACCESS		read-only
		STATUS			current
		DESCRIPTION		
				"The total number of packets received by the NPU from the AU in Slot 8
				 and submitted to the Data port."
		::=  {  rbNPUDataPortCountersEntry 20  }

	rbNpuDataPortPacketsSbmtFromSlot9   OBJECT-TYPE
		SYNTAX		 	Counter32
		MAX-ACCESS		read-only
		STATUS			current
		DESCRIPTION		
				"The total number of packets received by the NPU from the AU in Slot 9
				 and submitted to the Data port."
		::=  {  rbNPUDataPortCountersEntry 21  }

	rbNpuDataPortPacketsDiscardedOnTx   OBJECT-TYPE
		SYNTAX		 	Counter32
		MAX-ACCESS		read-only
		STATUS			current
		DESCRIPTION		
				"Always 0. Currently packets are not discarded on Tx to the Data port."
		::=  {  rbNPUDataPortCountersEntry 22  }


-- ####################################################################################
    rbMBSTDataPortCountersTable OBJECT-TYPE
              SYNTAX  SEQUENCE OF RbMBSTDataPortCountersEntry
              MAX-ACCESS  not-accessible
              STATUS  current
              DESCRIPTION
                      "A table of MBST Data port counters." 
              ::= { rbMBSTDataPortCounters 1 }

    rbMBSTDataPortCountersEntry OBJECT-TYPE
              SYNTAX  RbMBSTDataPortCountersEntry
              MAX-ACCESS  not-accessible
              STATUS      current
              DESCRIPTION
                      "Entry in the rbMBSTDataPortCountersTable."
              INDEX   { rbMBSTDataPortIfSlot }
              ::= { rbMBSTDataPortCountersTable 1 }

	RbMBSTDataPortCountersEntry  ::=  SEQUENCE {
	    rbMBSTDataPortIfSlot 	             Integer32,
		rbMBSTDataPortResetCounters          INTEGER,
		rbMBSTDataPortTotalBytesRx           Counter32,
		rbMBSTDataPortDataBytesRx            Counter32,
		rbMBSTDataPortDataBytesDiscardedOnRx Counter32,
		rbMBSTDataPortTotalBytesTx           Counter32,
		rbMBSTDataPortDataBytesTx            Counter32,
		rbMBSTDataPortDataBytesDiscardedOnTx Counter32
 		}


	rbMBSTDataPortIfSlot	OBJECT-TYPE	
		SYNTAX			Integer32 ( 1 )
		MAX-ACCESS		read-only
		STATUS			current
		DESCRIPTION		
				"The MBST Data Port Table index - always 1." 
		::=  {  rbMBSTDataPortCountersEntry  1  }

	rbMBSTDataPortResetCounters   OBJECT-TYPE
		SYNTAX		 	INTEGER
		                {
                          noAction (0),
		                  reset (1)
	                    }   
		MAX-ACCESS		read-write
		STATUS			current
		DESCRIPTION		
				"When set to reset (1), the Data port counters will be initialized to 0.
				 noAction (0) value is available to support Get and Get Next commands.
				 It should not be used in Set commands."
		::=  {  rbMBSTDataPortCountersEntry  2  }

	rbMBSTDataPortTotalBytesRx   OBJECT-TYPE
		SYNTAX		 	Counter32
		MAX-ACCESS		read-only
		STATUS			current
		DESCRIPTION		
				"The total number of bytes received from the Data port, including Management frames.
				 Frames with errors are not included."
		::=  {  rbMBSTDataPortCountersEntry 3  }

	rbMBSTDataPortDataBytesRx   OBJECT-TYPE
		SYNTAX		 	Counter32
		MAX-ACCESS		read-only
		STATUS			current
		DESCRIPTION		
				"The total number of data bytes received from the Data port.
				 Management frames and frames with errors are not included."
		::=  {  rbMBSTDataPortCountersEntry 4  }

	rbMBSTDataPortDataBytesDiscardedOnRx   OBJECT-TYPE
		SYNTAX		 	Counter32
		MAX-ACCESS		read-only
		STATUS			current
		DESCRIPTION		
				"The total number of bytes in data packets received from the Data port
				 that were discarded due to switching and classification failures."
		::=  {  rbMBSTDataPortCountersEntry 5  }

	rbMBSTDataPortTotalBytesTx   OBJECT-TYPE
		SYNTAX		 	Counter32
		MAX-ACCESS		read-only
		STATUS			current
		DESCRIPTION		
				"The total number of bytes transmitted to the Data port, including Management frames.
				 Frames with errors are not included."
		::=  {  rbMBSTDataPortCountersEntry 6  }

	rbMBSTDataPortDataBytesTx   OBJECT-TYPE
		SYNTAX		 	Counter32
		MAX-ACCESS		read-only
		STATUS			current
		DESCRIPTION		
				"The total number of data bytes transmitted to the Data port.
				 Management frames and frames with errors are not included."
		::=  {  rbMBSTDataPortCountersEntry 7  }

	rbMBSTDataPortDataBytesDiscardedOnTx   OBJECT-TYPE
		SYNTAX		 	Counter32
		MAX-ACCESS		read-only
		STATUS			current
		DESCRIPTION		
				"This count is always 0 (No discards)."
		::=  {  rbMBSTDataPortCountersEntry 8  }


-- ####################################################################################
    rbMngmntPortCountersTable OBJECT-TYPE
              SYNTAX  SEQUENCE OF RbMngmntPortCountersEntry
              MAX-ACCESS  not-accessible
              STATUS  current
              DESCRIPTION
                      "A table of Management port counters." 
              ::= { rbManagementPortCounters 1 }

    rbMngmntPortCountersEntry OBJECT-TYPE
              SYNTAX  RbMngmntPortCountersEntry
              MAX-ACCESS  not-accessible
              STATUS      current
              DESCRIPTION
                      "Entry in the rbMngmntPortCountersTable."
              INDEX   { rbMngmntPortIfSlot }
              ::= { rbMngmntPortCountersTable 1 }

	RbMngmntPortCountersEntry  ::=  SEQUENCE {
		rbMngmntPortResetCounters          INTEGER,
		rbMngmntPortPacketsRx			   Counter32,
		rbMngmntPortPacketsDiscardedOnRx   Counter32,
		rbMngmntPortPacketsTx              Counter32,
		rbMngmntPortPacketsDiscardedOnTx   Counter32,
	    rbMngmntPortIfSlot 	               Integer32
 		}


	rbMngmntPortResetCounters   OBJECT-TYPE
		SYNTAX		 	INTEGER
		                {
                          noAction (0),
		                  reset (1)
	                    }   
		MAX-ACCESS		read-write
		STATUS			current
		DESCRIPTION		
				"When set to reset (1), the Management port counters will be initialized to 0.
				 noAction (0) value is available to support Get and Get Next commands.
				 It should not be used in Set commands."
		::=  {  rbMngmntPortCountersEntry  1  }

	rbMngmntPortPacketsRx   OBJECT-TYPE
		SYNTAX		 	Counter32
		MAX-ACCESS		read-only
		STATUS			current
		DESCRIPTION		
				"The total number of packets received on the Management port.
				 Error packets are not counted."
		::=  {  rbMngmntPortCountersEntry 2  }

	rbMngmntPortPacketsDiscardedOnRx   OBJECT-TYPE
		SYNTAX		 	Counter32
		MAX-ACCESS		read-only
		STATUS			current
		DESCRIPTION		
				"The total number of packets received on the Management port that were discarded."
		::=  {  rbMngmntPortCountersEntry 3  }

	rbMngmntPortPacketsTx   OBJECT-TYPE
		SYNTAX		 	Counter32
		MAX-ACCESS		read-only
		STATUS			current
		DESCRIPTION		
				"The total number of packets transmitted on the Management port.
				 Error packets are not counted."
		::=  {  rbMngmntPortCountersEntry 4  }

	rbMngmntPortPacketsDiscardedOnTx   OBJECT-TYPE
		SYNTAX		 	Counter32
		MAX-ACCESS		read-only
		STATUS			current
		DESCRIPTION		
				"The total number of packet discarded on Tx on the Management port."
		::=  {  rbMngmntPortCountersEntry 5  }

	rbMngmntPortIfSlot	OBJECT-TYPE	
		SYNTAX			Integer32 ( 1 .. 6 )
		MAX-ACCESS		read-only
		STATUS			current
		DESCRIPTION		
				"For NPU - the NPU's slot number: 5 or 6. In current version only 5 is applicable.
				 For MBST - the MBST Management Port Table index (always 1)." 
		::=  {  rbMngmntPortCountersEntry  6  }


-- ####################################################################################
    rbSUEthernetCountersTable OBJECT-TYPE
              SYNTAX  SEQUENCE OF RbSUEthernetCountersEntry
              MAX-ACCESS  not-accessible
              STATUS  current
              DESCRIPTION
                      "A table of SU Ethernet port Counters" 
              ::= { rbSUEthernetCounters 1 }

    rbSUEthernetCountersEntry OBJECT-TYPE
              SYNTAX  RbSUEthernetCountersEntry
              MAX-ACCESS  not-accessible
              STATUS      current
              DESCRIPTION
                      "Entry in the rbSUEthernetCountersTable."
              INDEX   { rbPMIfSuMacAddr }
              ::= { rbSUEthernetCountersTable 1 }

	RbSUEthernetCountersEntry  ::=  SEQUENCE {
	    rbPMIfSuMacAddr 	               MacAddress,
		rbSUEthernetResetCounters          INTEGER,
		rbSUEthernetDataBytesRx            Counter32,
		rbSUEthernetDataBytesDiscardedOnRx Counter32,
		rbSUEthernetDataBytesTx            Counter32,
		rbSUEthernetDataBytesDiscardedOnTx Counter32
 		}


	rbPMIfSuMacAddr	OBJECT-TYPE	
		SYNTAX			MacAddress
		MAX-ACCESS		read-only
		STATUS			current
		DESCRIPTION		
				"MAC Address of SU." 
		::=  {  rbSUEthernetCountersEntry  1  }

	rbSUEthernetResetCounters   OBJECT-TYPE
		SYNTAX		 	INTEGER
		                {
                          noAction (0),
		                  reset (1)
	                    }   
		MAX-ACCESS		read-write
		STATUS			current
		DESCRIPTION		
				"When set to reset (1), the SU Ethernet port counters will be initialized to 0.
				 noAction (0) value is available to support Get and Get Next commands.
				 It should not be used in Set commands."
		::=  {  rbSUEthernetCountersEntry  2  }

	rbSUEthernetDataBytesRx   OBJECT-TYPE
		SYNTAX		 	Counter32
		MAX-ACCESS		read-only
		STATUS			current
		DESCRIPTION		
				"The total number of data bytes received on the Ethernet port,
				 excluding management frames and errors."
		::=  {  rbSUEthernetCountersEntry 3  }

	rbSUEthernetDataBytesDiscardedOnRx   OBJECT-TYPE
		SYNTAX		 	Counter32
		MAX-ACCESS		read-only
		STATUS			current
		DESCRIPTION		
				"The total number of data bytes discarded when a packet received
				 from the Ethernet is not forwarded to the Wireless port due to bridging
				 and classification considerations."
		::=  {  rbSUEthernetCountersEntry 4  }

	rbSUEthernetDataBytesTx   OBJECT-TYPE
		SYNTAX		 	Counter32
		MAX-ACCESS		read-only
		STATUS			current
		DESCRIPTION		
				"The total number of data bytes transmitted on the Ethernet port,
				 excluding management frames and errors."
		::=  {  rbSUEthernetCountersEntry 5  }

	rbSUEthernetDataBytesDiscardedOnTx   OBJECT-TYPE
		SYNTAX		 	Counter32
		MAX-ACCESS		read-only
		STATUS			current
		DESCRIPTION		
				"The total number of data bytes discarded when a packet received on
				 the Wireless port is not forwarded to the Ethernet due to bridging
				 and VLAN considerations."
		::=  {  rbSUEthernetCountersEntry 6  }


-- ####################################################################################
    rbSUWirelessCountersTable OBJECT-TYPE
              SYNTAX  SEQUENCE OF RbSUWirelessCountersEntry
              MAX-ACCESS  not-accessible
              STATUS  current
              DESCRIPTION
                      "A table of SU Wireless port Counters." 
              ::= { rbSUWirelessCounters 1 }

    rbSUWirelessCountersEntry OBJECT-TYPE
              SYNTAX  RbSUWirelessCountersEntry
              MAX-ACCESS  not-accessible
              STATUS      current
              DESCRIPTION
                      "Entry in the rbSUWirelessCountersTable."
              INDEX   { rbPMIfSuMacAddr }
              ::= { rbSUWirelessCountersTable 1 }

	RbSUWirelessCountersEntry  ::=  SEQUENCE {
		rbSUWirelessResetCounters          INTEGER,
		rbSUWirelessDataBytesRx            Counter32,
		rbSUWirelessDataBytesDiscardedOnRx Counter32,
		rbSUWirelessDataBytesTx            Counter32,
		rbSUWirelessDataBytesDiscardedOnTx Counter32,
		rbSUWirelessARQEnabledBytesTx      Counter32,
		rbSUWirelessRTxBytes               Counter32,
		rbSUWirelessRTxRate                Gauge32
 		}


	rbSUWirelessResetCounters   OBJECT-TYPE
		SYNTAX		 	INTEGER
		                {
                          noAction (0),
		                  reset (1)
	                    }   
		MAX-ACCESS		read-write
		STATUS			current
		DESCRIPTION		
				"When set to reset (1), the SU Wireless port counters will be initialized to 0.
				 noAction (0) value is available to support Get and Get Next commands.
				 It should not be used in Set commands."
		::=  {  rbSUWirelessCountersEntry  1  }

	rbSUWirelessDataBytesRx   OBJECT-TYPE
		SYNTAX		 	Counter32
		MAX-ACCESS		read-only
		STATUS			current
		DESCRIPTION		
				"The total number of data bytes received on the Wireless port,
				 excluding management frames and errors."
		::=  {  rbSUWirelessCountersEntry 2  }

	rbSUWirelessDataBytesDiscardedOnRx   OBJECT-TYPE
		SYNTAX		 	Counter32
		MAX-ACCESS		read-only
		STATUS			current
		DESCRIPTION		
				"The total number of data bytes in packets discarded on Rx
				 on the Wireless port due to MAC protocol RX errors, such as
				 duplicate sequence number, wrong sequence number etc. (not CRC errors)."
		::=  {  rbSUWirelessCountersEntry 3  }

	rbSUWirelessDataBytesTx   OBJECT-TYPE
		SYNTAX		 	Counter32
		MAX-ACCESS		read-only
		STATUS			current
		DESCRIPTION		
				"The total number of data bytes transmitted on the Wireless port,
				 excluding MAC management frames and errors."
		::=  {  rbSUWirelessCountersEntry 4  }

	rbSUWirelessDataBytesDiscardedOnTx   OBJECT-TYPE
		SYNTAX		 	Counter32
		MAX-ACCESS		read-only
		STATUS			current
		DESCRIPTION		
				"The total number of data bytes in packets discarded on Tx
				 due to congestion in the wireless medium."
		::=  {  rbSUWirelessCountersEntry 5  }

	rbSUWirelessARQEnabledBytesTx   OBJECT-TYPE
		SYNTAX		 	Counter32
		MAX-ACCESS		read-only
		STATUS			current
		DESCRIPTION		
				"The total number of bytes transmitted over BE and NRT connections.
				 Applicable only if the ARQ mechanism is enabled."
		::=  {  rbSUWirelessCountersEntry 6  }

	rbSUWirelessRTxBytes   OBJECT-TYPE
		SYNTAX		 	Counter32
		MAX-ACCESS		read-only
		STATUS			current
		DESCRIPTION		
				"The total number of unacknowledged bytes that were retransmitted.
				 Retransmissions are applicable only to BE and NRT connections
				 provided the ARQ mechanism is enabled."
		::=  {  rbSUWirelessCountersEntry 7  }
		
	rbSUWirelessRTxRate  OBJECT-TYPE
		SYNTAX		 	Gauge32   
		MAX-ACCESS		read-only
		STATUS			current
		DESCRIPTION		
				"Retransmission Rate in percents: 
				 100*(Bytes Retransmitted)/(ARQ Enabled Bytes Transmitted)."
		::=  {  rbSUWirelessCountersEntry  8  }


-- ####################################################################################
    rbAUBackplaneCountersTable OBJECT-TYPE
              SYNTAX  SEQUENCE OF RbAUBackplaneCountersEntry
              MAX-ACCESS  not-accessible
              STATUS  current
              DESCRIPTION
                      "A table of Backplane (NPU/AU connection) Counters."  
              ::= { rbAUBackplaneCounters 1 }

    rbAUBackplaneCountersEntry OBJECT-TYPE
              SYNTAX  RbAUBackplaneCountersEntry
              MAX-ACCESS  not-accessible
              STATUS      current
              DESCRIPTION
                      "Entry in the rbAUBackplaneCountersTable."
              INDEX   { rbPMIfAUSlot }
              ::= { rbAUBackplaneCountersTable 1 }

	RbAUBackplaneCountersEntry  ::=  SEQUENCE {
		rbPMIfAUSlot                        Integer32,
		rbAUBackplaneResetCounters          INTEGER,
		rbAUBackplaneDataBytesRx            Counter32,
		rbAUBackplaneDataBytesDiscardedOnRx Counter32,
		rbAUBackplaneDataBytesTx            Counter32,
		rbAUBackplaneDataBytesDiscardedOnTx Counter32
 		}


	rbPMIfAUSlot	OBJECT-TYPE	
		SYNTAX			Integer32  ( 1 .. 9 ) 
		MAX-ACCESS		read-only
		STATUS			current
		DESCRIPTION		
				"Physical placement of the card in the chassis (the Slot number 1-4, 7-9)."
		::=  {  rbAUBackplaneCountersEntry  1  }

	rbAUBackplaneResetCounters   OBJECT-TYPE
		SYNTAX		 	INTEGER
		                {
                          noAction (0),
		                  reset (1)
	                    }   
		MAX-ACCESS		read-write
		STATUS			current
		DESCRIPTION		
				"When set to reset (1), the Back plane port counters will be initialized to 0.
				 noAction (0) value is available to support Get and Get Next commands.
				 It should not be used in Set commands."
		::=  {  rbAUBackplaneCountersEntry  2  }

	rbAUBackplaneDataBytesRx   OBJECT-TYPE
		SYNTAX		 	Counter32
		MAX-ACCESS		read-only
		STATUS			current
		DESCRIPTION		
				"The total number of data bytes received from the Back-panel (NPU),
				 excluding management frames and errors."
		::=  {  rbAUBackplaneCountersEntry 3  }

	rbAUBackplaneDataBytesDiscardedOnRx   OBJECT-TYPE
		SYNTAX		 	Counter32
		MAX-ACCESS		read-only
		STATUS			current
		DESCRIPTION		
				"The total number of bytes in data packets discarded due to communication
				 errors between the AU and the NPU."
		::=  {  rbAUBackplaneCountersEntry 4  }

	rbAUBackplaneDataBytesTx   OBJECT-TYPE
		SYNTAX		 	Counter32
		MAX-ACCESS		read-only
		STATUS			current
		DESCRIPTION		
				"The total number of data bytes transmitted to the Back-panel (NPU),
				 excluding management frames and errors."
		::=  {  rbAUBackplaneCountersEntry 5  }

	rbAUBackplaneDataBytesDiscardedOnTx   OBJECT-TYPE
		SYNTAX		 	Counter32
		MAX-ACCESS		read-only
		STATUS			current
		DESCRIPTION		
				"This count is always 0 (No discards on Tx)."
		::=  {  rbAUBackplaneCountersEntry 6  }


-- ####################################################################################
    rbAUWirelessCountersTable OBJECT-TYPE
              SYNTAX  SEQUENCE OF RbAUWirelessCountersEntry
              MAX-ACCESS  not-accessible
              STATUS  current
              DESCRIPTION
                      "A table of AU Wireless port Counters." 
              ::= { rbAUWirelessCounters 1 }

    rbAUWirelessCountersEntry OBJECT-TYPE
              SYNTAX  RbAUWirelessCountersEntry
              MAX-ACCESS  not-accessible
              STATUS      current
              DESCRIPTION
                      "Entry in the rbAUWirelessCountersTable."
              INDEX   { rbAUWirelessAUSlot }
              ::= { rbAUWirelessCountersTable 1 }

	RbAUWirelessCountersEntry  ::=  SEQUENCE {
		rbAUWirelessResetCounters          INTEGER,
		rbAUWirelessDataBytesRx            Counter32,
		rbAUWirelessDataBytesDiscardedOnRx Counter32,
		rbAUWirelessDataBytesTx            Counter32,
		rbAUWirelessDataBytesDiscardedOnTx Counter32,
		rbAUWirelessARQEnabledBytesTx      Counter32,
		rbAUWirelessRTxBytes               Counter32,
		rbAUWirelessRTxRate                Gauge32,
		rbAUWirelessAUSlot                 Integer32
 		}


	rbAUWirelessResetCounters   OBJECT-TYPE
		SYNTAX		 	INTEGER
		                {
                          noAction (0),
		                  reset (1)
	                    }   
		MAX-ACCESS		read-write
		STATUS			current
		DESCRIPTION		
				"When set to reset (1), the AU Wireless port counters will be initialized to 0.
				 noAction (0) value is available to support Get and Get Next commands.
				 It should not be used in Set commands."
		::=  {  rbAUWirelessCountersEntry  1  }

	rbAUWirelessDataBytesRx   OBJECT-TYPE
		SYNTAX		 	Counter32
		MAX-ACCESS		read-only
		STATUS			current
		DESCRIPTION		
				"The total number of data bytes received on the Wireless port,
				 excluding MAC management frames and errors."
		::=  {  rbAUWirelessCountersEntry 2  }

	rbAUWirelessDataBytesDiscardedOnRx   OBJECT-TYPE
		SYNTAX		 	Counter32
		MAX-ACCESS		read-only
		STATUS			current
		DESCRIPTION		
				"The total number of bytes in packets received on the Wireless link
				 and discarded due to MAC protocol receive errors, such as
				 duplicate sequence number, wrong sequence number etc. (not CRC errors)."
		::=  {  rbAUWirelessCountersEntry 3  }

	rbAUWirelessDataBytesTx   OBJECT-TYPE
		SYNTAX		 	Counter32
		MAX-ACCESS		read-only
		STATUS			current
		DESCRIPTION		
				"The total number of data bytes transmitted to the Wireless link,
				 excluding MAC Management frames and frames with errors."
		::=  {  rbAUWirelessCountersEntry 4  }

	rbAUWirelessDataBytesDiscardedOnTx   OBJECT-TYPE
		SYNTAX		 	Counter32
		MAX-ACCESS		read-only
		STATUS			current
		DESCRIPTION		
				"The total number of bytes in packets discarded due to congestion in the wireless medium."
		::=  {  rbAUWirelessCountersEntry 5  }

	rbAUWirelessARQEnabledBytesTx   OBJECT-TYPE
		SYNTAX		 	Counter32
		MAX-ACCESS		read-only
		STATUS			current
		DESCRIPTION		
				"The total number of bytes transmitted over BE and NRT connections.
				 Applicable only if the ARQ mechanism is enabled."
		::=  {  rbAUWirelessCountersEntry 6  }

	rbAUWirelessRTxBytes   OBJECT-TYPE
		SYNTAX		 	Counter32
		MAX-ACCESS		read-only
		STATUS			current
		DESCRIPTION		
				"The total number of unacknowledged bytes that were retransmitted.
				 Retransmissions are applicable only to BE and NRT connections provided
				 the ARQ mechanism is enabled."
		::=  {  rbAUWirelessCountersEntry 7  }
		
	rbAUWirelessRTxRate  OBJECT-TYPE
		SYNTAX		 	Gauge32   
		MAX-ACCESS		read-only
		STATUS			current
		DESCRIPTION		
				"Retransmission Rate in percents: 
				 100*(Bytes Retransmitted)/(ARQ Enabled Bytes Transmitted)."
		::=  {  rbAUWirelessCountersEntry  8  }

	rbAUWirelessAUSlot	OBJECT-TYPE	
		SYNTAX			Integer32  ( 1 .. 9 ) 
		MAX-ACCESS		read-only
		STATUS			current
		DESCRIPTION		
				"For NPU - the physical placement of the card in the chassis (the Slot number 1-4, 7-9).
				 For MBST - the MBST Wireless port Table index (always 1)." 
		::=  {  rbAUWirelessCountersEntry  9  }




END

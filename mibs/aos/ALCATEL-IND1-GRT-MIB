ALCATEL-IND1-GRT-MIB DEFINITIONS ::= BEGIN
IMPORTS
        MODULE-IDENTITY, OBJECT-TYPE,
    Integer32, Unsigned32
        FROM SNMPv2-SMI
    InetAddressType, InetAddress
        FROM INET-ADDRESS-MIB
    SnmpAdminString
        FROM SNMP-FRAMEWORK-MIB
    MODULE-COMPLIANCE, OBJECT-GROUP
        FROM SNMPv2-CONF
    routingIND1GlobalRouteTableMIB
        FROM ALCATEL-IND1-BASE ;


alcatelIND1GRTMIB MODULE-IDENTITY

    LAST-UPDATED  "200704030000Z"
    ORGANIZATION  "Alcatel-Lucent"
    CONTACT-INFO
        "Please consult with Customer Service to ensure the most appropriate
         version of this document is used with the products in question:

                    Alcatel-Lucent, Enterprise Solutions Division
                   (Formerly Alcatel Internetworking, Incorporated)
                           26801 West Agoura Road
                        Agoura Hills, CA  91301-5122
                          United States Of America

        Telephone:               North America  +1 800 995 2696
                                 Latin America  +1 877 919 9526
                                 Europe         +31 23 556 0100
                                 Asia           +65 394 7933
                                 All Other      +1 818 878 4507

        Electronic Mail:         support@ind.alcatel.com
        World Wide Web:          http://alcatel-lucent.com/wps/portal/enterprise
        File Transfer Protocol:  ftp://ftp.ind.alcatel.com/pub/products/mibs"

    DESCRIPTION
        "This module describes an authoritative enterprise-specific Simple
         Network Management Protocol (SNMP) Management Information Base (MIB):

             This proprietary MIB contains management information for 
             the configuration of Route Leaked Global Routing Table 

         The right to make changes in specification and other information
         contained in this document without prior notice is reserved.

         No liability shall be assumed for any incidental, indirect, special, or
         consequential damages whatsoever arising from or related to this
         document or the information contained herein.

         Vendors, end-users, and other interested parties are granted
         non-exclusive license to use this specification in connection with
         management of the products for which it is intended to be used.

                     Copyright (C) 1995-2007 Alcatel-Lucent
                         ALL RIGHTS RESERVED WORLDWIDE"

    REVISION      "200704030000Z"
    DESCRIPTION
        "The latest version of this MIB Module."
        
        ::= { routingIND1GlobalRouteTableMIB 1 }
        
alcatelIND1GRTMIBObjects OBJECT IDENTIFIER ::= { alcatelIND1GRTMIB 2 }

alaGrtConfig      OBJECT IDENTIFIER ::= { alcatelIND1GRTMIBObjects 1 }

-- Textual Conventions
   AlaGrtRouteDistinguisher ::= TEXTUAL-CONVENTION
        STATUS      current
        DESCRIPTION
            "Syntax for a route distinguisher and route target
            as defined in [RFC4346]."
        SYNTAX  OCTET STRING(SIZE (0..256))

-- The Global Route Table

alaGrtRouteTable 	OBJECT-TYPE
	SYNTAX   SEQUENCE OF AlaGrtRouteEntry
	MAX-ACCESS not-accessible
	STATUS   current
	DESCRIPTION
		"The Global Routing Table."
	::= { alaGrtConfig 1 }

alaGrtRouteEntry OBJECT-TYPE
	SYNTAX   AlaGrtRouteEntry
	MAX-ACCESS not-accessible
	STATUS   current
	DESCRIPTION
		"A particular route in the Global Route Table"
	INDEX {	alaGrtRouteDistinguisher,alaGrtRouteDest,
	        alaGrtRouteMaskLen,alaGrtRouteNextHop }
	::= { alaGrtRouteTable 1 }

AlaGrtRouteEntry ::= SEQUENCE {
	alaGrtRouteDistinguisher    AlaGrtRouteDistinguisher,
	alaGrtRouteDest  	    InetAddress,
        alaGrtRouteDestType         InetAddressType,
	alaGrtRouteMaskLen	    Integer32,
	alaGrtRouteNextHop          InetAddress,
        alaGrtRouteNextHopType      InetAddressType,
	alaGrtRouteMetric           Unsigned32,
	alaGrtRouteTag              Unsigned32,
	alaGrtRouteVrfName          SnmpAdminString 
       }

alaGrtRouteDistinguisher OBJECT-TYPE
	SYNTAX   AlaGrtRouteDistinguisher
	MAX-ACCESS not-accessible
	STATUS   current
	DESCRIPTION
		"The route distinguisher of a global route."
	::= { alaGrtRouteEntry 1 }

alaGrtRouteDest OBJECT-TYPE
	SYNTAX   InetAddress (SIZE (4 | 16))
	MAX-ACCESS not-accessible
	STATUS   current
	DESCRIPTION
		"The destination IP address of this route."
	::= { alaGrtRouteEntry 2 }

alaGrtRouteDestType OBJECT-TYPE
         SYNTAX InetAddressType
         MAX-ACCESS not-accessible
        STATUS   current
        DESCRIPTION
                "The destination IP address type of this route."
        ::= { alaGrtRouteEntry 3 }

alaGrtRouteMaskLen OBJECT-TYPE
	SYNTAX   Integer32 (0..16)
	MAX-ACCESS not-accessible
	STATUS   current
	DESCRIPTION
		"The destination mask length of this route"
	::= { alaGrtRouteEntry 4 }

alaGrtRouteNextHop OBJECT-TYPE
	SYNTAX   InetAddress (SIZE (4 | 16))
	MAX-ACCESS not-accessible
	STATUS   current
	DESCRIPTION
		"The Gateway for this route"
	::= { alaGrtRouteEntry 5 }

alaGrtRouteNextHopType OBJECT-TYPE
        SYNTAX   InetAddressType 
        MAX-ACCESS not-accessible
        STATUS   current
        DESCRIPTION
                "The Gateway Type for this route"
        ::= { alaGrtRouteEntry 6 }

alaGrtRouteMetric OBJECT-TYPE
	SYNTAX   Unsigned32
	MAX-ACCESS read-only
	STATUS   current
	DESCRIPTION
		"The metric for this route"
	::= { alaGrtRouteEntry 7 }

alaGrtRouteTag OBJECT-TYPE
	SYNTAX   Unsigned32
	MAX-ACCESS read-only
	STATUS   current
	DESCRIPTION
		"The tag for this route"
	::= { alaGrtRouteEntry 8 }

alaGrtRouteVrfName OBJECT-TYPE
	SYNTAX   SnmpAdminString 
	MAX-ACCESS read-only
	STATUS   current
	DESCRIPTION
		"The name of the VRF this route came from"
	::= { alaGrtRouteEntry 9 }

-- conformance information

alcatelIND1GRTMIBConformance OBJECT IDENTIFIER ::= { alcatelIND1GRTMIB 1 }
alcatelIND1GRTMIBCompliances OBJECT IDENTIFIER ::= { alcatelIND1GRTMIBConformance 1 }
alcatelIND1GRTMIBGroups      OBJECT IDENTIFIER ::= { alcatelIND1GRTMIBConformance 2 }

-- compliance statements

alaGlobalRouteTableCompliance MODULE-COMPLIANCE
        STATUS  current
        DESCRIPTION
                "The compliance statement for routers running Route Leak functionality using Route Maps
                and implementing the ALCATEL-IND1-GRT MIB."
    MODULE  -- this module
        MANDATORY-GROUPS { alaGlobalRouteTableMIBGroup }

    ::= { alcatelIND1GRTMIBCompliances 1 }

-- units of conformance

alaGlobalRouteTableMIBGroup OBJECT-GROUP
    OBJECTS { alaGrtRouteVrfName,
              alaGrtRouteMetric,
              alaGrtRouteTag
            }
    STATUS  current
    DESCRIPTION
            "A collection of objects to support management of the Global Routing Table."
    ::= { alcatelIND1GRTMIBGroups 1 }


END

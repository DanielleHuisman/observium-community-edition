--
-- NETBOTZ-MIB       module definition
--

NETBOTZ410-MIB DEFINITIONS ::= BEGIN
   IMPORTS
       MODULE-IDENTITY, OBJECT-TYPE,NOTIFICATION-TYPE, enterprises, Counter32,Integer32         FROM SNMPv2-SMI
       TEXTUAL-CONVENTION, DisplayString, DateAndTime                				FROM SNMPv2-TC;

netBotz-APC MODULE-IDENTITY
    LAST-UPDATED "201607220000Z"
    ORGANIZATION "Schneider Electric / APC"
    CONTACT-INFO
            "Postal: Schneider Electric / APC
                     132 Fairgrounds Road
                     West Kingston, RI 02892
                     US

             Contact: http://www.apc.com/us/en/support/contact-us/index.jsp"
   DESCRIPTION
            "NetBotz-APC BotzWare MIB"
   REVISION     "201611020000Z" --  02 November 2016
   DESCRIPTION  "Replaced the generic phone number with the support web page"
   REVISION     "201604260000Z" --  26 April 2016
   DESCRIPTION  "for Netbotz Version 4.5.2"
   REVISION     "201002020000Z" --  02 February 2010
   DESCRIPTION  "for Netbotz Version 4.1.0"
   ::= { enterprises 5528 100 1 }

netBotzAPC				OBJECT IDENTIFIER ::= { enterprises 5528 }
netBotz					OBJECT IDENTIFIER ::= { netBotzAPC 100 }
netBotzTraps				OBJECT IDENTIFIER ::= { netBotz 10 }
netBotzTrapParms			OBJECT IDENTIFIER ::= { netBotz 11 }
netBotzProducts				OBJECT IDENTIFIER ::= { netBotz 20 }

netBotzGenericTraps			OBJECT IDENTIFIER ::= { netBotzTraps 1 }
netBotzSensorTraps			OBJECT IDENTIFIER ::= { netBotzTraps 2 }
netBotzPodTraps				OBJECT IDENTIFIER ::= { netBotzTraps 3 }
netBotzPortTraps			OBJECT IDENTIFIER ::= { netBotzTraps 4 }

netBotzTempSensorTraps			OBJECT IDENTIFIER ::= { netBotzSensorTraps 1 }
netBotzHumiditySensorTraps		OBJECT IDENTIFIER ::= { netBotzSensorTraps 2 }
netBotzDewPointSensorTraps		OBJECT IDENTIFIER ::= { netBotzSensorTraps 3 }
netBotzAirFlowSensorTraps		OBJECT IDENTIFIER ::= { netBotzSensorTraps 4 }
netBotzAudioSensorTraps			OBJECT IDENTIFIER ::= { netBotzSensorTraps 5 }
netBotzAmpDetectSensorTraps		OBJECT IDENTIFIER ::= { netBotzSensorTraps 6 }
netBotzDryContactSensorTraps		OBJECT IDENTIFIER ::= { netBotzSensorTraps 7 }
netBotzCameraMotionSensorTraps 		OBJECT IDENTIFIER ::= { netBotzSensorTraps 8 }
netBotzDoorSensorTraps			OBJECT IDENTIFIER ::= { netBotzSensorTraps 9 }
netBotzMicPlugSensorTraps		OBJECT IDENTIFIER ::= { netBotzSensorTraps 10 }
netBotzSpeakerPlugSensorTraps		OBJECT IDENTIFIER ::= { netBotzSensorTraps 11 }
netBotzTVSignalSensorTraps		OBJECT IDENTIFIER ::= { netBotzSensorTraps 12 }
netBotzGPSPositionSensorTraps		OBJECT IDENTIFIER ::= { netBotzSensorTraps 13 }
netBotzGPSMovementSensorTraps		OBJECT IDENTIFIER ::= { netBotzSensorTraps 14 }
netBotzGPSStatusSensorTraps		OBJECT IDENTIFIER ::= { netBotzSensorTraps 15 }
netBotzWirelessStatusSensorTraps	OBJECT IDENTIFIER ::= { netBotzSensorTraps 22 }
netBotzPacketDropSensorTraps		OBJECT IDENTIFIER ::= { netBotzSensorTraps 23 }
netBotzSNMPCrawlerSensorTraps		OBJECT IDENTIFIER ::= { netBotzSensorTraps 24 }
netBotzPlugModuleStatusSensorTraps	OBJECT IDENTIFIER ::= { netBotzSensorTraps 25 }
netBotzOutputControlSensorTraps		OBJECT IDENTIFIER ::= { netBotzSensorTraps 26 }
netBotzMultiRAESensorTraps		OBJECT IDENTIFIER ::= { netBotzSensorTraps 27 }
netBotzMultiRAESensorStatusTraps	OBJECT IDENTIFIER ::= { netBotzSensorTraps 28 }
netBotzMultiRAEDeviceStatusTraps	OBJECT IDENTIFIER ::= { netBotzSensorTraps 29 }
netBotzLinkStatusSensorTraps		OBJECT IDENTIFIER ::= { netBotzSensorTraps 30 }
netBotzLoopVoltageSensorTraps		OBJECT IDENTIFIER ::= { netBotzSensorTraps 31 }
netBotzVoltageSensorTraps		OBJECT IDENTIFIER ::= { netBotzSensorTraps 32 }
netBotzFanSpeedSensorTraps		OBJECT IDENTIFIER ::= { netBotzSensorTraps 33 }
netBotzAppPowerSensorTraps		OBJECT IDENTIFIER ::= { netBotzSensorTraps 34 }
netBotzPowerFactorSensorTraps		OBJECT IDENTIFIER ::= { netBotzSensorTraps 35 }
netBotzTimeSensorTraps		OBJECT IDENTIFIER ::= { netBotzSensorTraps 36 }
netBotzPowerWattsSensorTraps		OBJECT IDENTIFIER ::= { netBotzSensorTraps 37 }

netBotzBasePodTraps	OBJECT IDENTIFIER ::= { netBotzPodTraps 1 }
netBotzSensorPodTraps	OBJECT IDENTIFIER ::= { netBotzPodTraps 2 }
netBotzCameraPodTraps	OBJECT IDENTIFIER ::= { netBotzPodTraps 3 }
netBotzCCTVPodTraps	OBJECT IDENTIFIER ::= { netBotzPodTraps 4 }
netBotz4to20mAPodTraps	OBJECT IDENTIFIER ::= { netBotzPodTraps 5 }

netBotzBotz		OBJECT IDENTIFIER ::= { netBotzProducts 10 }

netBotzWallBotz500	 OBJECT IDENTIFIER ::= { netBotzBotz 2000 }
netBotz420Wall		 OBJECT IDENTIFIER ::= { netBotzBotz 2001 }
raeSystemsAreaConnect500 OBJECT IDENTIFIER ::= { netBotzBotz 2002 }
netBotz420Rack		 OBJECT IDENTIFIER ::= { netBotzBotz 2003 }
netBotz320Wall		 OBJECT IDENTIFIER ::= { netBotzBotz 2004 }
netBotz320Rack		 OBJECT IDENTIFIER ::= { netBotzBotz 2005 }
netBotz420ERack		 OBJECT IDENTIFIER ::= { netBotzBotz 2006 }
netBotz320ERack		 OBJECT IDENTIFIER ::= { netBotzBotz 2007 }
netBotz220Camera	 OBJECT IDENTIFIER ::= { netBotzBotz 2008 }
apprion500		 OBJECT IDENTIFIER ::= { netBotzBotz 2009 }
avocent500		 OBJECT IDENTIFIER ::= { netBotzBotz 2010 }
netBotz320EWall		 OBJECT IDENTIFIER ::= { netBotzBotz 2011 }
netBotz420EWall		 OBJECT IDENTIFIER ::= { netBotzBotz 2012 }
netBotz550Rack		 OBJECT IDENTIFIER ::= { netBotzBotz 2013 }
netBotz450Rack		 OBJECT IDENTIFIER ::= { netBotzBotz 2014 }
netBotz455Wall		 OBJECT IDENTIFIER ::= { netBotzBotz 2015 }
netBotz355Wall		 OBJECT IDENTIFIER ::= { netBotzBotz 2016 }
netBotz570Rack		 OBJECT IDENTIFIER ::= { netBotzBotz 2017 } 

--        MODULE-COMPLIANCE, OBJECT-GROUP,
--        NOTIFICATION-GROUP                     FROM SNMPv2-CONF;


OperStatus ::= TEXTUAL-CONVENTION
    STATUS current
    DESCRIPTION
        "The operational status of the device entity."
    SYNTAX INTEGER { disconnected(0), error(1), normal(2) }

ErrorStatus ::= TEXTUAL-CONVENTION
    STATUS current
    DESCRIPTION
        "The error status of the device entity.  If there are no error conditions
         reported for the entity, the status is normal.  Otherwise, the status is
         reported as the severity value of the highest severity error condition
         that is not resolved for the entity."
    SYNTAX INTEGER { normal(0), info(1), warning(2), error(3), critical(4), failure(5) }

BoolValue ::= TEXTUAL-CONVENTION
    STATUS current
    DESCRIPTION
        "A boolean value."
    SYNTAX INTEGER { no(0), yes(1), null(2) }

--BoolValue ::= TEXTUAL-CONVENTION
--    STATUS current
--    DESCRIPTION
--        "A boolean value."
--    SYNTAX INTEGER { no(0), yes(1), null(2) }

netBotzEnclosures        OBJECT IDENTIFIER ::= { netBotz 2 }
netBotzPorts             OBJECT IDENTIFIER ::= { netBotz 3 }
netBotzSensors           OBJECT IDENTIFIER ::= { netBotz 4 }
netBotzErrors            OBJECT IDENTIFIER ::= { netBotz 5 }

netBotzSensorCounts      OBJECT IDENTIFIER ::= { netBotzEnclosures 2}
netBotzNumericSensors    OBJECT IDENTIFIER ::= { netBotzSensors 1 }
netBotzStateSensors      OBJECT IDENTIFIER ::= { netBotzSensors 2 }


--
-- Top-level error status - worst active alert severity
--
netBotzErrorStatus OBJECT-TYPE
    SYNTAX     ErrorStatus
    MAX-ACCESS read-only
    STATUS     current
    DESCRIPTION
        "The error status of the appliance.  If there are no error conditions
         reported for the appliance, the status is normal.  Otherwise, the status is
         reported as the severity value of the highest severity error condition
         that is not resolved for the appliance."
    ::= { netBotz 100 }

--
-- Enclosures
--

enclosureTable OBJECT-TYPE
    SYNTAX     SEQUENCE OF EnclosureEntry
    MAX-ACCESS not-accessible
    STATUS     current
    DESCRIPTION
        "A list of enclosures (base enclosure and pods)."
    ::= { netBotzEnclosures 1 }

enclosureEntry OBJECT-TYPE
    SYNTAX     EnclosureEntry
    MAX-ACCESS not-accessible
    STATUS     current
    DESCRIPTION
        "Enclosure entry."
    INDEX { enclosureIndex }
    ::= { enclosureTable 1 }

EnclosureEntry ::= SEQUENCE {
    enclosureId                          DisplayString,
    enclosureStatus                      OperStatus,
    enclosureErrorStatus                 ErrorStatus,
    enclosureLabel                       DisplayString,
    enclosureParentEncId                 DisplayString,
    enclosureDockedToEncId               DisplayString,
    enclosureIndex                       Counter32
}

enclosureId OBJECT-TYPE
    SYNTAX     DisplayString (SIZE (0..127))
    MAX-ACCESS read-only
    STATUS     current
    DESCRIPTION
        "The id of the physical enclosure."
    ::= { enclosureEntry 1 }

enclosureStatus OBJECT-TYPE
    SYNTAX     OperStatus 
    MAX-ACCESS read-only
    STATUS     current
    DESCRIPTION
        "The operational status of the enclosure."
    ::= { enclosureEntry 2 }
    
enclosureErrorStatus OBJECT-TYPE
    SYNTAX     ErrorStatus
    MAX-ACCESS read-only
    STATUS     current
    DESCRIPTION
        "The error status of the enclosure.  If there are no error conditions
         reported for the enclosure, the status is normal.  Otherwise, the status is
         reported as the severity value of the highest severity error condition
         that is not resolved for the enclosure."
    ::= { enclosureEntry 3 }

enclosureLabel OBJECT-TYPE
    SYNTAX     DisplayString
    MAX-ACCESS read-only
    STATUS     current
    DESCRIPTION
        "The unique label assigned to the enclosure (or pod)."
    ::= { enclosureEntry 4 }

enclosureParentEncId OBJECT-TYPE
    SYNTAX     DisplayString (SIZE (0..127))
    MAX-ACCESS read-only
    STATUS     current
    DESCRIPTION
        "The id of the parent enclosure this enclosure is attached to."
    ::= { enclosureEntry 5 }
    
enclosureDockedToEncId OBJECT-TYPE
    SYNTAX     DisplayString (SIZE (0..127))
    MAX-ACCESS read-only
    STATUS     current
    DESCRIPTION
        "The id of the enclosure this enclosure is hard-docked with,
         i.e. as when sensor and camera pods are docked with the base
         system unit."
    ::= { enclosureEntry 6 }

enclosureIndex OBJECT-TYPE
    SYNTAX     Counter32
    MAX-ACCESS read-only
    STATUS     current
    DESCRIPTION
        "The index of the physical enclosure."
    ::= { enclosureEntry 7 }

-- +++++++++++++++++++++++++++++++++++++++++++++++++++++++++++++
-- Sensor-Counts Group
-- This group defines counters of sensors in an integer 
-- value which is defined by the contained subgroups
alinkSensorCountTable OBJECT-TYPE
    SYNTAX     SEQUENCE OF AlinkSensorCountEntry
    MAX-ACCESS not-accessible
    STATUS     current
    DESCRIPTION
        "A count of alink-related sensors."
    ::= { netBotzSensorCounts 1 }

alinkSensorCountEntry OBJECT-TYPE
    SYNTAX     AlinkSensorCountEntry
    MAX-ACCESS not-accessible
    STATUS     current
    DESCRIPTION
        "A count-of-sensors entry."
    INDEX { alinkSensorCountIndex }
    ::= { alinkSensorCountTable 1 }

AlinkSensorCountEntry ::= SEQUENCE {
    alinkSensorCountId                      DisplayString,
    alinkSensorCountValue                   Integer32,
    alinkSensorCountLabel                   DisplayString,
    alinkSensorCountEncId                   DisplayString,
    alinkSensorCountValueStr                DisplayString,
    alinkSensorCountValueInt                Integer32,
    alinkSensorCountIndex                   Counter32
}

alinkSensorCountId OBJECT-TYPE
    SYNTAX     DisplayString (SIZE (0..127))
    MAX-ACCESS read-only
    STATUS     current
    DESCRIPTION
        "The unique id of the sensor."
    ::= { alinkSensorCountEntry 1 }

alinkSensorCountValue OBJECT-TYPE
    SYNTAX     Integer32 (0..65535)
    MAX-ACCESS read-only
    STATUS     current
    DESCRIPTION
        "The number of known connected sensors."
    ::= { alinkSensorCountEntry 2 }

alinkSensorCountLabel OBJECT-TYPE
    SYNTAX     DisplayString
    MAX-ACCESS read-only
    STATUS     current
    DESCRIPTION
        "The unique label assigned to the sensor count."
    ::= { alinkSensorCountEntry 3 }

alinkSensorCountEncId OBJECT-TYPE
    SYNTAX     DisplayString (SIZE (0..127))
    MAX-ACCESS read-only
    STATUS     current
    DESCRIPTION
        "The id of the physical enclosure represented by the sensor count."
    ::= { alinkSensorCountEntry 4 }

alinkSensorCountValueStr OBJECT-TYPE
    SYNTAX     DisplayString
    MAX-ACCESS read-only
    STATUS     current
    DESCRIPTION
        "The sensor count value shown as a string."
    ::= { alinkSensorCountEntry 5 }

alinkSensorCountValueInt OBJECT-TYPE
    SYNTAX     Integer32 (0..6554)
    MAX-ACCESS read-only
    STATUS     current
    DESCRIPTION
        "The sensor count as integer value."
    ::= { alinkSensorCountEntry 6 }

alinkSensorCountIndex OBJECT-TYPE
    SYNTAX     Counter32
    MAX-ACCESS read-only
    STATUS     current
    DESCRIPTION
        "The index of the sensor counter."
    ::= { alinkSensorCountEntry 7 }

-- +++++++++++++++++++++++++++++++++++++++++++++++++++++++++++++


--
-- Ports
--

dinPortTable OBJECT-TYPE
    SYNTAX     SEQUENCE OF DINPortEntry
    MAX-ACCESS not-accessible
    STATUS     current
    DESCRIPTION
        "A list of DIN port entries."
    ::= { netBotzPorts 1 }

dinPortEntry OBJECT-TYPE
    SYNTAX     DINPortEntry
    MAX-ACCESS not-accessible
    STATUS     current
    DESCRIPTION
        "DIN port entry."
    INDEX { dinPortIndex }
    ::= { dinPortTable 1 }

DINPortEntry ::= SEQUENCE {
    dinPortId                            DisplayString,
    dinPortStatus                        OperStatus,
    dinPortLabel                         DisplayString,
    dinPortEncId                         DisplayString,
    dinPortSensorIdSuffix                DisplayString,
    dinPortSupportsAverage               BoolValue,
    dinPortSupportsRMS                   BoolValue,
    dinPortSupportsDryContact            BoolValue,
    dinPortIndex                         Counter32
}

dinPortId OBJECT-TYPE
    SYNTAX     DisplayString (SIZE (0..127))
    MAX-ACCESS read-only
    STATUS     current
    DESCRIPTION
        "The unique id of the port."
    ::= { dinPortEntry 1 }

dinPortStatus OBJECT-TYPE
    SYNTAX     OperStatus 
    MAX-ACCESS read-only
    STATUS     current
    DESCRIPTION
        "The operational status of the port."
    ::= { dinPortEntry 2 }

dinPortLabel OBJECT-TYPE
    SYNTAX     DisplayString
    MAX-ACCESS read-only
    STATUS     current
    DESCRIPTION
        "The unique label assigned to the port."
    ::= { dinPortEntry 3 }

dinPortEncId OBJECT-TYPE
    SYNTAX     DisplayString (SIZE (0..127))
    MAX-ACCESS read-only
    STATUS     current
    DESCRIPTION
        "The id of the physical enclosure containing the port."
    ::= { dinPortEntry 4 }

dinPortSensorIdSuffix OBJECT-TYPE
    SYNTAX     DisplayString
    MAX-ACCESS read-only
    STATUS     current
    DESCRIPTION
        "The ID suffix added to a sensor plugged into the port.
         The ID suffix is combined with the sensor class ID when
         generating a local unique id for the DIN sensor."
    ::= { dinPortEntry 5 }

dinPortSupportsAverage OBJECT-TYPE
    SYNTAX     BoolValue
    MAX-ACCESS read-only
    STATUS     current
    DESCRIPTION
        "Whether the port supports returning the average voltage
         reading of the sensor.  This is used to determine which
         classes of sensors are supported by the port."
    ::= { dinPortEntry 6 }

dinPortSupportsRMS OBJECT-TYPE
    SYNTAX     BoolValue
    MAX-ACCESS read-only
    STATUS     current
    DESCRIPTION
        "Whether the port supports returning the AC RMS voltage
         reading of the sensor.  This is used to determine which
         classes of sensors are supported by the port."
    ::= { dinPortEntry 7 }

dinPortSupportsDryContact OBJECT-TYPE
    SYNTAX     BoolValue
    MAX-ACCESS read-only
    STATUS     current
    DESCRIPTION
        "Whether the port supports generating the 'open' and
         'closed' state of a dry contact sensor. This information
         is used to determine which classes of sensors are supported
         by the port."
    ::= { dinPortEntry 8 }

dinPortIndex OBJECT-TYPE
    SYNTAX     Counter32
    MAX-ACCESS read-only
    STATUS     current
    DESCRIPTION
        "The index of the port."
    ::= { dinPortEntry 9 }

otherPortTable OBJECT-TYPE
    SYNTAX     SEQUENCE OF OtherPortEntry
    MAX-ACCESS not-accessible
    STATUS     current
    DESCRIPTION
        "A list of other port entries."
    ::= { netBotzPorts 10 }

otherPortEntry OBJECT-TYPE
    SYNTAX     OtherPortEntry
    MAX-ACCESS not-accessible
    STATUS     current
    DESCRIPTION
        "Other port entry."
    INDEX { otherPortIndex }
    ::= { otherPortTable 1 }

OtherPortEntry ::= SEQUENCE {
    otherPortId                            DisplayString,
    otherPortStatus                        OperStatus,
    otherPortLabel                         DisplayString,
    otherPortEncId                         DisplayString,
    otherPortIndex                         Counter32
}

otherPortId OBJECT-TYPE
    SYNTAX     DisplayString (SIZE (0..127))
    MAX-ACCESS read-only
    STATUS     current
    DESCRIPTION
        "The unique id of the port."
    ::= { otherPortEntry 1 }

otherPortStatus OBJECT-TYPE
    SYNTAX     OperStatus 
    MAX-ACCESS read-only
    STATUS     current
    DESCRIPTION
        "The operational status of the port."
    ::= { otherPortEntry 2 }

otherPortLabel OBJECT-TYPE
    SYNTAX     DisplayString
    MAX-ACCESS read-only
    STATUS     current
    DESCRIPTION
        "The unique label assigned to the port."
    ::= { otherPortEntry 3 }

otherPortEncId OBJECT-TYPE
    SYNTAX     DisplayString (SIZE (0..127))
    MAX-ACCESS read-only
    STATUS     current
    DESCRIPTION
        "The id of the physical enclosure containing the port."
    ::= { otherPortEntry 4 }

otherPortIndex OBJECT-TYPE
    SYNTAX     Counter32
    MAX-ACCESS read-only
    STATUS     current
    DESCRIPTION
        "The index of the port."
    ::= { otherPortEntry 5 }

-- Numeric Sensors Group
-- This group defines sensors for which the concepts of "less than"
-- and "greater than" are meaningful.

tempSensorTable OBJECT-TYPE
    SYNTAX     SEQUENCE OF TempSensorEntry
    MAX-ACCESS not-accessible
    STATUS     current
    DESCRIPTION
        "A list of temperature sensor entries."
    ::= { netBotzNumericSensors 1 }

tempSensorEntry OBJECT-TYPE
    SYNTAX     TempSensorEntry
    MAX-ACCESS not-accessible
    STATUS     current
    DESCRIPTION
        "A temperature sensor entry."
    INDEX { tempSensorIndex }
    ::= { tempSensorTable 1 }

TempSensorEntry ::= SEQUENCE {
    tempSensorId                       DisplayString,
    tempSensorValue                    Integer32,
    tempSensorErrorStatus              ErrorStatus,
    tempSensorLabel                    DisplayString,
    tempSensorEncId                    DisplayString,
    tempSensorPortId                   DisplayString,
    tempSensorValueStr                 DisplayString,
    tempSensorValueInt                 Integer32,
    tempSensorValueIntF                Integer32,
    tempSensorIndex                    Counter32
}

tempSensorId   OBJECT-TYPE
    SYNTAX     DisplayString (SIZE (0..127))
    MAX-ACCESS read-only
    STATUS     current
    DESCRIPTION
        "The unique id of the sensor."
    ::= { tempSensorEntry 1 }

tempSensorValue OBJECT-TYPE
    SYNTAX     Integer32 (-500..1000)
    MAX-ACCESS read-only
    STATUS     current
    DESCRIPTION
        "The temperature measured by the sensor in tenths of a degree Celsius."
    ::= { tempSensorEntry 2 }

tempSensorErrorStatus OBJECT-TYPE
    SYNTAX     ErrorStatus
    MAX-ACCESS read-only
    STATUS     current
    DESCRIPTION
        "The error status of the sensor.  If there are no error conditions
         reported for the sensor, the status is normal.  Otherwise, the status is
         reported as the severity value of the highest severity error condition
         that is not resolved for the sensor."
    ::= { tempSensorEntry 3 }

tempSensorLabel OBJECT-TYPE
    SYNTAX     DisplayString
    MAX-ACCESS read-only
    STATUS     current
    DESCRIPTION
        "The unique label assigned to the sensor."
    ::= { tempSensorEntry 4 }

tempSensorEncId OBJECT-TYPE
    SYNTAX     DisplayString (SIZE (0..127))
    MAX-ACCESS read-only
    STATUS     current
    DESCRIPTION
        "The id of the physical enclosure containing the sensor."
    ::= { tempSensorEntry 5 }

tempSensorPortId OBJECT-TYPE
    SYNTAX     DisplayString (SIZE (0..127))
    MAX-ACCESS read-only
    STATUS     current
    DESCRIPTION
        "The id of the port the sensor is plugged into (or empty string
         if it is not plugged into a port)."
    ::= { tempSensorEntry 6 }

tempSensorValueStr OBJECT-TYPE
    SYNTAX     DisplayString
    MAX-ACCESS read-only
    STATUS     current
    DESCRIPTION
        "The temperature reading, in degrees celsius, shown as a string (or empty string
         if it is not plugged into a port)."
    ::= { tempSensorEntry 7 }

tempSensorValueInt OBJECT-TYPE
    SYNTAX     Integer32 (-50..100)
    MAX-ACCESS read-only
    STATUS     current
    DESCRIPTION
        "The temperature measured by the sensor in degree Celsius."
    ::= { tempSensorEntry 8 }

tempSensorValueIntF OBJECT-TYPE
    SYNTAX     Integer32 (-50..212)
    MAX-ACCESS read-only
    STATUS     current
    DESCRIPTION
        "The temperature measured by the sensor in degree Farenheit."
    ::= { tempSensorEntry 9 }

tempSensorIndex   OBJECT-TYPE
    SYNTAX     Counter32
    MAX-ACCESS read-only
    STATUS     current
    DESCRIPTION
        "The index of the sensor."
    ::= { tempSensorEntry 10 }

humiSensorTable OBJECT-TYPE
    SYNTAX     SEQUENCE OF HumiSensorEntry
    MAX-ACCESS not-accessible
    STATUS     current
    DESCRIPTION
        "A list of humidity sensor entries."
    ::= { netBotzNumericSensors 2 }

humiSensorEntry OBJECT-TYPE
    SYNTAX     HumiSensorEntry
    MAX-ACCESS not-accessible
    STATUS     current
    DESCRIPTION
        "A humidity sensor entry."
    INDEX { humiSensorIndex }
    ::= { humiSensorTable 1 }

HumiSensorEntry ::= SEQUENCE {
    humiSensorId                       DisplayString,
    humiSensorValue                    Integer32,
    humiSensorErrorStatus              ErrorStatus,
    humiSensorLabel                    DisplayString,
    humiSensorEncId                    DisplayString,
    humiSensorPortId                   DisplayString,
    humiSensorValueStr                 DisplayString,
    humiSensorValueInt                 Integer32,
    humiSensorIndex                    Counter32
}

humiSensorId   OBJECT-TYPE
    SYNTAX     DisplayString (SIZE (0..127))
    MAX-ACCESS read-only
    STATUS     current
    DESCRIPTION
        "The unique id of the sensor."
    ::= { humiSensorEntry 1 }

humiSensorValue OBJECT-TYPE
    SYNTAX     Integer32 (0..1000)
    MAX-ACCESS read-only
    STATUS     current
    DESCRIPTION
        "The relative humidity measured by the sensor in tenths of a percent."
    ::= { humiSensorEntry 2 }

humiSensorErrorStatus OBJECT-TYPE
    SYNTAX     ErrorStatus
    MAX-ACCESS read-only
    STATUS     current
    DESCRIPTION
        "The error status of the sensor.  If there are no error conditions
         reported for the sensor, the status is normal.  Otherwise, the status is
         reported as the severity value of the highest severity error condition
         that is not resolved for the sensor."
    ::= { humiSensorEntry 3 }

humiSensorLabel OBJECT-TYPE
    SYNTAX     DisplayString
    MAX-ACCESS read-only
    STATUS     current
    DESCRIPTION
        "The unique label assigned to the sensor."
    ::= { humiSensorEntry 4 }

humiSensorEncId OBJECT-TYPE
    SYNTAX     DisplayString (SIZE (0..127))
    MAX-ACCESS read-only
    STATUS     current
    DESCRIPTION
        "The id of the physical enclosure containing the sensor."
    ::= { humiSensorEntry 5 }

humiSensorPortId OBJECT-TYPE
    SYNTAX     DisplayString (SIZE (0..127))
    MAX-ACCESS read-only
    STATUS     current
    DESCRIPTION
        "The id of the port the sensor is plugged into (or empty string
         if it is not plugged into a port)."
    ::= { humiSensorEntry 6 }

humiSensorValueStr OBJECT-TYPE
    SYNTAX     DisplayString
    MAX-ACCESS read-only
    STATUS     current
    DESCRIPTION
        "The humidity reading, in percent, shown as a string (or empty string
         if it is not plugged into a port)."
    ::= { humiSensorEntry 7 }

humiSensorValueInt OBJECT-TYPE
    SYNTAX     Integer32 (0..100)
    MAX-ACCESS read-only
    STATUS     current
    DESCRIPTION
        "The relative humidity measured by the sensor in percent."
    ::= { humiSensorEntry 8 }

humiSensorIndex   OBJECT-TYPE
    SYNTAX     Counter32
    MAX-ACCESS read-only
    STATUS     current
    DESCRIPTION
        "The index of the sensor."
    ::= { humiSensorEntry 9 }

dewPointSensorTable OBJECT-TYPE
    SYNTAX     SEQUENCE OF DewPointSensorEntry
    MAX-ACCESS not-accessible
    STATUS     current
    DESCRIPTION
        "A list of dew point sensor entries."
    ::= { netBotzNumericSensors 3 }

dewPointSensorEntry OBJECT-TYPE
    SYNTAX     DewPointSensorEntry
    MAX-ACCESS not-accessible
    STATUS     current
    DESCRIPTION
        "A dew point sensor entry."
    INDEX { dewPointSensorIndex }
    ::= { dewPointSensorTable 1 }

DewPointSensorEntry ::= SEQUENCE {
    dewPointSensorId                      DisplayString,
    dewPointSensorValue                   Integer32,
    dewPointSensorErrorStatus             ErrorStatus,
    dewPointSensorLabel                   DisplayString,
    dewPointSensorEncId                   DisplayString,
    dewPointSensorPortId                  DisplayString,
    dewPointSensorValueStr                DisplayString,
    dewPointSensorValueInt                Integer32,
    dewPointSensorValueIntF               Integer32,   
    dewPointSensorIndex                   Counter32
}

dewPointSensorId OBJECT-TYPE
    SYNTAX     DisplayString (SIZE (0..127))
    MAX-ACCESS read-only
    STATUS     current
    DESCRIPTION
        "The unique id of the sensor."
    ::= { dewPointSensorEntry 1 }

dewPointSensorValue OBJECT-TYPE
    SYNTAX     Integer32 (-500..1000)
    MAX-ACCESS read-only
    STATUS     current
    DESCRIPTION
        "The dew point value measured by the sensor in tenths of a degree Celsius."
    ::= { dewPointSensorEntry 2 }

dewPointSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { dewPointSensorEntry 3 }

dewPointSensorLabel OBJECT-TYPE
    SYNTAX     DisplayString
    MAX-ACCESS read-only
    STATUS     current
    DESCRIPTION
        "The unique label assigned to the sensor."
    ::= { dewPointSensorEntry 4 }

dewPointSensorEncId OBJECT-TYPE
    SYNTAX     DisplayString (SIZE (0..127))
    MAX-ACCESS read-only
    STATUS     current
    DESCRIPTION
        "The id of the physical enclosure containing the sensor."
    ::= { dewPointSensorEntry 5 }

dewPointSensorPortId OBJECT-TYPE
    SYNTAX     DisplayString (SIZE (0..127))
    MAX-ACCESS read-only
    STATUS     current
    DESCRIPTION
        "The id of the port the sensor is plugged into (or empty string
         if it is not plugged into a port)."
    ::= { dewPointSensorEntry 6 }

dewPointSensorValueStr OBJECT-TYPE
    SYNTAX     DisplayString
    MAX-ACCESS read-only
    STATUS     current
    DESCRIPTION
        "The dew point reading, in degrees celsius, shown as a string (or empty string
         if it is not plugged into a port)."
    ::= { dewPointSensorEntry 7 }

dewPointSensorValueInt OBJECT-TYPE
    SYNTAX     Integer32 (-50..100)
    MAX-ACCESS read-only
    STATUS     current
    DESCRIPTION
        "The dew point value measured by the sensor in degrees Celsius."
    ::= { dewPointSensorEntry 8 }

dewPointSensorValueIntF OBJECT-TYPE
    SYNTAX     Integer32 (-40..122)
    MAX-ACCESS read-only
    STATUS     current
    DESCRIPTION
        "The dew point reading in degrees Farenheit, measured by the sensor."
    ::= { dewPointSensorEntry 9 }

dewPointSensorIndex OBJECT-TYPE
    SYNTAX     Counter32
    MAX-ACCESS read-only
    STATUS     current
    DESCRIPTION
        "The index of the sensor."
    ::= { dewPointSensorEntry 10 }

audioSensorTable OBJECT-TYPE
    SYNTAX     SEQUENCE OF AudioSensorEntry
    MAX-ACCESS not-accessible
    STATUS     current
    DESCRIPTION
        "A list of audio sensor entries."
    ::= { netBotzNumericSensors 4 }

audioSensorEntry OBJECT-TYPE
    SYNTAX     AudioSensorEntry
    MAX-ACCESS not-accessible
    STATUS     current
    DESCRIPTION
        "An audio sensor entry."
    INDEX { audioSensorIndex }
    ::= { audioSensorTable 1 }

AudioSensorEntry ::= SEQUENCE {
    audioSensorId                      DisplayString,
    audioSensorValue                   Integer32,
    audioSensorErrorStatus             ErrorStatus,
    audioSensorLabel                   DisplayString,
    audioSensorEncId                   DisplayString,
    audioSensorPortId                  DisplayString,
    audioSensorValueStr                DisplayString,
    audioSensorValueInt                Integer32,
    audioSensorIndex                   Counter32
}

audioSensorId  OBJECT-TYPE
    SYNTAX     DisplayString (SIZE (0..127))
    MAX-ACCESS read-only
    STATUS     current
    DESCRIPTION
        "The unique id of the sensor."
    ::= { audioSensorEntry 1 }

audioSensorValue OBJECT-TYPE
    SYNTAX     Integer32
    MAX-ACCESS read-only
    STATUS     current
    DESCRIPTION
        "The (unitless) audio level measured by the sensor."
    ::= { audioSensorEntry 2 }

audioSensorErrorStatus OBJECT-TYPE
    SYNTAX     ErrorStatus
    MAX-ACCESS read-only
    STATUS     current
    DESCRIPTION
        "The error status of the sensor.  If there are no error conditions
         reported for the sensor, the status is normal.  Otherwise, the status is
         reported as the severity value of the highest severity error condition
         that is not resolved for the sensor."
    ::= { audioSensorEntry 3 }

audioSensorLabel OBJECT-TYPE
    SYNTAX     DisplayString
    MAX-ACCESS read-only
    STATUS     current
    DESCRIPTION
        "The unique label assigned to the sensor."
   ::= { audioSensorEntry 4 }

audioSensorEncId OBJECT-TYPE
    SYNTAX     DisplayString (SIZE (0..127))
    MAX-ACCESS read-only
    STATUS     current
    DESCRIPTION
        "The id of the physical enclosure containing the sensor."
    ::= { audioSensorEntry 5 }

audioSensorPortId OBJECT-TYPE
    SYNTAX     DisplayString (SIZE (0..127))
    MAX-ACCESS read-only
    STATUS     current
    DESCRIPTION
        "The id of the port the sensor is plugged into (or empty string
         if it is not plugged into a port)."
    ::= { audioSensorEntry 6 }

audioSensorValueStr OBJECT-TYPE
    SYNTAX     DisplayString
    MAX-ACCESS read-only
    STATUS     current
    DESCRIPTION
        "The audio reading shown as a string (or empty string
         if it is not plugged into a port)."
    ::= { audioSensorEntry 7 }

audioSensorValueInt OBJECT-TYPE
    SYNTAX     Integer32
    MAX-ACCESS read-only
    STATUS     current
    DESCRIPTION
        "The (unitless) audio level measured by the sensor (1/10 of audioSensorValue)."
    ::= { audioSensorEntry 8 }

audioSensorIndex  OBJECT-TYPE
    SYNTAX     Counter32
    MAX-ACCESS read-only
    STATUS     current
    DESCRIPTION
        "The index of the sensor."
    ::= { audioSensorEntry 9 }

airFlowSensorTable OBJECT-TYPE
    SYNTAX     SEQUENCE OF AirFlowSensorEntry
    MAX-ACCESS not-accessible
    STATUS     current
    DESCRIPTION
        "A list of airflow sensor entries."
    ::= { netBotzNumericSensors 5 }

airFlowSensorEntry OBJECT-TYPE
    SYNTAX     AirFlowSensorEntry
    MAX-ACCESS not-accessible
    STATUS     current
    DESCRIPTION
        "An air flow sensor entry."
    INDEX { airFlowSensorIndex }
    ::= { airFlowSensorTable 1 }

AirFlowSensorEntry ::= SEQUENCE {
    airFlowSensorId                      DisplayString,
    airFlowSensorValue                   Integer32,
    airFlowSensorErrorStatus             ErrorStatus,
    airFlowSensorLabel                   DisplayString,
    airFlowSensorEncId                   DisplayString,
    airFlowSensorPortId                  DisplayString,
    airFlowSensorValueStr                DisplayString,
    airFlowSensorValueInt                Integer32,
    airFlowSensorIndex                   Counter32
}

airFlowSensorId OBJECT-TYPE
    SYNTAX     DisplayString (SIZE (0..127))
    MAX-ACCESS read-only
    STATUS     current
    DESCRIPTION
        "The unique id of the sensor."
    ::= { airFlowSensorEntry 1 }

airFlowSensorValue OBJECT-TYPE
    SYNTAX     Integer32 (0..10000)
    MAX-ACCESS read-only
    STATUS     current
    DESCRIPTION
        "The air flow measured by the sensor in tenths of a meter per minute."
    ::= { airFlowSensorEntry 2 }

airFlowSensorErrorStatus OBJECT-TYPE
    SYNTAX     ErrorStatus
    MAX-ACCESS read-only
    STATUS     current
    DESCRIPTION
        "The error status of the sensor.  If there are no error conditions
         reported for the sensor, the status is normal.  Otherwise, the status is
         reported as the severity value of the highest severity error condition
         that is not resolved for the sensor."
    ::= { airFlowSensorEntry 3 }

airFlowSensorLabel OBJECT-TYPE
    SYNTAX     DisplayString
    MAX-ACCESS read-only
    STATUS     current
    DESCRIPTION
        "The unique label assigned to the sensor."
    ::= { airFlowSensorEntry 4 }

airFlowSensorEncId OBJECT-TYPE
    SYNTAX     DisplayString (SIZE (0..127))
    MAX-ACCESS read-only
    STATUS     current
    DESCRIPTION
        "The id of the physical enclosure containing the sensor."
    ::= { airFlowSensorEntry 5 }

airFlowSensorPortId OBJECT-TYPE
    SYNTAX     DisplayString (SIZE (0..127))
    MAX-ACCESS read-only
    STATUS     current
    DESCRIPTION
        "The id of the port the sensor is plugged into (or empty string
         if it is not plugged into a port)."
    ::= { airFlowSensorEntry 6 }

airFlowSensorValueStr OBJECT-TYPE
    SYNTAX     DisplayString
    MAX-ACCESS read-only
    STATUS     current
    DESCRIPTION
        "The airflow reading, in meters per minute, shown as a string (or empty string
         if it is not plugged into a port)."
    ::= { airFlowSensorEntry 7 }

airFlowSensorValueInt OBJECT-TYPE
    SYNTAX     Integer32 (0..1000)
    MAX-ACCESS read-only
    STATUS     current
    DESCRIPTION
        "The air flow measured by the sensor in meters per minute."
    ::= { airFlowSensorEntry 8 }

airFlowSensorIndex OBJECT-TYPE
    SYNTAX     Counter32
    MAX-ACCESS read-only
    STATUS     current
    DESCRIPTION
        "The index of the sensor."
    ::= { airFlowSensorEntry 9 }

ampDetectSensorTable OBJECT-TYPE
    SYNTAX     SEQUENCE OF AmpDetectSensorEntry
    MAX-ACCESS not-accessible
    STATUS     current
    DESCRIPTION
        "A list of amp detect sensor entries."
    ::= { netBotzNumericSensors 6 }

ampDetectSensorEntry OBJECT-TYPE
    SYNTAX     AmpDetectSensorEntry
    MAX-ACCESS not-accessible
    STATUS     current
    DESCRIPTION
        "An ampere sensor entry."
    INDEX { ampDetectSensorIndex }
    ::= { ampDetectSensorTable 1 }

AmpDetectSensorEntry ::= SEQUENCE {
    ampDetectSensorId                      DisplayString,
    ampDetectSensorValue                   Integer32,
    ampDetectSensorErrorStatus             ErrorStatus,
    ampDetectSensorLabel                   DisplayString,
    ampDetectSensorEncId                   DisplayString,
    ampDetectSensorPortId                  DisplayString,
    ampDetectSensorValueStr                DisplayString,
    ampDetectSensorValueInt                Integer32,
    ampDetectSensorIndex                   Counter32
}

ampDetectSensorId OBJECT-TYPE
    SYNTAX     DisplayString (SIZE (0..127))
    MAX-ACCESS read-only
    STATUS     current
    DESCRIPTION
        "The unique id of the sensor."
    ::= { ampDetectSensorEntry 1 }

ampDetectSensorValue OBJECT-TYPE
    SYNTAX     Integer32 (0..65535)
    MAX-ACCESS read-only
    STATUS     current
    DESCRIPTION
        "The value measured by the sensor in tenths of an ampere."
    ::= { ampDetectSensorEntry 2 }

ampDetectSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { ampDetectSensorEntry 3 }

ampDetectSensorLabel OBJECT-TYPE
    SYNTAX     DisplayString
    MAX-ACCESS read-only
    STATUS     current
    DESCRIPTION
        "The unique label assigned to the sensor."
    ::= { ampDetectSensorEntry 4 }

ampDetectSensorEncId OBJECT-TYPE
    SYNTAX     DisplayString (SIZE (0..127))
    MAX-ACCESS read-only
    STATUS     current
    DESCRIPTION
        "The id of the physical enclosure containing the sensor."
    ::= { ampDetectSensorEntry 5 }

ampDetectSensorPortId OBJECT-TYPE
    SYNTAX     DisplayString (SIZE (0..127))
    MAX-ACCESS read-only
    STATUS     current
    DESCRIPTION
        "The id of the port the sensor is plugged into (or empty string
         if it is not plugged into a port)."
    ::= { ampDetectSensorEntry 6 }

ampDetectSensorValueStr OBJECT-TYPE
    SYNTAX     DisplayString
    MAX-ACCESS read-only
    STATUS     current
    DESCRIPTION
        "The amp detect reading, in amperes, shown as a string (or empty string
         if it is not plugged into a port)."
    ::= { ampDetectSensorEntry 7 }

ampDetectSensorValueInt OBJECT-TYPE
    SYNTAX     Integer32 (0..6554)
    MAX-ACCESS read-only
    STATUS     current
    DESCRIPTION
        "The value measured by the sensor in amperes."
    ::= { ampDetectSensorEntry 8 }

ampDetectSensorIndex OBJECT-TYPE
    SYNTAX     Counter32
    MAX-ACCESS read-only
    STATUS     current
    DESCRIPTION
        "The index of the sensor."
    ::= { ampDetectSensorEntry 9 }

-- 
--  Table Index 7 is allocated to "analogInputSensorTable"
--  but has not ever been implemented
--


otherNumericSensorTable OBJECT-TYPE
    SYNTAX     SEQUENCE OF OtherNumericSensorEntry
    MAX-ACCESS not-accessible
    STATUS     current
    DESCRIPTION
        "A list of other numeric sensor entries."
    ::= { netBotzNumericSensors 10 }

otherNumericSensorEntry OBJECT-TYPE
    SYNTAX     OtherNumericSensorEntry
    MAX-ACCESS not-accessible
    STATUS     current
    DESCRIPTION
        "Other numeric sensor entry."
    INDEX { otherNumericSensorIndex }
    ::= { otherNumericSensorTable 1 }

OtherNumericSensorEntry ::= SEQUENCE {
    otherNumericSensorId                      DisplayString,
    otherNumericSensorValue                   Integer32,
    otherNumericSensorErrorStatus             ErrorStatus,
    otherNumericSensorLabel                   DisplayString,
    otherNumericSensorEncId                   DisplayString,
    otherNumericSensorPortId                  DisplayString,
    otherNumericSensorValueStr                DisplayString,
    otherNumericSensorValueInt                Integer32,
    otherNumericSensorUnits                   DisplayString,
    otherNumericSensorValueIntX1000           Integer32,
    otherNumericSensorValueIntX1000000           Integer32,
    otherNumericSensorIndex                   Counter32
}

otherNumericSensorId OBJECT-TYPE
    SYNTAX     DisplayString (SIZE (0..127))
    MAX-ACCESS read-only
    STATUS     current
    DESCRIPTION
        "The unique id of the sensor."
    ::= { otherNumericSensorEntry 1 }

otherNumericSensorValue OBJECT-TYPE
    SYNTAX     Integer32
    MAX-ACCESS read-only
    STATUS     current
    DESCRIPTION
        "The value measured by the sensor in tenths of the unit of measure."
    ::= { otherNumericSensorEntry 2 }

otherNumericSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { otherNumericSensorEntry 3 }

otherNumericSensorLabel OBJECT-TYPE
    SYNTAX     DisplayString
    MAX-ACCESS read-only
    STATUS     current
    DESCRIPTION
        "The unique label assigned to the sensor."
    ::= { otherNumericSensorEntry 4 }

otherNumericSensorEncId OBJECT-TYPE
    SYNTAX     DisplayString (SIZE (0..127))
    MAX-ACCESS read-only
    STATUS     current
    DESCRIPTION
        "The id of the physical enclosure containing the sensor."
    ::= { otherNumericSensorEntry 5 }

otherNumericSensorPortId OBJECT-TYPE
    SYNTAX     DisplayString (SIZE (0..127))
    MAX-ACCESS read-only
    STATUS     current
    DESCRIPTION
        "The id of the port the sensor is plugged into (or empty string
         if it is not plugged into a port)."
    ::= { otherNumericSensorEntry 6 }

otherNumericSensorValueStr OBJECT-TYPE
    SYNTAX     DisplayString
    MAX-ACCESS read-only
    STATUS     current
    DESCRIPTION
        "The sensor reading shown as a string (or empty string
         if it is not plugged into a port)."
    ::= { otherNumericSensorEntry 7 }

otherNumericSensorValueInt OBJECT-TYPE
    SYNTAX     Integer32
    MAX-ACCESS read-only
    STATUS     current
    DESCRIPTION
        "The value measured by the sensor in the unit of measure (1/10 of otherNumericSensorValue)"
    ::= { otherNumericSensorEntry 8 }

otherNumericSensorUnits OBJECT-TYPE
    SYNTAX     DisplayString
    MAX-ACCESS read-only
    STATUS     current
    DESCRIPTION
        "The unit of measure for the sensor value."
    ::= { otherNumericSensorEntry 9 }

otherNumericSensorValueIntX1000 OBJECT-TYPE
    SYNTAX     Integer32
    MAX-ACCESS read-only
    STATUS     current
    DESCRIPTION
        "The value measured by the sensor in thousandths of the unit of measure (100 times otherNumericSensorValue)"
    ::= { otherNumericSensorEntry 10 }

otherNumericSensorValueIntX1000000 OBJECT-TYPE
    SYNTAX     Integer32
    MAX-ACCESS read-only
    STATUS     current
    DESCRIPTION
        "The value measured by the sensor in millionths of the unit of measure (100000 times otherNumericSensorValue)"
    ::= { otherNumericSensorEntry 11 }

otherNumericSensorIndex OBJECT-TYPE
    SYNTAX     Counter32
    MAX-ACCESS read-only
    STATUS     current
    DESCRIPTION
        "The index of the sensor."
    ::= { otherNumericSensorEntry 12 }
        
-- State Sensors Group
-- This group defines sensors having an integer value which is
-- a defined state id or index.

dryContactSensorTable OBJECT-TYPE
    SYNTAX     SEQUENCE OF DryContactSensorEntry
    MAX-ACCESS not-accessible
    STATUS     current
    DESCRIPTION
        "A list of dry contact sensor entries."
    ::= { netBotzStateSensors 1 }

dryContactSensorEntry OBJECT-TYPE
    SYNTAX     DryContactSensorEntry
    MAX-ACCESS not-accessible
    STATUS     current
    DESCRIPTION
        "Dry contact sensor entry."
    INDEX { dryContactSensorIndex }
    ::= { dryContactSensorTable 1 }

DryContactSensorEntry ::= SEQUENCE {
    dryContactSensorId                      DisplayString,
    dryContactSensorValue                   INTEGER,
    dryContactSensorErrorStatus             ErrorStatus,
    dryContactSensorLabel                   DisplayString,
    dryContactSensorEncId                   DisplayString,
    dryContactSensorPortId                  DisplayString,
    dryContactSensorValueStr              DisplayString,
    dryContactSensorIndex                   Counter32
}

dryContactSensorId OBJECT-TYPE
    SYNTAX     DisplayString (SIZE (0..127))
    MAX-ACCESS read-only
    STATUS     current
    DESCRIPTION
        "The unique id of the sensor."
    ::= { dryContactSensorEntry 1 }

dryContactSensorValue OBJECT-TYPE
    SYNTAX     INTEGER { null(-1), open(0), closed(1) }
    MAX-ACCESS read-only
    STATUS     current
    DESCRIPTION
        "Whether the dry sensor contact is open or closed."
    ::= { dryContactSensorEntry 2 }

dryContactSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { dryContactSensorEntry 3 }

dryContactSensorLabel OBJECT-TYPE
    SYNTAX     DisplayString
    MAX-ACCESS read-only
    STATUS     current
    DESCRIPTION
        "The unique label assigned to the sensor."
    ::= { dryContactSensorEntry 4 }

dryContactSensorEncId OBJECT-TYPE
    SYNTAX     DisplayString (SIZE (0..127))
    MAX-ACCESS read-only
    STATUS     current
    DESCRIPTION
        "The id of the physical enclosure containing the sensor."
    ::= { dryContactSensorEntry 5 }

dryContactSensorPortId OBJECT-TYPE
    SYNTAX     DisplayString (SIZE (0..127))
    MAX-ACCESS read-only
    STATUS     current
    DESCRIPTION
        "The id of the port the sensor is plugged into (or empty string
         if it is not plugged into a port)."
    ::= { dryContactSensorEntry 6 }

dryContactSensorValueStr OBJECT-TYPE
    SYNTAX     DisplayString
    MAX-ACCESS read-only
    STATUS     current
    DESCRIPTION
        "The enum value label for the state reported by the sensor."
    ::= { dryContactSensorEntry 7 }

dryContactSensorIndex OBJECT-TYPE
    SYNTAX     Counter32
    MAX-ACCESS read-only
    STATUS     current
    DESCRIPTION
        "The index of the sensor."
    ::= { dryContactSensorEntry 8 }

doorSwitchSensorTable OBJECT-TYPE
    SYNTAX     SEQUENCE OF DoorSwitchSensorEntry
    MAX-ACCESS not-accessible
    STATUS     current
    DESCRIPTION
        "A list of door switch sensor entries."
    ::= { netBotzStateSensors 2 }

doorSwitchSensorEntry OBJECT-TYPE
    SYNTAX     DoorSwitchSensorEntry
    MAX-ACCESS not-accessible
    STATUS     current
    DESCRIPTION
        "Door switch sensor entry."
    INDEX { doorSwitchSensorIndex }
    ::= { doorSwitchSensorTable 1 }

DoorSwitchSensorEntry ::= SEQUENCE {
    doorSwitchSensorId                      DisplayString,
    doorSwitchSensorValue                   INTEGER,
    doorSwitchSensorErrorStatus             ErrorStatus,
    doorSwitchSensorLabel                   DisplayString,
    doorSwitchSensorEncId                   DisplayString,
    doorSwitchSensorPortId                  DisplayString,
    doorSwitchSensorValueStr              DisplayString,
    doorSwitchSensorIndex                   Counter32
}

doorSwitchSensorId OBJECT-TYPE
    SYNTAX     DisplayString (SIZE (0..127))
    MAX-ACCESS read-only
    STATUS     current
    DESCRIPTION
        "The unique id of the sensor."
    ::= { doorSwitchSensorEntry 1 }

doorSwitchSensorValue OBJECT-TYPE
    SYNTAX     INTEGER { null(-1), open(0), closed(1) }
    MAX-ACCESS read-only
    STATUS     current
    DESCRIPTION
        "Whether the door is open or closed."
    ::= { doorSwitchSensorEntry 2 }

doorSwitchSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { doorSwitchSensorEntry 3 }

doorSwitchSensorLabel OBJECT-TYPE
    SYNTAX     DisplayString
    MAX-ACCESS read-only
    STATUS     current
    DESCRIPTION
        "The unique label assigned to the sensor."
    ::= { doorSwitchSensorEntry 4 }

doorSwitchSensorEncId OBJECT-TYPE
    SYNTAX     DisplayString (SIZE (0..127))
    MAX-ACCESS read-only
    STATUS     current
    DESCRIPTION
        "The id of the physical enclosure containing the sensor."
    ::= { doorSwitchSensorEntry 5 }

doorSwitchSensorPortId OBJECT-TYPE
    SYNTAX     DisplayString (SIZE (0..127))
    MAX-ACCESS read-only
    STATUS     current
    DESCRIPTION
        "The id of the port the sensor is plugged into (or empty string
         if it is not plugged into a port)."
    ::= { doorSwitchSensorEntry 6 }

doorSwitchSensorValueStr OBJECT-TYPE
    SYNTAX     DisplayString
    MAX-ACCESS read-only
    STATUS     current
    DESCRIPTION
        "The enum value label for the state reported by the sensor."
    ::= { doorSwitchSensorEntry 7 }

doorSwitchSensorIndex OBJECT-TYPE
    SYNTAX     Counter32
    MAX-ACCESS read-only
    STATUS     current
    DESCRIPTION
        "The index of the sensor."
    ::= { doorSwitchSensorEntry 8 }

cameraMotionSensorTable OBJECT-TYPE
    SYNTAX     SEQUENCE OF CameraMotionSensorEntry
    MAX-ACCESS not-accessible
    STATUS     current
    DESCRIPTION
        "A list of camera motion sensor entries."
    ::= { netBotzStateSensors 3 }

cameraMotionSensorEntry OBJECT-TYPE
    SYNTAX     CameraMotionSensorEntry
    MAX-ACCESS not-accessible
    STATUS     current
    DESCRIPTION
        "Camera motion sensor entry."
    INDEX { cameraMotionSensorIndex }
    ::= { cameraMotionSensorTable 1 }

CameraMotionSensorEntry ::= SEQUENCE {
    cameraMotionSensorId                      DisplayString,
    cameraMotionSensorValue                   INTEGER,
    cameraMotionSensorErrorStatus             ErrorStatus,
    cameraMotionSensorLabel                   DisplayString,
    cameraMotionSensorEncId                   DisplayString,
    cameraMotionSensorPortId                  DisplayString,
    cameraMotionSensorValueStr	              DisplayString,
    cameraMotionSensorIndex                   Counter32
}

cameraMotionSensorId OBJECT-TYPE
    SYNTAX     DisplayString (SIZE (0..127))
    MAX-ACCESS read-only
    STATUS     current
    DESCRIPTION
        "The unique id of the sensor."
    ::= { cameraMotionSensorEntry 1 }

cameraMotionSensorValue OBJECT-TYPE
    SYNTAX     INTEGER { null(-1), noMotion(0), motionDetected(1) }
    MAX-ACCESS read-only
    STATUS     current
    DESCRIPTION
        "Whether motion is detected by the camera sensor."
    ::= { cameraMotionSensorEntry 2 }

cameraMotionSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { cameraMotionSensorEntry 3 }

cameraMotionSensorLabel OBJECT-TYPE
    SYNTAX     DisplayString
    MAX-ACCESS read-only
    STATUS     current
    DESCRIPTION
        "The unique label assigned to the sensor."
    ::= { cameraMotionSensorEntry 4 }

cameraMotionSensorEncId OBJECT-TYPE
    SYNTAX     DisplayString (SIZE (0..127))
    MAX-ACCESS read-only
    STATUS     current
    DESCRIPTION
        "The id of the physical enclosure containing the sensor."
    ::= { cameraMotionSensorEntry 5 }

cameraMotionSensorPortId OBJECT-TYPE
    SYNTAX     DisplayString (SIZE (0..127))
    MAX-ACCESS read-only
    STATUS     current
    DESCRIPTION
        "The id of the port the sensor is plugged into (or empty string
         if it is not plugged into a port)."
    ::= { cameraMotionSensorEntry 6 }

cameraMotionSensorValueStr OBJECT-TYPE
    SYNTAX     DisplayString
    MAX-ACCESS read-only
    STATUS     current
    DESCRIPTION
        "The enum value label for the state reported by the sensor."
    ::= { cameraMotionSensorEntry 7 }

cameraMotionSensorIndex OBJECT-TYPE
    SYNTAX     Counter32
    MAX-ACCESS read-only
    STATUS     current
    DESCRIPTION
        "The index of the sensor."
    ::= { cameraMotionSensorEntry 8 }

otherStateSensorTable OBJECT-TYPE
    SYNTAX     SEQUENCE OF OtherStateSensorEntry
    MAX-ACCESS not-accessible
    STATUS     current
    DESCRIPTION
        "A list of other state sensor entries."
    ::= { netBotzStateSensors 10 }

otherStateSensorEntry OBJECT-TYPE
    SYNTAX     OtherStateSensorEntry
    MAX-ACCESS not-accessible
    STATUS     current
    DESCRIPTION
        "Other state sensor entry."
    INDEX { otherStateSensorIndex }
    ::= { otherStateSensorTable 1 }

OtherStateSensorEntry ::= SEQUENCE {
    otherStateSensorId                      DisplayString,
    otherStateSensorValue                   INTEGER,
    otherStateSensorErrorStatus             ErrorStatus,
    otherStateSensorLabel                   DisplayString,
    otherStateSensorEncId                   DisplayString,
    otherStateSensorPortId                  DisplayString,
    otherStateSensorValueStr              DisplayString,
    otherStateSensorIndex                   Counter32
}

otherStateSensorId OBJECT-TYPE
    SYNTAX     DisplayString (SIZE (0..127))
    MAX-ACCESS read-only
    STATUS     current
    DESCRIPTION
        "The unique id of the sensor."
    ::= { otherStateSensorEntry 1 }

otherStateSensorValue OBJECT-TYPE
    SYNTAX     INTEGER
    MAX-ACCESS read-only
    STATUS     current
    DESCRIPTION
        "State value reported by the sensor."
    ::= { otherStateSensorEntry 2 }
    
otherStateSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { otherStateSensorEntry 3 }

otherStateSensorLabel OBJECT-TYPE
    SYNTAX     DisplayString
    MAX-ACCESS read-only
    STATUS     current
    DESCRIPTION
        "The unique label assigned to the sensor."
    ::= { otherStateSensorEntry 4 }

otherStateSensorEncId OBJECT-TYPE
    SYNTAX     DisplayString (SIZE (0..127))
    MAX-ACCESS read-only
    STATUS     current
    DESCRIPTION
        "The id of the physical enclosure containing the sensor."
    ::= { otherStateSensorEntry 5 }

otherStateSensorPortId OBJECT-TYPE
    SYNTAX     DisplayString (SIZE (0..127))
    MAX-ACCESS read-only
    STATUS     current
    DESCRIPTION
        "The id of port the sensor is plugged into (or empty string
         if it is not plugged into a port)."
    ::= { otherStateSensorEntry 6 }

otherStateSensorValueStr OBJECT-TYPE
    SYNTAX     DisplayString
    MAX-ACCESS read-only
    STATUS     current
    DESCRIPTION
        "The enum value label for the state reported by the sensor."
    ::= { otherStateSensorEntry 7 }

otherStateSensorIndex OBJECT-TYPE
    SYNTAX     Counter32
    MAX-ACCESS read-only
    STATUS     current
    DESCRIPTION
        "The index of the sensor."
    ::= { otherStateSensorEntry 8 }



-- Error Conditions Group
--

errorCondTable OBJECT-TYPE
    SYNTAX     SEQUENCE OF ErrorCondEntry
    MAX-ACCESS not-accessible
    STATUS     current
    DESCRIPTION
        "A list of active and resolved error conditions."
    ::= { netBotzErrors 1 }

errorCondEntry OBJECT-TYPE
    SYNTAX     ErrorCondEntry
    MAX-ACCESS not-accessible
    STATUS     current
    DESCRIPTION
        "Error condition entry."
    INDEX { errorCondIndex }
    ::= { errorCondTable 1 }

ErrorCondEntry ::= SEQUENCE {
    errorCondId                          DisplayString,
    errorCondSeverity                    ErrorStatus,
    errorCondTypeId                      DisplayString,
    errorCondStartTime                   DateAndTime,
    errorCondStartTimeStr                DisplayString,
    errorCondResolved                    BoolValue,
    errorCondResolvedTime                DateAndTime,
    errorCondResolvedTimeStr             DisplayString,
    errorCondEncId                       DisplayString,
    errorCondPortId                      DisplayString,
    errorCondSensorId                    DisplayString,
    errorCondIndex                       Counter32
}

errorCondId    OBJECT-TYPE
    SYNTAX     DisplayString (SIZE (0..127))
    MAX-ACCESS read-only
    STATUS     current
    DESCRIPTION
        "The unique id of the error condition."
    ::= { errorCondEntry 1 }

errorCondSeverity OBJECT-TYPE
    SYNTAX     ErrorStatus
    MAX-ACCESS read-only
    STATUS     current
    DESCRIPTION
        "The relative severity of the error condition."
    ::= { errorCondEntry 2 }

errorCondTypeId  OBJECT-TYPE
    SYNTAX     DisplayString (SIZE (0..127))
    MAX-ACCESS read-only
    STATUS     current
    DESCRIPTION
        "The error type id reported for the error condition."
    ::= { errorCondEntry 3 }

errorCondStartTime OBJECT-TYPE
    SYNTAX     DateAndTime
    MAX-ACCESS read-only
    STATUS     current
    DESCRIPTION
        "The start time of the error condition, in msec since 1/1/1970."
    ::= { errorCondEntry 4 }

errorCondStartTimeStr OBJECT-TYPE
    SYNTAX     DisplayString
    MAX-ACCESS read-only
    STATUS     current
    DESCRIPTION
        "The start time of the error condition, as ISO date-time formatted string (UTC)."
    ::= { errorCondEntry 5 }

errorCondResolved OBJECT-TYPE
    SYNTAX     BoolValue
    MAX-ACCESS read-only
    STATUS     current
    DESCRIPTION
        "Whether the error condition was resolved."
    ::= { errorCondEntry 6 }

errorCondResolvedTime OBJECT-TYPE
    SYNTAX     DateAndTime
    MAX-ACCESS read-only
    STATUS     current
    DESCRIPTION
        "The time the error condition was resolved (if it was resolved), in msec since 1/1/1970."
    ::= { errorCondEntry 7 }

errorCondResolvedTimeStr OBJECT-TYPE
    SYNTAX     DisplayString
    MAX-ACCESS read-only
    STATUS     current
    DESCRIPTION
        "The time the error condition was resolved (if it was resolved), as ISO date-time formatted string (UTC)."
    ::= { errorCondEntry 8 }

errorCondEncId OBJECT-TYPE
    SYNTAX     DisplayString (SIZE (0..127))
    MAX-ACCESS read-only
    STATUS     current
    DESCRIPTION
        "The id of the physical enclosure associated with the error."
    ::= { errorCondEntry 9 }

errorCondPortId OBJECT-TYPE
    SYNTAX     DisplayString (SIZE (0..127))
    MAX-ACCESS read-only
    STATUS     current
    DESCRIPTION
        "The id of the port associated with the error (or empty string
         if the error is not associated with a port)."
    ::= { errorCondEntry 10 }

errorCondSensorId OBJECT-TYPE
    SYNTAX     DisplayString (SIZE (0..127))
    MAX-ACCESS read-only
    STATUS     current
    DESCRIPTION
        "The id of the sensor associated with the error (or empty string
         if the error is not associated with a sensor.)"
    ::= { errorCondEntry 11 }

errorCondIndex OBJECT-TYPE
    SYNTAX     Counter32
    MAX-ACCESS read-only
    STATUS     current
    DESCRIPTION
        "The index of the error condition."
    ::= { errorCondEntry 12 }


-- Alert specific definitions
--

netBotzTrapErrorID	OBJECT-TYPE
	SYNTAX		DisplayString (SIZE (0..127))
	MAX-ACCESS		read-only
	STATUS		current
	DESCRIPTION 	"Unique ID of error condition that produced the trap"
	::= { netBotzTrapParms 1 }

netBotzTrapErrorType	OBJECT-TYPE
	SYNTAX		DisplayString (SIZE (0..127))
	MAX-ACCESS		read-only
	STATUS		current
	DESCRIPTION 	"Symbolic ID of error type"
	::= { netBotzTrapParms 2 }


netBotzTrapErrorTypeLabel	OBJECT-TYPE
	SYNTAX		DisplayString
	MAX-ACCESS		read-only
	STATUS		current
	DESCRIPTION 	"Label for error type"
	::= { netBotzTrapParms 3 }


netBotzTrapSensorID	OBJECT-TYPE
	SYNTAX		DisplayString (SIZE (0..127))
	MAX-ACCESS		read-only
	STATUS		current
	DESCRIPTION 	"ID of sensor associated with error condition that produced the trap"
	::= { netBotzTrapParms 4 }

netBotzTrapSensorLabel	OBJECT-TYPE
	SYNTAX		DisplayString
	MAX-ACCESS		read-only
	STATUS		current
	DESCRIPTION 	"Label of sensor associated with error condition that produced the trap"
	::= { netBotzTrapParms 5 }

netBotzTrapPodID	OBJECT-TYPE
	SYNTAX		DisplayString (SIZE (0..127))
	MAX-ACCESS		read-only
	STATUS		current
	DESCRIPTION 	"ID of pod associated with error condition that produced the trap"
	::= { netBotzTrapParms 6 }

netBotzTrapPodLabel	OBJECT-TYPE
	SYNTAX		DisplayString
	MAX-ACCESS		read-only
	STATUS		current
	DESCRIPTION 	"Label of pod associated with error condition that produced the trap"
	::= { netBotzTrapParms 7 }

netBotzTrapPortID	OBJECT-TYPE
	SYNTAX		DisplayString (SIZE (0..127))
	MAX-ACCESS		read-only
	STATUS		current
	DESCRIPTION 	"ID of port associated with error condition that produced the trap"
	::= { netBotzTrapParms 8 }

netBotzTrapPortLabel	OBJECT-TYPE
	SYNTAX		DisplayString
	MAX-ACCESS		read-only
	STATUS		current
	DESCRIPTION 	"Label of port associated with error condition that produced the trap"
	::= { netBotzTrapParms 9 }

netBotzTrapStartTime	OBJECT-TYPE
	SYNTAX		INTEGER
	MAX-ACCESS		read-only
	STATUS		current
	DESCRIPTION	"Start time (in UTC seconds) for error that produced the trap"
	::= { netBotzTrapParms 10 }

netBotzTrapNotifyTime	OBJECT-TYPE
	SYNTAX		INTEGER
	MAX-ACCESS		read-only
	STATUS		current
	DESCRIPTION	"Notification time (in UTC seconds) for error that produced the trap"
	::= { netBotzTrapParms 11 }

netBotzTrapResolveTime	OBJECT-TYPE
	SYNTAX		INTEGER
	MAX-ACCESS		read-only
	STATUS		current
	DESCRIPTION	"Resolve time (in UTC seconds) for error that produced the trap"
	::= { netBotzTrapParms 12 }

netBotzTrapSeverity	OBJECT-TYPE
	SYNTAX		INTEGER {
			information(0),
			warning(1),
			error(2),
			critical(3),
			failure(4)
			}
	MAX-ACCESS		read-only
	STATUS		current
	DESCRIPTION	"Severity of error that produced the trap"
	::= { netBotzTrapParms 13 }

netBotzTrapSensorValue	OBJECT-TYPE
	SYNTAX		DisplayString
	MAX-ACCESS		read-only
	STATUS		current
	DESCRIPTION 	"String presentation of value of sensor"
	::= { netBotzTrapParms 14 }

netBotzTrapSensorValueInt	OBJECT-TYPE
	SYNTAX		INTEGER
	MAX-ACCESS		read-only
	STATUS		current
	DESCRIPTION 	"Whole integer representation of value of sensor (without decimal portion)"
	::= { netBotzTrapParms 15 }

netBotzTrapSensorValueFraction	OBJECT-TYPE
	SYNTAX		INTEGER
	MAX-ACCESS		read-only
	STATUS		current
	DESCRIPTION 	"Fractional portion of value of sensor (multiplied by 1000000)"
	::= { netBotzTrapParms 16 }


netBotzTempTooHigh NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION "Temperature sensor value too high."
	::= { netBotzTempSensorTraps 0 2 }

netBotzTempTooHighRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION "Temperature sensor value is no longer too high."
	::= { netBotzTempSensorTraps 0 102 }

netBotzTempTooLow NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION "Temperature sensor value too low."
	::= { netBotzTempSensorTraps 0 3 }

netBotzTempTooLowRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION "Temperature sensor value is no longer too low."
	::= { netBotzTempSensorTraps 0 103 }

netBotzTempTooHighTooLong NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Temperature sensor value too high for too long."
	::= { netBotzTempSensorTraps 0 4 }

netBotzTempTooHighTooLongRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Temperature sensor value is no longer too high for too long."
	::= { netBotzTempSensorTraps 0 104 }

netBotzTempTooLowTooLong NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Temperature sensor value too low for too long."
	::= { netBotzTempSensorTraps 0 5 }

netBotzTempTooLowForTooLongRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Temperature sensor value is no longer too low for too long."
	::= { netBotzTempSensorTraps 0 105 }

netBotzTempUnplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Temperature sensor unplugged."
	::= { netBotzTempSensorTraps 0 6 }

netBotzTempReplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Temperature sensor no longer unplugged."
	::= { netBotzTempSensorTraps 0 106 }

netBotzTempIncreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Temperature sensor value increasing too quickly."
	::= { netBotzTempSensorTraps 0 8 }

netBotzTempNotIncreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Temperature sensor value no longer increasing too quickly."
	::= { netBotzTempSensorTraps 0 108 }

netBotzTempDecreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Temperature sensor value decreasing too quickly."
	::= { netBotzTempSensorTraps 0 9 }

netBotzTempNotDecreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Temperature sensor value no longer decreasing too quickly."
	::= { netBotzTempSensorTraps 0 109 }

netBotzTempError NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Temperature sensor error."
	::= { netBotzTempSensorTraps 0 1 }

netBotzTempErrorRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Temperature sensor error resolved."
	::= { netBotzTempSensorTraps 0 101 }

netBotzHumidityTooHigh NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Humidity sensor value too high."
	::= { netBotzHumiditySensorTraps 0 2 }

netBotzHumidityTooHighRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Humidity sensor value is no longer too high."
	::= { netBotzHumiditySensorTraps 0 102 }

netBotzHumidityTooLow NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Humidity sensor value too low."
	::= { netBotzHumiditySensorTraps 0 3 }

netBotzHumidityTooLowRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Humidity sensor value is no longer too low."
	::= { netBotzHumiditySensorTraps 0 103 }

netBotzHumidityTooHighTooLong NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Humidity sensor value too high for too long."
	::= { netBotzHumiditySensorTraps 0 4 }

netBotzHumidityTooHighTooLongRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Humidity sensor value is no longer too high for too long."
	::= { netBotzHumiditySensorTraps 0 104 }

netBotzHumidityTooLowTooLong NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Humidity sensor value too low for too long."
	::= { netBotzHumiditySensorTraps 0 5 }

netBotzHumidityTooLowForTooLongRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Humidity sensor value is no longer too low for too long."
	::= { netBotzHumiditySensorTraps 0 105 }

netBotzHumidityUnplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Humidity sensor unplugged."
	::= { netBotzHumiditySensorTraps 0 6 }

netBotzHumidityReplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Humidity sensor no longer unplugged."
	::= { netBotzHumiditySensorTraps 0 106 }

netBotzHumidityIncreasingTooQuickly NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Humidity sensor value increasing too quickly."
	::= { netBotzHumiditySensorTraps 0 8 }

netBotzHumidityNotIncreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Humidity sensor value no longer increasing too quickly."
	::= { netBotzHumiditySensorTraps 0 108 }

netBotzHumidityDecreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Humidity sensor value decreasing too quickly."
	::= { netBotzHumiditySensorTraps 0 9 }

netBotzHumidityNotDecreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Humidity sensor value no longer decreasing too quickly."
	::= { netBotzHumiditySensorTraps 0 109 }

netBotzHumidityError NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Humidity sensor error."
	::= { netBotzHumiditySensorTraps 0 1 }

netBotzHumidityErrorRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Humidity sensor error resolved."
	::= { netBotzHumiditySensorTraps 0 101 }

netBotzDewPointTooHigh NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"DewPoint sensor value too high."
	::= { netBotzDewPointSensorTraps 0 2 }

netBotzDewPointTooHighRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"DewPoint sensor value is no longer too high."
	::= { netBotzDewPointSensorTraps 0 102 }

netBotzDewPointTooLow NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"DewPoint sensor value too low."
	::= { netBotzDewPointSensorTraps 0 3 }

netBotzDewPointTooLowRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"DewPoint sensor value is no longer too low."
	::= { netBotzDewPointSensorTraps 0 103 }

netBotzDewPointTooHighTooLong NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"DewPoint sensor value too high for too long."
	::= { netBotzDewPointSensorTraps 0 4 }

netBotzDewPointTooHighTooLongRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"DewPoint sensor value is no longer too high for too long."
	::= { netBotzDewPointSensorTraps 0 104 }

netBotzDewPointTooLowTooLong NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"DewPoint sensor value too low for too long."
	::= { netBotzDewPointSensorTraps 0 5 }

netBotzDewPointTooLowForTooLongRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"DewPoint sensor value is no longer too low for too long."
	::= { netBotzDewPointSensorTraps 0 105 }

netBotzDewPointUnplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"DewPoint sensor unplugged."
	::= { netBotzDewPointSensorTraps 0 6 }

netBotzDewPointReplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"DewPoint sensor no longer unplugged."
	::= { netBotzDewPointSensorTraps 0 106 }

netBotzDewPointIncreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"DewPoint sensor value increasing too quickly."
	::= { netBotzDewPointSensorTraps 0 8 }

netBotzDewPointNotIncreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"DewPoint sensor value no longer increasing too quickly."
	::= { netBotzDewPointSensorTraps 0 108 }

netBotzDewPointDecreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"DewPoint sensor value decreasing too quickly."
	::= { netBotzDewPointSensorTraps 0 9 }

netBotzDewPointNotDecreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"DewPoint sensor value no longer decreasing too quickly."
	::= { netBotzDewPointSensorTraps 0 109 }

netBotzDewPointError NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"DewPoint sensor error."
	::= { netBotzDewPointSensorTraps 0 1 }

netBotzDewPointErrorRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"DewPoint sensor error resolved."
	::= { netBotzDewPointSensorTraps 0 101 }

netBotzAirFlowTooHigh NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"AirFlow sensor value too high."
	::= { netBotzAirFlowSensorTraps 0 2 }

netBotzAirFlowTooHighRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"AirFlow sensor value is no longer too high."
	::= { netBotzAirFlowSensorTraps 0 102 }

netBotzAirFlowTooLow NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"AirFlow sensor value too low."
	::= { netBotzAirFlowSensorTraps 0 3 }

netBotzAirFlowTooLowRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"AirFlow sensor value is no longer too low."
	::= { netBotzAirFlowSensorTraps 0 103 }

netBotzAirFlowTooHighTooLong NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"AirFlow sensor value too high for too long."
	::= { netBotzAirFlowSensorTraps 0 4 }

netBotzAirFlowTooHighTooLongRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"AirFlow sensor value is no longer too high for too long."
	::= { netBotzAirFlowSensorTraps 0 104 }

netBotzAirFlowTooLowTooLong NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"AirFlow sensor value too low for too long."
	::= { netBotzAirFlowSensorTraps 0 5 }

netBotzAirFlowTooLowForTooLongRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"AirFlow sensor value is no longer too low for too long."
	::= { netBotzAirFlowSensorTraps 0 105 }

netBotzAirFlowUnplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"AirFlow sensor unplugged."
	::= { netBotzAirFlowSensorTraps 0 6 }

netBotzAirFlowReplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"AirFlow sensor no longer unplugged."
	::= { netBotzAirFlowSensorTraps 0 106 }

netBotzAirFlowIncreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"AirFlow sensor value increasing too quickly."
	::= { netBotzAirFlowSensorTraps 0 8 }

netBotzAirFlowNotIncreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"AirFlow sensor value no longer increasing too quickly."
	::= { netBotzAirFlowSensorTraps 0 108 }

netBotzAirFlowDecreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"AirFlow sensor value decreasing too quickly."
	::= { netBotzAirFlowSensorTraps 0 9 }

netBotzAirFlowNotDecreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"AirFlow sensor value no longer decreasing too quickly."
	::= { netBotzAirFlowSensorTraps 0 109 }

netBotzAirFlowError NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"AirFlow sensor error."
	::= { netBotzAirFlowSensorTraps 0 1 }

netBotzAirFlowErrorRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"AirFlow sensor error resolved."
	::= { netBotzAirFlowSensorTraps 0 101 }

netBotzAudioTooHigh NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Audio sensor value too high."
	::= { netBotzAudioSensorTraps 0 2 }

netBotzAudioTooHighRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Audio sensor value is no longer too high."
	::= { netBotzAudioSensorTraps 0 102 }

netBotzAudioTooLow NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Audio sensor value too low."
	::= { netBotzAudioSensorTraps 0 3 }

netBotzAudioTooLowRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Audio sensor value is no longer too low."
	::= { netBotzAudioSensorTraps 0 103 }

netBotzAudioTooHighTooLong NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Audio sensor value too high for too long."
	::= { netBotzAudioSensorTraps 0 4 }

netBotzAudioTooHighTooLongRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Audio sensor value is no longer too high for too long."
	::= { netBotzAudioSensorTraps 0 104 }

netBotzAudioTooLowTooLong NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Audio sensor value too low for too long."
	::= { netBotzAudioSensorTraps 0 5 }

netBotzAudioTooLowForTooLongRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Audio sensor value is no longer too low for too long."
	::= { netBotzAudioSensorTraps 0 105 }

netBotzAudioUnplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Audio sensor unplugged."
	::= { netBotzAudioSensorTraps 0 6 }

netBotzAudioReplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Audio sensor no longer unplugged."
	::= { netBotzAudioSensorTraps 0 106 }

netBotzAudioIncreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Audio sensor value increasing too quickly."
	::= { netBotzAudioSensorTraps 0 8 }

netBotzAudioNotIncreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Audio sensor value no longer increasing too quickly."
	::= { netBotzAudioSensorTraps 0 108 }

netBotzAudioDecreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Audio sensor value decreasing too quickly."
	::= { netBotzAudioSensorTraps 0 9 }

netBotzAudioNotDecreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Audio sensor value no longer decreasing too quickly."
	::= { netBotzAudioSensorTraps 0 109 }

netBotzAudioError NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Audio sensor error."
	::= { netBotzAudioSensorTraps 0 1 }

netBotzAudioErrorRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Audio sensor error resolved."
	::= { netBotzAudioSensorTraps 0 101 }

netBotzAmpDetectTooHigh NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Amp Detectsensor value too high."
	::= { netBotzAmpDetectSensorTraps 0 2 }

netBotzAmpDetectTooHighRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Amp Detectsensor value is no longer too high."
	::= { netBotzAmpDetectSensorTraps 0 102 }

netBotzAmpDetectTooLow NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Amp Detectsensor value too low."
	::= { netBotzAmpDetectSensorTraps 0 3 }

netBotzAmpDetectTooLowRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Amp Detectsensor value is no longer too low."
	::= { netBotzAmpDetectSensorTraps 0 103 }

netBotzAmpDetectTooHighTooLong NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Amp Detectsensor value too high for too long."
	::= { netBotzAmpDetectSensorTraps 0 4 }

netBotzAmpDetectTooHighTooLongRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Amp Detectsensor value is no longer too high for too long."
	::= { netBotzAmpDetectSensorTraps 0 104 }

netBotzAmpDetectTooLowTooLong NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Amp Detectsensor value too low for too long."
	::= { netBotzAmpDetectSensorTraps 0 5 }

netBotzAmpDetectTooLowForTooLongRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Amp Detectsensor value is no longer too low for too long."
	::= { netBotzAmpDetectSensorTraps 0 105 }

netBotzAmpDetectUnplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Amp Detectsensor unplugged."
	::= { netBotzAmpDetectSensorTraps 0 6 }

netBotzAmpDetectReplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Amp Detectsensor no longer unplugged."
	::= { netBotzAmpDetectSensorTraps 0 106 }

netBotzAmpDetectIncreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Amp Detectsensor value increasing too quickly."
	::= { netBotzAmpDetectSensorTraps 0 8 }

netBotzAmpDetectNotIncreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Amp Detectsensor value no longer increasing too quickly."
	::= { netBotzAmpDetectSensorTraps 0 108 }

netBotzAmpDetectDecreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Amp Detectsensor value decreasing too quickly."
	::= { netBotzAmpDetectSensorTraps 0 9 }

netBotzAmpDetectNotDecreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Amp Detectsensor value no longer decreasing too quickly."
	::= { netBotzAmpDetectSensorTraps 0 109 }

netBotzAmpDetectError NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Amp Detectsensor error."
	::= { netBotzAmpDetectSensorTraps 0 1 }

netBotzAmpDetectErrorRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Amp Detectsensor error resolved."
	::= { netBotzAmpDetectSensorTraps 0 101 }

netBotzDryContactUnplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Dry Contact sensor unplugged."
	::= { netBotzDryContactSensorTraps 0 6 }

netBotzDryContactReplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Dry Contact sensor no longer unplugged."
	::= { netBotzDryContactSensorTraps 0 106 }

netBotzDryContactError NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Dry Contact sensor error."
	::= { netBotzDryContactSensorTraps 0 1 }

netBotzDryContactErrorRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Dry Contact sensor error resolved."
	::= { netBotzDryContactSensorTraps 0 101 }

netBotzDryContactValueError NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Dry Contact sensor value error."
	::= { netBotzDryContactSensorTraps 0 10 }

netBotzDryContactValueErrorRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Dry Contact sensor value error resolved."
	::= { netBotzDryContactSensorTraps 0 110 }

netBotzCameraMotionSensorUnplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Camera Motion Sensor sensor unplugged."
	::= { netBotzCameraMotionSensorTraps 0 6 }

netBotzCameraMotionSensorReplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Camera Motion Sensor sensor no longer unplugged."
	::= { netBotzCameraMotionSensorTraps 0 106 }

netBotzCameraMotionSensorError NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Camera Motion Sensor sensor error."
	::= { netBotzCameraMotionSensorTraps 0 1 }

netBotzCameraMotionSensorErrorRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Camera Motion Sensor sensor error resolved."
	::= { netBotzCameraMotionSensorTraps 0 101 }

netBotzCameraMotionSensorValueError NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Camera Motion Sensor sensor value error."
	::= { netBotzCameraMotionSensorTraps 0 10 }

netBotzCameraMotionSensorValueErrorRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Camera Motion Sensor sensor value error resolved."
	::= { netBotzCameraMotionSensorTraps 0 110 }

netBotzDoorSensorUnplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Door Sensor sensor unplugged."
	::= { netBotzDoorSensorTraps 0 6 }

netBotzDoorSensorReplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Door Sensor sensor no longer unplugged."
	::= { netBotzDoorSensorTraps 0 106 }

netBotzDoorSensorError NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Door Sensor sensor error."
	::= { netBotzDoorSensorTraps 0 1 }

netBotzDoorSensorErrorRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Door Sensor sensor error resolved."
	::= { netBotzDoorSensorTraps 0 101 }

netBotzDoorSensorValueError NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Door Sensor sensor value error."
	::= { netBotzDoorSensorTraps 0 10 }

netBotzDoorSensorValueErrorRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Door Sensor sensor value error resolved."
	::= { netBotzDoorSensorTraps 0 110 }

netBotzMicPlugSensorUnplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"MicPlug Sensor sensor unplugged."
	::= { netBotzMicPlugSensorTraps 0 6 }

netBotzMicPlugSensorReplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"MicPlug Sensor sensor no longer unplugged."
	::= { netBotzMicPlugSensorTraps 0 106 }

netBotzMicPlugSensorError NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"MicPlug Sensor sensor error."
	::= { netBotzMicPlugSensorTraps 0 1 }

netBotzMicPlugSensorErrorRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"MicPlug Sensor sensor error resolved."
	::= { netBotzMicPlugSensorTraps 0 101 }

netBotzMicPlugSensorValueError NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"MicPlug Sensor sensor value error."
	::= { netBotzMicPlugSensorTraps 0 10 }

netBotzMicPlugSensorValueErrorRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"MicPlug Sensor sensor value error resolved."
	::= { netBotzMicPlugSensorTraps 0 110 }

netBotzSpeakerPlugSensorUnplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"SpeakerPlug Sensor sensor unplugged."
	::= { netBotzSpeakerPlugSensorTraps 0 6 }

netBotzSpeakerPlugSensorReplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"SpeakerPlug Sensor sensor no longer unplugged."
	::= { netBotzSpeakerPlugSensorTraps 0 106 }

netBotzSpeakerPlugSensorError NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"SpeakerPlug Sensor sensor error."
	::= { netBotzSpeakerPlugSensorTraps 0 1 }

netBotzSpeakerPlugSensorErrorRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"SpeakerPlug Sensor sensor error resolved."
	::= { netBotzSpeakerPlugSensorTraps 0 101 }

netBotzSpeakerPlugSensorValueError NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"SpeakerPlug Sensor sensor value error."
	::= { netBotzSpeakerPlugSensorTraps 0 10 }

netBotzSpeakerPlugSensorValueErrorRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"SpeakerPlug Sensor sensor value error resolved."
	::= { netBotzSpeakerPlugSensorTraps 0 110 }


netBotzTVSignalSensorUnplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"TVSignal Sensor sensor unplugged."
	::= { netBotzTVSignalSensorTraps 0 6 }

netBotzTVSignalSensorReplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"TVSignal Sensor sensor no longer unplugged."
	::= { netBotzTVSignalSensorTraps 0 106 }

netBotzTVSignalSensorError NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"TVSignal Sensor sensor error."
	::= { netBotzTVSignalSensorTraps 0 1 }

netBotzTVSignalSensorErrorRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"TVSignal Sensor sensor error resolved."
	::= { netBotzTVSignalSensorTraps 0 101 }

netBotzTVSignalSensorValueError NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"TVSignal Sensor sensor value error."
	::= { netBotzTVSignalSensorTraps 0 10 }

netBotzTVSignalSensorValueErrorRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"TVSignal Sensor sensor value error resolved."
	::= { netBotzTVSignalSensorTraps 0 110 }

netBotzPodUnplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Pod unplugged."
	::= { netBotzPodTraps 0 7 }

netBotzPodReplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Pod no longer unplugged."
	::= { netBotzPodTraps 0 107 }

netBotzSensorPodUnplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Sensor Pod unplugged."
	::= { netBotzSensorPodTraps 0 7 }

netBotzSensorPodReplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Sensor Pod no longer unplugged."
	::= { netBotzSensorPodTraps 0 107 }

netBotzCameraPodUnplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Camera Pod unplugged."
	::= { netBotzCameraPodTraps 0 7 }

netBotzCameraPodReplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Camera Pod no longer unplugged."
	::= { netBotzCameraPodTraps 0 107 }

netBotzCCTVPodUnplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"CCTV Pod unplugged."
	::= { netBotzCCTVPodTraps 0 7 }

netBotzCCTVPodReplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"CCTV Pod no longer unplugged."
	::= { netBotzCCTVPodTraps 0 107 }

netBotz4to20mAPodUnplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"4-20mA Pod unplugged."
	::= { netBotz4to20mAPodTraps 0 7 }

netBotz4to20mAPodReplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"4-20mA Pod no longer unplugged."
	::= { netBotz4to20mAPodTraps 0 107 }

netBotzLogonError NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Multiple failed logon attempts."
	::= { netBotzPodTraps 0 11 }

netBotzLogonErrorResolved NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Failed logon attempts stopped, or logon succeeded."
	::= { netBotzPodTraps 0 111 }

netBotzDriveNotFoundError NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Configured add-on drive not found or has malfunctioned."
	::= { netBotzPodTraps 0 12 }

netBotzDriveNotFoundErrorResolved NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Missing add-on drive has bee found."
	::= { netBotzPodTraps 0 112 }

netBotzRmtLinkError NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Configured remote link has failed."
	::= { netBotzPodTraps 0 13 }

netBotzRmtLinkErrorResolved NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Configured remote link has returned to normal."
	::= { netBotzPodTraps 0 113 }

netBotzGPSPositionTooHigh NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Position sensor value too high."
	::= { netBotzGPSPositionSensorTraps 0 2 }

netBotzGPSPositionTooHighRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Position sensor value is no longer too high."
	::= { netBotzGPSPositionSensorTraps 0 102 }

netBotzGPSPositionTooLow NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Position sensor value too low."
	::= { netBotzGPSPositionSensorTraps 0 3 }

netBotzGPSPositionTooLowRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Position sensor value is no longer too low."
	::= { netBotzGPSPositionSensorTraps 0 103 }

netBotzGPSPositionTooHighTooLong NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Position sensor value too high for too long."
	::= { netBotzGPSPositionSensorTraps 0 4 }

netBotzGPSPositionTooHighTooLongRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Position sensor value is no longer too high for too long."
	::= { netBotzGPSPositionSensorTraps 0 104 }

netBotzGPSPositionTooLowTooLong NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Position ensor value too low for too long."
	::= { netBotzGPSPositionSensorTraps 0 5 }

netBotzGPSPositionTooLowForTooLongRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Position sensor value is no longer too low for too long."
	::= { netBotzGPSPositionSensorTraps 0 105 }

netBotzGPSPositionUnplugged NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Position sensor unplugged."
	::= { netBotzGPSPositionSensorTraps 0 6 }

netBotzGPSPositionReplugged NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Position sensor no longer unplugged."
	::= { netBotzGPSPositionSensorTraps 0 106 }

netBotzGPSPositionIncreasingTooQuickly NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Position sensor value increasing too quickly."
	::= { netBotzGPSPositionSensorTraps 0 8 }

netBotzGPSPositionNotIncreasingTooQuickly NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Position sensor value no longer increasing too quickly."
	::= { netBotzGPSPositionSensorTraps 0 108 }

netBotzGPSPositionDecreasingTooQuickly NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Position sensor value decreasing too quickly."
	::= { netBotzGPSPositionSensorTraps 0 9 }

netBotzGPSPositionNotDecreasingTooQuickly NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Position sensor value no longer decreasing too quickly."
	::= { netBotzGPSPositionSensorTraps 0 109 }

netBotzGPSPositionError NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Position sensor error."
	::= { netBotzGPSPositionSensorTraps 0 1 }

netBotzGPSPositionErrorRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Position sensor error resolved."
	::= { netBotzGPSPositionSensorTraps 0 101 }

netBotzGPSMovementTooHigh NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Movement sensor value too high."
	::= { netBotzGPSMovementSensorTraps 0 2 }

netBotzGPSMovementTooHighRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Movement sensor value is no longer too high."
	::= { netBotzGPSMovementSensorTraps 0 102 }

netBotzGPSMovementTooLow NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Movement sensor value too low."
	::= { netBotzGPSMovementSensorTraps 0 3 }

netBotzGPSMovementTooLowRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Movement sensor value is no longer too low."
	::= { netBotzGPSMovementSensorTraps 0 103 }

netBotzGPSMovementTooHighTooLong NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Movement sensor value too high for too long."
	::= { netBotzGPSMovementSensorTraps 0 4 }

netBotzGPSMovementTooHighTooLongRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Movement sensor value is no longer too high for too long."
	::= { netBotzGPSMovementSensorTraps 0 104 }

netBotzGPSMovementTooLowTooLong NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Movement ensor value too low for too long."
	::= { netBotzGPSMovementSensorTraps 0 5 }

netBotzGPSMovementTooLowForTooLongRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Movement sensor value is no longer too low for too long."
	::= { netBotzGPSMovementSensorTraps 0 105 }

netBotzGPSMovementUnplugged NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Movement sensor unplugged."
	::= { netBotzGPSMovementSensorTraps 0 6 }

netBotzGPSMovementReplugged NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Movement sensor no longer unplugged."
	::= { netBotzGPSMovementSensorTraps 0 106 }

netBotzGPSMovementIncreasingTooQuickly NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Movement sensor value increasing too quickly."
	::= { netBotzGPSMovementSensorTraps 0 8 }

netBotzGPSMovementNotIncreasingTooQuickly NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Movement sensor value no longer increasing too quickly."
	::= { netBotzGPSMovementSensorTraps 0 108 }

netBotzGPSMovementDecreasingTooQuickly NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Movement sensor value decreasing too quickly."
	::= { netBotzGPSMovementSensorTraps 0 9 }

netBotzGPSMovementNotDecreasingTooQuickly NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Movement sensor value no longer decreasing too quickly."
	::= { netBotzGPSMovementSensorTraps 0 109 }

netBotzGPSMovementError NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Movement sensor error."
	::= { netBotzGPSMovementSensorTraps 0 1 }

netBotzGPSMovementErrorRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Movement sensor error resolved."
	::= { netBotzGPSMovementSensorTraps 0 101 }

netBotzPacketDropTooHigh NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Packet Drop sensor value too high."
	::= { netBotzPacketDropSensorTraps 0 2 }

netBotzPacketDropTooHighRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Packet Drop sensor value is no longer too high."
	::= { netBotzPacketDropSensorTraps 0 102 }

netBotzPacketDropTooLow NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Packet Drop sensor value too low."
	::= { netBotzPacketDropSensorTraps 0 3 }

netBotzPacketDropTooLowRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Packet Drop sensor value is no longer too low."
	::= { netBotzPacketDropSensorTraps 0 103 }

netBotzPacketDropTooHighTooLong NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Packet Drop sensor value too high for too long."
	::= { netBotzPacketDropSensorTraps 0 4 }

netBotzPacketDropTooHighTooLongRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Packet Drop sensor value is no longer too high for too long."
	::= { netBotzPacketDropSensorTraps 0 104 }

netBotzPacketDropTooLowTooLong NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Packet Drop ensor value too low for too long."
	::= { netBotzPacketDropSensorTraps 0 5 }

netBotzPacketDropTooLowForTooLongRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Packet Drop sensor value is no longer too low for too long."
	::= { netBotzPacketDropSensorTraps 0 105 }

netBotzPacketDropUnplugged NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Packet Drop sensor unplugged."
	::= { netBotzPacketDropSensorTraps 0 6 }

netBotzPacketDropReplugged NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Packet Drop sensor no longer unplugged."
	::= { netBotzPacketDropSensorTraps 0 106 }

netBotzPacketDropIncreasingTooQuickly NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Packet Drop sensor value increasing too quickly."
	::= { netBotzPacketDropSensorTraps 0 8 }

netBotzPacketDropNotIncreasingTooQuickly NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Packet Drop sensor value no longer increasing too quickly."
	::= { netBotzPacketDropSensorTraps 0 108 }

netBotzPacketDropDecreasingTooQuickly NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Packet Drop sensor value decreasing too quickly."
	::= { netBotzPacketDropSensorTraps 0 9 }

netBotzPacketDropNotDecreasingTooQuickly NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Packet Drop sensor value no longer decreasing too quickly."
	::= { netBotzPacketDropSensorTraps 0 109 }

netBotzPacketDropError NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Packet Drop sensor error."
	::= { netBotzPacketDropSensorTraps 0 1 }

netBotzPacketDropErrorRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Packet Drop sensor error resolved."
	::= { netBotzPacketDropSensorTraps 0 101 }

netBotzSNMPCrawlerTooHigh NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"SNMP Crawler sensor value too high."
	::= { netBotzSNMPCrawlerSensorTraps 0 2 }

netBotzSNMPCrawlerTooHighRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"SNMP Crawler sensor value is no longer too high."
	::= { netBotzSNMPCrawlerSensorTraps 0 102 }

netBotzSNMPCrawlerTooLow NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"SNMP Crawler sensor value too low."
	::= { netBotzSNMPCrawlerSensorTraps 0 3 }

netBotzSNMPCrawlerTooLowRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"SNMP Crawler sensor value is no longer too low."
	::= { netBotzSNMPCrawlerSensorTraps 0 103 }

netBotzSNMPCrawlerTooHighTooLong NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"SNMP Crawler sensor value too high for too long."
	::= { netBotzSNMPCrawlerSensorTraps 0 4 }

netBotzSNMPCrawlerTooHighTooLongRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"SNMP Crawler sensor value is no longer too high for too long."
	::= { netBotzSNMPCrawlerSensorTraps 0 104 }

netBotzSNMPCrawlerTooLowTooLong NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"SNMP Crawler ensor value too low for too long."
	::= { netBotzSNMPCrawlerSensorTraps 0 5 }

netBotzSNMPCrawlerTooLowForTooLongRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"SNMP Crawler sensor value is no longer too low for too long."
	::= { netBotzSNMPCrawlerSensorTraps 0 105 }

netBotzSNMPCrawlerUnplugged NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"SNMP Crawler sensor unplugged."
	::= { netBotzSNMPCrawlerSensorTraps 0 6 }

netBotzSNMPCrawlerReplugged NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"SNMP Crawler sensor no longer unplugged."
	::= { netBotzSNMPCrawlerSensorTraps 0 106 }

netBotzSNMPCrawlerIncreasingTooQuickly NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"SNMP Crawler sensor value increasing too quickly."
	::= { netBotzSNMPCrawlerSensorTraps 0 8 }

netBotzSNMPCrawlerNotIncreasingTooQuickly NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"SNMP Crawler sensor value no longer increasing too quickly."
	::= { netBotzSNMPCrawlerSensorTraps 0 108 }

netBotzSNMPCrawlerDecreasingTooQuickly NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"SNMP Crawler sensor value decreasing too quickly."
	::= { netBotzSNMPCrawlerSensorTraps 0 9 }

netBotzSNMPCrawlerNotDecreasingTooQuickly NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"SNMP Crawler sensor value no longer decreasing too quickly."
	::= { netBotzSNMPCrawlerSensorTraps 0 109 }

netBotzSNMPCrawlerError NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"SNMP Crawler sensor error."
	::= { netBotzSNMPCrawlerSensorTraps 0 1 }

netBotzSNMPCrawlerErrorRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"SNMP Crawler sensor error resolved."
	::= { netBotzSNMPCrawlerSensorTraps 0 101 }

netBotzSNMPCrawlerSensorValueError NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"SNMP Crawler Sensor sensor value error."
	::= { netBotzSNMPCrawlerSensorTraps 0 10 }

netBotzSNMPCrawlerSensorValueErrorRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"SNMP Crawler Sensor sensor value error resolved."
	::= { netBotzSNMPCrawlerSensorTraps 0 110 }

netBotzGPSStatusSensorUnplugged NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Status Sensor sensor unplugged."
	::= { netBotzGPSStatusSensorTraps 0 6 }

netBotzGPSStatusSensorReplugged NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Status Sensor sensor no longer unplugged."
	::= { netBotzGPSStatusSensorTraps 0 106 }

netBotzGPSStatusSensorError NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Status Sensor sensor error."
	::= { netBotzGPSStatusSensorTraps 0 1 }

netBotzGPSStatusSensorErrorRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Status Sensor sensor error resolved."
	::= { netBotzGPSStatusSensorTraps 0 101 }

netBotzGPSStatusSensorValueError NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Status Sensor sensor value error."
	::= { netBotzGPSStatusSensorTraps 0 10 }

netBotzGPSStatusSensorValueErrorRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"GPS Status Sensor sensor value error resolved."
	::= { netBotzGPSStatusSensorTraps 0 110 }

netBotzWirelessStatusSensorUnplugged NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Wireless Status Sensor sensor unplugged."
	::= { netBotzWirelessStatusSensorTraps 0 6 }

netBotzWirelessStatusSensorReplugged NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Wireless Status Sensor sensor no longer unplugged."
	::= { netBotzWirelessStatusSensorTraps 0 106 }

netBotzWirelessStatusSensorError NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Wireless Status Sensor sensor error."
	::= { netBotzWirelessStatusSensorTraps 0 1 }

netBotzWirelessStatusSensorErrorRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Wireless Status Sensor sensor error resolved."
	::= { netBotzWirelessStatusSensorTraps 0 101 }

netBotzWirelessStatusSensorValueError NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Wireless Status Sensor sensor value error."
	::= { netBotzWirelessStatusSensorTraps 0 10 }

netBotzWirelessStatusSensorValueErrorRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Wireless Status Sensor sensor value error resolved."
	::= { netBotzWirelessStatusSensorTraps 0 110 }

netBotzPlugModuleStatusSensorUnplugged NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Power Control plug module unplugged."
	::= { netBotzPlugModuleStatusSensorTraps 0 6 }

netBotzPlugModuleStatusSensorReplugged NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Power Control plug module no longer unplugged."
	::= { netBotzPlugModuleStatusSensorTraps 0 106 }

netBotzPlugModuleStatusSensorError NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Power Control plug module error."
	::= { netBotzPlugModuleStatusSensorTraps 0 1 }

netBotzPlugModuleStatusSensorErrorRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Power Control plug module error resolved."
	::= { netBotzPlugModuleStatusSensorTraps 0 101 }

netBotzPlugModuleStatusSensorValueError NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Power Control plug module value error."
	::= { netBotzPlugModuleStatusSensorTraps 0 10 }

netBotzPlugModuleStatusSensorValueErrorRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Power Control plug module value error resolved."
	::= { netBotzPlugModuleStatusSensorTraps 0 110 }

netBotzOutputControlSensorUnplugged NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Output Control Sensor unplugged."
	::= { netBotzOutputControlSensorTraps 0 6 }

netBotzOutputControlSensorReplugged NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Output Control Sensor no longer unplugged."
	::= { netBotzOutputControlSensorTraps 0 106 }

netBotzOutputControlSensorError NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Output Control Sensor error."
	::= { netBotzOutputControlSensorTraps 0 1 }

netBotzOutputControlSensorErrorRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Output Control Sensor error resolved."
	::= { netBotzOutputControlSensorTraps 0 101 }

netBotzOutputControlSensorValueError NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Output Control Sensor value error."
	::= { netBotzOutputControlSensorTraps 0 10 }

netBotzOutputControlSensorValueErrorRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Output Control Sensor value error resolved."
	::= { netBotzOutputControlSensorTraps 0 110 }


netBotzMultiRAESensorTooHigh NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"MultiRAE sensor value too high."
	::= { netBotzMultiRAESensorTraps 0 2 }

netBotzMultiRAESensorTooHighRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"MultiRAE sensor value is no longer too high."
	::= { netBotzMultiRAESensorTraps 0 102 }

netBotzMultiRAESensorTooLow NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"MultiRAE sensor value too low."
	::= { netBotzMultiRAESensorTraps 0 3 }

netBotzMultiRAESensorTooLowRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"MultiRAE sensor value is no longer too low."
	::= { netBotzMultiRAESensorTraps 0 103 }

netBotzMultiRAESensorTooHighTooLong NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"MultiRAE sensor value too high for too long."
	::= { netBotzMultiRAESensorTraps 0 4 }

netBotzMultiRAESensorTooHighTooLongRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"MultiRAE sensor value is no longer too high for too long."
	::= { netBotzMultiRAESensorTraps 0 104 }

netBotzMultiRAESensorTooLowTooLong NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"MultiRAE ensor value too low for too long."
	::= { netBotzMultiRAESensorTraps 0 5 }

netBotzMultiRAESensorTooLowForTooLongRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"MultiRAE sensor value is no longer too low for too long."
	::= { netBotzMultiRAESensorTraps 0 105 }

netBotzMultiRAESensorUnplugged NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"MultiRAE sensor unplugged."
	::= { netBotzMultiRAESensorTraps 0 6 }

netBotzMultiRAESensorReplugged NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"MultiRAE sensor no longer unplugged."
	::= { netBotzMultiRAESensorTraps 0 106 }

netBotzMultiRAESensorIncreasingTooQuickly NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"MultiRAE sensor value increasing too quickly."
	::= { netBotzMultiRAESensorTraps 0 8 }

netBotzMultiRAESensorNotIncreasingTooQuickly NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"MultiRAE sensor value no longer increasing too quickly."
	::= { netBotzMultiRAESensorTraps 0 108 }

netBotzMultiRAESensorDecreasingTooQuickly NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"MultiRAE sensor value decreasing too quickly."
	::= { netBotzMultiRAESensorTraps 0 9 }

netBotzMultiRAESensorNotDecreasingTooQuickly NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"MultiRAE sensor value no longer decreasing too quickly."
	::= { netBotzMultiRAESensorTraps 0 109 }

netBotzMultiRAESensorError NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"MultiRAE sensor error."
	::= { netBotzMultiRAESensorTraps 0 1 }

netBotzMultiRAESensorErrorRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"MultiRAE sensor error resolved."
	::= { netBotzMultiRAESensorTraps 0 101 }

netBotzMultiRAESensorSensorValueError NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"MultiRAE Sensor sensor value error."
	::= { netBotzMultiRAESensorTraps 0 10 }

netBotzMultiRAESensorSensorValueErrorRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"MultiRAE Sensor sensor value error resolved."
	::= { netBotzMultiRAESensorTraps 0 110 }
		

netBotzMultiRAESensorStatusUnplugged NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"MultiRAE Sensor Status unplugged."
	::= { netBotzMultiRAESensorStatusTraps 0 6 }

netBotzMultiRAESensorStatusReplugged NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"MultiRAE Sensor Status no longer unplugged."
	::= { netBotzMultiRAESensorStatusTraps 0 106 }

netBotzMultiRAESensorStatusError NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"MultiRAE Sensor Status error."
	::= { netBotzMultiRAESensorStatusTraps 0 1 }

netBotzMultiRAESensorStatusErrorRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"MultiRAE Sensor Status error resolved."
	::= { netBotzMultiRAESensorStatusTraps 0 101 }

netBotzMultiRAESensorStatusValueError NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"MultiRAE Sensor Status value error."
	::= { netBotzMultiRAESensorStatusTraps 0 10 }

netBotzMultiRAESensorStatusValueErrorRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"MultiRAE Sensor Status value error resolved."
	::= { netBotzMultiRAESensorStatusTraps 0 110 }


netBotzMultiRAEDeviceStatusUnplugged NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"MultiRAE Device Status unplugged."
	::= { netBotzMultiRAEDeviceStatusTraps 0 6 }

netBotzMultiRAEDeviceStatusReplugged NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"MultiRAE Device Status no longer unplugged."
	::= { netBotzMultiRAEDeviceStatusTraps 0 106 }

netBotzMultiRAEDeviceStatusError NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"MultiRAE Device Status error."
	::= { netBotzMultiRAEDeviceStatusTraps 0 1 }

netBotzMultiRAEDeviceStatusErrorRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"MultiRAE Device Status error resolved."
	::= { netBotzMultiRAEDeviceStatusTraps 0 101 }

netBotzMultiRAEDeviceStatusValueError NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"MultiRAE Device Status value error."
	::= { netBotzMultiRAEDeviceStatusTraps 0 10 }

netBotzMultiRAEDeviceStatusValueErrorRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"MultiRAE Device Status value error resolved."
	::= { netBotzMultiRAEDeviceStatusTraps 0 110 }

netBotzLinkStatusSensorUnplugged NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Link Status sensor unplugged."
	::= { netBotzLinkStatusSensorTraps 0 6 }

netBotzLinkStatusSensorReplugged NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Link Status sensor no longer unplugged."
	::= { netBotzLinkStatusSensorTraps 0 106 }

netBotzLinkStatusSensorError NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Link Status sensor error."
	::= { netBotzLinkStatusSensorTraps 0 1 }

netBotzLinkStatusSensorErrorRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Link Status sensor error resolved."
	::= { netBotzLinkStatusSensorTraps 0 101 }

netBotzLinkStatusSensorValueError NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Link Status sensor value error."
	::= { netBotzLinkStatusSensorTraps 0 10 }

netBotzLinkStatusSensorValueErrorRTN NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Link Status sensor value error resolved."
	::= { netBotzLinkStatusSensorTraps 0 110 }

netBotzLoopVoltageTooHigh NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Loop Voltage sensor value too high."
	::= { netBotzLoopVoltageSensorTraps 0 2 }

netBotzLoopVoltageTooHighRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Loop Voltage sensor value is no longer too high."
	::= { netBotzLoopVoltageSensorTraps 0 102 }

netBotzLoopVoltageTooLow NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Loop Voltage sensor value too low."
	::= { netBotzLoopVoltageSensorTraps 0 3 }

netBotzLoopVoltageTooLowRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Loop Voltage sensor value is no longer too low."
	::= { netBotzLoopVoltageSensorTraps 0 103 }

netBotzLoopVoltageTooHighTooLong NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Loop Voltage sensor value too high for too long."
	::= { netBotzLoopVoltageSensorTraps 0 4 }

netBotzLoopVoltageTooHighTooLongRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Loop Voltage sensor value is no longer too high for too long."
	::= { netBotzLoopVoltageSensorTraps 0 104 }

netBotzLoopVoltageTooLowTooLong NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Loop Voltage sensor value too low for too long."
	::= { netBotzLoopVoltageSensorTraps 0 5 }

netBotzLoopVoltageTooLowForTooLongRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Loop Voltage sensor value is no longer too low for too long."
	::= { netBotzLoopVoltageSensorTraps 0 105 }

netBotzLoopVoltageUnplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Loop Voltage sensor unplugged."
	::= { netBotzLoopVoltageSensorTraps 0 6 }

netBotzLoopVoltageReplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Loop Voltage sensor no longer unplugged."
	::= { netBotzLoopVoltageSensorTraps 0 106 }

netBotzLoopVoltageIncreasingTooQuickly NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Loop Voltage sensor value increasing too quickly."
	::= { netBotzLoopVoltageSensorTraps 0 8 }

netBotzLoopVoltageNotIncreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Loop Voltage sensor value no longer increasing too quickly."
	::= { netBotzLoopVoltageSensorTraps 0 108 }

netBotzLoopVoltageDecreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Loop Voltage sensor value decreasing too quickly."
	::= { netBotzLoopVoltageSensorTraps 0 9 }

netBotzLoopVoltageNotDecreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Loop Voltage sensor value no longer decreasing too quickly."
	::= { netBotzLoopVoltageSensorTraps 0 109 }

netBotzLoopVoltageError NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Loop Voltage sensor error."
	::= { netBotzLoopVoltageSensorTraps 0 1 }

netBotzLoopVoltageErrorRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Loop Voltage sensor error resolved."
	::= { netBotzLoopVoltageSensorTraps 0 101 }

netBotzVoltageTooHigh NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Voltage sensor value too high."
	::= { netBotzVoltageSensorTraps 0 2 }

netBotzVoltageTooHighRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Voltage sensor value is no longer too high."
	::= { netBotzVoltageSensorTraps 0 102 }

netBotzVoltageTooLow NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Voltage sensor value too low."
	::= { netBotzVoltageSensorTraps 0 3 }

netBotzVoltageTooLowRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Voltage sensor value is no longer too low."
	::= { netBotzVoltageSensorTraps 0 103 }

netBotzVoltageTooHighTooLong NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Voltage sensor value too high for too long."
	::= { netBotzVoltageSensorTraps 0 4 }

netBotzVoltageTooHighTooLongRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Voltage sensor value is no longer too high for too long."
	::= { netBotzVoltageSensorTraps 0 104 }

netBotzVoltageTooLowTooLong NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Voltage sensor value too low for too long."
	::= { netBotzVoltageSensorTraps 0 5 }

netBotzVoltageTooLowForTooLongRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Voltage sensor value is no longer too low for too long."
	::= { netBotzVoltageSensorTraps 0 105 }

netBotzVoltageUnplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Voltage sensor unplugged."
	::= { netBotzVoltageSensorTraps 0 6 }

netBotzVoltageReplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Voltage sensor no longer unplugged."
	::= { netBotzVoltageSensorTraps 0 106 }

netBotzVoltageIncreasingTooQuickly NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Voltage sensor value increasing too quickly."
	::= { netBotzVoltageSensorTraps 0 8 }

netBotzVoltageNotIncreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Voltage sensor value no longer increasing too quickly."
	::= { netBotzVoltageSensorTraps 0 108 }

netBotzVoltageDecreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Voltage sensor value decreasing too quickly."
	::= { netBotzVoltageSensorTraps 0 9 }

netBotzVoltageNotDecreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Voltage sensor value no longer decreasing too quickly."
	::= { netBotzVoltageSensorTraps 0 109 }

netBotzVoltageError NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Voltage sensor error."
	::= { netBotzVoltageSensorTraps 0 1 }

netBotzVoltageErrorRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Voltage sensor error resolved."
	::= { netBotzVoltageSensorTraps 0 101 }
    
netBotzFanSpeedTooHigh NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Fan Speed sensor value too high."
	::= { netBotzFanSpeedSensorTraps 0 2 }

netBotzFanSpeedTooHighRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Fan Speed sensor value is no longer too high."
	::= { netBotzFanSpeedSensorTraps 0 102 }

netBotzFanSpeedTooLow NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Fan Speed sensor value too low."
	::= { netBotzFanSpeedSensorTraps 0 3 }

netBotzFanSpeedTooLowRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Fan Speed sensor value is no longer too low."
	::= { netBotzFanSpeedSensorTraps 0 103 }

netBotzFanSpeedTooHighTooLong NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Fan Speed sensor value too high for too long."
	::= { netBotzFanSpeedSensorTraps 0 4 }

netBotzFanSpeedTooHighTooLongRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Fan Speed sensor value is no longer too high for too long."
	::= { netBotzFanSpeedSensorTraps 0 104 }

netBotzFanSpeedTooLowTooLong NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Fan Speed sensor value too low for too long."
	::= { netBotzFanSpeedSensorTraps 0 5 }

netBotzFanSpeedTooLowForTooLongRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Fan Speed sensor value is no longer too low for too long."
	::= { netBotzFanSpeedSensorTraps 0 105 }

netBotzFanSpeedUnplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Fan Speed sensor unplugged."
	::= { netBotzFanSpeedSensorTraps 0 6 }

netBotzFanSpeedReplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Fan Speed sensor no longer unplugged."
	::= { netBotzFanSpeedSensorTraps 0 106 }

netBotzFanSpeedIncreasingTooQuickly NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Fan Speed sensor value increasing too quickly."
	::= { netBotzFanSpeedSensorTraps 0 8 }

netBotzFanSpeedNotIncreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Fan Speed sensor value no longer increasing too quickly."
	::= { netBotzFanSpeedSensorTraps 0 108 }

netBotzFanSpeedDecreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Fan Speed sensor value decreasing too quickly."
	::= { netBotzFanSpeedSensorTraps 0 9 }

netBotzFanSpeedNotDecreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Fan Speed sensor value no longer decreasing too quickly."
	::= { netBotzFanSpeedSensorTraps 0 109 }

netBotzFanSpeedError NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Fan Speed sensor error."
	::= { netBotzFanSpeedSensorTraps 0 1 }

netBotzFanSpeedErrorRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Fan Speed sensor error resolved."
	::= { netBotzFanSpeedSensorTraps 0 101 }

netBotzAppPowerTooHigh NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"App Power sensor value too high."
	::= { netBotzAppPowerSensorTraps 0 2 }

netBotzAppPowerTooHighRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"App Power sensor value is no longer too high."
	::= { netBotzAppPowerSensorTraps 0 102 }

netBotzAppPowerTooLow NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"App Power sensor value too low."
	::= { netBotzAppPowerSensorTraps 0 3 }

netBotzAppPowerTooLowRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"App Power sensor value is no longer too low."
	::= { netBotzAppPowerSensorTraps 0 103 }

netBotzAppPowerTooHighTooLong NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"App Power sensor value too high for too long."
	::= { netBotzAppPowerSensorTraps 0 4 }

netBotzAppPowerTooHighTooLongRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"App Power sensor value is no longer too high for too long."
	::= { netBotzAppPowerSensorTraps 0 104 }

netBotzAppPowerTooLowTooLong NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"App Power sensor value too low for too long."
	::= { netBotzAppPowerSensorTraps 0 5 }

netBotzAppPowerTooLowForTooLongRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"App Power sensor value is no longer too low for too long."
	::= { netBotzAppPowerSensorTraps 0 105 }

netBotzAppPowerUnplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"App Power sensor unplugged."
	::= { netBotzAppPowerSensorTraps 0 6 }

netBotzAppPowerReplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"App Power sensor no longer unplugged."
	::= { netBotzAppPowerSensorTraps 0 106 }

netBotzAppPowerIncreasingTooQuickly NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"App Power sensor value increasing too quickly."
	::= { netBotzAppPowerSensorTraps 0 8 }

netBotzAppPowerNotIncreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"App Power sensor value no longer increasing too quickly."
	::= { netBotzAppPowerSensorTraps 0 108 }

netBotzAppPowerDecreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"App Power sensor value decreasing too quickly."
	::= { netBotzAppPowerSensorTraps 0 9 }

netBotzAppPowerNotDecreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"App Power sensor value no longer decreasing too quickly."
	::= { netBotzAppPowerSensorTraps 0 109 }

netBotzAppPowerError NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"App Power sensor error."
	::= { netBotzAppPowerSensorTraps 0 1 }

netBotzAppPowerErrorRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"App Power sensor error resolved."
	::= { netBotzAppPowerSensorTraps 0 101 }

netBotzPowerFactorTooHigh NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Power Factor sensor value too high."
	::= { netBotzPowerFactorSensorTraps 0 2 }

netBotzPowerFactorTooHighRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Power Factor sensor value is no longer too high."
	::= { netBotzPowerFactorSensorTraps 0 102 }

netBotzPowerFactorTooLow NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Power Factor sensor value too low."
	::= { netBotzPowerFactorSensorTraps 0 3 }

netBotzPowerFactorTooLowRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Power Factor sensor value is no longer too low."
	::= { netBotzPowerFactorSensorTraps 0 103 }

netBotzPowerFactorTooHighTooLong NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Power Factor sensor value too high for too long."
	::= { netBotzPowerFactorSensorTraps 0 4 }

netBotzPowerFactorTooHighTooLongRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Power Factor sensor value is no longer too high for too long."
	::= { netBotzPowerFactorSensorTraps 0 104 }

netBotzPowerFactorTooLowTooLong NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Power Factor sensor value too low for too long."
	::= { netBotzPowerFactorSensorTraps 0 5 }

netBotzPowerFactorTooLowForTooLongRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Power Factor sensor value is no longer too low for too long."
	::= { netBotzPowerFactorSensorTraps 0 105 }

netBotzPowerFactorUnplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Power Factor sensor unplugged."
	::= { netBotzPowerFactorSensorTraps 0 6 }

netBotzPowerFactorReplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Power Factor sensor no longer unplugged."
	::= { netBotzPowerFactorSensorTraps 0 106 }

netBotzPowerFactorIncreasingTooQuickly NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Power Factor sensor value increasing too quickly."
	::= { netBotzPowerFactorSensorTraps 0 8 }

netBotzPowerFactorNotIncreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Power Factor sensor value no longer increasing too quickly."
	::= { netBotzPowerFactorSensorTraps 0 108 }

netBotzPowerFactorDecreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Power Factor sensor value decreasing too quickly."
	::= { netBotzPowerFactorSensorTraps 0 9 }

netBotzPowerFactorNotDecreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Power Factor sensor value no longer decreasing too quickly."
	::= { netBotzPowerFactorSensorTraps 0 109 }

netBotzPowerFactorError NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Power Factor sensor error."
	::= { netBotzPowerFactorSensorTraps 0 1 }

netBotzPowerFactorErrorRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Power Factor sensor error resolved."
	::= { netBotzPowerFactorSensorTraps 0 101 }

netBotzTimeSensorTooHigh NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Time sensor value too high."
	::= { netBotzTimeSensorTraps 0 2 }

netBotzTimeSensorTooHighRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Time sensor value is no longer too high."
	::= { netBotzTimeSensorTraps 0 102 }

netBotzTimeSensorTooLow NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Time sensor value too low."
	::= { netBotzTimeSensorTraps 0 3 }

netBotzTimeSensorTooLowRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Time sensor value is no longer too low."
	::= { netBotzTimeSensorTraps 0 103 }

netBotzTimeSensorTooHighTooLong NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Time sensor value too high for too long."
	::= { netBotzTimeSensorTraps 0 4 }

netBotzTimeSensorTooHighTooLongRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Time sensor value is no longer too high for too long."
	::= { netBotzTimeSensorTraps 0 104 }

netBotzTimeSensorTooLowTooLong NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Time sensor value too low for too long."
	::= { netBotzTimeSensorTraps 0 5 }

netBotzTimeSensorTooLowForTooLongRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Time sensor value is no longer too low for too long."
	::= { netBotzTimeSensorTraps 0 105 }

netBotzTimeSensorUnplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Time sensor unplugged."
	::= { netBotzTimeSensorTraps 0 6 }

netBotzTimeSensorReplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Time sensor no longer unplugged."
	::= { netBotzTimeSensorTraps 0 106 }
    
netBotzTimeSensorIncreasingTooQuickly NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Time sensor value increasing too quickly."
	::= { netBotzTimeSensorTraps 0 8 }

netBotzTimeSensorNotIncreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Time sensor value no longer increasing too quickly."
	::= { netBotzTimeSensorTraps 0 108 }

netBotzTimeSensorDecreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Time sensor value decreasing too quickly."
	::= { netBotzTimeSensorTraps 0 9 }

netBotzTimeSensorNotDecreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Time sensor value no longer decreasing too quickly."
	::= { netBotzTimeSensorTraps 0 109 }

netBotzTimeSensorError NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Time sensor error."
	::= { netBotzTimeSensorTraps 0 1 }

netBotzTimeSensorErrorRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Time sensor error resolved."
	::= { netBotzTimeSensorTraps 0 101 }
    
netBotzPowerWattsSensorTooHigh NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Power Watts sensor value too high."
	::= { netBotzPowerWattsSensorTraps 0 2 }

netBotzPowerWattsSensorTooHighRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Power Watts sensor value is no longer too high."
	::= { netBotzPowerWattsSensorTraps 0 102 }

netBotzPowerWattsSensorTooLow NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Power Watts sensor value too low."
	::= { netBotzPowerWattsSensorTraps 0 3 }

netBotzPowerWattsSensorTooLowRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Power Watts sensor value is no longer too low."
	::= { netBotzPowerWattsSensorTraps 0 103 }

netBotzPowerWattsSensorTooHighTooLong NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Power Watts sensor value too high for too long."
	::= { netBotzPowerWattsSensorTraps 0 4 }

netBotzPowerWattsSensorTooHighTooLongRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Power Watts sensor value is no longer too high for too long."
	::= { netBotzPowerWattsSensorTraps 0 104 }

netBotzPowerWattsSensorTooLowTooLong NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Power Watts sensor value too low for too long."
	::= { netBotzPowerWattsSensorTraps 0 5 }

netBotzPowerWattsSensorTooLowForTooLongRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Power Watts sensor value is no longer too low for too long."
	::= { netBotzPowerWattsSensorTraps 0 105 }

netBotzPowerWattsSensorUnplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Power Watts sensor unplugged."
	::= { netBotzPowerWattsSensorTraps 0 6 }

netBotzPowerWattsSensorReplugged NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Power Watts sensor no longer unplugged."
	::= { netBotzPowerWattsSensorTraps 0 106 }
    
netBotzPowerWattsSensorIncreasingTooQuickly NOTIFICATION-TYPE
	OBJECTS {
		netBotzTrapErrorID,
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Power Watts sensor value increasing too quickly."
	::= { netBotzPowerWattsSensorTraps 0 8 }

netBotzPowerWattsSensorNotIncreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Power Watts sensor value no longer increasing too quickly."
	::= { netBotzPowerWattsSensorTraps 0 108 }

netBotzPowerWattsSensorDecreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Power Watts sensor value decreasing too quickly."
	::= { netBotzPowerWattsSensorTraps 0 9 }

netBotzPowerWattsSensorNotDecreasingTooQuickly NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION
	"Power Watts sensor value no longer decreasing too quickly."
	::= { netBotzPowerWattsSensorTraps 0 109 }

netBotzPowerWattsSensorError NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Power Watts sensor error."
	::= { netBotzPowerWattsSensorTraps 0 1 }

netBotzPowerWattsSensorErrorRTN NOTIFICATION-TYPE
	OBJECTS {
		netBotzTrapErrorID,	
		netBotzTrapErrorType,
		netBotzTrapErrorTypeLabel,
		netBotzTrapSensorID,
		netBotzTrapSensorLabel,
		netBotzTrapPodID,
		netBotzTrapPodLabel,
		netBotzTrapPortID,
		netBotzTrapPortLabel,
		netBotzTrapStartTime,
		netBotzTrapNotifyTime,
		netBotzTrapResolveTime,
		netBotzTrapSeverity,
		netBotzTrapSensorValue,
		netBotzTrapSensorValueInt,
		netBotzTrapSensorValueFraction
		}
	STATUS		current
	DESCRIPTION 
	"Power Watts sensor error resolved."
	::= { netBotzPowerWattsSensorTraps 0 101 }
    
END

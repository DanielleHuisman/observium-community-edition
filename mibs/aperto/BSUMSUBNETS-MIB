BSUMSUBNETS-MIB DEFINITIONS ::= BEGIN

	IMPORTS
		IpAddress
			FROM RFC1155-SMI
		OBJECT-TYPE, MODULE-IDENTITY
			FROM SNMPv2-SMI
		aniBsuWirelessPort
			FROM BSUWIRELESSIF-MIB
		bsu
			FROM ANIROOT-MIB;

aniBsuMultSubnets  MODULE-IDENTITY
	LAST-UPDATED "0105091130Z"      -- Wed May 9 11:30:00 PDT 2001
	ORGANIZATION "Aperto Networks"
	CONTACT-INFO
	  "       
	  Postal:  Aperto Networks Inc
		   1637 S Main Street 
		   Milpitas, California 95035
	  Tel:	   +1 408 719 9977
	  "       
	DESCRIPTION
	   "This group gives the BSU Multiple Subnets information. 
	    
	    The aniBsuSubnetConfTable is used to view and configure
	    subnets per wireless port.

	    There can be upto 1024 <Ip Address/Subnet Mask> pairs.
	    For a given WSS port, there can be multiple and different 
	    subnets. This means that each subnet specified by an
	    <Ip Address masked by the Subnet Mask> has to be distinct.
	    Atleast one Ip Address and Subnet Mask has to be specified.
	    In addition to the subnet being distinct, each IP Address 
	    must be unique too.

	    If clustering is disabled, then Multiple Subnets on one
	    WSS port should not clash with Multiple Subnets on any
	    other WSS port.
	     
	    Clustering and multiple subnets can exists simultaneously 
	    as long as they are not on the same WSS. If clustering is 
	    enabled but not all WSS are clustered, then those that are 
	    not part of the cluster can have multiple subnets. 
	    Eg. If WSS1 and WSS2 are clustered, but WSS3 and WSS4 are 
	    not, then WSS3 and WSS4 can have multiple subnets.

	    To add a new subnet to the table, first set the 
	    aniBsuSubnetConfAddr. Next send an SNMP set request
	    on aniBsuSubnetConfMask.

	    Currently, deletion and modification of entries is not supported.

	    When the BSU is in Bridge mode, this multiple subnets table is 
	    not valid and will not be displayed.
	   "
	::= { bsu 6 }


-- The BSU Multiple Subnets Configuration Group

aniBsuSubnetConfTable OBJECT-TYPE
	SYNTAX  SEQUENCE OF AniBsuSubnetConfEntry
	MAX-ACCESS  not-accessible
	STATUS      current
	DESCRIPTION
	   "This table contains the Multiple Subnets information per
	    wireless port.
	   "
	::= { aniBsuMultSubnets 1 }

aniBsuSubnetConfEntry OBJECT-TYPE
	SYNTAX  AniBsuSubnetConfEntry
	MAX-ACCESS  not-accessible
	STATUS      current
	DESCRIPTION
	   "An entry in the aniBsuSubnetConfTable.
	   "
	INDEX   { aniBsuWirelessPort, aniBsuSubnetConfAddr }
	::= { aniBsuSubnetConfTable 1 }

AniBsuSubnetConfEntry ::=
		SEQUENCE {
			aniBsuSubnetConfAddr 	
				IpAddress,
			aniBsuSubnetConfMask 	
				IpAddress
		}

aniBsuSubnetConfAddr OBJECT-TYPE
	SYNTAX  IpAddress
	MAX-ACCESS  read-create
	STATUS      current
	DESCRIPTION
	   "The IP Address of the configured Subnet.
	   "
	::= { aniBsuSubnetConfEntry 1 }

aniBsuSubnetConfMask OBJECT-TYPE
	SYNTAX  IpAddress
	MAX-ACCESS  read-create
	STATUS      current
	DESCRIPTION
	   "The Subnet Mask.
	   "
	::= { aniBsuSubnetConfEntry 2 }

END

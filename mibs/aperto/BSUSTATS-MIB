BSUSTATS-MIB DEFINITIONS ::= BEGIN

	IMPORTS
		OBJECT-TYPE, MODULE-IDENTITY, Integer32, Counter32
			FROM SNMPv2-SMI
		DisplayString, TruthValue
			FROM SNMPv2-TC
		aniBsuWirelessPort
			FROM BSUWIRELESSIF-MIB
		bsu
			FROM ANIROOT-MIB;

		-- the BSU Statistics Group
			-- BSU RF Port Level Statistics 

aniBsuStatistics  MODULE-IDENTITY
	LAST-UPDATED "0105091130Z"      -- Wed May 9 11:30:00 PDT 2001
	ORGANIZATION "Aperto Networks"
	CONTACT-INFO
	  "       
	  Postal:  Aperto Networks Inc
		   1637 S Main Street 
		   Milpitas, California 95035
	  Tel:	   +1 408 719 9977
	  "       
	DESCRIPTION
	   "This group contains Statistical information for the BSU. 

	    aniBsuRfStatsTable shows the RF Port level statistics.

	    aniBsuStatsBWGroup shows the bandwidth allocation statistics.

	    aniBsuRfSigQStatsTable shows the Signal Quality Port level statistics.
	   " 
	::= { bsu 3 }


aniBsuStatsGrp OBJECT IDENTIFIER
	::= { aniBsuStatistics 1 }


        -- BSU RF Port Level Statistics Group

aniBsuRfStatsTable OBJECT-TYPE
	SYNTAX      SEQUENCE OF AniBsuRfStatsEntry
	MAX-ACCESS  not-accessible
	STATUS      current
	DESCRIPTION
	   "This table provides the statistics information for the BSU Wireless ports.
	   "
	::= { aniBsuStatistics 2 }

aniBsuRfStatsEntry OBJECT-TYPE
	SYNTAX      AniBsuRfStatsEntry
	MAX-ACCESS  not-accessible
	STATUS      current
	DESCRIPTION
	   "An entry with objects that provide statistics information 
	    for each RF port monitored by the BSU.
	   "
	INDEX { aniBsuWirelessPort }
	::= { aniBsuRfStatsTable 1 }

AniBsuRfStatsEntry ::= SEQUENCE {
	aniBsuRfStatsInPackets		Counter32,
	aniBsuRfStatsOutPackets		Counter32,
	aniBsuRfStatsInOctets	 	Counter32,
	aniBsuRfStatsOutOctets		Counter32,
	aniBsuRfStatsNumSusLinked	Integer32
	}

aniBsuRfStatsInPackets OBJECT-TYPE
	SYNTAX      Counter32
	MAX-ACCESS  read-only
	STATUS      current
	DESCRIPTION
	   "This object counts total number of packets received through
	    the Wireless port as identified by aniBsuWirelessPort.
	   "
	--DEFAULT next-function-async     aniBsuRfStatsEntry_next
	::= { aniBsuRfStatsEntry 1 }

aniBsuRfStatsOutPackets OBJECT-TYPE
	SYNTAX      Counter32
	MAX-ACCESS  read-only
	STATUS      current
	DESCRIPTION
	   "This object counts total number of packets transmitted through
	    the Wireless port as identified by aniBsuWirelessPort.
	   "
	--DEFAULT next-function-async     aniBsuRfStatsEntry_next
	::= { aniBsuRfStatsEntry 2 }

aniBsuRfStatsInOctets OBJECT-TYPE
	SYNTAX      Counter32
	MAX-ACCESS  read-only
	STATUS      current
	DESCRIPTION
	   "The cumulative number of Packet Data Octets received
             on this Wireless port.
	   "
	--DEFAULT next-function-async     aniBsuRfStatsEntry_next
        ::= { aniBsuRfStatsEntry 3 }

aniBsuRfStatsOutOctets OBJECT-TYPE
	SYNTAX      Counter32
	MAX-ACCESS  read-only
	STATUS      current
	DESCRIPTION
	   "The cumulative number of Packet Data Octets transmitted
             on this Wireless port.
	   "
	--DEFAULT next-function-async     aniBsuRfStatsEntry_next
        ::= { aniBsuRfStatsEntry 4 }

aniBsuRfStatsNumSusLinked OBJECT-TYPE
	SYNTAX      Integer32 (0..1024)
	MAX-ACCESS  read-only
	STATUS      current
	DESCRIPTION
	   "The number of SUs linked to this wireless port.
	   "
	::={ aniBsuRfStatsEntry 5 }

-- Bandwidth Statistics

aniBsuStatsBWGroup  OBJECT IDENTIFIER
	--DEFAULT next-function-async     std_next_async
	::= { aniBsuStatistics 3 }

aniBsuStatsBWTable OBJECT-TYPE
	SYNTAX      SEQUENCE OF AniBsuStatsBWEntry
	MAX-ACCESS  not-accessible
	STATUS      current
	DESCRIPTION
	   "This table shows the bandwidth allocation statistics
	    per wireless port for each service class.
	   "
	::= { aniBsuStatsBWGroup 1 }

aniBsuStatsBWEntry OBJECT-TYPE
	SYNTAX      AniBsuStatsBWEntry
	MAX-ACCESS  not-accessible
	STATUS      current
	DESCRIPTION
	   "The entries for aniBsuStatsBWTable.
	   "
	INDEX {  aniBsuWirelessPort, aniBsuStatsBWServiceClass }
	--DEFAULT get-function-async     aniBsuStatsBWEntry_get
	--DEFAULT next-function-async     aniBsuStatsBWEntry_next
	::= { aniBsuStatsBWTable 1 }

AniBsuStatsBWEntry ::= SEQUENCE {
	aniBsuStatsBWServiceClass	INTEGER,
	aniBsuStatsBWUSMaxAllocation	Counter32,
	aniBsuStatsBWUSMaxAllocPercent	Integer32,
	aniBsuStatsBWUSCurrAllocation	Counter32,
	aniBsuStatsBWUSSubscrPercent 	DisplayString,
	aniBsuStatsBWDSMaxAllocation	Counter32,
	aniBsuStatsBWDSMaxAllocPercent	Integer32,
	aniBsuStatsBWDSCurrAllocation	Counter32,
	aniBsuStatsBWDSSubscrPercent	DisplayString
	}

aniBsuStatsBWServiceClass OBJECT-TYPE 
	SYNTAX INTEGER {
			besteffort(1),
			cir(2),
			cbr(3)
	}
	MAX-ACCESS  read-only
	STATUS      current
	DESCRIPTION
	   "The service class name.
	   "
	::= { aniBsuStatsBWEntry 1 }

aniBsuStatsBWUSMaxAllocation OBJECT-TYPE
	SYNTAX      Counter32
	MAX-ACCESS  read-only
	STATUS      current
	DESCRIPTION
	   "The maximum upstream bandwidth allocation in 
	    bits per second.
	    This value is available on the configuration manager.
	   "
	::= { aniBsuStatsBWEntry 2 }

aniBsuStatsBWUSMaxAllocPercent OBJECT-TYPE
	SYNTAX      Integer32
	MAX-ACCESS  read-only
	STATUS      current
	DESCRIPTION
	   "The maximum upstream bandwidth allocation displayed 
	    as a percentage.
	   "
	::= { aniBsuStatsBWEntry 3 }

aniBsuStatsBWUSCurrAllocation OBJECT-TYPE
	SYNTAX      Counter32
	MAX-ACCESS  read-only
	STATUS      current
	DESCRIPTION
	   "The current upstream bandwidth allocation in 
	    bits per second. This value is the accumulation
	    of all the SUs upstream allocated bandwidth for
	    this service class on this wireless port.

	    This object is not applicable in case of best effort service 
	    class and is always displayed as 0.
	   "
	::= { aniBsuStatsBWEntry 4 }

aniBsuStatsBWUSSubscrPercent OBJECT-TYPE
	SYNTAX      DisplayString
	MAX-ACCESS  read-only
	STATUS      current
	DESCRIPTION
	   "The ratio of aniBsuStatsBWUSCurrAllocPercent and 
	    aniBsuStatsBWUSMaxAllocation displayed as a percentage.

	    aniBsuStatsBWUSSubscrPercent = 
	    (aniBsuStatsBWUSCurrAllocPercent/aniBsuStatsBWUSMaxAllocation)*100

	    This object is not applicable in case of best effort service 
	    class and a string 'not-applicable' is returned.
	   "
	::= { aniBsuStatsBWEntry 5 }

aniBsuStatsBWDSMaxAllocation OBJECT-TYPE
	SYNTAX      Counter32
	MAX-ACCESS  read-only
	STATUS      current
	DESCRIPTION
	   "The maximum downstream bandwidth allocation in 
	    bits per second.
	    This value is available on the configuration manager.
	   "
	::= { aniBsuStatsBWEntry 6 }

aniBsuStatsBWDSMaxAllocPercent OBJECT-TYPE
	SYNTAX      Integer32
	MAX-ACCESS  read-only
	STATUS      current
	DESCRIPTION
	   "The maximum downstream bandwidth allocation displayed 
	    as a percentage.
	   "
	::= { aniBsuStatsBWEntry 7 }

aniBsuStatsBWDSCurrAllocation OBJECT-TYPE
	SYNTAX      Counter32
	MAX-ACCESS  read-only
	STATUS      current
	DESCRIPTION
	   "The current downstream bandwidth allocation in 
	    bits per second. This value is the accumulation
	    of all the SUs downstream allocated bandwidth for
	    this service class on this wireless port.

	    This object is not applicable in case of best effort service 
	    class and is always displayed as 0.
	   "
	::= { aniBsuStatsBWEntry 8 }

aniBsuStatsBWDSSubscrPercent OBJECT-TYPE
	SYNTAX      DisplayString
	MAX-ACCESS  read-only
	STATUS      current
	DESCRIPTION
	   "The ratio of aniBsuStatsBWDSCurrAllocPercent and 
	    aniBsuStatsBWDSMaxAllocation displayed as a percentage.

	    aniBsuStatsBWDSSubscrPercent = 
	    (aniBsuStatsBWDSCurrAllocPercent/aniBsuStatsBWDSMaxAllocation)*100

	    This object is not applicable in case of best effort service 
	    class and a string 'not-applicable' is returned.
	   "
	::= { aniBsuStatsBWEntry 9 }

aniBsuStatsBWTotalTable OBJECT-TYPE
	SYNTAX      SEQUENCE OF AniBsuStatsBWTotalEntry
	MAX-ACCESS  not-accessible
	STATUS      current
	DESCRIPTION
	   "This table displays the total bandwidth allocation
	    for each wireless port.
	   "
	::= { aniBsuStatsBWGroup 2 }

aniBsuStatsBWTotalEntry OBJECT-TYPE
	SYNTAX      AniBsuStatsBWTotalEntry
	MAX-ACCESS  not-accessible
	STATUS      current
	DESCRIPTION
	   "The entries for aniBsuStatsBWTotalTable.
	   "
	INDEX {  aniBsuWirelessPort }
	--DEFAULT get-function-async     aniBsuStatsBWTotalEntry_get
	--DEFAULT next-function-async     aniBsuStatsBWTotalEntry_next
	::= { aniBsuStatsBWTotalTable 1 }

AniBsuStatsBWTotalEntry ::= SEQUENCE {
	aniBsuStatsBWTotalUSMaxAllocation	Counter32,
	aniBsuStatsBWTotalDSMaxAllocation	Counter32
	}

aniBsuStatsBWTotalUSMaxAllocation OBJECT-TYPE
	SYNTAX      Counter32
	MAX-ACCESS  read-only
	STATUS      current
	DESCRIPTION
	   "The total upstream maximum bandwidth allocations for this wireless port.
	    It includes bandwidth information of all the service classes
	    on this particular port.
	   "
	::= { aniBsuStatsBWTotalEntry 1 }

aniBsuStatsBWTotalDSMaxAllocation OBJECT-TYPE
	SYNTAX      Counter32
	MAX-ACCESS  read-only
	STATUS      current
	DESCRIPTION
	   "The total downstream maximum bandwidth allocations for this wireless port.
	    It includes bandwidth information of all the service classes
	    on this particular port.
	   "
	::= { aniBsuStatsBWTotalEntry 2 }


        -- BSU RF Port Signal Quality Statistics Group

aniBsuRfSigQStatsTable OBJECT-TYPE
	SYNTAX      SEQUENCE OF AniBsuRfSigQStatsEntry
	MAX-ACCESS  not-accessible
	STATUS      current
	DESCRIPTION
	   "This table provides the signal quality statistics information for 
	    the BSU Wireless ports.
	   "
	::= { aniBsuStatistics 4 }

aniBsuRfSigQStatsEntry OBJECT-TYPE
	SYNTAX      AniBsuRfSigQStatsEntry
	MAX-ACCESS  not-accessible
	STATUS      current
	DESCRIPTION
	   "An entry with objects that provide signal quality statistics information 
	    for each RF port monitored by the BSU.
	   "
	INDEX { aniBsuWirelessPort }
	--DEFAULT get-function-async     aniBsuRfSigQStatsEntry_get
	--DEFAULT next-function-async     aniBsuRfSigQStatsEntry_next
	::= { aniBsuRfSigQStatsTable 1 }

AniBsuRfSigQStatsEntry ::= SEQUENCE {
	aniBsuRfSigQStatsNoFecErrorCount	Counter32,
	aniBsuRfSigQStatsCorrFecErrorCount	Counter32,
	aniBsuRfSigQStatsUncorrFecErrorCount 	Counter32,
	aniBsuRfSigQStatsNoUniqueWordCount	Counter32,
	aniBsuRfSigQStatsCollidedBurstCount	Counter32,
	aniBsuRfSigQStatsNoEnergyCount		Counter32,
	aniBsuRfSigQStatsPayloadLenErrorCount	Counter32,
	aniBsuRfSigQStatsBurstErrorRate		DisplayString,
	aniBsuRfSigQStatsResetCounter		TruthValue
	}

aniBsuRfSigQStatsNoFecErrorCount OBJECT-TYPE
	SYNTAX      Counter32
	MAX-ACCESS  read-only
	STATUS      current
	DESCRIPTION
	   "The no FEC error count.
	   "
	::= { aniBsuRfSigQStatsEntry 1 }

aniBsuRfSigQStatsCorrFecErrorCount OBJECT-TYPE
	SYNTAX      Counter32
	MAX-ACCESS  read-only
	STATUS      current
	DESCRIPTION
	   "The correctable FEC error count.
	   "
	::= { aniBsuRfSigQStatsEntry 2 }

aniBsuRfSigQStatsUncorrFecErrorCount OBJECT-TYPE
	SYNTAX      Counter32
	MAX-ACCESS  read-only
	STATUS      current
	DESCRIPTION
	   "The uncorrectable FEC error count.
	   "
	::= { aniBsuRfSigQStatsEntry 3 }

aniBsuRfSigQStatsNoUniqueWordCount OBJECT-TYPE
	SYNTAX      Counter32
	MAX-ACCESS  read-only
	STATUS      current
	DESCRIPTION
	   "The no unique word count.
	   "
	::= { aniBsuRfSigQStatsEntry 4 }

aniBsuRfSigQStatsCollidedBurstCount OBJECT-TYPE
	SYNTAX      Counter32
	MAX-ACCESS  read-only
	STATUS      current
	DESCRIPTION
	   "The collided burst count.
	   "
	::= { aniBsuRfSigQStatsEntry 5 }

aniBsuRfSigQStatsNoEnergyCount OBJECT-TYPE
	SYNTAX      Counter32
	MAX-ACCESS  read-only
	STATUS      current
	DESCRIPTION
	   "The no energy count.
	   "
	::= { aniBsuRfSigQStatsEntry 6 }

aniBsuRfSigQStatsPayloadLenErrorCount OBJECT-TYPE
	SYNTAX      Counter32
	MAX-ACCESS  read-only
	STATUS      current
	DESCRIPTION
	   "The payload length error count.
	   "
	::= { aniBsuRfSigQStatsEntry 7 }

aniBsuRfSigQStatsBurstErrorRate OBJECT-TYPE
	SYNTAX      DisplayString
	MAX-ACCESS  read-only
	STATUS      current
	DESCRIPTION
	   "The burst error rate.
	    This percentage is calculated using the formula
	    Burst Error Rate = (Bad Bursts/(Good Bursts + Bad Bursts)) x 100
	    where 
	    Good Bursts = aniBsuRfSigQStatsNoFecErrorCount + 
			aniBsuRfSigQStatsCorrFecErrorCount
	    Bad Bursts = aniBsuRfSigQStatsCollidedBurstCount + 
		 aniBsuRfSigQStatsNoUniqueWordCount + aniBsuRfSigQStatsUncorrFecErrorCount
	   "
	::= { aniBsuRfSigQStatsEntry 8 }

aniBsuRfSigQStatsResetCounter OBJECT-TYPE
	SYNTAX      TruthValue
	MAX-ACCESS  read-write
	STATUS      current
	DESCRIPTION
	   "This provids an option to reset all the signal quality statistics 
	    counters for a particular wireless port.
	    Setting this object to true(1) resets the counters to 0.
	    Setting the object to false(2) is not allowed.

	    If a Get request is sent, the value false(2) will be returned.
	   "
	::= { aniBsuRfSigQStatsEntry 9 }


	END

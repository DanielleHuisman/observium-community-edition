BSUSUINV-MIB DEFINITIONS ::= BEGIN

	IMPORTS
		IpAddress
			FROM RFC1155-SMI
		OBJECT-TYPE, MODULE-IDENTITY 
			FROM SNMPv2-SMI
		DisplayString, MacAddress
			FROM SNMPv2-TC
		aniBsuWirelessPort
			FROM BSUWIRELESSIF-MIB
		aniBsuSuGroup
			FROM ANIROOT-MIB;

	-- the BSU SU Inventory group

aniBsuSuInventory  MODULE-IDENTITY
	LAST-UPDATED "0105091130Z"      -- Wed May 9 11:30:00 PDT 2001
	ORGANIZATION "Aperto Networks"
	CONTACT-INFO
	  "       
	  Postal:  Aperto Networks Inc
		   1637 S Main Street 
		   Milpitas, California 95035
	  Tel:	   +1 408 719 9977
	  "       
	DESCRIPTION
	   "This group allows viewing of SU Inventory information 
	    maintained by the BSU. It provides information about all the SUs 
	    connected to the particular BSU.
	   "
     ::= { aniBsuSuGroup 1 }


	-- The SU Inventory Table

aniBsuSuInvTable OBJECT-TYPE
	SYNTAX      SEQUENCE OF AniBsuSuInvEntry
	MAX-ACCESS  not-accessible
	STATUS      current
	DESCRIPTION
	   "A set of objects in the BSU, maintained for each
	    SU connected to this BSU.
	   "
	::= { aniBsuSuInventory 1 }

aniBsuSuInvEntry OBJECT-TYPE
	SYNTAX      AniBsuSuInvEntry
	MAX-ACCESS  not-accessible
	STATUS      current
	DESCRIPTION
	   "Inventory information for a single SU.
	    An entry in this table exists for each SU that is connected 
	    to the BSU.
	   "
	INDEX { aniBsuWirelessPort, aniBsuSuMacAddr }
	::= { aniBsuSuInvTable 1 }

AniBsuSuInvEntry ::= SEQUENCE {
	aniBsuSuMacAddr		MacAddress,		
	aniBsuSuIpAddr		IpAddress,		
	aniBsuSuName		DisplayString,		
	aniBsuSuCustomerName	DisplayString,		
	aniBsuSuLinkStatus	INTEGER,			
	aniBsuSuModelNumber	DisplayString		
        }

aniBsuSuMacAddr OBJECT-TYPE 
	SYNTAX      MacAddress
	MAX-ACCESS  read-only
	STATUS      current
	DESCRIPTION
	   "MAC address of this SU.
	   "
	::= { aniBsuSuInvEntry 1 }


aniBsuSuIpAddr OBJECT-TYPE 
	SYNTAX      IpAddress
	MAX-ACCESS  read-only
	STATUS      current
	DESCRIPTION
	   "IP address of this SU.
	   "
	::= { aniBsuSuInvEntry 3 }

aniBsuSuName OBJECT-TYPE
	SYNTAX      DisplayString (SIZE (0..31))
	MAX-ACCESS  read-only
	STATUS      current
	DESCRIPTION
	   "The administrative name for the SU.
	   "
	::= { aniBsuSuInvEntry 4 }

aniBsuSuCustomerName OBJECT-TYPE
	SYNTAX      DisplayString (SIZE (0..31))
	MAX-ACCESS  read-only
	STATUS      current
	DESCRIPTION
	   "The administrative name of the customer who uses this SU.
	   "
	::= { aniBsuSuInvEntry 5 }

aniBsuSuLinkStatus OBJECT-TYPE 
	SYNTAX	INTEGER {
		initial(1),
		ulm-req-rcvd(2),
		ulm-rsp-sent(3),
		dhcp-req-rcvd(4),
		dhcp-rsp-sent(5),
		tod-req-rcvd(6),
		tod-rsp-sent(7),
		config-file-req-rcvd(8),
		config-file-req-sent(9),
		reg-req-rcvd(10),
		lic-rsp-recd(11),
		reg-rsp-sent(12),
		reg-ack-rcvd(13),
		operational(14),
		stand-by(15),
		delete(255)
	}	
	MAX-ACCESS  read-write
	STATUS      current
	DESCRIPTION
	   "The link status of this SU.

	    When set to delete(255), the SU gets deleted from the inventory.
	    Note that any SU that is currently operational cannot be removed
	    from the inventory. 
	   "
	::= { aniBsuSuInvEntry 6 }

aniBsuSuModelNumber OBJECT-TYPE
	SYNTAX      DisplayString
	MAX-ACCESS  read-only
	STATUS      current
	DESCRIPTION
	   "The model number of the SU.
	    If the model number is not available, a blank string will be displayed.
	   "
	::= { aniBsuSuInvEntry 7 }

	END

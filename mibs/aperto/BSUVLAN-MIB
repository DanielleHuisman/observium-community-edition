BSUVLAN-MIB DEFINITIONS ::= BEGIN

	IMPORTS
		OBJECT-TYPE, MODULE-IDENTITY
			FROM SNMPv2-SMI
		DisplayString
			FROM SNMPv2-TC
		bsu
			FROM ANIROOT-MIB;


aniBsuVlan  MODULE-IDENTITY
	LAST-UPDATED "0210251725Z"      -- Fri Oct 25 17:25:00 PDT 2002
	ORGANIZATION "Aperto Networks"
	CONTACT-INFO
	  "       
	  Postal:  Aperto Networks Inc
		   1637 S Main Street 
		   Milpitas, California 95035
	  Tel:	   +1 408 719 9977
	  "       
	DESCRIPTION
	   "This group shows the VLAN information for the BSU.
	   "
	::= { bsu 11 }

	aniBsuVlanConf	     OBJECT IDENTIFIER ::= { aniBsuVlan 1 }


	-- the BSU VLAN Configuration group

aniBsuVlanConfMgmtVlanId OBJECT-TYPE
	SYNTAX      INTEGER (1..4094)
	MAX-ACCESS  read-only
	STATUS      current
	DESCRIPTION
	   "The Management VLAN ID for the BSU. 
	   The value 0 will be displayed when it is disabled.
	   "
	::= { aniBsuVlanConf 1 }

    -- obsolete aniBsuVlanConfPortRule, aniBsuVlanConfDefaultId
	-- rename aniBsuVlanConfDefaultPriority to aniBsuVlanConfMgmtVlanPriority


aniBsuVlanConfOuterTagId OBJECT-TYPE
	SYNTAX      INTEGER (1..4094)
	MAX-ACCESS  read-only
	STATUS      current
	DESCRIPTION
	   "The VLAN ID for the outer tag. 
	   "
	::= { aniBsuVlanConf 4 }

aniBsuVlanConfMgmtVlanIdPriority OBJECT-TYPE
	SYNTAX      INTEGER (0..7)
	MAX-ACCESS  read-only
	STATUS      current
	DESCRIPTION
	   "The priority of the management VLAN ID. 
	   "
	::= { aniBsuVlanConf 5 }

aniBsuVlanConfOuterTagPriority OBJECT-TYPE
	SYNTAX      INTEGER (0..7)
	MAX-ACCESS  read-only
	STATUS      current
	DESCRIPTION
	   "The priority of the outer tag VLAN ID.
	    It is tied to the outer tag VLAN ID.
		The value 0 will be displayed when it is disabled.
	   "
	::= { aniBsuVlanConf 6 }

aniBsuVlanConfSUMgmtVlanIdList OBJECT-TYPE
	SYNTAX      DisplayString 
	MAX-ACCESS  read-only
	STATUS      current
	DESCRIPTION
	   "The SU Management VLAN ID List
	   "
	::= { aniBsuVlanConf 7 }


END

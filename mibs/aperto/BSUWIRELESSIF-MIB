BSUWIRELESSIF-MIB DEFINITIONS ::= BEGIN

	IMPORTS
		OBJECT-TYPE, MODULE-IDENTITY, Integer32
			FROM SNMPv2-SMI
		MacAddress, TruthValue, DisplayString
			FROM SNMPv2-TC
		bsu
			FROM ANIROOT-MIB;


	-- the BSU Wireless Interface group

aniBsuWirelessIf  MODULE-IDENTITY
	LAST-UPDATED "0302101530Z"      -- Wed Feb 10 15:30:00 PDT 2003
	ORGANIZATION "Aperto Networks"
	CONTACT-INFO
	  "       
	  Postal:  Aperto Networks Inc
		   1637 S Main Street 
		   Milpitas, California 95035
	  Tel:	   +1 408 719 9977
	  "       
	DESCRIPTION
	   "This group contains BSU Wireless Interface information. 
	    It shows parameters for each configured Wireless Port on the BSU.  

	    It displays the following tables:
	    aniBsuWirelessPortTable - with basic wireless port information
	    aniBsuChannelTable - with Channel related information
	    aniBsuQosLinkTable - with QOS Link related information
	    aniBsuPowerControlTable - with Power control related information
	    aniBsuAntennaTable - with Antenna related information
	    aniBsuSectorTable  - with Sector related information

	    aniBsuWirelessPtPConfGroup - PacketWave 620  Wireless Configuration group
	    aniBsuWirelessPtpStatusGroup - PacketWave 620  Wireless Status information

	    aniBsuWirelessFreqAdminTable - PacketWave 620/750/1000  FrequencyTable Configuration 
	    aniBsuWirelessFreqOperTable - PacketWave 620/750/1000 Current FrequencyTable display 
	    aniBsuWirelessSysConfGroup - PacketWave 1000/760 per system Configuration group
	    aniBsuWirelessIfConfTable - PacketWave 1000/760 per port Wireless Configuration table
	    aniBsuWirelessAFSTable - PacketWave 1000/760 per port AFS Configuration table

	   "
	::= { bsu 2 }


aniBsuWirelessPortTable OBJECT-TYPE
	SYNTAX      SEQUENCE OF AniBsuWirelessPortEntry
	MAX-ACCESS  not-accessible
	STATUS      current
	DESCRIPTION
	   "This table contains entries with basic information about 
	    each BSU Wireless Port.
	   "
	::= { aniBsuWirelessIf 1 }

aniBsuWirelessPortEntry OBJECT-TYPE
	SYNTAX      AniBsuWirelessPortEntry
	MAX-ACCESS  not-accessible
	STATUS      current
	DESCRIPTION
	   "An entry containing basic information for
	    this particular wireless port.
	   "
	INDEX { aniBsuWirelessPort }
	::= { aniBsuWirelessPortTable 1 }

AniBsuWirelessPortEntry ::= SEQUENCE {
	aniBsuWirelessPort	INTEGER,
	aniBsuPortMacAddr	MacAddress,
	aniBsuPortState 	INTEGER,
	aniBsuPortReset		TruthValue,
	aniBsuPortFlag 		INTEGER
	}

aniBsuWirelessPort OBJECT-TYPE
	SYNTAX	INTEGER {
			wireless-port1(1),
			wireless-port2(2),
			wireless-port3(3),
			wireless-port4(4),
			wireless-port5(5),
			wireless-port6(6)
		}
	MAX-ACCESS  read-only
	STATUS      current
	DESCRIPTION
	   "The wireless port number.
	   "
	::= { aniBsuWirelessPortEntry 1 }

aniBsuPortMacAddr OBJECT-TYPE
	SYNTAX      MacAddress
	MAX-ACCESS  read-only
	STATUS      current
	DESCRIPTION
	   "The MAC Address of the wireless port.
	    
	    This field is not applicable when BSU is running as a bridge.
	    The agent will display a blank string for this case.
	   " 
	::= { aniBsuWirelessPortEntry 2 }

aniBsuPortState OBJECT-TYPE
	SYNTAX	INTEGER {
			unavailable(1),
			initial(2),
			unconfig(3),
			starting(4),
			configured-no-radio-detected(5),
			operational-radio(6),
			stopped(7),
			resetting(8),
			disabled(9)
		}
	MAX-ACCESS  read-only
	STATUS      current
	DESCRIPTION
	   "The current state of the wireless port."
	::= { aniBsuWirelessPortEntry 3 }

aniBsuPortReset OBJECT-TYPE
	SYNTAX      TruthValue 
	MAX-ACCESS  read-write
	STATUS      current
	DESCRIPTION
	   "This object is used to reset an individual wireless port. 
	    Setting this parameter to true(1) causes the port to reset.
	   "
	::= { aniBsuWirelessPortEntry 4 }

aniBsuPortFlag OBJECT-TYPE
	SYNTAX	INTEGER {
			enable(1),
			disable(2)
		}
	MAX-ACCESS  read-write
	STATUS      current
	DESCRIPTION
	   "This flag is used to turn a particular wireless port 
	    on or off, that is, to selectively enable(1) or disable(2) 
	    a port.

	    It is valid only for configured ports.
	    By default, all configured ports are enabled unless 
	    explicitly disabled during configuration. The disabled ports 
	    may later be enabled dynamically(without reboot).
	   "
	DEFVAL { 1 }
	::= { aniBsuWirelessPortEntry 5 }




aniBsuChannelTable OBJECT-TYPE
	SYNTAX      SEQUENCE OF AniBsuChannelEntry
	MAX-ACCESS  not-accessible
	STATUS      current
	DESCRIPTION
	   "This table contains Channel related information 
	    for each BSU Wireless interface.
	   "
	::= { aniBsuWirelessIf 4 }

aniBsuChannelEntry OBJECT-TYPE
	SYNTAX      AniBsuChannelEntry
	MAX-ACCESS  not-accessible
	STATUS      current
	DESCRIPTION
	   "An entry containing Channel attributes for
	    this particular interface.
	   "
	INDEX { aniBsuWirelessPort }
	::= { aniBsuChannelTable 1 }

AniBsuChannelEntry ::= SEQUENCE {
	aniBsuChannelFrequency		DisplayString,	
	aniBsuChannelWidth		DisplayString,	   
	aniBsuFrequencyBand		INTEGER, 
	aniBsuNumServFlowsPerSu		Integer32,
	aniBsuNumSusSupported 		Integer32,
	aniBsuSuRadioRegPowerLimit	INTEGER,
	aniBsuTargetFrequency		DisplayString	
	}

aniBsuChannelFrequency  OBJECT-TYPE
	SYNTAX      DisplayString
	UNITS       "MHz"
	MAX-ACCESS  read-only
	STATUS      current
	DESCRIPTION
	   "The Current Channel Center Frequency in MHz. 
	    If no radio is detected, this object will display a value of 0.

	    When Frequency Band is FDD, both transmit and receive
	    frequencies will be displayed in the format
	    'transmit frequency - receive frequency'.
	   "
	::= { aniBsuChannelEntry 2 }

aniBsuFrequencyBand OBJECT-TYPE
	SYNTAX	INTEGER {
			unii-5-3GHz(1),
			unii-5-8GHz(2),
			general-5-8GHz(3),
			ism-5-8GHz(10),
			mmds-2-6GHz(4),
			general-2-6GHz(5),
			general-3-5GHz(6),
			etsi-3-5GHz-50(7),
			etsi-3-5GHz-100(8),
			fdd-3-5GHz(11),
			general-5-3GHz(12)
		}
	MAX-ACCESS  read-only
	STATUS      current
	DESCRIPTION
	   "The Frequency Band to which the Channel Center Frequency
	    belongs. 

	    Valid Range:
	    1 - 5.3 GHz UNII Band (5250 - 5350 MHz)
	    12 - 5.3 GHz General Band (5150 - 5350 MHz)
	    2 - 5.8 GHz UNII Band (5725 - 5825 MHz)
	    3 - 5.8 GHz General (5725 - 5925 MHz)
	    10 - 5.8 GHz ISM Band (5725 - 5850 MHz)
	    4 - 2.6 GHz MMDS Band (2500 - 2689 MHz)
	    5 - 2.6 GHz General (2500 - 2700 MHz)
	    6 - 3.5 GHz General (3300 - 3800 MHz)
	    7 - 3.5 GHz ETSI Band - 50 MHz duplexing Scheme 
			(3410 - 3800 MHz)
	    8 - 3.5 GHz ETSI Band - 100 MHz duplexing Scheme 
			(3410 - 3800 MHz)
	    11 - 3.5 GHz FDD Band
	   "
	::= { aniBsuChannelEntry 3 }

aniBsuChannelWidth OBJECT-TYPE
	SYNTAX      DisplayString 
	MAX-ACCESS  read-only
	STATUS      current
	DESCRIPTION
	   "The Width of frequency channel in MHz.
	   "
	::= { aniBsuChannelEntry 4 }

aniBsuNumServFlowsPerSu  OBJECT-TYPE
	SYNTAX  Integer32 
	MAX-ACCESS  read-only
	STATUS      current
	DESCRIPTION
	   "The number of Service Flows supported per SU.
	   "
	::= { aniBsuChannelEntry 6 }

aniBsuNumSusSupported OBJECT-TYPE
	SYNTAX      Integer32
	MAX-ACCESS  read-only
	STATUS      current
	DESCRIPTION
	   "The number of SUs supported by this wireless port.
	   "
	::= { aniBsuChannelEntry 7 }

aniBsuSuRadioRegPowerLimit OBJECT-TYPE
	SYNTAX	INTEGER 
	UNITS       "dBm"
	MAX-ACCESS  read-only
	STATUS      current
	DESCRIPTION
	   "This parameter constraints the maximum power at
	    which a SU radio can transmit. This information is
	    conveyed to all the SUs within a WSS via the CD packet. 
	    It is equal to the EIRP (Effective Incidental Radiated Power)
	    specified by the Regulatory Body.

	    Note: If you are using an older version of the Configuration
	    Manager, this object is not defined in dBm. Instead, the following 
	    values will be displayed:
	    nominal(1),
	    one-level-above-nominal(2),
	    two-levels-above-nominal(3),
	    three-levels-above-nominal(4),
	    one-level-below-nominal(5),
	    two-levels-below-nominal(6)
	   "
	::= { aniBsuChannelEntry 9 }

aniBsuTargetFrequency  OBJECT-TYPE
	SYNTAX      DisplayString
	UNITS       "MHz"
	MAX-ACCESS  read-only
	STATUS      current
	DESCRIPTION
	   "The Current Target Frequency in MHz. 
	    To change the configuration of this value, use the object
	    aniBsuWirelessIfConfTargetFrequency for PW1000 
	    (or aniBsuWirelessPtPConfTargetFrequency for PW620).

	    When Frequency Band is FDD, both transmit and receive
	    frequencies will be displayed in the format
	    'transmit frequency - receive frequency'. Target frequency
	    cannot be modified for FDD band.
	   "
	::= { aniBsuChannelEntry 10 }

aniBsuQosLinkTable OBJECT-TYPE
	SYNTAX      SEQUENCE OF AniBsuQosLinkEntry
	MAX-ACCESS  not-accessible
	STATUS      current
	DESCRIPTION
	   "This table contains QOS Link related information 
	    for each BSU Wireless port.

	    The total sum of BE, CIR, CBR bandwidths should be 100%.
	   "
	::= { aniBsuWirelessIf 6 }

aniBsuQosLinkEntry OBJECT-TYPE
	SYNTAX      AniBsuQosLinkEntry
	MAX-ACCESS  not-accessible
	STATUS      current
	DESCRIPTION
	   "An entry containing QOS Link 
	    attributes for this particular port.
	   "
	INDEX { aniBsuWirelessPort }
	::= { aniBsuQosLinkTable 1 }

AniBsuQosLinkEntry ::= SEQUENCE {
	aniBsuBEBandwidth		Integer32,
	aniBsuCIRBandwidth		Integer32,
	aniBsuCBRBandwidth		Integer32
	}

aniBsuBEBandwidth OBJECT-TYPE
	SYNTAX      Integer32
	MAX-ACCESS  read-only
	STATUS      current
	DESCRIPTION
	   "The BE Bandwidth as a percentage of total bandwidth.
	   "
	::= { aniBsuQosLinkEntry 1 }

aniBsuCIRBandwidth OBJECT-TYPE
	SYNTAX      Integer32
	MAX-ACCESS  read-only
	STATUS      current
	DESCRIPTION
	   "The CIR Bandwidth as a percentage of total bandwidth.
	   "
	::= { aniBsuQosLinkEntry 2 }

aniBsuCBRBandwidth OBJECT-TYPE
	SYNTAX      Integer32
	MAX-ACCESS  read-only
	STATUS      current
	DESCRIPTION
	   "The CBR Bandwidth as a percentage of total bandwidth.
	   "
	::= { aniBsuQosLinkEntry 3 }


aniBsuPowerControlTable OBJECT-TYPE
	SYNTAX      SEQUENCE OF AniBsuPowerControlEntry
	MAX-ACCESS  not-accessible
	STATUS      current
	DESCRIPTION
	   "This table contains Power Control related information for 
	    each BSU Wireless port.
	   "
	::= { aniBsuWirelessIf 7 }

aniBsuPowerControlEntry OBJECT-TYPE
	SYNTAX      AniBsuPowerControlEntry
	MAX-ACCESS  not-accessible
	STATUS      current
	DESCRIPTION
	   "An entry containing Power Control attributes for this 
	    particular port.
	   "
	INDEX { aniBsuWirelessPort }
	::= { aniBsuPowerControlTable 1 }

AniBsuPowerControlEntry ::= SEQUENCE {
	aniBsuReceivePower	Integer32,	   
	aniBsuWssRadioRegPowerLimit	INTEGER	   
	}

aniBsuReceivePower OBJECT-TYPE
	SYNTAX      Integer32 (-90..-60)
	UNITS       "dBm"
	MAX-ACCESS  read-write
	STATUS      current
	DESCRIPTION
	   "This parameter sets the upstream receiver power
	    on the WSS. The range is between -60 to -90 (dBm)

	    It cannot be modified when BSU is in point to point mode.
	   "
	::= { aniBsuPowerControlEntry 2 }

aniBsuWssRadioRegPowerLimit OBJECT-TYPE
	SYNTAX	INTEGER 
	UNITS       "dBm"
	MAX-ACCESS  read-only
	STATUS      current
	DESCRIPTION
	   "This parameter constraints the maximum power at
	    which the radio for this WSS can transmit. It is
	    equal to the EIRP (Effective Incidental Radiated Power)
	    specified by the Regulatory Body.

	    Note: If you are using an older version of the Configuration
	    Manager, this object is not defined in dBm. Instead, the following 
	    values will be displayed:
	    nominal(1),
	    one-level-above-nominal(2),
	    two-levels-above-nominal(3),
	    three-levels-above-nominal(4),
	    one-level-below-nominal(5),
	    two-levels-below-nominal(6)
	   "
	::= { aniBsuPowerControlEntry 3 }

aniBsuAntennaTable OBJECT-TYPE
	SYNTAX      SEQUENCE OF AniBsuAntennaEntry
	MAX-ACCESS  not-accessible
	STATUS      current
	DESCRIPTION
	   "This table contains Antenna related information for 
	    each BSU Wireless port.
	   "
	::= { aniBsuWirelessIf 8 }

aniBsuAntennaEntry OBJECT-TYPE
	SYNTAX      AniBsuAntennaEntry
	MAX-ACCESS  not-accessible
	STATUS      current
	DESCRIPTION
	   "An entry containing Antenna attributes for this 
	    particular port.
	   "
	INDEX { aniBsuWirelessPort }
	::= { aniBsuAntennaTable 1 }

AniBsuAntennaEntry ::= SEQUENCE {
	aniBsuAntennaDiversityFlag	INTEGER,
	aniBsuAntennaDiversityMode	INTEGER,
	aniBsuBcastAntennaPolarization	INTEGER
	}

aniBsuAntennaDiversityFlag OBJECT-TYPE
	SYNTAX  INTEGER {
			enable (1),
			disable (2)
		}
	MAX-ACCESS  read-only
	STATUS      current
	DESCRIPTION
	   "This flag shows whether antenna diversity has been enabled (1)
	    or disabled (2) for this SU.
	   "
	::= { aniBsuAntennaEntry 1 }

aniBsuAntennaDiversityMode  OBJECT-TYPE
	SYNTAX  INTEGER {
			sync-based (1),
			training-seq-based (2)
		}
	MAX-ACCESS  read-only
	STATUS      current
	DESCRIPTION
	   "This shows whether diversity is Sync Based (1) or
	    Training Sequence Based (2) 
	   "
	::= { aniBsuAntennaEntry 2 }

aniBsuBcastAntennaPolarization OBJECT-TYPE
	SYNTAX	INTEGER {
			horizontal(1),
			vertical(2),
			horizontal-and-vertical(3)
		}
	MAX-ACCESS  read-only
	STATUS      current
	DESCRIPTION
	   "The default broadcast antenna polarization.
	   "
	::= { aniBsuAntennaEntry 4 }


aniBsuSectorTable OBJECT-TYPE
	SYNTAX      SEQUENCE OF AniBsuSectorEntry
	MAX-ACCESS  not-accessible
	STATUS      current
	DESCRIPTION
	   "This table contains Sector related information for 
	    each BSU Wireless port.
	   "
	::= { aniBsuWirelessIf 9 }

aniBsuSectorEntry OBJECT-TYPE
	SYNTAX      AniBsuSectorEntry
	MAX-ACCESS  not-accessible
	STATUS      current
	DESCRIPTION
	   "An entry containing Sector attributes for this 
	    particular port.
	   "
	INDEX { aniBsuWirelessPort }
	::= { aniBsuSectorTable 1 }

AniBsuSectorEntry ::= SEQUENCE {
	aniBsuSectorName	DisplayString
	}

aniBsuSectorName OBJECT-TYPE 
	SYNTAX      DisplayString (SIZE (0..80))
	MAX-ACCESS  read-only
	STATUS      current
	DESCRIPTION
	   "The descriptive name of the sector identified by 
	    aniBsuSectorId.
	   "
	::= { aniBsuSectorEntry 2 }


-- Configuration for PW620 (Point to Point):

-- The aniBsuWirelessPtPConfGroup contains configurable wireless 
-- paramters for each AP. 

aniBsuWirelessPtPConfGroup OBJECT IDENTIFIER
	::= { aniBsuWirelessIf 10 }

aniBsuWirelessPtPConfFrequencyBand OBJECT-TYPE
	SYNTAX	INTEGER {
			unii-5-3GHz(1),
			unii-5-8GHz(2),
			general-5-8GHz(3),
			ism-5-8GHz(10),
			mmds-2-6GHz(4),
			general-2-6GHz(5),
			general-3-5GHz(6),
			etsi-3-5GHz-50(7),
			etsi-3-5GHz-100(8)
		}
	MAX-ACCESS  read-only
	STATUS      current
	DESCRIPTION
	   "The Frequency Band to which the Channel Center Frequency
	    belongs. 

	    Valid Range:
	    1 - 5.3 GHz UNII Band (5250 - 5350 MHz)
	    12 - 5.3 GHz General Band (5150 - 5350 MHz)
	    2 - 5.8 GHz UNII Band (5725 - 5825 MHz)
	    3 - 5.8 GHz General (5650 - 5925 MHz)
	    10 - 5.8 GHz ISM Band (5725 - 5850 MHz)
	    4 - 2.6 GHz MMDS Band (2500 - 2689 MHz)
	    5 - 2.6 GHz General (2500 - 2700 MHz)
	    6 - 3.5 GHz General (3300 - 3800 MHz)
	    7 - 3.5 GHz ETSI Band - 50 MHz duplexing Scheme 
			(3410 - 3800 MHz)
	    8 - 3.5 GHz ETSI Band - 100 MHz duplexing Scheme 
			(3410 - 3800 MHz)
	   "
	::= { aniBsuWirelessPtPConfGroup 1 }

aniBsuWirelessPtPConfChannelWidth OBJECT-TYPE
	SYNTAX	INTEGER {
			width-2(2000),
			width-3(3000),
			width-4(4000),
			width-5(5000),
			width-6(6000),
			width-7(7000),
			width-3-5(3500)
		}
	MAX-ACCESS  read-write
	STATUS      current
	DESCRIPTION
	   "The Channel Width.
	    width-2 refers to 2MHz, width-3 refers to 3MHz
	    width-4 refers to 4MHz, width-5 refers to 5MHz,width-6 refers to 6MHz
	    width-7 refers to 7MHz, width-1-75 refers to 1.75MHz, width-3-5 refers to 3.5MHz
		Channel Width depends on Frequency Band. The valid range  is as follows:
		3.5 GHz (ETSI)  should allow channel width 3.5, 7; the rest of bands
		should allow channel width 2,3, 4, 5 and 6
		The Channel Width, Frame size, Downstream/Upstream ratio and cell radius are dependent on each other and the following
	    restrictions should be taken into account when configuring the system:
		Low Latency Mode
	    Channel Width = 1.75, 2, 3, 3.5 or 4 Not supported
	    Channel Width = 5, distance must be <= 30km 
		Percentage downstream bandwidth must be >= 50 
		Channel Width = 6 or 7, distance must be <= 40km
		Percentage downstream bandwidth must be >= 50 

		Normal Mode
		Channel Width = 1.75 Not supported
		Channel Width = 2, if DS/US is 50/50 then distance must be <100km
		Channel Width = 2, if DS/US is 60/40 then distance must be <90km
		Channel Width = 2, if DS/US is 70/30 then distance must be <50km

		Channel Width = 3, if DS/US is 50/50 then distance must be <100km
		Channel Width = 3, if DS/US is 60/40 then distance must be <100km
		Channel Width = 3, if DS/US is 70/30 then distance must be <90km

	    Channel Width = 3.5, 4,5, 6 and 7, DS/US must be >= 50 
	
		Note: It is required to upload the configuration and then reboot the device for the changes to take effect. 
	   "
	::= { aniBsuWirelessPtPConfGroup 2 }

aniBsuWirelessPtPConfTDDFrameSize OBJECT-TYPE
	SYNTAX	INTEGER {
			low-latency(1),
			normal-mode(2)
		}
	MAX-ACCESS  read-write
	STATUS      current
	DESCRIPTION
	   "The total size of the TDD Frame.

	    For PW620, only low-latency and normal-mode are allowed.
	    Also refer to the constraints listed under 
	    aniBsuWirelessPtPConfChannelWidth description.

	    Note: When this object is changed through SNMP agent,
	    it is required to upload the configuration (set
	    aniDevControlStartUpload in the device_control.mib
	    to true) and then reboot the device for the changes
	    to take effect. 
	   "
	::= { aniBsuWirelessPtPConfGroup 3 }

aniBsuWirelessPtPConfCellRadius OBJECT-TYPE
	SYNTAX      INTEGER {
			radius10km(10000),
			radius20km(20000),
			radius30km(30000),
			radius40km(40000),
			radius50km(50000),
			radius60km(60000),
			radius70km(70000),
			radius80km(80000),
			radius90km(90000),
			radius100km(100000)
		}
	MAX-ACCESS  read-write
	STATUS      current
	DESCRIPTION
	   "The cell radius or link distance

	    Refer to the constraints listed under 
	    aniBsuWirelessPtPConfChannelWidth description.

	    Note: When this object is changed through SNMP agent,
	    it is required to upload the configuration (set
	    aniDevControlStartUpload in the device_control.mib
	    to true) and then reboot the device for the changes
	    to take effect. 
	   "
	::= { aniBsuWirelessPtPConfGroup 4 }

aniBsuWirelessPtPConfDSUSRatio OBJECT-TYPE
	SYNTAX	INTEGER {
			ds70-us30(70),
			ds60-us40(60),
			ds50-us50(50),
			ds40-us60(40),
			ds30-us70(30)
		}
	MAX-ACCESS  read-write
	STATUS      current
	DESCRIPTION
	   "The Downstream upstream ratio (DS/US ratio).
	    This allows the user to configure how the total available 
	    bandwidth is split between downstream and upsteam.

	    ds70-us30 is 70/30
	    ds60-us40 is 60/40
	    ds50-us50 is 50/50
	    ds40-us60 is 40/60
	    ds30-us70 is 30/70

	    Also refer to the constraints listed under 
	    aniBsuWirelessPtPConfChannelWidth description.

	    Note: When this object is changed through SNMP agent,
	    it is required to upload the configuration (set
	    aniDevControlStartUpload in the device_control.mib
	    to true) and then reboot the device for the changes
	    to take effect. 
	   "
	::= { aniBsuWirelessPtPConfGroup 5 }

aniBsuWirelessPtPConfPolarization OBJECT-TYPE
	SYNTAX	INTEGER {
			vertical(2)
		}
	MAX-ACCESS  read-only
	STATUS      current
	DESCRIPTION
	   "The antenna polarization.

	   "
	::= { aniBsuWirelessPtPConfGroup 6 }

aniBsuWirelessPtPConfTargetFrequency  OBJECT-TYPE
	SYNTAX      DisplayString
	UNITS       "MHz"
	MAX-ACCESS  read-write
	STATUS      current
	DESCRIPTION
	   "The Target Frequency in MHz. 

	    Its range depends on Channel Width.

	    1) 5.3 GHz UNII Band (5250 - 5350 MHz). The center 
	    frequencies in this band are within 5250 + Half of 
	    Channel Width MHz and 5350 - Half of Channel Width MHz 
	    and can have any integer value (in MHz)

	    2) 5.8 GHz UNII Band (5725  - 5825 MHz). The center 
	    frequencies in this band are within 5725 + Half of 
	    Channel Width MHz and 5825 - Half of Channel Width MHz 
	    and can have any integer value (in MHz).

	    3) 5.8 GHz General (5650 - 5925 MHz). The center 
	    frequencies in this band are within 5650 + Half of 
	    Channel Width MHz and 5925 - Half of Channel Width MHz 
	    and can have any integer value (in MHz).

	    4) 2.6 GHz MMDS Band (2500 - 2689 MHz). The center 
	    frequencies in this band are 2503 + 6N MHz 
	    where N = 0,1,2,.,30

	    5) 2.6 GHz General (2500 - 2700 MHz). The center 
	    frequencies in this band are within 2500 + Half of 
	    Channel Width MHz and 2700  - Half of Channel Width 
	    MHz and can have any integer value (in MHz).

	    6) 3.5 GHz General (3300 - 3800 MHz). The center 
	    frequencies in this band are within 3300 + Half of 
	    Channel Width MHz and 3800 - Half of Channel Width 
	    MHz and can have any integer value (in MHz).

	    7) 3.5 GHz ETSI Band - 50 MHz duplexing Scheme 
	    (3410 - 3800 MHz). 

	    8) 3.5 GHz ETSI Band - 100 MHz duplexing scheme 
	    (3410 - 3800 MHz). 

	    10) 5.8 GHz ISM Band (5725 - 5850 MHz). The center
	    frequencies in this band are within 5725 + Half of 
	    Channel Width MHz and 5850 - Half of Channel Width
	    MHz and can have any integer value (in MHz).

	    11) 5.3 GHz General Band (5150 - 5350 MHz). The center 
	    frequencies in this band are within 5150 + Half of 
	    Channel Width MHz and 5350 - Half of Channel Width MHz 
	    and can have any integer value (in MHz)

	    Note: The term Half of Channel Width in all the descriptions 
	    above, is a rounded off value (with 0.5 rounded to 1).

	    Note: When this object is changed through SNMP agent,
	    the value could take effect immediately depending on
	    the current channel center frequency value. If 
	    aniBsuWirelessPtPConfTargetFrequency is modified, but 
	    the current aniBsuChannelFrequency value is still one of
	    the entries in aniBsuWirelessFreqOperTable, then the target 
	    frequency will not take effect immediately. However it 
	    could take effect later on when the current frequency entry is
	    deleted from the frequency table.
	   "
	::= { aniBsuWirelessPtPConfGroup 7 }

aniBsuWirelessPtPConfBsuRadioRegPowerLimit OBJECT-TYPE
	SYNTAX	INTEGER 
	UNITS       "dBm"
	MAX-ACCESS  read-write
	STATUS      current
	DESCRIPTION
	   "It is the maximum power at which the BSU radio is allowed to 
	    transmit. Antenna Gain is added to this maximum power to get
	    EIRP (Effective Incidental Radiated Power)

	    Valid Range - 
		For 5.3GHz radios: 8 to 20 dBm
		For 5.8GHz radios: 8 to 20 dBm
		For 3.5GHz radios: 10 to 23 dBm
		For 2.6GHz radios: 10 to 23 dBm
	   "
	::= { aniBsuWirelessPtPConfGroup 8 }

aniBsuWirelessPtPConfSuRadioRegPowerLimit OBJECT-TYPE
	SYNTAX	INTEGER 
	UNITS       "dBm"
	MAX-ACCESS  read-write
	STATUS      current
	DESCRIPTION
	   "It is the maximum power at which a SU radio is allowed to 
	    transmit. This information is conveyed to all the SUs via 
	    the CD packet. Antenna Gain is added to this maximum power 
	    to get EIRP (Effective Incidental Radiated Power)

	    Valid Range - 
		For 5.3GHz radios: 8 to 20 dBm
		For 5.8GHz radios: 8 to 20 dBm
		For 3.5GHz radios: 10 to 23 dBm
		For 2.6GHz radios: 10 to 23 dBm
	   "
	::= { aniBsuWirelessPtPConfGroup 9 }

aniBsuWirelessPtPConfModify OBJECT-TYPE
	SYNTAX      TruthValue
	MAX-ACCESS  read-write
	STATUS      current
	DESCRIPTION
	   "This flag is used to modify and commit the changes of the dependent 
	    parameters from this group: 
	    aniBsuWirelessPtPConfChannelWidth
	    aniBsuWirelessPtPConfTDDFrameSize
	    aniBsuWirelessPtPConfCellRadius
	    aniBsuWirelessPtPConfDSUSRatio
	    aniBsuWirelessPtPConfPolarization
	    aniBsuWirelessPtPConfTargetFrequency
	    aniBsuWirelessPtPConfBsuRadioRegPowerLimit
	    aniBsuWirelessPtPConfSuRadioRegPowerLimit
	    aniBsuWirelessFreqAdminTable

	    Setting this object to true(1) causes the agent to validate
	    the entire set of parameters. If these set of values are 
	    acceptable, then the new values are changed on the device.
	    However, for the changes to take effect, it is required to upload
	    the configuration (set aniDevControlStartUpload in the device_control.mib
	    to true) and then reboot the device.

	    If the validation fails when aniBsuWirelessPtPConfModify is set 
	    to true(1), the changes are not commited and an error is returned.
	    In that case, the modified parameters in this group may not
	    reflect the correct values. They will display the values last
	    configured by the user, rather than the current values on the device.
	    To view the current values for
	    aniBsuWirelessPtPConfChannelWidth refer to aniBsuChannelWidth
	    aniBsuWirelessPtPConfTDDFrameSize refer to aniBsuTDDFrameSize
	    aniBsuWirelessPtPConfCellRadius refer to aniBsuStatusCellRadius (bsu_status.mib)
	    aniBsuWirelessPtPConfTargetFrequency refer to aniBsuTargetFrequency
	    aniBsuWirelessPtPConfBsuRadioRegPowerLimit refer to aniBsuWssRadioRegPowerLimit
	    aniBsuWirelessPtPConfSuRadioRegPowerLimit refer to aniBsuSuRadioRegPowerLimit
	    aniBsuWirelessFreqAdminTable refer to aniBsuWirelessFreqOperTable

	    A Get request on this object will always return false(2).
	   "
	::= { aniBsuWirelessPtPConfGroup 10 }

aniBsuWirelessPtPConfBsuId OBJECT-TYPE
	SYNTAX      DisplayString (SIZE (0..14))
	MAX-ACCESS  read-write
	STATUS      current
	DESCRIPTION
	   "The unique AP/BSU identifier.
	    This is the AP ID required for generating seed for
	    frequency reuse support.

	    Note: When this object is changed through SNMP agent,
	    it is required to upload the configuration (set
	    aniDevControlStartUpload in the device_control.mib
	    to true) and then reboot the device for the changes
	    to take effect.
	   "
	::= { aniBsuWirelessPtPConfGroup 11 }

aniBsuWirelessPtPConfVerifyAllSu OBJECT-TYPE
	SYNTAX      DisplayString
	MAX-ACCESS  read-only
	STATUS      current
	DESCRIPTION
	   "This flag is used to verify if the current set of BSU
	    wireless parameters, that is, 
	    aniBsuWirelessPtPConfChannelWidth,
	    aniBsuWirelessPtPConfTargetFrequency,
	    aniBsuWirelessPtPConfBsuId
	    are correctly configured on all the SUs connected.
	    The values are compared against all the SUs connected to this BSU.

	    Sending a Get request on this object causes the agent to verify
	    the above set of parameters. If these set of values are 
	    incorrect, an error string is returned indicating that some
	    values are not in sync. If the current set of values are
	    correct, then the string 'No error' is displayed.

	    This object might require upto 10 seconds to respond if multiple SUs 
	    are connected. Therefore, to ensure that it does not timeout before
	    getting the complete results, the SNMP Manager tool should increase
	    it's timeout value for this object to more than 10 seconds.
	   "
	::= { aniBsuWirelessPtPConfGroup 12 }

aniBsuWirelessPtPConfSwitchToFrequency  OBJECT-TYPE
	SYNTAX      DisplayString
	UNITS       "MHz"
	MAX-ACCESS  read-write
	STATUS      current
	DESCRIPTION
	   "The Frequency selected to be switched. 
	    This frequency should be either one of the frequency entries in the
	    aniBsuWirelessFreqOperTable or the current target frequency
	    aniBsuTargetFrequency.

	    A get request on this object will display the current
	    frequency, aniBsuChannelFrequency and if no radio is detected, 
	    it will display 0.00.
	   "
	::= { aniBsuWirelessPtPConfGroup 13 }

aniBsuWirelessPtPConfSuAFSTimeout  OBJECT-TYPE
	SYNTAX      INTEGER (1..300)
	MAX-ACCESS  read-write
	STATUS      current
	DESCRIPTION
	   "Configure AFS SU Timeout (second)
	   "
	::= { aniBsuWirelessPtPConfGroup 14 }

aniBsuWirelessPtPStatusGroup OBJECT IDENTIFIER
	::= { aniBsuWirelessIf 11 }

aniBsuWirelessPtPStatusMaxDSAvailBW OBJECT-TYPE
	SYNTAX      DisplayString
	MAX-ACCESS  read-only
	STATUS      current
	DESCRIPTION
	   "The maximum Downstream available bandwidth in kbps
	    based on the current wireless configuration.
	   "
	::= { aniBsuWirelessPtPStatusGroup 1 }

aniBsuWirelessPtPStatusMaxUSAvailBW OBJECT-TYPE
	SYNTAX      DisplayString
	MAX-ACCESS  read-only
	STATUS      current
	DESCRIPTION
	   "The maximum Upstream available bandwidth in kbps
	    based on the current wireless configuration.
	   "
	::= { aniBsuWirelessPtPStatusGroup 2 }

aniBsuWirelessPtPStatusTDDFrameSize OBJECT-TYPE
	SYNTAX	INTEGER {
			low-latency(1),
			normal-mode(2)
		}
	MAX-ACCESS  read-only
	STATUS      current
	DESCRIPTION
	   "The total size of the TDD Frame 
	    low-latency is 2000 ticks
		normal-mode is 5000 ticks or 2500 ticks

	    For PW620, only low-latency and normal-mode are allowed.
	    Also refer to the constraints listed under 
	    aniBsuWirelessPtPConfChannelWidth description.

	   "
	::= { aniBsuWirelessPtPStatusGroup 3 }


-- Frequency Related Configuration and Status

aniBsuWirelessFreqAdminTable OBJECT-TYPE
	SYNTAX      SEQUENCE OF AniBsuWirelessFreqAdminEntry
	MAX-ACCESS  not-accessible
	STATUS      current
	DESCRIPTION
	   "This table is used to configure the BSU frequency table.
	   "
	::= { aniBsuWirelessIf 12 }

aniBsuWirelessFreqAdminEntry OBJECT-TYPE
	SYNTAX      AniBsuWirelessFreqAdminEntry
	MAX-ACCESS  not-accessible
	STATUS      current
	DESCRIPTION
	   "An entry containing the frequncy for this 
	    particular index.
	   "
	INDEX { aniBsuWirelessPort, aniBsuWirelessFreqAdminIndex }
	::= { aniBsuWirelessFreqAdminTable 1 }

AniBsuWirelessFreqAdminEntry ::= SEQUENCE {
	aniBsuWirelessFreqAdminIndex		INTEGER,
	aniBsuWirelessFreqAdminFreqValue	DisplayString
	}

aniBsuWirelessFreqAdminIndex OBJECT-TYPE
	SYNTAX      INTEGER
	MAX-ACCESS  read-only
	STATUS      current
	DESCRIPTION
	   "The index for this table.
	   "
	::= { aniBsuWirelessFreqAdminEntry 1 }

aniBsuWirelessFreqAdminFreqValue  OBJECT-TYPE
	SYNTAX      DisplayString
	UNITS       "MHz"
	MAX-ACCESS  read-write
	STATUS      current
	DESCRIPTION
	   "This object is used to configure the desired frequency 
	    values for the frequency table. Upto 19 frequency values 
	    can be added to the table. All frequencies should belong
	    to the same frequency band. For range and validation,
	    refer to aniBsuWirelessIfConfTargetFrequency description.
	    
	    Once the values are all added/modified, the object aniBsuWirelessIfConfModify 
	    (defined in the aniBsuWirelessIfConfTable) needs to be set to true(1). The 
	    aniBsuWirelessIfConfModify flag is used to modify and commit 
	    the changes of the dependent wireless parameters including all 
	    the entries of the aniBsuWirelessFreqAdminTable.

	    If the validation fails when aniBsuWirelessIfConfModify is set 
	    to true(1), these changes are not commited and an error is returned.
	    In that case, the modified parameters in this table may not
	    reflect the correct values. They will display the values last
	    configured by the user, rather than the actual values on the device.
	    To view the current values, refer to the aniBsuWirelessFreqOperTable.
	    Each entry in this aniBsuWirelessFreqAdminTable has a
	    corresponding entry displaying the actual values in the 
	    aniBsuWirelessFreqOperTable.
	   "
	::= { aniBsuWirelessFreqAdminEntry 2 }

aniBsuWirelessFreqOperTable OBJECT-TYPE
	SYNTAX      SEQUENCE OF AniBsuWirelessFreqOperEntry
	MAX-ACCESS  not-accessible
	STATUS      current
	DESCRIPTION
	   "This table is used to view the current frequency table.

	    Each entry in the aniBsuWirelessFreqAdminTable has a
	    corresponding entry in this table. All parameters
	    within this aniBsuWirelessFreqOperTable have read-only access. 
	    These objects reflect the actual frequency table values.
	   "
	::= { aniBsuWirelessIf 13 }

aniBsuWirelessFreqOperEntry OBJECT-TYPE
	SYNTAX      AniBsuWirelessFreqOperEntry
	MAX-ACCESS  not-accessible
	STATUS      current
	DESCRIPTION
	   "An entry containing the frequncy for this 
	    particular index.
	   "
	INDEX { aniBsuWirelessPort, aniBsuWirelessFreqOperIndex }
	::= { aniBsuWirelessFreqOperTable 1 }

AniBsuWirelessFreqOperEntry ::= SEQUENCE {
	aniBsuWirelessFreqOperIndex		INTEGER,
	aniBsuWirelessFreqOperFreqValue		DisplayString
	}

aniBsuWirelessFreqOperIndex OBJECT-TYPE
	SYNTAX      INTEGER
	MAX-ACCESS  read-only
	STATUS      current
	DESCRIPTION
	   "The index for this table.
	   "
	::= { aniBsuWirelessFreqOperEntry 1 }

aniBsuWirelessFreqOperFreqValue  OBJECT-TYPE
	SYNTAX      DisplayString
	UNITS       "MHz"
	MAX-ACCESS  read-only
	STATUS      current
	DESCRIPTION
	   "This object displays the current frequency value within the
	    frequency table.

	    To change the configuration of the frequency table, use the 
	    aniBsuWirelessFreqAdminTable. The correspoding entry with a
	    read-write access for this object is aniBsuWirelessFreqAdminFreqValue.
	   "
	::= { aniBsuWirelessFreqOperEntry 2 }

-- System level Wireless Parameters (configured per BSU)

aniBsuWirelessSysConfGroup OBJECT IDENTIFIER
	::= { aniBsuWirelessIf 14 }

aniBsuWirelessSysConfBsuId OBJECT-TYPE
	SYNTAX      DisplayString (SIZE (0..38))
	MAX-ACCESS  read-write
	STATUS      current
	DESCRIPTION
	   "The unique BSU identifier.
	    This is the BSU ID required for generating seed for
	    frequency reuse support.

	    Note: When this object is changed through SNMP agent,
	    it is required to upload the configuration (set
	    aniDevControlStartUpload in the device_control.mib
	    to true) and then reboot the device for the changes
	    to take effect.
	   "
	::= { aniBsuWirelessSysConfGroup 1 }

aniBsuWirelessSysConfFrameSize OBJECT-TYPE
	SYNTAX      Integer32
	MAX-ACCESS  read-only
	STATUS      current
	DESCRIPTION
	   "The total size of the Frame in ticks.
	   "
	::= { aniBsuWirelessSysConfGroup 2 }

aniBsuWirelessSysConfFrameDownstreamSize OBJECT-TYPE
	SYNTAX      Integer32
	MAX-ACCESS  read-only
	STATUS      current
	DESCRIPTION
	   "The number of ticks in the Downstream portion of 
	    the frame.
	   " 
	::= { aniBsuWirelessSysConfGroup 3 }

aniBsuWirelessSysConfFrameUpstreamSize OBJECT-TYPE
	SYNTAX      Integer32
	MAX-ACCESS  read-only
	STATUS      current
	DESCRIPTION
	   "The number of ticks in the Upstream portion of 
	    the frame.
	   " 
	::= { aniBsuWirelessSysConfGroup 4 }

aniBsuWirelessSysConfDSUSRatio OBJECT-TYPE
	SYNTAX	INTEGER {
			ds70-us30(70),
			ds60-us40(60),
			ds50-us50(50),
			ds40-us60(40),
			ds30-us70(30)
		}
	MAX-ACCESS  read-only
	STATUS      current
	DESCRIPTION
	   "The Downstream upstream ratio (DS/US ratio).

	    ds70-us30 is 70/30
	    ds60-us40 is 60/40
	    ds50-us50 is 50/50
	    ds40-us60 is 40/60
	    ds30-us70 is 30/70

	   "
	::= { aniBsuWirelessSysConfGroup 5 }


aniBsuWirelessIfConfTable OBJECT-TYPE
	SYNTAX      SEQUENCE OF AniBsuWirelessIfConfEntry
	MAX-ACCESS  not-accessible
	STATUS      current
	DESCRIPTION
	   "This table is used to configure the BSU wireless parameters
	    per wireless port.
	   "
	::= { aniBsuWirelessIf 15 }

aniBsuWirelessIfConfEntry OBJECT-TYPE
	SYNTAX      AniBsuWirelessIfConfEntry
	MAX-ACCESS  not-accessible
	STATUS      current
	DESCRIPTION
	   "An entry for this particular wireless port.
	   "
	INDEX { aniBsuWirelessPort }
	::= { aniBsuWirelessIfConfTable 1 }

AniBsuWirelessIfConfEntry ::= SEQUENCE {
	aniBsuWirelessIfConfTargetFrequency	DisplayString,
    aniBsuWirelessIfConfVerifyAllSu DisplayString,
	aniBsuWirelessIfConfSwitchToFrequency	DisplayString,
	aniBsuWirelessIfConfModify		TruthValue
	}

aniBsuWirelessIfConfTargetFrequency  OBJECT-TYPE
	SYNTAX      DisplayString
	UNITS       "MHz"
	MAX-ACCESS  read-write
	STATUS      current
	DESCRIPTION
	   "The Target Frequency in MHz. 

	    Its range depends on Channel Width.

	    1) 5.3 GHz UNII Band (5250 - 5350 MHz). The center 
	    frequencies in this band are within 5250 + Half of 
	    Channel Width MHz and 5350 - Half of Channel Width MHz 
	    and can have any integer value (in MHz)

	    2) 5.8 GHz UNII Band (5725  - 5825 MHz). The center 
	    frequencies in this band are within 5725 + Half of 
	    Channel Width MHz and 5825 - Half of Channel Width MHz 
	    and can have any integer value (in MHz).

	    3) 5.8 GHz General (5650 - 5925 MHz). The center 
	    frequencies in this band are within 5650 + Half of 
	    Channel Width MHz and 5925 - Half of Channel Width MHz 
	    and can have any integer value (in MHz).

	    4) 2.6 GHz MMDS Band (2500 - 2689 MHz). The center 
	    frequencies in this band are 2503 + 6N MHz 
	    where N = 0,1,2,.,30

	    5) 2.6 GHz General (2500 - 2700 MHz). The center 
	    frequencies in this band are within 2500 + Half of 
	    Channel Width MHz and 2700  - Half of Channel Width 
	    MHz and can have any integer value (in MHz).

	    6) 3.5 GHz General (3300 - 3800 MHz). The center 
	    frequencies in this band are within 3300 + Half of 
	    Channel Width MHz and 3800 - Half of Channel Width 
	    MHz and can have any integer value (in MHz).

	    7) 3.5 GHz ETSI Band - 50 MHz duplexing Scheme 
	    (3410 - 3800 MHz). 

	    8) 3.5 GHz ETSI Band - 100 MHz duplexing scheme 
	    (3410 - 3800 MHz). 

	    10) 5.8 GHz ISM Band (5725 - 5850 MHz). The center
	    frequencies in this band are within 5725 + Half of 
	    Channel Width MHz and 5850 - Half of Channel Width
	    MHz and can have any integer value (in MHz).

	    11) 5.3 GHz General Band (5150 - 5350 MHz). The center 
	    frequencies in this band are within 5150 + Half of 
	    Channel Width MHz and 5350 - Half of Channel Width MHz 
	    and can have any integer value (in MHz)


	    Note: The term Half of Channel Width in all the descriptions 
	    above, is a rounded off value (with 0.5 rounded to 1).

	    Note: When this object is changed through SNMP agent,
	    the value could take effect immediately depending on
	    the current channel center frequency value. If 
	    aniBsuWirelessIfConfTargetFrequency is modified, but 
	    the current aniBsuChannelFrequency value is still one of
	    the entries in aniBsuWirelessFreqOperTable, then the target 
	    frequency will not take effect immediately. However it 
	    could take effect later on when the current frequency entry is
	    deleted from the frequency table.
	   "
	::= { aniBsuWirelessIfConfEntry 1 }

aniBsuWirelessIfConfVerifyAllSu OBJECT-TYPE
	SYNTAX      DisplayString
	MAX-ACCESS  read-only
	STATUS      current
	DESCRIPTION
	   "This flag is used to verify if the current set of BSU
	    wireless parameters, that is, 
	    aniBsuWirelessPtPConfChannelWidth,
	    aniBsuWirelessPtPConfTargetFrequency,
	    aniBsuWirelessPtPConfBsuId
	    are correctly configured on all the SUs connected.
	    The values are compared against all the SUs connected to this BSU.

	    Sending a Get request on this object causes the agent to verify
	    the above set of parameters. If these set of values are 
	    incorrect, an error string is returned indicating that some
	    values are not in sync. If the current set of values are
	    correct, then the string 'No error' is displayed.

	    This object might require upto 10 seconds to respond if multiple SUs 
	    are connected. Therefore, to ensure that it does not timeout before
	    getting the complete results, the SNMP Manager tool should increase
	    it's timeout value for this object to more than 10 seconds.
	   "
	::= { aniBsuWirelessIfConfEntry 2 }

aniBsuWirelessIfConfSwitchToFrequency  OBJECT-TYPE
	SYNTAX      DisplayString
	UNITS       "MHz"
	MAX-ACCESS  read-write
	STATUS      current
	DESCRIPTION
	   "The Frequency selected to be switched. 
	    This frequency should be either one of the frequency entries in the
	    aniBsuWirelessFreqOperTable or the current target frequency
	    aniBsuTargetFrequency.

	    A get request on this object will display the current
	    frequency, aniBsuChannelFrequency and if no radio is detected, 
	    it will display 0.00.
	   "
	::= { aniBsuWirelessIfConfEntry 3 }


aniBsuWirelessIfConfModify OBJECT-TYPE
	SYNTAX      TruthValue
	MAX-ACCESS  read-write
	STATUS      current
	DESCRIPTION
	   "This flag is used to modify and commit the changes of the dependent 
	    parameters from this group: 
	    aniBsuWirelessIfConfTargetFrequency
	    aniBsuWirelessFreqAdminTable

	    Setting this object to true(1) causes the agent to validate
	    the entire set of parameters. If these set of values are 
	    acceptable, then the new values are changed on the device.
	    However, for the changes to take effect, it is required to upload
	    the configuration (set aniDevControlStartUpload in the device_control.mib
	    to true) and then reboot the device.

	    If the validation fails when aniBsuWirelessIfConfModify is set 
	    to true(1), the changes are not commited and an error is returned.
	    In that case, the modified parameters in this group may not
	    reflect the correct values. They will display the values last
	    configured by the user, rather than the current values on the device.
	    To view the current values for
	    aniBsuWirelessIfConfTargetFrequency refer to aniBsuTargetFrequency
	    aniBsuWirelessFreqAdminTable refer to aniBsuWirelessFreqOperTable

	    A Get request on this object will always return false(2).
	   "
	::= { aniBsuWirelessIfConfEntry 50 }


aniBsuWirelessAFSTable OBJECT-TYPE
	SYNTAX      SEQUENCE OF AniBsuWirelessAFSConfEntry
	MAX-ACCESS  not-accessible
	STATUS      current
	DESCRIPTION
	   "This table is used to configure the BSU wireless AFS parameters
	    per wireless port.
	   "
	::= { aniBsuWirelessIf 16 }

aniBsuWirelessAFSConfEntry OBJECT-TYPE
	SYNTAX      AniBsuWirelessAFSConfEntry
	MAX-ACCESS  not-accessible
	STATUS      current
	DESCRIPTION
	   "An entry for this particular wireless port.
	   "
	INDEX { aniBsuWirelessPort }
	::= { aniBsuWirelessAFSTable 1 }

AniBsuWirelessAFSConfEntry ::= SEQUENCE {
	aniBsuWirelessAFSFlag INTEGER,
	aniBsuWirelessAFSMinSwitchDuration INTEGER,
	aniBsuWirelessAFSMinNotificationDuration INTEGER,
	aniBsuWirelessAFSErrPercentage INTEGER,
	aniBsuWirelessAFSMinSwitchBytes INTEGER
	}


aniBsuWirelessAFSFlag  OBJECT-TYPE
	SYNTAX	INTEGER {
		enable(1),
		disable(2)
	}           
	MAX-ACCESS  read-write
	STATUS      current
	DESCRIPTION
	   "Enable or disable AFS.
	   "

	::= { aniBsuWirelessAFSConfEntry 1 }

aniBsuWirelessAFSMinSwitchDuration  OBJECT-TYPE
	SYNTAX      INTEGER (1..600)
	MAX-ACCESS  read-write
	STATUS      current
	DESCRIPTION
	   "Configure AFS minimum switch duration in database (second)  
	   "

	::= { aniBsuWirelessAFSConfEntry 2 }

aniBsuWirelessAFSMinNotificationDuration  OBJECT-TYPE
	SYNTAX      INTEGER (1..540)
	MAX-ACCESS  read-write
	STATUS      current
	DESCRIPTION
	   "Configure AFS minimum notification duration (second)  
	   "

	::= { aniBsuWirelessAFSConfEntry 3 }

aniBsuWirelessAFSErrPercentage  OBJECT-TYPE
	SYNTAX      INTEGER (1..100)
	MAX-ACCESS  read-write
	STATUS      current
	DESCRIPTION
	   "Configure AFS minimum error percentage.  
	   "

	::= { aniBsuWirelessAFSConfEntry 4 }

aniBsuWirelessAFSMinSwitchBytes  OBJECT-TYPE
	SYNTAX      INTEGER (1000..20000)
	MAX-ACCESS  read-write
	STATUS      current
	DESCRIPTION
	   "Configure AFS minimum switch bytes.  
	   "

	::= { aniBsuWirelessAFSConfEntry 5 }




	END

ARECA-SAS-CARD3-MIB DEFINITIONS ::= BEGIN

IMPORTS 		
		enterprises, OBJECT-TYPE
			FROM RFC1155-SMI
		TRAP-TYPE
            FROM RFC-1215;

-- the path to the root

--internet				OBJECT IDENTIFIER ::= { iso org(3) dod(6) 1 }
--directory				OBJECT IDENTIFIER ::= { internet 1 }
--mgmt					OBJECT IDENTIFIER ::= { internet 2 }
--experimental			OBJECT IDENTIFIER ::= { internet 3 }
--private				OBJECT IDENTIFIER ::= { internet 4 }
--enterprises			OBJECT IDENTIFIER ::= { private 1 }
areca					OBJECT IDENTIFIER ::= { enterprises 18928 }
arecaGroup1				OBJECT IDENTIFIER ::= { areca 1 }
sasRaidCard3 			OBJECT IDENTIFIER ::= { arecaGroup1 131 }
systemInformation		OBJECT IDENTIFIER ::= { sasRaidCard3 1 }
hwMonitor				OBJECT IDENTIFIER ::= { sasRaidCard3 2 }
hddInformation			OBJECT IDENTIFIER ::= { sasRaidCard3 3 }
raidsetInformation		OBJECT IDENTIFIER ::= { sasRaidCard3 4 }
volumesetInformation	OBJECT IDENTIFIER ::= { sasRaidCard3 5 }
eventInformation		OBJECT IDENTIFIER ::= { sasRaidCard3 6 }

-- definition of object types

-- definition of object types of system information

siVendor	OBJECT-TYPE
	SYNTAX	OCTET STRING
	ACCESS 	read-only
	STATUS	mandatory
	DESCRIPTION
		"The vendor name of raid subsystem."
	::= { systemInformation 1 }

siModel OBJECT-TYPE
	SYNTAX	OCTET STRING
	ACCESS 	read-only
	STATUS	mandatory
	DESCRIPTION
		"The model name of raid subsystem."
	::= { systemInformation 2 }

siSerial OBJECT-TYPE
	SYNTAX	OCTET STRING
	ACCESS 	read-only
	STATUS	mandatory
	DESCRIPTION
		"The serial number of raid subsystem."
	::= { systemInformation 3 }	
	
siFirmVer OBJECT-TYPE
	SYNTAX	OCTET STRING
	ACCESS 	read-only
	STATUS	mandatory
	DESCRIPTION
		"The firmware version of raid subsystem."
	::= { systemInformation 4 }	
	
siBootVer OBJECT-TYPE
	SYNTAX	OCTET STRING
	ACCESS 	read-only
	STATUS	mandatory
	DESCRIPTION
		"The Boot version of raid subsystem."
	::= { systemInformation 5 }	
	
siMbrVer OBJECT-TYPE
	SYNTAX	OCTET STRING
	ACCESS 	read-only
	STATUS	mandatory
	DESCRIPTION
		"The master boot record version of raid subsystem."
	::= { systemInformation 6 }		
	
siProcessor OBJECT-TYPE
	SYNTAX	OCTET STRING
	ACCESS 	read-only
	STATUS	mandatory
	DESCRIPTION
		"The processor name of raid subsystem."
	::= { systemInformation 7 }	
	
siCpuSpeed	OBJECT-TYPE
	SYNTAX	INTEGER
	ACCESS 	read-only
	STATUS	mandatory
	DESCRIPTION
		"The CPU speed (in MHZ, e.g. 400) of Raid subsystem."
	::= { systemInformation 8 }

siICache	OBJECT-TYPE
	SYNTAX	INTEGER {	
					s32K(32768), 
					s512K(524288) 
					} 
	ACCESS 	read-only
	STATUS	mandatory
	DESCRIPTION
		"The CPU internal Instruction cache size (in bytes, e.g. 32768) of Raid subsystem."
	::= { systemInformation 9 }

siDCache	OBJECT-TYPE
	SYNTAX	INTEGER { 
					s32K(32768), 
					s512K(524288) 
					}			
	ACCESS 	read-only
	STATUS	mandatory
	DESCRIPTION
		"The CPU interanl data cache size (in bytes, e.g. 32768) of Raid subsystem."
	::= { systemInformation 10 }

siSCache	OBJECT-TYPE
	SYNTAX	INTEGER { 
					s32K(32768), 
					s512K(524288) 
					}
	ACCESS 	read-only
	STATUS	mandatory
	DESCRIPTION
		"The CPU secondary cache size (in bytes, e.g. 32768) of Raid subsystem."
	::= { systemInformation 11 }

siMemory	OBJECT-TYPE
	SYNTAX	INTEGER
	ACCESS 	read-only
	STATUS	mandatory
	DESCRIPTION
		"The memory size (in MB, e.g. 128) of Raid subsystem."
	::= { systemInformation 12 }

siMemSpeed	OBJECT-TYPE
	SYNTAX	INTEGER
	ACCESS 	read-only
	STATUS	mandatory
	DESCRIPTION
		"The memory speed (in MHz) of Raid subsystem."
	::= { systemInformation 13 }

siEcc		OBJECT-TYPE
	SYNTAX	INTEGER{
			no(0),
			yes(1)
			}
	ACCESS 	read-only
	STATUS	mandatory
	DESCRIPTION
		"The sdram ECC capability of Raid subsystem (0:no ECC, 1:ECC)."
	::= { systemInformation 14 }

siHosts		OBJECT-TYPE
	SYNTAX	INTEGER
	ACCESS 	read-only
	STATUS	mandatory
	DESCRIPTION
		"The number of host channels, e.g. 2."
	::= { systemInformation 15 }

siRaidSets	OBJECT-TYPE
	SYNTAX	INTEGER
	ACCESS 	read-only
	STATUS	mandatory
	DESCRIPTION
		"The number of RAIDSET supported, e.g. 16."
	::= { systemInformation 16 }

siVolumeSets	OBJECT-TYPE
	SYNTAX	INTEGER
	ACCESS 	read-only
	STATUS	mandatory
	DESCRIPTION
		"The number of VOLUMESET supported, e.g. 16."
	::= { systemInformation 17 }
	
siEvents	OBJECT-TYPE
	SYNTAX	INTEGER
	ACCESS 	read-only
	STATUS	mandatory
	DESCRIPTION
		"The number of events supported, e.g. 16."
	::= { systemInformation 18 }	
	
siRaid6		OBJECT-TYPE
	SYNTAX	INTEGER {
			 no(0),			 
			 yes(1) 
			}
			
	ACCESS 	read-only
	STATUS	mandatory
	DESCRIPTION
		"0:no RAID6, 1:RAID6."
	::= { systemInformation 19 }		
	
siDhcp		OBJECT-TYPE
	SYNTAX	INTEGER {
			 disabled(0),
			 enabled(1)
			}
	ACCESS 	read-only
	STATUS	mandatory
	DESCRIPTION
		"0:disabled, 1:enabled."
	::= { systemInformation 20 }			

siBeeper	OBJECT-TYPE
	SYNTAX	INTEGER {
	 		 disabled(0),
	 		 enabled(1)
	 		}
	ACCESS 	read-only
	STATUS	mandatory
	DESCRIPTION
		"0:disabled, 1:enabled."
	::= { systemInformation 21 }			

siUsage		OBJECT-TYPE
	SYNTAX	INTEGER {
	   		 normal(0),
	   		 jbod(1)
	   		}
	ACCESS 	read-only
	STATUS	mandatory
	DESCRIPTION
		"0:normal, 1:JBOD."
	::= { systemInformation 22 }			

siRebuildRate	OBJECT-TYPE
	SYNTAX	INTEGER
	ACCESS 	read-only
	STATUS	mandatory
	DESCRIPTION
		"5,20,50,80 in %."
	::= { systemInformation 23 }

siBaudRate	OBJECT-TYPE
	SYNTAX	INTEGER {
			 s1200bps(1200),
			 s2400bps(2400),
			 s4800bps(4800),
			 s9600bps(9600),
			 s19200bps(19200),
			 s38400bps(38400),
			 s57600bps(57600),
			 s115200bps(115200)
			}
	ACCESS 	read-only
	STATUS	mandatory
	DESCRIPTION
		"1200,2400,4800,9600,19200,38400,57600,115200."
	::= { systemInformation 24 }


-- definition of object types of H/W monitor

controllerBoard			OBJECT IDENTIFIER ::= { hwMonitor 1 }
hwEnclosure1			OBJECT IDENTIFIER ::= { hwMonitor 2 }
hwEnclosure2			OBJECT IDENTIFIER ::= { hwMonitor 3 }
hwEnclosure3			OBJECT IDENTIFIER ::= { hwMonitor 4 }
hwEnclosure4			OBJECT IDENTIFIER ::= { hwMonitor 5 }
hwEnclosure5			OBJECT IDENTIFIER ::= { hwMonitor 6 }
hwEnclosure6			OBJECT IDENTIFIER ::= { hwMonitor 7 }
hwEnclosure7			OBJECT IDENTIFIER ::= { hwMonitor 8 }
hwEnclosure8			OBJECT IDENTIFIER ::= { hwMonitor 9 }

-- controller board
hwControllerBoardInstalled	OBJECT-TYPE
	SYNTAX	INTEGER
	ACCESS 	read-only
	STATUS	mandatory
	DESCRIPTION
		"Enclosure Installed?"
	::= { controllerBoard 1 }

hwControllerBoardDescription	OBJECT-TYPE
	SYNTAX	OCTET STRING
	ACCESS 	read-only
	STATUS	mandatory
	DESCRIPTION
		"Enclosure description."
	::= { controllerBoard 2 }
	
hwControllerBoardNumberOfPower	OBJECT-TYPE
	SYNTAX	INTEGER
	ACCESS 	read-only
	STATUS	mandatory
	DESCRIPTION
		"# of power supply, e.g. 2."
	::= { controllerBoard 3 }	
	
hwControllerBoardNumberOfVol	OBJECT-TYPE
	SYNTAX	INTEGER
	ACCESS 	read-only
	STATUS	mandatory
	DESCRIPTION
		"# of Voltage, e.g. 2."
	::= { controllerBoard 4 }

hwControllerBoardNumberOfFan	OBJECT-TYPE
	SYNTAX	INTEGER
	ACCESS 	read-only
	STATUS	mandatory
	DESCRIPTION
		"# of Fan, e.g. 2."
	::= { controllerBoard 5 }		

hwControllerBoardNumberOfTemp	OBJECT-TYPE
	SYNTAX	INTEGER
	ACCESS 	read-only
	STATUS	mandatory
	DESCRIPTION
		"# of Temperature, e.g. 2."
	::= { controllerBoard 6 }	

hwControllerBoardPowerTable 	OBJECT-TYPE
	SYNTAX 	SEQUENCE OF HwControllerBoardPowerEntry
	ACCESS	not-accessible
	STATUS	mandatory
	DESCRIPTION
		"A table containing Power information."
	::= { controllerBoard 7 }

hwControllerBoardPowerEntry 	OBJECT-TYPE
	SYNTAX	HwControllerBoardPowerEntry
	ACCESS	not-accessible
	STATUS	mandatory
	DESCRIPTION
		"Information about a particular current power state."
	INDEX	{ hwControllerBoardPowerIndex }
	::= { hwControllerBoardPowerTable 1 }
	
HwControllerBoardPowerEntry ::= SEQUENCE { hwControllerBoardPowerIndex INTEGER,
			    hwControllerBoardPowerDesc OCTET STRING,
			    hwControllerBoardPowerState INTEGER }

hwControllerBoardPowerIndex	OBJECT-TYPE
	SYNTAX	INTEGER
	ACCESS 	read-only
	STATUS	mandatory
	DESCRIPTION
		"Power index, 1..#of powers."
	::= { hwControllerBoardPowerEntry 1 }		    
			    
hwControllerBoardPowerDesc	OBJECT-TYPE
	SYNTAX	OCTET STRING
	ACCESS 	read-only
	STATUS	mandatory
	DESCRIPTION
		"Power description."
	::= { hwControllerBoardPowerEntry 2 }
			    
hwControllerBoardPowerState	OBJECT-TYPE
	SYNTAX	INTEGER {
			 failed(0),
			 ok(1)
			}
	ACCESS 	read-only
	STATUS	mandatory
	DESCRIPTION
		"Power state 0:failed, 1:ok."
	::= { hwControllerBoardPowerEntry 3 }		
	
hwControllerBoardVolTable 	OBJECT-TYPE
	SYNTAX 	SEQUENCE OF HwControllerBoardVolEntry
	ACCESS	not-accessible
	STATUS	mandatory
	DESCRIPTION
		"A table containing voltage information."
	::= { controllerBoard 8 }

hwControllerBoardVolEntry 	OBJECT-TYPE
	SYNTAX	HwControllerBoardVolEntry
	ACCESS	not-accessible
	STATUS	mandatory
	DESCRIPTION
		"Information about a particular current voltage state."
	INDEX	{ hwControllerBoardVolIndex }
	::= { hwControllerBoardVolTable 1 }
	
HwControllerBoardVolEntry ::= SEQUENCE { hwControllerBoardVolIndex INTEGER,
			  hwControllerBoardVolDesc OCTET STRING,
			  hwControllerBoardVolValue INTEGER }

hwControllerBoardVolIndex	OBJECT-TYPE
	SYNTAX	INTEGER
	ACCESS 	read-only
	STATUS	mandatory
	DESCRIPTION
		"Voltage index, 1..#of voltages."
	::= { hwControllerBoardVolEntry 1 }		    

hwControllerBoardVolDesc	OBJECT-TYPE
	SYNTAX	OCTET STRING
	ACCESS 	read-only
	STATUS	mandatory
	DESCRIPTION
		"Voltage description."
	::= { hwControllerBoardVolEntry 2 }
			    
hwControllerBoardVolValue	OBJECT-TYPE
	SYNTAX	INTEGER
	ACCESS 	read-only
	STATUS	mandatory
	DESCRIPTION
		"Voltage value."
	::= { hwControllerBoardVolEntry 3 }

hwControllerBoardFanTable 	OBJECT-TYPE
	SYNTAX 	SEQUENCE OF HwControllerBoardFanEntry
	ACCESS	not-accessible
	STATUS	mandatory
	DESCRIPTION
		"A table containing Fan information."
	::= { controllerBoard 9 }

hwControllerBoardFanEntry 	OBJECT-TYPE
	SYNTAX	HwControllerBoardFanEntry
	ACCESS	not-accessible
	STATUS	mandatory
	DESCRIPTION
		"Information about a particular current fan state."
	INDEX	{ hwControllerBoardFanIndex }
	::= { hwControllerBoardFanTable 1 }
	
HwControllerBoardFanEntry ::= SEQUENCE { hwControllerBoardFanIndex INTEGER,
			  hwControllerBoardFanDesc OCTET STRING,
			  hwControllerBoardFanSpeed INTEGER }

hwControllerBoardFanIndex	OBJECT-TYPE
	SYNTAX	INTEGER
	ACCESS 	read-only
	STATUS	mandatory
	DESCRIPTION
		"Fan index, 1..#of fans."
	::= { hwControllerBoardFanEntry 1 }		    

hwControllerBoardFanDesc	OBJECT-TYPE
	SYNTAX	OCTET STRING
	ACCESS 	read-only
	STATUS	mandatory
	DESCRIPTION
		"Fan description."
	::= { hwControllerBoardFanEntry 2 }
			    
hwControllerBoardFanSpeed	OBJECT-TYPE
	SYNTAX	INTEGER
	ACCESS 	read-only
	STATUS	mandatory
	DESCRIPTION
		"Fan speed in RPM, e.g. 3200."
	::= { hwControllerBoardFanEntry 3 }

hwControllerBoardTempTable 	OBJECT-TYPE
	SYNTAX 	SEQUENCE OF HwControllerBoardTempEntry
	ACCESS	not-accessible
	STATUS	mandatory
	DESCRIPTION
		"A table containing temperature information."
	::= { controllerBoard 10 }

hwControllerBoardTempEntry 	OBJECT-TYPE
	SYNTAX	HwControllerBoardTempEntry
	ACCESS	not-accessible
	STATUS	mandatory
	DESCRIPTION
		"Information about a particular current temperature state."
	INDEX	{ hwControllerBoardTempIndex }
	::= { hwControllerBoardTempTable 1 }
	
HwControllerBoardTempEntry ::= SEQUENCE { hwControllerBoardTempIndex INTEGER,
			   hwControllerBoardTempDesc OCTET STRING,
			   hwControllerBoardTempValue INTEGER
			 }

hwControllerBoardTempIndex	OBJECT-TYPE
	SYNTAX	INTEGER
	ACCESS 	read-only
	STATUS	mandatory
	DESCRIPTION
		"Temperature index, 1..#of voltages."
	::= { hwControllerBoardTempEntry 1 }		    

hwControllerBoardTempDesc	OBJECT-TYPE
	SYNTAX	OCTET STRING
	ACCESS 	read-only
	STATUS	mandatory
	DESCRIPTION
		"Temperature description."
	::= { hwControllerBoardTempEntry 2 }
			    
hwControllerBoardTempValue	OBJECT-TYPE
	SYNTAX	INTEGER
	ACCESS 	read-only
	STATUS	mandatory
	DESCRIPTION
		"Temperature value."
	::= { hwControllerBoardTempEntry 3 }


-- Enclosure#01
hwEnclosure01Installed	OBJECT-TYPE
	SYNTAX	INTEGER
	ACCESS 	read-only
	STATUS	mandatory
	DESCRIPTION
		"Enclosure Installed?"
	::= { hwEnclosure1 1 }

hwEnclosure01Description	OBJECT-TYPE
	SYNTAX	OCTET STRING
	ACCESS 	read-only
	STATUS	mandatory
	DESCRIPTION
		"Enclosure description."
	::= { hwEnclosure1 2 }
	
hwEnclosure01NumberOfPower	OBJECT-TYPE
	SYNTAX	INTEGER
	ACCESS 	read-only
	STATUS	mandatory
	DESCRIPTION
		"# of power supply, e.g. 2."
	::= { hwEnclosure1 3 }	
	
hwEnclosure01NumberOfVol	OBJECT-TYPE
	SYNTAX	INTEGER
	ACCESS 	read-only
	STATUS	mandatory
	DESCRIPTION
		"# of Voltage, e.g. 2."
	::= { hwEnclosure1 4 }

hwEnclosure01NumberOfFan	OBJECT-TYPE
	SYNTAX	INTEGER
	ACCESS 	read-only
	STATUS	mandatory
	DESCRIPTION
		"# of Fan, e.g. 2."
	::= { hwEnclosure1 5 }	

hwEnclosure01NumberOfTemp	OBJECT-TYPE
	SYNTAX	INTEGER
	ACCESS 	read-only
	STATUS	mandatory
	DESCRIPTION
		"# of Temperature, e.g. 2."
	::= { hwEnclosure1 6 }	

hwEnclosure01PowerTable		OBJECT-TYPE
	SYNTAX 	SEQUENCE OF HwEnclosure01PowerEntry
	ACCESS	not-accessible
	STATUS	mandatory
	DESCRIPTION
		"A table containing Power information."
	::= { hwEnclosure1 7 }

hwEnclosure01PowerEntry 	OBJECT-TYPE
	SYNTAX	HwEnclosure01PowerEntry
	ACCESS	not-accessible
	STATUS	mandatory
	DESCRIPTION
		"Information about a particular current power state."
	INDEX	{ hwEnclosure01PowerIndex }
	::= { hwEnclosure01PowerTable 1 }
	
HwEnclosure01PowerEntry ::= SEQUENCE { hwEnclosure01PowerIndex INTEGER,
			    hwEnclosure01PowerDesc OCTET STRING,
			    hwEnclosure01PowerState INTEGER }

hwEnclosure01PowerIndex	OBJECT-TYPE
	SYNTAX	INTEGER
	ACCESS 	read-only
	STATUS	mandatory
	DESCRIPTION
		"Power index, 1..#of powers."
	::= { hwEnclosure01PowerEntry 1 }		    
			    
hwEnclosure01PowerDesc	OBJECT-TYPE
	SYNTAX	OCTET STRING
	ACCESS 	read-only
	STATUS	mandatory
	DESCRIPTION
		"Power description."
	::= { hwEnclosure01PowerEntry 2 }
			    
hwEnclosure01PowerState	OBJECT-TYPE
	SYNTAX	INTEGER {
			 failed(0),
			 ok(1)
			}
	ACCESS 	read-only
	STATUS	mandatory
	DESCRIPTION
		"Power state 0:failed, 1:ok."
	::= { hwEnclosure01PowerEntry 3 }		
	

hwEnclosure01VolTable 	OBJECT-TYPE
	SYNTAX 	SEQUENCE OF HwEnclosure01VolEntry
	ACCESS	not-accessible
	STATUS	mandatory
	DESCRIPTION
		"A table containing voltage information."
	::= { hwEnclosure1 8 }

hwEnclosure01VolEntry 	OBJECT-TYPE
	SYNTAX	HwEnclosure01VolEntry
	ACCESS	not-accessible
	STATUS	mandatory
	DESCRIPTION
		"Information about a particular current voltage state."
	INDEX	{ hwEnclosure01VolIndex }
	::= { hwEnclosure01VolTable 1 }
	
HwEnclosure01VolEntry ::= SEQUENCE { hwEnclosure01VolIndex INTEGER,
			  hwEnclosure01VolDesc OCTET STRING,
			  hwEnclosure01VolValue INTEGER }

hwEnclosure01VolIndex	OBJECT-TYPE
	SYNTAX	INTEGER
	ACCESS 	read-only
	STATUS	mandatory
	DESCRIPTION
		"Voltage index, 1..#of voltages."
	::= { hwEnclosure01VolEntry 1 }		    

hwEnclosure01VolDesc	OBJECT-TYPE
	SYNTAX	OCTET STRING
	ACCESS 	read-only
	STATUS	mandatory
	DESCRIPTION
		"Voltage description."
	::= { hwEnclosure01VolEntry 2 }
			    
hwEnclosure01VolValue	OBJECT-TYPE
	SYNTAX	INTEGER
	ACCESS 	read-only
	STATUS	mandatory
	DESCRIPTION
		"Voltage value."
	::= { hwEnclosure01VolEntry 3 }


hwEnclosure01FanTable 	OBJECT-TYPE
	SYNTAX 	SEQUENCE OF HwEnclosure01FanEntry
	ACCESS	not-accessible
	STATUS	mandatory
	DESCRIPTION
		"A table containing Fan information."
	::= { hwEnclosure1 9 }

hwEnclosure01FanEntry 	OBJECT-TYPE
	SYNTAX	HwEnclosure01FanEntry
	ACCESS	not-accessible
	STATUS	mandatory
	DESCRIPTION
		"Information about a particular current fan state."
	INDEX	{ hwEnclosure01FanIndex }
	::= { hwEnclosure01FanTable 1 }
	
HwEnclosure01FanEntry ::= SEQUENCE { hwEnclosure01FanIndex INTEGER,
			  hwEnclosure01FanDesc OCTET STRING,
			  hwEnclosure01FanSpeed INTEGER }

hwEnclosure01FanIndex	OBJECT-TYPE
	SYNTAX	INTEGER
	ACCESS 	read-only
	STATUS	mandatory
	DESCRIPTION
		"Fan index, 1..#of fans."
	::= { hwEnclosure01FanEntry 1 }		    

hwEnclosure01FanDesc	OBJECT-TYPE
	SYNTAX	OCTET STRING
	ACCESS 	read-only
	STATUS	mandatory
	DESCRIPTION
		"Fan description."
	::= { hwEnclosure01FanEntry 2 }
			    
hwEnclosure01FanSpeed	OBJECT-TYPE
	SYNTAX	INTEGER
	ACCESS 	read-only
	STATUS	mandatory
	DESCRIPTION
		"Fan speed in RPM, e.g. 3200."
	::= { hwEnclosure01FanEntry 3 }

hwEnclosure01TempTable 	OBJECT-TYPE
	SYNTAX 	SEQUENCE OF HwEnclosure01TempEntry
	ACCESS	not-accessible
	STATUS	mandatory
	DESCRIPTION
		"A table containing temperature information."
	::= { hwEnclosure1 10 }

hwEnclosure01TempEntry 	OBJECT-TYPE
	SYNTAX	HwEnclosure01TempEntry
	ACCESS	not-accessible
	STATUS	mandatory
	DESCRIPTION
		"Information about a particular current temperature state."
	INDEX	{ hwEnclosure01TempIndex }
	::= { hwEnclosure01TempTable 1 }
	
HwEnclosure01TempEntry ::= SEQUENCE { hwEnclosure01TempIndex INTEGER,
			   hwEnclosure01TempDesc OCTET STRING,
			   hwEnclosure01TempValue INTEGER
			 }

hwEnclosure01TempIndex	OBJECT-TYPE
	SYNTAX	INTEGER
	ACCESS 	read-only
	STATUS	mandatory
	DESCRIPTION
		"Temperature index, 1..#of voltages."
	::= { hwEnclosure01TempEntry 1 }		    

hwEnclosure01TempDesc	OBJECT-TYPE
	SYNTAX	OCTET STRING
	ACCESS 	read-only
	STATUS	mandatory
	DESCRIPTION
		"Temperature description."
	::= { hwEnclosure01TempEntry 2 }
			    
hwEnclosure01TempValue	OBJECT-TYPE
	SYNTAX	INTEGER
	ACCESS 	read-only
	STATUS	mandatory
	DESCRIPTION
		"Temperature value."
	::= { hwEnclosure01TempEntry 3 }
	

-- Enclosure#02
hwEnclosure02Installed	OBJECT-TYPE
	SYNTAX	INTEGER
	ACCESS 	read-only
	STATUS	mandatory
	DESCRIPTION
		"Enclosure Installed?"
	::= { hwEnclosure2 1 }

hwEnclosure02Description	OBJECT-TYPE
	SYNTAX	OCTET STRING
	ACCESS 	read-only
	STATUS	mandatory
	DESCRIPTION
		"Enclosure description."
	::= { hwEnclosure2 2 }
	
hwEnclosure02NumberOfPower	OBJECT-TYPE
	SYNTAX	INTEGER
	ACCESS 	read-only
	STATUS	mandatory
	DESCRIPTION
		"# of power supply, e.g. 2."
	::= { hwEnclosure2 3 }	
	
hwEnclosure02NumberOfVol	OBJECT-TYPE
	SYNTAX	INTEGER
	ACCESS 	read-only
	STATUS	mandatory
	DESCRIPTION
		"# of Voltage, e.g. 2."
	::= { hwEnclosure2 4 }

hwEnclosure02NumberOfFan	OBJECT-TYPE
	SYNTAX	INTEGER
	ACCESS 	read-only
	STATUS	mandatory
	DESCRIPTION
		"# of Fan, e.g. 2."
	::= { hwEnclosure2 5 }		

hwEnclosure02NumberOfTemp	OBJECT-TYPE
	SYNTAX	INTEGER
	ACCESS 	read-only
	STATUS	mandatory
	DESCRIPTION
		"# of Temperature, e.g. 2."
	::= { hwEnclosure2 6 }	

hwEnclosure02PowerTable 	OBJECT-TYPE
	SYNTAX 	SEQUENCE OF HwEnclosure02PowerEntry
	ACCESS	not-accessible
	STATUS	mandatory
	DESCRIPTION
		"A table containing Power information."
	::= { hwEnclosure2 7 }

hwEnclosure02PowerEntry 	OBJECT-TYPE
	SYNTAX	HwEnclosure02PowerEntry
	ACCESS	not-accessible
	STATUS	mandatory
	DESCRIPTION
		"Information about a particular current power state."
	INDEX	{ hwEnclosure02PowerIndex }
	::= { hwEnclosure02PowerTable 1 }
	
HwEnclosure02PowerEntry ::= SEQUENCE { hwEnclosure02PowerIndex INTEGER,
			    hwEnclosure02PowerDesc OCTET STRING,
			    hwEnclosure02PowerState INTEGER }

hwEnclosure02PowerIndex	OBJECT-TYPE
	SYNTAX	INTEGER
	ACCESS 	read-only
	STATUS	mandatory
	DESCRIPTION
		"Power index, 1..#of powers."
	::= { hwEnclosure02PowerEntry 1 }		    
			    
hwEnclosure02PowerDesc	OBJECT-TYPE
	SYNTAX	OCTET STRING
	ACCESS 	read-only
	STATUS	mandatory
	DESCRIPTION
		"Power description."
	::= { hwEnclosure02PowerEntry 2 }
			    
hwEnclosure02PowerState	OBJECT-TYPE
	SYNTAX	INTEGER {
			 failed(0),
			 ok(1)
			}
	ACCESS 	read-only
	STATUS	mandatory
	DESCRIPTION
		"Power state 0:failed, 1:ok."
	::= { hwEnclosure02PowerEntry 3 }		
	
hwEnclosure02VolTable 	OBJECT-TYPE
	SYNTAX 	SEQUENCE OF HwEnclosure02VolEntry
	ACCESS	not-accessible
	STATUS	mandatory
	DESCRIPTION
		"A table containing voltage information."
	::= { hwEnclosure2 8 }

hwEnclosure02VolEntry 	OBJECT-TYPE
	SYNTAX	HwEnclosure02VolEntry
	ACCESS	not-accessible
	STATUS	mandatory
	DESCRIPTION
		"Information about a particular current voltage state."
	INDEX	{ hwEnclosure02VolIndex }
	::= { hwEnclosure02VolTable 1 }
	
HwEnclosure02VolEntry ::= SEQUENCE { hwEnclosure02VolIndex INTEGER,
			  hwEnclosure02VolDesc OCTET STRING,
			  hwEnclosure02VolValue INTEGER }

hwEnclosure02VolIndex	OBJECT-TYPE
	SYNTAX	INTEGER
	ACCESS 	read-only
	STATUS	mandatory
	DESCRIPTION
		"Voltage index, 1..#of voltages."
	::= { hwEnclosure02VolEntry 1 }		    

hwEnclosure02VolDesc	OBJECT-TYPE
	SYNTAX	OCTET STRING
	ACCESS 	read-only
	STATUS	mandatory
	DESCRIPTION
		"Voltage description."
	::= { hwEnclosure02VolEntry 2 }
			    
hwEnclosure02VolValue	OBJECT-TYPE
	SYNTAX	INTEGER
	ACCESS 	read-only
	STATUS	mandatory
	DESCRIPTION
		"Voltage value."
	::= { hwEnclosure02VolEntry 3 }

hwEnclosure02FanTable 	OBJECT-TYPE
	SYNTAX 	SEQUENCE OF HwEnclosure02FanEntry
	ACCESS	not-accessible
	STATUS	mandatory
	DESCRIPTION
		"A table containing Fan information."
	::= { hwEnclosure2 9 }

hwEnclosure02FanEntry 	OBJECT-TYPE
	SYNTAX	HwEnclosure02FanEntry
	ACCESS	not-accessible
	STATUS	mandatory
	DESCRIPTION
		"Information about a particular current fan state."
	INDEX	{ hwEnclosure02FanIndex }
	::= { hwEnclosure02FanTable 1 }
	
HwEnclosure02FanEntry ::= SEQUENCE { hwEnclosure02FanIndex INTEGER,
			  hwEnclosure02FanDesc OCTET STRING,
			  hwEnclosure02FanSpeed INTEGER }

hwEnclosure02FanIndex	OBJECT-TYPE
	SYNTAX	INTEGER
	ACCESS 	read-only
	STATUS	mandatory
	DESCRIPTION
		"Fan index, 1..#of fans."
	::= { hwEnclosure02FanEntry 1 }		    

hwEnclosure02FanDesc	OBJECT-TYPE
	SYNTAX	OCTET STRING
	ACCESS 	read-only
	STATUS	mandatory
	DESCRIPTION
		"Fan description."
	::= { hwEnclosure02FanEntry 2 }
			    
hwEnclosure02FanSpeed	OBJECT-TYPE
	SYNTAX	INTEGER
	ACCESS 	read-only
	STATUS	mandatory
	DESCRIPTION
		"Fan speed in RPM, e.g. 3200."
	::= { hwEnclosure02FanEntry 3 }

hwEnclosure02TempTable 	OBJECT-TYPE
	SYNTAX 	SEQUENCE OF HwEnclosure02TempEntry
	ACCESS	not-accessible
	STATUS	mandatory
	DESCRIPTION
		"A table containing temperature information."
	::= { hwEnclosure2 10 }

hwEnclosure02TempEntry 	OBJECT-TYPE
	SYNTAX	HwEnclosure02TempEntry
	ACCESS	not-accessible
	STATUS	mandatory
	DESCRIPTION
		"Information about a particular current temperature state."
	INDEX	{ hwEnclosure02TempIndex }
	::= { hwEnclosure02TempTable 1 }
	
HwEnclosure02TempEntry ::= SEQUENCE { hwEnclosure02TempIndex INTEGER,
			   hwEnclosure02TempDesc OCTET STRING,
			   hwEnclosure02TempValue INTEGER
			 }

hwEnclosure02TempIndex	OBJECT-TYPE
	SYNTAX	INTEGER
	ACCESS 	read-only
	STATUS	mandatory
	DESCRIPTION
		"Temperature index, 1..#of voltages."
	::= { hwEnclosure02TempEntry 1 }		    

hwEnclosure02TempDesc	OBJECT-TYPE
	SYNTAX	OCTET STRING
	ACCESS 	read-only
	STATUS	mandatory
	DESCRIPTION
		"Temperature description."
	::= { hwEnclosure02TempEntry 2 }
			    
hwEnclosure02TempValue	OBJECT-TYPE
	SYNTAX	INTEGER
	ACCESS 	read-only
	STATUS	mandatory
	DESCRIPTION
		"Temperature value."
	::= { hwEnclosure02TempEntry 3 }




-- Enclosure#03
hwEnclosure03Installed	OBJECT-TYPE
	SYNTAX	INTEGER
	ACCESS 	read-only
	STATUS	mandatory
	DESCRIPTION
		"Enclosure Installed?"
	::= { hwEnclosure3 1 }

hwEnclosure03Description	OBJECT-TYPE
	SYNTAX	OCTET STRING
	ACCESS 	read-only
	STATUS	mandatory
	DESCRIPTION
		"Enclosure description."
	::= { hwEnclosure3 2 }
	
hwEnclosure03NumberOfPower	OBJECT-TYPE
	SYNTAX	INTEGER
	ACCESS 	read-only
	STATUS	mandatory
	DESCRIPTION
		"# of power supply, e.g. 2."
	::= { hwEnclosure3 3 }	
	
hwEnclosure03NumberOfVol	OBJECT-TYPE
	SYNTAX	INTEGER
	ACCESS 	read-only
	STATUS	mandatory
	DESCRIPTION
		"# of Voltage, e.g. 2."
	::= { hwEnclosure3 4 }

hwEnclosure03NumberOfFan	OBJECT-TYPE
	SYNTAX	INTEGER
	ACCESS 	read-only
	STATUS	mandatory
	DESCRIPTION
		"# of Fan, e.g. 2."
	::= { hwEnclosure3 5 }		

hwEnclosure03NumberOfTemp	OBJECT-TYPE
	SYNTAX	INTEGER
	ACCESS 	read-only
	STATUS	mandatory
	DESCRIPTION
		"# of Temperature, e.g. 2."
	::= { hwEnclosure3 6 }	

hwEnclosure03PowerTable 	OBJECT-TYPE
	SYNTAX 	SEQUENCE OF HwEnclosure03PowerEntry
	ACCESS	not-accessible
	STATUS	mandatory
	DESCRIPTION
		"A table containing Power information."
	::= { hwEnclosure3 7 }

hwEnclosure03PowerEntry 	OBJECT-TYPE
	SYNTAX	HwEnclosure03PowerEntry
	ACCESS	not-accessible
	STATUS	mandatory
	DESCRIPTION
		"Information about a particular current power state."
	INDEX	{ hwEnclosure03PowerIndex }
	::= { hwEnclosure03PowerTable 1 }
	
HwEnclosure03PowerEntry ::= SEQUENCE { hwEnclosure03PowerIndex INTEGER,
			    hwEnclosure03PowerDesc OCTET STRING,
			    hwEnclosure03PowerState INTEGER }

hwEnclosure03PowerIndex	OBJECT-TYPE
	SYNTAX	INTEGER
	ACCESS 	read-only
	STATUS	mandatory
	DESCRIPTION
		"Power index, 1..#of powers."
	::= { hwEnclosure03PowerEntry 1 }		    
			    
hwEnclosure03PowerDesc	OBJECT-TYPE
	SYNTAX	OCTET STRING
	ACCESS 	read-only
	STATUS	mandatory
	DESCRIPTION
		"Power description."
	::= { hwEnclosure03PowerEntry 2 }
			    
hwEnclosure03PowerState	OBJECT-TYPE
	SYNTAX	INTEGER {
			 failed(0),
			 ok(1)
			}
	ACCESS 	read-only
	STATUS	mandatory
	DESCRIPTION
		"Power state 0:failed, 1:ok."
	::= { hwEnclosure03PowerEntry 3 }		
	

hwEnclosure03VolTable 	OBJECT-TYPE
	SYNTAX 	SEQUENCE OF HwEnclosure03VolEntry
	ACCESS	not-accessible
	STATUS	mandatory
	DESCRIPTION
		"A table containing voltage information."
	::= { hwEnclosure3 8 }

hwEnclosure03VolEntry 	OBJECT-TYPE
	SYNTAX	HwEnclosure03VolEntry
	ACCESS	not-accessible
	STATUS	mandatory
	DESCRIPTION
		"Information about a particular current voltage state."
	INDEX	{ hwEnclosure03VolIndex }
	::= { hwEnclosure03VolTable 1 }
	
HwEnclosure03VolEntry ::= SEQUENCE { hwEnclosure03VolIndex INTEGER,
			  hwEnclosure03VolDesc OCTET STRING,
			  hwEnclosure03VolValue INTEGER }

hwEnclosure03VolIndex	OBJECT-TYPE
	SYNTAX	INTEGER
	ACCESS 	read-only
	STATUS	mandatory
	DESCRIPTION
		"Voltage index, 1..#of voltages."
	::= { hwEnclosure03VolEntry 1 }		    

hwEnclosure03VolDesc	OBJECT-TYPE
	SYNTAX	OCTET STRING
	ACCESS 	read-only
	STATUS	mandatory
	DESCRIPTION
		"Voltage description."
	::= { hwEnclosure03VolEntry 2 }
			    
hwEnclosure03VolValue	OBJECT-TYPE
	SYNTAX	INTEGER
	ACCESS 	read-only
	STATUS	mandatory
	DESCRIPTION
		"Voltage value."
	::= { hwEnclosure03VolEntry 3 }

hwEnclosure03FanTable 	OBJECT-TYPE
	SYNTAX 	SEQUENCE OF HwEnclosure03FanEntry
	ACCESS	not-accessible
	STATUS	mandatory
	DESCRIPTION
		"A table containing Fan information."
	::= { hwEnclosure3 9 }

hwEnclosure03FanEntry 	OBJECT-TYPE
	SYNTAX	HwEnclosure03FanEntry
	ACCESS	not-accessible
	STATUS	mandatory
	DESCRIPTION
		"Information about a particular current fan state."
	INDEX	{ hwEnclosure03FanIndex }
	::= { hwEnclosure03FanTable 1 }
	
HwEnclosure03FanEntry ::= SEQUENCE { hwEnclosure03FanIndex INTEGER,
			  hwEnclosure03FanDesc OCTET STRING,
			  hwEnclosure03FanSpeed INTEGER }

hwEnclosure03FanIndex	OBJECT-TYPE
	SYNTAX	INTEGER
	ACCESS 	read-only
	STATUS	mandatory
	DESCRIPTION
		"Fan index, 1..#of fans."
	::= { hwEnclosure03FanEntry 1 }		    

hwEnclosure03FanDesc	OBJECT-TYPE
	SYNTAX	OCTET STRING
	ACCESS 	read-only
	STATUS	mandatory
	DESCRIPTION
		"Fan description."
	::= { hwEnclosure03FanEntry 2 }
			    
hwEnclosure03FanSpeed	OBJECT-TYPE
	SYNTAX	INTEGER
	ACCESS 	read-only
	STATUS	mandatory
	DESCRIPTION
		"Fan speed in RPM, e.g. 3200."
	::= { hwEnclosure03FanEntry 3 }

hwEnclosure03TempTable 	OBJECT-TYPE
	SYNTAX 	SEQUENCE OF HwEnclosure03TempEntry
	ACCESS	not-accessible
	STATUS	mandatory
	DESCRIPTION
		"A table containing temperature information."
	::= { hwEnclosure3 10 }

hwEnclosure03TempEntry 	OBJECT-TYPE
	SYNTAX	HwEnclosure03TempEntry
	ACCESS	not-accessible
	STATUS	mandatory
	DESCRIPTION
		"Information about a particular current temperature state."
	INDEX	{ hwEnclosure03TempIndex }
	::= { hwEnclosure03TempTable 1 }
	
HwEnclosure03TempEntry ::= SEQUENCE { hwEnclosure03TempIndex INTEGER,
			   hwEnclosure03TempDesc OCTET STRING,
			   hwEnclosure03TempValue INTEGER
			 }

hwEnclosure03TempIndex	OBJECT-TYPE
	SYNTAX	INTEGER
	ACCESS 	read-only
	STATUS	mandatory
	DESCRIPTION
		"Temperature index, 1..#of voltages."
	::= { hwEnclosure03TempEntry 1 }		    

hwEnclosure03TempDesc	OBJECT-TYPE
	SYNTAX	OCTET STRING
	ACCESS 	read-only
	STATUS	mandatory
	DESCRIPTION
		"Temperature description."
	::= { hwEnclosure03TempEntry 2 }
			    
hwEnclosure03TempValue	OBJECT-TYPE
	SYNTAX	INTEGER
	ACCESS 	read-only
	STATUS	mandatory
	DESCRIPTION
		"Temperature value."
	::= { hwEnclosure03TempEntry 3 }



-- Enclosure#04
hwEnclosure04Installed	OBJECT-TYPE
	SYNTAX	INTEGER
	ACCESS 	read-only
	STATUS	mandatory
	DESCRIPTION
		"Enclosure Installed?"
	::= { hwEnclosure4 1 }

hwEnclosure04Description	OBJECT-TYPE
	SYNTAX	OCTET STRING
	ACCESS 	read-only
	STATUS	mandatory
	DESCRIPTION
		"Enclosure description."
	::= { hwEnclosure4 2 }
	
hwEnclosure04NumberOfPower	OBJECT-TYPE
	SYNTAX	INTEGER
	ACCESS 	read-only
	STATUS	mandatory
	DESCRIPTION
		"# of power supply, e.g. 2."
	::= { hwEnclosure4 3 }	
	
hwEnclosure04NumberOfVol	OBJECT-TYPE
	SYNTAX	INTEGER
	ACCESS 	read-only
	STATUS	mandatory
	DESCRIPTION
		"# of Voltage, e.g. 2."
	::= { hwEnclosure4 4 }

hwEnclosure04NumberOfFan	OBJECT-TYPE
	SYNTAX	INTEGER
	ACCESS 	read-only
	STATUS	mandatory
	DESCRIPTION
		"# of Fan, e.g. 2."
	::= { hwEnclosure4 5 }		

hwEnclosure04NumberOfTemp	OBJECT-TYPE
	SYNTAX	INTEGER
	ACCESS 	read-only
	STATUS	mandatory
	DESCRIPTION
		"# of Temperature, e.g. 2."
	::= { hwEnclosure4 6 }	

hwEnclosure04PowerTable 	OBJECT-TYPE
	SYNTAX 	SEQUENCE OF HwEnclosure04PowerEntry
	ACCESS	not-accessible
	STATUS	mandatory
	DESCRIPTION
		"A table containing Power information."
	::= { hwEnclosure4 7 }

hwEnclosure04PowerEntry 	OBJECT-TYPE
	SYNTAX	HwEnclosure04PowerEntry
	ACCESS	not-accessible
	STATUS	mandatory
	DESCRIPTION
		"Information about a particular current power state."
	INDEX	{ hwEnclosure04PowerIndex }
	::= { hwEnclosure04PowerTable 1 }
	
HwEnclosure04PowerEntry ::= SEQUENCE { hwEnclosure04PowerIndex INTEGER,
			    hwEnclosure04PowerDesc OCTET STRING,
			    hwEnclosure04PowerState INTEGER }

hwEnclosure04PowerIndex	OBJECT-TYPE
	SYNTAX	INTEGER
	ACCESS 	read-only
	STATUS	mandatory
	DESCRIPTION
		"Power index, 1..#of powers."
	::= { hwEnclosure04PowerEntry 1 }		    
			    
hwEnclosure04PowerDesc	OBJECT-TYPE
	SYNTAX	OCTET STRING
	ACCESS 	read-only
	STATUS	mandatory
	DESCRIPTION
		"Power description."
	::= { hwEnclosure04PowerEntry 2 }
			    
hwEnclosure04PowerState	OBJECT-TYPE
	SYNTAX	INTEGER {
			 failed(0),
			 ok(1)
			}
	ACCESS 	read-only
	STATUS	mandatory
	DESCRIPTION
		"Power state 0:failed, 1:ok."
	::= { hwEnclosure04PowerEntry 3 }		
	

hwEnclosure04VolTable 	OBJECT-TYPE
	SYNTAX 	SEQUENCE OF HwEnclosure04VolEntry
	ACCESS	not-accessible
	STATUS	mandatory
	DESCRIPTION
		"A table containing voltage information."
	::= { hwEnclosure4 8 }

hwEnclosure04VolEntry 	OBJECT-TYPE
	SYNTAX	HwEnclosure04VolEntry
	ACCESS	not-accessible
	STATUS	mandatory
	DESCRIPTION
		"Information about a particular current voltage state."
	INDEX	{ hwEnclosure04VolIndex }
	::= { hwEnclosure04VolTable 1 }
	
HwEnclosure04VolEntry ::= SEQUENCE { hwEnclosure04VolIndex INTEGER,
			  hwEnclosure04VolDesc OCTET STRING,
			  hwEnclosure04VolValue INTEGER }

hwEnclosure04VolIndex	OBJECT-TYPE
	SYNTAX	INTEGER
	ACCESS 	read-only
	STATUS	mandatory
	DESCRIPTION
		"Voltage index, 1..#of voltages."
	::= { hwEnclosure04VolEntry 1 }		    

hwEnclosure04VolDesc	OBJECT-TYPE
	SYNTAX	OCTET STRING
	ACCESS 	read-only
	STATUS	mandatory
	DESCRIPTION
		"Voltage description."
	::= { hwEnclosure04VolEntry 2 }
			    
hwEnclosure04VolValue	OBJECT-TYPE
	SYNTAX	INTEGER
	ACCESS 	read-only
	STATUS	mandatory
	DESCRIPTION
		"Voltage value."
	::= { hwEnclosure04VolEntry 3 }

hwEnclosure04FanTable 	OBJECT-TYPE
	SYNTAX 	SEQUENCE OF HwEnclosure04FanEntry
	ACCESS	not-accessible
	STATUS	mandatory
	DESCRIPTION
		"A table containing Fan information."
	::= { hwEnclosure4 9 }

hwEnclosure04FanEntry 	OBJECT-TYPE
	SYNTAX	HwEnclosure04FanEntry
	ACCESS	not-accessible
	STATUS	mandatory
	DESCRIPTION
		"Information about a particular current fan state."
	INDEX	{ hwEnclosure04FanIndex }
	::= { hwEnclosure04FanTable 1 }
	
HwEnclosure04FanEntry ::= SEQUENCE { hwEnclosure04FanIndex INTEGER,
			  hwEnclosure04FanDesc OCTET STRING,
			  hwEnclosure04FanSpeed INTEGER }

hwEnclosure04FanIndex	OBJECT-TYPE
	SYNTAX	INTEGER
	ACCESS 	read-only
	STATUS	mandatory
	DESCRIPTION
		"Fan index, 1..#of fans."
	::= { hwEnclosure04FanEntry 1 }		    

hwEnclosure04FanDesc	OBJECT-TYPE
	SYNTAX	OCTET STRING
	ACCESS 	read-only
	STATUS	mandatory
	DESCRIPTION
		"Fan description."
	::= { hwEnclosure04FanEntry 2 }
			    
hwEnclosure04FanSpeed	OBJECT-TYPE
	SYNTAX	INTEGER
	ACCESS 	read-only
	STATUS	mandatory
	DESCRIPTION
		"Fan speed in RPM, e.g. 3200."
	::= { hwEnclosure04FanEntry 3 }

hwEnclosure04TempTable 	OBJECT-TYPE
	SYNTAX 	SEQUENCE OF HwEnclosure04TempEntry
	ACCESS	not-accessible
	STATUS	mandatory
	DESCRIPTION
		"A table containing temperature information."
	::= { hwEnclosure4 10 }

hwEnclosure04TempEntry 	OBJECT-TYPE
	SYNTAX	HwEnclosure04TempEntry
	ACCESS	not-accessible
	STATUS	mandatory
	DESCRIPTION
		"Information about a particular current temperature state."
	INDEX	{ hwEnclosure04TempIndex }
	::= { hwEnclosure04TempTable 1 }
	
HwEnclosure04TempEntry ::= SEQUENCE { hwEnclosure04TempIndex INTEGER,
			   hwEnclosure04TempDesc OCTET STRING,
			   hwEnclosure04TempValue INTEGER
			 }

hwEnclosure04TempIndex	OBJECT-TYPE
	SYNTAX	INTEGER
	ACCESS 	read-only
	STATUS	mandatory
	DESCRIPTION
		"Temperature index, 1..#of voltages."
	::= { hwEnclosure04TempEntry 1 }		    

hwEnclosure04TempDesc	OBJECT-TYPE
	SYNTAX	OCTET STRING
	ACCESS 	read-only
	STATUS	mandatory
	DESCRIPTION
		"Temperature description."
	::= { hwEnclosure04TempEntry 2 }
			    
hwEnclosure04TempValue	OBJECT-TYPE
	SYNTAX	INTEGER
	ACCESS 	read-only
	STATUS	mandatory
	DESCRIPTION
		"Temperature value."
	::= { hwEnclosure04TempEntry 3 }



-- Enclosure#05
hwEnclosure05Installed	OBJECT-TYPE
	SYNTAX	INTEGER
	ACCESS 	read-only
	STATUS	mandatory
	DESCRIPTION
		"Enclosure Installed?"
	::= { hwEnclosure5 1 }

hwEnclosure05Description	OBJECT-TYPE
	SYNTAX	OCTET STRING
	ACCESS 	read-only
	STATUS	mandatory
	DESCRIPTION
		"Enclosure description."
	::= { hwEnclosure5 2 }
	
hwEnclosure05NumberOfPower	OBJECT-TYPE
	SYNTAX	INTEGER
	ACCESS 	read-only
	STATUS	mandatory
	DESCRIPTION
		"# of power supply, e.g. 2."
	::= { hwEnclosure5 3 }	
	
hwEnclosure05NumberOfVol	OBJECT-TYPE
	SYNTAX	INTEGER
	ACCESS 	read-only
	STATUS	mandatory
	DESCRIPTION
		"# of Voltage, e.g. 2."
	::= { hwEnclosure5 4 }

hwEnclosure05NumberOfFan	OBJECT-TYPE
	SYNTAX	INTEGER
	ACCESS 	read-only
	STATUS	mandatory
	DESCRIPTION
		"# of Fan, e.g. 2."
	::= { hwEnclosure5 5 }		

hwEnclosure05NumberOfTemp	OBJECT-TYPE
	SYNTAX	INTEGER
	ACCESS 	read-only
	STATUS	mandatory
	DESCRIPTION
		"# of Temperature, e.g. 2."
	::= { hwEnclosure5 6 }	

hwEnclosure05PowerTable 	OBJECT-TYPE
	SYNTAX 	SEQUENCE OF HwEnclosure05PowerEntry
	ACCESS	not-accessible
	STATUS	mandatory
	DESCRIPTION
		"A table containing Power information."
	::= { hwEnclosure5 7 }

hwEnclosure05PowerEntry 	OBJECT-TYPE
	SYNTAX	HwEnclosure05PowerEntry
	ACCESS	not-accessible
	STATUS	mandatory
	DESCRIPTION
		"Information about a particular current power state."
	INDEX	{ hwEnclosure05PowerIndex }
	::= { hwEnclosure05PowerTable 1 }
	
HwEnclosure05PowerEntry ::= SEQUENCE { hwEnclosure05PowerIndex INTEGER,
			    hwEnclosure05PowerDesc OCTET STRING,
			    hwEnclosure05PowerState INTEGER }

hwEnclosure05PowerIndex	OBJECT-TYPE
	SYNTAX	INTEGER
	ACCESS 	read-only
	STATUS	mandatory
	DESCRIPTION
		"Power index, 1..#of powers."
	::= { hwEnclosure05PowerEntry 1 }		    
			    
hwEnclosure05PowerDesc	OBJECT-TYPE
	SYNTAX	OCTET STRING
	ACCESS 	read-only
	STATUS	mandatory
	DESCRIPTION
		"Power description."
	::= { hwEnclosure05PowerEntry 2 }
			    
hwEnclosure05PowerState	OBJECT-TYPE
	SYNTAX	INTEGER {
			 failed(0),
			 ok(1)
			}
	ACCESS 	read-only
	STATUS	mandatory
	DESCRIPTION
		"Power state 0:failed, 1:ok."
	::= { hwEnclosure05PowerEntry 3 }		
	

hwEnclosure05VolTable 	OBJECT-TYPE
	SYNTAX 	SEQUENCE OF HwEnclosure05VolEntry
	ACCESS	not-accessible
	STATUS	mandatory
	DESCRIPTION
		"A table containing voltage information."
	::= { hwEnclosure5 8 }

hwEnclosure05VolEntry 	OBJECT-TYPE
	SYNTAX	HwEnclosure05VolEntry
	ACCESS	not-accessible
	STATUS	mandatory
	DESCRIPTION
		"Information about a particular current voltage state."
	INDEX	{ hwEnclosure05VolIndex }
	::= { hwEnclosure05VolTable 1 }
	
HwEnclosure05VolEntry ::= SEQUENCE { hwEnclosure05VolIndex INTEGER,
			  hwEnclosure05VolDesc OCTET STRING,
			  hwEnclosure05VolValue INTEGER }

hwEnclosure05VolIndex	OBJECT-TYPE
	SYNTAX	INTEGER
	ACCESS 	read-only
	STATUS	mandatory
	DESCRIPTION
		"Voltage index, 1..#of voltages."
	::= { hwEnclosure05VolEntry 1 }		    

hwEnclosure05VolDesc	OBJECT-TYPE
	SYNTAX	OCTET STRING
	ACCESS 	read-only
	STATUS	mandatory
	DESCRIPTION
		"Voltage description."
	::= { hwEnclosure05VolEntry 2 }
			    
hwEnclosure05VolValue	OBJECT-TYPE
	SYNTAX	INTEGER
	ACCESS 	read-only
	STATUS	mandatory
	DESCRIPTION
		"Voltage value."
	::= { hwEnclosure05VolEntry 3 }

hwEnclosure05FanTable 	OBJECT-TYPE
	SYNTAX 	SEQUENCE OF HwEnclosure05FanEntry
	ACCESS	not-accessible
	STATUS	mandatory
	DESCRIPTION
		"A table containing Fan information."
	::= { hwEnclosure5 9 }

hwEnclosure05FanEntry 	OBJECT-TYPE
	SYNTAX	HwEnclosure05FanEntry
	ACCESS	not-accessible
	STATUS	mandatory
	DESCRIPTION
		"Information about a particular current fan state."
	INDEX	{ hwEnclosure05FanIndex }
	::= { hwEnclosure05FanTable 1 }
	
HwEnclosure05FanEntry ::= SEQUENCE { hwEnclosure05FanIndex INTEGER,
			  hwEnclosure05FanDesc OCTET STRING,
			  hwEnclosure05FanSpeed INTEGER }

hwEnclosure05FanIndex	OBJECT-TYPE
	SYNTAX	INTEGER
	ACCESS 	read-only
	STATUS	mandatory
	DESCRIPTION
		"Fan index, 1..#of fans."
	::= { hwEnclosure05FanEntry 1 }		    

hwEnclosure05FanDesc	OBJECT-TYPE
	SYNTAX	OCTET STRING
	ACCESS 	read-only
	STATUS	mandatory
	DESCRIPTION
		"Fan description."
	::= { hwEnclosure05FanEntry 2 }
			    
hwEnclosure05FanSpeed	OBJECT-TYPE
	SYNTAX	INTEGER
	ACCESS 	read-only
	STATUS	mandatory
	DESCRIPTION
		"Fan speed in RPM, e.g. 3200."
	::= { hwEnclosure05FanEntry 3 }

hwEnclosure05TempTable 	OBJECT-TYPE
	SYNTAX 	SEQUENCE OF HwEnclosure05TempEntry
	ACCESS	not-accessible
	STATUS	mandatory
	DESCRIPTION
		"A table containing temperature information."
	::= { hwEnclosure5 10 }

hwEnclosure05TempEntry 	OBJECT-TYPE
	SYNTAX	HwEnclosure05TempEntry
	ACCESS	not-accessible
	STATUS	mandatory
	DESCRIPTION
		"Information about a particular current temperature state."
	INDEX	{ hwEnclosure05TempIndex }
	::= { hwEnclosure05TempTable 1 }
	
HwEnclosure05TempEntry ::= SEQUENCE { hwEnclosure05TempIndex INTEGER,
			   hwEnclosure05TempDesc OCTET STRING,
			   hwEnclosure05TempValue INTEGER
			 }

hwEnclosure05TempIndex	OBJECT-TYPE
	SYNTAX	INTEGER
	ACCESS 	read-only
	STATUS	mandatory
	DESCRIPTION
		"Temperature index, 1..#of voltages."
	::= { hwEnclosure05TempEntry 1 }		    

hwEnclosure05TempDesc	OBJECT-TYPE
	SYNTAX	OCTET STRING
	ACCESS 	read-only
	STATUS	mandatory
	DESCRIPTION
		"Temperature description."
	::= { hwEnclosure05TempEntry 2 }
			    
hwEnclosure05TempValue	OBJECT-TYPE
	SYNTAX	INTEGER
	ACCESS 	read-only
	STATUS	mandatory
	DESCRIPTION
		"Temperature value."
	::= { hwEnclosure05TempEntry 3 }


-- Enclosure#06
hwEnclosure06Installed	OBJECT-TYPE
	SYNTAX	INTEGER
	ACCESS 	read-only
	STATUS	mandatory
	DESCRIPTION
		"Enclosure Installed?"
	::= { hwEnclosure6 1 }

hwEnclosure06Description	OBJECT-TYPE
	SYNTAX	OCTET STRING
	ACCESS 	read-only
	STATUS	mandatory
	DESCRIPTION
		"Enclosure description."
	::= { hwEnclosure6 2 }
	
hwEnclosure06NumberOfPower	OBJECT-TYPE
	SYNTAX	INTEGER
	ACCESS 	read-only
	STATUS	mandatory
	DESCRIPTION
		"# of power supply, e.g. 2."
	::= { hwEnclosure6 3 }	
	
hwEnclosure06NumberOfVol	OBJECT-TYPE
	SYNTAX	INTEGER
	ACCESS 	read-only
	STATUS	mandatory
	DESCRIPTION
		"# of Voltage, e.g. 2."
	::= { hwEnclosure6 4 }

hwEnclosure06NumberOfFan	OBJECT-TYPE
	SYNTAX	INTEGER
	ACCESS 	read-only
	STATUS	mandatory
	DESCRIPTION
		"# of Fan, e.g. 2."
	::= { hwEnclosure6 5 }		

hwEnclosure06NumberOfTemp	OBJECT-TYPE
	SYNTAX	INTEGER
	ACCESS 	read-only
	STATUS	mandatory
	DESCRIPTION
		"# of Temperature, e.g. 2."
	::= { hwEnclosure6 6 }	

hwEnclosure06PowerTable 	OBJECT-TYPE
	SYNTAX 	SEQUENCE OF HwEnclosure06PowerEntry
	ACCESS	not-accessible
	STATUS	mandatory
	DESCRIPTION
		"A table containing Power information."
	::= { hwEnclosure6 7 }

hwEnclosure06PowerEntry 	OBJECT-TYPE
	SYNTAX	HwEnclosure06PowerEntry
	ACCESS	not-accessible
	STATUS	mandatory
	DESCRIPTION
		"Information about a particular current power state."
	INDEX	{ hwEnclosure06PowerIndex }
	::= { hwEnclosure06PowerTable 1 }
	
HwEnclosure06PowerEntry ::= SEQUENCE { hwEnclosure06PowerIndex INTEGER,
			    hwEnclosure06PowerDesc OCTET STRING,
			    hwEnclosure06PowerState INTEGER }

hwEnclosure06PowerIndex	OBJECT-TYPE
	SYNTAX	INTEGER
	ACCESS 	read-only
	STATUS	mandatory
	DESCRIPTION
		"Power index, 1..#of powers."
	::= { hwEnclosure06PowerEntry 1 }		    
			    
hwEnclosure06PowerDesc	OBJECT-TYPE
	SYNTAX	OCTET STRING
	ACCESS 	read-only
	STATUS	mandatory
	DESCRIPTION
		"Power description."
	::= { hwEnclosure06PowerEntry 2 }
			    
hwEnclosure06PowerState	OBJECT-TYPE
	SYNTAX	INTEGER {
			 failed(0),
			 ok(1)
			}
	ACCESS 	read-only
	STATUS	mandatory
	DESCRIPTION
		"Power state 0:failed, 1:ok."
	::= { hwEnclosure06PowerEntry 3 }		
	
hwEnclosure06VolTable 	OBJECT-TYPE
	SYNTAX 	SEQUENCE OF HwEnclosure06VolEntry
	ACCESS	not-accessible
	STATUS	mandatory
	DESCRIPTION
		"A table containing voltage information."
	::= { hwEnclosure6 8 }

hwEnclosure06VolEntry 	OBJECT-TYPE
	SYNTAX	HwEnclosure06VolEntry
	ACCESS	not-accessible
	STATUS	mandatory
	DESCRIPTION
		"Information about a particular current voltage state."
	INDEX	{ hwEnclosure06VolIndex }
	::= { hwEnclosure06VolTable 1 }
	
HwEnclosure06VolEntry ::= SEQUENCE { hwEnclosure06VolIndex INTEGER,
			  hwEnclosure06VolDesc OCTET STRING,
			  hwEnclosure06VolValue INTEGER }

hwEnclosure06VolIndex	OBJECT-TYPE
	SYNTAX	INTEGER
	ACCESS 	read-only
	STATUS	mandatory
	DESCRIPTION
		"Voltage index, 1..#of voltages."
	::= { hwEnclosure06VolEntry 1 }		    

hwEnclosure06VolDesc	OBJECT-TYPE
	SYNTAX	OCTET STRING
	ACCESS 	read-only
	STATUS	mandatory
	DESCRIPTION
		"Voltage description."
	::= { hwEnclosure06VolEntry 2 }
			    
hwEnclosure06VolValue	OBJECT-TYPE
	SYNTAX	INTEGER
	ACCESS 	read-only
	STATUS	mandatory
	DESCRIPTION
		"Voltage value."
	::= { hwEnclosure06VolEntry 3 }

hwEnclosure06FanTable 	OBJECT-TYPE
	SYNTAX 	SEQUENCE OF HwEnclosure06FanEntry
	ACCESS	not-accessible
	STATUS	mandatory
	DESCRIPTION
		"A table containing Fan information."
	::= { hwEnclosure6 9 }

hwEnclosure06FanEntry 	OBJECT-TYPE
	SYNTAX	HwEnclosure06FanEntry
	ACCESS	not-accessible
	STATUS	mandatory
	DESCRIPTION
		"Information about a particular current fan state."
	INDEX	{ hwEnclosure06FanIndex }
	::= { hwEnclosure06FanTable 1 }
	
HwEnclosure06FanEntry ::= SEQUENCE { hwEnclosure06FanIndex INTEGER,
			  hwEnclosure06FanDesc OCTET STRING,
			  hwEnclosure06FanSpeed INTEGER }

hwEnclosure06FanIndex	OBJECT-TYPE
	SYNTAX	INTEGER
	ACCESS 	read-only
	STATUS	mandatory
	DESCRIPTION
		"Fan index, 1..#of fans."
	::= { hwEnclosure06FanEntry 1 }		    

hwEnclosure06FanDesc	OBJECT-TYPE
	SYNTAX	OCTET STRING
	ACCESS 	read-only
	STATUS	mandatory
	DESCRIPTION
		"Fan description."
	::= { hwEnclosure06FanEntry 2 }
			    
hwEnclosure06FanSpeed	OBJECT-TYPE
	SYNTAX	INTEGER
	ACCESS 	read-only
	STATUS	mandatory
	DESCRIPTION
		"Fan speed in RPM, e.g. 3200."
	::= { hwEnclosure06FanEntry 3 }

hwEnclosure06TempTable 	OBJECT-TYPE
	SYNTAX 	SEQUENCE OF HwEnclosure06TempEntry
	ACCESS	not-accessible
	STATUS	mandatory
	DESCRIPTION
		"A table containing temperature information."
	::= { hwEnclosure6 10 }

hwEnclosure06TempEntry 	OBJECT-TYPE
	SYNTAX	HwEnclosure06TempEntry
	ACCESS	not-accessible
	STATUS	mandatory
	DESCRIPTION
		"Information about a particular current temperature state."
	INDEX	{ hwEnclosure06TempIndex }
	::= { hwEnclosure06TempTable 1 }
	
HwEnclosure06TempEntry ::= SEQUENCE { hwEnclosure06TempIndex INTEGER,
			   hwEnclosure06TempDesc OCTET STRING,
			   hwEnclosure06TempValue INTEGER
			 }

hwEnclosure06TempIndex	OBJECT-TYPE
	SYNTAX	INTEGER
	ACCESS 	read-only
	STATUS	mandatory
	DESCRIPTION
		"Temperature index, 1..#of voltages."
	::= { hwEnclosure06TempEntry 1 }		    

hwEnclosure06TempDesc	OBJECT-TYPE
	SYNTAX	OCTET STRING
	ACCESS 	read-only
	STATUS	mandatory
	DESCRIPTION
		"Temperature description."
	::= { hwEnclosure06TempEntry 2 }
			    
hwEnclosure06TempValue	OBJECT-TYPE
	SYNTAX	INTEGER
	ACCESS 	read-only
	STATUS	mandatory
	DESCRIPTION
		"Temperature value."
	::= { hwEnclosure06TempEntry 3 }


-- Enclosure#07
hwEnclosure07Installed	OBJECT-TYPE
	SYNTAX	INTEGER
	ACCESS 	read-only
	STATUS	mandatory
	DESCRIPTION
		"Enclosure Installed?"
	::= { hwEnclosure7 1 }

hwEnclosure07Description	OBJECT-TYPE
	SYNTAX	OCTET STRING
	ACCESS 	read-only
	STATUS	mandatory
	DESCRIPTION
		"Enclosure description."
	::= { hwEnclosure7 2 }
	
hwEnclosure07NumberOfPower	OBJECT-TYPE
	SYNTAX	INTEGER
	ACCESS 	read-only
	STATUS	mandatory
	DESCRIPTION
		"# of power supply, e.g. 2."
	::= { hwEnclosure7 3 }	
	
hwEnclosure07NumberOfVol	OBJECT-TYPE
	SYNTAX	INTEGER
	ACCESS 	read-only
	STATUS	mandatory
	DESCRIPTION
		"# of Voltage, e.g. 2."
	::= { hwEnclosure7 4 }

hwEnclosure07NumberOfFan	OBJECT-TYPE
	SYNTAX	INTEGER
	ACCESS 	read-only
	STATUS	mandatory
	DESCRIPTION
		"# of Fan, e.g. 2."
	::= { hwEnclosure7 5 }		

hwEnclosure07NumberOfTemp	OBJECT-TYPE
	SYNTAX	INTEGER
	ACCESS 	read-only
	STATUS	mandatory
	DESCRIPTION
		"# of Temperature, e.g. 2."
	::= { hwEnclosure7 6 }	

hwEnclosure07PowerTable 	OBJECT-TYPE
	SYNTAX 	SEQUENCE OF HwEnclosure07PowerEntry
	ACCESS	not-accessible
	STATUS	mandatory
	DESCRIPTION
		"A table containing Power information."
	::= { hwEnclosure7 7 }

hwEnclosure07PowerEntry 	OBJECT-TYPE
	SYNTAX	HwEnclosure07PowerEntry
	ACCESS	not-accessible
	STATUS	mandatory
	DESCRIPTION
		"Information about a particular current power state."
	INDEX	{ hwEnclosure07PowerIndex }
	::= { hwEnclosure07PowerTable 1 }
	
HwEnclosure07PowerEntry ::= SEQUENCE { hwEnclosure07PowerIndex INTEGER,
			    hwEnclosure07PowerDesc OCTET STRING,
			    hwEnclosure07PowerState INTEGER }

hwEnclosure07PowerIndex	OBJECT-TYPE
	SYNTAX	INTEGER
	ACCESS 	read-only
	STATUS	mandatory
	DESCRIPTION
		"Power index, 1..#of powers."
	::= { hwEnclosure07PowerEntry 1 }		    
			    
hwEnclosure07PowerDesc	OBJECT-TYPE
	SYNTAX	OCTET STRING
	ACCESS 	read-only
	STATUS	mandatory
	DESCRIPTION
		"Power description."
	::= { hwEnclosure07PowerEntry 2 }
			    
hwEnclosure07PowerState	OBJECT-TYPE
	SYNTAX	INTEGER {
			 failed(0),
			 ok(1)
			}
	ACCESS 	read-only
	STATUS	mandatory
	DESCRIPTION
		"Power state 0:failed, 1:ok."
	::= { hwEnclosure07PowerEntry 3 }		
	
hwEnclosure07VolTable 	OBJECT-TYPE
	SYNTAX 	SEQUENCE OF HwEnclosure07VolEntry
	ACCESS	not-accessible
	STATUS	mandatory
	DESCRIPTION
		"A table containing voltage information."
	::= { hwEnclosure7 8 }

hwEnclosure07VolEntry 	OBJECT-TYPE
	SYNTAX	HwEnclosure07VolEntry
	ACCESS	not-accessible
	STATUS	mandatory
	DESCRIPTION
		"Information about a particular current voltage state."
	INDEX	{ hwEnclosure07VolIndex }
	::= { hwEnclosure07VolTable 1 }
	
HwEnclosure07VolEntry ::= SEQUENCE { hwEnclosure07VolIndex INTEGER,
			  hwEnclosure07VolDesc OCTET STRING,
			  hwEnclosure07VolValue INTEGER }

hwEnclosure07VolIndex	OBJECT-TYPE
	SYNTAX	INTEGER
	ACCESS 	read-only
	STATUS	mandatory
	DESCRIPTION
		"Voltage index, 1..#of voltages."
	::= { hwEnclosure07VolEntry 1 }		    

hwEnclosure07VolDesc	OBJECT-TYPE
	SYNTAX	OCTET STRING
	ACCESS 	read-only
	STATUS	mandatory
	DESCRIPTION
		"Voltage description."
	::= { hwEnclosure07VolEntry 2 }
			    
hwEnclosure07VolValue	OBJECT-TYPE
	SYNTAX	INTEGER
	ACCESS 	read-only
	STATUS	mandatory
	DESCRIPTION
		"Voltage value."
	::= { hwEnclosure07VolEntry 3 }

hwEnclosure07FanTable 	OBJECT-TYPE
	SYNTAX 	SEQUENCE OF HwEnclosure07FanEntry
	ACCESS	not-accessible
	STATUS	mandatory
	DESCRIPTION
		"A table containing Fan information."
	::= { hwEnclosure7 9 }

hwEnclosure07FanEntry 	OBJECT-TYPE
	SYNTAX	HwEnclosure07FanEntry
	ACCESS	not-accessible
	STATUS	mandatory
	DESCRIPTION
		"Information about a particular current fan state."
	INDEX	{ hwEnclosure07FanIndex }
	::= { hwEnclosure07FanTable 1 }
	
HwEnclosure07FanEntry ::= SEQUENCE { hwEnclosure07FanIndex INTEGER,
			  hwEnclosure07FanDesc OCTET STRING,
			  hwEnclosure07FanSpeed INTEGER }

hwEnclosure07FanIndex	OBJECT-TYPE
	SYNTAX	INTEGER
	ACCESS 	read-only
	STATUS	mandatory
	DESCRIPTION
		"Fan index, 1..#of fans."
	::= { hwEnclosure07FanEntry 1 }		    

hwEnclosure07FanDesc	OBJECT-TYPE
	SYNTAX	OCTET STRING
	ACCESS 	read-only
	STATUS	mandatory
	DESCRIPTION
		"Fan description."
	::= { hwEnclosure07FanEntry 2 }
			    
hwEnclosure07FanSpeed	OBJECT-TYPE
	SYNTAX	INTEGER
	ACCESS 	read-only
	STATUS	mandatory
	DESCRIPTION
		"Fan speed in RPM, e.g. 3200."
	::= { hwEnclosure07FanEntry 3 }

hwEnclosure07TempTable 	OBJECT-TYPE
	SYNTAX 	SEQUENCE OF HwEnclosure07TempEntry
	ACCESS	not-accessible
	STATUS	mandatory
	DESCRIPTION
		"A table containing temperature information."
	::= { hwEnclosure7 10 }

hwEnclosure07TempEntry 	OBJECT-TYPE
	SYNTAX	HwEnclosure07TempEntry
	ACCESS	not-accessible
	STATUS	mandatory
	DESCRIPTION
		"Information about a particular current temperature state."
	INDEX	{ hwEnclosure07TempIndex }
	::= { hwEnclosure07TempTable 1 }
	
HwEnclosure07TempEntry ::= SEQUENCE { hwEnclosure07TempIndex INTEGER,
			   hwEnclosure07TempDesc OCTET STRING,
			   hwEnclosure07TempValue INTEGER
			 }

hwEnclosure07TempIndex	OBJECT-TYPE
	SYNTAX	INTEGER
	ACCESS 	read-only
	STATUS	mandatory
	DESCRIPTION
		"Temperature index, 1..#of voltages."
	::= { hwEnclosure07TempEntry 1 }		    

hwEnclosure07TempDesc	OBJECT-TYPE
	SYNTAX	OCTET STRING
	ACCESS 	read-only
	STATUS	mandatory
	DESCRIPTION
		"Temperature description."
	::= { hwEnclosure07TempEntry 2 }
			    
hwEnclosure07TempValue	OBJECT-TYPE
	SYNTAX	INTEGER
	ACCESS 	read-only
	STATUS	mandatory
	DESCRIPTION
		"Temperature value."
	::= { hwEnclosure07TempEntry 3 }


-- Enclosure#08
hwEnclosure08Installed	OBJECT-TYPE
	SYNTAX	INTEGER
	ACCESS 	read-only
	STATUS	mandatory
	DESCRIPTION
		"Enclosure Installed?"
	::= { hwEnclosure8 1 }

hwEnclosure08Description	OBJECT-TYPE
	SYNTAX	OCTET STRING
	ACCESS 	read-only
	STATUS	mandatory
	DESCRIPTION
		"Enclosure description."
	::= { hwEnclosure8 2 }
	
hwEnclosure08NumberOfPower	OBJECT-TYPE
	SYNTAX	INTEGER
	ACCESS 	read-only
	STATUS	mandatory
	DESCRIPTION
		"# of power supply, e.g. 2."
	::= { hwEnclosure8 3 }	
	
hwEnclosure08NumberOfVol	OBJECT-TYPE
	SYNTAX	INTEGER
	ACCESS 	read-only
	STATUS	mandatory
	DESCRIPTION
		"# of Voltage, e.g. 2."
	::= { hwEnclosure8 4 }

hwEnclosure08NumberOfFan	OBJECT-TYPE
	SYNTAX	INTEGER
	ACCESS 	read-only
	STATUS	mandatory
	DESCRIPTION
		"# of Fan, e.g. 2."
	::= { hwEnclosure8 5 }		

hwEnclosure08NumberOfTemp	OBJECT-TYPE
	SYNTAX	INTEGER
	ACCESS 	read-only
	STATUS	mandatory
	DESCRIPTION
		"# of Temperature, e.g. 2."
	::= { hwEnclosure8 6 }	

hwEnclosure08PowerTable 	OBJECT-TYPE
	SYNTAX 	SEQUENCE OF HwEnclosure08PowerEntry
	ACCESS	not-accessible
	STATUS	mandatory
	DESCRIPTION
		"A table containing Power information."
	::= { hwEnclosure8 7 }

hwEnclosure08PowerEntry 	OBJECT-TYPE
	SYNTAX	HwEnclosure08PowerEntry
	ACCESS	not-accessible
	STATUS	mandatory
	DESCRIPTION
		"Information about a particular current power state."
	INDEX	{ hwEnclosure08PowerIndex }
	::= { hwEnclosure08PowerTable 1 }
	
HwEnclosure08PowerEntry ::= SEQUENCE { hwEnclosure08PowerIndex INTEGER,
			    hwEnclosure08PowerDesc OCTET STRING,
			    hwEnclosure08PowerState INTEGER }

hwEnclosure08PowerIndex	OBJECT-TYPE
	SYNTAX	INTEGER
	ACCESS 	read-only
	STATUS	mandatory
	DESCRIPTION
		"Power index, 1..#of powers."
	::= { hwEnclosure08PowerEntry 1 }		    
			    
hwEnclosure08PowerDesc	OBJECT-TYPE
	SYNTAX	OCTET STRING
	ACCESS 	read-only
	STATUS	mandatory
	DESCRIPTION
		"Power description."
	::= { hwEnclosure08PowerEntry 2 }
			    
hwEnclosure08PowerState	OBJECT-TYPE
	SYNTAX	INTEGER {
			 failed(0),
			 ok(1)
			}
	ACCESS 	read-only
	STATUS	mandatory
	DESCRIPTION
		"Power state 0:failed, 1:ok."
	::= { hwEnclosure08PowerEntry 3 }		
	
hwEnclosure08VolTable 	OBJECT-TYPE
	SYNTAX 	SEQUENCE OF HwEnclosure08VolEntry
	ACCESS	not-accessible
	STATUS	mandatory
	DESCRIPTION
		"A table containing voltage information."
	::= { hwEnclosure8 8 }

hwEnclosure08VolEntry 	OBJECT-TYPE
	SYNTAX	HwEnclosure08VolEntry
	ACCESS	not-accessible
	STATUS	mandatory
	DESCRIPTION
		"Information about a particular current voltage state."
	INDEX	{ hwEnclosure08VolIndex }
	::= { hwEnclosure08VolTable 1 }
	
HwEnclosure08VolEntry ::= SEQUENCE { hwEnclosure08VolIndex INTEGER,
			  hwEnclosure08VolDesc OCTET STRING,
			  hwEnclosure08VolValue INTEGER }

hwEnclosure08VolIndex	OBJECT-TYPE
	SYNTAX	INTEGER
	ACCESS 	read-only
	STATUS	mandatory
	DESCRIPTION
		"Voltage index, 1..#of voltages."
	::= { hwEnclosure08VolEntry 1 }		    

hwEnclosure08VolDesc	OBJECT-TYPE
	SYNTAX	OCTET STRING
	ACCESS 	read-only
	STATUS	mandatory
	DESCRIPTION
		"Voltage description."
	::= { hwEnclosure08VolEntry 2 }
			    
hwEnclosure08VolValue	OBJECT-TYPE
	SYNTAX	INTEGER
	ACCESS 	read-only
	STATUS	mandatory
	DESCRIPTION
		"Voltage value."
	::= { hwEnclosure08VolEntry 3 }

hwEnclosure08FanTable 	OBJECT-TYPE
	SYNTAX 	SEQUENCE OF HwEnclosure08FanEntry
	ACCESS	not-accessible
	STATUS	mandatory
	DESCRIPTION
		"A table containing Fan information."
	::= { hwEnclosure8 9 }

hwEnclosure08FanEntry 	OBJECT-TYPE
	SYNTAX	HwEnclosure08FanEntry
	ACCESS	not-accessible
	STATUS	mandatory
	DESCRIPTION
		"Information about a particular current fan state."
	INDEX	{ hwEnclosure08FanIndex }
	::= { hwEnclosure08FanTable 1 }
	
HwEnclosure08FanEntry ::= SEQUENCE { hwEnclosure08FanIndex INTEGER,
			  hwEnclosure08FanDesc OCTET STRING,
			  hwEnclosure08FanSpeed INTEGER }

hwEnclosure08FanIndex	OBJECT-TYPE
	SYNTAX	INTEGER
	ACCESS 	read-only
	STATUS	mandatory
	DESCRIPTION
		"Fan index, 1..#of fans."
	::= { hwEnclosure08FanEntry 1 }		    

hwEnclosure08FanDesc	OBJECT-TYPE
	SYNTAX	OCTET STRING
	ACCESS 	read-only
	STATUS	mandatory
	DESCRIPTION
		"Fan description."
	::= { hwEnclosure08FanEntry 2 }
			    
hwEnclosure08FanSpeed	OBJECT-TYPE
	SYNTAX	INTEGER
	ACCESS 	read-only
	STATUS	mandatory
	DESCRIPTION
		"Fan speed in RPM, e.g. 3200."
	::= { hwEnclosure08FanEntry 3 }

hwEnclosure08TempTable 	OBJECT-TYPE
	SYNTAX 	SEQUENCE OF HwEnclosure08TempEntry
	ACCESS	not-accessible
	STATUS	mandatory
	DESCRIPTION
		"A table containing temperature information."
	::= { hwEnclosure8 10 }

hwEnclosure08TempEntry 	OBJECT-TYPE
	SYNTAX	HwEnclosure08TempEntry
	ACCESS	not-accessible
	STATUS	mandatory
	DESCRIPTION
		"Information about a particular current temperature state."
	INDEX	{ hwEnclosure08TempIndex }
	::= { hwEnclosure08TempTable 1 }
	
HwEnclosure08TempEntry ::= SEQUENCE { hwEnclosure08TempIndex INTEGER,
			   hwEnclosure08TempDesc OCTET STRING,
			   hwEnclosure08TempValue INTEGER
			 }

hwEnclosure08TempIndex	OBJECT-TYPE
	SYNTAX	INTEGER
	ACCESS 	read-only
	STATUS	mandatory
	DESCRIPTION
		"Temperature index, 1..#of voltages."
	::= { hwEnclosure08TempEntry 1 }		    

hwEnclosure08TempDesc	OBJECT-TYPE
	SYNTAX	OCTET STRING
	ACCESS 	read-only
	STATUS	mandatory
	DESCRIPTION
		"Temperature description."
	::= { hwEnclosure08TempEntry 2 }
			    
hwEnclosure08TempValue	OBJECT-TYPE
	SYNTAX	INTEGER
	ACCESS 	read-only
	STATUS	mandatory
	DESCRIPTION
		"Temperature value."
	::= { hwEnclosure08TempEntry 3 }



-- definition of object types of HDD information

hddEnclosure1			OBJECT IDENTIFIER ::= { hddInformation 1 }
hddEnclosure2			OBJECT IDENTIFIER ::= { hddInformation 2 }
hddEnclosure3			OBJECT IDENTIFIER ::= { hddInformation 3 }
hddEnclosure4			OBJECT IDENTIFIER ::= { hddInformation 4 }
hddEnclosure5			OBJECT IDENTIFIER ::= { hddInformation 5 }
hddEnclosure6			OBJECT IDENTIFIER ::= { hddInformation 6 }
hddEnclosure7			OBJECT IDENTIFIER ::= { hddInformation 7 }
hddEnclosure8			OBJECT IDENTIFIER ::= { hddInformation 8 }


-- Enclosure#01 hdd info


hddEnclosure01Installed	OBJECT-TYPE
	SYNTAX	INTEGER
	ACCESS 	read-only
	STATUS	mandatory
	DESCRIPTION
		"Enclosure Installed?"
	::= { hddEnclosure1 1 }

hddEnclosure01Description	OBJECT-TYPE
	SYNTAX	OCTET STRING
	ACCESS 	read-only
	STATUS	mandatory
	DESCRIPTION
		"Enclosure description."
	::= { hddEnclosure1 2 }
	
hddEnclosure01NumberOfSlot	OBJECT-TYPE
	SYNTAX	INTEGER
	ACCESS 	read-only
	STATUS	mandatory
	DESCRIPTION
		"# of slot"
	::= { hddEnclosure1 3 }	

hddEnclosure01InfoTable 	OBJECT-TYPE
	SYNTAX 	SEQUENCE OF HddEnclosure01InfoEntry
	ACCESS	not-accessible
	STATUS	mandatory
	DESCRIPTION
		"A table containing HDD information."
	::= { hddEnclosure1 4 }

hddEnclosure01InfoEntry 	OBJECT-TYPE
	SYNTAX	HddEnclosure01InfoEntry
	ACCESS	not-accessible
	STATUS	mandatory
	DESCRIPTION
		"Information about a particular current HDD state."
	INDEX	{ hddEnclosure01Slots }
	::= { hddEnclosure01InfoTable 1 }
	
HddEnclosure01InfoEntry ::= SEQUENCE { hddEnclosure01Slots INTEGER,
			    hddEnclosure01Desc OCTET STRING,
			    hddEnclosure01Name OCTET STRING,
			    hddEnclosure01Serial OCTET STRING,
			    hddEnclosure01FirmVer OCTET STRING,
			    hddEnclosure01Capacity INTEGER,
			    hddEnclosure01Type INTEGER,
			    hddEnclosure01State OCTET STRING }

hddEnclosure01Slots	OBJECT-TYPE
	SYNTAX	INTEGER
	ACCESS 	read-only
	STATUS	mandatory
	DESCRIPTION
		"HDD slot#, 1..#of HDD."
	::= { hddEnclosure01InfoEntry 1 }

hddEnclosure01Desc		OBJECT-TYPE
	SYNTAX	OCTET STRING
	ACCESS 	read-only
	STATUS	mandatory
	DESCRIPTION
		"HDD description."
	::= { hddEnclosure01InfoEntry 2 }

hddEnclosure01Name		OBJECT-TYPE
	SYNTAX	OCTET STRING
	ACCESS 	read-only
	STATUS	mandatory
	DESCRIPTION
		"HDD name."
	::= { hddEnclosure01InfoEntry 3 }

hddEnclosure01Serial	OBJECT-TYPE
	SYNTAX	OCTET STRING
	ACCESS 	read-only
	STATUS	mandatory
	DESCRIPTION
		"HDD serial number."
	::= { hddEnclosure01InfoEntry 4 }

hddEnclosure01FirmVer	OBJECT-TYPE
	SYNTAX	OCTET STRING
	ACCESS 	read-only
	STATUS	mandatory
	DESCRIPTION
		"HDD firmware reversion."
	::= { hddEnclosure01InfoEntry 5 }

hddEnclosure01Capacity	OBJECT-TYPE
	SYNTAX	INTEGER
	ACCESS 	read-only
	STATUS	mandatory
	DESCRIPTION
		"HDD total capacity in mega byte."
	::= { hddEnclosure01InfoEntry 6 }

hddEnclosure01Type		OBJECT-TYPE
	SYNTAX	INTEGER {
			 sata(1),
			 sas(2)
			}
	ACCESS 	read-only
	STATUS	mandatory
	DESCRIPTION
		"HDD Type."
	::= { hddEnclosure01InfoEntry 7 }

hddEnclosure01State	OBJECT-TYPE
	SYNTAX	OCTET STRING
	ACCESS 	read-only
	STATUS	mandatory
	DESCRIPTION
		"HDD state."
	::= { hddEnclosure01InfoEntry 8 }
	
	
-- Enclosure#02 hdd info

hddEnclosure02Installed	OBJECT-TYPE
	SYNTAX	INTEGER
	ACCESS 	read-only
	STATUS	mandatory
	DESCRIPTION
		"Enclosure Installed?"
	::= { hddEnclosure2 1 }

hddEnclosure02Description	OBJECT-TYPE
	SYNTAX	OCTET STRING
	ACCESS 	read-only
	STATUS	mandatory
	DESCRIPTION
		"Enclosure description."
	::= { hddEnclosure2 2 }
	
hddEnclosure02NumberOfSlot	OBJECT-TYPE
	SYNTAX	INTEGER
	ACCESS 	read-only
	STATUS	mandatory
	DESCRIPTION
		"# of slot."
	::= { hddEnclosure2 3 }	

hddEnclosure02InfoTable 	OBJECT-TYPE
	SYNTAX 	SEQUENCE OF HddEnclosure02InfoEntry
	ACCESS	not-accessible
	STATUS	mandatory
	DESCRIPTION
		"A table containing HDD information."
	::= { hddEnclosure2 4 }

hddEnclosure02InfoEntry 	OBJECT-TYPE
	SYNTAX	HddEnclosure02InfoEntry
	ACCESS	not-accessible
	STATUS	mandatory
	DESCRIPTION
		"Information about a particular current HDD state."
	INDEX	{ hddEnclosure02Slots }
	::= { hddEnclosure02InfoTable 1 }
	
HddEnclosure02InfoEntry ::= SEQUENCE { hddEnclosure02Slots INTEGER,
			    hddEnclosure02Desc OCTET STRING,
			    hddEnclosure02Name OCTET STRING,
			    hddEnclosure02Serial OCTET STRING,
			    hddEnclosure02FirmVer OCTET STRING,
			    hddEnclosure02Capacity INTEGER,
			    hddEnclosure02Type INTEGER,
			    hddEnclosure02State OCTET STRING }

hddEnclosure02Slots	OBJECT-TYPE
	SYNTAX	INTEGER
	ACCESS 	read-only
	STATUS	mandatory
	DESCRIPTION
		"HDD slot#, 1..#of HDD."
	::= { hddEnclosure02InfoEntry 1 }

hddEnclosure02Desc		OBJECT-TYPE
	SYNTAX	OCTET STRING
	ACCESS 	read-only
	STATUS	mandatory
	DESCRIPTION
		"HDD name."
	::= { hddEnclosure02InfoEntry 2 }

hddEnclosure02Name		OBJECT-TYPE
	SYNTAX	OCTET STRING
	ACCESS 	read-only
	STATUS	mandatory
	DESCRIPTION
		"HDD name."
	::= { hddEnclosure02InfoEntry 3 }

hddEnclosure02Serial	OBJECT-TYPE
	SYNTAX	OCTET STRING
	ACCESS 	read-only
	STATUS	mandatory
	DESCRIPTION
		"HDD serial number."
	::= { hddEnclosure02InfoEntry 4 }

hddEnclosure02FirmVer	OBJECT-TYPE
	SYNTAX	OCTET STRING
	ACCESS 	read-only
	STATUS	mandatory
	DESCRIPTION
		"HDD firmware reversion."
	::= { hddEnclosure02InfoEntry 5 }

hddEnclosure02Capacity	OBJECT-TYPE
	SYNTAX	INTEGER
	ACCESS 	read-only
	STATUS	mandatory
	DESCRIPTION
		"HDD total capacity in mega byte."
	::= { hddEnclosure02InfoEntry 6 }

hddEnclosure02Type		OBJECT-TYPE	
	SYNTAX	INTEGER {
			 sata(1),
			 sas(2)
			}
	ACCESS 	read-only
	STATUS	mandatory
	DESCRIPTION
		"HDD Type."
	::= { hddEnclosure02InfoEntry 7 }

hddEnclosure02State	OBJECT-TYPE
	SYNTAX	OCTET STRING
	ACCESS 	read-only
	STATUS	mandatory
	DESCRIPTION
		"HDD state."
	::= { hddEnclosure02InfoEntry 8 }
	
	
	
-- Enclosure#03 hdd info
hddEnclosure03Installed	OBJECT-TYPE
	SYNTAX	INTEGER
	ACCESS 	read-only
	STATUS	mandatory
	DESCRIPTION
		"Enclosure Installed?"
	::= { hddEnclosure3 1 }

hddEnclosure03Description	OBJECT-TYPE
	SYNTAX	OCTET STRING
	ACCESS 	read-only
	STATUS	mandatory
	DESCRIPTION
		"Enclosure description."
	::= { hddEnclosure3 2 }
	
hddEnclosure03NumberOfSlot	OBJECT-TYPE
	SYNTAX	INTEGER
	ACCESS 	read-only
	STATUS	mandatory
	DESCRIPTION
		"# of slot."
	::= { hddEnclosure3 3 }	

hddEnclosure03InfoTable 	OBJECT-TYPE
	SYNTAX 	SEQUENCE OF HddEnclosure03InfoEntry
	ACCESS	not-accessible
	STATUS	mandatory
	DESCRIPTION
		"A table containing HDD information."
	::= { hddEnclosure3 4 }

hddEnclosure03InfoEntry 	OBJECT-TYPE
	SYNTAX	HddEnclosure03InfoEntry
	ACCESS	not-accessible
	STATUS	mandatory
	DESCRIPTION
		"Information about a particular current HDD state."
	INDEX	{ hddEnclosure03Slots }
	::= { hddEnclosure03InfoTable 1 }
	
HddEnclosure03InfoEntry ::= SEQUENCE { hddEnclosure03Slots INTEGER,
                            hddEnclosure03Desc OCTET STRING,
			    hddEnclosure03Name OCTET STRING,
			    hddEnclosure03Serial OCTET STRING,
			    hddEnclosure03FirmVer OCTET STRING,
			    hddEnclosure03Capacity INTEGER,
			    hddEnclosure03Type INTEGER,
			    hddEnclosure03State OCTET STRING }

hddEnclosure03Slots	OBJECT-TYPE
	SYNTAX	INTEGER
	ACCESS 	read-only
	STATUS	mandatory
	DESCRIPTION
		"HDD slot#, 1..#of HDD."
	::= { hddEnclosure03InfoEntry 1 }

hddEnclosure03Desc		OBJECT-TYPE
	SYNTAX	OCTET STRING
	ACCESS 	read-only
	STATUS	mandatory
	DESCRIPTION
		"HDD name."
	::= { hddEnclosure03InfoEntry 2 }

hddEnclosure03Name		OBJECT-TYPE
	SYNTAX	OCTET STRING
	ACCESS 	read-only
	STATUS	mandatory
	DESCRIPTION
		"HDD name."
	::= { hddEnclosure03InfoEntry 3 }

hddEnclosure03Serial	OBJECT-TYPE
	SYNTAX	OCTET STRING
	ACCESS 	read-only
	STATUS	mandatory
	DESCRIPTION
		"HDD serial number."
	::= { hddEnclosure03InfoEntry 4 }

hddEnclosure03FirmVer	OBJECT-TYPE
	SYNTAX	OCTET STRING
	ACCESS 	read-only
	STATUS	mandatory
	DESCRIPTION
		"HDD firmware reversion."
	::= { hddEnclosure03InfoEntry 5 }

hddEnclosure03Capacity	OBJECT-TYPE
	SYNTAX	INTEGER
	ACCESS 	read-only
	STATUS	mandatory
	DESCRIPTION
		"HDD total capacity in mega byte."
	::= { hddEnclosure03InfoEntry 6 }

hddEnclosure03Type		OBJECT-TYPE
	SYNTAX	INTEGER {
			 sata(1),
			 sas(2)
			}
	ACCESS 	read-only
	STATUS	mandatory
	DESCRIPTION
		"HDD Type."
	::= { hddEnclosure03InfoEntry 7 }

hddEnclosure03State	OBJECT-TYPE
	SYNTAX	OCTET STRING
	ACCESS 	read-only
	STATUS	mandatory
	DESCRIPTION
		"HDD state."
	::= { hddEnclosure03InfoEntry 8 }
	
	
-- Enclosure#04 hdd info
hddEnclosure04Installed	OBJECT-TYPE
	SYNTAX	INTEGER
	ACCESS 	read-only
	STATUS	mandatory
	DESCRIPTION
		"Enclosure Installed?"
	::= { hddEnclosure4 1 }

hddEnclosure04Description	OBJECT-TYPE
	SYNTAX	OCTET STRING
	ACCESS 	read-only
	STATUS	mandatory
	DESCRIPTION
		"Enclosure description."
	::= { hddEnclosure4 2 }
	
hddEnclosure04NumberOfSlot	OBJECT-TYPE
	SYNTAX	INTEGER
	ACCESS 	read-only
	STATUS	mandatory
	DESCRIPTION
		"# of slot."
	::= { hddEnclosure4 3 }	

hddEnclosure04InfoTable 	OBJECT-TYPE
	SYNTAX 	SEQUENCE OF HddEnclosure04InfoEntry
	ACCESS	not-accessible
	STATUS	mandatory
	DESCRIPTION
		"A table containing HDD information."
	::= { hddEnclosure4 4 }

hddEnclosure04InfoEntry 	OBJECT-TYPE
	SYNTAX	HddEnclosure04InfoEntry
	ACCESS	not-accessible
	STATUS	mandatory
	DESCRIPTION
		"Information about a particular current HDD state."
	INDEX	{ hddEnclosure04Slots }
	::= { hddEnclosure04InfoTable 1 }
	
HddEnclosure04InfoEntry ::= SEQUENCE { hddEnclosure04Slots INTEGER,
			    hddEnclosure04Desc OCTET STRING,
			    hddEnclosure04Name OCTET STRING,
			    hddEnclosure04Serial OCTET STRING,
			    hddEnclosure04FirmVer OCTET STRING,
			    hddEnclosure04Capacity INTEGER,
			    hddEnclosure04Type INTEGER,
			    hddEnclosure04State OCTET STRING }

hddEnclosure04Slots	OBJECT-TYPE
	SYNTAX	INTEGER
	ACCESS 	read-only
	STATUS	mandatory
	DESCRIPTION
		"HDD slot#, 1..#of HDD."
	::= { hddEnclosure04InfoEntry 1 }

hddEnclosure04Desc		OBJECT-TYPE
	SYNTAX	OCTET STRING
	ACCESS 	read-only
	STATUS	mandatory
	DESCRIPTION
		"HDD name."
	::= { hddEnclosure04InfoEntry 2 }

hddEnclosure04Name		OBJECT-TYPE
	SYNTAX	OCTET STRING
	ACCESS 	read-only
	STATUS	mandatory
	DESCRIPTION
		"HDD name."
	::= { hddEnclosure04InfoEntry 3 }

hddEnclosure04Serial	OBJECT-TYPE
	SYNTAX	OCTET STRING
	ACCESS 	read-only
	STATUS	mandatory
	DESCRIPTION
		"HDD serial number."
	::= { hddEnclosure04InfoEntry 4 }

hddEnclosure04FirmVer	OBJECT-TYPE
	SYNTAX	OCTET STRING
	ACCESS 	read-only
	STATUS	mandatory
	DESCRIPTION
		"HDD firmware reversion."
	::= { hddEnclosure04InfoEntry 5 }

hddEnclosure04Capacity	OBJECT-TYPE
	SYNTAX	INTEGER
	ACCESS 	read-only
	STATUS	mandatory
	DESCRIPTION
		"HDD total capacity in mega byte."
	::= { hddEnclosure04InfoEntry 6 }

hddEnclosure04Type		OBJECT-TYPE	
	SYNTAX	INTEGER {
			 sata(1),
			 sas(2)
			}
	ACCESS 	read-only
	STATUS	mandatory
	DESCRIPTION
		"HDD Type."
	::= { hddEnclosure04InfoEntry 7 }

hddEnclosure04State	OBJECT-TYPE
	SYNTAX	OCTET STRING
	ACCESS 	read-only
	STATUS	mandatory
	DESCRIPTION
		"HDD state."
	::= { hddEnclosure04InfoEntry 8 }
	
	
-- Enclosure#05 hdd info
hddEnclosure05Installed	OBJECT-TYPE
	SYNTAX	INTEGER
	ACCESS 	read-only
	STATUS	mandatory
	DESCRIPTION
		"Enclosure Installed?"
	::= { hddEnclosure5 1 }

hddEnclosure05Description	OBJECT-TYPE
	SYNTAX	OCTET STRING
	ACCESS 	read-only
	STATUS	mandatory
	DESCRIPTION
		"Enclosure description."
	::= { hddEnclosure5 2 }
	
hddEnclosure05NumberOfSlot	OBJECT-TYPE
	SYNTAX	INTEGER
	ACCESS 	read-only
	STATUS	mandatory
	DESCRIPTION
		"# of slot."
	::= { hddEnclosure5 3 }	


hddEnclosure05InfoTable 	OBJECT-TYPE
	SYNTAX 	SEQUENCE OF HddEnclosure05InfoEntry
	ACCESS	not-accessible
	STATUS	mandatory
	DESCRIPTION
		"A table containing HDD information."
	::= { hddEnclosure5 4 }

hddEnclosure05InfoEntry 	OBJECT-TYPE
	SYNTAX	HddEnclosure05InfoEntry
	ACCESS	not-accessible
	STATUS	mandatory
	DESCRIPTION
		"Information about a particular current HDD state."
	INDEX	{ hddEnclosure05Slots }
	::= { hddEnclosure05InfoTable 1 }
	
HddEnclosure05InfoEntry ::= SEQUENCE { hddEnclosure05Slots INTEGER,
			    hddEnclosure05Desc OCTET STRING,
			    hddEnclosure05Name OCTET STRING,
			    hddEnclosure05Serial OCTET STRING,
			    hddEnclosure05FirmVer OCTET STRING,
			    hddEnclosure05Capacity INTEGER,
			    hddEnclosure05Type INTEGER,
			    hddEnclosure05State OCTET STRING }

hddEnclosure05Slots	OBJECT-TYPE
	SYNTAX	INTEGER
	ACCESS 	read-only
	STATUS	mandatory
	DESCRIPTION
		"HDD slot#, 1..#of HDD."
	::= { hddEnclosure05InfoEntry 1 }

hddEnclosure05Desc		OBJECT-TYPE
	SYNTAX	OCTET STRING
	ACCESS 	read-only
	STATUS	mandatory
	DESCRIPTION
		"HDD name."
	::= { hddEnclosure05InfoEntry 2 }

hddEnclosure05Name		OBJECT-TYPE
	SYNTAX	OCTET STRING
	ACCESS 	read-only
	STATUS	mandatory
	DESCRIPTION
		"HDD name."
	::= { hddEnclosure05InfoEntry 3 }

hddEnclosure05Serial	OBJECT-TYPE
	SYNTAX	OCTET STRING
	ACCESS 	read-only
	STATUS	mandatory
	DESCRIPTION
		"HDD serial number."
	::= { hddEnclosure05InfoEntry 4 }

hddEnclosure05FirmVer	OBJECT-TYPE
	SYNTAX	OCTET STRING
	ACCESS 	read-only
	STATUS	mandatory
	DESCRIPTION
		"HDD firmware reversion."
	::= { hddEnclosure05InfoEntry 5 }

hddEnclosure05Capacity	OBJECT-TYPE
	SYNTAX	INTEGER
	ACCESS 	read-only
	STATUS	mandatory
	DESCRIPTION
		"HDD total capacity in mega byte."
	::= { hddEnclosure05InfoEntry 6 }

hddEnclosure05Type		OBJECT-TYPE	
	SYNTAX	INTEGER {
			 sata(1),
			 sas(2)
			}
	ACCESS 	read-only
	STATUS	mandatory
	DESCRIPTION
		"HDD Type."
	::= { hddEnclosure05InfoEntry 7 }

hddEnclosure05State	OBJECT-TYPE
	SYNTAX	OCTET STRING
	ACCESS 	read-only
	STATUS	mandatory
	DESCRIPTION
		"HDD state."
	::= { hddEnclosure05InfoEntry 8 }
	
-- Enclosure#06 hdd info
hddEnclosure06Installed	OBJECT-TYPE
	SYNTAX	INTEGER
	ACCESS 	read-only
	STATUS	mandatory
	DESCRIPTION
		"Enclosure Installed?"
	::= { hddEnclosure6 1 }

hddEnclosure06Description	OBJECT-TYPE
	SYNTAX	OCTET STRING
	ACCESS 	read-only
	STATUS	mandatory
	DESCRIPTION
		"Enclosure description."
	::= { hddEnclosure6 2 }
	
hddEnclosure06NumberOfSlot	OBJECT-TYPE
	SYNTAX	INTEGER
	ACCESS 	read-only
	STATUS	mandatory
	DESCRIPTION
		"# of power supply, e.g. 2."
	::= { hddEnclosure6 3 }	


hddEnclosure06InfoTable 	OBJECT-TYPE
	SYNTAX 	SEQUENCE OF HddEnclosure06InfoEntry
	ACCESS	not-accessible
	STATUS	mandatory
	DESCRIPTION
		"A table containing HDD information."
	::= { hddEnclosure6 4 }

hddEnclosure06InfoEntry 	OBJECT-TYPE
	SYNTAX	HddEnclosure06InfoEntry
	ACCESS	not-accessible
	STATUS	mandatory
	DESCRIPTION
		"Information about a particular current HDD state."
	INDEX	{ hddEnclosure06Slots }
	::= { hddEnclosure06InfoTable 1 }
	
HddEnclosure06InfoEntry ::= SEQUENCE { hddEnclosure06Slots INTEGER,
			    hddEnclosure06Desc OCTET STRING,
			    hddEnclosure06Name OCTET STRING,
			    hddEnclosure06Serial OCTET STRING,
			    hddEnclosure06FirmVer OCTET STRING,
			    hddEnclosure06Capacity INTEGER,
			    hddEnclosure06Type INTEGER,
			    hddEnclosure06State OCTET STRING }

hddEnclosure06Slots	OBJECT-TYPE
	SYNTAX	INTEGER
	ACCESS 	read-only
	STATUS	mandatory
	DESCRIPTION
		"HDD slot#, 1..#of HDD."
	::= { hddEnclosure06InfoEntry 1 }

hddEnclosure06Desc		OBJECT-TYPE
	SYNTAX	OCTET STRING
	ACCESS 	read-only
	STATUS	mandatory
	DESCRIPTION
		"HDD name."
	::= { hddEnclosure06InfoEntry 2 }	

hddEnclosure06Name		OBJECT-TYPE
	SYNTAX	OCTET STRING
	ACCESS 	read-only
	STATUS	mandatory
	DESCRIPTION
		"HDD name."
	::= { hddEnclosure06InfoEntry 3 }

hddEnclosure06Serial	OBJECT-TYPE
	SYNTAX	OCTET STRING
	ACCESS 	read-only
	STATUS	mandatory
	DESCRIPTION
		"HDD serial number."
	::= { hddEnclosure06InfoEntry 4 }

hddEnclosure06FirmVer	OBJECT-TYPE
	SYNTAX	OCTET STRING
	ACCESS 	read-only
	STATUS	mandatory
	DESCRIPTION
		"HDD firmware reversion."
	::= { hddEnclosure06InfoEntry 5 }

hddEnclosure06Capacity	OBJECT-TYPE
	SYNTAX	INTEGER
	ACCESS 	read-only
	STATUS	mandatory
	DESCRIPTION
		"HDD total capacity in mega byte."
	::= { hddEnclosure06InfoEntry 6 }

hddEnclosure06Type		OBJECT-TYPE
	SYNTAX	INTEGER {	
			 sata(1),
			 sas(2)
			}
	ACCESS 	read-only
	STATUS	mandatory
	DESCRIPTION
		"HDD Type."
	::= { hddEnclosure06InfoEntry 7 }

hddEnclosure06State	OBJECT-TYPE
	SYNTAX	OCTET STRING
	ACCESS 	read-only
	STATUS	mandatory
	DESCRIPTION
		"HDD state."
	::= { hddEnclosure06InfoEntry 8 }
	

-- Enclosure#07 hdd info
hddEnclosure07Installed	OBJECT-TYPE
	SYNTAX	INTEGER
	ACCESS 	read-only
	STATUS	mandatory
	DESCRIPTION
		"Enclosure Installed?"
	::= { hddEnclosure7 1 }

hddEnclosure07Description	OBJECT-TYPE
	SYNTAX	OCTET STRING
	ACCESS 	read-only
	STATUS	mandatory
	DESCRIPTION
		"Enclosure description."
	::= { hddEnclosure7 2 }
	
hddEnclosure07NumberOfSlot	OBJECT-TYPE
	SYNTAX	INTEGER
	ACCESS 	read-only
	STATUS	mandatory
	DESCRIPTION
		"# of power supply, e.g. 2."
	::= { hddEnclosure7 3 }	

hddEnclosure07InfoTable 	OBJECT-TYPE
	SYNTAX 	SEQUENCE OF HddEnclosure07InfoEntry
	ACCESS	not-accessible
	STATUS	mandatory
	DESCRIPTION
		"A table containing HDD information."
	::= { hddEnclosure7 4 }

hddEnclosure07InfoEntry 	OBJECT-TYPE
	SYNTAX	HddEnclosure07InfoEntry
	ACCESS	not-accessible
	STATUS	mandatory
	DESCRIPTION
		"Information about a particular current HDD state."
	INDEX	{ hddEnclosure07Slots }
	::= { hddEnclosure07InfoTable 1 }
	
HddEnclosure07InfoEntry ::= SEQUENCE { hddEnclosure07Slots INTEGER,
			    hddEnclosure07Desc OCTET STRING,
			    hddEnclosure07Name OCTET STRING,
			    hddEnclosure07Serial OCTET STRING,
			    hddEnclosure07FirmVer OCTET STRING,
			    hddEnclosure07Capacity INTEGER,
			    hddEnclosure07Type INTEGER,
			    hddEnclosure07State OCTET STRING }

hddEnclosure07Slots	OBJECT-TYPE
	SYNTAX	INTEGER
	ACCESS 	read-only
	STATUS	mandatory
	DESCRIPTION
		"HDD slot#, 1..#of HDD."
	::= { hddEnclosure07InfoEntry 1 }

hddEnclosure07Desc		OBJECT-TYPE
	SYNTAX	OCTET STRING
	ACCESS 	read-only
	STATUS	mandatory
	DESCRIPTION
		"HDD name."
	::= { hddEnclosure07InfoEntry 2 }

hddEnclosure07Name		OBJECT-TYPE
	SYNTAX	OCTET STRING
	ACCESS 	read-only
	STATUS	mandatory
	DESCRIPTION
		"HDD name."
	::= { hddEnclosure07InfoEntry 3 }

hddEnclosure07Serial	OBJECT-TYPE
	SYNTAX	OCTET STRING
	ACCESS 	read-only
	STATUS	mandatory
	DESCRIPTION
		"HDD serial number."
	::= { hddEnclosure07InfoEntry 4 }

hddEnclosure07FirmVer	OBJECT-TYPE
	SYNTAX	OCTET STRING
	ACCESS 	read-only
	STATUS	mandatory
	DESCRIPTION
		"HDD firmware reversion."
	::= { hddEnclosure07InfoEntry 5 }

hddEnclosure07Capacity	OBJECT-TYPE
	SYNTAX	INTEGER
	ACCESS 	read-only
	STATUS	mandatory
	DESCRIPTION
		"HDD total capacity in mega byte."
	::= { hddEnclosure07InfoEntry 6 }

hddEnclosure07Type		OBJECT-TYPE
	SYNTAX	INTEGER {
			 sata(1),
			 sas(2)
			}
	ACCESS 	read-only
	STATUS	mandatory
	DESCRIPTION
		"HDD Type."
	::= { hddEnclosure07InfoEntry 7 }

hddEnclosure07State	OBJECT-TYPE
	SYNTAX	OCTET STRING
	ACCESS 	read-only
	STATUS	mandatory
	DESCRIPTION
		"HDD state."
	::= { hddEnclosure07InfoEntry 8 }
	

-- Enclosure#08 hdd info
hddEnclosure08Installed	OBJECT-TYPE
	SYNTAX	INTEGER
	ACCESS 	read-only
	STATUS	mandatory
	DESCRIPTION
		"Enclosure Installed?"
	::= { hddEnclosure8 1 }

hddEnclosure08Description	OBJECT-TYPE
	SYNTAX	OCTET STRING
	ACCESS 	read-only
	STATUS	mandatory
	DESCRIPTION
		"Enclosure description."
	::= { hddEnclosure8 2 }
	
hddEnclosure08NumberOfSlot	OBJECT-TYPE
	SYNTAX	INTEGER
	ACCESS 	read-only
	STATUS	mandatory
	DESCRIPTION
		"# of power supply, e.g. 2."
	::= { hddEnclosure8 3 }	

hddEnclosure08InfoTable 	OBJECT-TYPE
	SYNTAX 	SEQUENCE OF HddEnclosure08InfoEntry
	ACCESS	not-accessible
	STATUS	mandatory
	DESCRIPTION
		"A table containing HDD information."
	::= { hddEnclosure8 4 }

hddEnclosure08InfoEntry 	OBJECT-TYPE
	SYNTAX	HddEnclosure08InfoEntry
	ACCESS	not-accessible
	STATUS	mandatory
	DESCRIPTION
		"Information about a particular current HDD state."
	INDEX	{ hddEnclosure08Slots }
	::= { hddEnclosure08InfoTable 1 }
	
HddEnclosure08InfoEntry ::= SEQUENCE { hddEnclosure08Slots INTEGER,
			    hddEnclosure08Desc OCTET STRING,
			    hddEnclosure08Name OCTET STRING,
			    hddEnclosure08Serial OCTET STRING,
			    hddEnclosure08FirmVer OCTET STRING,
			    hddEnclosure08Capacity INTEGER,
			    hddEnclosure08Type INTEGER,
			    hddEnclosure08State OCTET STRING }

hddEnclosure08Slots	OBJECT-TYPE
	SYNTAX	INTEGER
	ACCESS 	read-only
	STATUS	mandatory
	DESCRIPTION
		"HDD slot#, 1..#of HDD."
	::= { hddEnclosure08InfoEntry 1 }

hddEnclosure08Desc		OBJECT-TYPE
	SYNTAX	OCTET STRING
	ACCESS 	read-only
	STATUS	mandatory
	DESCRIPTION
		"HDD name."
	::= { hddEnclosure08InfoEntry 2 }


hddEnclosure08Name		OBJECT-TYPE
	SYNTAX	OCTET STRING
	ACCESS 	read-only
	STATUS	mandatory
	DESCRIPTION
		"HDD name."
	::= { hddEnclosure08InfoEntry 3 }

hddEnclosure08Serial	OBJECT-TYPE
	SYNTAX	OCTET STRING
	ACCESS 	read-only
	STATUS	mandatory
	DESCRIPTION
		"HDD serial number."
	::= { hddEnclosure08InfoEntry 4 }

hddEnclosure08FirmVer	OBJECT-TYPE
	SYNTAX	OCTET STRING
	ACCESS 	read-only
	STATUS	mandatory
	DESCRIPTION
		"HDD firmware reversion."
	::= { hddEnclosure08InfoEntry 5 }

hddEnclosure08Capacity	OBJECT-TYPE
	SYNTAX	INTEGER
	ACCESS 	read-only
	STATUS	mandatory
	DESCRIPTION
		"HDD total capacity in mega byte."
	::= { hddEnclosure08InfoEntry 6 }

hddEnclosure08Type		OBJECT-TYPE
	SYNTAX	INTEGER {
			 sata(1),
			 sas(2)
			}
	ACCESS 	read-only
	STATUS	mandatory
	DESCRIPTION
		"HDD Type."
	::= { hddEnclosure08InfoEntry 7 }

hddEnclosure08State	OBJECT-TYPE
	SYNTAX	OCTET STRING
	ACCESS 	read-only
	STATUS	mandatory
	DESCRIPTION
		"HDD state."
	::= { hddEnclosure08InfoEntry 8 }							
		

-- definition of object types of RaidSet information

raidInfoTable 	OBJECT-TYPE
	SYNTAX 	SEQUENCE OF RaidInfoEntry
	ACCESS	not-accessible
	STATUS	mandatory
	DESCRIPTION
		"A table containing RaidSet information."
	::= { raidsetInformation 1 }

raidInfoEntry 	OBJECT-TYPE
	SYNTAX	RaidInfoEntry
	ACCESS	not-accessible
	STATUS	mandatory
	DESCRIPTION
		"Information about a particular current RaidSet state."
	INDEX	{ raidNumber }
	::= { raidInfoTable 1 }
	
RaidInfoEntry ::= SEQUENCE { raidNumber INTEGER,
			     raidName OCTET STRING,
			     raidDisks INTEGER,
			     raidState OCTET STRING,
			     raidTotalCapacity INTEGER,
			     raidFreeCapacity INTEGER,
			     raidMemberDiskCapacity INTEGER,			    
			     raidMemberDiskChannels OCTET STRING }

raidNumber	OBJECT-TYPE
	SYNTAX	INTEGER
	ACCESS 	read-only
	STATUS	mandatory
	DESCRIPTION
		"RiadSet#, 0..#raidset-1."
	::= { raidInfoEntry 1 }

raidName		OBJECT-TYPE
	SYNTAX	OCTET STRING
	ACCESS 	read-only
	STATUS	mandatory
	DESCRIPTION
		"Raid set name."
	::= { raidInfoEntry 2 }

raidDisks	OBJECT-TYPE
	SYNTAX	INTEGER
	ACCESS 	read-only
	STATUS	mandatory
	DESCRIPTION
		"Member disks."
	::= { raidInfoEntry 3 }

raidState	OBJECT-TYPE
	SYNTAX	OCTET STRING
	ACCESS 	read-only
	STATUS	mandatory
	DESCRIPTION
		"Raid state."
	::= { raidInfoEntry 4 }

raidTotalCapacity	OBJECT-TYPE
	SYNTAX	INTEGER
	ACCESS 	read-only
	STATUS	mandatory
	DESCRIPTION
		"RaidSet total capacity in MB, totla capacity."
	::= { raidInfoEntry 5 }

raidFreeCapacity	OBJECT-TYPE
	SYNTAX	INTEGER
	ACCESS 	read-only
	STATUS	mandatory
	DESCRIPTION
		"RaidSet free capacity in MB, totla capacity."
	::= { raidInfoEntry 6 }

raidMemberDiskCapacity	OBJECT-TYPE
	SYNTAX	INTEGER
	ACCESS 	read-only
	STATUS	mandatory
	DESCRIPTION
		"RaidSet member disk capacity in MB, totla capacity."
	::= { raidInfoEntry 7 }

raidMemberDiskChannels	OBJECT-TYPE
	SYNTAX	OCTET STRING
	ACCESS 	read-only
	STATUS	mandatory
	DESCRIPTION
		"Member disk channels."
	::= { raidInfoEntry 8 }


-- definition of object types of VolumeSet information

volInfoTable 	OBJECT-TYPE
	SYNTAX 	SEQUENCE OF VolInfoEntry
	ACCESS	not-accessible
	STATUS	mandatory
	DESCRIPTION
		"A table containing VolumeSet information."
	::= { volumesetInformation 1 }

volInfoEntry 	OBJECT-TYPE
	SYNTAX	VolInfoEntry
	ACCESS	not-accessible
	STATUS	mandatory
	DESCRIPTION
		"Information about a particular current VolumeSet state."
	INDEX	{ volNumber }
	::= { volInfoTable 1 }
	
VolInfoEntry ::= SEQUENCE { volNumber INTEGER,
			    volName OCTET STRING,
			    volRaidName OCTET STRING,
			    volCapacity INTEGER,
			    volState OCTET STRING,			
			    volProgress INTEGER,
			    volCluster INTEGER,
			    volChannel INTEGER,
			    volSCSIID INTEGER,
			    volSCSILUN INTEGER,
			    volRaidLevel OCTET STRING,
			    volStripes INTEGER,
			    volDisks INTEGER,
			    volCache INTEGER,
			    volTag INTEGER,			    			    
			    volMaxSpeed OCTET STRING,
			    volCurrentSpeed OCTET STRING }
	
volNumber	OBJECT-TYPE
	SYNTAX	INTEGER
	ACCESS 	read-only
	STATUS	mandatory
	DESCRIPTION
		"Volume number, 0..#of volume-1."
	::= { volInfoEntry 1 }

volName	OBJECT-TYPE
	SYNTAX	OCTET STRING
	ACCESS 	read-only
	STATUS	mandatory
	DESCRIPTION
		"Volume name."
	::= { volInfoEntry 2 }

volRaidName	OBJECT-TYPE
	SYNTAX	OCTET STRING
	ACCESS 	read-only
	STATUS	mandatory
	DESCRIPTION
		"Raid name."
	::= { volInfoEntry 3 }

volCapacity	OBJECT-TYPE
	SYNTAX	INTEGER
	ACCESS 	read-only
	STATUS	mandatory
	DESCRIPTION
		"In MB, Capacity."
	::= { volInfoEntry 4 }

volState	OBJECT-TYPE
	SYNTAX	OCTET STRING
	ACCESS 	read-only
	STATUS	mandatory
	DESCRIPTION
		"VolumeSet state."
	::= { volInfoEntry 5 }

volProgress	OBJECT-TYPE
	SYNTAX	INTEGER
	ACCESS 	read-only
	STATUS	mandatory
	DESCRIPTION
		"percentage."
	::= { volInfoEntry 6 }

volCluster	OBJECT-TYPE
	SYNTAX	INTEGER
	ACCESS 	read-only
	STATUS	mandatory
	DESCRIPTION
		"Clustering, 0:no, 1:yes."
	::= { volInfoEntry 7 }

volChannel	OBJECT-TYPE
	SYNTAX	INTEGER
	ACCESS 	read-only
	STATUS	mandatory
	DESCRIPTION
		"SCSI Channel,0,1."
	::= { volInfoEntry 8 }

volSCSIID	OBJECT-TYPE
	SYNTAX	INTEGER
	ACCESS 	read-only
	STATUS	mandatory
	DESCRIPTION
		"SCSI ID, 0..15."
	::= { volInfoEntry 9 }

volSCSILUN	OBJECT-TYPE
	SYNTAX	INTEGER
	ACCESS 	read-only
	STATUS	mandatory
	DESCRIPTION
		"SCSI LUN, 0..7."
	::= { volInfoEntry 10 }

volRaidLevel	OBJECT-TYPE
	SYNTAX	OCTET STRING
	ACCESS 	read-only
	STATUS	mandatory
	DESCRIPTION
		"Raid Level, 0,1,10,3,5,6,30,50,60,00,100."
	::= { volInfoEntry 11 }

volStripes	OBJECT-TYPE
	SYNTAX	INTEGER {
			 s4K(4096),
			 s8K(8192),
			 s16K(16384),
			 s32K(32768),
			 s64K(65536),
			 s128K(131072)
			}
	ACCESS 	read-only
	STATUS	mandatory
	DESCRIPTION
		"Stripe size, in bytes."
	::= { volInfoEntry 12 }

volDisks	OBJECT-TYPE
	SYNTAX	INTEGER
	ACCESS 	read-only
	STATUS	mandatory
	DESCRIPTION
		"Disks."
	::= { volInfoEntry 13 }

volCache	OBJECT-TYPE
	SYNTAX	INTEGER {
			 write-through(0),
			 write-back(1)
			}
	ACCESS 	read-only
	STATUS	mandatory
	DESCRIPTION
		"Cache enabled, 0:no, 1:yes."
	::= { volInfoEntry 14 }
	
volTag		OBJECT-TYPE
	SYNTAX	INTEGER {
	 		 disabled(0),
	 		 enabled(1)
	 		}
	ACCESS 	read-only
	STATUS	mandatory
	DESCRIPTION
		"Tag enabled, 0:no, 1:yes."
	::= { volInfoEntry 15 }	

volMaxSpeed	OBJECT-TYPE
	SYNTAX	OCTET STRING
	ACCESS 	read-only
	STATUS	mandatory
	DESCRIPTION
		"Max speed."
	::= { volInfoEntry 16 }	

volCurrentSpeed	OBJECT-TYPE
	SYNTAX	OCTET STRING
	ACCESS 	read-only
	STATUS	mandatory
	DESCRIPTION
		"Current speed."
	::= { volInfoEntry 17 }	

-- definition of object types of Event information

eventInfoTable 	OBJECT-TYPE
	SYNTAX 	SEQUENCE OF EventInfoEntry
	ACCESS	not-accessible
	STATUS	mandatory
	DESCRIPTION
		"A table containing Event information."
	::= { eventInformation 1 }

eventInfoEntry 	OBJECT-TYPE
	SYNTAX	EventInfoEntry
	ACCESS	not-accessible
	STATUS	mandatory
	DESCRIPTION
		"Information about a particular current event."
	INDEX	{ eventNumber }
	::= { eventInfoTable 1 }
	
EventInfoEntry ::= SEQUENCE { eventNumber INTEGER,
			      eventString OCTET STRING }

eventNumber	OBJECT-TYPE
	SYNTAX	INTEGER
	ACCESS 	read-only
	STATUS	mandatory
	DESCRIPTION
		"Event number, 0..#events-1."
	::= { eventInfoEntry 1 }	

eventString	OBJECT-TYPE
	SYNTAX	OCTET STRING
	ACCESS 	read-only
	STATUS	mandatory
	DESCRIPTION
		"Event string."
	::= { eventInfoEntry 2 }


-- Areca Raid Subsystem Trap Group
raidSubSysTraps		OBJECT IDENTIFIER ::= { sasRaidCard3 7 }

-- Traps definitions
-- RaidSet Traps
rsCreate	TRAP-TYPE
	ENTERPRISE	raidSubSysTraps
	VARIABLES	{ eventString }
	DESCRIPTION
		"%s."
	::= 128

rsDelete	TRAP-TYPE
	ENTERPRISE	raidSubSysTraps
	VARIABLES	{ eventString }
	DESCRIPTION
		"%s."
	::= 129

rsExpand	TRAP-TYPE
	ENTERPRISE	raidSubSysTraps
	VARIABLES	{ eventString }
	DESCRIPTION
		"%s."
	::= 130
	
rsRebuild	TRAP-TYPE
	ENTERPRISE	raidSubSysTraps
	VARIABLES	{ eventString }
	DESCRIPTION
		"%s."
	::= 131
	
rsDegraded	TRAP-TYPE
	ENTERPRISE	raidSubSysTraps
	VARIABLES	{ eventString }
	DESCRIPTION
		"%s."
	::= 132
	
rsNoEvent	TRAP-TYPE
	ENTERPRISE	raidSubSysTraps
	VARIABLES	{ eventString }
	DESCRIPTION
		"%s."
	::= 133


-- VolumeSet Traps
vsInitializing 	TRAP-TYPE
	ENTERPRISE	raidSubSysTraps
	VARIABLES	{ eventString }
	DESCRIPTION
		"%s."
	::= 256

vsRebuilding 	TRAP-TYPE
	ENTERPRISE	raidSubSysTraps
	VARIABLES	{ eventString }
	DESCRIPTION
		"%s."
	::= 257

vsMigrating 	TRAP-TYPE
	ENTERPRISE	raidSubSysTraps
	VARIABLES	{ eventString }
	DESCRIPTION
		"%s."
	::= 258

vsChecking	 TRAP-TYPE
	ENTERPRISE	raidSubSysTraps
	VARIABLES	{ eventString }
	DESCRIPTION
		"%s."
	::= 259
	
vsCompleteInit	 TRAP-TYPE
	ENTERPRISE	raidSubSysTraps
	VARIABLES	{ eventString }
	DESCRIPTION
		"%s."
	::= 260		

vsCompleteRebuild	 TRAP-TYPE
	ENTERPRISE	raidSubSysTraps
	VARIABLES	{ eventString }
	DESCRIPTION
		"%s."
	::= 261	
	
vsCompleteMigrating	 TRAP-TYPE
	ENTERPRISE	raidSubSysTraps
	VARIABLES	{ eventString }
	DESCRIPTION
		"%s."
	::= 262	
	
vsCompleteChecking	 TRAP-TYPE
	ENTERPRISE	raidSubSysTraps
	VARIABLES	{ eventString }
	DESCRIPTION
		"%s."
	::= 263			

vsCreate	 TRAP-TYPE
	ENTERPRISE	raidSubSysTraps
	VARIABLES	{ eventString }
	DESCRIPTION
		"%s."
	::= 264	
	
vsDelete	 TRAP-TYPE
	ENTERPRISE	raidSubSysTraps
	VARIABLES	{ eventString }
	DESCRIPTION
		"%s."
	::= 265		

vsModify	 TRAP-TYPE
	ENTERPRISE	raidSubSysTraps
	VARIABLES	{ eventString }
	DESCRIPTION
		"%s."
	::= 266	
	
vsDegraded	 TRAP-TYPE
	ENTERPRISE	raidSubSysTraps
	VARIABLES	{ eventString }
	DESCRIPTION
		"%s."
	::= 267		

vsFailed	 TRAP-TYPE
	ENTERPRISE	raidSubSysTraps
	VARIABLES	{ eventString }
	DESCRIPTION
		"%s."
	::= 268

vsRevived	 TRAP-TYPE
	ENTERPRISE	raidSubSysTraps
	VARIABLES	{ eventString }
	DESCRIPTION
		"%s."
	::= 269

vsTotals	 TRAP-TYPE
	ENTERPRISE	raidSubSysTraps
	VARIABLES	{ eventString }
	DESCRIPTION
		"%s."
	::= 270
	
	
-- IDE Device Traps
pdAdded	 	TRAP-TYPE
	ENTERPRISE	raidSubSysTraps
	VARIABLES	{ eventString }
	DESCRIPTION
		"%s."
	::= 384

pdRemoved	 TRAP-TYPE
	ENTERPRISE	raidSubSysTraps
	VARIABLES	{ eventString }
	DESCRIPTION
		"%s."
	::= 385

pdReadError	 TRAP-TYPE
	ENTERPRISE	raidSubSysTraps
	VARIABLES	{ eventString }
	DESCRIPTION
		"%s."
	::= 386

pdWriteError	 TRAP-TYPE
	ENTERPRISE	raidSubSysTraps
	VARIABLES	{ eventString }
	DESCRIPTION
		"%s."
	::= 387
	
pdAtaEccError	 TRAP-TYPE
	ENTERPRISE	raidSubSysTraps
	VARIABLES	{ eventString }
	DESCRIPTION
		"%s."
	::= 388
	
pdAtaChangeMode	 TRAP-TYPE
	ENTERPRISE	raidSubSysTraps
	VARIABLES	{ eventString }
	DESCRIPTION
		"%s."
	::= 389
	
pdTimeOut	 TRAP-TYPE
	ENTERPRISE	raidSubSysTraps
	VARIABLES	{ eventString }
	DESCRIPTION
		"%s."
	::= 390
	
pdMarkFailed	 TRAP-TYPE
	ENTERPRISE	raidSubSysTraps
	VARIABLES	{ eventString }
	DESCRIPTION
		"%s."
	::= 391
	
pdPciError	 TRAP-TYPE
	ENTERPRISE	raidSubSysTraps
	VARIABLES	{ eventString }
	DESCRIPTION
		"%s."
	::= 392
	
pdSmartFailed	 TRAP-TYPE
	ENTERPRISE	raidSubSysTraps
	VARIABLES	{ eventString }
	DESCRIPTION
		"%s."
	::= 393
	
pdCreatePass	 TRAP-TYPE
	ENTERPRISE	raidSubSysTraps
	VARIABLES	{ eventString }
	DESCRIPTION
		"%s."
	::= 394
	
pdModifyPass	 TRAP-TYPE
	ENTERPRISE	raidSubSysTraps
	VARIABLES	{ eventString }
	DESCRIPTION
		"%s."
	::= 395
	
pdDeletePass	 TRAP-TYPE
	ENTERPRISE	raidSubSysTraps
	VARIABLES	{ eventString }
	DESCRIPTION
		"%s."
	::= 396
	
pdTotals	 TRAP-TYPE
	ENTERPRISE	raidSubSysTraps
	VARIABLES	{ eventString }
	DESCRIPTION
		"%s."
	::= 397										

-- SCSI Bus Traps
scsiReset	TRAP-TYPE
	ENTERPRISE	raidSubSysTraps
	VARIABLES	{ eventString }
	DESCRIPTION
		"%s."
	::= 512	
	
scsiParity	TRAP-TYPE
	ENTERPRISE	raidSubSysTraps
	VARIABLES	{ eventString }
	DESCRIPTION
		"%s."
	::= 513	
	
scsiModeChange	TRAP-TYPE
	ENTERPRISE	raidSubSysTraps
	VARIABLES	{ eventString }
	DESCRIPTION
		"%s."
	::= 514
	
scsiTotals	TRAP-TYPE
	ENTERPRISE	raidSubSysTraps
	VARIABLES	{ eventString }
	DESCRIPTION
		"%s."
	::= 515
	
-- Hardware Monitor Traps	
hwSdram1BitEcc		TRAP-TYPE
	ENTERPRISE	raidSubSysTraps
	VARIABLES	{ eventString }
	DESCRIPTION
		"%s."
	::= 640	

hwSdramMultiBitEcc	TRAP-TYPE
	ENTERPRISE	raidSubSysTraps
	VARIABLES	{ eventString }
	DESCRIPTION
		"%s."
	::= 641	
	
hwTempController	TRAP-TYPE
	ENTERPRISE	raidSubSysTraps
	VARIABLES	{ eventString }
	DESCRIPTION
		"%s."
	::= 642	


hwTempBackplane		TRAP-TYPE
	ENTERPRISE	raidSubSysTraps
	VARIABLES	{ eventString }
	DESCRIPTION
		"%s."
	::= 643

hwVoltage15	TRAP-TYPE
	ENTERPRISE	raidSubSysTraps
	VARIABLES	{ eventString }
	DESCRIPTION
		"%s."
	::= 644

hwVoltage3	TRAP-TYPE
	ENTERPRISE	raidSubSysTraps
	VARIABLES	{ eventString }
	DESCRIPTION
		"%s."
	::= 645

hwVoltage5	TRAP-TYPE
	ENTERPRISE	raidSubSysTraps
	VARIABLES	{ eventString }
	DESCRIPTION
		"%s."
	::= 646

hwVoltage12	TRAP-TYPE
	ENTERPRISE	raidSubSysTraps
	VARIABLES	{ eventString }
	DESCRIPTION
		"%s."
	::= 647
	
	
hwVoltage13	TRAP-TYPE
	ENTERPRISE	raidSubSysTraps
	VARIABLES	{ eventString }
	DESCRIPTION
		"%s."
	::= 648
	
hwVoltage25	TRAP-TYPE
	ENTERPRISE	raidSubSysTraps
	VARIABLES	{ eventString }
	DESCRIPTION
		"%s."
	::= 649
	
hwVoltage125	TRAP-TYPE
	ENTERPRISE	raidSubSysTraps
	VARIABLES	{ eventString }
	DESCRIPTION
		"%s."
	::= 650

hwPower1Failed	TRAP-TYPE
	ENTERPRISE	raidSubSysTraps
	VARIABLES	{ eventString }
	DESCRIPTION
		"%s."
	::= 651
	
hwFan1Failed	TRAP-TYPE
	ENTERPRISE	raidSubSysTraps
	VARIABLES	{ eventString }
	DESCRIPTION
		"%s."
	::= 652
	
hwPower2Failed	TRAP-TYPE
	ENTERPRISE	raidSubSysTraps
	VARIABLES	{ eventString }
	DESCRIPTION
		"%s."
	::= 653
	
hwFan2Failed	TRAP-TYPE
	ENTERPRISE	raidSubSysTraps
	VARIABLES	{ eventString }
	DESCRIPTION
		"%s."
	::= 654
	
hwPower3Failed	TRAP-TYPE
	ENTERPRISE	raidSubSysTraps
	VARIABLES	{ eventString }
	DESCRIPTION
		"%s."
	::= 655
	
hwFan3Failed	TRAP-TYPE
	ENTERPRISE	raidSubSysTraps
	VARIABLES	{ eventString }
	DESCRIPTION
		"%s."
	::= 656

hwPower4Failed	TRAP-TYPE
	ENTERPRISE	raidSubSysTraps
	VARIABLES	{ eventString }
	DESCRIPTION
		"%s."
	::= 657
	
hwFan4Failed	TRAP-TYPE
	ENTERPRISE	raidSubSysTraps
	VARIABLES	{ eventString }
	DESCRIPTION
		"%s."
	::= 658

hwUpsPowerLoss	TRAP-TYPE	
	ENTERPRISE	raidSubSysTraps
	VARIABLES	{ eventString }
	DESCRIPTION
		"%s."
	::= 659

hwTempControllerR	TRAP-TYPE
	ENTERPRISE	raidSubSysTraps
	VARIABLES	{ eventString }
	DESCRIPTION
		"%s."
	::= 660


hwTempBackplaneR		TRAP-TYPE
	ENTERPRISE	raidSubSysTraps
	VARIABLES	{ eventString }
	DESCRIPTION
		"%s."
	::= 661

hwVoltage15R	TRAP-TYPE
	ENTERPRISE	raidSubSysTraps
	VARIABLES	{ eventString }
	DESCRIPTION
		"%s."
	::= 662

hwVoltage3R	TRAP-TYPE
	ENTERPRISE	raidSubSysTraps
	VARIABLES	{ eventString }
	DESCRIPTION
		"%s."
	::= 663

hwVoltage5R	TRAP-TYPE
	ENTERPRISE	raidSubSysTraps
	VARIABLES	{ eventString }
	DESCRIPTION
		"%s."
	::= 664

hwVoltage12R	TRAP-TYPE
	ENTERPRISE	raidSubSysTraps
	VARIABLES	{ eventString }
	DESCRIPTION
		"%s."
	::= 665
	
	
hwVoltage13R	TRAP-TYPE
	ENTERPRISE	raidSubSysTraps
	VARIABLES	{ eventString }
	DESCRIPTION
		"%s."
	::= 666
	
hwVoltage25R	TRAP-TYPE
	ENTERPRISE	raidSubSysTraps
	VARIABLES	{ eventString }
	DESCRIPTION
		"%s."
	::= 667
	
hwVoltage125R	TRAP-TYPE
	ENTERPRISE	raidSubSysTraps
	VARIABLES	{ eventString }
	DESCRIPTION
		"%s."
	::= 668

hwPower1FailedR	TRAP-TYPE
	ENTERPRISE	raidSubSysTraps
	VARIABLES	{ eventString }
	DESCRIPTION
		"%s."
	::= 669
	
hwFan1FailedR	TRAP-TYPE
	ENTERPRISE	raidSubSysTraps
	VARIABLES	{ eventString }
	DESCRIPTION
		"%s."
	::= 670
	
hwPower2FailedR	TRAP-TYPE
	ENTERPRISE	raidSubSysTraps
	VARIABLES	{ eventString }
	DESCRIPTION
		"%s."
	::= 671
	
hwFan2FailedR	TRAP-TYPE
	ENTERPRISE	raidSubSysTraps
	VARIABLES	{ eventString }
	DESCRIPTION
		"%s."
	::= 672
	
hwPower3FailedR	TRAP-TYPE
	ENTERPRISE	raidSubSysTraps
	VARIABLES	{ eventString }
	DESCRIPTION
		"%s."
	::= 673
	
hwFan3FailedR	TRAP-TYPE
	ENTERPRISE	raidSubSysTraps
	VARIABLES	{ eventString }
	DESCRIPTION
		"%s."
	::= 674

hwPower4FailedR	TRAP-TYPE
	ENTERPRISE	raidSubSysTraps
	VARIABLES	{ eventString }
	DESCRIPTION
		"%s."
	::= 675
	
hwFan4FailedR	TRAP-TYPE
	ENTERPRISE	raidSubSysTraps
	VARIABLES	{ eventString }
	DESCRIPTION
		"%s."
	::= 676
	
hwUPSPowerR	TRAP-TYPE
	ENTERPRISE	raidSubSysTraps
	VARIABLES	{ eventString }
	DESCRIPTION
		"%s."
	::= 677
	
	
hwSystemRestarted	TRAP-TYPE
	ENTERPRISE	raidSubSysTraps
	VARIABLES	{ eventString }
	DESCRIPTION
		"%s."
	::= 678	
	
	
hwTest	TRAP-TYPE
	ENTERPRISE	raidSubSysTraps
	VARIABLES	{ eventString }
	DESCRIPTION
		"%s."
	::= 679	

hwSystemRecovered	TRAP-TYPE
	ENTERPRISE	raidSubSysTraps
	VARIABLES	{ eventString }
	DESCRIPTION
		"%s."
	::= 680	
	

-- New Traps	

ghmRecover	TRAP-TYPE
ENTERPRISE	raidSubSysTraps
	VARIABLES	{ eventString }
	DESCRIPTION
		"%s."
	::= 768
	
ghmOverTemp	TRAP-TYPE
ENTERPRISE	raidSubSysTraps
	VARIABLES	{ eventString }
	DESCRIPTION
		"%s."
	::= 769

ghmFailed	TRAP-TYPE
ENTERPRISE	raidSubSysTraps
	VARIABLES	{ eventString }
	DESCRIPTION
		"%s."
	::= 770

ghmUnderVoltage	TRAP-TYPE
ENTERPRISE	raidSubSysTraps
	VARIABLES	{ eventString }
	DESCRIPTION
		"%s."
	::= 771
	
ghmOverVoltage	TRAP-TYPE
ENTERPRISE	raidSubSysTraps
	VARIABLES	{ eventString }
	DESCRIPTION
		"%s."
	::= 772
	
ghmDiscovered	TRAP-TYPE
ENTERPRISE	raidSubSysTraps
	VARIABLES	{ eventString }
	DESCRIPTION
		"%s."
	::= 773	
	

ghmLostMig	TRAP-TYPE
ENTERPRISE	raidSubSysTraps
	VARIABLES	{ eventString }
	DESCRIPTION
		"%s."
	::= 774	
	
	
ghmRestartLBA	TRAP-TYPE
ENTERPRISE	raidSubSysTraps
	VARIABLES	{ eventString }
	DESCRIPTION
		"%s."
	::= 775	
	
ghmHTTPLogin	TRAP-TYPE
ENTERPRISE	raidSubSysTraps
	VARIABLES	{ eventString }
	DESCRIPTION
		"%s."
	::= 776	
	
ghmTelnetLogin	TRAP-TYPE
ENTERPRISE	raidSubSysTraps
	VARIABLES	{ eventString }
	DESCRIPTION
		"%s."
	::= 777
	
ghmVt100Login	TRAP-TYPE
ENTERPRISE	raidSubSysTraps
	VARIABLES	{ eventString }
	DESCRIPTION
		"%s."
	::= 778	

ghmGUILogin	TRAP-TYPE
ENTERPRISE	raidSubSysTraps
	VARIABLES	{ eventString }
	DESCRIPTION
		"%s."
	::= 779	
	
ghmFCLinkUp	TRAP-TYPE
ENTERPRISE	raidSubSysTraps
	VARIABLES	{ eventString }
	DESCRIPTION
		"%s."
	::= 780	
	
ghmFCLinkDown	TRAP-TYPE
ENTERPRISE	raidSubSysTraps
	VARIABLES	{ eventString }
	DESCRIPTION
		"%s."
	::= 781	
	
ghm16BytesCDB	TRAP-TYPE
ENTERPRISE	raidSubSysTraps
	VARIABLES	{ eventString }
	DESCRIPTION
		"%s."
	::= 782	
	
ghmInitLBA	TRAP-TYPE
ENTERPRISE	raidSubSysTraps
	VARIABLES	{ eventString }
	DESCRIPTION
		"%s."
	::= 783
	
ghmRebuildLBA	TRAP-TYPE
ENTERPRISE	raidSubSysTraps
	VARIABLES	{ eventString }
	DESCRIPTION
		"%s."
	::= 784	
	
ghmMigrateLBA	TRAP-TYPE
ENTERPRISE	raidSubSysTraps
	VARIABLES	{ eventString }
	DESCRIPTION
		"%s."
	::= 785	
	
END

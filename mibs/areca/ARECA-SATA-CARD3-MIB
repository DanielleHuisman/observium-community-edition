ARECA-SATA-CARD3-MIB DEFINITIONS ::= BEGIN

IMPORTS 		
		enterprises, OBJECT-TYPE
			FROM RFC1155-SMI
		TRAP-TYPE
            FROM RFC-1215;	
	
-- the path to the root

--internet				OBJECT IDENTIFIER ::= { iso org(3) dod(6) 1 }
--directory				OBJECT IDENTIFIER ::= { internet 1 }
--mgmt					OBJECT IDENTIFIER ::= { internet 2 }
--experimental			OBJECT IDENTIFIER ::= { internet 3 }
--private				OBJECT IDENTIFIER ::= { internet 4 }
--enterprises			OBJECT IDENTIFIER ::= { private 1 }
areca			 		OBJECT IDENTIFIER ::= { enterprises 18928 }
arecaGroup1				OBJECT IDENTIFIER ::= { areca 1 }
sataRaidCard3	 		OBJECT IDENTIFIER ::= { arecaGroup1 3 }
systemInformation		OBJECT IDENTIFIER ::= { sataRaidCard3 1 }
hwMonitor				OBJECT IDENTIFIER ::= { sataRaidCard3 2 }
hddInformation			OBJECT IDENTIFIER ::= { sataRaidCard3 3 }
raidsetInformation		OBJECT IDENTIFIER ::= { sataRaidCard3 4 }
volumesetInformation	OBJECT IDENTIFIER ::= { sataRaidCard3 5 }
eventInformation		OBJECT IDENTIFIER ::= { sataRaidCard3 6 }

-- definition of object types

-- definition of object types of system information

siVendor	OBJECT-TYPE
	SYNTAX	OCTET STRING
	ACCESS 	read-only
	STATUS	mandatory
	DESCRIPTION
		"The vendor name of raid subsystem."
	::= { systemInformation 1 }

siModel OBJECT-TYPE
	SYNTAX	OCTET STRING
	ACCESS 	read-only
	STATUS	mandatory
	DESCRIPTION
		"The model name of raid subsystem."
	::= { systemInformation 2 }

siSerial OBJECT-TYPE
	SYNTAX	OCTET STRING
	ACCESS 	read-only
	STATUS	mandatory
	DESCRIPTION
		"The serial number of raid subsystem."
	::= { systemInformation 3 }	
	
siFirmVer OBJECT-TYPE
	SYNTAX	OCTET STRING
	ACCESS 	read-only
	STATUS	mandatory
	DESCRIPTION
		"The firmware version of raid subsystem."
	::= { systemInformation 4 }	
	
siBootVer OBJECT-TYPE
	SYNTAX	OCTET STRING
	ACCESS 	read-only
	STATUS	mandatory
	DESCRIPTION
		"The Boot version of raid subsystem."
	::= { systemInformation 5 }	
	
siMbrVer OBJECT-TYPE
	SYNTAX	OCTET STRING
	ACCESS 	read-only
	STATUS	mandatory
	DESCRIPTION
		"The master boot record version of raid subsystem."
	::= { systemInformation 6 }		
	
siProcessor OBJECT-TYPE
	SYNTAX	OCTET STRING
	ACCESS 	read-only
	STATUS	mandatory
	DESCRIPTION
		"The processor name of raid subsystem."
	::= { systemInformation 7 }	
	
siCpuSpeed	OBJECT-TYPE
	SYNTAX	INTEGER
	ACCESS 	read-only
	STATUS	mandatory
	DESCRIPTION
		"The CPU speed (in MHZ, e.g. 400) of Raid subsystem."
	::= { systemInformation 8 }

siICache	OBJECT-TYPE
	SYNTAX	INTEGER {	
					s32K(32768),
					s512K(524288) 
					} 
	ACCESS 	read-only
	STATUS	mandatory
	DESCRIPTION
		"The CPU internal Instruction cache size (in bytes, e.g. 32768) of Raid subsystem."
	::= { systemInformation 9 }

siDCache	OBJECT-TYPE
	SYNTAX	INTEGER { 
					s32K(32768), 
					s512K(524288) 
					}			
	ACCESS 	read-only
	STATUS	mandatory
	DESCRIPTION
		"The CPU interanl data cache size (in bytes, e.g. 32768) of Raid subsystem."
	::= { systemInformation 10 }

siSCache	OBJECT-TYPE
	SYNTAX	INTEGER { 
					s32K(32768), 
					s512K(524288) 
					}
	ACCESS 	read-only
	STATUS	mandatory
	DESCRIPTION
		"The CPU secondary cache size (in bytes, e.g. 32768) of Raid subsystem."
	::= { systemInformation 11 }

siMemory	OBJECT-TYPE
	SYNTAX	INTEGER
	ACCESS 	read-only
	STATUS	mandatory
	DESCRIPTION
		"The memory size (in MB, e.g. 128) of Raid subsystem."
	::= { systemInformation 12 }

siMemSpeed	OBJECT-TYPE
	SYNTAX	INTEGER
	ACCESS 	read-only
	STATUS	mandatory
	DESCRIPTION
		"The memory speed (in MHz) of Raid subsystem."
	::= { systemInformation 13 }

siEcc		OBJECT-TYPE
	SYNTAX	INTEGER{
			no(0),
			yes(1)
			}
	ACCESS 	read-only
	STATUS	mandatory
	DESCRIPTION
		"The sdram ECC capability of Raid subsystem (0:no ECC, 1:ECC)."
	::= { systemInformation 14 }

siHosts		OBJECT-TYPE
	SYNTAX	INTEGER
	ACCESS 	read-only
	STATUS	mandatory
	DESCRIPTION
		"The number of host channels, e.g. 2."
	::= { systemInformation 15 }

siHddSlots	OBJECT-TYPE
	SYNTAX	INTEGER
	ACCESS 	read-only
	STATUS	mandatory
	DESCRIPTION
		"The number of HDD slots, e.g. 16."
	::= { systemInformation 16 }

siRaidSets	OBJECT-TYPE
	SYNTAX	INTEGER
	ACCESS 	read-only
	STATUS	mandatory
	DESCRIPTION
		"The number of RAIDSET supported, e.g. 16."
	::= { systemInformation 17 }

siVolumeSets	OBJECT-TYPE
	SYNTAX	INTEGER
	ACCESS 	read-only
	STATUS	mandatory
	DESCRIPTION
		"The number of VOLUMESET supported, e.g. 16."
	::= { systemInformation 18 }
	
siEvents	OBJECT-TYPE
	SYNTAX	INTEGER
	ACCESS 	read-only
	STATUS	mandatory
	DESCRIPTION
		"The number of events supported, e.g. 16."
	::= { systemInformation 19 }	
	
siFans		OBJECT-TYPE
	SYNTAX	INTEGER
	ACCESS 	read-only
	STATUS	mandatory
	DESCRIPTION
		"The number of FANS, e.g. 2."
	::= { systemInformation 20 }		

siPowers	OBJECT-TYPE
	SYNTAX	INTEGER
	ACCESS 	read-only
	STATUS	mandatory
	DESCRIPTION
		"The number of Powers, e.g. 2."
	::= { systemInformation 21 }		
	
siRaid6		OBJECT-TYPE
	SYNTAX	INTEGER {
			 no(0),			 
			 yes(1) 
			}
			
	ACCESS 	read-only
	STATUS	mandatory
	DESCRIPTION
		"0:no RAID6, 1:RAID6."
	::= { systemInformation 22 }		
	
siDhcp		OBJECT-TYPE
	SYNTAX	INTEGER {
			 disabled(0),
			 enabled(1)
			}
	ACCESS 	read-only
	STATUS	mandatory
	DESCRIPTION
		"0:disabled, 1:enabled."
	::= { systemInformation 23 }			

siBeeper	OBJECT-TYPE
	SYNTAX	INTEGER {
	 		 disabled(0),
	 		 enabled(1)
	 		}
	ACCESS 	read-only
	STATUS	mandatory
	DESCRIPTION
		"0:disabled, 1:enabled."
	::= { systemInformation 24 }			

siUsage		OBJECT-TYPE
	SYNTAX	INTEGER {
	   		 normal(0),
	   		 jbod(1)
	   		}
	ACCESS 	read-only
	STATUS	mandatory
	DESCRIPTION
		"0:normal, 1:JBOD."
	::= { systemInformation 25 }			

siMaxATA	OBJECT-TYPE
	SYNTAX	INTEGER {
			 ata33(33),
			 ata66(66),
			 ata100(100),
			 ata133(133),
			 serialATA(150)
			}			 
	ACCESS 	read-only
	STATUS	mandatory
	DESCRIPTION
		"33/66/100/133 if ATA, 150 if SATA."
	::= { systemInformation 26 }			

siRebuildRate	OBJECT-TYPE
	SYNTAX	INTEGER
	ACCESS 	read-only
	STATUS	mandatory
	DESCRIPTION
		"5,20,50,80 in %."
	::= { systemInformation 27 }

siBaudRate	OBJECT-TYPE
	SYNTAX	INTEGER {
			 s1200bps(1200),
			 s2400bps(2400),
			 s4800bps(4800),
			 s9600bps(9600),
			 s19200bps(19200),
			 s38400bps(38400),
			 s57600bps(57600),
			 s115200bps(115200)
			}
	ACCESS 	read-only
	STATUS	mandatory
	DESCRIPTION
		"1200,2400,4800,9600,19200,38400,57600,115200."
	::= { systemInformation 28 }


-- definition of object types of H/W monitor
-- Controller Board
hwControllerBoardInstalled	OBJECT-TYPE
	SYNTAX	INTEGER
	ACCESS 	read-only
	STATUS	mandatory
	DESCRIPTION
		"Enclosure Installed?"
	::= { hwMonitor 1 }

hwControllerBoardDescription	OBJECT-TYPE
	SYNTAX	OCTET STRING
	ACCESS 	read-only
	STATUS	mandatory
	DESCRIPTION
		"Enclosure description."
	::= { hwMonitor 2 }
	
hwControllerBoardNumberOfPower	OBJECT-TYPE
	SYNTAX	INTEGER
	ACCESS 	read-only
	STATUS	mandatory
	DESCRIPTION
		"# of power supply, e.g. 2."
	::= { hwMonitor 3 }	
	
hwControllerBoardNumberOfVol	OBJECT-TYPE
	SYNTAX	INTEGER
	ACCESS 	read-only
	STATUS	mandatory
	DESCRIPTION
		"# of Voltage, e.g. 2."
	::= { hwMonitor 4 }

hwControllerBoardNumberOfFan	OBJECT-TYPE
	SYNTAX	INTEGER
	ACCESS 	read-only
	STATUS	mandatory
	DESCRIPTION
		"# of Fan, e.g. 2."
	::= { hwMonitor 5 }		

hwControllerBoardNumberOfTemp	OBJECT-TYPE
	SYNTAX	INTEGER
	ACCESS 	read-only
	STATUS	mandatory
	DESCRIPTION
		"# of Temperature, e.g. 2."
	::= { hwMonitor 6 }	

hwControllerBoardPowerTable 	OBJECT-TYPE
	SYNTAX 	SEQUENCE OF HwControllerBoardPowerEntry
	ACCESS	not-accessible
	STATUS	mandatory
	DESCRIPTION
		"A table containing Power information."
	::= { hwMonitor 7 }

hwControllerBoardPowerEntry 	OBJECT-TYPE
	SYNTAX	HwControllerBoardPowerEntry
	ACCESS	not-accessible
	STATUS	mandatory
	DESCRIPTION
		"Information about a particular current power state."
	INDEX	{ hwControllerBoardPowerIndex }
	::= { hwControllerBoardPowerTable 1 }
	
HwControllerBoardPowerEntry ::= SEQUENCE { hwControllerBoardPowerIndex INTEGER,
			    hwControllerBoardPowerDesc OCTET STRING,
			    hwControllerBoardPowerState INTEGER }

hwControllerBoardPowerIndex	OBJECT-TYPE
	SYNTAX	INTEGER
	ACCESS 	read-only
	STATUS	mandatory
	DESCRIPTION
		"Power index, 1..#of powers."
	::= { hwControllerBoardPowerEntry 1 }		    
			    
hwControllerBoardPowerDesc	OBJECT-TYPE
	SYNTAX	OCTET STRING
	ACCESS 	read-only
	STATUS	mandatory
	DESCRIPTION
		"Power description."
	::= { hwControllerBoardPowerEntry 2 }
			    
hwControllerBoardPowerState	OBJECT-TYPE
	SYNTAX	INTEGER {
			 failed(0),
			 ok(1)
			}
	ACCESS 	read-only
	STATUS	mandatory
	DESCRIPTION
		"Power state 0:failed, 1:ok."
	::= { hwControllerBoardPowerEntry 3 }		
	
hwControllerBoardVolTable 	OBJECT-TYPE
	SYNTAX 	SEQUENCE OF HwControllerBoardVolEntry
	ACCESS	not-accessible
	STATUS	mandatory
	DESCRIPTION
		"A table containing voltage information."
	::= { hwMonitor 8 }

hwControllerBoardVolEntry 	OBJECT-TYPE
	SYNTAX	HwControllerBoardVolEntry
	ACCESS	not-accessible
	STATUS	mandatory
	DESCRIPTION
		"Information about a particular current voltage state."
	INDEX	{ hwControllerBoardVolIndex }
	::= { hwControllerBoardVolTable 1 }
	
HwControllerBoardVolEntry ::= SEQUENCE { hwControllerBoardVolIndex INTEGER,
			  hwControllerBoardVolDesc OCTET STRING,
			  hwControllerBoardVolValue INTEGER }

hwControllerBoardVolIndex	OBJECT-TYPE
	SYNTAX	INTEGER
	ACCESS 	read-only
	STATUS	mandatory
	DESCRIPTION
		"Voltage index, 1..#of voltages."
	::= { hwControllerBoardVolEntry 1 }		    

hwControllerBoardVolDesc	OBJECT-TYPE
	SYNTAX	OCTET STRING
	ACCESS 	read-only
	STATUS	mandatory
	DESCRIPTION
		"Voltage description."
	::= { hwControllerBoardVolEntry 2 }
			    
hwControllerBoardVolValue	OBJECT-TYPE
	SYNTAX	INTEGER
	ACCESS 	read-only
	STATUS	mandatory
	DESCRIPTION
		"Voltage value."
	::= { hwControllerBoardVolEntry 3 }

hwControllerBoardFanTable 	OBJECT-TYPE
	SYNTAX 	SEQUENCE OF HwControllerBoardFanEntry
	ACCESS	not-accessible
	STATUS	mandatory
	DESCRIPTION
		"A table containing Fan information."
	::= { hwMonitor 9 }

hwControllerBoardFanEntry 	OBJECT-TYPE
	SYNTAX	HwControllerBoardFanEntry
	ACCESS	not-accessible
	STATUS	mandatory
	DESCRIPTION
		"Information about a particular current fan state."
	INDEX	{ hwControllerBoardFanIndex }
	::= { hwControllerBoardFanTable 1 }
	
HwControllerBoardFanEntry ::= SEQUENCE { hwControllerBoardFanIndex INTEGER,
			  hwControllerBoardFanDesc OCTET STRING,
			  hwControllerBoardFanSpeed INTEGER }

hwControllerBoardFanIndex	OBJECT-TYPE
	SYNTAX	INTEGER
	ACCESS 	read-only
	STATUS	mandatory
	DESCRIPTION
		"Fan index, 1..#of fans."
	::= { hwControllerBoardFanEntry 1 }		    

hwControllerBoardFanDesc	OBJECT-TYPE
	SYNTAX	OCTET STRING
	ACCESS 	read-only
	STATUS	mandatory
	DESCRIPTION
		"Fan description."
	::= { hwControllerBoardFanEntry 2 }
			    
hwControllerBoardFanSpeed	OBJECT-TYPE
	SYNTAX	INTEGER
	ACCESS 	read-only
	STATUS	mandatory
	DESCRIPTION
		"Fan speed in RPM, e.g. 3200."
	::= { hwControllerBoardFanEntry 3 }

hwControllerBoardTempTable 	OBJECT-TYPE
	SYNTAX 	SEQUENCE OF HwControllerBoardTempEntry
	ACCESS	not-accessible
	STATUS	mandatory
	DESCRIPTION
		"A table containing temperature information."
	::= { hwMonitor 10 }

hwControllerBoardTempEntry 	OBJECT-TYPE
	SYNTAX	HwControllerBoardTempEntry
	ACCESS	not-accessible
	STATUS	mandatory
	DESCRIPTION
		"Information about a particular current temperature state."
	INDEX	{ hwControllerBoardTempIndex }
	::= { hwControllerBoardTempTable 1 }
	
HwControllerBoardTempEntry ::= SEQUENCE { hwControllerBoardTempIndex INTEGER,
			   hwControllerBoardTempDesc OCTET STRING,
			   hwControllerBoardTempValue INTEGER
			 }

hwControllerBoardTempIndex	OBJECT-TYPE
	SYNTAX	INTEGER
	ACCESS 	read-only
	STATUS	mandatory
	DESCRIPTION
		"Temperature index, 1..#of voltages."
	::= { hwControllerBoardTempEntry 1 }		    

hwControllerBoardTempDesc	OBJECT-TYPE
	SYNTAX	OCTET STRING
	ACCESS 	read-only
	STATUS	mandatory
	DESCRIPTION
		"Temperature description."
	::= { hwControllerBoardTempEntry 2 }
			    
hwControllerBoardTempValue	OBJECT-TYPE
	SYNTAX	INTEGER
	{	
			 na(-128)
	}
	ACCESS 	read-only
	STATUS	mandatory
	DESCRIPTION
		"Temperature value."
	::= { hwControllerBoardTempEntry 3 }
	
	
	

-- definition of object types of HDD information

hddInfoTable 	OBJECT-TYPE
	SYNTAX 	SEQUENCE OF HddInfoEntry
	ACCESS	not-accessible
	STATUS	mandatory
	DESCRIPTION
		"A table containing HDD information."
	::= { hddInformation 1 }

hddInfoEntry 	OBJECT-TYPE
	SYNTAX	HddInfoEntry
	ACCESS	not-accessible
	STATUS	mandatory
	DESCRIPTION
		"Information about a particular current HDD state."
	INDEX	{ hddSlots }
	::= { hddInfoTable 1 }
	
HddInfoEntry ::= SEQUENCE { hddSlots INTEGER,
			    hddName OCTET STRING,
			    hddSerial OCTET STRING,
			    hddFirmVer OCTET STRING,
			    hddCapacity INTEGER,
			    hddPio INTEGER,
			    hddCudma INTEGER,
			    hddSudma INTEGER,
			    hddState OCTET STRING }

hddSlots	OBJECT-TYPE
	SYNTAX	INTEGER
	ACCESS 	read-only
	STATUS	mandatory
	DESCRIPTION
		"HDD slot#, 1..#of HDD."
	::= { hddInfoEntry 1 }

hddName		OBJECT-TYPE
	SYNTAX	OCTET STRING
	ACCESS 	read-only
	STATUS	mandatory
	DESCRIPTION
		"HDD name."
	::= { hddInfoEntry 2 }

hddSerial	OBJECT-TYPE
	SYNTAX	OCTET STRING
	ACCESS 	read-only
	STATUS	mandatory
	DESCRIPTION
		"HDD serial number."
	::= { hddInfoEntry 3 }

hddFirmVer	OBJECT-TYPE
	SYNTAX	OCTET STRING
	ACCESS 	read-only
	STATUS	mandatory
	DESCRIPTION
		"HDD firmware reversion."
	::= { hddInfoEntry 4 }

hddCapacity	OBJECT-TYPE
	SYNTAX	INTEGER
	ACCESS 	read-only
	STATUS	mandatory
	DESCRIPTION
		"HDD total capacity in mega byte."
	::= { hddInfoEntry 5 }

hddPio		OBJECT-TYPE
	SYNTAX	INTEGER
	ACCESS 	read-only
	STATUS	mandatory
	DESCRIPTION
		"HDD PIO mode."
	::= { hddInfoEntry 6 }

hddCudma	OBJECT-TYPE
	SYNTAX	INTEGER
	ACCESS 	read-only
	STATUS	mandatory
	DESCRIPTION
		"HDD CUDMA mode."
	::= { hddInfoEntry 7 }

hddSudma	OBJECT-TYPE
	SYNTAX	INTEGER
	ACCESS 	read-only
	STATUS	mandatory
	DESCRIPTION
		"HDD SUDMA mode."
	::= { hddInfoEntry 8 }
	
hddState	OBJECT-TYPE
	SYNTAX	OCTET STRING
	ACCESS 	read-only
	STATUS	mandatory
	DESCRIPTION
		"HDD state."
	::= { hddInfoEntry 9 }

-- definition of object types of RaidSet information

raidInfoTable 	OBJECT-TYPE
	SYNTAX 	SEQUENCE OF RaidInfoEntry
	ACCESS	not-accessible
	STATUS	mandatory
	DESCRIPTION
		"A table containing RaidSet information."
	::= { raidsetInformation 1 }

raidInfoEntry 	OBJECT-TYPE
	SYNTAX	RaidInfoEntry
	ACCESS	not-accessible
	STATUS	mandatory
	DESCRIPTION
		"Information about a particular current RaidSet state."
	INDEX	{ raidNumber }
	::= { raidInfoTable 1 }
	
RaidInfoEntry ::= SEQUENCE { raidNumber INTEGER,
			     raidName OCTET STRING,
			     raidDisks INTEGER,
			     raidState OCTET STRING,
			     raidTotalCapacity INTEGER,
			     raidFreeCapacity INTEGER,
			     raidMemberDiskCapacity INTEGER,			    
			     raidMemberDiskChannels OCTET STRING }

raidNumber	OBJECT-TYPE
	SYNTAX	INTEGER
	ACCESS 	read-only
	STATUS	mandatory
	DESCRIPTION
		"RiadSet#, 0..#raidset-1."
	::= { raidInfoEntry 1 }

raidName		OBJECT-TYPE
	SYNTAX	OCTET STRING
	ACCESS 	read-only
	STATUS	mandatory
	DESCRIPTION
		"Raid set name."
	::= { raidInfoEntry 2 }

raidDisks	OBJECT-TYPE
	SYNTAX	INTEGER
	ACCESS 	read-only
	STATUS	mandatory
	DESCRIPTION
		"Member disks."
	::= { raidInfoEntry 3 }

raidState	OBJECT-TYPE
	SYNTAX	OCTET STRING
	ACCESS 	read-only
	STATUS	mandatory
	DESCRIPTION
		"Raid state."
	::= { raidInfoEntry 4 }

raidTotalCapacity	OBJECT-TYPE
	SYNTAX	INTEGER
	ACCESS 	read-only
	STATUS	mandatory
	DESCRIPTION
		"RaidSet total capacity in MB, totla capacity."
	::= { raidInfoEntry 5 }

raidFreeCapacity	OBJECT-TYPE
	SYNTAX	INTEGER
	ACCESS 	read-only
	STATUS	mandatory
	DESCRIPTION
		"RaidSet free capacity in MB, totla capacity."
	::= { raidInfoEntry 6 }

raidMemberDiskCapacity	OBJECT-TYPE
	SYNTAX	INTEGER
	ACCESS 	read-only
	STATUS	mandatory
	DESCRIPTION
		"RaidSet member disk capacity in MB, totla capacity."
	::= { raidInfoEntry 7 }

raidMemberDiskChannels	OBJECT-TYPE
	SYNTAX	OCTET STRING
	ACCESS 	read-only
	STATUS	mandatory
	DESCRIPTION
		"Member disk channels."
	::= { raidInfoEntry 8 }


-- definition of object types of VolumeSet information

volInfoTable 	OBJECT-TYPE
	SYNTAX 	SEQUENCE OF VolInfoEntry
	ACCESS	not-accessible
	STATUS	mandatory
	DESCRIPTION
		"A table containing VolumeSet information."
	::= { volumesetInformation 1 }

volInfoEntry 	OBJECT-TYPE
	SYNTAX	VolInfoEntry
	ACCESS	not-accessible
	STATUS	mandatory
	DESCRIPTION
		"Information about a particular current VolumeSet state."
	INDEX	{ volNumber }
	::= { volInfoTable 1 }
	
VolInfoEntry ::= SEQUENCE { volNumber INTEGER,
			    volName OCTET STRING,
			    volRaidName OCTET STRING,
			    volCapacity INTEGER,
			    volState OCTET STRING,			
			    volProgress INTEGER,
			    volCluster INTEGER,
			    volChannel INTEGER,
			    volSCSIID INTEGER,
			    volSCSILUN INTEGER,
			    volRaidLevel INTEGER,
			    volStripes INTEGER,
			    volDisks INTEGER,
			    volCache INTEGER,
			    volTag INTEGER,			    			    
			    volMaxSpeed OCTET STRING,
			    volCurrentSpeed OCTET STRING }
	
volNumber	OBJECT-TYPE
	SYNTAX	INTEGER
	ACCESS 	read-only
	STATUS	mandatory
	DESCRIPTION
		"Volume number, 0..#of volume-1."
	::= { volInfoEntry 1 }

volName	OBJECT-TYPE
	SYNTAX	OCTET STRING
	ACCESS 	read-only
	STATUS	mandatory
	DESCRIPTION
		"Volume name."
	::= { volInfoEntry 2 }

volRaidName	OBJECT-TYPE
	SYNTAX	OCTET STRING
	ACCESS 	read-only
	STATUS	mandatory
	DESCRIPTION
		"Raid name."
	::= { volInfoEntry 3 }

volCapacity	OBJECT-TYPE
	SYNTAX	INTEGER
	ACCESS 	read-only
	STATUS	mandatory
	DESCRIPTION
		"In MB, Capacity."
	::= { volInfoEntry 4 }

volState	OBJECT-TYPE
	SYNTAX	OCTET STRING
	ACCESS 	read-only
	STATUS	mandatory
	DESCRIPTION
		"VolumeSet state."
	::= { volInfoEntry 5 }

volProgress	OBJECT-TYPE
	SYNTAX	INTEGER
	ACCESS 	read-only
	STATUS	mandatory
	DESCRIPTION
		"percentage."
	::= { volInfoEntry 6 }

volCluster	OBJECT-TYPE
	SYNTAX	INTEGER
	ACCESS 	read-only
	STATUS	mandatory
	DESCRIPTION
		"Clustering, 0:no, 1:yes."
	::= { volInfoEntry 7 }

volChannel	OBJECT-TYPE
	SYNTAX	INTEGER
	ACCESS 	read-only
	STATUS	mandatory
	DESCRIPTION
		"SCSI Channel,0,1."
	::= { volInfoEntry 8 }

volSCSIID	OBJECT-TYPE
	SYNTAX	INTEGER
	ACCESS 	read-only
	STATUS	mandatory
	DESCRIPTION
		"SCSI ID, 0..15."
	::= { volInfoEntry 9 }

volSCSILUN	OBJECT-TYPE
	SYNTAX	INTEGER
	ACCESS 	read-only
	STATUS	mandatory
	DESCRIPTION
		"SCSI LUN, 0..7."
	::= { volInfoEntry 10 }

volRaidLevel	OBJECT-TYPE
	SYNTAX	INTEGER
	ACCESS 	read-only
	STATUS	mandatory
	DESCRIPTION
		"Raid Level, 0,1,3,5,6."
	::= { volInfoEntry 11 }

volStripes	OBJECT-TYPE
	SYNTAX	INTEGER {
			 s4K(4096),
			 s8K(8192),
			 s16K(16384),
			 s32K(32768),
			 s64K(65536),
			 s128K(131072)
			}
	ACCESS 	read-only
	STATUS	mandatory
	DESCRIPTION
		"Stripe size, in bytes."
	::= { volInfoEntry 12 }

volDisks	OBJECT-TYPE
	SYNTAX	INTEGER
	ACCESS 	read-only
	STATUS	mandatory
	DESCRIPTION
		"Disks."
	::= { volInfoEntry 13 }

volCache	OBJECT-TYPE
	SYNTAX	INTEGER {
			 write-through(0),
			 write-back(1)
			}
	ACCESS 	read-only
	STATUS	mandatory
	DESCRIPTION
		"Cache enabled, 0:no, 1:yes."
	::= { volInfoEntry 14 }
	
volTag		OBJECT-TYPE
	SYNTAX	INTEGER {
	 		 disabled(0),
	 		 enabled(1)
	 		}
	ACCESS 	read-only
	STATUS	mandatory
	DESCRIPTION
		"Tag enabled, 0:no, 1:yes."
	::= { volInfoEntry 15 }	

volMaxSpeed	OBJECT-TYPE
	SYNTAX	OCTET STRING
	ACCESS 	read-only
	STATUS	mandatory
	DESCRIPTION
		"Max speed."
	::= { volInfoEntry 16 }	

volCurrentSpeed	OBJECT-TYPE
	SYNTAX	OCTET STRING
	ACCESS 	read-only
	STATUS	mandatory
	DESCRIPTION
		"Current speed."
	::= { volInfoEntry 17 }	

-- definition of object types of Event information

eventInfoTable 	OBJECT-TYPE
	SYNTAX 	SEQUENCE OF EventInfoEntry
	ACCESS	not-accessible
	STATUS	mandatory
	DESCRIPTION
		"A table containing Event information."
	::= { eventInformation 1 }

eventInfoEntry 	OBJECT-TYPE
	SYNTAX	EventInfoEntry
	ACCESS	not-accessible
	STATUS	mandatory
	DESCRIPTION
		"Information about a particular current event."
	INDEX	{ eventNumber }
	::= { eventInfoTable 1 }
	
EventInfoEntry ::= SEQUENCE { eventNumber INTEGER,
			      eventString OCTET STRING }

eventNumber	OBJECT-TYPE
	SYNTAX	INTEGER
	ACCESS 	read-only
	STATUS	mandatory
	DESCRIPTION
		"Event number, 0..#events-1."
	::= { eventInfoEntry 1 }	

eventString	OBJECT-TYPE
	SYNTAX	OCTET STRING
	ACCESS 	read-only
	STATUS	mandatory
	DESCRIPTION
		"Event string."
	::= { eventInfoEntry 2 }


-- Areca Raid Subsystem Trap Group
raidSubSysTraps		OBJECT IDENTIFIER ::= { sataRaidCard3 7 }

-- Traps definitions
-- RaidSet Traps
rsCreate	TRAP-TYPE
	ENTERPRISE	raidSubSysTraps
	VARIABLES	{ eventString }
	DESCRIPTION
		"%s."
	::= 128

rsDelete	TRAP-TYPE
	ENTERPRISE	raidSubSysTraps
	VARIABLES	{ eventString }
	DESCRIPTION
		"%s."
	::= 129

rsExpand	TRAP-TYPE
	ENTERPRISE	raidSubSysTraps
	VARIABLES	{ eventString }
	DESCRIPTION
		"%s."
	::= 130
	
rsRebuild	TRAP-TYPE
	ENTERPRISE	raidSubSysTraps
	VARIABLES	{ eventString }
	DESCRIPTION
		"%s."
	::= 131
	
rsDegraded	TRAP-TYPE
	ENTERPRISE	raidSubSysTraps
	VARIABLES	{ eventString }
	DESCRIPTION
		"%s."
	::= 132
	
rsNoEvent	TRAP-TYPE
	ENTERPRISE	raidSubSysTraps
	VARIABLES	{ eventString }
	DESCRIPTION
		"%s."
	::= 133


-- VolumeSet Traps
vsInitializing 	TRAP-TYPE
	ENTERPRISE	raidSubSysTraps
	VARIABLES	{ eventString }
	DESCRIPTION
		"%s."
	::= 256

vsRebuilding 	TRAP-TYPE
	ENTERPRISE	raidSubSysTraps
	VARIABLES	{ eventString }
	DESCRIPTION
		"%s."
	::= 257

vsMigrating 	TRAP-TYPE
	ENTERPRISE	raidSubSysTraps
	VARIABLES	{ eventString }
	DESCRIPTION
		"%s."
	::= 258

vsChecking	 TRAP-TYPE
	ENTERPRISE	raidSubSysTraps
	VARIABLES	{ eventString }
	DESCRIPTION
		"%s."
	::= 259
	
vsCompleteInit	 TRAP-TYPE
	ENTERPRISE	raidSubSysTraps
	VARIABLES	{ eventString }
	DESCRIPTION
		"%s."
	::= 260		

vsCompleteRebuild	 TRAP-TYPE
	ENTERPRISE	raidSubSysTraps
	VARIABLES	{ eventString }
	DESCRIPTION
		"%s."
	::= 261	
	
vsCompleteMigrating	 TRAP-TYPE
	ENTERPRISE	raidSubSysTraps
	VARIABLES	{ eventString }
	DESCRIPTION
		"%s."
	::= 262	
	
vsCompleteChecking	 TRAP-TYPE
	ENTERPRISE	raidSubSysTraps
	VARIABLES	{ eventString }
	DESCRIPTION
		"%s."
	::= 263			

vsCreate	 TRAP-TYPE
	ENTERPRISE	raidSubSysTraps
	VARIABLES	{ eventString }
	DESCRIPTION
		"%s."
	::= 264	
	
vsDelete	 TRAP-TYPE
	ENTERPRISE	raidSubSysTraps
	VARIABLES	{ eventString }
	DESCRIPTION
		"%s."
	::= 265		

vsModify	 TRAP-TYPE
	ENTERPRISE	raidSubSysTraps
	VARIABLES	{ eventString }
	DESCRIPTION
		"%s."
	::= 266	
	
vsDegraded	 TRAP-TYPE
	ENTERPRISE	raidSubSysTraps
	VARIABLES	{ eventString }
	DESCRIPTION
		"%s."
	::= 267		

vsFailed	 TRAP-TYPE
	ENTERPRISE	raidSubSysTraps
	VARIABLES	{ eventString }
	DESCRIPTION
		"%s."
	::= 268

vsRevived	 TRAP-TYPE
	ENTERPRISE	raidSubSysTraps
	VARIABLES	{ eventString }
	DESCRIPTION
		"%s."
	::= 269

vsTotals	 TRAP-TYPE
	ENTERPRISE	raidSubSysTraps
	VARIABLES	{ eventString }
	DESCRIPTION
		"%s."
	::= 270
	
	
-- IDE Device Traps
pdAdded	 	TRAP-TYPE
	ENTERPRISE	raidSubSysTraps
	VARIABLES	{ eventString }
	DESCRIPTION
		"%s."
	::= 384

pdRemoved	 TRAP-TYPE
	ENTERPRISE	raidSubSysTraps
	VARIABLES	{ eventString }
	DESCRIPTION
		"%s."
	::= 385

pdReadError	 TRAP-TYPE
	ENTERPRISE	raidSubSysTraps
	VARIABLES	{ eventString }
	DESCRIPTION
		"%s."
	::= 386

pdWriteError	 TRAP-TYPE
	ENTERPRISE	raidSubSysTraps
	VARIABLES	{ eventString }
	DESCRIPTION
		"%s."
	::= 387
	
pdAtaEccError	 TRAP-TYPE
	ENTERPRISE	raidSubSysTraps
	VARIABLES	{ eventString }
	DESCRIPTION
		"%s."
	::= 388
	
pdAtaChangeMode	 TRAP-TYPE
	ENTERPRISE	raidSubSysTraps
	VARIABLES	{ eventString }
	DESCRIPTION
		"%s."
	::= 389
	
pdTimeOut	 TRAP-TYPE
	ENTERPRISE	raidSubSysTraps
	VARIABLES	{ eventString }
	DESCRIPTION
		"%s."
	::= 390
	
pdMarkFailed	 TRAP-TYPE
	ENTERPRISE	raidSubSysTraps
	VARIABLES	{ eventString }
	DESCRIPTION
		"%s."
	::= 391
	
pdPciError	 TRAP-TYPE
	ENTERPRISE	raidSubSysTraps
	VARIABLES	{ eventString }
	DESCRIPTION
		"%s."
	::= 392
	
pdSmartFailed	 TRAP-TYPE
	ENTERPRISE	raidSubSysTraps
	VARIABLES	{ eventString }
	DESCRIPTION
		"%s."
	::= 393
	
pdCreatePass	 TRAP-TYPE
	ENTERPRISE	raidSubSysTraps
	VARIABLES	{ eventString }
	DESCRIPTION
		"%s."
	::= 394
	
pdModifyPass	 TRAP-TYPE
	ENTERPRISE	raidSubSysTraps
	VARIABLES	{ eventString }
	DESCRIPTION
		"%s."
	::= 395
	
pdDeletePass	 TRAP-TYPE
	ENTERPRISE	raidSubSysTraps
	VARIABLES	{ eventString }
	DESCRIPTION
		"%s."
	::= 396
	
pdTotals	 TRAP-TYPE
	ENTERPRISE	raidSubSysTraps
	VARIABLES	{ eventString }
	DESCRIPTION
		"%s."
	::= 397										

-- SCSI Bus Traps
scsiReset	TRAP-TYPE
	ENTERPRISE	raidSubSysTraps
	VARIABLES	{ eventString }
	DESCRIPTION
		"%s."
	::= 512	
	
scsiParity	TRAP-TYPE
	ENTERPRISE	raidSubSysTraps
	VARIABLES	{ eventString }
	DESCRIPTION
		"%s."
	::= 513	
	
scsiModeChange	TRAP-TYPE
	ENTERPRISE	raidSubSysTraps
	VARIABLES	{ eventString }
	DESCRIPTION
		"%s."
	::= 514
	
scsiTotals	TRAP-TYPE
	ENTERPRISE	raidSubSysTraps
	VARIABLES	{ eventString }
	DESCRIPTION
		"%s."
	::= 515
	
-- Hardware Monitor Traps	
hwSdram1BitEcc		TRAP-TYPE
	ENTERPRISE	raidSubSysTraps
	VARIABLES	{ eventString }
	DESCRIPTION
		"%s."
	::= 640	

hwSdramMultiBitEcc	TRAP-TYPE
	ENTERPRISE	raidSubSysTraps
	VARIABLES	{ eventString }
	DESCRIPTION
		"%s."
	::= 641	
	
hwTempController	TRAP-TYPE
	ENTERPRISE	raidSubSysTraps
	VARIABLES	{ eventString }
	DESCRIPTION
		"%s."
	::= 642	


hwTempBackplane		TRAP-TYPE
	ENTERPRISE	raidSubSysTraps
	VARIABLES	{ eventString }
	DESCRIPTION
		"%s."
	::= 643

hwVoltage15	TRAP-TYPE
	ENTERPRISE	raidSubSysTraps
	VARIABLES	{ eventString }
	DESCRIPTION
		"%s."
	::= 644

hwVoltage3	TRAP-TYPE
	ENTERPRISE	raidSubSysTraps
	VARIABLES	{ eventString }
	DESCRIPTION
		"%s."
	::= 645

hwVoltage5	TRAP-TYPE
	ENTERPRISE	raidSubSysTraps
	VARIABLES	{ eventString }
	DESCRIPTION
		"%s."
	::= 646

hwVoltage12	TRAP-TYPE
	ENTERPRISE	raidSubSysTraps
	VARIABLES	{ eventString }
	DESCRIPTION
		"%s."
	::= 647
	
	
hwVoltage13	TRAP-TYPE
	ENTERPRISE	raidSubSysTraps
	VARIABLES	{ eventString }
	DESCRIPTION
		"%s."
	::= 648
	
hwVoltage25	TRAP-TYPE
	ENTERPRISE	raidSubSysTraps
	VARIABLES	{ eventString }
	DESCRIPTION
		"%s."
	::= 649
	
hwVoltage125	TRAP-TYPE
	ENTERPRISE	raidSubSysTraps
	VARIABLES	{ eventString }
	DESCRIPTION
		"%s."
	::= 650

hwPower1Failed	TRAP-TYPE
	ENTERPRISE	raidSubSysTraps
	VARIABLES	{ eventString }
	DESCRIPTION
		"%s."
	::= 651
	
hwFan1Failed	TRAP-TYPE
	ENTERPRISE	raidSubSysTraps
	VARIABLES	{ eventString }
	DESCRIPTION
		"%s."
	::= 652
	
hwPower2Failed	TRAP-TYPE
	ENTERPRISE	raidSubSysTraps
	VARIABLES	{ eventString }
	DESCRIPTION
		"%s."
	::= 653
	
hwFan2Failed	TRAP-TYPE
	ENTERPRISE	raidSubSysTraps
	VARIABLES	{ eventString }
	DESCRIPTION
		"%s."
	::= 654
	
hwPower3Failed	TRAP-TYPE
	ENTERPRISE	raidSubSysTraps
	VARIABLES	{ eventString }
	DESCRIPTION
		"%s."
	::= 655
	
hwFan3Failed	TRAP-TYPE
	ENTERPRISE	raidSubSysTraps
	VARIABLES	{ eventString }
	DESCRIPTION
		"%s."
	::= 656

hwPower4Failed	TRAP-TYPE
	ENTERPRISE	raidSubSysTraps
	VARIABLES	{ eventString }
	DESCRIPTION
		"%s."
	::= 657
	
hwFan4Failed	TRAP-TYPE
	ENTERPRISE	raidSubSysTraps
	VARIABLES	{ eventString }
	DESCRIPTION
		"%s."
	::= 658

hwUpsPowerLoss	TRAP-TYPE	
	ENTERPRISE	raidSubSysTraps
	VARIABLES	{ eventString }
	DESCRIPTION
		"%s."
	::= 659

hwTempControllerR	TRAP-TYPE
	ENTERPRISE	raidSubSysTraps
	VARIABLES	{ eventString }
	DESCRIPTION
		"%s."
	::= 660


hwTempBackplaneR		TRAP-TYPE
	ENTERPRISE	raidSubSysTraps
	VARIABLES	{ eventString }
	DESCRIPTION
		"%s."
	::= 661

hwVoltage15R	TRAP-TYPE
	ENTERPRISE	raidSubSysTraps
	VARIABLES	{ eventString }
	DESCRIPTION
		"%s."
	::= 662

hwVoltage3R	TRAP-TYPE
	ENTERPRISE	raidSubSysTraps
	VARIABLES	{ eventString }
	DESCRIPTION
		"%s."
	::= 663

hwVoltage5R	TRAP-TYPE
	ENTERPRISE	raidSubSysTraps
	VARIABLES	{ eventString }
	DESCRIPTION
		"%s."
	::= 664

hwVoltage12R	TRAP-TYPE
	ENTERPRISE	raidSubSysTraps
	VARIABLES	{ eventString }
	DESCRIPTION
		"%s."
	::= 665
	
	
hwVoltage13R	TRAP-TYPE
	ENTERPRISE	raidSubSysTraps
	VARIABLES	{ eventString }
	DESCRIPTION
		"%s."
	::= 666
	
hwVoltage25R	TRAP-TYPE
	ENTERPRISE	raidSubSysTraps
	VARIABLES	{ eventString }
	DESCRIPTION
		"%s."
	::= 667
	
hwVoltage125R	TRAP-TYPE
	ENTERPRISE	raidSubSysTraps
	VARIABLES	{ eventString }
	DESCRIPTION
		"%s."
	::= 668

hwPower1FailedR	TRAP-TYPE
	ENTERPRISE	raidSubSysTraps
	VARIABLES	{ eventString }
	DESCRIPTION
		"%s."
	::= 669
	
hwFan1FailedR	TRAP-TYPE
	ENTERPRISE	raidSubSysTraps
	VARIABLES	{ eventString }
	DESCRIPTION
		"%s."
	::= 670
	
hwPower2FailedR	TRAP-TYPE
	ENTERPRISE	raidSubSysTraps
	VARIABLES	{ eventString }
	DESCRIPTION
		"%s."
	::= 671
	
hwFan2FailedR	TRAP-TYPE
	ENTERPRISE	raidSubSysTraps
	VARIABLES	{ eventString }
	DESCRIPTION
		"%s."
	::= 672
	
hwPower3FailedR	TRAP-TYPE
	ENTERPRISE	raidSubSysTraps
	VARIABLES	{ eventString }
	DESCRIPTION
		"%s."
	::= 673
	
hwFan3FailedR	TRAP-TYPE
	ENTERPRISE	raidSubSysTraps
	VARIABLES	{ eventString }
	DESCRIPTION
		"%s."
	::= 674

hwPower4FailedR	TRAP-TYPE
	ENTERPRISE	raidSubSysTraps
	VARIABLES	{ eventString }
	DESCRIPTION
		"%s."
	::= 675
	
hwFan4FailedR	TRAP-TYPE
	ENTERPRISE	raidSubSysTraps
	VARIABLES	{ eventString }
	DESCRIPTION
		"%s."
	::= 676
	

hwUPSPowerR	TRAP-TYPE
	ENTERPRISE	raidSubSysTraps
	VARIABLES	{ eventString }
	DESCRIPTION
		"%s."
	::= 677
	
	
hwSystemRestarted	TRAP-TYPE
	ENTERPRISE	raidSubSysTraps
	VARIABLES	{ eventString }
	DESCRIPTION
		"%s."
	::= 678	
	
	
hwTest	TRAP-TYPE
	ENTERPRISE	raidSubSysTraps
	VARIABLES	{ eventString }
	DESCRIPTION
		"%s."
	::= 679	

hwSystemRecovered	TRAP-TYPE
	ENTERPRISE	raidSubSysTraps
	VARIABLES	{ eventString }
	DESCRIPTION
		"%s."
	::= 680	
	

-- New Traps	

ghmRecover	TRAP-TYPE
ENTERPRISE	raidSubSysTraps
	VARIABLES	{ eventString }
	DESCRIPTION
		"%s."
	::= 768
	
ghmOverTemp	TRAP-TYPE
ENTERPRISE	raidSubSysTraps
	VARIABLES	{ eventString }
	DESCRIPTION
		"%s."
	::= 769

ghmFailed	TRAP-TYPE
ENTERPRISE	raidSubSysTraps
	VARIABLES	{ eventString }
	DESCRIPTION
		"%s."
	::= 770

ghmUnderVoltage	TRAP-TYPE
ENTERPRISE	raidSubSysTraps
	VARIABLES	{ eventString }
	DESCRIPTION
		"%s."
	::= 771
	
ghmOverVoltage	TRAP-TYPE
ENTERPRISE	raidSubSysTraps
	VARIABLES	{ eventString }
	DESCRIPTION
		"%s."
	::= 772
	
ghmDiscovered	TRAP-TYPE
ENTERPRISE	raidSubSysTraps
	VARIABLES	{ eventString }
	DESCRIPTION
		"%s."
	::= 773	
	

ghmLostMig	TRAP-TYPE
ENTERPRISE	raidSubSysTraps
	VARIABLES	{ eventString }
	DESCRIPTION
		"%s."
	::= 774	
	
	
ghmRestartLBA	TRAP-TYPE
ENTERPRISE	raidSubSysTraps
	VARIABLES	{ eventString }
	DESCRIPTION
		"%s."
	::= 775	
	
ghmHTTPLogin	TRAP-TYPE
ENTERPRISE	raidSubSysTraps
	VARIABLES	{ eventString }
	DESCRIPTION
		"%s."
	::= 776	
	
ghmTelnetLogin	TRAP-TYPE
ENTERPRISE	raidSubSysTraps
	VARIABLES	{ eventString }
	DESCRIPTION
		"%s."
	::= 777
	
ghmVt100Login	TRAP-TYPE
ENTERPRISE	raidSubSysTraps
	VARIABLES	{ eventString }
	DESCRIPTION
		"%s."
	::= 778	

ghmGUILogin	TRAP-TYPE
ENTERPRISE	raidSubSysTraps
	VARIABLES	{ eventString }
	DESCRIPTION
		"%s."
	::= 779	
	
ghmFCLinkUp	TRAP-TYPE
ENTERPRISE	raidSubSysTraps
	VARIABLES	{ eventString }
	DESCRIPTION
		"%s."
	::= 780	
	
ghmFCLinkDown	TRAP-TYPE
ENTERPRISE	raidSubSysTraps
	VARIABLES	{ eventString }
	DESCRIPTION
		"%s."
	::= 781	
	
ghm16BytesCDB	TRAP-TYPE
ENTERPRISE	raidSubSysTraps
	VARIABLES	{ eventString }
	DESCRIPTION
		"%s."
	::= 782	
	
ghmInitLBA	TRAP-TYPE
ENTERPRISE	raidSubSysTraps
	VARIABLES	{ eventString }
	DESCRIPTION
		"%s."
	::= 783
	
ghmRebuildLBA	TRAP-TYPE
ENTERPRISE	raidSubSysTraps
	VARIABLES	{ eventString }
	DESCRIPTION
		"%s."
	::= 784	
	
ghmMigrateLBA	TRAP-TYPE
ENTERPRISE	raidSubSysTraps
	VARIABLES	{ eventString }
	DESCRIPTION
		"%s."
	::= 785
	
	
		
END

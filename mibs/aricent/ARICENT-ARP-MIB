-- Copyright (C) 2006-2012 Aricent Group . All Rights Reserved

-- ARP Proprietary MIB Definition
-- /*****************************************************************
--  *                                                               *
--  * $RCSfile: fsarp.mib,v $                                          *  
--  *                                                               *
--  * $Date: 2015/09/13 09:21:50 $                                                      *
--  *                                                               *
--  * $Revision: 1.11 $                                                  *
--  *                                                               *
--  ****************************************************************/

-- ARP MIB.

-- The MIB contains scalars used to configure ARP functionaly.

 ARICENT-ARP-MIB DEFINITIONS ::= BEGIN
      
 IMPORTS 
    OBJECT-TYPE, MODULE-IDENTITY, IpAddress, 
    Counter32, Integer32,
    enterprises            FROM SNMPv2-SMI
    DisplayString,
    TruthValue, RowStatus  FROM SNMPv2-TC; 

-- futuresoftware OBJECT IDENTIFIER ::= { enterprises 2076 }

   fsarp MODULE-IDENTITY
   LAST-UPDATED "201209040000Z"
   ORGANIZATION "ARICENT COMMUNICATIONS SOFTWARE"
   CONTACT-INFO "support@aricent.com"
    DESCRIPTION " This mib module is for ARP module"
    REVISION "201209040000Z"
    DESCRIPTION " This mib module is for ARP module"
::= { enterprises futuresoftware(2076) 109} 

-- The different groups in  ARP MIB are as follows:
   arp OBJECT IDENTIFIER ::= { fsarp 1 }
   arptest OBJECT IDENTIFIER ::= { fsarp 2 }

-- ARP Group
-- This group defines objects for ARP.
   fsArpCacheTimeout  OBJECT-TYPE
        SYNTAX   Integer32 (30..86400)
        MAX-ACCESS   read-write
        STATUS   current
        DESCRIPTION " Time after which the entry in cache is deleted "
        DEFVAL { 300 }
        ::= { arp 1 }

   fsArpCachePendTime  OBJECT-TYPE
        SYNTAX   Integer32	(30..3000)
        MAX-ACCESS   read-write
        STATUS   current
        DESCRIPTION " Time for which an unresolved entry will be
   		    held until response is received "
        DEFVAL { 30 }
        ::= { arp 2 }

   fsArpMaxRetries  OBJECT-TYPE
        SYNTAX   Integer32 (2..10)
        MAX-ACCESS   read-write
        STATUS   current
        DESCRIPTION " Maximum number of retry attempts before aborting
  		    resolving "
        DEFVAL { 3 }
        ::= { arp 3 }

-- ARPTEST Group
-- This group defines objects for ARPTEST.

   fsArpPendingEntryCount  OBJECT-TYPE
        SYNTAX   Integer32 
        MAX-ACCESS   read-only
        STATUS   current
        DESCRIPTION " Number of pending or ageout entries in the ARP Cache
  		    database "
        ::= { arptest 1 }


   fsArpCacheEntryCount  OBJECT-TYPE
        SYNTAX   Integer32 
        MAX-ACCESS   read-only
        STATUS   current
        DESCRIPTION " Number of ARP Cache entries in the ARP Cache
  		    database "
        ::= { arptest 2 }

   fsArpRedEntryTime  OBJECT-TYPE
        SYNTAX   Integer32
        MAX-ACCESS   read-only
        STATUS   current
        DESCRIPTION " Time when the node starts entering active state 
            from standby state "
        ::= { arptest 3 }

    fsArpRedExitTime  OBJECT-TYPE
        SYNTAX   Integer32
        MAX-ACCESS   read-only
        STATUS   current
        DESCRIPTION " Time when the node completes entering active state
            from standby state "
        ::= { arptest 4 }

   fsArpCacheFlushStatus OBJECT-TYPE
    SYNTAX     TruthValue
    MAX-ACCESS read-write
    STATUS     current
    DESCRIPTION "This object removes all dynamically learnt arp entries 
    when it is set as 'true'. After flush/clear, this object is set to 'false'"
   ::= { arptest 5 }

   fsArpGlobalDebug  OBJECT-TYPE
    SYNTAX   Integer32 (0..255)
    MAX-ACCESS read-write
    STATUS   current
    DESCRIPTION
        "Enables the tracing in the ARP. A 32 bit integer
        is used to store the Tracing level in the specified module.
        Different Tracing Levels -
        BIT 0 - Initialisation and Shutdown Trace.
        BIT 1 - Management trace.
        BIT 2 - Data path trace.
        BIT 3 - Control Plane trace.
        BIT 4 - Packet Dump.
        BIT 5 - OS Resource trace.
        BIT 6 - All Failure trace (All failures including Packet Validation)
        BIT 7 - Buffer Trace."
    DEFVAL { 0 }
    ::= { arptest 6 }


   END

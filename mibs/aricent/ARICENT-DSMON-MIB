-- Copyright (C) 2009-2012 Aricent Group . All Rights Reserved

-- $Id: fsdsmon.mib,v 1.3 2012/09/07 09:52:05 siva Exp $

ARICENT-DSMON-MIB DEFINITIONS ::= BEGIN

-- Remote Monitoring MIB extensions for Differenciated Seriveces

-- Enterprises MIB for DSMON product (for Trace).

IMPORTS 
    MODULE-IDENTITY, OBJECT-TYPE,
    enterprises, Unsigned32        FROM SNMPv2-SMI;


fsdsmon MODULE-IDENTITY
     LAST-UPDATED "201209050000Z"
     ORGANIZATION "ARICENT COMMUNICATIONS SOFTWARE"
     CONTACT-INFO "support@aricent.com" 
     DESCRIPTION
           " This MIB module is for managing DSMON implementations."
     REVISION "201209050000Z"
     DESCRIPTION
           " This MIB module is for managing DSMON implementations."

                  ::= { enterprises aricent-communication-holding-ltd (29601) cas(3) 4 }
    
-- fsDsmon Trace object
         fsDsmonTrace OBJECT-TYPE
              SYNTAX  Unsigned32 
              MAX-ACCESS read-write
              STATUS current
              DESCRIPTION
		  "This object defines the traces that are defined for dsmon.
                   Bit 1 - Function Entry
                   Bit 2 - Function Exit
                   Bit 3 - Critical
                   Bit 4 - Memory failures
                   Bit 5 - Debug"
         ::=  { fsdsmon  1 }

-- fsDsmon admin status object
         fsDsmonAdminStatus OBJECT-TYPE
              SYNTAX  INTEGER { enabled(1), disabled(2) } 
              MAX-ACCESS read-write
              STATUS current
              DESCRIPTION
		  "This object defines the admin status for dsmon"
              DEFVAL { 2 }
 
         ::=  { fsdsmon  2 }
 
END

-- Copyright (C) 2015 Aricent. All Rights Reserved.

-- $Id: fselmi.mib,v 1.8 2015/05/27 13:50:15 siva Exp $

ARICENT-ELMI-MIB DEFINITIONS ::= BEGIN

IMPORTS

    OBJECT-TYPE,MODULE-IDENTITY, Integer32,
    enterprises,Counter32,NOTIFICATION-TYPE FROM SNMPv2-SMI
    TEXTUAL-CONVENTION FROM SNMPv2-TC;

futureElmiMIB MODULE-IDENTITY
    LAST-UPDATED "201209050000Z"
    ORGANIZATION "ARICENT COMMUNICATIONS SOFTWARE"
    CONTACT-INFO "support@aricent.com"
    DESCRIPTION "This mib module is for Proprietary
       Ethernet LMI-Network Side implementation" 
    REVISION "201209050000Z"
    DESCRIPTION "This mib module is for Proprietary
       Ethernet LMI-Network Side implementation" 
::= { enterprises futuresoftware(2076) 159}

EnabledStatus ::= TEXTUAL-CONVENTION
    STATUS      current
    DESCRIPTION 
        "A simple status value for the object." 
    SYNTAX      INTEGER { enabled(1), disabled(2) }   
      
futureElmi     OBJECT IDENTIFIER   ::= { futureElmiMIB 1 }
futureElmiTrapsControl OBJECT IDENTIFIER ::= { futureElmiMIB 2 }
futureElmiTraps OBJECT IDENTIFIER ::= { futureElmiMIB 3 }

-- ------------------------------
-- fsElmi group
-- ------------------------------

fsElmiSystemControl OBJECT-TYPE
   SYNTAX      INTEGER { start(1), shutdown(2) } 
   MAX-ACCESS  read-write
   STATUS      current
   DESCRIPTION
      "The administrative shutdown status requested by management for the ELMI  
       feature. The value start (1) indicates that ELMI should be active in 
       the device on all ports. The value shutdown (2) indicates that ELMI 
       should be shutdown in the device on all ports."

   ::= { futureElmi 1 }

fsElmiModuleStatus OBJECT-TYPE
   SYNTAX      EnabledStatus
   MAX-ACCESS  read-write
   STATUS      current
   DESCRIPTION      
      "The module status configured by management for the ELMI feature.
       The value enabled(1) indicates that ELMI is enabled at system level.
       If set to disabled(2) then ELMI cannot be enabled on a interface.
  
       Note: This will be set to enabled(1) by default when fsElmiSystemControl
       is set to 'start'."

   DEFVAL {enabled}
   ::= { futureElmi 2 }

fsElmiActivePortCount OBJECT-TYPE
   SYNTAX      Counter32 
   MAX-ACCESS  read-only  
   STATUS      current
   DESCRIPTION
      "Number of Ports on which ELMI is active."
   ::= { futureElmi 3 } 

fsElmiTraceOption OBJECT-TYPE
   SYNTAX      Integer32
   MAX-ACCESS  read-write 
   STATUS      current
   DESCRIPTION
     "This object is used to enable trace statements for the ELMI
      Module.

      A four byte integer is used for enabling the level of tracing. 
      Each bit in the four byte integer, represents a particular 
      level of trace. 

      The mapping between the bit positions & the level of trace is 
      as follows: 
      0 - Init and Shutdown Traces
      1 - Management Traces
      2 - Data Path Traces
      3 - Control Plane Traces
      4 - Packet Dump Traces
      5 - Traces related to All Resources except Buffers
      6 - All Failure Traces
      7 - Buffer Traces

      16 - Memory related Trace statements
      17 - Event Handling Trace statements
      18 - Timer Module Trace statements

      The remaining bits are unused. Combinations of trace levels are 
      also allowed.

      For example if the bits 0 and 1 are set, then the trace
      statements related to Enable/Disable and management 
      will be printed.

      The user has to enter the corresponding integer value for the
      bits set. For example if bits 0 and 1 are to be set then user has
      to give the value for this object as 3.
      
      Setting the trace option to any value will cause the debug option
      to be set to 0 (i.e.) the trace option and debug option are mutually
      exclusive."
      
   DEFVAL  { 0 }
   ::= { futureElmi 4 } 

fsElmiBufferOverFlowCount OBJECT-TYPE
   SYNTAX      Counter32 
   MAX-ACCESS  read-only  
   STATUS      current
   DESCRIPTION
     "The number of times buffer overflows/failures have occurred."
   ::= { futureElmi 5 } 

fsElmiMemAllocFailureCount OBJECT-TYPE
   SYNTAX      Counter32 
   MAX-ACCESS  read-only  
   STATUS      current
   DESCRIPTION
     "The number of times memory allocation failures have occurred."
   ::= { futureElmi 6 } 

-- -------------------------------------
-- fsElmiPortTable - Start
-- -------------------------------------

fsElmiPortTable OBJECT-TYPE
   SYNTAX SEQUENCE OF FsElmiPortEntry
   MAX-ACCESS    not-accessible
   STATUS        current
   DESCRIPTION
     "List of ports."
   ::= { futureElmi 7 }

fsElmiPortEntry OBJECT-TYPE
   SYNTAX       FsElmiPortEntry
   MAX-ACCESS   not-accessible
   STATUS       current
   DESCRIPTION
     "ELMI Module Port Parameters."
   INDEX { fsElmiPort }
   ::= { fsElmiPortTable 1 }

FsElmiPortEntry ::=
    SEQUENCE {
    fsElmiPort
        Integer32,
    fsElmiPortElmiStatus
        EnabledStatus,
    fsElmiUniSide
        INTEGER,
    fsElmiOperStatus
        EnabledStatus,
    fsElmiStatusCounter
        Integer32,
    fsElmiPollingVerificationTimerValue
        Integer32,
    fsElmiPollingTimerValue
        Integer32,
    fsElmiPollingCounterValue
        Integer32,
    fsElmiNoOfConfiguredEvcs
        Integer32,
    fsElmiRxElmiCheckEnqMsgCount
           Counter32,
    fsElmiRxFullStatusEnqMsgCount
        Counter32,
    fsElmiRxFullStatusContEnqMsgCount
        Counter32,
    fsElmiTxElmiCheckMsgCount
           Counter32,
    fsElmiTxFullStatusMsgCount
        Counter32,
    fsElmiTxFullStatusContMsgCount
        Counter32,
    fsElmiTxAsyncStatusMsgCount
        Counter32,
    fsElmiRxElmiCheckMsgCount
           Counter32,
    fsElmiRxFullStatusMsgCount
        Counter32,
    fsElmiRxFullStatusContMsgCount
        Counter32,
    fsElmiRxAsyncStatusMsgCount
        Counter32,
    fsElmiTxElmiCheckEnqMsgCount
           Counter32,
    fsElmiTxFullStatusEnqMsgCount
        Counter32,
    fsElmiTxFullStatusContEnqMsgCount
        Counter32,
    fsElmiRxValidMsgCount
        Counter32,
    fsElmiRxInvalidMsgCount
        Counter32,
    fsElmiRelErrStatusTimeOutCount
        Counter32,
    fsElmiRelErrInvalidSeqNumCount
        Counter32,
    fsElmiRelErrInvalidStatusRespCount
        Counter32,
    fsElmiRelErrRxUnSolicitedStatusCount
        Counter32,
    fsElmiProErrInvalidProtVerCount
        Counter32,
    fsElmiProErrInvalidEvcRefIdCount
        Counter32,
    fsElmiProErrInvalidMessageTypeCount
        Counter32,
    fsElmiProErrOutOfSequenceInfoEleCount
        Counter32,
    fsElmiProErrDuplicateInfoEleCount
        Counter32,
    fsElmiProErrMandatoryInfoEleMissingCount
        Counter32,
    fsElmiProErrInvalidMandatoryInfoEleCount
        Counter32,
    fsElmiProErrInvalidNonMandatoryInfoEleCount
        Counter32,
    fsElmiProErrUnrecognizedInfoEleCount
        Counter32,
    fsElmiProErrUnexpectedInfoEleCount
        Counter32,
    fsElmiProErrShortMessageCount
        Counter32
     }
 

-- Common to both UNI-C and UNI-N

fsElmiPort       OBJECT-TYPE
   SYNTAX        Integer32 (1..65535)
   MAX-ACCESS    not-accessible
   STATUS        current
   DESCRIPTION
     "A unique value, greater than zero, indicating the port number."
   ::= { fsElmiPortEntry 1 }

fsElmiPortElmiStatus OBJECT-TYPE
   SYNTAX      EnabledStatus
   MAX-ACCESS  read-write
   STATUS      current
   DESCRIPTION
     "The administrative value for the port
      to configure ELMI enable(1)/disable(2) on this Port 
      By default ELMI should be disabled on each port."
   DEFVAL {disabled}
   ::= { fsElmiPortEntry 2 } 

fsElmiUniSide OBJECT-TYPE
   SYNTAX      INTEGER { unic(1), unin(2) } 
   MAX-ACCESS  read-write 
   STATUS      current
   DESCRIPTION
     "This object tells whether ELMI is running at UNI-C(1) or at UNI-N(2)
      side."
   DEFVAL {2} 
   ::= {fsElmiPortEntry 3  }

fsElmiOperStatus OBJECT-TYPE
   SYNTAX      EnabledStatus
   MAX-ACCESS  read-only
   STATUS      current
   DESCRIPTION
     "The operational status of ELMI enabled/disabled on this port."
   DEFVAL {disabled}
   ::= { fsElmiPortEntry 4 } 

fsElmiStatusCounter OBJECT-TYPE
   SYNTAX      Integer32 (2..10)
   MAX-ACCESS  read-write
   STATUS      current
   DESCRIPTION
     "The administrative default value for Status Counter."
   DEFVAL {4}
   ::= { fsElmiPortEntry 5 }

fsElmiPollingVerificationTimerValue OBJECT-TYPE
   SYNTAX      Integer32 (5..30)
   MAX-ACCESS  read-write
   STATUS      current
   DESCRIPTION
     "The administrative default value for Polling Verification Timer.
      This object is applicable only at UNI-N side."
   DEFVAL {15}
   ::= { fsElmiPortEntry 6 }

fsElmiPollingTimerValue OBJECT-TYPE
   SYNTAX      Integer32 (5..30)
   MAX-ACCESS  read-write
   STATUS      current
   DESCRIPTION
     "The administrative default value for Polling Timer.
      This object is applicable only at UNI-C side."
   DEFVAL {10}
   ::= { fsElmiPortEntry 7 }

fsElmiPollingCounterValue OBJECT-TYPE
   SYNTAX      Integer32 (1..65000)
   MAX-ACCESS  read-write
   STATUS      current
   DESCRIPTION
     "ELMI Polling Counter Default Value.
      This object is applicable only at UNI-C side."
   DEFVAL {360}
   ::= { fsElmiPortEntry 8 }

fsElmiNoOfConfiguredEvcs OBJECT-TYPE
   SYNTAX      Integer32 
   MAX-ACCESS  read-only
   STATUS      current
   DESCRIPTION
     "Number of EVCs Configured on this Port."
   ::= { fsElmiPortEntry 9 }
   
fsElmiRxElmiCheckEnqMsgCount OBJECT-TYPE 
   SYNTAX      Counter32
   MAX-ACCESS  read-only
   STATUS      current
   DESCRIPTION
     "Number of ELMI Check Enquiry message(s) received on this 
      port.
      This object is applicable only at UNI-N side"
   ::= { fsElmiPortEntry 10 }

fsElmiRxFullStatusEnqMsgCount OBJECT-TYPE 
   SYNTAX      Counter32
   MAX-ACCESS  read-only
   STATUS      current
   DESCRIPTION
     "Number of ELMI full status enquiry message(s) received 
      on this port.
      This object is applicable only at UNI-N side."
   ::= { fsElmiPortEntry 11 }

fsElmiRxFullStatusContEnqMsgCount OBJECT-TYPE 
   SYNTAX      Counter32
   MAX-ACCESS  read-only
   STATUS      current
   DESCRIPTION
     "Number of ELMI full status continued enquiry message(s) 
      received on this port.
      This object is applicable only at UNI-N side."
   ::= { fsElmiPortEntry 12 }

fsElmiTxElmiCheckMsgCount OBJECT-TYPE 
   SYNTAX      Counter32
   MAX-ACCESS  read-only
   STATUS      current
   DESCRIPTION
     "Number of ELMI check message transmitted by this port.
      This object is applicable only at UNI-N side."
   ::= { fsElmiPortEntry 13 }

fsElmiTxFullStatusMsgCount OBJECT-TYPE 
   SYNTAX      Counter32
   MAX-ACCESS  read-only
   STATUS      current
   DESCRIPTION
     "Number of ELMI full status STATUS message transmitted by this port.
      This object is applicable only at UNI-N side."
   ::= { fsElmiPortEntry 14 }

fsElmiTxFullStatusContMsgCount OBJECT-TYPE 
   SYNTAX      Counter32
   MAX-ACCESS  read-only
   STATUS      current
   DESCRIPTION
     "Number of ELMI full status continued STATUS message transmitted 
      by this port.
      This object is applicable only at UNI-N side."
   ::= { fsElmiPortEntry 15 }

fsElmiTxAsyncStatusMsgCount OBJECT-TYPE 
   SYNTAX      Counter32
   MAX-ACCESS  read-only
   STATUS      current
   DESCRIPTION
     "Number of asynchronous ELMI STATUS message(s)
      transmitted by this port.
      This object is applicable only at UNI-N side."
   ::= { fsElmiPortEntry 16 }

fsElmiRxElmiCheckMsgCount OBJECT-TYPE 
   SYNTAX      Counter32
   MAX-ACCESS  read-only
   STATUS      current
   DESCRIPTION
     "Number of ELMI check STATUS message
      received on this port.
      This object is applicable only at UNI-C side."
   ::= { fsElmiPortEntry 17 }

fsElmiRxFullStatusMsgCount OBJECT-TYPE 
   SYNTAX      Counter32
   MAX-ACCESS  read-only
   STATUS      current
   DESCRIPTION
     "Number of ELMI full status STATUS Message 
      received on this port.
      This object is applicable only at UNI-C side."
   ::= { fsElmiPortEntry 18 }

fsElmiRxFullStatusContMsgCount OBJECT-TYPE 
   SYNTAX      Counter32
   MAX-ACCESS  read-only
   STATUS      current
   DESCRIPTION
     "Number of ELMI full status continued STATUS message
      received on this port.
      This object is applicable only at UNI-C side."
   ::= { fsElmiPortEntry 19 }

fsElmiRxAsyncStatusMsgCount OBJECT-TYPE 
   SYNTAX      Counter32
   MAX-ACCESS  read-only
   STATUS      current
   DESCRIPTION
     "Number of asynchronous ELMI STATUS message
      received on this port.
      This object is applicable only at UNI-C side."
   ::= { fsElmiPortEntry 20 }
 
fsElmiTxElmiCheckEnqMsgCount OBJECT-TYPE 
   SYNTAX      Counter32
   MAX-ACCESS  read-only
   STATUS      current
   DESCRIPTION
     "Number of ELMI check enquiry message(s) transmitted on this 
      port.
      This object is applicable only at UNI-C side."
   ::= { fsElmiPortEntry 21 }

fsElmiTxFullStatusEnqMsgCount OBJECT-TYPE 
   SYNTAX      Counter32
   MAX-ACCESS  read-only
   STATUS      current
   DESCRIPTION
     "Number of ELMI full status enquiry message(s) transmitted 
      on this port.
      This object is applicable only at UNI-C side."
   ::= { fsElmiPortEntry 22 }

fsElmiTxFullStatusContEnqMsgCount OBJECT-TYPE 
   SYNTAX      Counter32
   MAX-ACCESS  read-only
   STATUS      current
   DESCRIPTION
     "Number of ELMI full status continued enquiry message(s) 
      transmitted on this port.
      This object is applicable only at UNI-C side."
   ::= { fsElmiPortEntry 23 }

fsElmiRxValidMsgCount OBJECT-TYPE 
   SYNTAX      Counter32
   MAX-ACCESS  read-only
   STATUS      current
   DESCRIPTION
     "Number of valid messages received on this port."
   ::= { fsElmiPortEntry 24 }

fsElmiRxInvalidMsgCount OBJECT-TYPE 
   SYNTAX      Counter32
   MAX-ACCESS  read-only
   STATUS      current
   DESCRIPTION
     "Number of invalid messages received on this 
           port."     
   ::= { fsElmiPortEntry 25 }

fsElmiRelErrStatusTimeOutCount OBJECT-TYPE 
   SYNTAX      Counter32
   MAX-ACCESS  read-only
   STATUS      current
   DESCRIPTION
     "Number of times status request has been sent but not
      received any reply. 
      This object is applicable only at UNI-C side."
   ::= { fsElmiPortEntry 26 }

fsElmiRelErrInvalidSeqNumCount OBJECT-TYPE 
   SYNTAX      Counter32
   MAX-ACCESS  read-only
   STATUS      current
   DESCRIPTION
     "Number of times the sequence numbers of Ethernet LMI
      packets do not match the sequence numbers expected"
   ::= { fsElmiPortEntry 27 }

fsElmiRelErrInvalidStatusRespCount OBJECT-TYPE 
   SYNTAX      Counter32
   MAX-ACCESS  read-only
   STATUS      current
   DESCRIPTION
     "Number of times a status response received was invalid and
      discarded.
      This object is applicable only at UNI-C side."
   ::= { fsElmiPortEntry 28 }

fsElmiRelErrRxUnSolicitedStatusCount OBJECT-TYPE 
   SYNTAX      Counter32
   MAX-ACCESS  read-only
   STATUS      current
   DESCRIPTION
     "Number of times status was received that had not been
      requested.
      This object is applicable only at UNI-C side." 
   ::= { fsElmiPortEntry 29 }

fsElmiProErrInvalidProtVerCount OBJECT-TYPE 
   SYNTAX      Counter32
   MAX-ACCESS  read-only
   STATUS      current
   DESCRIPTION
     "Number of times the protocol version in Ethernet LMI
      packets does not match what is supported."
   ::= { fsElmiPortEntry 30 }

fsElmiProErrInvalidEvcRefIdCount OBJECT-TYPE 
   SYNTAX      Counter32
   MAX-ACCESS  read-only
   STATUS      current
   DESCRIPTION
     "Number of times EVC reference IDs are invalid in Ethernet
      LMI packets."
   ::= { fsElmiPortEntry 31 }

fsElmiProErrInvalidMessageTypeCount OBJECT-TYPE 
   SYNTAX      Counter32
   MAX-ACCESS  read-only
   STATUS      current
   DESCRIPTION
     "Number of messages received whose message type is not valid for LMI."
   ::= { fsElmiPortEntry 32 }

fsElmiProErrOutOfSequenceInfoEleCount OBJECT-TYPE 
   SYNTAX      Counter32
   MAX-ACCESS  read-only
   STATUS      current
   DESCRIPTION
     "Number of information elements (IEs) that are not in the
      correct sequence."
   ::= { fsElmiPortEntry 33 }

fsElmiProErrDuplicateInfoEleCount OBJECT-TYPE 
   SYNTAX      Counter32
   MAX-ACCESS  read-only
   STATUS      current
   DESCRIPTION
     "Number of duplicated IEs."
   ::= { fsElmiPortEntry 34 }

fsElmiProErrMandatoryInfoEleMissingCount OBJECT-TYPE 
   SYNTAX      Counter32
   MAX-ACCESS  read-only
   STATUS      current
   DESCRIPTION
     "Number of mandatory IEs that are missing."
   ::= { fsElmiPortEntry 35 }

fsElmiProErrInvalidMandatoryInfoEleCount OBJECT-TYPE 
   SYNTAX      Counter32
   MAX-ACCESS  read-only
   STATUS      current
   DESCRIPTION
     "Number of mandatory IEs that are invalid"
   ::= { fsElmiPortEntry 36 }

fsElmiProErrInvalidNonMandatoryInfoEleCount OBJECT-TYPE 
   SYNTAX      Counter32
   MAX-ACCESS  read-only
   STATUS      current
   DESCRIPTION
     "Number of non-mandatory IEs that are invalid."
   ::= { fsElmiPortEntry 37 }

fsElmiProErrUnrecognizedInfoEleCount OBJECT-TYPE 
   SYNTAX      Counter32
   MAX-ACCESS  read-only
   STATUS      current
   DESCRIPTION
     "Number of IEs that are not recognized."
   ::= { fsElmiPortEntry 38 }

fsElmiProErrUnexpectedInfoEleCount OBJECT-TYPE 
   SYNTAX      Counter32
   MAX-ACCESS  read-only
   STATUS      current
   DESCRIPTION
     "Number of IEs that are unexpected."
   ::= { fsElmiPortEntry 39 }

fsElmiProErrShortMessageCount OBJECT-TYPE 
   SYNTAX      Counter32
   MAX-ACCESS  read-only
   STATUS      current
   DESCRIPTION
     "Number of times the Ethernet LMI message received is
      shorter than supported packets."
   ::= { fsElmiPortEntry 40 }


-- -------------------------------------
-- fsElmiPortTable - End
-- -------------------------------------

-- -------------------------------------
-- TRAP MIB BEGIN
-- -------------------------------------

fsElmiSetGlobalTrapOption OBJECT-TYPE
   SYNTAX   Integer32 (0..1)
   MAX-ACCESS   read-write
   STATUS   current
   DESCRIPTION
     "This object is used to enable and disable ELMI traps for memory
      failure.
        0 - Traps are not enabled.
        1 - Protocol and Memory failure traps enabled" 
   ::= { futureElmiTrapsControl 1 }

fsElmiSetTraps OBJECT-TYPE
   SYNTAX   Integer32 (0..3)
   MAX-ACCESS   read-write
   STATUS   current
   DESCRIPTION
     "This object is used to enable and  disable 
      ELMI traps. Currently the following are defined
      0 - Traps are not enabled.
      1 - Protocol Errors occurred.
      2 - Memory failure occurred
      3 - All the above Traps "
   ::= { futureElmiTrapsControl 2 }

fsElmiErrTrapType OBJECT-TYPE
       SYNTAX   INTEGER   {
                    none (0),
                    memfail (1),
                    bufffail (2)
                    }
       MAX-ACCESS  read-only
       STATUS  current
       DESCRIPTION
           "The error event like
            none - none of the below values
            memfail - memory allocation failure
            bufffail - buffer allocation failure"
   ::= { futureElmiTrapsControl 3 }


fsElmiPortTrapNotificationTable OBJECT-TYPE
   SYNTAX SEQUENCE OF FsElmiPortTrapNotificationEntry 
   MAX-ACCESS not-accessible
   STATUS     current
   DESCRIPTION
     "This table is used to store the notification information
      occurred in each of the port for protocol specific traps and 
      invalid packet received."
   ::= { futureElmiTrapsControl 4 }

fsElmiPortTrapNotificationEntry OBJECT-TYPE
   SYNTAX      FsElmiPortTrapNotificationEntry 
   MAX-ACCESS  not-accessible
   STATUS      current
   DESCRIPTION
     "This entry is used to store the notification information"
      INDEX { fsElmiPortTrapIndex}
   ::= { fsElmiPortTrapNotificationTable 1 }

FsElmiPortTrapNotificationEntry ::=
     SEQUENCE {
        fsElmiPortTrapIndex
            Integer32,
        fsElmiPvtExpired
            INTEGER,
        fsElmiPtExpired
            INTEGER,
        fsElmiEvcStatus
            INTEGER,
        fsElmiUniStatus
            INTEGER,
        fsElmiEvcId
        OCTET STRING,
        fsElmiErrType
        INTEGER,
        fsElmiOperStatusStatus
        INTEGER
        }

fsElmiPortTrapIndex OBJECT-TYPE
   SYNTAX      Integer32 (1..65535)
   MAX-ACCESS  not-accessible
   STATUS      current
   DESCRIPTION
     "A unique value, greater than zero, indicating the Port number."
   ::= { fsElmiPortTrapNotificationEntry 1 }

fsElmiPvtExpired OBJECT-TYPE
   SYNTAX      INTEGER {
                        pvtTimerExpired(0)
                       }
   MAX-ACCESS  read-only
   STATUS  current
   DESCRIPTION
     "PVT Expired Info.
      This trap is applicable only at UNI-N side."
   ::= { fsElmiPortTrapNotificationEntry 2 }

fsElmiPtExpired OBJECT-TYPE
   SYNTAX      INTEGER {
                        ptTimerExpired(0)
                       }
   MAX-ACCESS  read-only
   STATUS  current
   DESCRIPTION
     "PT Expired Info.
      This trap is applicable only at UNI-C side."
   ::= { fsElmiPortTrapNotificationEntry 3 }

fsElmiEvcStatus OBJECT-TYPE
   SYNTAX     INTEGER {
                evcNew(0),
                evcDelete(1),
                evcChange(2)
                   }
   MAX-ACCESS  read-only
   STATUS  current
   DESCRIPTION
     "EVC Information
      This trap is applicable only at UNI-C side"
   ::= { fsElmiPortTrapNotificationEntry 4 }

fsElmiUniStatus OBJECT-TYPE
   SYNTAX     INTEGER {
                uniChange(0)
                   }
   MAX-ACCESS  read-only
   STATUS  current
   DESCRIPTION
     "UNI Information
      This trap is applicable only at UNI-C side"
   ::= { fsElmiPortTrapNotificationEntry 5 }

fsElmiEvcId OBJECT-TYPE
   SYNTAX      OCTET STRING (SIZE (100))
   MAX-ACCESS  read-only
   STATUS  current
   DESCRIPTION
     "Ethernet Virtual Connection Identifier
      This trap is applicable only at UNI-C side"
   ::= { fsElmiPortTrapNotificationEntry 6 }

fsElmiErrType OBJECT-TYPE
   SYNTAX      INTEGER {
            reliabilityErrType(0),
                protocolErrType(1)
                   } 
   MAX-ACCESS  read-only
   STATUS      current
   DESCRIPTION
     "Error Type Information"
   ::= { fsElmiPortTrapNotificationEntry 7 }
 
fsElmiOperStatusStatus OBJECT-TYPE
   SYNTAX     INTEGER {
                fsElmiOperEnabled(0),
                fsElmiOperDisabled(1)
                   }
   MAX-ACCESS  read-only
   STATUS  current
   DESCRIPTION
     "EVC Information
      This trap is applicable only at UNI-C side"
   ::= { fsElmiPortTrapNotificationEntry 8 }

fsElmiTraps OBJECT IDENTIFIER ::= { futureElmiTraps 0 }

fsElmiInvalidMsgRxdTrap NOTIFICATION-TYPE
   OBJECTS {
                     fsElmiErrType
           }
   STATUS             current
   DESCRIPTION
     "Generated when the invalid packet is received on any port"
   ::= { fsElmiTraps 1 }

fsElmiErrTrap NOTIFICATION-TYPE
        OBJECTS {
           fsElmiErrTrapType
                }
        STATUS             current
        DESCRIPTION
         "Generated when any of the error events like memory failure or buffer failure "
   ::= { fsElmiTraps 2 }

fsElmiPvtExpiredTrap NOTIFICATION-TYPE
   OBJECTS {
                fsElmiPvtExpired
           }
   STATUS             current
   DESCRIPTION
     "Generated when PVT Expires.
      This trap is applicable only at UNI-N side."
   ::= { fsElmiTraps 3 }


fsElmiPtExpiredTrap NOTIFICATION-TYPE
   OBJECTS {
                 fsElmiPtExpired
           }
   STATUS             current
   DESCRIPTION
     "Generated when PT Expires.
      This trap is applicable only at UNI-C side."
   ::= { fsElmiTraps 4 }

fsElmiEvcTrap NOTIFICATION-TYPE
   OBJECTS {
                fsElmiEvcId,
                fsElmiEvcStatus
           }
   STATUS             current
   DESCRIPTION
     "Generated when EVC status changes.
        This trap is applicable only at UNI-C side."
   ::= { fsElmiTraps 5 }

fsElmiUniTrap NOTIFICATION-TYPE
   OBJECTS {
                  fsElmiUniStatus
           }
   STATUS             current
   DESCRIPTION
     "UNI Status Change.
      This trap is applicable only at UNI-C side."
   ::= { fsElmiTraps 6 }

fsElmiOperStatusTrap NOTIFICATION-TYPE
   OBJECTS {
                     fsElmiOperStatusStatus
           }
   STATUS             current
   DESCRIPTION
     "UNI Status Change.
      This trap is applicable only at UNI-C side."
   ::= { fsElmiTraps 7 }


-- TRAP MIB END

END

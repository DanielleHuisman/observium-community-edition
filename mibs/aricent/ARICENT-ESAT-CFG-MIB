-- Copyright (C) 2014 Aricent Group . All Rights Reserved

-- $Id: fsesat.mib,v 1.1 2014/08/14 10:54:31 siva Exp $

-- ARICENT ESAT proprietary MIB Definition

ARICENT-ESAT-CFG-MIB DEFINITIONS ::= BEGIN

IMPORTS 
OBJECT-TYPE, 
    enterprises,
    Unsigned32,
    Integer32,
    Counter64          FROM SNMPv2-SMI
    RowStatus          FROM SNMPv2-TC
    InterfaceIndex     FROM IF-MIB
    MODULE-IDENTITY    FROM SNMPv2-SMI
    MacAddress         FROM SNMPv2-TC
    VlanId             FROM Q-BRIDGE-MIB;

    fsEsat MODULE-IDENTITY
    LAST-UPDATED "201406180000Z" 
    ORGANIZATION "ARICENT COMMUNICATIONS SOFTWARE" 
    CONTACT-INFO 

    "The Aricent Group, One Tower Center Boulevard, 
    18th Floor, East Brunswick, NJ 08816, USA
    E-mail:support@aricent.com"

    DESCRIPTION 
    "The enterprise ID 29601 is originally assigned to Aricent Communications Pvt. Limited.
    Aricent Communications is a part of Aricent Group."

    REVISION "201406180000Z"

    DESCRIPTION 
    "The proprietary MIB for Aricent ESAT Configurations." 

    ::= { enterprises aricent-communication-holding-ltd(29601) iss(2) 88 }

    fsEsatSystemControl OBJECT-TYPE
    SYNTAX      INTEGER { start(1), shutdown(2)}
    MAX-ACCESS  read-write
    STATUS      current
    DESCRIPTION
    "This object specifies the admin status of Ethernet Service Activation Test (ESAT) Module in the system. 
    Y.1564 is an Ethernet service activation test methodology, and is the standard for turning up, installing,
    and troubleshooting Ethernet-based services. Y.1564 is the only standard test methodology that allows
    a complete validation of Ethernet service level agreements (SLAs) in a single test.

    When set as 'start',resources required by ESAT
    module are allocated & ESAT module starts running.

    When shutdown, all resources used by ESAT module
    are released to the system "
    DEFVAL  { shutdown }
    ::= { fsEsat 1 }

    fsEsatTraceOption OBJECT-TYPE
    SYNTAX      Integer32 (0..4294967295)
    MAX-ACCESS  read-write
    STATUS      current
    DESCRIPTION
    "This object is used to enable the trace statements in
    ESAT Module.

    A FOUR BYTE integer is specified for enabling the level of tracing.
    Each BIT in the four byte integer, represents a 
    level of Trace.

    The mapping between the bit positions & the level of trace is
    as follows:
    0 - Init and Shutdown Traces
    1 - Management Traces
    2 - Data Path Traces
    3 - Control Plane Traces
    4 - Packet Dump Traces
    5 - Traces related to All Resources except Buffers
    6 - All Failure Traces
    7 - Buffer Traces
    8 - Critical Traces

    The remaining bits are unused. Combination of levels are
    also allowed.

    For example if the bits 0 and 1 are set, then the Trace
    statements related to Init-Shutdown and Management
    are generated.

    The user has to enter the corresponding INTEGER VALUE for the
    bits set. For example if bits 0 and 1 are set, the user has to
    enter the value 3."
    DEFVAL  { 0 }
    ::= { fsEsat 2 }


    -- Service Level Agreement Table 

    fsEsatSlaTable OBJECT-TYPE
    SYNTAX      SEQUENCE OF FsEsatSlaEntry
    MAX-ACCESS  not-accessible
    STATUS      current
    DESCRIPTION
    "This table contains ESAT SLA configurations."
    ::= { fsEsat 3 }

    fsEsatSlaEntry OBJECT-TYPE
    SYNTAX      FsEsatSlaEntry
    MAX-ACCESS  not-accessible
    STATUS      current
    DESCRIPTION
    "This entry contains information about a particular ESAT SLA 
    Configuration."
    INDEX   { fsEsatSlaId }
    ::= { fsEsatSlaTable 1 }

    FsEsatSlaEntry ::=
    SEQUENCE {
        fsEsatSlaId             Unsigned32,
        fsEsatSlaIfIndex        InterfaceIndex,
        fsEsatSlaEvcIndex       VlanId,
        fsEsatSlaMEG            Unsigned32,
        fsEsatSlaME             Unsigned32,
        fsEsatSlaMEP            Unsigned32,
        fsEsatSlaRateStep       Integer32,
        fsEsatSlaFreqDelay      Integer32,
        fsEsatSlaDuration       Integer32,
        fsEsatSlaDirection      INTEGER,
        fsEsatSlaTrafProfileId  Integer32,
        fsEsatSlaSacId          Integer32,
        fsEsatSlaStatus         INTEGER,
        fsEsatSlaRowStatus      RowStatus
    }

    fsEsatSlaId OBJECT-TYPE
    SYNTAX      Unsigned32 ( 1..255 )
    MAX-ACCESS  not-accessible
    STATUS      current
    DESCRIPTION
    "This object specifies the ESAT Service Level Agreement Identifier. This is a free running index used to 
    identify a SLA. "
    ::= { fsEsatSlaEntry 1 }

    fsEsatSlaIfIndex OBJECT-TYPE
    SYNTAX      InterfaceIndex
    MAX-ACCESS  read-write
    STATUS      current
    DESCRIPTION
    "This object specifies the Interface Index on which the ESAT test is performed."
    ::= { fsEsatSlaEntry 2 }

    fsEsatSlaEvcIndex OBJECT-TYPE
    SYNTAX      VlanId
    MAX-ACCESS  read-write
    STATUS      current
    DESCRIPTION
    "This object specifies the  service under test. The EVC is configured 
    using the MEF MIB. Internally this object refers to 
    fsEvcIndex in MEF MIB."
    ::= { fsEsatSlaEntry 3 }

    fsEsatSlaMEG OBJECT-TYPE
    SYNTAX      Unsigned32
    MAX-ACCESS  read-write
    STATUS      current
    DESCRIPTION
    "This object specifies the Maintenance Entity Group (MEG) of the fsEsatSlaEntry.
    Internally this object refers to MIB object dot1agCfmMdIndex
    of ECFM 802.1ag standard."
    ::= { fsEsatSlaEntry 4 }

    fsEsatSlaME OBJECT-TYPE
    SYNTAX      Unsigned32
    MAX-ACCESS  read-write
    STATUS      current
    DESCRIPTION
    "This object specifies  the Maintenance Entity (ME) of the fsEsatSlaEntry.
    Internally this object refers to MIB object dot1agCfmMaIndex
    of ECFM 802.1ag standard."
    ::= { fsEsatSlaEntry 5 }

    fsEsatSlaMEP OBJECT-TYPE
    SYNTAX      Unsigned32 (1..8191)
    MAX-ACCESS  read-write
    STATUS      current
    DESCRIPTION
    "This object specifies the Maintenance Association End Point (MEP) of the 
    fsEsatSlaEntry. Internally this object refers to MIB object 
    dot1agCfmMepIdentifier of ECFM 802.1ag standard."
    ::= { fsEsatSlaEntry 6 }

    fsEsatSlaRateStep OBJECT-TYPE
    SYNTAX      Integer32 ( 10..100 )
    MAX-ACCESS  read-write
    STATUS      current
    DESCRIPTION
    "This object specifies the step load CIR (Committed Information Rate) configuration test. 
    If no value is provided, 25% of CIR is sent first, followed by 50% of CIR
    and so on; the complete CIR is generated  in 4 steps. For eg, If the rate step is configured as 10, CIR
    is generated at an incremental 10% for a set of 10 steps for the 
    configured CIR."
    DEFVAL  { 25 }
    ::= { fsEsatSlaEntry 7 }

    fsEsatSlaFreqDelay OBJECT-TYPE
    SYNTAX      Integer32 ( 0..60 ) 
    MAX-ACCESS  read-write
    STATUS      current
    DESCRIPTION
    "This object specifies  the delay in seconds between each packet part of the traffic generation."
    DEFVAL  { 0 }
    ::= { fsEsatSlaEntry 8 }

    fsEsatSlaDuration OBJECT-TYPE
    SYNTAX      Integer32 ( 1..3600 ) 
    MAX-ACCESS  read-write
    STATUS      current
    DESCRIPTION
    "This object specifies the duration of the complete Ethernet Service Activation Test in seconds. 
    For CIR configuration test, the CIR traffic is generated for the configured
    duration. For step load CIR configuration test, the duration 
    configured is divided into number of rate steps configured using the object 
    fsEsatSlaRateStep. "
    DEFVAL  { 5 }
    ::= { fsEsatSlaEntry 9 }

    fsEsatSlaDirection OBJECT-TYPE
    SYNTAX      INTEGER {
        external(1),
            internal(2)
    }    
    MAX-ACCESS  read-write
    STATUS      current
    DESCRIPTION
    "This object specifies the direction of the measurements . In a bridge, the
    performance measurements can be done either at user-to-network interface (UNI)port or network-to-network interface (NNI) port. 
    If the direction is specified as internal, measurement is done at 
    UNI port and if the direction is specified as external, measurement
    is done at NNI port."
    DEFVAL  { 1 }
    ::= { fsEsatSlaEntry 10 }

    fsEsatSlaTrafProfileId OBJECT-TYPE
    SYNTAX      INTEGER (1..255)
    MAX-ACCESS  read-write
    STATUS      current
    DESCRIPTION
    "This object specifies the Traffic Profile to which the SLA is currently mapped. Multiple 
    packet profiles can be created and each can be associated to a 
    given SLA. Each packet profile contains packet information such as 
    Ethernet Header, VLAN tag and payload."
    ::= { fsEsatSlaEntry 11 }

    fsEsatSlaSacId OBJECT-TYPE
    SYNTAX      INTEGER (1..255)
    MAX-ACCESS  read-write
    STATUS      current
    DESCRIPTION
    "This object specifies the Service Acceptance Criteria to which the SLA is currently mapped.
    Multiple SACs can be created and each can be associated to a given SLA.
    Each SAC refers to the minimum Information rate, frame loss ratio, frame
    transmit delay, frame delay variation for the service under test."
    ::= { fsEsatSlaEntry 12 }

    fsEsatSlaStatus OBJECT-TYPE
    SYNTAX      INTEGER { start(1), stop(2)}
    MAX-ACCESS  read-write
    STATUS      current
    DESCRIPTION
    "This object specifies the ESAT SLA status. It is used to start or stop the SLA under test."
    DEFVAL  { 2 }
    ::= { fsEsatSlaEntry 13 }

    fsEsatSlaRowStatus OBJECT-TYPE
    SYNTAX      RowStatus
    MAX-ACCESS  read-write
    STATUS      current
    DESCRIPTION
    "This object specifies the row status and is used to create or
    deletea new entry by setting this object to the appropriate value as
    mentioned in SMI-v2."
    ::= { fsEsatSlaEntry 14 }
    -- Traffic Profile Table

    fsEsatTrafProfTable OBJECT-TYPE
    SYNTAX      SEQUENCE OF FsEsatTrafProfEntry
    MAX-ACCESS  not-accessible
    STATUS      current
    DESCRIPTION
    "This table contains Traffic Profile configurations."
    ::= { fsEsat 4 }

    fsEsatTrafProfEntry OBJECT-TYPE
    SYNTAX      FsEsatTrafProfEntry 
    MAX-ACCESS  not-accessible
    STATUS      current
    DESCRIPTION
    "This entry contains information about a particular Traffic Profile configuration."
    INDEX   { fsEsatTrafProfId }
    ::= {  fsEsatTrafProfTable 1 }

    FsEsatTrafProfEntry ::=
    SEQUENCE {
        fsEsatTrafProfId            Unsigned32,
        fsEsatTrafProfDir           INTEGER,
        fsEsatTrafProfTagType       INTEGER,
        fsEsatTrafProfInVlan        VlanId,
        fsEsatTrafProfOutVlan       VlanId,
        fsEsatTrafProfInCos         Integer32,
        fsEsatTrafProfOutCos        Integer32,
        fsEsatTrafProfPktSize       Integer32,
        fsEsatTrafProfSrcMac        MacAddress,
        fsEsatTrafProfDestMac       MacAddress,
        fsEsatTrafProfPayload       OCTET STRING,
        fsEsatTrafProfRowStatus     RowStatus
    }

    fsEsatTrafProfId OBJECT-TYPE
    SYNTAX      Unsigned32 ( 1..255 ) 
    MAX-ACCESS  not-accessible
    STATUS      current
    DESCRIPTION
    "This object specifies the ESAT Traffic Profile Identifier. This is a free running index."
    ::= { fsEsatTrafProfEntry 1 }

    fsEsatTrafProfDir OBJECT-TYPE
    SYNTAX      INTEGER {
                 external (1),
                 internal (2)
    }
    MAX-ACCESS  read-write 
    STATUS      current
    DESCRIPTION
    "This object specifies the direction of ESAT Traffic Profile Generation. When this object is set as external, 
    the traffic is generated at the wire-side of network-to-network interface (NNI) and is transmitted 
    to the responder through the same interface.When this object is set as internal the 
    traffic is generated at the user-to-network interface (UNI) and 
    transmitted to the responder through NNI respectively."
    DEFVAL  { 1 }
    ::= { fsEsatTrafProfEntry 2 }

    fsEsatTrafProfTagType OBJECT-TYPE
    SYNTAX      INTEGER {
                 untagged (1),
                 singletagged (2),
                 doubletagged (3),
                 prioritytagged (4)
    }
    MAX-ACCESS  read-write 
    STATUS      current
    DESCRIPTION
    "This object specifies the type of ESAT vlan tag to be used for Traffic Profile Generation. This 
    specifies the type of packet to be used to generate traffic."
    ::= { fsEsatTrafProfEntry 3 }

    fsEsatTrafProfInVlan OBJECT-TYPE
    SYNTAX      VlanId 
    MAX-ACCESS  read-write 
    STATUS      current
    DESCRIPTION
    "This object specifies the the VLAN ID for the inner vlan
    tag of the interface from which the message will be
    sent. This is 
    applicable if the fsEsatTrafProfTagType is single tagged or double tagged."
    ::= { fsEsatTrafProfEntry 4 }

    fsEsatTrafProfOutVlan OBJECT-TYPE
    SYNTAX      VlanId
    MAX-ACCESS  read-write 
    STATUS      current
    DESCRIPTION
    "This object specifies the ESAT Outer VLAN ID to be used as part of profile frame. This is applicable
    if the fsEsatTrafProfTagType is double tagged."
    ::= { fsEsatTrafProfEntry 5 }

    fsEsatTrafProfInCos OBJECT-TYPE
    SYNTAX      Integer32 ( 0..7 )
    MAX-ACCESS  read-write 
    STATUS      current
    DESCRIPTION
    "This object specifies the class of service (CoS) value
    for the inner VLAN tag of the interface from which the
    message will be sent. This 
    is applicable if the fsEsatTrafProfTagType is single tagged, double 
    tagged or priority tagged."
    ::= { fsEsatTrafProfEntry 6 }

    fsEsatTrafProfOutCos OBJECT-TYPE
    SYNTAX      Integer32 ( 0..7 )
    MAX-ACCESS  read-write 
    STATUS      current
    DESCRIPTION
    " This object specifies the ESAT Outer Class of Service to be used as part of profile frame. This 
    is applicable if the fsEsatTrafProfTagType is double tagged"
    ::= { fsEsatTrafProfEntry 7 }

    fsEsatTrafProfPktSize OBJECT-TYPE
    SYNTAX      Integer32 ( 64..1518 ) 
    MAX-ACCESS  read-write
    STATUS      current
    DESCRIPTION
    "This object specifies the ESAT Traffic Profile Packet Size in bytes."
    DEFVAL  { 512 }
    ::= { fsEsatTrafProfEntry 8 }

    fsEsatTrafProfSrcMac OBJECT-TYPE
    SYNTAX      MacAddress
    MAX-ACCESS  read-write
    STATUS      current
    DESCRIPTION
    "This object specifies the ESAT Source MAC address in the packet profile."
    ::= { fsEsatTrafProfEntry 9 }

    fsEsatTrafProfDestMac OBJECT-TYPE
    SYNTAX      MacAddress
    MAX-ACCESS  read-write
    STATUS      current
    DESCRIPTION
    "This object specifies the ESAT Destination MAC address in the packet profile."
    ::= { fsEsatTrafProfEntry 10 }

    fsEsatTrafProfPayload OBJECT-TYPE
    SYNTAX      OCTET STRING (SIZE (0..16))
    MAX-ACCESS  read-write
    STATUS      current
    DESCRIPTION
    "This object specifies the ESAT Payload in the packet profile."
    ::= { fsEsatTrafProfEntry 11 }

    fsEsatTrafProfRowStatus OBJECT-TYPE
    SYNTAX      RowStatus
    MAX-ACCESS  read-write
    STATUS      current
    DESCRIPTION
    "This object sp;ecifies the row status and is used to create or delete a new entry by setting this object to the appropriate value as
    mentioned in SMI-v2."
    ::= { fsEsatTrafProfEntry 12 }

    -- Service Acceptance Criteria Profile Table

    fsEsatSacTable OBJECT-TYPE
    SYNTAX      SEQUENCE OF FsEsatSacEntry
    MAX-ACCESS  not-accessible
    STATUS      current
    DESCRIPTION
    "This table contains Service Acceptance Criteria Profile configuration. 
    Service Acceptance Criteria (SAC) is a set of criteria used to ensure that a service meets its
    functionality and quality requirement and that the service is ready to operate when it has been
    deployed."
    ::= { fsEsat 5 }

    fsEsatSacEntry OBJECT-TYPE
    SYNTAX      FsEsatSacEntry 
    MAX-ACCESS  not-accessible
    STATUS      current
    DESCRIPTION
    "This entry contains information about a particular SAC Profile configuration."
    INDEX   { fsEsatSacId }
    ::= {  fsEsatSacTable 1 }

    FsEsatSacEntry ::=
    SEQUENCE {
        fsEsatSacId            Unsigned32,
        fsEsatSacInfoRate      Integer32,
        fsEsatSacFrLossRatio   Integer32,
        fsEsatSacFrTxDelay     Integer32,
        fsEsatSacFrDelayVar    Integer32, 
        fsEsatSacRowStatus     RowStatus
    }

    fsEsatSacId OBJECT-TYPE
    SYNTAX      Unsigned32 ( 1..255 ) 
    MAX-ACCESS  not-accessible
    STATUS      current
    DESCRIPTION
    "This object specifies the ESAT SAC Identifier used to identify a particular
    SAC entry."
    ::= { fsEsatSacEntry 1 }

    fsEsatSacInfoRate OBJECT-TYPE
    SYNTAX      Integer32
    MAX-ACCESS  read-write 
    STATUS      current
    DESCRIPTION
    "This object specifies the ESAT Information Rate configured as part of this SAC. This is 
    the minimum Information Rate above which a test is declared fail. Information rate is a bit rate measure 
    of available or consumed data communication resources expressed in bits/second."
    ::= { fsEsatSacEntry 2 }

    fsEsatSacFrLossRatio OBJECT-TYPE
    SYNTAX      Integer32 ( 0..100 )
    MAX-ACCESS  read-write
    STATUS      current
    DESCRIPTION
    "This object specifies the ESAT Frame Loss Ratio (FLR) configured as part of this SAC. This is 
    the minimum frame loss ratio above which a test is declared fail. 
    Frame Loss Ratio measures the number of packets lost over the total number of packets sent. 
    Frame loss can be due to a number of issues such as network congestion or errors during transmissions."
    ::= { fsEsatSacEntry 3 }

    fsEsatSacFrTxDelay OBJECT-TYPE
    SYNTAX      Integer32
    MAX-ACCESS  read-write
    STATUS      current
    DESCRIPTION
    "This object specifies the ESAT Frame Transfer Delay (FTD)configured as part of this SAC. This is 
    the minimum frame transfer delay (in milliseconds)above which a test is declared fail. 
    Frame Transfer delay measures the round-trip time (RTT) taken by a test frame to travel through a 
    network device or across the network and back to the test port "
    ::= { fsEsatSacEntry 4 }

    fsEsatSacFrDelayVar OBJECT-TYPE
    SYNTAX      Integer32
    MAX-ACCESS  read-write
    STATUS      current
    DESCRIPTION
    "This object specifies the ESAT Frame Delay Variation configured as part of this SAC. This is 
    the minimum frame delay variation (in milliseconds) above which a test is declared fail. 
    Frame Delay Variation (FDV) measures the variations in the time delay between packet deliveries."
    ::= { fsEsatSacEntry 5 }

    fsEsatSacRowStatus OBJECT-TYPE
    SYNTAX      RowStatus
    MAX-ACCESS  read-write
    STATUS      current
    DESCRIPTION
    "This object specifies the row status and is used to create or delete a new entry by setting this object to the appropriate value as
    mentioned in SMI-v2."
    ::= { fsEsatSacEntry 6 }

    -- SLA Statistics Table

    fsEsatStatsTable OBJECT-TYPE
    SYNTAX      SEQUENCE OF FsEsatStatsEntry
    MAX-ACCESS  not-accessible
    STATUS      current
    DESCRIPTION
    "This table contains the statistics of the SLA operation performed."
    ::= { fsEsat 6 }

    fsEsatStatsEntry OBJECT-TYPE
    SYNTAX      FsEsatStatsEntry
    MAX-ACCESS  not-accessible
    STATUS      current
    DESCRIPTION
    "This entry specifies the statistics about a particular step in the SLA operation performed."
    INDEX   { fsEsatSlaId, fsEsatStatsStepId }
    ::= {  fsEsatStatsTable 1 }

    FsEsatStatsEntry ::=
    SEQUENCE {
        fsEsatStatsStepId             Integer32,
        fsEsatStatsResult             INTEGER,
        fsEsatStatsDuration           Unsigned32,
        fsEsatStatsTxPkts             Unsigned32,
        fsEsatStatsTxBytes            Counter64,
        fsEsatStatsRxPkts             Unsigned32,
        fsEsatStatsRxBytes            Counter64,
        fsEsatStatsIrMin              Integer32,
        fsEsatStatsIrMean             Integer32,
        fsEsatStatsIrMax              Integer32,
        fsEsatStatsFrLossCnt          Integer32,
        fsEsatStatsFrLossRatio        Integer32,
        fsEsatStatsFrTxDelayMin       Integer32,
        fsEsatStatsFrTxDelayMean      Integer32,
        fsEsatStatsFrTxDelayMax       Integer32,
        fsEsatStatsFrDelayVarMin      Integer32,
        fsEsatStatsFrDelayVarMean     Integer32,
        fsEsatStatsFrDelayVarMax      Integer32,
        fsEsatStatsPortStateCounter   Integer32
    }

    fsEsatStatsStepId OBJECT-TYPE
    SYNTAX      Integer32 ( 1..10 ) 
    MAX-ACCESS  not-accessible
    STATUS      current
    DESCRIPTION
    "This object specifies the ESAT Step Index in SLA operation statistics. A report is generated for each 
    fsEsatSlaRateStep configured.. 
    CIR configuration testis performed  only in one step."
    ::= { fsEsatStatsEntry 1 }

    fsEsatStatsResult OBJECT-TYPE
    SYNTAX      INTEGER {
             pass (1),
             fail (2)
    }
    MAX-ACCESS  read-only 
    STATUS      current
    DESCRIPTION
    "This oject specifies the step result for Ethernet Service Activation Test"
    ::= { fsEsatStatsEntry 2 }

    fsEsatStatsDuration OBJECT-TYPE
    SYNTAX      Unsigned32
    MAX-ACCESS  read-only 
    STATUS      current
    DESCRIPTION
    "This object specifies the duration of the step of Ethernet Service Activation Test 
    ."
    ::= { fsEsatStatsEntry 3 }

    fsEsatStatsTxPkts OBJECT-TYPE
    SYNTAX      Unsigned32
    MAX-ACCESS  read-only 
    STATUS      current
    DESCRIPTION
    "This object specifies the number of packets transmitted during the step test. If the
    target does not support this counter, this value is maintanined as zero"
    ::= { fsEsatStatsEntry  4 }

    fsEsatStatsTxBytes OBJECT-TYPE
    SYNTAX      Counter64 
    MAX-ACCESS  read-only 
    STATUS      current
    DESCRIPTION
    "This object specifies the number of bytes transmitted during the step test. If the
    target does not support this counter, this value is maintanined as zero "
    ::= { fsEsatStatsEntry 5 }

    fsEsatStatsRxPkts OBJECT-TYPE
    SYNTAX      Unsigned32
    MAX-ACCESS  read-only 
    STATUS      current
    DESCRIPTION
    "This object specifies the number of packets received during the step test. If the
    target does not support this counter, this value is maintained as zero"
    ::= { fsEsatStatsEntry  6 }

    fsEsatStatsRxBytes OBJECT-TYPE
    SYNTAX      Counter64 
    MAX-ACCESS  read-only 
    STATUS      current
    DESCRIPTION
    "This object specifies the number of bytes received during the step test. If the
    target does not support this counter, value shall be zero"
    ::= { fsEsatStatsEntry 7 }

    fsEsatStatsIrMin OBJECT-TYPE
    SYNTAX      Integer32 
    MAX-ACCESS  read-only 
    STATUS      current
    DESCRIPTION
    "This object specifies the Minimum Information Rate for the step test."
    ::= { fsEsatStatsEntry 8 }

    fsEsatStatsIrMean OBJECT-TYPE
    SYNTAX      Integer32 
    MAX-ACCESS  read-only 
    STATUS      current
    DESCRIPTION
    "This object specifies the Mean Information Rate for the step test."
    ::= { fsEsatStatsEntry 9 }

    fsEsatStatsIrMax OBJECT-TYPE
    SYNTAX      Integer32 
    MAX-ACCESS  read-only 
    STATUS      current
    DESCRIPTION
    " This object specifies the Maximum Information Rate for step test."
    ::= { fsEsatStatsEntry 10 }

    fsEsatStatsFrLossCnt OBJECT-TYPE
    SYNTAX      Integer32 
    MAX-ACCESS  read-only 
    STATUS      current
    DESCRIPTION
    "This object specifies the number of frames lost during the step test."
    ::= { fsEsatStatsEntry  11 }

    fsEsatStatsFrLossRatio OBJECT-TYPE
    SYNTAX      Integer32 
    MAX-ACCESS  read-only 
    STATUS      current
    DESCRIPTION
    "This object specifies the Frame Loss Ratio observed during the step test."
    ::= { fsEsatStatsEntry  12 }

    fsEsatStatsFrTxDelayMin OBJECT-TYPE
    SYNTAX      Integer32 
    MAX-ACCESS  read-only 
    STATUS      current
    DESCRIPTION
    "This object specifies the Minimum Frame Transfer Delay observed during the step test."
    ::= { fsEsatStatsEntry  13 }

    fsEsatStatsFrTxDelayMean OBJECT-TYPE
    SYNTAX      Integer32 
    MAX-ACCESS  read-only 
    STATUS      current
    DESCRIPTION
    "This object specifies the Mean Frame Transfer Delay observed during the step test."
    ::= { fsEsatStatsEntry  14 }

    fsEsatStatsFrTxDelayMax OBJECT-TYPE
    SYNTAX      Integer32 
    MAX-ACCESS  read-only 
    STATUS      current
    DESCRIPTION
    "This object specifies the Maximum Frame Transfer Delay observed during the step test."
    ::= { fsEsatStatsEntry  15 }

    fsEsatStatsFrDelayVarMin OBJECT-TYPE
    SYNTAX      Integer32 
    MAX-ACCESS  read-only 
    STATUS      current
    DESCRIPTION
    "This object specifies the Minimum Frame Delay Variation observed during the step test."
    ::= { fsEsatStatsEntry  16 }

    fsEsatStatsFrDelayVarMean OBJECT-TYPE
    SYNTAX      Integer32 
    MAX-ACCESS  read-only 
    STATUS      current
    DESCRIPTION
    "This object specifies the Mean Frame Delay Variation observed during the step test."
    ::= { fsEsatStatsEntry  17 }

    fsEsatStatsFrDelayVarMax OBJECT-TYPE
    SYNTAX      Integer32 
    MAX-ACCESS  read-only 
    STATUS      current
    DESCRIPTION
    "This object specifies the Maximum Frame Delay Variation observed during the step test."
    ::= { fsEsatStatsEntry  18 }

    fsEsatStatsPortStateCounter OBJECT-TYPE
    SYNTAX      Integer32 
    MAX-ACCESS  read-only 
    STATUS      current
    DESCRIPTION
    "This object specifies the number of times the port has toggled during each step test."
    ::= { fsEsatStatsEntry  19 }

END

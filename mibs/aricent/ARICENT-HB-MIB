-- Copyright (C) 2014 Aricent Group . All Rights Reserved

-- $Id: fshb.mib,v 1.4 2015/11/11 08:40:56 siva Exp $

-- ARICENT HB Proprietary MIB Definition
 
ARICENT-HB-MIB DEFINITIONS ::= BEGIN 

IMPORTS
   MODULE-IDENTITY, OBJECT-TYPE,
   Unsigned32,enterprises  FROM SNMPv2-SMI
   ZeroBasedCounter32      FROM RMON2-MIB
   TruthValue              FROM SNMPv2-TC;
    
   fsHb MODULE-IDENTITY 
      LAST-UPDATED "201412100000Z" 
      ORGANIZATION "ARICENT COMMUNICATIONS SOFTWARE" 
      CONTACT-INFO "support@aricent.com" 
      DESCRIPTION 
         "The MIB for Heart Beat module. " 
      REVISION "201412100000Z"
      DESCRIPTION 
         "The MIB for Heart Beat module. " 

   ::= { enterprises aricent-communication-holding-ltd(29601) iss(2) 93 }



-- ----------------------------------------------------------------- -- 
-- groups in the MIB  
-- ----------------------------------------------------------------- -- 
 
      fsHbScalar                    OBJECT IDENTIFIER ::= { fsHb 0 }
      fsHbStatistics                OBJECT IDENTIFIER ::= { fsHb 1 }

-- ---------------------------------------------------------------- --

-- MIB Objects

fsHbInterval OBJECT-TYPE
    SYNTAX     Unsigned32 (10..5000)
    MAX-ACCESS read-write
    STATUS     current
    DESCRIPTION
               "This object specifies the time interval in milli-seconds, between
		the Heart Beat messages. This value should be 4 times lesser than 
		PeerDead Interval. This value must be same for all the nodes in 
		the network."
    DEFVAL { 500 }
    ::= {fsHbScalar 1}

fsHbPeerDeadIntMultiplier OBJECT-TYPE
    SYNTAX     Unsigned32 (4..10)
    MAX-ACCESS read-write
    STATUS     current
    DESCRIPTION
               "This object specifies the multiplier value by which the heart beat
		interval is multiplied to get the peer dead interval.
                ie, Peer Dead Interval = fsHbInterval * fsHbPeerDeadIntMultiplier
                 
                During Mib save restore operation the following mib objects are
                restored in the same order as mentioned below,
                 - fsHbInterval
                 - fsHbPeerDeadIntMultiplier"

    DEFVAL { 4 }
    ::= {fsHbScalar 2}

fsHbTrcLevel OBJECT-TYPE
    SYNTAX     Unsigned32
    MAX-ACCESS read-write
    STATUS     current
    DESCRIPTION
             "This object specifies the trace level required for HB.
              The levels are defined as follows:
              0x00000001 -- Init-Shut Trace.
              0x00000002 -- Management Trace.
              0x00000004 -- Control path Trace.
              0x00000008 -- Critical Trace.
              0x00000010 -- Peer Discovery state machine Trace.
              0x00000020 -- Socket APIs Trace.
              0x00000040 -- Notification Trace.
              0x00000080 -- All failure Trace.
              0x00000100 -- Buffer Trace.
              0x00000200 -- Event Trace.
              0x00000400 -- Packet dump Trace.
              0x00000800 -- SNMP Trace.
	      0x00001000 -- Switchover Trace.
              0x00001FFF -- All Trace."


    DEFVAL { '00000000'H }
    ::= {fsHbScalar 3}

fsHbStatsEnable OBJECT-TYPE
   SYNTAX                   INTEGER {
                              enabled(1),
                              disabled(2)
                                    }
    MAX-ACCESS        read-write
    STATUS            current
    DESCRIPTION
               "This object specifies the option to enable/disable the statistics collection
                of the heart beat module."

    DEFVAL  {enabled}
    ::= {fsHbScalar 4}

fsHbClearStats OBJECT-TYPE
   SYNTAX             TruthValue
    MAX-ACCESS        read-write
    STATUS            current
    DESCRIPTION
               "This object clears the statistics collection of the HeartBeat
                module. The statistics has no effect when the value is 
                set to false. By default, the statistics value is false.
                When it is set to true, the statistics are cleared and
                the value is set back to false. This object always returns
                false when read."

    DEFVAL  {false}
    ::= {fsHbScalar 5}

-- *******************************************************************
--   Statistics Counters
-- *******************************************************************

--
-- TX Statistics
--

fsHbStatsMsgTxCount  OBJECT-TYPE
    SYNTAX      ZeroBasedCounter32
    MAX-ACCESS  read-only
    STATUS      current
    DESCRIPTION
         "This object specifies the total number of heart beat messages successfully sent
          from this node."
    ::= {fsHbStatistics 1}

fsHbStatsMsgTxFailedCount  OBJECT-TYPE
    SYNTAX      ZeroBasedCounter32
    MAX-ACCESS  read-only
    STATUS      current
    DESCRIPTION
         "This object specifies the total number of heart beat messages failed while sending."
    ::= {fsHbStatistics 2}

--
-- RX Statistics
--

fsHbStatsMsgRxCount  OBJECT-TYPE
    SYNTAX      ZeroBasedCounter32
    MAX-ACCESS  read-only
    STATUS      current
    DESCRIPTION
         "This object specifies the  total number of heart beat messages received at this node."
    ::= {fsHbStatistics 3}

fsHbStatsMsgRxProcCount OBJECT-TYPE
    SYNTAX      ZeroBasedCounter32
    MAX-ACCESS  read-only
    STATUS      current
    DESCRIPTION
         "This object specifies total number of heart beat messages received and processed at this 
          node successfully."
    ::= {fsHbStatistics 4}

fsHbStatsRxFailedCount OBJECT-TYPE
    SYNTAX      ZeroBasedCounter32
    MAX-ACCESS  read-only
    STATUS      current
    DESCRIPTION
         "This object specifies total number of heart beat messages failed while processing in this node."
    ::= {fsHbStatistics 5}
END

-- Copyright (C) 2009-2012 Aricent Group . All Rights Reserved

-- /********************************************************************
--  * $Id: fshttp.mib,v 1.5 2013/02/12 12:10:45 siva Exp $
--  *
--  * Description: MIB for http module. 
--  *******************************************************************/

-- Introduction

-- This document explains the propreitary MIB implemented for the HTTP
-- product.

-- The proprietary MIB definitions, which contains MIB table for
-- redirection feature for HTTP and MIBs for HTTP authentication scheme.
-- For futher reading on HTTP Redirection or HTTP Authentication, refer 
-- RFC .

-- The scalars in this MIB

-- fsHttpRedirectionStatus		This scalar holds the status of HTTP 
--                                      redirection feature.

-- fsOperHttpAuthScheme         This scalar holds the HTTP authentication 
--                              scheme used to authenticate the HTTP 
--                              sessions. This value is set only once at 
--                              startup and cannot be modified on-the-fly.

-- fsConfigHttpAuthScheme       This scalar holds the HTTP authentication 
--                              scheme that can be modified at run time. The 
--                              new value of the authentication scheme gets 
--                              reflected only when the ISS configuration is
--                              saved and restored after an ISS restart.

-- The Tables in the MIB

-- fsHttpRedirectionTable    This index of table is URL which needs to be 
--                           redirected, elements are IP Address and Domain 
--                           Name of the HTTP server where this URL has to be 
--                           redirected, ONE can specify any one of IP address
--                           or Domain Name.

-- Management Information Base for HTTP Product

ARICENT-HTTP-MIB DEFINITIONS ::= BEGIN

IMPORTS
    MODULE-IDENTITY, OBJECT-TYPE,
    enterprises                      FROM SNMPv2-SMI
    RowStatus, DisplayString	     FROM SNMPv2-TC
    InetAddress, InetAddressType     FROM INET-ADDRESS-MIB;

fsHttpMIB MODULE-IDENTITY
    LAST-UPDATED "201209050000Z"
    ORGANIZATION "ARICENT COMMUNICATIONS SOFTWARE" 
    CONTACT-INFO "support@aricent.com" 
         DESCRIPTION	 "The MIB module for management of HTTP Routers
                    Initial Version"
	 REVISION "201209050000Z"
         DESCRIPTION	 "The MIB module for management of HTTP Routers
                    Initial Version"
	 ::= { enterprises aricent-communication-holding-ltd(29601) iss(2) 44 }

fsHttpMIBObjects   OBJECT IDENTIFIER ::= { fsHttpMIB 1 }
futureHttpScalars  OBJECT IDENTIFIER ::= { fsHttpMIBObjects 1 }
futureHttpTables   OBJECT IDENTIFIER ::= { fsHttpMIBObjects 2 }


-- SCALAR_TABLE_BEGIN

--
-- Start of mib objects for controlling the status of HTTP redirection
--


fsHttpRedirectionStatus OBJECT-TYPE
    SYNTAX	    INTEGER { disabled (1), enabled (2) } 
    MAX-ACCESS	    read-write 
    STATUS	    current
    DESCRIPTION
	    "The status of the HTTP redirection"
    DEFVAL     { 1 }
    ::= { futureHttpScalars 1 }

--
-- End of mib objects for controlling the status of HTTP redirection
--
--
-- Start of mib objects for controlling HTTP authentication
--

fsOperHttpAuthScheme OBJECT-TYPE
    SYNTAX      INTEGER { default (0), basic (1), digest (2) }
    MAX-ACCESS  read-only
    STATUS      current
    DESCRIPTION
        "This MIB holds the operational HTTP Authentication scheme value.
         This value is initialized on ISS start up and cannot be modified
         at run-time. This value is used to authenticate all the HTTP sessions.
         During ISS startup,this operational value is read and initialised
         from the MIB object fsConfigHttpAuthScheme.
         The value digest refers to the Digest authentication scheme of RFC 2617.
         The value basic refers to the Basic authentication scheme of RFC 2617.
         The value default refers proprietary Form-based
         authentication scheme."
    DEFVAL      { 0 }
    ::= { futureHttpScalars 2 }

fsConfigHttpAuthScheme OBJECT-TYPE
    SYNTAX      INTEGER { default (0), basic (1), digest (2) }
    MAX-ACCESS  read-write
    STATUS      current
    DESCRIPTION
        "This MIB holds the configured HTTP Authentication scheme value.
         This value can be modified at run time. The modified value is stored
         in a conf file and applied during the next start up of ISS.
         The value digest refers to the Digest authentication scheme of RFC 2617.
         The value basic refers to the Basic authentication scheme of RFC 2617.
         The value default refers proprietary Form-based
         authentication scheme."
    DEFVAL     { 0 }
    ::= { futureHttpScalars 3 }

fsHttpRequestCount OBJECT-TYPE
    SYNTAX  INTEGER
    MAX-ACCESS read-write
    STATUS current
    DESCRIPTION
         "The number of HTTP request packets received. The purpose of having this statistics
          counter object as read-write access(instead of read only) is to clear the counter 
		  when needed. "
    DEFVAL     { 0 }
    ::= { futureHttpScalars 4 }

fsHttpRequestDiscards OBJECT-TYPE
    SYNTAX  INTEGER
    MAX-ACCESS read-write
    STATUS current
    DESCRIPTION
         "The number of HTTP packets discarded.  The purpose of having this statistics
          counter object as read-write access(instead of read only) is to clear the counter
          when needed."
    DEFVAL     { 0 }
    ::= { futureHttpScalars 5 }
--
-- End of mib objects for controlling HTTP authentication
--

-- SCALAR_TABLE_END

--
-- The HTTP Redirection Information Table
--

fsHttpRedirectionTable OBJECT-TYPE
    SYNTAX     SEQUENCE OF FsHttpRedirectionEntry
    MAX-ACCESS not-accessible
    STATUS     current
    DESCRIPTION
              "The (conceptual) table listing the Redirection related objects"
    ::= { futureHttpTables 1 }

fsHttpRedirectionEntry OBJECT-TYPE
    SYNTAX     FsHttpRedirectionEntry
    MAX-ACCESS not-accessible
    STATUS     current
    DESCRIPTION
	    "An entry (conceptual row) in the fsHttpRedirectionTable."
    INDEX      { fsHttpRedirectionURL }
    ::= { fsHttpRedirectionTable 1 }

FsHttpRedirectionEntry ::= SEQUENCE {
    fsHttpRedirectionURL	   DisplayString,
    fsHttpRedirectedSrvAddrType    InetAddressType,
    fsHttpRedirectedSrvIP          InetAddress,
    fsHttpRedirectedSrvDomainName  DisplayString,
    fsHttpRedirectionEntryStatus   RowStatus
}

fsHttpRedirectionURL OBJECT-TYPE
    SYNTAX     DisplayString (SIZE (100))
    MAX-ACCESS not-accessible
    STATUS     current
    DESCRIPTION
	    "The URL which has to be redirected"
    ::= { fsHttpRedirectionEntry 1 }

fsHttpRedirectedSrvAddrType OBJECT-TYPE
    SYNTAX            InetAddressType
    MAX-ACCESS        read-write
    STATUS            current
    DESCRIPTION
            "The Address type of HTTP server to which URL has to be 
              redirected"
     ::= { fsHttpRedirectionEntry 2 }

fsHttpRedirectedSrvIP OBJECT-TYPE
    SYNTAX     InetAddress
    MAX-ACCESS read-write
    STATUS     current
    DESCRIPTION
          " The IP address of the HTTP Server to which redirect has to be done
          interface belongs to"   
    ::= { fsHttpRedirectionEntry 3 }      


fsHttpRedirectedSrvDomainName OBJECT-TYPE
    SYNTAX           DisplayString
    MAX-ACCESS       read-write
    STATUS           current
    DESCRIPTION
            "The domain name of the HTTP server to which the URL has to be 
              has to redirected"
    ::= { fsHttpRedirectionEntry 4 }

fsHttpRedirectionEntryStatus OBJECT-TYPE
    SYNTAX           RowStatus 
    MAX-ACCESS       read-create
    STATUS           current
    DESCRIPTION
            "The status of HTTP redirection table entry"
    ::= { fsHttpRedirectionEntry 5 }

END

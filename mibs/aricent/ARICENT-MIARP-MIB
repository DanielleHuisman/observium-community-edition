-- Copyright (C) 2009-2012 Aricent Group . All Rights Reserved

-- $Id: fsmparp.mib,v 1.5 2015/09/13 09:21:51 siva Exp $

-- ARP Proprietary MI MIB.

-- The MIB contains the table used to configure ARP functionaly.

 ARICENT-MIARP-MIB DEFINITIONS ::= BEGIN

 IMPORTS
    OBJECT-TYPE, MODULE-IDENTITY, Integer32,
    enterprises            FROM SNMPv2-SMI
    fsMIStdIpContextId     FROM ARICENT-MISTD-IPVX-MIB;

    fsMiArp MODULE-IDENTITY
    LAST-UPDATED "201209050000Z"
    ORGANIZATION "ARICENT COMMUNICATIONS SOFTWARE"
    CONTACT-INFO "support@aricent.com"
    DESCRIPTION
        "The proprietary MIB module for ARP. The MIB provides
         objects for configuring arp functionality."
    REVISION "201209050000Z"
    DESCRIPTION
        "The proprietary MIB module for ARP. The MIB provides
         objects for configuring arp functionality."
        ::=  { enterprises aricent-communication-holding-ltd(29601) iss(2) 33 }

-- The Arp Configuration Table
   
    fsMIArpTable OBJECT-TYPE
    SYNTAX SEQUENCE OF FsMIArpEntry
    MAX-ACCESS not-accessible
    STATUS     current
    DESCRIPTION
        "Table to store the virtual router specific arp configurations"
    ::= {fsMiArp 1}

    fsMIArpEntry OBJECT-TYPE
    SYNTAX     FsMIArpEntry
    MAX-ACCESS not-accessible
    STATUS     current
    DESCRIPTION
        "Each entry has arp configuration information for the Virtual router"
    INDEX { fsMIStdIpContextId }
    ::= {fsMIArpTable 1}

    FsMIArpEntry ::= SEQUENCE {
        fsMIArpCacheTimeout        Integer32,
        fsMIArpCachePendTime       Integer32,
        fsMIArpMaxRetries          Integer32,
        fsMIArpPendingEntryCount   Integer32,
        fsMIArpCacheEntryCount     Integer32,
        fsMIArpContextDebug        Integer32
    }

    fsMIArpCacheTimeout OBJECT-TYPE
    SYNTAX     Integer32 (30..86400)
    MAX-ACCESS read-write
    STATUS     current
    DESCRIPTION
        "Time after which the entry in cache is deleted"
    DEFVAL {7200}
    ::= {fsMIArpEntry 1}

    fsMIArpCachePendTime OBJECT-TYPE
    SYNTAX     Integer32 (30..3000)
    MAX-ACCESS read-write
    STATUS     current
    DESCRIPTION
        "Time for which an unresolved entry will be
         held until response is received "
    DEFVAL { 30 }
    ::= {fsMIArpEntry 2}

    fsMIArpMaxRetries OBJECT-TYPE
    SYNTAX     Integer32 (2..10)
    MAX-ACCESS read-write
    STATUS     current
    DESCRIPTION
        "Maximum number of retry attempts before aborting resolving."
    DEFVAL { 3 }
    ::= {fsMIArpEntry 3}

   fsMIArpPendingEntryCount  OBJECT-TYPE
        SYNTAX   Integer32 
        MAX-ACCESS   read-only
        STATUS   current
        DESCRIPTION " Number of pending or ageout entries in the ARP Cache
  		    database "
        ::= { fsMIArpEntry 4 }

   fsMIArpCacheEntryCount  OBJECT-TYPE
        SYNTAX   Integer32 
        MAX-ACCESS   read-only
        STATUS   current
        DESCRIPTION " Number of ARP Cache entries in the ARP Cache
  		    database "
        ::= { fsMIArpEntry 5 }

   fsMIArpContextDebug  OBJECT-TYPE
       SYNTAX   Integer32 (0..255)
       MAX-ACCESS read-write
       STATUS   current
       DESCRIPTION
           "Enables the tracing in the ARP. A 32 bit integer
           is used to store the Tracing level in the specified module.
           Different Tracing Levels -
           BIT 0 - Initialisation and Shutdown Trace.
           BIT 1 - Management trace.
           BIT 2 - Data path trace.
           BIT 3 - Control Plane trace.
           BIT 4 - Packet Dump.
           BIT 5 - OS Resource trace.
           BIT 6 - All Failure trace (All failures including Packet Validation)
           BIT 7 - Buffer Trace."
       DEFVAL { 0 }
       ::= { fsMIArpEntry 6 }

 END

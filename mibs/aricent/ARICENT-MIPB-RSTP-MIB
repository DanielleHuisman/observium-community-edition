-- Copyright (C) 2016.Aricent. All Rights Reserved.

-- $Id: fsmpbrst.mib,v 1.6 2016/02/28 10:54:47 siva Exp $

ARICENT-MIPB-RSTP-MIB DEFINITIONS ::= BEGIN

-- ------------------------------------------------------------------
-- Proprietary MIB for C-VLAN component Rapid Spanning Tree Protocol
-- in Provider Bridges
-- ------------------------------------------------------------------

IMPORTS

   OBJECT-TYPE, MODULE-IDENTITY, Integer32,Counter32,
   TimeTicks, enterprises FROM SNMPv2-SMI
   TEXTUAL-CONVENTION, TruthValue FROM SNMPv2-TC
   Timeout, BridgeId FROM BRIDGE-MIB;

futureMIPbRstMIB MODULE-IDENTITY
    LAST-UPDATED "201209050000Z"
    ORGANIZATION "ARICENT COMMUNICATIONS SOFTWARE"
    CONTACT-INFO "support@aricent.com"
    DESCRIPTION "MIB for Rapid Spanning Tree Algorithm & Protocol in C-VLAN
                 component of Provider Bridges"
    REVISION "201209050000Z"
    DESCRIPTION "MIB for Rapid Spanning Tree Algorithm & Protocol in C-VLAN
                 component of Provider Bridges"
::= { enterprises futuresoftware(2076) 134 }

EnabledStatus ::= TEXTUAL-CONVENTION
    STATUS      current
    DESCRIPTION
        "A simple status value for the object." 
    SYNTAX      INTEGER { enabled(1), disabled(2) }


VlanId ::= TEXTUAL-CONVENTION
    STATUS      current
    DESCRIPTION
        "This value and the CEP port identifier are indices to C-VLAN port 
        tables. Values 1 to 4095 are permitted. Values from 1 to 4094 
        represents S-VLAN id. (CEP, 4095) identifies the CEP port in the
        C-VLAN component."
    SYNTAX      Integer32 (1..4095)


futureMIPbRst     OBJECT IDENTIFIER ::= { futureMIPbRstMIB 1 }

-- Provider Bridges C-VLAN component RSTP Port Extention Group 

fsMIPbRstContextInfoTable OBJECT-TYPE
   SYNTAX        SEQUENCE OF FsMIPbRstContextInfoEntry
   MAX-ACCESS    not-accessible
   STATUS        current
   DESCRIPTION
      "This object specifies the list of Provider Bridge related objects that
       can be configured per Virtual Context in the system."
   ::= { futureMIPbRst 1 }

fsMIPbRstContextInfoEntry OBJECT-TYPE
   SYNTAX        FsMIPbRstContextInfoEntry
   MAX-ACCESS    not-accessible
   STATUS        current
   DESCRIPTION
    "This object specifies the Virtual Context based Provider Bridge objects."
   INDEX { fsMIPbRstContextId }
   ::= { fsMIPbRstContextInfoTable 1 }

FsMIPbRstContextInfoEntry ::=
    SEQUENCE {
        fsMIPbRstContextId
           Integer32,
        fsMIPbProviderStpStatus
           EnabledStatus
}

fsMIPbRstContextId OBJECT-TYPE
   SYNTAX       Integer32 (0..65535)
   MAX-ACCESS   not-accessible
   STATUS       current
   DESCRIPTION
      "Identifies a Virtual Context."
   ::= { fsMIPbRstContextInfoEntry 1 }
 

fsMIPbProviderStpStatus OBJECT-TYPE
   SYNTAX      EnabledStatus
   MAX-ACCESS  read-write
   STATUS      current
   DESCRIPTION
      "This object specifies the administrative module status requested by
       management for the spanning tree operation in S-VLAN component of 
       Provider Bridges.This enables or disables spanning tree protocol 
       (RSTP/MSTP)on S-VLAN component ports.The status SET for this object 
       is applicable only for the Virtual Context identified by the Virtual
       Context Id in this entry.A value of 'enabled' (1) indicates that the
       spanning tree protocol will be enabled on all the ports of the S-VLAN
       component.A value of 'disabled'(2) indicates that the spanning tree 
       protocol will be disabled on all the ports of the S-VLAN component. 
       This object can be set only after the object fsRstSystemControl has 
       been set."

   ::= {fsMIPbRstContextInfoEntry 2}

fsMIPbRstCVlanBridgeTable OBJECT-TYPE
   SYNTAX SEQUENCE OF FsMIPbRstCVlanBridgeEntry
   MAX-ACCESS not-accessible
   STATUS     current
   DESCRIPTION
      "This table contains bridge related informatin for RSTP operation in the
       C-VLAN component."
   ::= { futureMIPbRst 2 }

fsMIPbRstCVlanBridgeEntry OBJECT-TYPE
   SYNTAX      FsMIPbRstCVlanBridgeEntry
   MAX-ACCESS  not-accessible
   STATUS      current
   DESCRIPTION
      "This object specifies each entry in this table which is for each C-VLAN
       component in Provider Bridges."
   INDEX { fsMIPbRstPort }
   ::= { fsMIPbRstCVlanBridgeTable 1 }

   FsMIPbRstCVlanBridgeEntry ::=
   SEQUENCE {
         fsMIPbRstPort                            Integer32,
         fsMIPbRstCVlanBridgeId                   BridgeId,
         fsMIPbRstCVlanBridgeDesignatedRoot       BridgeId,
         fsMIPbRstCVlanBridgeRootCost             Integer32,
         fsMIPbRstCVlanBridgeMaxAge               Timeout,
         fsMIPbRstCVlanBridgeHelloTime            Timeout,
         fsMIPbRstCVlanBridgeHoldTime             Integer32,
         fsMIPbRstCVlanBridgeForwardDelay         Timeout,
         fsMIPbRstCVlanBridgeTxHoldCount          Integer32,
         fsMIPbRstCVlanStpHelloTime               Timeout,
         fsMIPbRstCVlanStpMaxAge                  Timeout,
         fsMIPbRstCVlanStpForwardDelay            Timeout,
         fsMIPbRstCVlanStpTopChanges              Counter32,
         fsMIPbRstCVlanStpTimeSinceTopologyChange TimeTicks,
         fsMIPbRstCVlanStpDebugOption             Integer32

   }

fsMIPbRstPort OBJECT-TYPE
    SYNTAX Integer32(0..65535)
    MAX-ACCESS not-accessible
    STATUS current
    DESCRIPTION
       " This object specifies the port which is of type CEP. CEP port
       will be the index of the CVLAN Spanning tree."
       ::= { fsMIPbRstCVlanBridgeEntry 1 }


fsMIPbRstCVlanBridgeId OBJECT-TYPE
    SYNTAX  BridgeId
    MAX-ACCESS  read-only
    STATUS  current
    DESCRIPTION
       "This object specifies the Bridge-Identifier as used in the Spanning
        Tree Protocol operation in the C-VLAN component to uniquely identify 
        a bridge.Bridge Mac address field in this object will be the MAC
        address of the corresponding customer edge port.
        The Bridge priority field in this object will be always 0xf.
        The Bridge Identifier System Id extension field in this object will be 
        always 0xfff."
    ::= { fsMIPbRstCVlanBridgeEntry 2 }

fsMIPbRstCVlanBridgeDesignatedRoot OBJECT-TYPE
    SYNTAX  BridgeId
    MAX-ACCESS  read-only
    STATUS  current
    DESCRIPTION
       "This object specifies the bridge identifier of the root of the spanning
        tree as determined by the Spanning Tree Protocol as executed by this 
        C-VLAN component. This value is used as the Root Identifier parameter
        in all Configuration Bridge PDUs originated by this C-VLAN component."
       
    ::= { fsMIPbRstCVlanBridgeEntry 3 }

fsMIPbRstCVlanBridgeRootCost OBJECT-TYPE
    SYNTAX  Integer32
    MAX-ACCESS  read-only
    STATUS  current
    DESCRIPTION
       "This object specifies the cost of the path to the root as seen from 
        this C-VLAN component bridge."

    ::= { fsMIPbRstCVlanBridgeEntry 4 }

fsMIPbRstCVlanBridgeMaxAge OBJECT-TYPE
    SYNTAX  Timeout
    MAX-ACCESS  read-only
    STATUS  current
    DESCRIPTION
    "This object specifies the value that all bridges use for MaxAge when 
     this bridge is acting as the root.  Note that 802.1D-1990 specifies that
     the range for this parameter is related to the value of 
     dot1dStpBridgeHelloTime.The granularity of this timer is specified by
     802.1D-1990 to be 1 second.An agent may return a badValue error if a set 
     is attempted to a value which is not a whole number of seconds."
    ::= { fsMIPbRstCVlanBridgeEntry 5 }

fsMIPbRstCVlanBridgeHelloTime OBJECT-TYPE
    SYNTAX  Timeout
    MAX-ACCESS  read-only
    STATUS  current
    DESCRIPTION
    "This object specifies the value that all bridges use for HelloTime when
    this bridge is acting as the root.  The granularity of this
    timer is specified by 802.1D- 1990 to be  1 second. An agent
    may return a badValue error if a set is attempted to a value
    which is  not  a  whole number of seconds."
    ::= { fsMIPbRstCVlanBridgeEntry 6 }

fsMIPbRstCVlanBridgeHoldTime OBJECT-TYPE
    SYNTAX  Integer32
    MAX-ACCESS  read-only
    STATUS  current
    DESCRIPTION
      "This object specifies the time value which determines the interval
       length during which no more than two Configuration bridge PDUs shall be
       transmitted by this C-VLAN component, in units of hundredths of a
       second."
    ::= { fsMIPbRstCVlanBridgeEntry 7 }

fsMIPbRstCVlanBridgeForwardDelay OBJECT-TYPE
    SYNTAX  Timeout
    MAX-ACCESS  read-only
    STATUS  current
    DESCRIPTION
    "This object specifies the value that all bridges use for ForwardDelay 
     when this bridge is acting as the root.Note that 802.1D-1990 specifies
     that the range for this parameter is related to the value of
     dot1dStpBridgeMaxAge.The granularity of this timer is specified 
     by 802.1D-1990 to be 1 second. An agent may return a badValue error if a
     set is attempted to a value which is not a whole number of seconds."
    ::= { fsMIPbRstCVlanBridgeEntry 8 }

fsMIPbRstCVlanBridgeTxHoldCount  OBJECT-TYPE
   SYNTAX  Integer32
   MAX-ACCESS read-only
   STATUS  current
   DESCRIPTION
         "This object specifies the value used by the Port Transmit state
          machine to limit the maximum transmission rate."
   ::= { fsMIPbRstCVlanBridgeEntry 9 }


fsMIPbRstCVlanStpHelloTime OBJECT-TYPE
   SYNTAX  Timeout
   MAX-ACCESS read-only
   STATUS  current
   DESCRIPTION
   "This object specifies the amount of time between the transmissions of
    Configuration bridge PDUs by this C-VLAN component on any port when it
    is the root of the spanning tree or trying to become so, in units of
    hundredths of a second.This is the actual value that this bridge is
    currently using."
   ::= { fsMIPbRstCVlanBridgeEntry 10 }

 
 fsMIPbRstCVlanStpMaxAge OBJECT-TYPE
   SYNTAX  Timeout
   MAX-ACCESS read-only
   STATUS  current
   DESCRIPTION
   "This object specifies the maximum age of Spanning Tree Protocol information
    learned from the network on any port before it is discarded, 
    in units of hundredths of a second. This is the actual value that this 
    bridge is currently using."
   ::= { fsMIPbRstCVlanBridgeEntry 11 }

  
 fsMIPbRstCVlanStpForwardDelay OBJECT-TYPE
   SYNTAX  Timeout
   MAX-ACCESS read-only
   STATUS  current
   DESCRIPTION
   "This object specifies the time value, measured in units of hundredths
    of a second, controls how fast a port changes its spanning state when
    moving towards the Forwarding state.The value determines how long the
    port stays in each of the Listening and Learning states, which precede 
    the Forwarding state. This value is also used,when a topology change has
    been detected and is underway, to age all dynamic entries in the
    Forwarding Database. [Note that this value is the one that this bridge is
    currently using, in contrast to dot1dStpBridgeForwardDelay which is the
    value that this bridge and all others would start using if/when this bridge
    were to become the root.]"
   ::= { fsMIPbRstCVlanBridgeEntry 12 }


   fsMIPbRstCVlanStpTopChanges OBJECT-TYPE
   SYNTAX  Counter32
   MAX-ACCESS  read-only
   STATUS  current
   DESCRIPTION
   "This object specifies the total number of topology changes detected by
    this bridge since the management entity was last reset or initialized."
   ::=  { fsMIPbRstCVlanBridgeEntry 13 }

   fsMIPbRstCVlanStpTimeSinceTopologyChange OBJECT-TYPE
   SYNTAX  TimeTicks 
   MAX-ACCESS  read-only
   STATUS  current
   DESCRIPTION
   "This object specifies the time (in hundredths of a second) since the last 
    time a topology change was detected by the bridge entity."
   ::= { fsMIPbRstCVlanBridgeEntry 14 }


fsMIPbRstCVlanStpDebugOption OBJECT-TYPE
   SYNTAX      Integer32 (0..524287)
   MAX-ACCESS  read-write
   STATUS      current
   DESCRIPTION
      "This object is used to enable customer spanning-tree Debug Statements 
       in the STP Module.

       A FOUR BYTE integer is used for enabling the level of debugging. 
       Each BIT in the four byte integer, represents a particular 
       level of Debug. 

       The mapping between the bit positions & the level of debug is 
       as follows: 
       0 - Init and Shutdown Debug statements
       1 - Management Debug statements
       2 - Memory related Debug statements
       3 - BPDU related Debug statements
       4 - Event Handling Debug statements
       5 - Timer Module Debug statements
       6 - Port Information SEM Debug statements
       7 - Port Receive SEM Debug statements
       8 - Role Selection SEM Debug statements
       9 - Role Transition SEM Debug statements
      10 - State Transition SEM Debug statements
      11 - Protocol Migration SEM Debug statements
      12 - Topology Change SEM Debug statements
      13 - Port Transmit SEM Debug statements
      14 - Bridge Detection SEM Debug statements
      15 - All Failure Debug statements
      16 - Redundancy code flow Debug statements
      17 - State Machine variable changes Debug statements
      18 - Port Receive Pseudo Information SEM Debug statements

      The remaining bits are unused. Combination of debug levels are 
      also allowed.

      For example if the bits 0 and 1 are set, then the Debug
      statements related to Init-Shutdown and management 
      will be printed.

      The user has to enter the corresponding INTEGER VALUE for the
      bits set. For example if bits 0 and 1 are to be set then user has
      to give the value for this object as 3."
      DEFVAL  { 0 }
   ::= { fsMIPbRstCVlanBridgeEntry 15 } 



fsMIPbRstCVlanPortInfoTable OBJECT-TYPE
   SYNTAX SEQUENCE OF FsMIPbRstCVlanPortInfoEntry
   MAX-ACCESS not-accessible
   STATUS     current
   DESCRIPTION
      "This table contains the objects for RSTP in C-VLAN component of Provider 
       Bridges."
   ::= { futureMIPbRst 3 }

fsMIPbRstCVlanPortInfoEntry OBJECT-TYPE
   SYNTAX      FsMIPbRstCVlanPortInfoEntry
   MAX-ACCESS  not-accessible
   STATUS      current
   DESCRIPTION
      "This object specifies each entry in this table which is for each C-VLAN
       component in Provider Bridges. Here the port represents the Ports 
       (CEP/PEPs) of C-VLAN component. Each table entry gives the spanning tree
       information for the Customer Edge Port and Provider Edge Ports of C-VLAN
       components in Provider Bridges."
   INDEX { fsMIPbRstPort,fsMIPbRstCepSvid }
   ::= { fsMIPbRstCVlanPortInfoTable 1 }

FsMIPbRstCVlanPortInfoEntry ::=
   SEQUENCE {
      fsMIPbRstCepSvid 
         VlanId,
      fsMIPbRstCVlanPortPriority
         Integer32,
      fsMIPbRstCVlanPortPathCost
         Integer32,
      fsMIPbRstCVlanPortRole
         INTEGER,
      fsMIPbRstCVlanPortState
         INTEGER,
      fsMIPbRstCVlanPortAdminEdgePort
         TruthValue,
      fsMIPbRstCVlanPortOperEdgePort
         TruthValue,
      fsMIPbRstCVlanPortAdminPointToPoint
         INTEGER,
      fsMIPbRstCVlanPortOperPointToPoint
         TruthValue,
      fsMIPbRstCVlanPortAutoEdge
         TruthValue,
      fsMIPbRstCVlanPortDesignatedRoot
         BridgeId,
      fsMIPbRstCVlanPortDesignatedCost
         Integer32,
      fsMIPbRstCVlanPortDesignatedBridge
         BridgeId,
      fsMIPbRstCVlanPortDesignatedPort
         OCTET STRING,
      fsMIPbRstCVlanPortForwardTransitions
         Counter32
      }


fsMIPbRstCepSvid OBJECT-TYPE
    SYNTAX VlanId
    MAX-ACCESS not-accessible 
    STATUS  current
    DESCRIPTION
        "This object and the CEP port identifier are indices to C-VLAN port 
        tables. Values 1 to 4095 are permitted. Values from 1 to 4094 
        represents S-VLAN id. (CEP, 4095) identifies the CEP port in the
        C-VLAN component."
    ::= {fsMIPbRstCVlanPortInfoEntry 1}
    

fsMIPbRstCVlanPortPriority OBJECT-TYPE
    SYNTAX  Integer32 (0..255)
    MAX-ACCESS  read-only
    STATUS  current
    DESCRIPTION
        "This object specifies the value of the priority field which is 
         contained in the first in network byte order) octet of the (2 octet
         long) Port ID.  
         The other octet of the Port ID is given by the value of fsMIPbRstPort.
         Priority is always assumed as 32 for C-VLAN component Ports."
         
    REFERENCE
         "IEEE 802.1D-1990: Section 4.5.5.1"
    ::= { fsMIPbRstCVlanPortInfoEntry 2 }

fsMIPbRstCVlanPortPathCost OBJECT-TYPE
    SYNTAX  Integer32 (1..65535)
    MAX-ACCESS  read-only
    STATUS  current
    DESCRIPTION
         "This object specifies the contribution of this port to the path cost
          of paths towards the spanning tree root which include this port.
          802.1D-1990 recommends that the default value of this parameter be
          in inverse proportion to the speed of the attached LAN.
          Pathcost is always assumed as 128 for Provider Edge Ports.
          For CEP, port-path cost will be taken from dot1dStpPortPathCost of
          fsMIPbRstPort."
         
    REFERENCE
          "IEEE 802.1D-1990: Section 4.5.5.3"
    ::= { fsMIPbRstCVlanPortInfoEntry 3 }

fsMIPbRstCVlanPortRole OBJECT-TYPE
   SYNTAX      INTEGER {
                  disabledPort(0),
                  alternatePort(1),
                  backupPort(2),
                  rootPort(3),
                  designatedPort(4)
               }
   MAX-ACCESS  read-only
   STATUS      current
   DESCRIPTION
         "This object specifies the current Port Role assumed by this Port."
   ::= { fsMIPbRstCVlanPortInfoEntry 4 }

fsMIPbRstCVlanPortState OBJECT-TYPE
    SYNTAX  INTEGER {
                     disabled(1),
                     blocking(2),
                     listening(3),
                     learning(4),
                     forwarding(5),
                     broken(6)
                 }
    MAX-ACCESS  read-only
    STATUS  current
    DESCRIPTION
          "This object specifies the port's current state as defined by 
          application of the Spanning Tree Protocol.This state controls what
          action a port takes on reception of a frame.  If the bridge has
          detected a port that is malfunctioning it will place that port into
          the broken(6) state.For ports which are disabled
          (see dot1dStpPortEnable), this object will have a value of 
          disabled(1)."
    REFERENCE
          "IEEE 802.1D-1990: Section 4.5.5.2"
    ::= { fsMIPbRstCVlanPortInfoEntry 5 }

fsMIPbRstCVlanPortAdminEdgePort OBJECT-TYPE
    SYNTAX      TruthValue
    MAX-ACCESS  read-only
    STATUS      current
    DESCRIPTION
        "This object specifies the administrative value of the Edge Port
         parameter.A value of TRUE(1) indicates that this port should be
         assumed as an edge-port and a value of FALSE(2) indicates
         that this port should be assumed as a non-edge-port.
         This is always 'false' for a Provider Egde Port."
         
    REFERENCE
        "IEEE 802.1t clause 14.8.2, 18.3.3"
    ::= { fsMIPbRstCVlanPortInfoEntry 6 }

fsMIPbRstCVlanPortOperEdgePort OBJECT-TYPE
    SYNTAX      TruthValue
    MAX-ACCESS  read-only
    STATUS      current
    DESCRIPTION
        "This object specifies the operational value of the Edge Port 
        parameter.This object always assumes the value of 'False' for 
        Provider Edge Ports of C-VLAN component."
    REFERENCE
        "IEEE 802.1t clause 14.8.2, 18.3.4"
    ::= { fsMIPbRstCVlanPortInfoEntry 7 }

fsMIPbRstCVlanPortAdminPointToPoint OBJECT-TYPE
    SYNTAX      INTEGER {
                    forceTrue(0),
                    forceFalse(1),
                    auto(2)
                }
    MAX-ACCESS  read-only
    STATUS      current
    DESCRIPTION
        "This object specifies the administrative point-to-point status of the
         LAN segment attached to this port.A value of forceTrue(0) indicates
         that this port should always be treated as if it is connected to
         a point-to-point link. A value of forceFalse(1) indicates that this port
         should be treated as having a shared media connection. A value of
         auto(2) indicates that this port is considered to have a point-to-point
         link if it is an Aggregator and all of its members are aggregatable,
         or if the MAC entity is configured for full duplex operation, either
         through auto-negotiation or by management means.Provider Edge Ports 
         always assume the value of 'auto' for this object."
   REFERENCE
       "IEEE 802.1w clause 6.4.3, 6.5, 14.8.2"
   ::= { fsMIPbRstCVlanPortInfoEntry 8 }

fsMIPbRstCVlanPortOperPointToPoint OBJECT-TYPE
    SYNTAX      TruthValue
    MAX-ACCESS  read-only
    STATUS      current
    DESCRIPTION
        "This object specifies the operational point-to-point status of the LAN
         segment attached to this port.  It indicates whether a port is
         considered to have a point-to-point connection or not.
         This object will be set to 'True' for Provider Edge Ports 
         when the S-VLAN is attached to only two customer interfaces. 
         This will be set to 'False' when the S-VLAN is attached 
         to more than two customer interfaces."
     
    REFERENCE
        "IEEE 802.1w clause 6.4.3, 6.5, 14.8.2"
    ::= { fsMIPbRstCVlanPortInfoEntry 9 }

fsMIPbRstCVlanPortAutoEdge OBJECT-TYPE
    SYNTAX      TruthValue
    MAX-ACCESS  read-only
    STATUS      current
    DESCRIPTION
        " This object when TRUE(1) indicates that detection of a port 
         as Edge Port happens automatically and FALSE(2) 
         indicates that this feature is disabled.This object is always set to
         'True' for Provider Edge Ports of C-VLAN component."
    
    ::= { fsMIPbRstCVlanPortInfoEntry 10 }

fsMIPbRstCVlanPortDesignatedRoot OBJECT-TYPE
    SYNTAX  BridgeId
    MAX-ACCESS  read-only
    STATUS  current
    DESCRIPTION
       "This object specifies the unique Bridge Identifier of the Bridge
        recorded as the Root in the Configuration BPDUs transmitted by the
        Designated Bridge for the segment to which this port is attached."
    REFERENCE
       "IEEE 802.1D-1990: Section 4.5.5.4"

    ::= { fsMIPbRstCVlanPortInfoEntry 11 }

fsMIPbRstCVlanPortDesignatedCost OBJECT-TYPE
    SYNTAX  Integer32
    MAX-ACCESS  read-only
    STATUS  current
    DESCRIPTION
       "This object specifies the  path cost of the Designated Port of the
        segment connected to this port.This value is compared to the Root Path
        Cost field in received bridge PDUs."
    REFERENCE
       "IEEE 802.1D-1990: Section 4.5.5.5"
    ::= { fsMIPbRstCVlanPortInfoEntry 12 }

fsMIPbRstCVlanPortDesignatedBridge OBJECT-TYPE
   SYNTAX  BridgeId
   MAX-ACCESS  read-only
   STATUS  current
   DESCRIPTION
      "This object specifies the Bridge Identifier of the bridge which this
       port considers to be the Designated Bridge for this port's segment."
   REFERENCE
      "IEEE 802.1D-1990: Section 4.5.5.6"
   ::= { fsMIPbRstCVlanPortInfoEntry 13 }

fsMIPbRstCVlanPortDesignatedPort OBJECT-TYPE
   SYNTAX  OCTET STRING (SIZE (2))
   MAX-ACCESS  read-only
   STATUS  current
   DESCRIPTION
     "This object specifies the Port Identifier of the port on the Designated
      Bridge for this port' segment."
   REFERENCE
      "IEEE 802.1D-1990: Section 4.5.5.7"
   ::= { fsMIPbRstCVlanPortInfoEntry 14 }

fsMIPbRstCVlanPortForwardTransitions OBJECT-TYPE
    SYNTAX  Counter32
    MAX-ACCESS  read-only
    STATUS  current
    DESCRIPTION
      "This object specifies the number of times this port has transitioned
       from the Learning state to the Forwarding state."
   ::= { fsMIPbRstCVlanPortInfoEntry 15 }

fsMIPbRstCVlanPortSmTable OBJECT-TYPE
   SYNTAX SEQUENCE OF FsMIPbRstCVlanPortSmEntry
   MAX-ACCESS not-accessible
   STATUS     current
   DESCRIPTION
      "This table contains the objects for the state machine information of 
      C-VLAN component Ports Provider Edge Bridges."
   ::= { futureMIPbRst 4 }

fsMIPbRstCVlanPortSmEntry OBJECT-TYPE
   SYNTAX      FsMIPbRstCVlanPortSmEntry
   MAX-ACCESS  not-accessible
   STATUS      current
   DESCRIPTION
      "This object specifies each entry in this table which is for each C-VLAN
       component in Provider Bridges. Here the port represents the C-VLAN component
       ports. Each table entry gives the state machine information for a C-VLAN
       component Port in Provider Edge Bridges."
   INDEX { fsMIPbRstPort,fsMIPbRstCepSvid }
   ::= { fsMIPbRstCVlanPortSmTable 1 }

FsMIPbRstCVlanPortSmEntry ::=
   SEQUENCE {
      fsMIPbRstCVlanPortInfoSmState
         INTEGER,
      fsMIPbRstCVlanPortMigSmState
         INTEGER,
      fsMIPbRstCVlanPortRoleTransSmState
         INTEGER,
      fsMIPbRstCVlanPortStateTransSmState
         INTEGER,
      fsMIPbRstCVlanPortTopoChSmState
         INTEGER,
      fsMIPbRstCVlanPortTxSmState
         INTEGER
      }

fsMIPbRstCVlanPortInfoSmState OBJECT-TYPE
   SYNTAX      INTEGER {
                  disabled (0),
                  aged (1),
                  update (2),
                  superior (3),
                  repeat (4),
                  notdesignated (5),
                  present (6),
                  receive (7),
                  inferiordesignated (8)
               }
   MAX-ACCESS  read-only
   STATUS      current
   DESCRIPTION
      "This object specifies the current state of the Port Information state 
      machine.This object will hold the value 'disabled' when the Port 
      Information state machine is in the DISABLED state, the value 'aged'
      when the state machine is in the AGED state, the value 'update' when
      the state machine is in the UPDATE state, the value 'superior' when the
      state machine is in the SUPERIOR state, the value 'repeat' when the state 
      machine is in the REPEAT state, the value 'notdesignated' when the state
      machine is in the NOT_DESIGNATED state, the value 'present' when the state
      machine is in the CURRENT state and the value 'receive' when the state
      machine is in the RECEIVE state and the value 'inferiordesignated' when
      the state machine is in the INFERIOR_DESIGNATED state."
   ::= { fsMIPbRstCVlanPortSmEntry 1 }

fsMIPbRstCVlanPortMigSmState OBJECT-TYPE
   SYNTAX      INTEGER {
                  checkingrstp (0),
                  selectingstp (1),
                  sensing (2)
               }
   MAX-ACCESS  read-only
   STATUS      current
   DESCRIPTION
      "This object specifies the current state of the Port Protocol Migration 
      state machine.
      This object will hold the value 'checkingrstp' when the Protocol 
      Migration state machine is in the CHECKING_RSTP state, the value 
      'selectingstp' when the state machine is in the SELECTING_STP state,the 
      value 'sensing' when the state machine is in the SENSING state."
   ::= { fsMIPbRstCVlanPortSmEntry 2 }

fsMIPbRstCVlanPortRoleTransSmState OBJECT-TYPE
   SYNTAX      INTEGER {
                  init (0),
                  disableport (1),
                  disabledport (2),
                  rootport (3),
                  designatedport (4),
                  backupport (5),
                  rootproposed (6),
                  rootagreed(7),
                  reroot (8),
                  rootforward (9),
                  rootlearn (10),
                  rerooted (11),
                  designatedpropose (12),
                  designatedsynced (13),
                  designatedretired (14),
                  designatedforward (15),
                  designatedlearn (16),
                  designatedlisten (17)
               }
   MAX-ACCESS  read-only
   STATUS      current
   DESCRIPTION
      "This object specifies the current state of the Port Role Transition state 
      machine.
      
      This object will hold the value 'init' when the Port Role Transition state
      machine is in the INIT state, the value 'disableport' when the state 
      machine is in the DISABLE_PORT state, the value 'disabledport' when the 
      state machine is in the DISABLED_PORT state, the value 'rootport' when 
      the state machine is in the ROOT_PORT state, the value 'desgport' when 
      the state machine is in the DESIGNATED_PORT state, the value 'backupport' 
      when the state machine is in BACKUP_PORT state, the value 'rootproposed' 
      when the state machine is in the ROOT_PROPOSED state, the value 
      'rootagreed' when the state machine is in the ROOT_AGREED state, the 
      value 'reroot' when the state machine is in the REROOT
      state, the value 'rootforward' when the state machine is in the 
      ROOT_FORWARD state, the value 'rootlearn' when the state machine is in 
      the ROOT_LEARN state, the value 'rerooted' when the state machine is in 
      the REROOTED state, the value 'designatedpropose' when the state machine 
      is in the DESIGNATED_PROPOSE state, the value 'designatedsynced' when the 
      state machine is in the DESIGNATED_SYNCED state, the value 
      'designatedretired' when the state machine is in the DESIGNATED_RETIRED 
      state, the value 'designatedforward' when the state machine is in the 
      DESIGNATED_FORWARD state, the value 'designatedlearn' when the state 
      machine is in the DESIGNATED_LEARN state and the value 
      'designatedlisten' when the state machine is in the DESIGNATED_LISTEN
      state."
   ::= { fsMIPbRstCVlanPortSmEntry 3 }

fsMIPbRstCVlanPortStateTransSmState OBJECT-TYPE
   SYNTAX      INTEGER {
                  discarding (0),
                  learning (1),
                  forwarding (2)
               }
   MAX-ACCESS  read-only
   STATUS      current
   DESCRIPTION
      "This object specifies the current state of the Port State Transition
       state machine.
       This object will hold the value 'discarding' when the Port State Transition
       state machine is in the DISCARDING state, the value 'learning' when the 
       state machine is in the LEARNING state and the value 'forwarding' when the
       state machine is in the FORWARDING state." 
   ::= { fsMIPbRstCVlanPortSmEntry 4 }

fsMIPbRstCVlanPortTopoChSmState OBJECT-TYPE
   SYNTAX      INTEGER {
                  inactive (0),
                  learning (1),
                  detected (2),
                  active (3),
                  notifiedtcn (4),
                  notifiedtc (5),
                  propagating (6),
                  acknowledged (7)
               }
   MAX-ACCESS  read-only
   STATUS      current
   DESCRIPTION
      "This object specifies the current state of the Topology Change state
       machine.
      This object will hold the value 'inactive' when the Topology Change state
      machine is in the INACTIVE state, the value 'learning' when the state 
      machine is in the LEARNING state, the value 'active' when the state 
      machine is in the ACTIVE state, the value 'detected' when the state
      machine is in the DETECTED state,the value 'notifiedtcn' when the state
      machine is in the NOTIFIED_TCN state,the value 'notifiedtc' when the
      state machine is in the NOTIFIED_TC state,the value 'propagating' state
      when the state machine is in the PROPAGATING state and the value
      'acknowledged' when the state machine is in the ACKNOWLEDGED state." 
   ::= { fsMIPbRstCVlanPortSmEntry 5 }

fsMIPbRstCVlanPortTxSmState OBJECT-TYPE
   SYNTAX      INTEGER {
                  transmitinit (0),
                  transmitperiodic (1),
                  transmitconfig (2),
                  transmittcn (3),
                  transmitrstp (4),
                  idle (5)
               }
   MAX-ACCESS  read-only
   STATUS      current
   DESCRIPTION
      "This object specifies the current state of the Port Transmit state
       machine.
       This object will hold the value 'transmitinit' when the Port Transmit 
       state machine is in the TRANSMIT_INIT state, the value 'transmitperiodic'
       when the state machine is in the TRANSMIT_PERIODIC state, the value
       'transmitconfig' when the state machine is in the TRANSMIT_CONFIG state,
       the value 'transmittcn',when the state machine is in the TRANSMIT_TCN state,
       the value 'transmitrstp',when the state machine is in the TRANSMIT_RSTP
       state and the value 'idle' when the state machine is in the IDLE state."
   ::= { fsMIPbRstCVlanPortSmEntry 6 }

fsMIPbRstCVlanPortStatsTable OBJECT-TYPE
   SYNTAX SEQUENCE OF FsMIPbRstCVlanPortStatsEntry
   MAX-ACCESS not-accessible
   STATUS     current
   DESCRIPTION
      "This table contains the spanning tree statistics information for the 
      C-VLAN component ports."
   ::= { futureMIPbRst 5 }

fsMIPbRstCVlanPortStatsEntry OBJECT-TYPE
   SYNTAX      FsMIPbRstCVlanPortStatsEntry
   MAX-ACCESS  not-accessible
   STATUS      current
   DESCRIPTION
      "This object specifies each entry in this table which is for each C-VLAN
       component in Provider Bridges. Here the port represents the C-VLAN
       component ports.Each table entry gives the spanning tree protocol 
       statistics information for the C-VLAN component ports."
   INDEX { fsMIPbRstPort,fsMIPbRstCepSvid }
   ::= { fsMIPbRstCVlanPortStatsTable 1 }

FsMIPbRstCVlanPortStatsEntry ::=
   SEQUENCE {
      fsMIPbRstCVlanPortRxRstBpduCount
         Counter32,
      fsMIPbRstCVlanPortRxConfigBpduCount
         Counter32,
      fsMIPbRstCVlanPortRxTcnBpduCount
         Counter32,
      fsMIPbRstCVlanPortTxRstBpduCount
         Counter32,
      fsMIPbRstCVlanPortTxConfigBpduCount
         Counter32,
      fsMIPbRstCVlanPortTxTcnBpduCount
         Counter32,
      fsMIPbRstCVlanPortInvalidRstBpduRxCount
         Counter32,
      fsMIPbRstCVlanPortInvalidConfigBpduRxCount
         Counter32,
      fsMIPbRstCVlanPortInvalidTcnBpduRxCount
         Counter32,
      fsMIPbRstCVlanPortProtocolMigrationCount
         Counter32,
      fsMIPbRstCVlanPortEffectivePortState
         TruthValue
      }


fsMIPbRstCVlanPortRxRstBpduCount OBJECT-TYPE
   SYNTAX      Counter32
   MAX-ACCESS  read-only
   STATUS      current
   DESCRIPTION
      "This object specifies the number of RST BPDUs that have been received
       on this Port."
   ::= { fsMIPbRstCVlanPortStatsEntry 1 }

fsMIPbRstCVlanPortRxConfigBpduCount OBJECT-TYPE
   SYNTAX      Counter32
   MAX-ACCESS  read-only
   STATUS      current
   DESCRIPTION
      "This object specifies the number of Config BPDUs that have been
       received on this Port."
   ::= { fsMIPbRstCVlanPortStatsEntry 2 }

fsMIPbRstCVlanPortRxTcnBpduCount OBJECT-TYPE
   SYNTAX      Counter32
   MAX-ACCESS  read-only
   STATUS      current
   DESCRIPTION
      "This object specifies the number of TCN BPDUs that have been
       received on this Port."
   ::= { fsMIPbRstCVlanPortStatsEntry 3 }

fsMIPbRstCVlanPortTxRstBpduCount OBJECT-TYPE
   SYNTAX      Counter32
   MAX-ACCESS  read-only
   STATUS      current
   DESCRIPTION
      "This object specifies the number of RST BPDUs that have been
       transmitted by this Port."
   ::= { fsMIPbRstCVlanPortStatsEntry 4 }

fsMIPbRstCVlanPortTxConfigBpduCount OBJECT-TYPE
   SYNTAX      Counter32
   MAX-ACCESS  read-only
   STATUS      current
   DESCRIPTION
      "This object specifies the number of Config BPDUs that have been
       transmitted by this Port."
   ::= { fsMIPbRstCVlanPortStatsEntry 5 }

fsMIPbRstCVlanPortTxTcnBpduCount OBJECT-TYPE
   SYNTAX      Counter32
   MAX-ACCESS  read-only
   STATUS      current
   DESCRIPTION
      "This object specifies the number of TCN BPDUs that have been transmitted
       by this Port."
   ::= { fsMIPbRstCVlanPortStatsEntry 6 }

fsMIPbRstCVlanPortInvalidRstBpduRxCount OBJECT-TYPE
   SYNTAX      Counter32
   MAX-ACCESS  read-only
   STATUS      current
   DESCRIPTION
      "This object specifies the number of invalid RSTP BPDUs that have been 
      received on this Port." 
   ::= { fsMIPbRstCVlanPortStatsEntry 7 }

fsMIPbRstCVlanPortInvalidConfigBpduRxCount OBJECT-TYPE
   SYNTAX      Counter32
   MAX-ACCESS  read-only
   STATUS      current
   DESCRIPTION
      "This object specifies the number of invalid Configuration BPDUs that
       have been received on this Port."
   ::= { fsMIPbRstCVlanPortStatsEntry 8 }

fsMIPbRstCVlanPortInvalidTcnBpduRxCount OBJECT-TYPE
   SYNTAX      Counter32
   MAX-ACCESS  read-only
   STATUS      current
   DESCRIPTION
      "This object specifies the number of invalid TCN BPDUs that have been
       received on this Port."
   ::= { fsMIPbRstCVlanPortStatsEntry 9 }

fsMIPbRstCVlanPortProtocolMigrationCount OBJECT-TYPE
   SYNTAX      Counter32
   MAX-ACCESS  read-only
   STATUS      current
   DESCRIPTION
      "This object specifies the number of times the protocol has been migrated 
      from RSTP to STP and vice versa in CVLAN component."
   ::= { fsMIPbRstCVlanPortStatsEntry 10 }


fsMIPbRstCVlanPortEffectivePortState OBJECT-TYPE
      SYNTAX      TruthValue
      MAX-ACCESS  read-only            
      STATUS      current
      DESCRIPTION
          "This object specifies the effective Operational state of this port.
           This object will be set to TRUE only when the port is operationally
           up in the interface manager and the force Port State for this port 
           and specified port state is enabled.Otherwise this object is set
           to FALSE."

   ::= { fsMIPbRstCVlanPortStatsEntry 11 }

END

-- Copyright (C) 2016 Aricent. All Rights Reserved

-- $Id: fsmpb.mib,v 1.17 2016/02/18 09:47:31 siva Exp $

ARICENT-MIPROVIDERBRIDGE-MIB DEFINITIONS ::= BEGIN 
 
IMPORTS
 
    OBJECT-TYPE,MODULE-IDENTITY,
    Integer32, Unsigned32, Counter32, IpAddress, enterprises
       FROM SNMPv2-SMI
    RowStatus, MacAddress, TEXTUAL-CONVENTION, TruthValue
       FROM SNMPv2-TC
    VlanId, dot1qVlanIndex 
       FROM Q-BRIDGE-MIB
    dot1adMIPepEntry FROM ARICENT-MIDOT1AD-MIB
    EnabledStatus  
       FROM P-BRIDGE-MIB;
            
futureMIProviderBridgeMIB MODULE-IDENTITY
    LAST-UPDATED "201209050000Z"
    ORGANIZATION "ARICENT COMMUNICATIONS SOFTWARE"
    CONTACT-INFO "support@aricent.com"
    DESCRIPTION "||||||"
    REVISION "201209050000Z"
    DESCRIPTION "||||||"
::= { enterprises futuresoftware(2076) 127}

TunnelStatus ::= TEXTUAL-CONVENTION
    STATUS      current
    DESCRIPTION
        "To specify how to handle the L2 protocol packets received on a
         particular port. When the option is set to 'peer', the L2 protocol
         packets received on a particular port will be processed in the Bridge.
         When the option is set to 'tunnel', the L2 protocol packets received
         on a particular port will be transparently transmitted in the provider
         network and will not be processed in the Provider Bridges/Provider Edge
         Bridges. When the option is set to 'discard', the L2 protocol packets
         received over a particular port will not be processed and discarded."

    SYNTAX      INTEGER { peer(1), tunnel(2), discard(3) }

--Proprietary MIB implementation for the Provider Bridging functionality

fsMIPbSystem  OBJECT IDENTIFIER   ::= { futureMIProviderBridgeMIB 1 }
fsMIPbConfig  OBJECT IDENTIFIER   ::= { futureMIProviderBridgeMIB 2 }


fsMIPbContextInfoTable OBJECT-TYPE
   SYNTAX        SEQUENCE OF FsMIPbContextInfoEntry
   MAX-ACCESS    not-accessible
   STATUS        current
   DESCRIPTION
      "This object specifies the List of Provider Bridge related objects that
       can be configured per Virtual Context in the system."
   ::= { fsMIPbSystem 1 }

fsMIPbContextInfoEntry OBJECT-TYPE
   SYNTAX        FsMIPbContextInfoEntry
   MAX-ACCESS    not-accessible
   STATUS        current
   DESCRIPTION
      "This object specifies the Virtual Context based Provider Bridge objects."
   INDEX { fsMIPbContextId }
   ::= { fsMIPbContextInfoTable 1 }

FsMIPbContextInfoEntry ::=
    SEQUENCE {
        fsMIPbContextId
           Integer32,
        fsMIPbMulticastMacLimit
           Unsigned32,
        fsMIPbTunnelStpAddress
           MacAddress,
        fsMIPbTunnelLacpAddress
           MacAddress,
        fsMIPbTunnelDot1xAddress
           MacAddress,
        fsMIPbTunnelGvrpAddress
           MacAddress,
        fsMIPbTunnelGmrpAddress
           MacAddress
}

fsMIPbContextId OBJECT-TYPE
   SYNTAX       Integer32 (0..65535)
   MAX-ACCESS   not-accessible
   STATUS       current
   DESCRIPTION
      "This object specifies a Virtual Context."
   ::= { fsMIPbContextInfoEntry 1 }
   
fsMIPbMulticastMacLimit OBJECT-TYPE
   SYNTAX      Unsigned32 (0..4294967295)
   MAX-ACCESS  read-write
   STATUS      current
   DESCRIPTION
      "This object specifies MAC table size of the device. The
      size SET for this object is applicable only for the Virtual Context
      identified by the Virtual Context Id in this entry.The upper limit value 
      that can be SET for this object is limited by the underlying
      hardware. While on initialisation this object hold the maximum
      size of the Multicast MAC table of the device."
      ::= { fsMIPbContextInfoEntry 2 }

fsMIPbTunnelStpAddress OBJECT-TYPE
    SYNTAX      MacAddress
    MAX-ACCESS  read-write
    STATUS      deprecated
    DESCRIPTION
        "This object specifies the MAC address SET for this object is applicable
        only for the Virtual Context identified by the Virtual Context Id in
        this entry. The MAC address to be used for Customer STP BPDUs tunneling
        inside Provider Network. When tunneling is enabled on a port, this MAC
        address will be used as the the destination MAC address of the customer
        BPDUs received on a port where STP tunneling is enabled and the outgoing
        port is a proprietary PNP.
        Inside Provider Network, the BPDUs received with this MAC address
        will be treated as data packets and not processed.
        When the BPDU is sent out of the Provider Network, this MAC address
        will be replaced with the reserved address defined for Customer STP
        BPDUs. This configuration is allowed only for Provider Core or 
        Edge Bridges."

        ::= { fsMIPbContextInfoEntry 3 }

fsMIPbTunnelLacpAddress OBJECT-TYPE
    SYNTAX      MacAddress 
    MAX-ACCESS  read-write
    STATUS      deprecated
    DESCRIPTION
        "This object specifies the MAC address SET for this object is applicable
        only for the Virtual Context identified by the Virtual Context Id in
        this entry. The MAC address to be used for LACP packets tunneling inside
        Provider Network. When tunneling is enabled on a port, this MAC address
        will be used as the the destination MAC address of the customer LACP
        packets received over this port.
        Inside Provider Network, LACP packets received with this MAC address 
        will be treated as data packets and not processed. 
        When the tunneled LACP packets are sent out of the Provider Network, 
        this MAC address will be replaced with the reserved address defined 
        for LACP packets. This configuration is allowed only for Provider Core
        or Edge Bridges."
        
        ::= { fsMIPbContextInfoEntry 4 }

fsMIPbTunnelDot1xAddress OBJECT-TYPE
    SYNTAX      MacAddress 
    MAX-ACCESS  read-write
    STATUS      deprecated
    DESCRIPTION
        "This object specifies the MAC address SET for this object is applicable
        only for the Virtual Context identified by the Virtual Context Id in
        this entry. The MAC address to be used for Dot1x packets tunneling
        inside Provider Network. When tunneling is enabled on a port, this MAC
        address will be used as the the destination MAC address of the customer
        Dot1x packets received over this port. 
        Inside Provider Network, Dot1x packets received with this MAC address 
        will be treated as data packets and not processed.
        When the tunneled Dot1x packets are sent out of the Provider Network, 
        this MAC address will be replaced with the reserved address defined 
        for Dot1x packets. This configuration is allowed only for Provider Core
        or Edge Bridges."
        
    ::= { fsMIPbContextInfoEntry 5 }

fsMIPbTunnelGvrpAddress OBJECT-TYPE
    SYNTAX      MacAddress 
    MAX-ACCESS  read-write
    STATUS      deprecated
    DESCRIPTION
        "This object specifies the MAC address SET for this object is
         applicable only for the Virtual Context identified by the Virtual
         Context Id in this entry.
        The MAC address to be used for GVRP PDUs tunneling inside Provider 
        Network. When tunneling is enabled on a port, this MAC address will be 
        used as the the destination MAC address of the customer GVRP PDUs 
        received on a port where GVRP tunneling is enable and the outgoing 
        port is a proprietary PNP.
        Inside Provider Network, GVRP PDUs received with this MAC address 
        will be treated as data packets and not processed.        
        When the tunneled GVRP PDUs are sent out of the Provider Network, 
        this MAC address will be replaced with the reserved address defined 
        for GVRP PDUs. This configuration is allowed only for Provider Core or 
        Edge Bridges."
        
    ::= { fsMIPbContextInfoEntry 6 }

fsMIPbTunnelGmrpAddress OBJECT-TYPE
    SYNTAX      MacAddress 
    MAX-ACCESS  read-write
    STATUS      deprecated
    DESCRIPTION
        "This object specifies the MAC address SET for this object is applicable
         only for the Virtual Context identified by the Virtual Context Id in
        this entry. The MAC address to be used for GMRP PDUs tunneling inside
        Provider Network. When tunneling is enabled on a port, this MAC address
        will be used as the the destination MAC address of the customer GMRP
        PDUs received over this port. 
        Inside Provider Network, GMRP PDUs received with this MAC address 
        will be treated as data packets and not processed.
        When the tunneled GMRP PDUs are sent out of the Provider Network, 
        this MAC address will be replaced with the reserved address defined 
        for GMRP PDUs. This configuration is allowed only for Provider Core or 
        Edge Bridges."
        
    ::= { fsMIPbContextInfoEntry 7 }


-- -------------------------------------------------------------
-- The Provider Bridge Port Type Configuration Table
-- -------------------------------------------------------------

fsMIPbPortInfoTable OBJECT-TYPE
    SYNTAX      SEQUENCE OF FsMIPbPortInfoEntry
    MAX-ACCESS  not-accessible
    STATUS      current
    DESCRIPTION
        "This object specifies a table containing provider bridge related 
        configurations for the externally accessible ports.
        All the objects in this table are applicable 
        only when the Bridge Mode is set as ProviderBridge or 
        ProviderCoreBridge or ProviderEdgeBridge."
    ::= { fsMIPbConfig 1 }
    
fsMIPbPortInfoEntry OBJECT-TYPE
    SYNTAX      FsMIPbPortInfoEntry
    MAX-ACCESS  not-accessible
    STATUS      current
    DESCRIPTION
        "This object specifies each entry in this table representing the
         Provider Bridge related port configurations. This table is indexed by
         ifIndex."

    INDEX { fsMIPbPort }
            ::= { fsMIPbPortInfoTable 1 }
            
FsMIPbPortInfoEntry ::=
    SEQUENCE {
                fsMIPbPort                          Integer32,
                fsMIPbPortSVlanClassificationMethod INTEGER,
                fsMIPbPortSVlanIngressEtherType     Integer32,
                fsMIPbPortSVlanEgressEtherType      Integer32,
                fsMIPbPortSVlanEtherTypeSwapStatus  EnabledStatus,
                fsMIPbPortSVlanTranslationStatus    EnabledStatus,
                fsMIPbPortUnicastMacLearning        EnabledStatus,
                fsMIPbPortUnicastMacLimit           Unsigned32,
                fsMIPbPortBundleStatus              EnabledStatus,
                fsMIPbPortMultiplexStatus           EnabledStatus

            }
    
fsMIPbPort OBJECT-TYPE
   SYNTAX      Integer32 (1..65535)
   MAX-ACCESS  not-accessible
   STATUS      current
   DESCRIPTION
      "This object specifies the Index value of the port in the system for
       which this entry applies. The maximum index value of the port is defined
       by the system."
   ::= { fsMIPbPortInfoEntry 1 }


fsMIPbPortSVlanClassificationMethod OBJECT-TYPE
   SYNTAX      INTEGER {
                        sourceMac (1),
                        destinationMac (2),
                        cvlanSrcMac (3),
                        cvlanDstMac (4),
                        dscp (5),
                        cvlanDscp (6),
                        sourceIp (7),
                        destinationIp (8),
                        srcIpDstIp (9),
                        cvlanDstIp (10),
                        cvlan (11),
                        pvid (12)
    }
   MAX-ACCESS  read-write
   STATUS      current
   DESCRIPTION
    "This object specifies the type of SVLAN classification that has to be used
     for a given type of port. providerNetworkPort / customerNetworkPort  - 
     Port's 'pvid' will be the SVLAN classification for the untagged packets
     received over this interface.
     customerEdgePort - The SVLAN classification mechanism is always based on
     'cvlan' (i.e CVidRegistrationTable ).No other SVLAN classification
      mechanism is allowed for this port type.
     propCustomerNetworkPort / propCustomerEdgePort  - 'pvid' will be
     default SVLAN classification mechanism for this port. But the user is free to
     configure any other SVLAN classification mechanism except the
     CVidRegistrationTable (ie cvlan mechanism)
     For proprietary CEP and proprietary CNP ports,the SVLAN classification
     is based on one of the configured SVLAN classification methods mentioned
     here. If it is not configured, by default the port's 'PVID' is considered
     as the SVLAN for untagged packets."

   ::= { fsMIPbPortInfoEntry 2 }
 
fsMIPbPortSVlanIngressEtherType OBJECT-TYPE
    SYNTAX      Integer32 (1..65535)
    MAX-ACCESS  read-write
    STATUS      deprecated
    DESCRIPTION

    "This object specifies the S-VLAN tag ether type used for the packets 
    received on this port.Packets received on a port are considered tagged,
    when the packet ethertype matches with the port ether type configured.
    Otherwise, they will be considered untagged.
    By default, on all the ports, 0x88a8 will be configured as the ether type.
    On Proprietary Provider Network Ports 0x8100 will be configured as the 
    ingress ethertype. This object is deprecated. The new MIB object
    fsMIDot1qFutureVlanPortIngressEtherType indicates the Ingress Ethertype for
    a port."

    DEFVAL { 34984 }
    ::= { fsMIPbPortInfoEntry 3 }

fsMIPbPortSVlanEgressEtherType OBJECT-TYPE
    SYNTAX      Integer32 (1..65535)
    MAX-ACCESS  read-write
    STATUS      deprecated
    DESCRIPTION
    "This object specifies the ether type of the S-VLAN tag that has to
    be applied for all the outgoing packets on this port. If a valid value is
    in this object, all the packets which are outgoing on this port will
    contain the ether type as configured in this object. By Default 0x88a8
    will be used for packets transmitted  with S-VLAN on the ports.
    On Proprietary Provider Network Ports and Customer Edge Ports, 0x8100
    will be used as the ether type for the outgoing packets.
    This object is deprecated. The new MIB object
    fsMIDot1qFutureVlanPortEgressEtherType indicates the Egress Ethertype for a
    port."

    DEFVAL { 34984 }
    ::= { fsMIPbPortInfoEntry 4}

fsMIPbPortSVlanEtherTypeSwapStatus OBJECT-TYPE
    SYNTAX      EnabledStatus
    MAX-ACCESS  read-write
    STATUS      current
    DESCRIPTION
    "This object specifies whether the Ether Type Swapping can be
     applied on the S-VLAN tagged packets over this port.
     The Ether type swapping will only be applied on S-VLAN tag of a packet.
     This configuration is applicable for all values of Port Type other 
     than customer edge ports."
    DEFVAL { disabled }
    ::= { fsMIPbPortInfoEntry 5 }

fsMIPbPortSVlanTranslationStatus OBJECT-TYPE
    SYNTAX      EnabledStatus 
    MAX-ACCESS  read-write
    STATUS      current
    DESCRIPTION
    "This object specifies whether the VID Translation table can be 
    enabled on the incoming/outgoing packets on a particular port.
    The Service Vlan swapping is applicable only for the externally 
    accessible network ports (i.e.) Provider Network Port ,Customer Network port
    and proprietary Customer Network Port. The Service Vlan Translation status
    can be enabled or disabled on per port basis. By default, it is enabled on
    Provider Network Port and Customer Network Port(S-Tagged) and disabled on
    the other applicable port-types."
    ::= { fsMIPbPortInfoEntry 6 }

fsMIPbPortUnicastMacLearning OBJECT-TYPE 
   SYNTAX      EnabledStatus
   MAX-ACCESS  read-write 
   STATUS      deprecated 
   DESCRIPTION 
      "This object specifies a Truth value indicating the unicast MAC learning enabled/disabled
       status for this port. When Unicast Mac Learning is disabled, No
       Entry will be learned from the point of configuration on this port.
       When Mac Learning is enabled, Entries will be learned on this port."
   DEFVAL   { enabled } 
   ::= { fsMIPbPortInfoEntry 7 } 

fsMIPbPortUnicastMacLimit OBJECT-TYPE
   SYNTAX      Unsigned32 (0..4294967295)
   MAX-ACCESS  read-write
   STATUS      current
   DESCRIPTION
      "This object specifies the Limiting value on the number of distinct unicast destination MAC
       addresses that can be dynamically learnt over this interface.
       The lower limit and upper limit value that can be SET for this object
       is determined by the underlying hardware. This Limit is applicable for
       only dynamically learned entries and NOT for static unicast 
       entries."
   ::= { fsMIPbPortInfoEntry 8 }

fsMIPbPortBundleStatus OBJECT-TYPE
   SYNTAX      EnabledStatus
   MAX-ACCESS  read-write
   STATUS      current
   DESCRIPTION
      "This object specifies the a truth value indicating that Bundling
       enabled/disabled on port, this Object can be enabled/disabled only for
       CEP. For other ports setting and getting is not meaningful."
   DEFVAL   { enabled }    
   ::= { fsMIPbPortInfoEntry 9 }

fsMIPbPortMultiplexStatus OBJECT-TYPE
   SYNTAX      EnabledStatus
   MAX-ACCESS  read-write
   STATUS      current
   DESCRIPTION
      "This object specifies a Truth value indicating that Bundling
       enabled/disabled on port, this Object can be enabled/disabled only for
       CEP. For other ports setting and getting is not meaningful."
   DEFVAL   { enabled }    
   ::= { fsMIPbPortInfoEntry 10 }
   
   
-- -------------------------------------------------------------
-- The S-VLAN Port , SourceMAC based Configuration Table
-- -------------------------------------------------------------

fsMIPbSrcMacSVlanTable OBJECT-TYPE
    SYNTAX      SEQUENCE OF FsMIPbSrcMacSVlanEntry
    MAX-ACCESS  not-accessible
    STATUS      current
    DESCRIPTION
        "This object specifies a table containing per port, per SourceMAC based
        Service VLAN classification information in the device. Entries can be
        into this table only when the bridge is configured as a Provider Bridge
        and the Port Type for this port is SET as Proprietary Customer
        Edge Port / Proprietary Customer Network Port."
    ::= { fsMIPbConfig 2 }

fsMIPbSrcMacSVlanEntry OBJECT-TYPE
    SYNTAX      FsMIPbSrcMacSVlanEntry
    MAX-ACCESS  not-accessible
    STATUS      current
    DESCRIPTION
        "This object specifies the Information controlling Service VLAN classification at this
        specified port for an ingress frame with the specified Source
        MAC address in the ethernet header of the frame."
    INDEX { fsMIPbPort, fsMIPbSrcMacAddress }
            ::= { fsMIPbSrcMacSVlanTable 1 }

FsMIPbSrcMacSVlanEntry ::=
    SEQUENCE {
        fsMIPbSrcMacAddress            MacAddress,
        fsMIPbSrcMacSVlan              VlanId,
        fsMIPbSrcMacRowStatus          RowStatus
    }

fsMIPbSrcMacAddress OBJECT-TYPE
    SYNTAX      MacAddress
    MAX-ACCESS  not-accessible
    STATUS      current
    DESCRIPTION
        "This object specifies the Source MAC address present in the ethernet header of the
        frame received on this port for which Service VLAN is assigned
        based on this entry."
    ::= { fsMIPbSrcMacSVlanEntry 1 }

fsMIPbSrcMacSVlan OBJECT-TYPE
    SYNTAX      VlanId
    MAX-ACCESS  read-write
    STATUS      current
    DESCRIPTION
        "This object specifies the Service VLAN ID assigned to frames received on this port when
        the Source MAC address in the ethernet header of the frame is same
        as specified in this entry."
    ::= { fsMIPbSrcMacSVlanEntry 2 }
    
fsMIPbSrcMacRowStatus OBJECT-TYPE
    SYNTAX      RowStatus
    MAX-ACCESS  read-create
    STATUS      current
    DESCRIPTION
        "This object specifies the status of this entry. An entry is
        created in this table when this object is SET to 'createAndWait'.
        The entry in this table is used when the status of this object 
        is SET 'active'. The entry in this table is not used when this 
        object is SET 'notInService'. An entry created in this table is
        be deleted when this object is SET 'destroy'."
    ::= { fsMIPbSrcMacSVlanEntry 3 }
    
-- -------------------------------------------------------------
-- The S-VLAN Port , DestinationMAC based Configuration Table
-- -------------------------------------------------------------

fsMIPbDstMacSVlanTable OBJECT-TYPE
    SYNTAX      SEQUENCE OF FsMIPbDstMacSVlanEntry
    MAX-ACCESS  not-accessible
    STATUS      current
    DESCRIPTION
        "This object specifies a table containing per port, per Destination MAC based Service
        VLAN classification information in the device. Entries can be 
        configured into this table only when the bridge is configured 
        as a Provider Bridge. An entry in this table is possible only when the
        'Port Type' for this port is SET as Proprietary Customer Network Port
        or Proprietary Customer Edge Port."
    ::= { fsMIPbConfig 3 }

fsMIPbDstMacSVlanEntry OBJECT-TYPE
    SYNTAX      FsMIPbDstMacSVlanEntry
    MAX-ACCESS  not-accessible
    STATUS      current
    DESCRIPTION
        "This object specifies the Information controlling Service VLAN classification at this
        specified port for an ingress frame with the specified Destination MAC
        address in the ethernet header of the frame."
    INDEX { fsMIPbPort, fsMIPbDstMacAddress }
            ::= { fsMIPbDstMacSVlanTable 1 }

FsMIPbDstMacSVlanEntry ::=
    SEQUENCE {
        fsMIPbDstMacAddress            MacAddress,
        fsMIPbDstMacSVlan              VlanId,
        fsMIPbDstMacRowStatus          RowStatus
    }

fsMIPbDstMacAddress OBJECT-TYPE
    SYNTAX      MacAddress
    MAX-ACCESS  not-accessible
    STATUS      current
    DESCRIPTION
        "This object specifies the Destination MAC address present in the ethernet header of the
        frame received on this port for which Service VLAN is assigned
        based on this entry."
    ::= { fsMIPbDstMacSVlanEntry 1 }

    
fsMIPbDstMacSVlan OBJECT-TYPE
    SYNTAX      VlanId
    MAX-ACCESS  read-write
    STATUS      current
    DESCRIPTION
        "This object specifies the Service VLAN ID assigned to frames received on this port when
        the Destination MAC address in the ethernet header of the frame is
        same as specified in this entry."
    ::= { fsMIPbDstMacSVlanEntry 2 }
    
fsMIPbDstMacRowStatus OBJECT-TYPE
    SYNTAX      RowStatus
    MAX-ACCESS  read-create
    STATUS      current
    DESCRIPTION
        "This object specifies the status of this entry. An entry is
        created in this table when this object is SET to 'createAndWait'.
        The entry in this table is used when the status of this object 
        is SET 'active'. The entry in this table is not used when this 
        object is SET 'notInService'. An entry created in this table is
        deleted when this object is SET 'destroy'."
    ::= { fsMIPbDstMacSVlanEntry 3 }
   
-- -------------------------------------------------------------
-- The S-VLAN Port , C-VLAN, Source MAC based Configuration Table
-- -------------------------------------------------------------

fsMIPbCVlanSrcMacSVlanTable OBJECT-TYPE
    SYNTAX      SEQUENCE OF FsMIPbCVlanSrcMacSVlanEntry
    MAX-ACCESS  not-accessible
    STATUS      current
    DESCRIPTION
        "This object specifies the a table containing per Port, per Customer VLAN ID,
        per Source MAC based S-VLAN classification information in the device.
        Entries can be configured into this table only when the  bridge is
        configured as a Provider Bridge. An entry in this table is
        possible only when the 'PortType' for this port is SET as 
        Proprietary Customer Edge Port / Proprietary Customer Network Port."
    ::= { fsMIPbConfig 4 }

fsMIPbCVlanSrcMacSVlanEntry OBJECT-TYPE
    SYNTAX      FsMIPbCVlanSrcMacSVlanEntry
    MAX-ACCESS  not-accessible
    STATUS      current
    DESCRIPTION
        "This object specifies the Information controlling Service VLAN classification at this specified
        port for an ingress frame with the classified Customer VLAN ID and
        with the specified Source MAC address in the ethernet header of the frame.
        Classification of Customer VLAN ID may be from the Customer VLAN tag
        in the received frame OR based on Port CVLAN table."
    INDEX { fsMIPbPort, fsMIPbCVlanSrcMacCVlan, fsMIPbCVlanSrcMacAddr }
            ::= { fsMIPbCVlanSrcMacSVlanTable 1 }

FsMIPbCVlanSrcMacSVlanEntry ::=
    SEQUENCE {
        fsMIPbCVlanSrcMacCVlan         VlanId,
        fsMIPbCVlanSrcMacAddr          MacAddress,
        fsMIPbCVlanSrcMacSVlan         VlanId,
        fsMIPbCVlanSrcMacRowStatus     RowStatus
    }

fsMIPbCVlanSrcMacCVlan OBJECT-TYPE
    SYNTAX      VlanId
    MAX-ACCESS  not-accessible
    STATUS      current
    DESCRIPTION
        "This object specifies the Customer VLAN ID in the Customer VLAN tag of an ingress frame
        at this specified port OR the Customer VLAN ID for which the ingress
        frame is classified to this specified port."
    ::= { fsMIPbCVlanSrcMacSVlanEntry 1 }
    
fsMIPbCVlanSrcMacAddr OBJECT-TYPE
    SYNTAX      MacAddress
    MAX-ACCESS  not-accessible
    STATUS      current
    DESCRIPTION
        "This object specifies the Source MAC address in the ethernet header of the
        frame received on this port."
    ::= { fsMIPbCVlanSrcMacSVlanEntry 2 }
    
fsMIPbCVlanSrcMacSVlan OBJECT-TYPE
    SYNTAX      VlanId
    MAX-ACCESS  read-write
    STATUS      current
    DESCRIPTION
        "This object specifies the Service VLAN assigned to frames received on this port,
        When the Classified Customer VLAN ID is same as specified in 
        this entry and  When the Source MAC address in the ethernet header
        of the frame is same as specified in this entry.
        Classification of Customer VLAN ID may be from the Customer VLAN tag
        in the received frame OR based on Port CVLAN table."
    ::= { fsMIPbCVlanSrcMacSVlanEntry 3 }
    
 fsMIPbCVlanSrcMacRowStatus OBJECT-TYPE
    SYNTAX      RowStatus
    MAX-ACCESS  read-create
    STATUS      current
    DESCRIPTION
        "This object specifies the status of this entry. An entry is
        created in this table when this object is SET to 'createAndWait'.
        The entry in this table is used when the status of this object 
        is SET 'active'. The entry in this table is not used when this 
        object is SET 'notInService'. An entry created in this table is
        deleted when this object is SET 'destroy'."

    ::= { fsMIPbCVlanSrcMacSVlanEntry 4 }
    
 -- -------------------------------------------------------------
-- The S-VLAN Port , C-VLAN, Destination MAC based Configuration Table
-- -------------------------------------------------------------

fsMIPbCVlanDstMacSVlanTable OBJECT-TYPE
    SYNTAX      SEQUENCE OF FsMIPbCVlanDstMacSVlanEntry
    MAX-ACCESS  not-accessible
    STATUS      current
    DESCRIPTION
        "This object specifies a table containing per Port, per Customer VLAN ID,
        per Destination MAC based S-VLAN classification information in the
        device. Entries can be configured into this table only when the 
        bridge is configured as a Provider Bridge. An entry in this table
        is possible only when the 'Port Type' for this port is SET
        as Proprietary Customer Edge Port / Proprietary Customer Network Port."

    ::= { fsMIPbConfig 5 }

fsMIPbCVlanDstMacSVlanEntry OBJECT-TYPE
    SYNTAX      FsMIPbCVlanDstMacSVlanEntry
    MAX-ACCESS  not-accessible
    STATUS      current
    DESCRIPTION
        "This object specifies the Information controlling Service VLAN classification at this specified
        port for an ingress frame with the classified Customer VLAN ID and
        with the specified Destination MAC address in the ethernet header of 
        the frame. Classification of Customer VLAN ID may be from the Customer VLAN tag
        in the received frame OR based on Port CVLAN table."
    INDEX { fsMIPbPort, fsMIPbCVlanDstMacCVlan, fsMIPbCVlanDstMacAddr }
            ::= { fsMIPbCVlanDstMacSVlanTable 1 }

FsMIPbCVlanDstMacSVlanEntry ::=
    SEQUENCE {
        fsMIPbCVlanDstMacCVlan         VlanId,
        fsMIPbCVlanDstMacAddr          MacAddress,
        fsMIPbCVlanDstMacSVlan         VlanId,
        fsMIPbCVlanDstMacRowStatus     RowStatus
    }

fsMIPbCVlanDstMacCVlan OBJECT-TYPE
    SYNTAX      VlanId
    MAX-ACCESS  not-accessible
    STATUS      current
    DESCRIPTION
        "This object specifies the Customer VLAN ID in the Customer VLAN tag of an ingress frame
        at this specified port or the Customer VLAN ID for which the ingress
        frame is classified for at this specified port."
    ::= { fsMIPbCVlanDstMacSVlanEntry 1 }
    
fsMIPbCVlanDstMacAddr OBJECT-TYPE
    SYNTAX      MacAddress
    MAX-ACCESS  not-accessible
    STATUS      current
    DESCRIPTION
        "This object specifies the Destination MAC address in the ethernet header of the
        frame received on this port."
    ::= { fsMIPbCVlanDstMacSVlanEntry 2 }
    
fsMIPbCVlanDstMacSVlan OBJECT-TYPE
    SYNTAX      VlanId
    MAX-ACCESS  read-write
    STATUS      current
    DESCRIPTION
        "This object specifies the Service VLAN assigned to frames received on this port
        when the Classified Customer VLAN ID and when the Destination 
        MAC address in the ethernet header of the frame is same as 
        specified in this entry. Classification of Customer VLAN ID may be from
        the Customer VLAN tag in the received frame OR based on Port CVLAN table."
    ::= { fsMIPbCVlanDstMacSVlanEntry 3 }
    
 fsMIPbCVlanDstMacRowStatus OBJECT-TYPE
    SYNTAX      RowStatus
    MAX-ACCESS  read-create
    STATUS      current
    DESCRIPTION
        "This object specifies the status of this entry. An entry is
        created in this table when this object is SET to 'createAndWait'.
        The entry in this table is used when the status of this object 
        is SET 'active'. The entry in this table is not used when this 
        object is SET 'notInService'. An entry created in this table is
        deleted when this object is SET 'destroy'."

    ::= { fsMIPbCVlanDstMacSVlanEntry 4 }
   
-- -------------------------------------------------------------
-- The S-VLAN Port , DSCP based Configuration Table
-- -------------------------------------------------------------

fsMIPbDscpSVlanTable OBJECT-TYPE
    SYNTAX      SEQUENCE OF FsMIPbDscpSVlanEntry
    MAX-ACCESS  not-accessible
    STATUS      current
    DESCRIPTION
        "This object specifies a table containing per port, per DiffServ 
        Code Point (DSCP) value based Service VLAN classification information
        in the device. Entries can be configured into this table only when the bridge is 
        configured as a Provider Bridge and the 'PortType' for
        this port is SET as Proprietary Customer Network Port or 
        Proprietary Customer Edge Port."

    ::= { fsMIPbConfig 6 }

fsMIPbDscpSVlanEntry OBJECT-TYPE
    SYNTAX      FsMIPbDscpSVlanEntry
    MAX-ACCESS  not-accessible
    STATUS      current
    DESCRIPTION
        "This object specifies the Information controlling Service VLAN 
        classification at this specified port for an ingress IP frame with the
         DSCP value as specified in this entry."
    INDEX { fsMIPbPort, fsMIPbDscp }
            ::= { fsMIPbDscpSVlanTable 1 }

FsMIPbDscpSVlanEntry ::=
    SEQUENCE {
        fsMIPbDscp             Integer32,
        fsMIPbDscpSVlan        VlanId,
        fsMIPbDscpRowStatus    RowStatus
    }

fsMIPbDscp OBJECT-TYPE
    SYNTAX      Integer32 (0..63)
    MAX-ACCESS  not-accessible
    STATUS      current
    DESCRIPTION
        "This object specifies the DSCP value in the IP header of the 
         frame received on this port for which Service VLAN is assigned based
         on this entry."
    ::= { fsMIPbDscpSVlanEntry 1 }

    
fsMIPbDscpSVlan OBJECT-TYPE
    SYNTAX      VlanId
    MAX-ACCESS  read-write
    STATUS      current
    DESCRIPTION
        "This object specifies the Service VLAN ID assigned to IP 
         frames received on this port when the DSCP value in the IP header of
         the frame is same as specified in this entry."
    ::= { fsMIPbDscpSVlanEntry 2 }
    
fsMIPbDscpRowStatus OBJECT-TYPE
    SYNTAX      RowStatus
    MAX-ACCESS  read-create
    STATUS      current
    DESCRIPTION
        "This object specifies the status of this 
        entry. An entry is created in this table when this object is SET to
        'createAndWait'. The entry in this table is used when the status of
        this object is SET 'active'. The entry in this table is not used when this 
        object is SET 'notInService'. An entry created in this table is
        deleted when this object is SET 'destroy'."

    ::= { fsMIPbDscpSVlanEntry 3 }
    
-- -------------------------------------------------------------
-- The S-VLAN Port ,C-VLAN and DSCP based Configuration Table
-- -------------------------------------------------------------

fsMIPbCVlanDscpSVlanTable OBJECT-TYPE
    SYNTAX      SEQUENCE OF FsMIPbCVlanDscpSVlanEntry
    MAX-ACCESS  not-accessible
    STATUS      current
    DESCRIPTION
        "This object specifies a table containing per port, per Customer 
        VLAN ID, per DiffServ Code Point (DSCP) value based Service VLAN
        classification information in the device. Entries can be configured
        into this table only when the bridge is configured as a Provider Bridge
        and the 'PortType' for this port is SET as Proprietary Customer Edge
        Port / Proprietary Customer Network Port."

    ::= { fsMIPbConfig 7 }

fsMIPbCVlanDscpSVlanEntry OBJECT-TYPE
    SYNTAX      FsMIPbCVlanDscpSVlanEntry
    MAX-ACCESS  not-accessible
    STATUS      current
    DESCRIPTION
        "This object specifies the Information controlling Service VLAN 
         classification at this specified port for an ingress IP frame with the
         classified Customer VLAN ID as specified in this entry and the DSCP value 
         in the frame as specified in this entry.
        Classification of Customer VLAN ID may be from the Customer VLAN tag
        in the received frame OR based on Port CVLAN table."
    INDEX { fsMIPbPort, fsMIPbCVlanDscpCVlan, fsMIPbCVlanDscp }
            ::= { fsMIPbCVlanDscpSVlanTable 1 }

FsMIPbCVlanDscpSVlanEntry ::=
    SEQUENCE {
        fsMIPbCVlanDscpCVlan          VlanId, 
        fsMIPbCVlanDscp               Integer32,
        fsMIPbCVlanDscpSVlan          VlanId,
        fsMIPbCVlanDscpRowStatus      RowStatus
    }
    
fsMIPbCVlanDscpCVlan OBJECT-TYPE
    SYNTAX      VlanId
    MAX-ACCESS  not-accessible
    STATUS      current
    DESCRIPTION
        "This object specifies the Customer VLAN ID in the Customer
        VLAN tag of an ingress frame at this specified port or the Customer
        VLAN ID for which the ingress frame is classified for at this specified port."
    ::= { fsMIPbCVlanDscpSVlanEntry 1 }

fsMIPbCVlanDscp OBJECT-TYPE
    SYNTAX      Integer32 (0..63)
    MAX-ACCESS  not-accessible
    STATUS      current
    DESCRIPTION
        "This object specifies the DSCP value in the IP header of the 
         frame received on this port."
    ::= { fsMIPbCVlanDscpSVlanEntry 2 }

    
fsMIPbCVlanDscpSVlan OBJECT-TYPE
    SYNTAX      VlanId 
    MAX-ACCESS  read-write
    STATUS      current
    DESCRIPTION
        "This object specifies the Service VLAN ID assigned to frames 
         received on this port, when the classified Customer VLAN ID is the
         same as specified in this entry and when the DSCP value in the
         IP header of the frame is same as specified in this entry.
        Classification of Customer VLAN ID may be from the Customer VLAN tag
        in the received frame OR based on Port CVLAN table."
    ::= { fsMIPbCVlanDscpSVlanEntry 3 }
    
fsMIPbCVlanDscpRowStatus OBJECT-TYPE
    SYNTAX      RowStatus
    MAX-ACCESS  read-create
    STATUS      current
    DESCRIPTION
        "This object specifies the status of this 
        entry. An entry is created in this table when this object is SET to 'createAndWait'.
        The entry in this table is used when the status of this object 
        is SET 'active'. The entry in this table is not used when this 
        object is SET 'notInService'. An entry created in this table is
        deleted when this object is SET 'destroy'."

    ::= { fsMIPbCVlanDscpSVlanEntry 4 }
    
-- -------------------------------------------------------------
-- The S-VLAN Port ,Source IP Address based Configuration Table
-- -------------------------------------------------------------

fsMIPbSrcIpAddrSVlanTable OBJECT-TYPE
    SYNTAX      SEQUENCE OF FsMIPbSrcIpAddrSVlanEntry
    MAX-ACCESS  not-accessible
    STATUS      current
    DESCRIPTION
        "This object specifies a table containing per port, per Source IP 
        Address, based Service VLAN classification information in the device.
        Entries can be configured into this table only when the bridge is
        configured as a Provider Bridge and the 'PortType' for this port is SET as
        Proprietary Customer Network Port or Proprietary Customer Edge Port."
    ::= { fsMIPbConfig 8 }

fsMIPbSrcIpAddrSVlanEntry OBJECT-TYPE
    SYNTAX      FsMIPbSrcIpAddrSVlanEntry
    MAX-ACCESS  not-accessible
    STATUS      current
    DESCRIPTION
        "This object specifies the Information controlling Service VLAN 
        classification at this specified port for an ingress IP frame with the
        Source IP Address in the IP header of the frame as specified in this entry."
    INDEX { fsMIPbPort, fsMIPbSrcIpAddr }
    ::= { fsMIPbSrcIpAddrSVlanTable 1 }

FsMIPbSrcIpAddrSVlanEntry ::=
    SEQUENCE {
        fsMIPbSrcIpAddr            IpAddress,
        fsMIPbSrcIpSVlan           VlanId,
        fsMIPbSrcIpRowStatus       RowStatus
    }
    
fsMIPbSrcIpAddr OBJECT-TYPE
    SYNTAX      IpAddress
    MAX-ACCESS  not-accessible
    STATUS      current
    DESCRIPTION
        "This object specifies the Source IP Address in the IP header of an ingress
        IP frame at this specified port."
    ::= { fsMIPbSrcIpAddrSVlanEntry 1 }

fsMIPbSrcIpSVlan OBJECT-TYPE
    SYNTAX      VlanId 
    MAX-ACCESS  read-write
    STATUS      current
    DESCRIPTION
        "The Service VLAN ID assigned to frames ingress at this port
        when the Source IP address in the IP header of the frame is 
        same as specified in this entry."
    ::= { fsMIPbSrcIpAddrSVlanEntry 2 }
    
fsMIPbSrcIpRowStatus OBJECT-TYPE
    SYNTAX      RowStatus
    MAX-ACCESS  read-create
    STATUS      current
    DESCRIPTION
        "This object specifies the status of this entry. An entry is
        created in this table when this object is SET to 'createAndWait'.
        The entry in this table is used when the status of this object 
        is SET 'active'. The entry in this table is not used when this 
        object is SET 'notInService'. An entry created in this table is
        deleted when this object is SET 'destroy'."

    ::= { fsMIPbSrcIpAddrSVlanEntry 3 }
    
 -- -------------------------------------------------------------
-- The S-VLAN Port ,Destination IP Address based Configuration Table
-- -------------------------------------------------------------

fsMIPbDstIpAddrSVlanTable OBJECT-TYPE
    SYNTAX      SEQUENCE OF FsMIPbDstIpAddrSVlanEntry
    MAX-ACCESS  not-accessible
    STATUS      current
    DESCRIPTION
        "This object specifies a table containing per port, per Destination IP Address, based
        Service VLAN classification information in the device. Entries can
        be configured into this table only when the bridge is configured as 
        a Provider Bridge and the 'PortType' for this port is SET
        as Proprietary Customer Network Port or Proprietary Customer Edge Port."
    ::= { fsMIPbConfig 9 }

fsMIPbDstIpAddrSVlanEntry OBJECT-TYPE
    SYNTAX      FsMIPbDstIpAddrSVlanEntry
    MAX-ACCESS  not-accessible
    STATUS      current
    DESCRIPTION
        "This object specifies the Information controlling Service VLAN classification at this 
        specified port for an ingress IP frame with the Destination IP
        Address in the IP header of the frame as specified in this entry."
    INDEX { fsMIPbPort, fsMIPbDstIpAddr }
    ::= { fsMIPbDstIpAddrSVlanTable 1 }

FsMIPbDstIpAddrSVlanEntry ::=
    SEQUENCE {
        fsMIPbDstIpAddr            IpAddress,
        fsMIPbDstIpSVlan           VlanId,
        fsMIPbDstIpRowStatus       RowStatus
    }
    
fsMIPbDstIpAddr OBJECT-TYPE
    SYNTAX      IpAddress
    MAX-ACCESS  not-accessible
    STATUS      current
    DESCRIPTION
        "This object specifies the Destination IP Address in the IP header of an ingress
        IP frame at this specified port."
    ::= { fsMIPbDstIpAddrSVlanEntry 1 }

fsMIPbDstIpSVlan OBJECT-TYPE
    SYNTAX      VlanId
    MAX-ACCESS  read-write
    STATUS      current
    DESCRIPTION
        "This object specifies the Service VLAN ID assigned to frames 
         ingress at this port when the Destination IP address in the IP header
         of the frame is same as specified in this entry."
    ::= { fsMIPbDstIpAddrSVlanEntry 2 }
    
fsMIPbDstIpRowStatus OBJECT-TYPE
    SYNTAX      RowStatus
    MAX-ACCESS  read-create
    STATUS      current
    DESCRIPTION
        "This object specifies the status of this entry. An entry is
        created in this table when this object is SET to 'createAndWait'.
        The entry in this table is used when the status of this object 
        is SET 'active'. The entry in this table is not used when this 
        object is SET 'notInService'. An entry created in this table is
        deleted when this object is SET 'destroy'."
    ::= { fsMIPbDstIpAddrSVlanEntry 3 }
   
-- -------------------------------------------------------------
-- The S-VLAN Port ,SourceIP Address, DestinationIP Address  based
-- Configuration Table
-- -------------------------------------------------------------

fsMIPbSrcDstIpSVlanTable OBJECT-TYPE
    SYNTAX      SEQUENCE OF FsMIPbSrcDstIpSVlanEntry
    MAX-ACCESS  not-accessible
    STATUS      current
    DESCRIPTION
        "This object specifies a table containing per port, per Source IP Address,
        per Destination IP Address based Service VLAN classification information
        in the device. Entries can be configured into this table only when the bridge
        is configured as a Provider Bridge and the'PortType' for
        this port is SET as Proprietary Customer Network Port or Proprietary 
        Customer Edge Port."
    ::= { fsMIPbConfig  10}

fsMIPbSrcDstIpSVlanEntry OBJECT-TYPE
    SYNTAX      FsMIPbSrcDstIpSVlanEntry
    MAX-ACCESS  not-accessible
    STATUS      current
    DESCRIPTION
        "This object specifies Information controlling Service VLAN classification at this 
        specified port for an ingress IP frame with the Source and Destination
        IP Address in the IP header of the frame as specified in this entry."
    INDEX { fsMIPbPort, fsMIPbSrcDstSrcIpAddr, fsMIPbSrcDstDstIpAddr }
    ::= { fsMIPbSrcDstIpSVlanTable 1 }

FsMIPbSrcDstIpSVlanEntry ::=
    SEQUENCE {
        fsMIPbSrcDstSrcIpAddr            IpAddress,
        fsMIPbSrcDstDstIpAddr            IpAddress,
        fsMIPbSrcDstIpSVlan              VlanId,
        fsMIPbSrcDstIpRowStatus          RowStatus
    }
    
fsMIPbSrcDstSrcIpAddr OBJECT-TYPE
    SYNTAX      IpAddress
    MAX-ACCESS  not-accessible
    STATUS      current
    DESCRIPTION
        "This object specifies the Source IP Address in the IP header of an ingress
        IP frame at this specified port."
    ::= { fsMIPbSrcDstIpSVlanEntry 1 }
    
fsMIPbSrcDstDstIpAddr OBJECT-TYPE
    SYNTAX      IpAddress
    MAX-ACCESS  not-accessible
    STATUS      current
    DESCRIPTION
        "This object specifies the Destination IP Address in the IP header of an ingress
        IP frame at this specified port."
    ::= { fsMIPbSrcDstIpSVlanEntry 2 }


fsMIPbSrcDstIpSVlan OBJECT-TYPE
    SYNTAX      VlanId
    MAX-ACCESS  read-write
    STATUS      current
    DESCRIPTION
        "This object specifies the Service VLAN ID assigned to frames ingress at this port
        when the Source and Destination IP address in the IP header of 
        the frame are same as specified in this entry."
    ::= { fsMIPbSrcDstIpSVlanEntry 3 }
    
fsMIPbSrcDstIpRowStatus OBJECT-TYPE
    SYNTAX      RowStatus
    MAX-ACCESS  read-create
    STATUS      current
    DESCRIPTION
        "This object specifies the status of this entry. An entry is
        created in this table when this object is SET to 'createAndWait'.
        The entry in this table is used when the status of this object 
        is SET 'active'. The entry in this table is not used when this 
        object is SET 'notInService'. An entry created in this table is
        deleted when this object is SET 'destroy'."

    ::= { fsMIPbSrcDstIpSVlanEntry 4 }
    
-- -------------------------------------------------------------
-- The S-VLAN Port ,Customer VLAN ID, Destination IP Address based
-- Configuration Table
-- -------------------------------------------------------------

fsMIPbCVlanDstIpSVlanTable OBJECT-TYPE
    SYNTAX      SEQUENCE OF FsMIPbCVlanDstIpSVlanEntry
    MAX-ACCESS  not-accessible
    STATUS      current
    DESCRIPTION
        "This object specifies the A table containing per port, per Customer
        VLAN ID, per Destination IP Address, based Service VLAN classification information in the 
        device. Entries can be configured into this table only when the bridge
        is configured as Provider Bridge or Provider Edge Bridge and the 
        Port Type for this port is SET as Proprietary Customer Edge Port 
        / Proprietary Customer Network Port."
    ::= { fsMIPbConfig 11 }

fsMIPbCVlanDstIpSVlanEntry OBJECT-TYPE
    SYNTAX      FsMIPbCVlanDstIpSVlanEntry
    MAX-ACCESS  not-accessible
    STATUS      current
    DESCRIPTION
        "This object specifies the Information controlling Service VLAN classification at this specified
        port for an ingress IP frame with the classified Customer VLAN ID as 
        specified in this entry and the Destination IP Address in the IP header 
        of the frame as specified in this entry.
        Classification of Customer VLAN ID may be from the Customer VLAN tag
        in the received frame OR based on Port CVLAN table."
    INDEX { fsMIPbPort, fsMIPbCVlanDstIpCVlan, fsMIPbCVlanDstIp }
    ::= { fsMIPbCVlanDstIpSVlanTable 1 }

FsMIPbCVlanDstIpSVlanEntry ::=
    SEQUENCE {
        fsMIPbCVlanDstIpCVlan          VlanId,
        fsMIPbCVlanDstIp               IpAddress,
        fsMIPbCVlanDstIpSVlan          VlanId,
        fsMIPbCVlanDstIpRowStatus      RowStatus
    }
    
fsMIPbCVlanDstIpCVlan OBJECT-TYPE
    SYNTAX      VlanId
    MAX-ACCESS  not-accessible
    STATUS      current
    DESCRIPTION
        "This object specifies the Customer VLAN ID in the Customer VLAN tag of an ingress frame
        at this specified port or the Customer VLAN ID for which the ingress
        frame is classified for at this specified port."
    ::= { fsMIPbCVlanDstIpSVlanEntry 1 }
    
fsMIPbCVlanDstIp OBJECT-TYPE
    SYNTAX      IpAddress
    MAX-ACCESS  not-accessible
    STATUS      current
    DESCRIPTION
        "This object specifies the Destination IP Address in the IP header of an ingress
        IP frame at this specified port."
    ::= { fsMIPbCVlanDstIpSVlanEntry 2 }

fsMIPbCVlanDstIpSVlan OBJECT-TYPE
    SYNTAX      VlanId
    MAX-ACCESS  read-write
    STATUS      current
    DESCRIPTION
        "This object specifies the Service VLAN ID assigned to frames ingress at this port
        when the classified Customer VLAN ID is same as specified in this entry 
        and the Destination IP address in the IP header of the frame is same 
        as specified in this entry. Classification of Customer VLAN ID may be
        from the Customer VLAN tag in the received frame OR based on Port CVLAN table."
    ::= { fsMIPbCVlanDstIpSVlanEntry 3 }
    
fsMIPbCVlanDstIpRowStatus OBJECT-TYPE
    SYNTAX      RowStatus
    MAX-ACCESS  read-create
    STATUS      current
    DESCRIPTION
        "This object specifies the status of this entry. An entry is
        created in this table when this object is SET to 'createAndWait'.
        The entry in this table is used when the status of this object 
        is SET 'active'. The entry in this table is not used when this 
        object is SET 'notInService'. An entry created in this table is
        deleted when this object is SET 'destroy'."

    ::= { fsMIPbCVlanDstIpSVlanEntry 4 }
    
-- -------------------------------------------------------------
-- The C-VLAN Port based Configuration Table
-- -------------------------------------------------------------

fsMIPbPortBasedCVlanTable OBJECT-TYPE
    SYNTAX      SEQUENCE OF FsMIPbPortBasedCVlanEntry
    MAX-ACCESS  not-accessible
    STATUS      current
    DESCRIPTION
        "This object specifies a table containing Customer Edge Port / Proprietary
        Customer Edge Port / Proprietary Customer Network Port mapping to Customer VLAN on a
         providerBridge. This table is used for a classifying a untagged frame 
         received on above mentioned customer ports."
    ::= { fsMIPbConfig 12 }
    
fsMIPbPortBasedCVlanEntry OBJECT-TYPE
    SYNTAX      FsMIPbPortBasedCVlanEntry
    MAX-ACCESS  not-accessible
    STATUS      current
    DESCRIPTION
        "This object specifies an Entry in this table which will be 
        created whenever a port is configured as Customer Edge Port / Proprietary
        Customer Edge Port / Proprietary Customer
        Network Port. This Entry will be used on the ingress frame on the specified
        ports based on enabled status for classifying the frame to CVLAN. Also 
        the Entry will be deleted in this table, when the port type is modified 
        anything other than the specified one."
    INDEX { fsMIPbPort }
    ::= { fsMIPbPortBasedCVlanTable 1 }
            
FsMIPbPortBasedCVlanEntry ::=
    SEQUENCE {
        fsMIPbPortCVlan                   VlanId,
        fsMIPbPortCVlanClassifyStatus     EnabledStatus, 
        fsMIPbPortEgressUntaggedStatus    INTEGER
    }
    
fsMIPbPortCVlan OBJECT-TYPE
   SYNTAX      VlanId
   MAX-ACCESS  read-write
   STATUS      current
   DESCRIPTION
        "This object specifies the Customer VLAN ID assigned to untagged frames ingress at this
        specified Customer Edge Port / Proprietary Customer Edge Port /
        Proprietary Customer Network Port."
    ::= { fsMIPbPortBasedCVlanEntry 1 }

fsMIPbPortCVlanClassifyStatus OBJECT-TYPE
   SYNTAX      EnabledStatus
   MAX-ACCESS  read-write
   STATUS      current
   DESCRIPTION
        "This object specifies the C-VLAN classification status on a port.
         This Object can be enabled/disabled only for PropCEP/PropCNP. For CEP, 
         this object cannot be disabled."
    DEFVAL { enabled }
    ::= { fsMIPbPortBasedCVlanEntry 2 }

 fsMIPbPortEgressUntaggedStatus OBJECT-TYPE
   SYNTAX      INTEGER  { allow(1), deny(2) }
   MAX-ACCESS  read-write
   STATUS      current
   DESCRIPTION
        "This object specifies whether to allow or drop untagged packets 
         from being transmitted on CEP port. When it is set to allow, untagged packets 
         will be allowed to be transmitted on CEP port. By default, the object is set 
         to deny which will drop untagged packets from being transmitted on CEP port."
    DEFVAL { deny }
    ::= { fsMIPbPortBasedCVlanEntry 3 }

-- -------------------------------------------------------------
-- EtherType SwappingTable 
-- -------------------------------------------------------------

fsMIPbEtherTypeSwapTable OBJECT-TYPE
    SYNTAX      SEQUENCE OF FsMIPbEtherTypeSwapEntry
    MAX-ACCESS  not-accessible
    STATUS      current
    DESCRIPTION
    "This object specifies a Table containing the Translation information of the ethertype for a 
    Service VLAN in a given packet. This Table shall be used only at ingress 
    and NOT at egress of the Customer Network Port / Proprietary Customer Network 
    Port / Provider Network Port. This translation table is applicable for only
    Service VLAN and not for customer VLAN's."
    ::= { fsMIPbConfig 13 }
    
fsMIPbEtherTypeSwapEntry OBJECT-TYPE
    SYNTAX      FsMIPbEtherTypeSwapEntry
    MAX-ACCESS  not-accessible
    STATUS      current
    DESCRIPTION
    "This object specifies the entry containing the Local and Relay Ether type for a given packet on
    a particular port. This entry shall be applicable on all types of ports
    if and only if fsMIPbPortSVlanEtherTypeSwapStatus is Enabled on that Port."
    INDEX { fsMIPbPort, fsMIPbLocalEtherType}
    ::= { fsMIPbEtherTypeSwapTable 1 }
            
FsMIPbEtherTypeSwapEntry ::=
    SEQUENCE {
        fsMIPbLocalEtherType             Integer32,
        fsMIPbRelayEtherType             Integer32,
        fsMIPbEtherTypeSwapRowStatus     RowStatus
    }
   
fsMIPbLocalEtherType OBJECT-TYPE
    SYNTAX      Integer32 (1..65535) 
    MAX-ACCESS  not-accessible 
    STATUS      current
    DESCRIPTION
    "This object specifies the Ether type present in the service vlan tag of the ingress packet at
    the given port."
    ::= { fsMIPbEtherTypeSwapEntry 1 }

fsMIPbRelayEtherType OBJECT-TYPE
    SYNTAX      Integer32 (1..65535) 
    MAX-ACCESS  read-write
    STATUS      current
    DESCRIPTION
    "This object specifies the Relay Ether type mapped for the ether type present in the local
    service vlan tag of the ingress packet at the given port."
    ::= { fsMIPbEtherTypeSwapEntry 2 }

fsMIPbEtherTypeSwapRowStatus  OBJECT-TYPE
    SYNTAX      RowStatus 
    MAX-ACCESS  read-create 
    STATUS      current
    DESCRIPTION
        "This object specifies the status of this entry. An entry is
        created in this table when this object is SET to 'createAndWait'.
        The entry in this table is used when the status of this object 
        is SET 'active'. The entry in this table is not used when this 
        object is SET 'notInService'. An entry created in this table is
        be deleted when this object is SET 'destroy'."
    ::= { fsMIPbEtherTypeSwapEntry 3 }

-- ----------------------------------------------------------------
-- S-VLAN configuration table
-- ----------------------------------------------------------------
fsMIPbSVlanConfigTable OBJECT-TYPE
    SYNTAX      SEQUENCE OF FsMIPbSVlanConfigEntry
    MAX-ACCESS  not-accessible
    STATUS      current
    DESCRIPTION
    "This object specifies the table to configure the service type supported by
     an S-VLAN. Based on the service type configured for the S-VLAN, the oper point-to-point  
     state of PEP ports will be determined. The service type SET for S-VLAN is
     applicable only for the S-VLAN in specified Virtual Context identified by
     the Virtual Context identifier in this entry."

    ::= { fsMIPbConfig 14 }
    
fsMIPbSVlanConfigEntry OBJECT-TYPE
    SYNTAX      FsMIPbSVlanConfigEntry
    MAX-ACCESS  not-accessible
    STATUS      current
    DESCRIPTION

    "This object specifies the service type can be configured for an S-VLAN only when the VLAN 
    is already created in the system."

    INDEX { fsMIPbContextId, dot1qVlanIndex }
    ::= { fsMIPbSVlanConfigTable 1 }
            
FsMIPbSVlanConfigEntry ::=
    SEQUENCE {
        fsMIPbSVlanConfigServiceType          INTEGER
    }

fsMIPbSVlanConfigServiceType OBJECT-TYPE
    SYNTAX      INTEGER {
                    eLine (1),
                    eLan  (2)
                }
    MAX-ACCESS  read-write
    STATUS      current
    DESCRIPTION
       "The object specifies the service type supported by the S-VLAN in the 
       Virtual Context. When it is set to 'eLine', the S-VLAN connects not more 
       than two customer interfaces. If the service type for a vlan is 'eLine', 
       then learning member ports through GVRP will not be allowed.       
       Hence the oper point-to-point state of the PEPs connecting the S-VLAN can
       be set to True for specified Virtual Context.
       When it is set to 'eLan', the S-VLAN connects more than two customer
       interfaces.So, the oper point-to-point state of the PEPs connecting the
       S-VLAN will be set to False for specified Virtual Context.
       In case of IVL, When the service type is set to E-Line for a VLAN, 
       the MAC learning status will be set to 'disabled'. When it is set  
       to E-LAN, MAC learning status will be enabled for that VLAN."

    ::= { fsMIPbSVlanConfigEntry 1 }

-- ----------------------------------------------------------------
-- Tunnel protocol configuration table
-- ----------------------------------------------------------------
fsMIPbTunnelProtocolTable OBJECT-TYPE
   SYNTAX      SEQUENCE OF FsMIPbTunnelProtocolEntry
   MAX-ACCESS  not-accessible
   STATUS      deprecated
   DESCRIPTION
      "This object specifies the table containing information about the handling (Tunnel/Peer/
      Discard)of customer Layer 2 protocols (STP/GVRP/GMRP/LACP/Dot1x
      and IGMP) inside service provider network."
   ::= { fsMIPbConfig 15 }
 
fsMIPbTunnelProtocolEntry OBJECT-TYPE
   SYNTAX      FsMIPbTunnelProtocolEntry
   MAX-ACCESS  not-accessible
   STATUS      deprecated
   DESCRIPTION 
      "This object specifies the entry indicating the handling (Tunnel/Peer/Discard) of Layer 2
      protocols (STP/GVRP/GMRP/LACP/Dot1x and IGMP) on this port.
      This table is supported only for Provider Core or Provider Edge 
      Bridges."
      
   INDEX { fsMIPbPort }
   ::= { fsMIPbTunnelProtocolTable 1 }
    
 FsMIPbTunnelProtocolEntry ::=
 SEQUENCE {
    fsMIPbTunnelProtocolDot1x      TunnelStatus,
    fsMIPbTunnelProtocolLacp       TunnelStatus,
    fsMIPbTunnelProtocolStp        TunnelStatus,
    fsMIPbTunnelProtocolGvrp       TunnelStatus,
    fsMIPbTunnelProtocolGmrp       TunnelStatus,
    fsMIPbTunnelProtocolIgmp       TunnelStatus
 }

fsMIPbTunnelProtocolDot1x OBJECT-TYPE
   SYNTAX      TunnelStatus
   MAX-ACCESS  read-write
   STATUS      deprecated
   DESCRIPTION
      "This object specifies the object to specify whether to
       peer/tunnel/discard the Dot1x packets received on this port."
   ::= { fsMIPbTunnelProtocolEntry  1 }

fsMIPbTunnelProtocolLacp OBJECT-TYPE
   SYNTAX      TunnelStatus
   MAX-ACCESS  read-write
   STATUS      deprecated
   DESCRIPTION
      "This object specifies whether to peer/tunnel/discard the LACP packets
       received on this port."
   ::= { fsMIPbTunnelProtocolEntry 2 }

fsMIPbTunnelProtocolStp OBJECT-TYPE
   SYNTAX      TunnelStatus
   MAX-ACCESS  read-write
   STATUS      deprecated
   DESCRIPTION
     "This object specifies whether to peer/tunnel/discard the STP packets
      received on this port."
   ::= { fsMIPbTunnelProtocolEntry 3 }

fsMIPbTunnelProtocolGvrp OBJECT-TYPE
   SYNTAX      TunnelStatus
   MAX-ACCESS  read-write
   STATUS      deprecated 
   DESCRIPTION 
      "This object specifies whether to peer/tunnel/discard the GVRP packets
       received on this port."
   ::= { fsMIPbTunnelProtocolEntry 4 } 

fsMIPbTunnelProtocolGmrp OBJECT-TYPE
   SYNTAX      TunnelStatus
   MAX-ACCESS  read-write
   STATUS      deprecated
   DESCRIPTION
      "This object specifies whether to peer/tunnel/discard the GMRP packets
       received on this port."
   ::= { fsMIPbTunnelProtocolEntry 5 }

fsMIPbTunnelProtocolIgmp OBJECT-TYPE
   SYNTAX      TunnelStatus
   MAX-ACCESS  read-write
   STATUS      deprecated
   DESCRIPTION
      "This object specifies whether to peer/tunnel/discard the IGMP packets
      received on this port."
   ::= { fsMIPbTunnelProtocolEntry 6 }

-- ----------------------------------------------------------------
-- Tunnel protocol statistics table
-- ----------------------------------------------------------------
fsMIPbTunnelProtocolStatsTable OBJECT-TYPE
   SYNTAX      SEQUENCE OF FsMIPbTunnelProtocolStatsEntry
   MAX-ACCESS  not-accessible
   STATUS      deprecated
   DESCRIPTION
      "This object specifies the table containing statistics information about the tunneled 
       Layer 2 protocols (STP/GVRP/GMRP/LACP/Dot1x and IGMP) received 
       and transmitted over a port."
   ::= { fsMIPbConfig 16 }
 
fsMIPbTunnelProtocolStatsEntry OBJECT-TYPE
   SYNTAX      FsMIPbTunnelProtocolStatsEntry
   MAX-ACCESS  not-accessible
   STATUS      deprecated
   DESCRIPTION 
      "This object specifies the Entry indicating the handling (Tunnel/Peer/Discard) of Layer 2
      protocols (STP/GVRP/GMRP/LACP/Dot1x and IGMP) on this port.
      This table is supported only for Provider Core or Provider Edge 
      Bridges."

   INDEX { fsMIPbPort }
   ::= { fsMIPbTunnelProtocolStatsTable 1 }
    
FsMIPbTunnelProtocolStatsEntry ::=
 SEQUENCE {
      fsMIPbTunnelProtocolDot1xPktsRecvd Counter32,
      fsMIPbTunnelProtocolDot1xPktsSent  Counter32,
      fsMIPbTunnelProtocolLacpPktsRecvd  Counter32,
      fsMIPbTunnelProtocolLacpPktsSent   Counter32,
      fsMIPbTunnelProtocolStpPDUsRecvd   Counter32,
      fsMIPbTunnelProtocolStpPDUsSent    Counter32,
      fsMIPbTunnelProtocolGvrpPDUsRecvd  Counter32,
      fsMIPbTunnelProtocolGvrpPDUsSent   Counter32,
      fsMIPbTunnelProtocolGmrpPktsRecvd  Counter32,
      fsMIPbTunnelProtocolGmrpPktsSent   Counter32,
      fsMIPbTunnelProtocolIgmpPktsRecvd  Counter32,
      fsMIPbTunnelProtocolIgmpPktsSent   Counter32
   }

fsMIPbTunnelProtocolDot1xPktsRecvd OBJECT-TYPE
   SYNTAX      Counter32
   MAX-ACCESS  read-only
   STATUS      deprecated
   DESCRIPTION
      "This object specifies the number of tunneled Dot1x Packets received."
   ::= { fsMIPbTunnelProtocolStatsEntry 1 }

fsMIPbTunnelProtocolDot1xPktsSent OBJECT-TYPE
   SYNTAX      Counter32
   MAX-ACCESS  read-only
   STATUS      deprecated 
   DESCRIPTION 
      "This object specifies the number of tunneled Dot1x Packets transmitted."
   ::= { fsMIPbTunnelProtocolStatsEntry 2 }

fsMIPbTunnelProtocolLacpPktsRecvd OBJECT-TYPE 
   SYNTAX      Counter32
   MAX-ACCESS  read-only
   STATUS      deprecated 
   DESCRIPTION 
      "This object specifies the number of tunneled LACP Packets received."
   ::= { fsMIPbTunnelProtocolStatsEntry 3 } 

fsMIPbTunnelProtocolLacpPktsSent OBJECT-TYPE 
   SYNTAX      Counter32
   MAX-ACCESS  read-only
   STATUS      deprecated 
   DESCRIPTION 
      "This object specifies the number of tunneled LACP packets transmitted."
   ::= { fsMIPbTunnelProtocolStatsEntry 4 } 

fsMIPbTunnelProtocolStpPDUsRecvd OBJECT-TYPE
   SYNTAX      Counter32
   MAX-ACCESS  read-only
   STATUS      deprecated 
   DESCRIPTION 
      "This object specifies the number of tunneled STP PDUs received."
   ::= { fsMIPbTunnelProtocolStatsEntry 5 } 

fsMIPbTunnelProtocolStpPDUsSent OBJECT-TYPE 
   SYNTAX      Counter32
   MAX-ACCESS  read-only
   STATUS      deprecated 
   DESCRIPTION 
      "This object specifies the number of tunneled STP PDUs transmitted."
   ::= { fsMIPbTunnelProtocolStatsEntry 6 } 

fsMIPbTunnelProtocolGvrpPDUsRecvd OBJECT-TYPE 
   SYNTAX      Counter32
   MAX-ACCESS  read-only
   STATUS      deprecated 
   DESCRIPTION 
      "This object specifies the number of tunneled  GVRP PDUs received."
   ::= { fsMIPbTunnelProtocolStatsEntry 7 } 

fsMIPbTunnelProtocolGvrpPDUsSent OBJECT-TYPE 
   SYNTAX      Counter32
   MAX-ACCESS  read-only
   STATUS      deprecated 
   DESCRIPTION 
      "This object specifies the number of tunneled GVRP PDUs transmitted."
   ::= { fsMIPbTunnelProtocolStatsEntry 8 } 

fsMIPbTunnelProtocolGmrpPktsRecvd OBJECT-TYPE
   SYNTAX      Counter32
   MAX-ACCESS  read-only
   STATUS      deprecated
   DESCRIPTION
      "This object specifies the number of tunneled GMRP PDUs packets received."
   ::= { fsMIPbTunnelProtocolStatsEntry 9 }

fsMIPbTunnelProtocolGmrpPktsSent OBJECT-TYPE
   SYNTAX      Counter32
   MAX-ACCESS  read-only
   STATUS      deprecated 
   DESCRIPTION 
      "This object specifies the number of tunneled GMRP packets transmitted."
   ::= { fsMIPbTunnelProtocolStatsEntry 10 }

fsMIPbTunnelProtocolIgmpPktsRecvd OBJECT-TYPE 
   SYNTAX      Counter32
   MAX-ACCESS  read-only
   STATUS      deprecated 
   DESCRIPTION 
      "This object specifies the number of tunneled IGMP packets received."
   ::= { fsMIPbTunnelProtocolStatsEntry 11 } 

fsMIPbTunnelProtocolIgmpPktsSent OBJECT-TYPE 
   SYNTAX      Counter32
   MAX-ACCESS  read-only
   STATUS      deprecated 
   DESCRIPTION 
      "This object specifies the number of tunnelled IGMP packets transmitted."
   ::= { fsMIPbTunnelProtocolStatsEntry 12 }

-- ----------------------------------------------------------------
-- Provider Edge Port configuration table 
-- ----------------------------------------------------------------

fsMIPbPepExtTable OBJECT-TYPE
    SYNTAX      SEQUENCE OF FsMIPbPepExtEntry
    MAX-ACCESS  not-accessible
    STATUS      current
    DESCRIPTION
    "This object specifies an extension of dot1adMIPepTable table, and it provides
    additional configurations to PEPs (like Cos Preservations,..). 
    when a entry in dot1adMIPepTable is created, then an entry will be
    created in this table."
    
    ::= { fsMIPbConfig 17 }
    
fsMIPbPepExtEntry OBJECT-TYPE
    SYNTAX      FsMIPbPepExtEntry
    MAX-ACCESS  not-accessible
    STATUS      current
    DESCRIPTION

    "This object specifies the entry  containing information like 
    (COS preservation, ..) for the internal PEPs. Creation of an entry in this
    table is not allowed and only modification is allowed."
   
   AUGMENTS    { dot1adMIPepEntry }
   ::= { fsMIPbPepExtTable 1 }
            
FsMIPbPepExtEntry ::=
    SEQUENCE {
        fsMIPbPepExtCosPreservation     EnabledStatus
    }

fsMIPbPepExtCosPreservation OBJECT-TYPE
    SYNTAX      EnabledStatus
    MAX-ACCESS  read-write
    STATUS      current
    DESCRIPTION
      "This object is used to enable or disable COS preservation for a    
       service provided by this PEP." 

    DEFVAL      { disabled }
    ::= { fsMIPbPepExtEntry 1 }

-- ----------------------------------------------------------------
-- Customer vlan statistics  table 
-- ----------------------------------------------------------------


fsMIPbPortCVlanCounterTable OBJECT-TYPE
   SYNTAX      SEQUENCE OF FsMIPbPortCVlanCounterEntry
   MAX-ACCESS  not-accessible
   STATUS      current
   DESCRIPTION
             "This object specifies the table containing the statistics
              information for a specific Customer VLAN and CEP port combination.
              It contains number of Frames received and bytes received for 
              a customer VLAN + CEP port."
   ::= { fsMIPbConfig 18 }

fsMIPbPortCVlanCounterEntry OBJECT-TYPE
   SYNTAX      FsMIPbPortCVlanCounterEntry
   MAX-ACCESS  not-accessible
   STATUS      current
   DESCRIPTION
              "This object specifies each entry containing the customer VLAN
              statistics for a port."
   INDEX { fsMIPbPortCVlanContextId ,fsMIPbPortCVlanPort,fsMIPbPortCVlanIndex }
   ::= { fsMIPbPortCVlanCounterTable 1 }                                        
     FsMIPbPortCVlanCounterEntry ::=
   SEQUENCE {                                                                 
             fsMIPbPortCVlanContextId               Integer32,
             fsMIPbPortCVlanPort                    Integer32,
             fsMIPbPortCVlanIndex                   Unsigned32,
             fsMIPbPortCVlanCounterRxUcast          Counter32,
             fsMIPbPortCVlanCounterRxFrames         Counter32,
             fsMIPbPortCVlanCounterRxBytes          Counter32,
             fsMIPbPortCVlanCounterStatus           EnabledStatus,             
             fsMIPbPortCVlanClearCounter            TruthValue 
          }


fsMIPbPortCVlanContextId OBJECT-TYPE
   SYNTAX        Integer32 (0..65535)
   MAX-ACCESS    not-accessible
   STATUS        current
   DESCRIPTION
      "This object specifies the virtual context in the system."
   ::= { fsMIPbPortCVlanCounterEntry 1 }


fsMIPbPortCVlanPort OBJECT-TYPE
    SYNTAX      Integer32 (1..65535)
    MAX-ACCESS  read-only
    STATUS      current
    DESCRIPTION
        "This object specifies the interface index in the system. "
    ::= { fsMIPbPortCVlanCounterEntry 2 }

fsMIPbPortCVlanIndex OBJECT-TYPE
    SYNTAX      Unsigned32 (1..4095)
    MAX-ACCESS  read-only
    STATUS      current
    DESCRIPTION
        "This object specifies the Customer VLAN ID for which statistics 
        collection information is available."
    ::= { fsMIPbPortCVlanCounterEntry 3 }


fsMIPbPortCVlanCounterRxUcast OBJECT-TYPE
   SYNTAX      Counter32
   MAX-ACCESS  read-only
   STATUS      current
   DESCRIPTION
            "This object specifies the Number of unicast packets received for
            each entry."
   ::= { fsMIPbPortCVlanCounterEntry 4 }

fsMIPbPortCVlanCounterRxFrames OBJECT-TYPE
   SYNTAX      Counter32
   MAX-ACCESS  read-only
   STATUS      current
   DESCRIPTION
            "This object specifies the Number of frames(all types of packets)
            received for each entry."
   ::= { fsMIPbPortCVlanCounterEntry 5 }


fsMIPbPortCVlanCounterRxBytes OBJECT-TYPE
   SYNTAX      Counter32
   MAX-ACCESS  read-only
   STATUS      current
   DESCRIPTION
             "This object specifies the Number of bytes received for each entry."
   ::= { fsMIPbPortCVlanCounterEntry 6 }


fsMIPbPortCVlanCounterStatus OBJECT-TYPE
   SYNTAX      EnabledStatus
   MAX-ACCESS  read-write
   STATUS      current
   DESCRIPTION
      "This object specifies a Truth value indicating the statistics collection
      is enabled/disabled for this customer vlan.
       When statistics collection is set to disabled, stops collecting
       statistics on a specific entry in this table.
       When statistics collection is set to enabled, starts collecting
       statistics on a specific entry in this table. "
   DEFVAL   { disabled }
   ::= {fsMIPbPortCVlanCounterEntry 7 }

fsMIPbPortCVlanClearCounter OBJECT-TYPE
   SYNTAX      TruthValue
   MAX-ACCESS  read-write
   STATUS      current
   DESCRIPTION
            "This object is used to reset all the counter variables to initialization
            value (zero)."
   DEFVAL   {false}
   ::= { fsMIPbPortCVlanCounterEntry 8 }


END

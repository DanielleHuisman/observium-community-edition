-- Copyright (C) 2006-2012 Aricent. All Rights Reserved

-- $Id: fspbrst.mib,v 1.7 2016/02/18 09:47:31 siva Exp $

ARICENT-PB-RSTP-MIB DEFINITIONS ::= BEGIN

-- ------------------------------------------------------------------
-- Proprietary MIB for C-VLAN component Rapid Spanning Tree Protocol
-- in Provider Bridges
-- ------------------------------------------------------------------

IMPORTS

   OBJECT-TYPE, MODULE-IDENTITY, Integer32,Counter32,
   TimeTicks,enterprises FROM SNMPv2-SMI
   TEXTUAL-CONVENTION, TruthValue FROM SNMPv2-TC
   Timeout,BridgeId FROM BRIDGE-MIB;

futurePbRstMIB MODULE-IDENTITY
    LAST-UPDATED "201209050000Z"
    ORGANIZATION "ARICENT COMMUNICATIONS SOFTWARE"
    CONTACT-INFO "support@aricent.com"
    DESCRIPTION "MIB for Rapid Spanning Tree Algorithm & Protocol in C-VLAN
                 component of Provider Bridges"
    REVISION "201209050000Z"
    DESCRIPTION "MIB for Rapid Spanning Tree Algorithm & Protocol in C-VLAN
                 component of Provider Bridges"
::= { enterprises futuresoftware(2076) 123 }

EnabledStatus ::= TEXTUAL-CONVENTION
    STATUS      current
    DESCRIPTION
        "A simple status value for the object." 
    SYNTAX      INTEGER { enabled(1), disabled(2) }


VlanId ::= TEXTUAL-CONVENTION
    STATUS      current
    DESCRIPTION
        "This value and the CEP port identifier are indices to C-VLAN port 
        tables. Values 1 to 4095 are permitted. Values from 1 to 4094 
        represents S-VLAN id. (CEP, 4095) identifies the CEP port in the
        C-VLAN component."
    SYNTAX      Integer32 (1..4095)


futurePbRst     OBJECT IDENTIFIER ::= { futurePbRstMIB 1 }

-- Provider Bridges C-VLAN component RSTP Port Extention Group 

fsPbProviderStpStatus OBJECT-TYPE
   SYNTAX      EnabledStatus
   MAX-ACCESS  read-write
   STATUS      current
   DESCRIPTION
     "This object specifies the administrative module status requested by
      management for the spanning tree operation in S-VLAN component of Provider
      Bridges. This enables or disables spanning tree protocol (RSTP/MSTP)on
      S-VLAN component ports. A value of 'enabled' (1) indicates that the
      spanning tree protocol will be enabled on all the ports of the S-VLAN component.
       A value of 'disabled'(2) indicates that the spanning tree protocol will 
       be disabled on all the ports of the S-VLAN component. 
       This object can be set only after the object fsRstSystemControl has been 
       set."

   ::= {futurePbRst 1}

fsPbRstCVlanBridgeTable OBJECT-TYPE
   SYNTAX SEQUENCE OF FsPbRstCVlanBridgeEntry
   MAX-ACCESS not-accessible
   STATUS     current
   DESCRIPTION
      "This table contains bridge related information for RSTP operation in the
      C-VLAN component."
   ::= { futurePbRst 2 }

fsPbRstCVlanBridgeEntry OBJECT-TYPE
   SYNTAX      FsPbRstCVlanBridgeEntry
   MAX-ACCESS  not-accessible
   STATUS      current
   DESCRIPTION
      "Each entry in this table is for each C-VLAN component in Provider
       Bridges."
   INDEX { fsPbRstPort }
   ::= { fsPbRstCVlanBridgeTable 1 }

   FsPbRstCVlanBridgeEntry ::=
   SEQUENCE {
         fsPbRstPort                            Integer32,
         fsPbRstCVlanBridgeId                   BridgeId,
         fsPbRstCVlanBridgeDesignatedRoot       BridgeId,
         fsPbRstCVlanBridgeRootCost             Integer32,
         fsPbRstCVlanBridgeMaxAge               Timeout,
         fsPbRstCVlanBridgeHelloTime            Timeout,
         fsPbRstCVlanBridgeHoldTime             Integer32,
         fsPbRstCVlanBridgeForwardDelay         Timeout,
         fsPbRstCVlanBridgeTxHoldCount          Integer32,
         fsPbRstCVlanStpHelloTime               Timeout,
         fsPbRstCVlanStpMaxAge                  Timeout,
         fsPbRstCVlanStpForwardDelay            Timeout,
         fsPbRstCVlanStpTopChanges              Counter32,
         fsPbRstCVlanStpTimeSinceTopologyChange TimeTicks

   }

fsPbRstPort OBJECT-TYPE
    SYNTAX Integer32(0..65535)
    MAX-ACCESS not-accessible
    STATUS current
    DESCRIPTION
       "This object always indicates the port which is of type CEP. CEP port
       will be the index of the CVLAN Spanning tree."
       ::= { fsPbRstCVlanBridgeEntry 1}


fsPbRstCVlanBridgeId OBJECT-TYPE
    SYNTAX  BridgeId
    MAX-ACCESS  read-only
    STATUS  current
    DESCRIPTION
       "The Bridge-Identifier as used in the Spanning Tree Protocol operation
        in the C-VLAN component to uniquely identify a bridge.
        Bridge Mac address field in this object will be the MAC address of the
        corresponding customer edge port.
        The Bridge priority field in this object will be always 0xf.
        The Bridge Identifier System Id extension field in this object will be 
        always 0xfff."
    ::= { fsPbRstCVlanBridgeEntry 2 }

fsPbRstCVlanBridgeDesignatedRoot OBJECT-TYPE
    SYNTAX  BridgeId
    MAX-ACCESS  read-only
    STATUS  current
    DESCRIPTION
       "The bridge identifier of the root of the spanning tree as determined by 
       the Spanning Tree Protocol as executed by this C-VLAN component. This
       value is used as the Root Identifier parameter in all Configuration
       Bridge PDUs originated by this C-VLAN component."
       
    ::= { fsPbRstCVlanBridgeEntry 3 }

fsPbRstCVlanBridgeRootCost OBJECT-TYPE
    SYNTAX  Integer32
    MAX-ACCESS  read-only
    STATUS  current
    DESCRIPTION
       "The cost of the path to the root as seen from this C-VLAN component
        bridge."

    ::= { fsPbRstCVlanBridgeEntry 4 }

fsPbRstCVlanBridgeMaxAge OBJECT-TYPE
    SYNTAX  Timeout
    MAX-ACCESS  read-only
    STATUS  current
    DESCRIPTION
    "The value that all bridges use for MaxAge when  this bridge is acting as 
    the root. Note that 802.1D-1990 specifies that the range for this 
    parameter is related to the value of dot1dStpBridgeHelloTime. The
    granularity of this timer is specified by 802.1D-1990 to be 1 second. An
    agent may return a badValue error if a set is attempted to a value which is
    not a whole number of seconds."
    ::= { fsPbRstCVlanBridgeEntry 5 }

fsPbRstCVlanBridgeHelloTime OBJECT-TYPE
    SYNTAX  Timeout
    MAX-ACCESS  read-only
    STATUS  current
    DESCRIPTION
    "The value that all bridges use for HelloTime when
    this bridge is acting as the root. The granularity of this
    timer is specified by 802.1D- 1990 to be 1 second. An agent
    may return a badValue error if a set is attempted to a value
    which is not a  whole number of seconds."
    ::= { fsPbRstCVlanBridgeEntry 6 }

fsPbRstCVlanBridgeHoldTime OBJECT-TYPE
    SYNTAX  Integer32
    MAX-ACCESS  read-only
    STATUS  current
    DESCRIPTION
        "This time value determines the interval length during which no more 
        than two Configuration bridge PDUs shall be transmitted by this C-VLAN 
        component, in units of hundredths of a second."
    ::= { fsPbRstCVlanBridgeEntry 7 }

fsPbRstCVlanBridgeForwardDelay OBJECT-TYPE
    SYNTAX  Timeout
    MAX-ACCESS  read-only
    STATUS  current
    DESCRIPTION
    "The value that all bridges use for Forward Delay when this bridge is acting
     as the root. Note that 802.1D-1990 specifies that the range for this
     parameter is related to the value of  dot1dStpBridgeMaxAge. The granularity
     of this timer is specified  by 802.1D-1990 to be 1 second. An agent may
     return a badValue error if a set is attempted to a value which is not a
     whole number of seconds."
    ::= { fsPbRstCVlanBridgeEntry 8 }

fsPbRstCVlanBridgeTxHoldCount  OBJECT-TYPE
   SYNTAX  Integer32
   MAX-ACCESS read-only
   STATUS  current
   DESCRIPTION
         "The value used by the Port Transmit state machine to limit
          the maximum transmission rate."
   ::= { fsPbRstCVlanBridgeEntry 9 }


fsPbRstCVlanStpHelloTime OBJECT-TYPE
   SYNTAX  Timeout
   MAX-ACCESS read-only
   STATUS  current
   DESCRIPTION
   "The amount of time between the transmission of Configuration bridge 
   PDUs by this C-VLAN component on any port when it is the root of the 
   spanning tree or trying to become so, in units of hundredths of a second.
   This is the actual value that this bridge is currently using."
   ::= { fsPbRstCVlanBridgeEntry 10 }

 
 fsPbRstCVlanStpMaxAge OBJECT-TYPE
   SYNTAX  Timeout
   MAX-ACCESS read-only
   STATUS  current
   DESCRIPTION
   "The maximum age of Spanning Tree Protocol information learned from the 
   network on any port before it is discarded, in units of hundredths of
   a second. This is the actual value that this bridge is currently using."
   ::= { fsPbRstCVlanBridgeEntry 11 }

  
 fsPbRstCVlanStpForwardDelay OBJECT-TYPE
   SYNTAX  Timeout
   MAX-ACCESS read-only
   STATUS  current
   DESCRIPTION
   "This time value, measured in units of hundredths of a second, controls 
   how fast a port changes its spanning state when moving towards the Forwarding
   state. The value determines how long the port stays in each of the Listening
   and Learning states, which precede the Forwarding state. This value is also
   used, when a topology change has been detected and is underway, to age all
   dynamic entries in the Forwarding Database. [Note that this value is the one
   that this bridge is currently using, in contrast to
   dot1dStpBridgeForwardDelay which is the value that this bridge and all others
   would start using if/when this bridge were to become the root.]"
   ::= { fsPbRstCVlanBridgeEntry 12 }


   fsPbRstCVlanStpTopChanges OBJECT-TYPE
   SYNTAX  Counter32
   MAX-ACCESS  read-only
   STATUS  current
   DESCRIPTION
   "This object specifies the total number of topology changes detected by this
    bridge since the management entity was last reset or initialized."
   ::=  { fsPbRstCVlanBridgeEntry 13 }

   fsPbRstCVlanStpTimeSinceTopologyChange OBJECT-TYPE
   SYNTAX  TimeTicks 
   MAX-ACCESS  read-only
   STATUS  current
   DESCRIPTION
   "The time (in hundredths of a second) since the last time a topology 
   change was detected by the bridge entity."
   ::= { fsPbRstCVlanBridgeEntry 14 }




fsPbRstCVlanPortInfoTable OBJECT-TYPE
   SYNTAX SEQUENCE OF FsPbRstCVlanPortInfoEntry
   MAX-ACCESS not-accessible
   STATUS     current
   DESCRIPTION
      "This table contains the objects for RSTP in C-VLAN component of Provider 
       Bridges."
   ::= { futurePbRst 3 }

fsPbRstCVlanPortInfoEntry OBJECT-TYPE
   SYNTAX      FsPbRstCVlanPortInfoEntry
   MAX-ACCESS  not-accessible
   STATUS      current
   DESCRIPTION
      "Each entry in this table is for each C-VLAN component in Provider
       Bridges. Here the port represents the Ports (CEP/PEPs) of C-VLAN 
       component. Each table entry gives the spanning tree information for the 
       Customer Edge Port and Provider Edge Ports of C-VLAN components in 
       Provider Bridges."
   INDEX { fsPbRstPort,fsPbRstCepSvid }
   ::= { fsPbRstCVlanPortInfoTable 1 }

FsPbRstCVlanPortInfoEntry ::=
   SEQUENCE {
      fsPbRstCepSvid 
         VlanId,
      fsPbRstCVlanPortPriority
         Integer32,
      fsPbRstCVlanPortPathCost
         Integer32,
      fsPbRstCVlanPortRole
         INTEGER,
      fsPbRstCVlanPortState
         INTEGER,
      fsPbRstCVlanPortAdminEdgePort
         TruthValue,
      fsPbRstCVlanPortOperEdgePort
         TruthValue,
      fsPbRstCVlanPortAdminPointToPoint
         INTEGER,
      fsPbRstCVlanPortOperPointToPoint
         TruthValue,
      fsPbRstCVlanPortAutoEdge
         TruthValue,
      fsPbRstCVlanPortDesignatedRoot
         BridgeId,
      fsPbRstCVlanPortDesignatedCost
         Integer32,
      fsPbRstCVlanPortDesignatedBridge
         BridgeId,
      fsPbRstCVlanPortDesignatedPort
         OCTET STRING,
      fsPbRstCVlanPortForwardTransitions
         Counter32
      }


fsPbRstCepSvid OBJECT-TYPE
    SYNTAX VlanId
    MAX-ACCESS not-accessible 
    STATUS  current
    DESCRIPTION
        "This value and the CEP port identifier are indices to C-VLAN port 
        tables. Values 1 to 4095 are permitted. Values from 1 to 4094 
        represents S-VLAN id. (CEP, 4095) identifies the CEP port in the
        C-VLAN component."
    ::= {fsPbRstCVlanPortInfoEntry 1}
    

fsPbRstCVlanPortPriority OBJECT-TYPE
    SYNTAX  Integer32 (0..255)
    MAX-ACCESS  read-only
    STATUS  current
    DESCRIPTION
        "The value of the priority field which is contained in the first 
        (in network byte order) octet of the (2 octet long) Port ID.  
        The other octet of the Port ID is given by the value of fsPbRstPort.
         Priority is always assumed as 32 for C-VLAN component Ports."
         
    REFERENCE
         "IEEE 802.1D-1990: Section 4.5.5.1"
    ::= { fsPbRstCVlanPortInfoEntry 2 }

fsPbRstCVlanPortPathCost OBJECT-TYPE
    SYNTAX  Integer32 (1..65535)
    MAX-ACCESS  read-only
    STATUS  current
    DESCRIPTION
         "The contribution of this port to the path cost of paths towards the 
         spanning tree root which include this port. 802.1D-1990 recommends 
         that the default value of this parameter be in inverse proportion to 
         the speed of the attached LAN.
         Pathcost is always assumed as 128 for Provider Edge Ports.
         For CEP, port-path cost will be taken from dot1dStpPortPathCost of
         fsPbRstPort."
         
    REFERENCE
          "IEEE 802.1D-1990: Section 4.5.5.3"
    ::= { fsPbRstCVlanPortInfoEntry 3 }

fsPbRstCVlanPortRole OBJECT-TYPE
   SYNTAX      INTEGER {
                  disabledPort(0),
                  alternatePort(1),
                  backupPort(2),
                  rootPort(3),
                  designatedPort(4)
               }
   MAX-ACCESS  read-only
   STATUS      current
   DESCRIPTION
         "This indicates the current Port Role assumed by this Port."
   ::= { fsPbRstCVlanPortInfoEntry 4 }

fsPbRstCVlanPortState OBJECT-TYPE
    SYNTAX  INTEGER {
                     disabled(1),
                     blocking(2),
                     listening(3),
                     learning(4),
                     forwarding(5),
                     broken(6)
                 }
    MAX-ACCESS  read-only
    STATUS  current
    DESCRIPTION
          "The port's current state as defined by application of the Spanning 
          Tree Protocol. This state controls what action a port takes on 
          reception of a frame. If the bridge has detected a port that is 
          malfunctioning it will place that port into the broken(6) state.  For 
          ports which are disabled (see dot1dStpPortEnable), this object will 
          have a value of disabled(1)."
    REFERENCE
          "IEEE 802.1D-1990: Section 4.5.5.2"
    ::= { fsPbRstCVlanPortInfoEntry 5 }

fsPbRstCVlanPortAdminEdgePort OBJECT-TYPE
    SYNTAX      TruthValue
    MAX-ACCESS  read-only
    STATUS      current
    DESCRIPTION
        "This object specifies the administrative value of the Edge Port parameter.
        A value of TRUE(1) indicates that this port should be
         assumed as an edge-port and a value of FALSE(2) indicates
         that this port should be assumed as a non-edge-port.
         
         This is always 'false' for a Provider Egde Port."
         
    REFERENCE
        "IEEE 802.1t clause 14.8.2, 18.3.3"
    ::= { fsPbRstCVlanPortInfoEntry 6 }

fsPbRstCVlanPortOperEdgePort OBJECT-TYPE
    SYNTAX      TruthValue
    MAX-ACCESS  read-only
    STATUS      current
    DESCRIPTION
        "This object specifies the operational value of the Edge Port parameter.
        This object always assumes the value of 'False' for Provider Edge Ports
        of C-VLAN component."
    REFERENCE
        "IEEE 802.1t clause 14.8.2, 18.3.4"
    ::= { fsPbRstCVlanPortInfoEntry 7 }

fsPbRstCVlanPortAdminPointToPoint OBJECT-TYPE
    SYNTAX      INTEGER {
                    forceTrue(0),
                    forceFalse(1),
                    auto(2)
                }
    MAX-ACCESS  read-only
    STATUS      current
    DESCRIPTION
        "The administrative point-to-point status of the LAN segment
         attached to this port. A value of forceTrue(0) indicates that
         this port should always be treated as if it is connected to
         a point-to-point link. A value of forceFalse(1) indicates
         that this port should be treated as having a shared media
         connection. A value of auto(2) indicates that this port is
         considered to have a point-to-point link if it is an Aggregator
         and all of its members are aggregatable, or if the MAC entity
         is configured for full duplex operation, either through
         auto-negotiation or by management means.         
         Provider Edge Ports always assume the value of 'auto' for this 
         object."
   REFERENCE
       "IEEE 802.1w clause 6.4.3, 6.5, 14.8.2"
   ::= { fsPbRstCVlanPortInfoEntry 8 }

fsPbRstCVlanPortOperPointToPoint OBJECT-TYPE
    SYNTAX      TruthValue
    MAX-ACCESS  read-only
    STATUS      current
    DESCRIPTION
        "The operational point-to-point status of the LAN segment
         attached to this port. It indicates whether a port is
         considered to have a point-to-point connection or not.          
         This object will be set to 'True' for Provider Edge Ports 
         when the S-VLAN is attached to only two customer interfaces. 
         This will be set to 'False' when the S-VLAN is attached 
         to more than two customer interfaces."
     
    REFERENCE
        "IEEE 802.1w clause 6.4.3, 6.5, 14.8.2"
    ::= { fsPbRstCVlanPortInfoEntry 9 }

fsPbRstCVlanPortAutoEdge OBJECT-TYPE
    SYNTAX      TruthValue
    MAX-ACCESS  read-only
    STATUS      current
    DESCRIPTION
        "This parameter when TRUE(1) indicates that detection of a port 
         as Edge Port happens automatically and FALSE(2) 
         indicates that this feature is disabled.
         This object is always set to 'True' for Provider Edge Ports of 
         C-VLAN component."
    
    ::= { fsPbRstCVlanPortInfoEntry 10 }

fsPbRstCVlanPortDesignatedRoot OBJECT-TYPE
    SYNTAX  BridgeId
    MAX-ACCESS  read-only
    STATUS  current
    DESCRIPTION
       "The unique Bridge Identifier of the Bridge recorded as the Root 
       in the Configuration BPDUs transmitted by the Designated Bridge for 
       the segment to which this port is attached."
    REFERENCE
       "IEEE 802.1D-1990: Section 4.5.5.4"

    ::= { fsPbRstCVlanPortInfoEntry 11 }

fsPbRstCVlanPortDesignatedCost OBJECT-TYPE
    SYNTAX  Integer32
    MAX-ACCESS  read-only
    STATUS  current
    DESCRIPTION
       "The path cost of the Designated Port of the segment connected to this 
        port. This value is compared to the Root Path Cost field 
        in received bridge PDUs."
    REFERENCE
       "IEEE 802.1D-1990: Section 4.5.5.5"
    ::= { fsPbRstCVlanPortInfoEntry 12 }

fsPbRstCVlanPortDesignatedBridge OBJECT-TYPE
   SYNTAX  BridgeId
   MAX-ACCESS  read-only
   STATUS  current
   DESCRIPTION
      "The Bridge Identifier of the bridge which this port considers 
      to be the Designated Bridge for this port's segment."
   REFERENCE
      "IEEE 802.1D-1990: Section 4.5.5.6"
   ::= { fsPbRstCVlanPortInfoEntry 13 }

fsPbRstCVlanPortDesignatedPort OBJECT-TYPE
   SYNTAX  OCTET STRING (SIZE (2))
   MAX-ACCESS  read-only
   STATUS  current
   DESCRIPTION
     "The Port Identifier of the port on the Designated Bridge for this port's
      segment."
   REFERENCE
      "IEEE 802.1D-1990: Section 4.5.5.7"
   ::= { fsPbRstCVlanPortInfoEntry 14 }

fsPbRstCVlanPortForwardTransitions OBJECT-TYPE
    SYNTAX  Counter32
    MAX-ACCESS  read-only
    STATUS  current
    DESCRIPTION
      "The number of times this port has transitioned from the
      Learning state to the Forwarding state."
   ::= { fsPbRstCVlanPortInfoEntry 15 }

fsPbRstCVlanPortSmTable OBJECT-TYPE
   SYNTAX SEQUENCE OF FsPbRstCVlanPortSmEntry
   MAX-ACCESS not-accessible
   STATUS     current
   DESCRIPTION
      "This table contains the objects for the state machine information of 
      C-VLAN component Ports Provider Edge Bridges."
   ::= { futurePbRst 4 }

fsPbRstCVlanPortSmEntry OBJECT-TYPE
   SYNTAX      FsPbRstCVlanPortSmEntry
   MAX-ACCESS  not-accessible
   STATUS      current
   DESCRIPTION
      "Each entry in this table is for each C-VLAN component in Provider
       Bridges. Here the port represents the C-VLAN component ports. Each 
       table entry gives the state machine information for a C-VLAN component 
       Port in Provider Edge Bridges."
   INDEX { fsPbRstPort,fsPbRstCepSvid }
   ::= { fsPbRstCVlanPortSmTable 1 }

FsPbRstCVlanPortSmEntry ::=
   SEQUENCE {
      fsPbRstCVlanPortInfoSmState
         INTEGER,
      fsPbRstCVlanPortMigSmState
         INTEGER,
      fsPbRstCVlanPortRoleTransSmState
         INTEGER,
      fsPbRstCVlanPortStateTransSmState
         INTEGER,
      fsPbRstCVlanPortTopoChSmState
         INTEGER,
      fsPbRstCVlanPortTxSmState
         INTEGER
      }

fsPbRstCVlanPortInfoSmState OBJECT-TYPE
   SYNTAX      INTEGER {
                  disabled (0),
                  aged (1),
                  update (2),
                  superior (3),
                  repeat (4),
                  notdesignated (5),
                  present (6),
                  receive (7),
                  inferiordesignated (8)
               }
   MAX-ACCESS  read-only
   STATUS      current
   DESCRIPTION
      "This indicates the current state of the Port Information state machine.
      This object will hold the value 'disabled' when the Port Information state
      machine is in the DISABLED state, the value 'aged' when the state machine 
      is in the AGED state, the value 'update' when the state machine is in the
      UPDATE state, the value 'superior' when the state machine is in the
      SUPERIOR state, the value 'repeat' when the state machine is in the REPEAT
      state, the value 'notdesignated' when the state machine is in the 
      NOT_DESIGNATED state, the value 'present' when the state machine is in 
      the CURRENT state and the value 'receive' when the state machine is in 
      the RECEIVE state and the value 'inferiordesignated' when the state 
      machine is in the INFERIOR_DESIGNATED state."
   ::= { fsPbRstCVlanPortSmEntry 1 }

fsPbRstCVlanPortMigSmState OBJECT-TYPE
   SYNTAX      INTEGER {
                  checkingrstp (0),
                  selectingstp (1),
                  sensing (2)
               }
   MAX-ACCESS  read-only
   STATUS      current
   DESCRIPTION
      "This indicates the current state of the Port Protocol Migration state 
      machine. This object will hold the value 'checkingrstp' when the Protocol 
      Migration state machine is in the CHECKING_RSTP state, the value 
      'selectingstp' when the state machine is in the SELECTING_STP state, the 
      value 'sensing' when the state machine is in the SENSING state."
   ::= { fsPbRstCVlanPortSmEntry 2 }

fsPbRstCVlanPortRoleTransSmState OBJECT-TYPE
   SYNTAX      INTEGER {
                  init (0),
                  disableport (1),
                  disabledport (2),
                  rootport (3),
                  designatedport (4),
                  backupport (5),
                  rootproposed (6),
                  rootagreed(7),
                  reroot (8),
                  rootforward (9),
                  rootlearn (10),
                  rerooted (11),
                  designatedpropose (12),
                  designatedsynced (13),
                  designatedretired (14),
                  designatedforward (15),
                  designatedlearn (16),
                  designatedlisten (17)
               }
   MAX-ACCESS  read-only
   STATUS      current
   DESCRIPTION
     "This indicates the current state of the Port Role Transition state machine.
      This object will hold the value 'init' when the Port Role Transition state
      machine is in the INIT state, the value 'disableport' when the state 
      machine is in the DISABLE_PORT state, the value 'disabledport' when the 
      state machine is in the DISABLED_PORT state, the value 'rootport' when 
      the state machine is in the ROOT_PORT state, the value 'desgport' when 
      the state machine is in the DESIGNATED_PORT state, the value 'backupport' 
      when the state machine is in BACKUP_PORT state, the value 'rootproposed' 
      when the state machine is in the ROOT_PROPOSED state, the value 
      'rootagreed' when the state machine is in the ROOT_AGREED state, the 
      value 'reroot' when the state machine is in the REROOT
      state, the value 'rootforward' when the state machine is in the 
      ROOT_FORWARD state, the value 'rootlearn' when the state machine is in 
      the ROOT_LEARN state, the value 'rerooted' when the state machine is in 
      the REROOTED state, the value 'designatedpropose' when the state machine 
      is in the DESIGNATED_PROPOSE state, the value 'designatedsynced' when the 
      state machine is in the DESIGNATED_SYNCED state, the value 
      'designatedretired' when the state machine is in the DESIGNATED_RETIRED 
      state, the value 'designatedforward' when the state machine is in the 
      DESIGNATED_FORWARD state, the value 'designatedlearn' when the state 
      machine is in the DESIGNATED_LEARN state and the value 
      'designatedlisten' when the state machine is in the DESIGNATED_LISTEN
      state."
   ::= { fsPbRstCVlanPortSmEntry 3 }

fsPbRstCVlanPortStateTransSmState OBJECT-TYPE
   SYNTAX      INTEGER {
                  discarding (0),
                  learning (1),
                  forwarding (2)
               }
   MAX-ACCESS  read-only
   STATUS      current
   DESCRIPTION
      "This indicates the current state of the Port State Transition state machine.
      This object is used to hold the value 'discarding' when the Port State
      Transition state machine is in the DISCARDING state, the value 'learning'
      when the state machine is in the LEARNING state and the value 'forwarding'
      when the state machine is in the FORWARDING state." 
   ::= { fsPbRstCVlanPortSmEntry 4 }

fsPbRstCVlanPortTopoChSmState OBJECT-TYPE
   SYNTAX      INTEGER {
                  inactive (0),
                  learning (1),
                  detected (2),
                  active (3),
                  notifiedtcn (4),
                  notifiedtc (5),
                  propagating (6),
                  acknowledged (7)
               }
   MAX-ACCESS  read-only
   STATUS      current
   DESCRIPTION
      "This indicates the current state of the Topology Change state machine. 
      This object is used to hold the value 'inactive' when the Topology Change
      state machine is in the INACTIVE state, the value 'learning' when the state
      machine is in the LEARNING state, the value 'active' when the state
      machine is in the ACTIVE state, the value 'detected' when the state
      machine is in the DETECTED state, the value 'notifiedtcn' when the state
      machine is in the NOTIFIED_TCN state, the value 'notifiedtc' when the
      state machine is in the NOTIFIED_TC state, the value 'propagating' state
      when the state machine is in the PROPAGATING state and the value
      'acknowledged' when the state machine is in the ACKNOWLEDGED state." 
   ::= { fsPbRstCVlanPortSmEntry 5 }

fsPbRstCVlanPortTxSmState OBJECT-TYPE
   SYNTAX      INTEGER {
                  transmitinit (0),
                  transmitperiodic (1),
                  transmitconfig (2),
                  transmittcn (3),
                  transmitrstp (4),
                  idle (5)
               }
   MAX-ACCESS  read-only
   STATUS      current
   DESCRIPTION
      "This indicates the current state of the Port Transmit state machine.
      This object is used to hold the value 'transmitinit' when the Port Transmit
      state machine is in the TRANSMIT_INIT state, the value 'transmitperiodic'
      when the state machine is in the TRANSMIT_PERIODIC state, the value
      'transmitconfig' when the state machine is in the TRANSMIT_CONFIG state,
      the value 'transmittcn', when the state machine is in the TRANSMIT_TCN
      state, the value 'transmitrstp', when the state machine is in the
      TRANSMIT_RSTP state and the value 'idle' when the state machine is in the
      IDLE state."
   ::= { fsPbRstCVlanPortSmEntry 6 }

fsPbRstCVlanPortStatsTable OBJECT-TYPE
   SYNTAX SEQUENCE OF FsPbRstCVlanPortStatsEntry
   MAX-ACCESS not-accessible
   STATUS     current
   DESCRIPTION
      "This table contains the spanning tree statistics information for the 
      C-VLAN component ports."
   ::= { futurePbRst 5 }

fsPbRstCVlanPortStatsEntry OBJECT-TYPE
   SYNTAX      FsPbRstCVlanPortStatsEntry
   MAX-ACCESS  not-accessible
   STATUS      current
   DESCRIPTION
      "Each entry in this table is for each C-VLAN component in Provider
       Bridges. Here the port represents the C-VLAN component ports. 
       Each table entry gives the spanning tree protocol statistics 
       information for the C-VLAN component ports."
   INDEX { fsPbRstPort,fsPbRstCepSvid }
   ::= { fsPbRstCVlanPortStatsTable 1 }

FsPbRstCVlanPortStatsEntry ::=
   SEQUENCE {
      fsPbRstCVlanPortRxRstBpduCount
         Counter32,
      fsPbRstCVlanPortRxConfigBpduCount
         Counter32,
      fsPbRstCVlanPortRxTcnBpduCount
         Counter32,
      fsPbRstCVlanPortTxRstBpduCount
         Counter32,
      fsPbRstCVlanPortTxConfigBpduCount
         Counter32,
      fsPbRstCVlanPortTxTcnBpduCount
         Counter32,
      fsPbRstCVlanPortInvalidRstBpduRxCount
         Counter32,
      fsPbRstCVlanPortInvalidConfigBpduRxCount
         Counter32,
      fsPbRstCVlanPortInvalidTcnBpduRxCount
         Counter32,
      fsPbRstCVlanPortProtocolMigrationCount
         Counter32,
      fsPbRstCVlanPortEffectivePortState
         TruthValue
      }


fsPbRstCVlanPortRxRstBpduCount OBJECT-TYPE
   SYNTAX      Counter32
   MAX-ACCESS  read-only
   STATUS      current
   DESCRIPTION
      "The number of RST BPDUs that have been received on this Port."
   ::= { fsPbRstCVlanPortStatsEntry 1 }

fsPbRstCVlanPortRxConfigBpduCount OBJECT-TYPE
   SYNTAX      Counter32
   MAX-ACCESS  read-only
   STATUS      current
   DESCRIPTION
      "The number of Config BPDUs that have been received on this Port."
   ::= { fsPbRstCVlanPortStatsEntry 2 }

fsPbRstCVlanPortRxTcnBpduCount OBJECT-TYPE
   SYNTAX      Counter32
   MAX-ACCESS  read-only
   STATUS      current
   DESCRIPTION
      "The number of TCN BPDUs that have been received on this Port."
   ::= { fsPbRstCVlanPortStatsEntry 3 }

fsPbRstCVlanPortTxRstBpduCount OBJECT-TYPE
   SYNTAX      Counter32
   MAX-ACCESS  read-only
   STATUS      current
   DESCRIPTION
      "The number of RST BPDUs that have been transmitted by this Port."
   ::= { fsPbRstCVlanPortStatsEntry 4 }

fsPbRstCVlanPortTxConfigBpduCount OBJECT-TYPE
   SYNTAX      Counter32
   MAX-ACCESS  read-only
   STATUS      current
   DESCRIPTION
      "The number of Config BPDUs that have been transmitted by this Port."
   ::= { fsPbRstCVlanPortStatsEntry 5 }

fsPbRstCVlanPortTxTcnBpduCount OBJECT-TYPE
   SYNTAX      Counter32
   MAX-ACCESS  read-only
   STATUS      current
   DESCRIPTION
      "The number of TCN BPDUs that have been transmitted by this Port."
   ::= { fsPbRstCVlanPortStatsEntry 6 }

fsPbRstCVlanPortInvalidRstBpduRxCount OBJECT-TYPE
   SYNTAX      Counter32
   MAX-ACCESS  read-only
   STATUS      current
   DESCRIPTION
      "The number of invalid RSTP BPDUs that have been received on this Port." 
   ::= { fsPbRstCVlanPortStatsEntry 7 }

fsPbRstCVlanPortInvalidConfigBpduRxCount OBJECT-TYPE
   SYNTAX      Counter32
   MAX-ACCESS  read-only
   STATUS      current
   DESCRIPTION
      "The number of invalid Configuration BPDUs that have been received on this Port."
   ::= { fsPbRstCVlanPortStatsEntry 8 }

fsPbRstCVlanPortInvalidTcnBpduRxCount OBJECT-TYPE
   SYNTAX      Counter32
   MAX-ACCESS  read-only
   STATUS      current
   DESCRIPTION
      "The number of invalid TCN BPDUs that have been received on this 
       Port."
   ::= { fsPbRstCVlanPortStatsEntry 9 }

fsPbRstCVlanPortProtocolMigrationCount OBJECT-TYPE
   SYNTAX      Counter32
   MAX-ACCESS  read-only
   STATUS      current
   DESCRIPTION
      "The number of times the protocol has been migrated from RSTP to STP
      and vice versa in CVLAN component."
   ::= { fsPbRstCVlanPortStatsEntry 10 }


fsPbRstCVlanPortEffectivePortState OBJECT-TYPE
      SYNTAX      TruthValue
      MAX-ACCESS  read-only            
      STATUS      current
      DESCRIPTION
          "The effective Operational state of this port. This object 
           will be set to TRUE only when the port is operationally up in the 
           interface manager and the force Port State for this port and 
           specified port state is enabled. 
           Otherwise, this object is set to FALSE."

   ::= { fsPbRstCVlanPortStatsEntry 11 }

END

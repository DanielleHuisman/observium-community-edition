-- Copyright (C) 2006-2012 Aricent Group . All Rights Reserved

-- $Id: fspoe.mib,v 1.4 2012/09/07 09:52:05 siva Exp $

--    Poe Proprietary MIB Definition
      
--    This document explains the proprietary MIB implemented
--    for POE product.
      
--    This proprietary MIB definition, supplements the standard IEEE802.3af 
--    MIB and also provides management of certain proprietary features of
--    POE. 
      
--    The proprietary MIB definitions follows:


      ARICENT-POE-MIB DEFINITIONS ::= BEGIN
    
      IMPORTS
         MODULE-IDENTITY, OBJECT-TYPE, enterprises 
         FROM SNMPv2-SMI 
         RowStatus,MacAddress  
         FROM SNMPv2-TC
         InterfaceIndex
         FROM IF-MIB;    
                                                 

      fspoe MODULE-IDENTITY
            LAST-UPDATED "201209050000Z"
            ORGANIZATION "ARICENT COMMUNICATIONS SOFTWARE"
            CONTACT-INFO "support@aricent.com"
            DESCRIPTION
               " The proprietary MIB module for POE. "
	    REVISION "201209050000Z"
            DESCRIPTION
               " The proprietary MIB module for POE. "
      ::=  { enterprises futuresoftware (2076) 103 } 
   
-- ------------------------------------------------------------
-- groups in the MIB 
-- ------------------------------------------------------------

      fsPoeSystem                OBJECT IDENTIFIER ::= { fspoe 1 }

-- ------------------------------------------------------------------
-- The Poe System Group
-- ------------------------------------------------------------------
      fsPoeGlobalAdminStatus OBJECT-TYPE
           SYNTAX      INTEGER { start(1), shutdown(2)}
           MAX-ACCESS  read-write
           STATUS      current
           DESCRIPTION
               "Start or shutdown PoE Module in the system

                When set as 'start' PoE module initializes data structures and
                gets the power supply status.

                When shutdown, all resources used by PoE module
                will be released back to the system and also power will
                be shut on all PoE enabled ports"
           ::= { fsPoeSystem 1 }

-- Poe Mac Table 

      fsPoeMacTable OBJECT-TYPE
          SYNTAX      SEQUENCE OF FsPoeMacEntry
          MAX-ACCESS  not-accessible
          STATUS      current
          DESCRIPTION
             "This table contains information associated MAC Addresses for which 
              Power has to be applied."
          ::= { fsPoeSystem 2 }


      fsPoeMacEntry OBJECT-TYPE
          SYNTAX     FsPoeMacEntry 
          MAX-ACCESS  not-accessible
          STATUS      current
          DESCRIPTION
             "Powered Device(PD)s MAC address, the port through which its 
              been learnt"
          INDEX { fsPoePdMacAddress }
          ::= { fsPoeMacTable 1 }

      FsPoeMacEntry ::=
          SEQUENCE {
            fsPoePdMacAddress 
                 MacAddress,
            fsPoePdMacPort
                 InterfaceIndex,
           fsPoePdMacRowStatus 
                 RowStatus
          }

     fsPoePdMacAddress OBJECT-TYPE
           SYNTAX      MacAddress
           MAX-ACCESS  not-accessible
           STATUS      current
           DESCRIPTION
               "MAC address of the PD."
           ::= { fsPoeMacEntry 1 }
 
     fsPoePdMacPort OBJECT-TYPE
           SYNTAX InterfaceIndex 
           MAX-ACCESS read-only
           STATUS current
           DESCRIPTION
              "This object stores the port through which the fsPoePdMacAddress
               has been learnt "
           ::= { fsPoeMacEntry 2 }

     fsPoePdMacRowStatus OBJECT-TYPE
          SYNTAX      RowStatus
          MAX-ACCESS  read-create
          STATUS      current
          DESCRIPTION
              "This object indicates the status of this entry."
           ::= { fsPoeMacEntry 3 }
END

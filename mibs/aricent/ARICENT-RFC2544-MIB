-- Copyright (C) 2015 Aricent Group . All Rights Reserved

-- $Id: fs2544.mib,v 1.5 2016/05/20 10:18:07 siva Exp $

-- ARICENT RFC2544 proprietary MIB Definition

ARICENT-RFC2544-MIB DEFINITIONS ::= BEGIN

IMPORTS 
OBJECT-TYPE, 
    enterprises, Unsigned32,  Integer32,
    NOTIFICATION-TYPE  FROM SNMPv2-SMI

    RowStatus, TimeStamp,  TruthValue,
    DisplayString FROM SNMPv2-TC

    MODULE-IDENTITY    FROM SNMPv2-SMI

    IEEE8021PriorityCodePoint FROM IEEE8021-TC-MIB;

    fs2544 MODULE-IDENTITY
    LAST-UPDATED "201506260000Z" 
    ORGANIZATION "ARICENT COMMUNICATIONS SOFTWARE" 
    CONTACT-INFO 

    "The Aricent Group, One Tower Center Boulevard, 
    18th Floor, East Brunswick, NJ 08816, USA
    E-mail:support@aricent.com"

    DESCRIPTION 
      "The enterprise ID 29601 is originally assigned to Aricent Communications Pvt. Limited.
       Aricent Communications is a part of Aricent Group."

    REVISION "201506260000Z"

    DESCRIPTION 
      "The proprietary MIB for Aricent RFC2544 Benchmark Methodology Test for 
      Network Interconnect Devices." 

    ::= { enterprises aricent-communication-holding-ltd(29601) iss(2) 105 }


    -- ------------------------------------------------------------
    -- Groups in RFC2544  MIB
    -- ------------------------------------------------------------
    fs2544Context          OBJECT IDENTIFIER ::= { fs2544 1 }
    fs2544Sla              OBJECT IDENTIFIER ::= { fs2544 2 } 
    fs2544TrafficProfile   OBJECT IDENTIFIER ::= { fs2544 3 }
    fs2544Sac              OBJECT IDENTIFIER ::= { fs2544 4 }
    fs2544Statistics       OBJECT IDENTIFIER ::= { fs2544 5 }
    fs2544Notification     OBJECT IDENTIFIER ::= { fs2544 6 }     
    
    -- ------------------------------------------------------------
    -- RFC2544 Context table
    -- ------------------------------------------------------------

   
   fs2544ContextTable OBJECT-TYPE
       SYNTAX      SEQUENCE OF Fs2544ContextEntry
       MAX-ACCESS  not-accessible
       STATUS      current
       DESCRIPTION
          "This table contains all the global configurations of RFC2544
           per virtual context of the router."
       ::= { fs2544Context 1 }

   fs2544ContextEntry OBJECT-TYPE
       SYNTAX      Fs2544ContextEntry
       MAX-ACCESS  not-accessible
       STATUS      current
       DESCRIPTION
          "This object specifies an entry of virtual context RFC2544 Global 
           parameters."
       INDEX { fs2544ContextId }
       ::= { fs2544ContextTable 1 }

   Fs2544ContextEntry ::= SEQUENCE {
            fs2544ContextId                      Unsigned32,
            fs2544ContextName                    DisplayString,
            fs2544ContextSystemControl           INTEGER,
            fs2544ContextModuleStatus            INTEGER,
            fs2544ContextTraceOption             Unsigned32,
            fs2544ContextNumOfTestRunning        Unsigned32,
            fs2544ContextTrapStatus              INTEGER    
           } 

    fs2544ContextId OBJECT-TYPE
        SYNTAX        Unsigned32
        MAX-ACCESS    not-accessible
        STATUS        current
        DESCRIPTION
          "This object specifies an  unique identifier to identify the virtual 
           context."
        ::= { fs2544ContextEntry 1 }

   fs2544ContextName OBJECT-TYPE
       SYNTAX      DisplayString
       MAX-ACCESS  read-only
       STATUS      current
       DESCRIPTION
         "This object specifies context-name for the virtual context."
       ::= { fs2544ContextEntry 2 }

    fs2544ContextSystemControl OBJECT-TYPE
        SYNTAX      INTEGER  { 
                                 start(1), 
                                 shutdown(2) 
                             }
        MAX-ACCESS  read-write
        STATUS      current
        DESCRIPTION
          "This object specifies the administrative system control status of RFC2544
           module. 

           The value 'start' (1) indicates that all
           resources required by RFC2544 module should be allocated
           and RFC2544 should be supported in the virtual context.

           The value 'shutdown' (2) indicates that RFC2544 should be
           shutdown in the virtual context and all allocated memory must
           be  released.
           
           By default this object is set to shutdown(2) for all virtual 
           context"
        DEFVAL  { shutdown }
        ::= { fs2544ContextEntry 3 }

   fs2544ContextModuleStatus OBJECT-TYPE
        SYNTAX      INTEGER  { 
                                 enabled(1), 
                                 disabled(2) 
                             }
        MAX-ACCESS  read-write
        STATUS      current
        DESCRIPTION
          "This object sepcifies the administrative module status of RFC2544 module.
           This enables or disables RFC2544 in the system. 

           A value of 'enabled' (1) indicates that RFC2544 is 
           enabled in the virtaul context.

           A value of 'disabled' (2) indicates that RFC2544 is disabled
           in the virtual context.
           
           In disabled state, all the running tests will be stopped.
           
           By default this object is set to disbale(2) for all virtual 
           context."
        DEFVAL  { disabled }
        ::= { fs2544ContextEntry 4 }
      
    fs2544ContextTraceOption OBJECT-TYPE
        SYNTAX      Unsigned32 (0..4294967295)
        MAX-ACCESS  read-write
        STATUS      current
        DESCRIPTION
          "This object is used to enable the trace statements in
           RFC2544 Module.

           A FOUR BYTE integer is specified for enabling the level of tracing.
           Each BIT in the four byte integer, represents a 
           level of Trace.

           The mapping between the bit positions & the level of trace is
           as follows:
           0 - Start and Shutdown Traces
           1 - Configuration related traces
           2 - Y1731 interface related messages
           3 - Traces related to All Resources except Buffers
           4 - Timer start, stop and expiry traces  
           5 - Critical Traces
           6 - BenchMark test traces
           7 - Session record traces
           8 - All Failure traces 

           The remaining bits are unused. Combination of levels are
           also allowed.

           For example if the bits 0 and 1 are set, then the Trace
           statements related to Start-Shutdown and Configuration traces
           are generated.

           The user has to enter the corresponding INTEGER VALUE for the
           bits set. For example if bits 0 and 1 are set, the user has to
           enter the value 3.
           
           By default critical trace is enabled."
        DEFVAL  { '00000020'H } 
        ::= { fs2544ContextEntry 5 }

   fs2544ContextNumOfTestRunning OBJECT-TYPE
        SYNTAX      Unsigned32 
        MAX-ACCESS  read-only
        STATUS      current
        DESCRIPTION
          "This object specifies the number of test currently running 
           in a virtual context."
        ::= { fs2544ContextEntry 6 }
 
    fs2544ContextTrapStatus OBJECT-TYPE
        SYNTAX      INTEGER {
                                enable (1),
                                disable (2)
                            }    
        MAX-ACCESS  read-write
        STATUS      current
        DESCRIPTION
          "This object is used to enable or disable the transmission
           of TRAP notification messages.
            
           By default this object is set to enable for all 
           virtual context."
        ::= { fs2544ContextEntry 7 }


    -- ------------------------------------------------------------------
    -- RFC2544 Service Level Agreement Table
    -- ------------------------------------------------------------------

    fs2544SlaTable OBJECT-TYPE
        SYNTAX      SEQUENCE OF Fs2544SlaEntry
        MAX-ACCESS  not-accessible
        STATUS      current
        DESCRIPTION
           "This table contains Service Level Agreement configurations."
        ::= { fs2544Sla 1 }

    fs2544SlaEntry OBJECT-TYPE
        SYNTAX      Fs2544SlaEntry
        MAX-ACCESS  not-accessible
        STATUS      current
        DESCRIPTION
           "This entry contains information about a particular SLA
            Configuration."
        INDEX   { 
                  fs2544ContextId,
                  fs2544SlaId 
                }
        ::= { fs2544SlaTable 1 }

    Fs2544SlaEntry ::=
    SEQUENCE {
        fs2544SlaId                Unsigned32,
        fs2544SlaMEG               Unsigned32,
        fs2544SlaME                Unsigned32,
        fs2544SlaMEP               Unsigned32,
        fs2544SlaTrafficProfileId  Unsigned32,
        fs2544SlaSacId             Unsigned32,        
        fs2544SlaTestStatus        INTEGER,  
        fs2544SlaCurrentTestState  INTEGER, 
        fs2544SlaTestStartTime     TimeStamp,
        fs2544SlaTestEndTime       TimeStamp,   
        fs2544SlaRowStatus         RowStatus
           }

    fs2544SlaId OBJECT-TYPE
        SYNTAX      Unsigned32 ( 1..10 )
        MAX-ACCESS  not-accessible
        STATUS      current
        DESCRIPTION
           "This object specifies the RFC2544 Service Level Agreement Identifier. 
            This is a free running index used to identify a SLA. "
        ::= { fs2544SlaEntry 1 }

    fs2544SlaMEG OBJECT-TYPE
        SYNTAX      Unsigned32 (0..4294967295)
        MAX-ACCESS  read-write
        STATUS      current
        DESCRIPTION
          "This object specifies the Maintenance Entity Group (MEG).
           Internally this object refers to MIB object dot1agCfmMdIndex
           of ECFM 802.1ag standard.The value zero(0) is used for unmapping
           MEG from Sla."
        ::= { fs2544SlaEntry 2 }

    fs2544SlaME OBJECT-TYPE
        SYNTAX      Unsigned32(0..4294967295)
        MAX-ACCESS  read-write
        STATUS      current
        DESCRIPTION
           "This object specifies the Maintenance Entity (ME) 
           Internally this object refers to MIB object dot1agCfmMaIndex
           of ECFM 802.1ag standard. The value zero(0) is used for unmapping
           ME from Sla."
    ::= { fs2544SlaEntry 3 }

    fs2544SlaMEP OBJECT-TYPE
        SYNTAX      Unsigned32 (0..8191)
        MAX-ACCESS  read-write
        STATUS      current
        DESCRIPTION
          "This object specifies the Maintenance Association End Point (MEP).
           Internally this object refers to MIB object 
           dot1agCfmMepIdentifier of ECFM 802.1ag standard.The value zero(0) 
           is used for unmapping  MEP from Sla."
        ::= { fs2544SlaEntry 4 }

    fs2544SlaTrafficProfileId OBJECT-TYPE
        SYNTAX      Unsigned32 ( 0..10 )
        MAX-ACCESS  read-write
        STATUS      current
        DESCRIPTION
          "This object specifies the RFC2544 Traffic Profile Identifier that is to be 
          associated with SLA.The value zero(0) is used for unmapping traffic 
          profile from Sla." 
        ::= { fs2544SlaEntry 5 }

    fs2544SlaSacId OBJECT-TYPE
        SYNTAX      Unsigned32 ( 0..10 )
        MAX-ACCESS  read-write
        STATUS      current
        DESCRIPTION
           "This object specifies the RFC2544 SAC Identifier that is to be 
           associated with the SLA.The value zero(0) is used for unmapping  
           Sac from Sla."
        ::= { fs2544SlaEntry 6 }

    fs2544SlaTestStatus OBJECT-TYPE
        SYNTAX      INTEGER { 
                              start(1), 
                              stop(2)
                            }
        MAX-ACCESS  read-write
        STATUS      current
        DESCRIPTION
           "This object specifies the RFC2544 SLA test status. It is used to 
            start or stop the test."
        DEFVAL  { 2 }
        ::= { fs2544SlaEntry 7 }     

    fs2544SlaCurrentTestState OBJECT-TYPE
        SYNTAX      INTEGER { 
                             notInitiated (1),    -- test not initiated.
                             inProgress (2),      -- test in progress.
                             completed (3),       -- test successfully completed.
                             aborted (4)         -- test aborted.
                          }
         MAX-ACCESS  read-only
         STATUS      current
         DESCRIPTION 
            "This object specifies the current test state of the SLA."
         DEFVAL  { 1 }
         ::= { fs2544SlaEntry 8 }

    fs2544SlaTestStartTime OBJECT-TYPE
        SYNTAX      TimeStamp
        MAX-ACCESS  read-only
        STATUS      current
        DESCRIPTION
           "This object specifies the start time of the benchmark test in 
            RFC2544 ."
        ::= { fs2544SlaEntry 9 }

    fs2544SlaTestEndTime OBJECT-TYPE
        SYNTAX      TimeStamp
        MAX-ACCESS  read-only
        STATUS      current
        DESCRIPTION
           "This object specifies the end time of the benchmark test in 
            RFC2544 ."
        ::= { fs2544SlaEntry 10 }

    fs2544SlaRowStatus OBJECT-TYPE
        SYNTAX      RowStatus
        MAX-ACCESS  read-write
        STATUS      current
        DESCRIPTION
          "This object is used to create, modify, and/or
           delete a row in this table. When a row in this
           table has a row in the active(1) state, no
           objects in this row can be modified except the
           fs2544SlaRowStatus"
        ::= { fs2544SlaEntry 11 }

    -- ------------------------------------------------------------------
    -- RFC2544 Traffic Profile Table
    -- ------------------------------------------------------------------

    fs2544TrafficProfileTable OBJECT-TYPE
        SYNTAX      SEQUENCE OF Fs2544TrafficProfileEntry
        MAX-ACCESS  not-accessible
        STATUS      current
        DESCRIPTION
          "This table contains RFC2544 Test profile Table configurations."
        ::= { fs2544TrafficProfile 1 }

    fs2544TrafficProfileEntry OBJECT-TYPE
        SYNTAX      Fs2544TrafficProfileEntry
        MAX-ACCESS  not-accessible
        STATUS      current
        DESCRIPTION
          "This entry contains information about a particular test profile 
           Configuration."
        INDEX   { 
                   fs2544ContextId,
                   fs2544TrafficProfileId 
                }
        ::= { fs2544TrafficProfileTable 1 }

    Fs2544TrafficProfileEntry ::=
    SEQUENCE {
        fs2544TrafficProfileId                        Unsigned32,
        fs2544TrafficProfileName                      DisplayString,
        fs2544TrafficProfileSeqNoCheck                INTEGER,
        fs2544TrafficProfileDwellTime                 Integer32,
        fs2544TrafficProfileFrameSize                 DisplayString,
        fs2544TrafficProfilePCP                       IEEE8021PriorityCodePoint,
        fs2544TrafficProfileThTestStatus              TruthValue,
        fs2544TrafficProfileFlTestStatus              TruthValue,
        fs2544TrafficProfileLaTestStatus              TruthValue,
        fs2544TrafficProfileBbTestStatus              TruthValue,
        fs2544TrafficProfileThTrialDuration           Unsigned32,
        fs2544TrafficProfileThMaxRate                 Unsigned32,
        fs2544TrafficProfileThMinRate                 Unsigned32,
        fs2544TrafficProfileLaTrialDuration           Unsigned32,
        fs2544TrafficProfileLaDelayMeasureInterval    Unsigned32,
        fs2544TrafficProfileFlTrialDuration           Unsigned32,
        fs2544TrafficProfileFlMaxRate                 Unsigned32,
        fs2544TrafficProfileFlMinRate                 Unsigned32,
        fs2544TrafficProfileFlRateStep                Unsigned32, 
        fs2544TrafficProfileBbTrialDuration           Unsigned32,
        fs2544TrafficProfileBbTrialCount              Unsigned32,
        fs2544TrafficProfileThRateStep                Unsigned32,
        fs2544TrafficProfileRowStatus                 RowStatus
    }


    fs2544TrafficProfileId OBJECT-TYPE
        SYNTAX      Unsigned32 ( 1..255 )
        MAX-ACCESS  not-accessible
        STATUS      current
        DESCRIPTION
          "This object specifies the RFC2544 Traffic Profile Identifier. 
          This is a free running index used to identify a Benchmark Test.
          Traffic Profile cannot be deleted when it is associated with a 
          SLA."
        ::= { fs2544TrafficProfileEntry 1 }

    fs2544TrafficProfileName OBJECT-TYPE
        SYNTAX      DisplayString (SIZE (1..32)) 
        MAX-ACCESS  read-write
        STATUS      current
        DESCRIPTION
          "This object specifies the name of the RFC2544  profile. 
           By default, the test profile name will be constructed by 
           appending test profile ID to the string profile.
           
           Example: Default test profile name for a test with profile ID 1 is
           'Profile1`."
         ::= { fs2544TrafficProfileEntry 2 }

    fs2544TrafficProfileSeqNoCheck OBJECT-TYPE
        SYNTAX      INTEGER { 
                                enable(1), 
                                disable(2) 
                            }
        MAX-ACCESS  read-write
        STATUS      current
        DESCRIPTION
          "This object is used to enable or disable the validation of 
           sequence number in received frames.
           
           Enable  - Sequence number is validated for the received frames and 
                     this provides the report of the number of frames are 
                     dropped along with number of frames that arrived at 
                     out of order, the number of duplicate frames received 
                      number of gaps in the received frame 
                     numbering sequence.

           Disable - Sequence number is not validated for the received frames and 
                     this provides the report of the number of frames that are dropped."
        DEFVAL  { disable }
        ::= { fs2544TrafficProfileEntry 3 }

    fs2544TrafficProfileDwellTime OBJECT-TYPE
        SYNTAX      Integer32 ( 5..60 ) 
        MAX-ACCESS  read-write
        STATUS      current
        DESCRIPTION
          "This object specifies the number of seconds to wait after each trail 
          for the system to settle before reading the statistics from hardware."
        DEFVAL  { 5 }
        ::= { fs2544TrafficProfileEntry 4 }

    fs2544TrafficProfileFrameSize OBJECT-TYPE
        SYNTAX      DisplayString
        MAX-ACCESS  read-write
        STATUS      current
        DESCRIPTION
          "This object specifies the frame size used for each benchmark test.
           The configurable frame sizes are 64,128,256,512,1024,1280 and 1518.
           By default the test is done for all frame sizes 
           (64,128,256,512,1024,1280,1518) "
        ::= { fs2544TrafficProfileEntry 5 }

    fs2544TrafficProfilePCP OBJECT-TYPE
        SYNTAX      IEEE8021PriorityCodePoint
        MAX-ACCESS  read-write
        STATUS      current
        DESCRIPTION
          "This object specifies the PCP (Priority Code Point)
           that is to be inserted in the generated test frames.
           PCP value is inserted only if the Mep Type is Vlan based Mep."
        DEFVAL  { 1 }
        ::= { fs2544TrafficProfileEntry 6 }

    fs2544TrafficProfileThTestStatus OBJECT-TYPE
        SYNTAX      TruthValue
        MAX-ACCESS  read-write
        STATUS      current
        DESCRIPTION
          "This object enables or disables throughput test .
           Throughput test - Measures the maximum rate at 
           which none of the offered frames are dropped 
           on the device.
           
           If TRUE, then the throughput test will be enabled.
           If FALSE, then the throughput test will be disabled."
        DEFVAL  { true }
        ::= { fs2544TrafficProfileEntry 7 }

    fs2544TrafficProfileFlTestStatus OBJECT-TYPE
            SYNTAX      TruthValue
        MAX-ACCESS  read-write
        STATUS      current
        DESCRIPTION
          "This object enables or disables the Frame Loss Rate test .
           Frame Loss rate - Measures the performance 
           of a network device in overloaded state.

           If TRUE, then the Frame Loss Rate test will be enabled.
           If FALSE, then the Frame Loss rate test will be disabled."
        DEFVAL  { false }
        ::= { fs2544TrafficProfileEntry 8 }

    fs2544TrafficProfileLaTestStatus OBJECT-TYPE
        SYNTAX      TruthValue
        MAX-ACCESS  read-write
        STATUS      current
        DESCRIPTION
          "This object enables or Disables the Latency test
           Latency test - Measures the time taken by a test 
           frame to travel through a network device

           If TRUE, then the Latency test will be enabled.
           If FALSE, then the Latency test will be disabled."
        DEFVAL  { true }
        ::= { fs2544TrafficProfileEntry 9 }

    fs2544TrafficProfileBbTestStatus OBJECT-TYPE
        SYNTAX      TruthValue
        MAX-ACCESS  read-write
        STATUS      current
        DESCRIPTION
          "This object enables or Disbales the Back-To-Back 
           Frame test.
           Back-To-Back Frame Test - Measures the buffering 
           capacity of a device.

           If TRUE, then the Back-To-Back Frame test will be enabled.
           If FALSE, then the Back-To-Back Frame test will be disabled."
        DEFVAL  { false }
        ::= { fs2544TrafficProfileEntry 10 }

    fs2544TrafficProfileThTrialDuration OBJECT-TYPE
        SYNTAX      Unsigned32 ( 10..1800 )
        UNITS        "seconds"
        MAX-ACCESS  read-write
        STATUS      current
        DESCRIPTION
          "This object specifies the duration of each trails in seconds for 
           Throughput test."
        DEFVAL  { 60 }
        ::= { fs2544TrafficProfileEntry 11 }

    fs2544TrafficProfileThMaxRate OBJECT-TYPE
        SYNTAX      Unsigned32
        UNITS       "percentage"
        MAX-ACCESS  read-write
        STATUS      current
        DESCRIPTION
          "This object specifies the maximum rate for the Throughput 
           test.It is specified in % of the link's bandwidth.
           The default value is 100% of the link speed"
        DEFVAL  { 100 }   
        ::= { fs2544TrafficProfileEntry 12 }

    fs2544TrafficProfileThMinRate OBJECT-TYPE
        SYNTAX      Unsigned32
        UNITS       "percentage"
        MAX-ACCESS  read-write
        STATUS      current
        DESCRIPTION
          "This object specifies the minimum rate for the Throughput 
           test. It is specified in % of the link's bandwidth.
           The default value is 80% of the link speed"
        DEFVAL  { 80 }   
        ::= { fs2544TrafficProfileEntry 13 }

     fs2544TrafficProfileLaTrialDuration OBJECT-TYPE
        SYNTAX      Unsigned32 ( 10..1800 )
        UNITS        "seconds"
        MAX-ACCESS  read-write
        STATUS      current
        DESCRIPTION
          "This object specifies the trial duration for 
           Latency(Delay Measurement)Test in seconds."
        DEFVAL  { 120 }
        ::= { fs2544TrafficProfileEntry 14 }

    fs2544TrafficProfileLaDelayMeasureInterval OBJECT-TYPE
        SYNTAX      Unsigned32 (1..60)
        UNITS        "seconds"
        MAX-ACCESS  read-write
        STATUS      current
        DESCRIPTION
          "This object specifies the number of seconds between each 
           delay measurement."
        DEFVAL  { 10 }
        ::= {fs2544TrafficProfileEntry 15 }


    fs2544TrafficProfileFlTrialDuration OBJECT-TYPE
        SYNTAX      Unsigned32 ( 10..1800 )
        UNITS        "seconds"
        MAX-ACCESS  read-write
        STATUS      current
        DESCRIPTION
          "This object specifies the duration of the trail for 
           Frame Loss Test in seconds."
        DEFVAL  { 60 }
        ::= { fs2544TrafficProfileEntry 16 }

    fs2544TrafficProfileFlMaxRate OBJECT-TYPE
        SYNTAX      Unsigned32
        UNITS       "percentage"
        MAX-ACCESS  read-write
        STATUS      current
        DESCRIPTION
          "This object specifies the maximum rate for the Frame Loss 
           test. It is specified in % of the link's bandwidth.
           The default value is 100% of the link speed"
        DEFVAL  { 100 }   
        ::= { fs2544TrafficProfileEntry 17 }

    fs2544TrafficProfileFlMinRate OBJECT-TYPE
        SYNTAX      Unsigned32
        UNITS       "percentage"
        MAX-ACCESS  read-write
        STATUS      current
        DESCRIPTION
          "This object specifies the minimum rate for the Frame Loss
           test. It is specified in % of the link's bandwidth.
           The default value is 80% of the link speed"
        DEFVAL  { 80 }            
        ::= {fs2544TrafficProfileEntry 18 }

    fs2544TrafficProfileFlRateStep OBJECT-TYPE
        SYNTAX      Unsigned32
        UNITS       "percentage"
        MAX-ACCESS  read-write
        STATUS      current
        DESCRIPTION
          "This object specifies the granularity between the minimum and 
           maximum rates defined for Frame Loss Test. It is specified in % 
           of the link's bandwidth .
           The default value is 10% of the link speed"
         DEFVAL  { 10 }    
        ::= {fs2544TrafficProfileEntry 19 }

    fs2544TrafficProfileBbTrialDuration OBJECT-TYPE
        SYNTAX      Unsigned32 ( 100..10000 )
        UNITS       "milliseconds"
        MAX-ACCESS  read-write
        STATUS      current
        DESCRIPTION
          "This object specifies the trail duration for Back-To-Back test  
           in seconds."
        DEFVAL  { 2000 }
        ::= { fs2544TrafficProfileEntry 20 }

    fs2544TrafficProfileBbTrialCount OBJECT-TYPE
        SYNTAX      Unsigned32 ( 1..100 )
        MAX-ACCESS  read-write
        STATUS      current
        DESCRIPTION
          "This object specifies the number of times the Back-To-Back test 
           is to be executed."
        DEFVAL  { 50 }
        ::= { fs2544TrafficProfileEntry 21 }
   fs2544TrafficProfileThRateStep OBJECT-TYPE 
        SYNTAX      Unsigned32 
        UNITS       "percentage" 
        MAX-ACCESS  read-write 
        STATUS      current 
        DESCRIPTION 
          "This object specifies the granularity between the minimum and  
           maximum rates defined for Throughput Test. It is specified in %  
           of the link's bandwidth . 
           The default value is 10% of the link speed" 
        DEFVAL  { 10 }     
        ::= {fs2544TrafficProfileEntry 22 } 

    fs2544TrafficProfileRowStatus OBJECT-TYPE
        SYNTAX      RowStatus
        MAX-ACCESS  read-write
        STATUS      current
        DESCRIPTION
          "This object is used to create, modify, and/or
           delete a row in this table. When a row in this
           table has a row in the active(1) state, no
           objects in this row can be modified except the
           fs2544TrafficProfileRowStatus."
        ::= { fs2544TrafficProfileEntry 23 }


    -- ------------------------------------------------------------------
    --RFC2544 Service Acceptance Criteria Table
    -- ------------------------------------------------------------------
    fs2544SacTable OBJECT-TYPE
        SYNTAX      SEQUENCE OF Fs2544SacEntry
        MAX-ACCESS  not-accessible
        STATUS      current
        DESCRIPTION
          "This table contains RFC2544 Service Acceptance Criteria
           Table configurations."
        ::= { fs2544Sac 1 }

    fs2544SacEntry OBJECT-TYPE
        SYNTAX      Fs2544SacEntry
        MAX-ACCESS  not-accessible
        STATUS      current
        DESCRIPTION
          "This entry contains information about Service 
           Acceptance Criteria configuration."
        INDEX { 
                fs2544ContextId,
                fs2544SacId 
              }
        ::= { fs2544SacTable 1 }

    Fs2544SacEntry ::=
    SEQUENCE {
           fs2544SacId                        Unsigned32,
           fs2544SacThAllowedFrameLoss        Unsigned32,
           fs2544SacLaAllowedFrameLoss        Unsigned32,
           fs2544SacFlAllowedFrameLoss        Unsigned32,
           fs2544SacRowStatus                 RowStatus
        }

    fs2544SacId OBJECT-TYPE
        SYNTAX      Unsigned32 ( 1..10 )
        MAX-ACCESS  not-accessible
        STATUS      current
        DESCRIPTION
           "This object specifies the RFC2544 SAC Identifier. This is 
            used to identify a particular SAC entry.
            Sac cannot be deleted when it is associated with a SLA."
        ::= { fs2544SacEntry 1 }


    fs2544SacThAllowedFrameLoss OBJECT-TYPE
        SYNTAX      Unsigned32 ( 0..100 )
        UNITS       "percentage" 
        MAX-ACCESS  read-write
        STATUS      current
        DESCRIPTION
          "This object specifies the allowable frame loss in percentage 
           for the Throughput test ." 
        DEFVAL  { 0 }
        ::= {fs2544SacEntry 2 }

     fs2544SacLaAllowedFrameLoss OBJECT-TYPE
        SYNTAX      Unsigned32 ( 0..10 )
        UNITS       "percentage" 
        MAX-ACCESS  read-write
        STATUS      current
        DESCRIPTION
          "This object specifies the allowable frame loss in percentage
           for latency test."
        DEFVAL  { 0 }
        ::= {fs2544SacEntry 3 }

    fs2544SacFlAllowedFrameLoss OBJECT-TYPE
        SYNTAX      Unsigned32 ( 0..100 )
        UNITS       "percentage" 
        MAX-ACCESS  read-write
        STATUS      current
        DESCRIPTION
          "This object specifies the allowable frame loss in percentage 
           for Frame Loss Rate test."
        DEFVAL  { 0 }
        ::= {fs2544SacEntry 4 }


    fs2544SacRowStatus OBJECT-TYPE
        SYNTAX      RowStatus
        MAX-ACCESS  read-write
        STATUS      current
        DESCRIPTION
          "This object is used to create, modify, and/or
           delete a row in this table. When a row in this
           table has a row in the active(1) state, no
           objects in this row can be modified except the
           fs2544SacRowStatus."
       ::= { fs2544SacEntry 5 }

    -- ------------------------------------------------------------------
    --RFC2544  Statistics table
    -- ------------------------------------------------------------------
   fs2544ReportStatsTable OBJECT-TYPE
       SYNTAX      SEQUENCE OF Fs2544ReportStatsEntry
       MAX-ACCESS  not-accessible
       STATUS      current
       DESCRIPTION
         "This table contains the statistics of the benchmark test performed."
       ::= { fs2544Statistics 1 }

    fs2544ReportStatsEntry OBJECT-TYPE
        SYNTAX      Fs2544ReportStatsEntry
        MAX-ACCESS  not-accessible
        STATUS      current
        DESCRIPTION
          "This entry specifies the statistics about a particular Test performed."
    INDEX   { 
              fs2544ContextId,
              fs2544SlaId, 
              fs2544ReportStatsFrameSize
            }
    ::= {  fs2544ReportStatsTable 1 }

    Fs2544ReportStatsEntry ::=
    SEQUENCE {
       fs2544ReportStatsFrameSize                 Unsigned32,        
       fs2544ReportStatsThVerifiedBps             Unsigned32,
       fs2544ReportStatsThResult                  INTEGER,
       fs2544ReportStatsLatencyMin                Unsigned32,
       fs2544ReportStatsLatencyMax                Unsigned32,
       fs2544ReportStatsLatencyMean               Unsigned32,
       fs2544ReportStatsLatencyFailCount          Integer32,
       fs2544ReportStatsLaIterationCalculated     Integer32,
       fs2544ReportStatsLatencyResult             INTEGER,
       fs2544ReportStatsFLossRate                 Integer32,
       fs2544ReportStatsFLResult                  INTEGER,
       fs2544ReportStatsBacktoBackBurstSize       Integer32

     }
 
    fs2544ReportStatsFrameSize OBJECT-TYPE
        SYNTAX      Unsigned32 (64..1518)
        MAX-ACCESS  not-accessible
        STATUS      current
        DESCRIPTION
          "This object specifies the frame size for which the test is 
           performed."
        ::= { fs2544ReportStatsEntry 1 }
    

    fs2544ReportStatsThVerifiedBps OBJECT-TYPE
        SYNTAX      Unsigned32 
        MAX-ACCESS  read-only
        STATUS      current
        DESCRIPTION
          "This object specifies the verified throughput value."
        ::= { fs2544ReportStatsEntry 2 }

    fs2544ReportStatsThResult OBJECT-TYPE
        SYNTAX      INTEGER { 
                              pass (1),
                              fail (2),
                              notInitiated (3),
                              aborted (4)
                            }
        MAX-ACCESS  read-only
        STATUS      current
        DESCRIPTION
          "This object specifies the throughput result."
        ::= { fs2544ReportStatsEntry 3 }

     fs2544ReportStatsLatencyMin OBJECT-TYPE
          SYNTAX   Unsigned32
          MAX-ACCESS  read-only
          STATUS      current
          DESCRIPTION
            "This object specifies the Minimum delay measured."
          ::= { fs2544ReportStatsEntry 4 }

     fs2544ReportStatsLatencyMax OBJECT-TYPE
          SYNTAX   Unsigned32
          MAX-ACCESS  read-only
          STATUS      current
          DESCRIPTION
            "This object specifies the Maximum delay measured."
          ::= { fs2544ReportStatsEntry 5 }

     fs2544ReportStatsLatencyMean OBJECT-TYPE
          SYNTAX   Unsigned32
          MAX-ACCESS  read-only
          STATUS      current
          DESCRIPTION
            "This object specifies the Average delay measured."
          ::= { fs2544ReportStatsEntry 6 }

     fs2544ReportStatsLatencyFailCount OBJECT-TYPE
          SYNTAX      Integer32   
          MAX-ACCESS  read-only
          STATUS      current
          DESCRIPTION
            "This object specifies the number of failures against 
            each frame."
          ::= { fs2544ReportStatsEntry 7 }

     fs2544ReportStatsLaIterationCalculated OBJECT-TYPE
          SYNTAX      Integer32
          MAX-ACCESS  read-only
          STATUS      current
          DESCRIPTION
            "This object specifies the number of iterations used 
            for calculation."
          ::= { fs2544ReportStatsEntry 8 }

    fs2544ReportStatsLatencyResult OBJECT-TYPE
        SYNTAX      INTEGER { 
                              pass (1),
                              fail (2),
                              notApplicable (3),
                              aborted (4)
                            }
        MAX-ACCESS  read-only
        STATUS      current
        DESCRIPTION
          "This object specifies the Latency result."
        ::= { fs2544ReportStatsEntry 9 }

    fs2544ReportStatsFLossRate OBJECT-TYPE
        SYNTAX      Integer32
        MAX-ACCESS  read-only
        STATUS      current
        DESCRIPTION
          "This object specifies the Frame Loss Rate observed during the test."
    ::= { fs2544ReportStatsEntry  10 }

    fs2544ReportStatsFLResult OBJECT-TYPE
        SYNTAX      INTEGER { 
                              pass (1),
                              fail (2),
                              notApplicable (3),
                              aborted (4)

                            }
        MAX-ACCESS  read-only
        STATUS      current
        DESCRIPTION
          "This object specifies the Frame Loss rate result."
        ::= { fs2544ReportStatsEntry 11 }

    fs2544ReportStatsBacktoBackBurstSize OBJECT-TYPE
        SYNTAX      Integer32 
        MAX-ACCESS  read-only
        STATUS      current
        DESCRIPTION
          "This object specifies the Back to Back frame test result."
        ::= { fs2544ReportStatsEntry 12 }


-- ------------------------------------------------------------------
-- RFC2544  Notification Group
-- ------------------------------------------------------------------


   fs2544Traps OBJECT IDENTIFIER ::= { fs2544Notification 0 }

   fs2544TrapObjects OBJECT IDENTIFIER ::= { fs2544Notification 1 }

   fs2544TrapSlaId OBJECT-TYPE
       SYNTAX TruthValue
       MAX-ACCESS accessible-for-notify
       STATUS current
       DESCRIPTION
         "This object refers to the SLA Id on which the RFC2544
          is enabled and will be used in sending the failure Traps."
       ::= { fs2544TrapObjects 2 }

   fs2544TypeOfFailure OBJECT-TYPE
       SYNTAX      DisplayString (SIZE (1..32))
       MAX-ACCESS  accessible-for-notify
       STATUS      current
       DESCRIPTION
         "This object provides the text indicating a particular failure
          condition.
          'Unrecoverable/Transaction failure' will be set, when the below defects are
          detected in CFM when Service configuration/Performance test is in progress.

          These defect Conditions are:

          RdiCondition       - The MEP has encountered remote MEP defect condition.
          LossOfContinuity   - The MEP has encountered loss of continuity defect condition. "

      ::= { fs2544TrapObjects 3 }

   fs2544FailureTrap NOTIFICATION-TYPE
   OBJECTS  {
        fs2544ContextName,
        fs2544TrapSlaId,
        fs2544TypeOfFailure
    }
    STATUS   current
    DESCRIPTION
        "This trap is generated when there is any failure in the Service under test."
    ::= { fs2544Traps 1 }
    END

-- Copyright (C) 2006-2012 Aricent Group . All Rights Reserved

-- $Id: fssshmib.mib,v 1.11 2014/03/09 13:38:39 siva Exp $

-- SSH proprietary MIB Definition
 
ARICENT-SSH-MIB DEFINITIONS ::= BEGIN

IMPORTS 
   MODULE-IDENTITY, OBJECT-TYPE, 
   enterprises, Integer32, Unsigned32   
   FROM SNMPv2-SMI 
   TruthValue 
   FROM SNMPv2-TC; 

   ssh MODULE-IDENTITY 
      LAST-UPDATED "201209050000Z" 
      ORGANIZATION "ARICENT COMMUNICATIONS SOFTWARE" 
      CONTACT-INFO "support@aricent.com" 
      DESCRIPTION
         "The proprietary MIB for SSH."
      REVISION "201209050000Z"
      DESCRIPTION 
         "The proprietary MIB for SSH." 
   ::= { enterprises futuresoftware (2076) 97 }


-- ----------------------------------------------------------------- --
-- groups in the MIB
-- ----------------------------------------------------------------- --
 
      sshGeneralGroup             OBJECT IDENTIFIER ::= { ssh 1 }
 
-- ---------------------------------------------------------------- --

-- General Group 

sshVersionCompatibility      OBJECT-TYPE
   SYNTAX      TruthValue 
   MAX-ACCESS  read-write 
   STATUS      current 
   DESCRIPTION 

   "This object is to configure the SSH version compatibility mode.
   When set to TRUE, both SSH version-1 and SSH Version-2 will be supported.
   When set to FALSE, SSH version-2 only will be supported.

   By default SSH version-2 is supported."

   DEFVAL  { false } 
   ::= { sshGeneralGroup 1 }

sshCipherList OBJECT-TYPE
      SYNTAX Integer32
      MAX-ACCESS read-write
      STATUS current
      DESCRIPTION
      
      "This object is to configure the cipher-suites list.

      This object takes values as bit mask.  Setting a bit indicates that the 
      corresponding cipher-list will be used for Encryption. 

      The value of each bit position is as given below with bit 0 being the 
      least significant bit:
           BIT 7 - AES-CTR-256
           BIT 6 - AES-CTR-192
           BIT 5 - AES-CTR-128
           BIT 4 - AES-CBC-256
           BIT 3 - AES-CBC-192
           BIT 2 - AES-CBC-128
           BIT 1 - DES-CBC
           BIT 0 - 3DES-CBC"
          
   DEFVAL  { 'B5'H }
   ::= { sshGeneralGroup 2}

sshMacList OBJECT-TYPE
      SYNTAX Integer32(1..3)
      MAX-ACCESS read-write
      STATUS current
      DESCRIPTION

      "This object is to configure the MAC-list.

      This object takes values as bit mask. Setting a bit indicates that the 
      corresponding MAC-list will be used for authentication. 

      The value of each bit position is as given below with bit 0  being the 
      least significant bit: 
            BIT 1 - HMAC-MD5
            BIT 0 - HMAC-SHA1"
            
   DEFVAL  { 1 }
   ::= { sshGeneralGroup 3}


sshTrace     OBJECT-TYPE
         SYNTAX        Integer32
         MAX-ACCESS    read-write
         STATUS        current
         DESCRIPTION
         "Set the trace level for SSH.
            BIT 0 - Initialisation and Shutdown Trace.
            BIT 1 - Management trace.
            BIT 2 - Data path trace.
            BIT 3 - Control Plane trace.
            BIT 4 - Packet Dump.
            BIT 5 - OS Resource trace.
            BIT 6 - All Failure trace (All failures including Packet Validation)
            BIT 7 - Buffer Trace.
            BIT 8 - SSH Server Trace.
            
            Note:BIT 0 - Least significant bit
                 BIT 7 - Most significant bit

            For example,setting the trace level to the value -0001 0101, 
            will enable Init-Shutdown, data path and packet dump trace levels.

            Setting all the bits will enable all the trace levels and 
            resetting them will disable all the trace levels."

         ::= { sshGeneralGroup 4 }

sshStatus  OBJECT-TYPE
   SYNTAX      TruthValue 
   MAX-ACCESS  read-write
   STATUS      current
   DESCRIPTION
      "This object is for enabling or disabling ssh in the system."

   DEFVAL  { true }
   ::= { sshGeneralGroup 5}
sshTransportMaxAllowedBytes        OBJECT-TYPE
        SYNTAX                 Integer32(1..32768)
        MAX-ACCESS        read-write
        STATUS                current
        DESCRIPTION
        "This object is used to configure the maximum number of bytes allowed in an SSH transport connection. The SSH connection will be allowed only if the packet size does not exceed the value configured in this object and dropped otherwise."
   DEFVAL    { 32768 }
   ::= { sshGeneralGroup 6 }

sshSrvBindAddr OBJECT-TYPE
    SYNTAX   OCTET STRING (SIZE (4|16))
    MAX-ACCESS  read-write
    STATUS  current
    DESCRIPTION "This object defines the Ip address on which Ssh Server listens"
    ::=  { sshGeneralGroup 7 }

sshServerBindPortNo OBJECT-TYPE
    SYNTAX   Unsigned32
    MAX-ACCESS  read-write
    STATUS  current
    DESCRIPTION "This object defines the primary port number on which Ssh Server listens"
    DEFVAL    { 22 }
    ::=  { sshGeneralGroup 8 }

END

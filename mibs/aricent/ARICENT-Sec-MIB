-- Copyright (C) 2011-2012 Aricent Group . All Rights Reserved

--*************************************************************************
--$Id: fssec.mib,v 1.3 2012/09/07 09:52:06 siva Exp $
--
--Description : This file contains MIB definitions for FIPS feature.
--
--*************************************************************************/

--    Sec Proprietary MIB Definition

--    This document explains the proprietary MIB implemented
--    for Sec product.
--    This proprietary MIB definition,provides management of certain proprietary
--    features of Sec.

--    The proprietary MIB definitions follows:

ARICENT-Sec-MIB DEFINITIONS ::= BEGIN

IMPORTS
MODULE-IDENTITY, OBJECT-TYPE ,enterprises, 
Integer32 FROM SNMPv2-SMI;

fsSec MODULE-IDENTITY
LAST-UPDATED "201209050000Z"
ORGANIZATION "ARICENT COMMUNICATIONS SOFTWARE"
CONTACT-INFO "support@aricent.com"
     DESCRIPTION
     "This MIB is defined for handling Version and level of debug traces
     in Security module"
     REVISION "201209050000Z"
     DESCRIPTION
     "This MIB is defined for handling Version and level of debug traces
     in Security module"

     ::= { enterprises aricent-communication-holding-ltd (29601) iss(2) 64 }

-- --------------------------------------------------------
-- Groups in the fsSec module
-- --------------------------------------------------------

    fsSecSystem             OBJECT IDENTIFIER ::= {fsSec 1}

------------------------------------------------------------

-- The fsSec System Group

-- ----------------------------------------------------------

      fsSecDebugOption OBJECT-TYPE
           SYNTAX     Integer32 
           MAX-ACCESS read-write
           STATUS     current
           DESCRIPTION
              "This Object defines the traces that are defined for Security module. 
              The mapping between the bit position & the level of trace is as follows

              The mapping between the bit positions & the level of trace is
              as follows:
              0x00000001 - Init and shutdown traces.
              0x00000002 - Management related debug traces.
              0x00000008 - Packet flow related debug traces.
              0x00000020 - Resource trace message for all resource unavailability.
              0x00000040 - Failure traces will be displayed.

              The remaining bits are unused. Combination of levels are
              also allowed.

              A four byte integer is used for enabling the level of tracing.
              Each BIT in the four byte integer ,represents a particular 
              level of trace"
        DEFVAL  { 0 }
        ::= {fsSecSystem 1}
END

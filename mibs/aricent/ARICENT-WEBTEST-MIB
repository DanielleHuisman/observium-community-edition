-- Copyright (C) 2011-2012 Aricent Group . All Rights Reserved

-- /********************************************************************
--  * $Id: fswebtst.mib,v 1.3 2014/11/05 13:11:31 siva Exp $
--  *
--  * Description: Test MIB for webnm module. 
--  *******************************************************************/

-- Introduction

-- This document explains the proprietary Test MIB implemented for the HTTP
-- product.

-- The proprietary MIB definitions, contains tabular MIB objects 
-- for HTTP authentication scheme.

-- Management Information Base for HTTP Product

ARICENT-WEBTEST-MIB DEFINITIONS ::= BEGIN

IMPORTS
    MODULE-IDENTITY, OBJECT-TYPE, Integer32,
    enterprises                      FROM SNMPv2-SMI
    RowStatus, DisplayString	     FROM SNMPv2-TC
    InetAddress, InetAddressType     FROM INET-ADDRESS-MIB;

fsWebTstMIB MODULE-IDENTITY
    LAST-UPDATED "201209050000Z"
    ORGANIZATION "ARICENT COMMUNICATIONS SOFTWARE" 
    CONTACT-INFO "support@aricent.com" 
    DESCRIPTION  "The MIB module for management of HTTP
                          Test MIB objects"
    REVISION "201209050000Z"   
    DESCRIPTION	 "The MIB module for management of HTTP 
                          Test MIB objects"
	 ::= { enterprises aricent-communication-holding-ltd(29601) iss(2) 68}

futureHttpTstTable  OBJECT IDENTIFIER ::= { fsWebTstMIB 1 }

-- TABLE_BEGIN

--
-- Start of test mib objects for HTTP Authentication
--


fsHttpAuthTestTable OBJECT-TYPE
    SYNTAX     SEQUENCE OF FsHttpAuthTestEntry
    MAX-ACCESS not-accessible
    STATUS     current
    DESCRIPTION
              "This table lists the statistics related to HTTP Authentication functionality"
    ::= { futureHttpTstTable 1 } 

fsHttpAuthTestEntry OBJECT-TYPE
    SYNTAX     FsHttpAuthTestEntry
    MAX-ACCESS not-accessible
    STATUS     current
    DESCRIPTION
	    "An entry (row) in the fsHttpAuthTestTable."
    INDEX      { fsHttpSessionId }
    ::= { fsHttpAuthTestTable 1 }

FsHttpAuthTestEntry ::= SEQUENCE {
    fsHttpSessionId	           Integer32,
    fsHttpWWWAuthHeader        DisplayString,
    fsHttpAuthorizeHeader      DisplayString,
    fsHttpAuthInfoHeader       DisplayString,
    fsHttpWWWAuthScheme        DisplayString,
    fsHttpWWWAuthRealm         DisplayString,
    fsHttpWWWAuthUsername      DisplayString,
    fsHttpWWWAuthNonce         DisplayString,
    fsHttpWWWAuthQop           DisplayString,
    fsHttpWWWAuthAlgorithm     DisplayString,
    fsHttpWWWAuthStale         DisplayString,
    fsHttpAuthInfoQop          DisplayString,
    fsHttpAuthInfoRespAuth     DisplayString,
    fsHttpAuthInfoCnonce       DisplayString,
    fsHttpAuthInfoNonceCount   DisplayString
}

fsHttpSessionId OBJECT-TYPE
    SYNTAX     Integer32
    MAX-ACCESS not-accessible
    STATUS     current
    DESCRIPTION
	    "The Webnm Session Id of the HTTP client"
    ::= { fsHttpAuthTestEntry 1 }

fsHttpWWWAuthHeader OBJECT-TYPE
    SYNTAX            DisplayString (SIZE (50))
    MAX-ACCESS        read-only
    STATUS            current
    DESCRIPTION
            "The flag message indicating that the WWW Authenticate header has been sent to the HTTP Client"
     ::= { fsHttpAuthTestEntry 2 }

fsHttpAuthorizeHeader OBJECT-TYPE
    SYNTAX     DisplayString (SIZE (50))
    MAX-ACCESS read-only
    STATUS     current
    DESCRIPTION
          "The flag message indicating that the Authorization header has been received from the HTTP Client."   
    ::= { fsHttpAuthTestEntry 3 }      

fsHttpAuthInfoHeader OBJECT-TYPE
    SYNTAX           DisplayString (SIZE (50))
    MAX-ACCESS       read-only
    STATUS           current
    DESCRIPTION
            "The flag message indicating that the Authentication-Info header has been sent to the HTTP client."
    ::= { fsHttpAuthTestEntry 4 }

fsHttpWWWAuthScheme OBJECT-TYPE
    SYNTAX           DisplayString (SIZE (50))
    MAX-ACCESS       read-only
    STATUS           current
    DESCRIPTION
            "The flag message indicating that the WWW Authenticate header sent to the HTTP client contains the Authentication scheme."
    ::= { fsHttpAuthTestEntry 5 }

fsHttpWWWAuthRealm OBJECT-TYPE
    SYNTAX           DisplayString (SIZE (50))
    MAX-ACCESS       read-only
    STATUS           current
    DESCRIPTION
            "The flag message indicating that the WWW Authenticate header sent to the HTTP client contains the Realm directive."
    ::= { fsHttpAuthTestEntry 6 }

fsHttpWWWAuthUsername OBJECT-TYPE
    SYNTAX           DisplayString (SIZE (50))
    MAX-ACCESS       read-only
    STATUS           current
    DESCRIPTION
            "The flag message indicating that the WWW Authenticate header sent to the HTTP client contains the Username directive."
    ::= { fsHttpAuthTestEntry 7 }

fsHttpWWWAuthNonce OBJECT-TYPE
    SYNTAX           DisplayString (SIZE (50))
    MAX-ACCESS       read-only
    STATUS           current
    DESCRIPTION
            "The flag message indicating that the WWW Authenticate header sent to the HTTP client contains the Nonce directive."
    ::= { fsHttpAuthTestEntry 8 }

fsHttpWWWAuthQop OBJECT-TYPE
    SYNTAX           DisplayString (SIZE (50))
    MAX-ACCESS       read-only
    STATUS           current
    DESCRIPTION
            "The flag message indicating that the WWW Authenticate header sent to the HTTP client contains the QoP directive."
    ::= { fsHttpAuthTestEntry 9 }

fsHttpWWWAuthAlgorithm OBJECT-TYPE
    SYNTAX           DisplayString (SIZE (50))
    MAX-ACCESS       read-only
    STATUS           current
    DESCRIPTION
            "The flag message indicating that the WWW Authenticate header sent to the HTTP client contains the Algorithm directive."
    ::= { fsHttpAuthTestEntry 10 }

fsHttpWWWAuthStale OBJECT-TYPE
    SYNTAX           DisplayString (SIZE (50))
    MAX-ACCESS       read-only
    STATUS           current
    DESCRIPTION
            "The flag message indicating that the WWW Authenticate header sent to the HTTP client contains the Stale directive."
    ::= { fsHttpAuthTestEntry 11 }

fsHttpAuthInfoQop OBJECT-TYPE
    SYNTAX           DisplayString (SIZE (50))
    MAX-ACCESS       read-only
    STATUS           current
    DESCRIPTION
            "The flag message indicating that the Authentication-Info header sent to the HTTP client contains the QoP directive."
    ::= { fsHttpAuthTestEntry 12 }

fsHttpAuthInfoRespAuth OBJECT-TYPE
    SYNTAX           DisplayString (SIZE (50))
    MAX-ACCESS       read-only
    STATUS           current
    DESCRIPTION
            "The flag message indicating that the Authentication-Info header sent to the HTTP client contains the Response-Auth directive."
    ::= { fsHttpAuthTestEntry 13 }

fsHttpAuthInfoCnonce OBJECT-TYPE
    SYNTAX           DisplayString (SIZE (50))
    MAX-ACCESS       read-only
    STATUS           current
    DESCRIPTION
            "The flag message indicating that the Authentication-Info header sent to the HTTP client contains the Cnonce directive."
    ::= { fsHttpAuthTestEntry 14 }

fsHttpAuthInfoNonceCount OBJECT-TYPE
    SYNTAX           DisplayString (SIZE (50))
    MAX-ACCESS       read-only
    STATUS           current
    DESCRIPTION
            "The flag message indicating that the Authentication-Info header sent to the HTTP client contains the Nonce Count directive."
    ::= { fsHttpAuthTestEntry 15 }

--
-- End of test mib objects for HTTP authentication
--

-- TABLE_END

END

-- Copyright (C) 2012 Aricent Group . All Rights Reserved

--******************************************************************************
--$Id: fswssuser.mib,v 1.9 2015/06/27 11:40:18 siva Exp $
--
--Description : This file contains MIB definitions for WSS User Role module.
--
--******************************************************************************/

ARICENT-WSSUSERMGM-MIB DEFINITIONS ::= BEGIN
   
IMPORTS
   MODULE-IDENTITY, OBJECT-TYPE,
   enterprises, Integer32, Unsigned32,NOTIFICATION-TYPE FROM SNMPv2-SMI
   RowStatus, MacAddress , TEXTUAL-CONVENTION   FROM SNMPv2-TC;

fsWssUser MODULE-IDENTITY
      LAST-UPDATED "201503050000Z"
      ORGANIZATION "ARICENT COMMUNICATIONS SOFTWARE"
      CONTACT-INFO

        "ARICENT COMMUNICATIONS SOFTWARE
         3460 Hillview Avenue,
         Palo Alto, CA 94304-1388, USA,
         Phone : +1-650-391-1088
         E-mail:support@aricent.com"

      DESCRIPTION
         "Updated the mib file for user role related notification objects."

      REVISION "201409150000Z"

      DESCRIPTION
       "The enterprise ID 29601 is assigned to Aricent Communication
       Holdings Limitied. This is the initial version for user role 
       related mib objects."
   ::=  { enterprises aricent-communication-holding-ltd(29601) iss(2) 90 }

fsWssUserScalars              OBJECT IDENTIFIER ::= { fsWssUser 1 }
fsWssUserRole                 OBJECT IDENTIFIER ::= { fsWssUser 2 }
fsWssUserStats                OBJECT IDENTIFIER ::= { fsWssUser 3 }
fsWssUserNotifyObjects        OBJECT IDENTIFIER ::= { fsWssUser 4 }
fsWssUserNotifications        OBJECT IDENTIFIER ::= { fsWssUser 5 }

-- fsWssUserScalars BEGIN

fsWssUserRoleStatus    OBJECT-TYPE
    SYNTAX        INTEGER { enable(1), disable(2) }
    MAX-ACCESS    read-write
    STATUS        current
    DESCRIPTION
    "This object specifies the administrative status requested by management for the User Role.
     When enabled (1) the user's data access is limited by the
     threshold values of User Group attributes assigned to them.  
     When disabled(2), user's data access is not controlled by the limit specified
     for the User Group assigned to them.  Also any access restriction 
     rules controlled by the User Role Management feature is not applied."
     DEFVAL { disable }
      ::= { fsWssUserScalars 1 }

fsWssUserBlockedCount    OBJECT-TYPE
    SYNTAX        Unsigned32(0..4294967295)
    MAX-ACCESS    read-write
    STATUS        current
    DESCRIPTION
    "This object specifies the number of session blocked.
     The user session could have been blocked due to any
     restriction as per User Role Management functionality.
     When this object is read-only, it displays the statistics.
     This object accepts only value zero (0) as input. The value zero (0) clears the statistics"
      ::= { fsWssUserScalars 2 }

fsWssUserLoggedCount  OBJECT-TYPE
    SYNTAX        Unsigned32(0..4294967295)
    MAX-ACCESS    read-write
    STATUS        current
    DESCRIPTION
    "This object specifies the number of users logged in successfully.
     When this object is read-only, it displays the statistics. 
     This object accepts only value zero (0) as input. The value zero (0) clears the statistics"
      ::= { fsWssUserScalars 3 }

fsWssUserTraceOption OBJECT-TYPE
    SYNTAX      Integer32
    MAX-ACCESS  read-write
    STATUS      current
    DESCRIPTION 
    "This object enables tracing in the selected
    User Role Management  module.
               
    A 32 bit integer is used to store the Tracing level in the specified 
    module.
    Different Tracing Levels -

         BIT 0 - Init and Shutdown Traces
         BIT 1 - Management Traces
         BIT 2 - Data Path Traces
         BIT 3 - Control Plane Traces
         BIT 4 - Packet Dump Traces
         BIT 5 - Traces related to All Resources except Buffers
         BIT 6 - All Failure Traces
         BIT 7 - Buffer Traces
 
    Various combinations of levels are allowed.
 
    For example if the bits 0 and 1 are set, then the Trace
    Statements related to Init-Shutdown and management
    will be printed.

    The user has to enter the corresponding INTEGER VALUE for the
    bits set. For example if bits 0 and 1 are set then user has to
    set the value 3."
    
    DEFVAL{0}
      ::= { fsWssUserScalars 4 }


fsWssUserRoleTrapStatus OBJECT-TYPE
    SYNTAX      INTEGER {
                        enable (1),
                        disable (2) }

    MAX-ACCESS  read-write
    STATUS      current
    DESCRIPTION
    "This object enables or disables the trap for User Role Management."
    DEFVAL { disable }
    ::= { fsWssUserScalars 5 }




-- **********************************************************************
-- * fsWssUserGroupTable  TABLE
-- **********************************************************************
fsWssUserGroupTable  OBJECT-TYPE
    SYNTAX          SEQUENCE OF FsWssUserGroupEntry
    MAX-ACCESS      not-accessible
    STATUS          current
    DESCRIPTION
    "The User Group table contains the list of users 
     with the corresponding the data plan." 
    ::= { fsWssUserRole 1 }

fsWssUserGroupEntry OBJECT-TYPE
    SYNTAX          FsWssUserGroupEntry
    MAX-ACCESS      not-accessible
    STATUS          current
    DESCRIPTION
    "This object contains User Group related parameters."
    INDEX { fsWssUserGroupId }
    ::= { fsWssUserGroupTable 1 }

FsWssUserGroupEntry ::=
    SEQUENCE {  fsWssUserGroupId              Unsigned32,
                fsWssUserGroupName            OCTET STRING,
                fsWssUserGroupBandWidth       Unsigned32,
                fsWssUserGroupVolume          Unsigned32,
                fsWssUserGroupTime            Unsigned32 ,
                fsWssUserGroupRowStatus       RowStatus,
                fsWssUserGroupDLBandWidth     Unsigned32,
                fsWssUserGroupULBandWidth     Unsigned32
    }

fsWssUserGroupId     OBJECT-TYPE
    SYNTAX        Unsigned32 (1..1024)
    MAX-ACCESS    not-accessible
    STATUS        current
    DESCRIPTION
    "This object specifies the unique User Group Identifier assigned 
     to each data plan"
    ::= { fsWssUserGroupEntry 1 }


fsWssUserGroupName    OBJECT-TYPE
    SYNTAX         OCTET STRING
    MAX-ACCESS     read-write
    STATUS         current
    DESCRIPTION
    "This object specifies the name of the group which is associated to a 
    data plan. 
    In the start-up, the default user-group is created with user group name as Default.
    Other statically created user-groups are by default given the name 
    User-Group appended by its user group id. However this can be edited later"
    ::= {fsWssUserGroupEntry  2 }

fsWssUserGroupBandWidth OBJECT-TYPE
    SYNTAX      Unsigned32(0..4294967295)
    MAX-ACCESS  read-write
    STATUS      current
    DESCRIPTION
    "This object specifies the speed/rate, at which the data can be 
    used in Access point
    for the users in the user group. 

    The unit of bandwidth value represented by this MIB object is in Kbps."

    DEFVAL      { 256 }
    ::= {fsWssUserGroupEntry  3 }

fsWssUserGroupVolume  OBJECT-TYPE
    SYNTAX      Unsigned32(0..4294967295)
    MAX-ACCESS  read-write
    STATUS      current
    DESCRIPTION
    "This object specifies the volume of data in megabytes that can be 
    downloaded/uploaded in this data plan.

    The unit of Volume value represented by this MIB object is in MB.

    The value 0 in this MIB object represents unlimited data usage "
    DEFVAL      { 0 }
    ::= {fsWssUserGroupEntry  4 }

fsWssUserGroupTime  OBJECT-TYPE
    SYNTAX         Unsigned32 (0..31536000)
    MAX-ACCESS     read-write
    STATUS         current
    DESCRIPTION
    "This object indicates the time in seconds,till which the data plan is valid

    The default value is 0 which implies Unlimited time period."
    DEFVAL      { 0 }
    ::= { fsWssUserGroupEntry 5 }

fsWssUserGroupRowStatus OBJECT-TYPE
    SYNTAX         RowStatus
    MAX-ACCESS     read-create
    STATUS         current
    DESCRIPTION
    "This object is used to create, modify, and/or delete a row
    in the table.
    All the objects in a row can be modified only when the value
    of this object in the corresponding conceptual row is not
    'active'.  Thus, to modify one or more of the objects in
    this conceptual row:
          a. change the row status to 'notInService',
          b. change the values of the row
          c. change the row status to 'active'
    The fsUserGroupRowStatus may be changed to 'active'
    if all the managed objects in the conceptual row
    are assigned with valid values."
    ::= { fsWssUserGroupEntry 6 }


fsWssUserGroupDLBandWidth OBJECT-TYPE
    SYNTAX      Unsigned32(0..4294967295)
    MAX-ACCESS  read-write
    STATUS      current
    DESCRIPTION
    "This object specifies the speed/rate, at which the data can be 
    downloaded in Access point
    for the users in the user group. 

    The unit of bandwidth value represented by this MIB object is in Kbps."

    DEFVAL      { 256 }
    ::= {fsWssUserGroupEntry  7 }


fsWssUserGroupULBandWidth OBJECT-TYPE
    SYNTAX      Unsigned32(0..4294967295)
    MAX-ACCESS  read-write
    STATUS      current
    DESCRIPTION
    "This object specifies the speed/rate, at which the data can be 
    uploaded in Access point
    for the users in the user group. 

    The unit of bandwidth value represented by this MIB object is in Kbps."

    DEFVAL      { 256 }
    ::= {fsWssUserGroupEntry  8 }

-- **********************************************************************
-- * fsUserRoleTable 
-- **********************************************************************
fsWssUserRoleTable         OBJECT-TYPE
    SYNTAX          SEQUENCE OF FsWssUserRoleEntry
    MAX-ACCESS      not-accessible
    STATUS          current
    DESCRIPTION
    "This table contains list of users, mapped to
    a corresponding User Group representing the data plan"
    ::= { fsWssUserRole 2 }

fsWssUserRoleEntry OBJECT-TYPE
    SYNTAX          FsWssUserRoleEntry
    MAX-ACCESS      not-accessible
    STATUS          current
    DESCRIPTION
    "This object contains User Role related parameters."
    INDEX { fsWssUserRoleName, fsWssUserRoleWlanIndex }
    ::= { fsWssUserRoleTable 1 }

FsWssUserRoleEntry ::=
    SEQUENCE {  fsWssUserRoleName        OCTET STRING,
                fsWssUserRoleWlanIndex   Unsigned32,
                fsWssUserRoleGroupId     Unsigned32,
                fsWssUserRoleRowStatus   RowStatus
    }

fsWssUserRoleName OBJECT-TYPE
    SYNTAX         OCTET STRING (SIZE(0..32))
    MAX-ACCESS     not-accessible
    STATUS         current
    DESCRIPTION
    "This object specifies the user name with which the user login"
    ::= {fsWssUserRoleEntry  1 }

fsWssUserRoleWlanIndex OBJECT-TYPE
    SYNTAX        Unsigned32 (1..512)
    MAX-ACCESS    not-accessible
    STATUS        current
    DESCRIPTION
    "This object specifies the WLAN corresponding to
	the Service Set ID (SSID) to which the user belongs."
    ::= {fsWssUserRoleEntry  2 }

fsWssUserRoleGroupId  OBJECT-TYPE
    SYNTAX        Unsigned32 (1..1024)
    MAX-ACCESS    read-write
    STATUS        current
    DESCRIPTION
    "This object specifies the unique User Group Identifier"
    ::= { fsWssUserRoleEntry 3 }

fsWssUserRoleRowStatus OBJECT-TYPE
    SYNTAX         RowStatus
    MAX-ACCESS     read-create
    STATUS         current
    DESCRIPTION
    "This object is used to create, modify, and/or delete a row
    in the table.
    All objects in the row can be modified only when the value
    of fsWssUserGroupRowStatus in the corresponding conceptual row is not
    'active'. To modify one or more objects in
    the conceptual row do one of the following:
         a. change the row status to 'notInService',
         b. change the values of the row
         c. change the row status to 'active'
    The fsWssUserGroupRowStatus can be changed to 'active'
    if all the objects in the conceptual row
    are assigned with valid values."
    ::= { fsWssUserRoleEntry 4 }


-- **********************************************************************
-- * fsWssUserNameAccessList TABLE
-- **********************************************************************
fsWssUserNameAccessListTable  OBJECT-TYPE
    SYNTAX          SEQUENCE OF FsWssUserNameAccessListEntry
    MAX-ACCESS      not-accessible
    STATUS          current
    DESCRIPTION
    "This table contains the List of Users restricted to access, based on their User Name."
    ::= { fsWssUserRole 3}

fsWssUserNameAccessListEntry  OBJECT-TYPE
    SYNTAX          FsWssUserNameAccessListEntry
    MAX-ACCESS      not-accessible
    STATUS          current
    DESCRIPTION
    "This object specifies details of restricted users based on their User Name."
    INDEX {  fsWssUserNameAccessListUserName }
    ::= { fsWssUserNameAccessListTable 1 }

FsWssUserNameAccessListEntry  ::=
    SEQUENCE {  fsWssUserNameAccessListUserName        OCTET STRING,
		        fsWssUserNameAccessListRowStatus       RowStatus
    }

fsWssUserNameAccessListUserName OBJECT-TYPE
    SYNTAX         OCTET STRING (SIZE(0..32))
    MAX-ACCESS     not-accessible
    STATUS         current
    DESCRIPTION
    "This object specifies the user names which are restricted to login"
    ::= {fsWssUserNameAccessListEntry 1 }

fsWssUserNameAccessListRowStatus OBJECT-TYPE
    SYNTAX      RowStatus
    MAX-ACCESS  read-create
    STATUS      current
    DESCRIPTION
    "This variable is used to create, modify, and/or delete a row
    in the table.
    All the objects in a row can be modified only when the value
    of fsWssUserNameAccessListRowStatus object in the corresponding conceptual row is not
    'active'.  To modify one or more objects in the row.
         a. change the row status to 'notInService',
         b. change the values of the row
         c. change the row status to 'active'
    The fsUserNameAccessListRowStatus may be changed to 'active'
    if all the managed objects in the conceptual row
    are assigned with valid inputs."
    ::= { fsWssUserNameAccessListEntry 2 }

-- **********************************************************************
-- * fsWssUserMacAccessList TABLE
-- **********************************************************************
fsWssUserMacAccessListTable  OBJECT-TYPE
    SYNTAX          SEQUENCE OF FsWssUserMacAccessListEntry
    MAX-ACCESS      not-accessible
    STATUS          current
    DESCRIPTION
    "This table contains the list of Users restricted to access, 
    based on their user MAC addresses."
    ::= { fsWssUserRole 4}

fsWssUserMacAccessListEntry  OBJECT-TYPE
    SYNTAX          FsWssUserMacAccessListEntry
    MAX-ACCESS      not-accessible
    STATUS          current
    DESCRIPTION
    "This object maps the user name with the MAC address of the station"
    INDEX { fsWssUserMacAccessListStaMac }
    ::= { fsWssUserMacAccessListTable 1 }

FsWssUserMacAccessListEntry  ::=
    SEQUENCE {  fsWssUserMacAccessListStaMac          MacAddress,
		        fsWssUserMacAccessListRowStatus       RowStatus
    }

fsWssUserMacAccessListStaMac  OBJECT-TYPE
    SYNTAX                    MacAddress
    MAX-ACCESS                not-accessible
    STATUS                    current
    DESCRIPTION
    "This object contains the MAC address of the user for which the 
    access has to be restricted"
    ::= { fsWssUserMacAccessListEntry 1 }

fsWssUserMacAccessListRowStatus OBJECT-TYPE
    SYNTAX      RowStatus
    MAX-ACCESS  read-create
    STATUS      current
    DESCRIPTION
    "This object is used to create, modify, and/or delete a row
    in the table.
    All the objects in a row can be modified only when the value
    of fsWssUserMacAccessListRowStatus object in the corresponding conceptual row is not
    'active'.  To modify one or more objects in the row:
         a. change the row status to 'notInService',
         b. change the values of the row
         c. change the row status to 'active'
    The fsUserMacAccessListRowStatus can be changed to 'active'
    if all the managed objects in the conceptual row
    are assigned with valid inputs."
    ::= { fsWssUserMacAccessListEntry 2 }



-- **********************************************************************
-- * fsWssUserMappingTable TABLE
-- **********************************************************************
fsWssUserMappingTable  OBJECT-TYPE
    SYNTAX          SEQUENCE OF FsWssUserMappingEntry
    MAX-ACCESS      not-accessible
    STATUS          current
    DESCRIPTION
    "This table contains mapping the user name with the respective
    MAC address used.Therefore the same user credentials cannot be 
    used in different machines."
    ::= { fsWssUserRole 5}

fsWssUserMappingEntry OBJECT-TYPE
    SYNTAX          FsWssUserMappingEntry
    MAX-ACCESS      not-accessible
    STATUS          current
    DESCRIPTION
    "This table contains the user related entries."
    INDEX {  fsWssUserMappingName, fsWssUserMappingStaMac }
    ::= { fsWssUserMappingTable 1 }

FsWssUserMappingEntry ::=
    SEQUENCE {  fsWssUserMappingName            OCTET STRING,
                fsWssUserMappingStaMac          MacAddress,
	        fsWssUserMappingRowStatus       RowStatus
    }


fsWssUserMappingName OBJECT-TYPE
    SYNTAX         OCTET STRING  (SIZE(0..32))
    MAX-ACCESS  not-accessible
    STATUS         current
    DESCRIPTION
    "This object specifies the user name with which the user connects to the system"
    ::= {fsWssUserMappingEntry  1 }

fsWssUserMappingStaMac  OBJECT-TYPE
    SYNTAX      MacAddress
    MAX-ACCESS  not-accessible
    STATUS      current
    DESCRIPTION
    "This object specifies the station MAC address mapped with the user"
    ::= { fsWssUserMappingEntry 2 }

fsWssUserMappingRowStatus OBJECT-TYPE
    SYNTAX      RowStatus
    MAX-ACCESS  read-create
    STATUS      current
    DESCRIPTION
    "This object is used to create, modify, and/or delete a row
    in the table.
    All the objects in a row can be modified only when the value
    of fsWssUserMappingRowStatus object in the corresponding conceptual row is not
    'active'.  To modify one or more objects in the row.
         a. change the row status to 'notInService',
         b. change the values of the row
         c. change the row status to 'active'
    The fsUserMappingRowStatus can be changed to 'active' only
    if all the managed objects in the conceptual row
    are assigned with valid inputs."
    ::= { fsWssUserMappingEntry 3 }


-- fsWssUserSessionTable Table

fsWssUserSessionTable OBJECT-TYPE
    SYNTAX      SEQUENCE OF FsWssUserSessionEntry
    MAX-ACCESS  not-accessible
    STATUS      current
    DESCRIPTION
    "This table displays the user  statistics."
    ::= { fsWssUserStats 1 }

fsWssUserSessionEntry OBJECT-TYPE
    SYNTAX      FsWssUserSessionEntry
    MAX-ACCESS  not-accessible
    STATUS      current
    DESCRIPTION
    "This table contains the user session related entries ."
    INDEX { fsWssUserName, fsWssUserStaMac }
    ::= { fsWssUserSessionTable 1 }

FsWssUserStationMac ::= TEXTUAL-CONVENTION
    DISPLAY-HINT "1x:"
    STATUS      current
    DESCRIPTION
        "This object specifies the unique identifier of a WTP instance.
         As usual, the Base MAC address of the WTP is used."
    SYNTAX     OCTET STRING (SIZE(6|8))


FsWssUserIdName ::= TEXTUAL-CONVENTION
    DISPLAY-HINT "1x:"
    STATUS      current
    DESCRIPTION
        "This object specifies the unique identifier of a station instance.
         As usual, the MAC address of the station is used."
    SYNTAX       OCTET STRING  (SIZE(0..32))

-- End of Textual Convention

FsWssUserSessionEntry ::=
    SEQUENCE { 
        fsWssUserName               FsWssUserIdName,
        fsWssUserStaMac             FsWssUserStationMac,
        fsWssUserWlanIndex          Unsigned32, 
        fsWssUserAllotedBandWidth     Unsigned32,
        fsWssUserAllotedVolume	    Unsigned32,
        fsWssUserAllotedTime	    Unsigned32,
        fsWssUserUsedVolume	        Unsigned32,
        fsWssUserUsedTime	        Unsigned32,
        fsWssUserAllotedDLBandWidth   Unsigned32,
        fsWssUserAllotedULBandWidth   Unsigned32
    } 

fsWssUserName     OBJECT-TYPE
    SYNTAX        FsWssUserIdName
    MAX-ACCESS  not-accessible
    STATUS         current
    DESCRIPTION
    "This object specifies the user name with which the user connects to the system"
        ::= { fsWssUserSessionEntry 1 }

fsWssUserStaMac      OBJECT-TYPE
    SYNTAX      FsWssUserStationMac
    MAX-ACCESS  not-accessible
    STATUS      current
    DESCRIPTION
    "This object indicates the MAC address of the station with which 
	the user logs in"
       ::= { fsWssUserSessionEntry 2 }

fsWssUserWlanIndex   OBJECT-TYPE
    SYNTAX      Unsigned32 (1..512)
    MAX-ACCESS  read-only
    STATUS      current
    DESCRIPTION
    "This object indicates the WLAN of the corresponding 
    Service Set Identifier (SSID) with which the user connects to the system"
       ::= { fsWssUserSessionEntry 3 }

fsWssUserAllotedBandWidth OBJECT-TYPE
    SYNTAX      Unsigned32(0..4294967295)
    MAX-ACCESS  read-only
    STATUS      current
    DESCRIPTION
    "This object indicates the allotted speed/rate, in kbps with
    which the data can be used in the Access point
    for the users in this user group. 

    The value 0 in this object represents that no rate limiting 
    is done in this plan."
       ::= { fsWssUserSessionEntry 4 }

fsWssUserAllotedVolume  OBJECT-TYPE
    SYNTAX      Unsigned32(0..4294967295)
    MAX-ACCESS  read-only
    STATUS      current
    DESCRIPTION
    "This object indicates the allotted volume of data in megabytes that can be 
    downloaded/uploaded in this data plan.

    The value 0 in this object represents unlimited data usage 
    with this plan."
       ::= { fsWssUserSessionEntry 5 }

fsWssUserAllotedTime	OBJECT-TYPE
    SYNTAX         Unsigned32 (0..31536000)
    MAX-ACCESS     read-only
    STATUS         current
    DESCRIPTION
    "This object indicates the time in seconds, till which the data plan is valid. 
    The default value is 86400 seconds (60*60*24=1 day)."
       ::= { fsWssUserSessionEntry 6 }

fsWssUserUsedVolume	OBJECT-TYPE
    SYNTAX      Unsigned32(0..4294967295)
    MAX-ACCESS  read-only
    STATUS      current
    DESCRIPTION
    "This object indicates the volume consumed by the user" 
       ::= { fsWssUserSessionEntry 7 }

fsWssUserUsedTime	OBJECT-TYPE
    SYNTAX         Unsigned32 (0..31536000)
    MAX-ACCESS     read-only
    STATUS         current
    DESCRIPTION
    "This object indicates the time consumed by the user in the
	specified data plan." 

       ::= { fsWssUserSessionEntry 8 }


fsWssUserAllotedDLBandWidth OBJECT-TYPE
    SYNTAX      Unsigned32(0..4294967295)
    MAX-ACCESS  read-only
    STATUS      current
    DESCRIPTION
    "This object indicates the allotted speed/rate, in kbps with
    which the data can be downloaded in the Access point
    for the users in this user group. 

    The value 0 in this object represents that no rate limiting 
    is done in this plan."
       ::= { fsWssUserSessionEntry 9 }

fsWssUserAllotedULBandWidth OBJECT-TYPE
    SYNTAX      Unsigned32(0..4294967295)
    MAX-ACCESS  read-only
    STATUS      current
    DESCRIPTION
    "This object indicates the allotted speed/rate, in kbps with
    which the data can be uploaded in the Access point
    for the users in this user group.

    The value 0 in this object represents that no rate limiting
    is done in this plan."
 
	::= { fsWssUserSessionEntry 10 }

-- End of fsWssUserSessionTable


-- Notification Objects
fsWssUserTrapObjects OBJECT IDENTIFIER
    ::= {  fsWssUserNotifyObjects 1 }

fsWssUserStationMacAddress OBJECT-TYPE
    SYNTAX      FsWssUserStationMac
    MAX-ACCESS  accessible-for-notify
    STATUS      current
    DESCRIPTION
        "This object specifies the unique identifier of a WTP."
    ::= { fsWssUserTrapObjects 1 }

fsWssNtfUserName        OBJECT-TYPE
    SYNTAX       FsWssUserIdName 
    MAX-ACCESS  accessible-for-notify
    STATUS      current
    DESCRIPTION
        "This object specifies the User Name "
    ::= { fsWssUserTrapObjects 2 }

-- END OF TRAP OBJECTS
fsWssUserTraps OBJECT IDENTIFIER ::= {   fsWssUserNotifications 0 }

fsWssUserVolumeExceeded NOTIFICATION-TYPE
    OBJECTS    { fsWssUserWlanIndex,
                 fsWssNtfUserName,
                 fsWssUserStationMacAddress,
                 fsWssUserUsedVolume   }

   STATUS       current
   DESCRIPTION
   "This object specifies notification that is generated when the user has reached the maximum volume of usage"
     ::= { fsWssUserTraps 1 }


fsWssUserTimeExceeded NOTIFICATION-TYPE
    OBJECTS    { fsWssUserWlanIndex,
                 fsWssNtfUserName,
                 fsWssUserStationMacAddress,
                 fsWssUserUsedTime  }

    STATUS       current
    DESCRIPTION
    "This object specifies notification that is generated when the user's allocated time has exceeded
    for usage"
     ::= { fsWssUserTraps 2 }


END

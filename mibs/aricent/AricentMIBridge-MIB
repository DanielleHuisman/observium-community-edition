-- Copyright (C) 2006-2015 Aricent. All Rights Reserved

-- $Id: fsmpbrg.mib,v 1.4 2016/03/24 10:16:12 siva Exp $

AricentMIBridge-MIB DEFINITIONS ::= BEGIN

IMPORTS
       MODULE-IDENTITY, OBJECT-TYPE, NOTIFICATION-TYPE, OBJECT-IDENTITY,
       enterprises,Integer32, Counter32             FROM SNMPv2-SMI
       TEXTUAL-CONVENTION, TruthValue, MacAddress   FROM SNMPv2-TC
       MODULE-COMPLIANCE, OBJECT-GROUP,
       NOTIFICATION-GROUP                     FROM SNMPv2-CONF;
                         	
futureMIBridgeMIB MODULE-IDENTITY
    LAST-UPDATED "201209050000Z"
    ORGANIZATION "ARICENT COMMUNICATIONS SOFTWARE"
    CONTACT-INFO "support@aricent.com"
	 DESCRIPTION 
	 "This mib module is for Proprietary
	 Multiple Instance Bridge mib"
         REVISION "201209050000Z"
	 DESCRIPTION 
	 "This mib module is for Proprietary
	 Multiple Instance Bridge mib"
	 
::= { enterprises futuresoftware(2076) 117 }

BridgeId ::= TEXTUAL-CONVENTION
        STATUS  current
        DESCRIPTION 
		" Identifier of Bridge in 8 byte format"
        SYNTAX          OCTET STRING (SIZE (8))

fsMIDot1dFutureBridge   OBJECT IDENTIFIER   ::= {  futureMIBridgeMIB 1 }
fsMIDot1dFutureBase     OBJECT IDENTIFIER ::= { fsMIDot1dFutureBridge 1 }
fsMIDot1dFutureTp     OBJECT IDENTIFIER ::= { fsMIDot1dFutureBridge 2 }
fsMIDot1dFilter   OBJECT IDENTIFIER ::= { fsMIDot1dFutureBridge 3 }
fsMIDot1dMcast    OBJECT IDENTIFIER ::= { fsMIDot1dFutureBridge 4 }
 
-- the fsMIDot1dFutureBase group

fsMIDot1dFutureBaseTable OBJECT-TYPE
    SYNTAX SEQUENCE OF FsMIDot1dFutureBaseEntry
    MAX-ACCESS    not-accessible
    STATUS        current
    DESCRIPTION
       "This object specifies the list of per Virtual Context Bridge Module Parameters."
    ::= { fsMIDot1dFutureBase 1 }

fsMIDot1dFutureBaseEntry OBJECT-TYPE
   SYNTAX       FsMIDot1dFutureBaseEntry
   MAX-ACCESS   not-accessible
   STATUS       current
   DESCRIPTION
      "This object specifies the Virtual Context Bridge Module Parameters."
   INDEX { fsMIDot1dFutureBaseContextId }
   ::= { fsMIDot1dFutureBaseTable 1 }

FsMIDot1dFutureBaseEntry ::=
    SEQUENCE {
           fsMIDot1dFutureBaseContextId
              Integer32,
           fsMIDot1dBridgeSystemControl
              INTEGER,
           fsMIDot1dBaseBridgeStatus
              INTEGER,
           fsMIDot1dBaseBridgeCRCStatus
              INTEGER,
           fsMIDot1dBaseBridgeDebug
              Integer32, 
           fsMIDot1dBaseBridgeTrace
              Integer32,
           fsMIDot1dBaseBridgeMaxFwdDbEntries
              Integer32
}

fsMIDot1dFutureBaseContextId OBJECT-TYPE
   SYNTAX       Integer32 (0..65535)
   MAX-ACCESS   not-accessible
   STATUS       current
   DESCRIPTION
      "Virtual Context ID"
   ::= { fsMIDot1dFutureBaseEntry 1}

fsMIDot1dBridgeSystemControl OBJECT-TYPE
   SYNTAX      INTEGER { start(1), shutdown(2) }
   MAX-ACCESS  read-write
   STATUS      current
   DESCRIPTION
      "This object specifies the administrative system control status requested by management for
      the TB feature. The value 'start'(1) indicates that all resources 
      required by TB should be allocated and TB should be supported 
      in the device on all ports. The value shutdown(2) indicates that TB 
      should be shutdown in the device on all ports and all allocated memory 
      must be released."
       DEFVAL { start}
       ::= { fsMIDot1dFutureBaseEntry 2 }

fsMIDot1dBaseBridgeStatus OBJECT-TYPE
       SYNTAX  INTEGER{
                 up (1),
                 down (2),
                 downwithallinterfacesdown (3)
               }
       MAX-ACCESS  read-write
       STATUS  current
       DESCRIPTION
               "This object specifies the Control for Bridging services.
                Setting this object to down-with-all-interfaces-down(3),
                  assigns down(2) value to fsMIDot1dBasePortAdminStatus in 
                  all entries of fsMIDot1dFutureBasePortTable"
       DEFVAL { down }
       ::= { fsMIDot1dFutureBaseEntry 3 }

fsMIDot1dBaseBridgeCRCStatus OBJECT-TYPE
       SYNTAX  INTEGER{
                 withCRC(1),
                 withoutCRC(2)
               }
       MAX-ACCESS read-write
       STATUS current
       DESCRIPTION
               "This object when Set to withCRC(1) expects all LAN 
                frames to be received with CRC, and transmits through 
                WAN and LAN interface with the same CRC without 
                regeneration."
       DEFVAL { withoutCRC }
       ::= { fsMIDot1dFutureBaseEntry 4 }

fsMIDot1dBaseBridgeDebug   OBJECT-TYPE
   SYNTAX  Integer32 (0..255)
   MAX-ACCESS   read-write
   STATUS   current
   DESCRIPTION
      "This object is used to enable debugging facility for FutureTB/STP." 
   ::= { fsMIDot1dFutureBaseEntry 5  }

fsMIDot1dBaseBridgeTrace   OBJECT-TYPE
   SYNTAX  Integer32 (0..255)
   MAX-ACCESS   read-write
   STATUS   current
   DESCRIPTION
      "This object is used to enable Trace Statements in  
      FutureTB/STP module. 

      A FOUR BYTE integer is used for enabling the level of tracing.  
      Each BIT in the four byte integer, represents a particular  
      level of Trace.  

      The maping between the bit positions & the level of trace is  
      as follows:  
      0 - Init and Shutdown Traces 
      1 - Management Traces 
      2 - Data Path Traces 
      3 - Control Plane Traces 
      4 - Packet Dump Traces 
      5 - Traces related to All Resources except Buffers 
      6 - All Failure Traces 
      7 - Buffer Traces 

      The remaining bits are unused. Combination of levels are  
      also allowed. 

      For example if the bits 0 and 1 are set, then the Trace 
      statements related to Init-Shutdown and management  
      will be printed. 

      The user has to enter the corresponding INTEGER VALUE for the 
      bits set. For example if bits 0 and 1 are set then user has to  
      give the value 3." 
   ::= { fsMIDot1dFutureBaseEntry 6 }

fsMIDot1dBaseBridgeMaxFwdDbEntries   OBJECT-TYPE
   SYNTAX  Integer32 (1..65535)
   MAX-ACCESS   read-only
   STATUS   current
   DESCRIPTION
      "This object specifies the maximum entries in the Forwarding Database." 
   ::= { fsMIDot1dFutureBaseEntry 7 }



fsMIDot1dFutureBasePortTable OBJECT-TYPE
       SYNTAX  SEQUENCE OF FsMIDot1dFutureBasePortEntry
       MAX-ACCESS  not-accessible
       STATUS  current
       DESCRIPTION
               "This table contains generic information about
               every port that is associated with this bridge.
               Transparent, source-route, and srt ports are
               included."
       ::= { fsMIDot1dFutureBase 2 }

fsMIDot1dFutureBasePortEntry OBJECT-TYPE
       SYNTAX  FsMIDot1dFutureBasePortEntry
       MAX-ACCESS  not-accessible
       STATUS  current
       DESCRIPTION
               "This object specifies a list of information for each port of the
               bridge."
       REFERENCE
               "P802.1d/D9, July 14, 1989: Section 6.4.2, 6.6.1"
       INDEX  { fsMIDot1dFutureBasePort }
       ::= { fsMIDot1dFutureBasePortTable 1 }

   FsMIDot1dFutureBasePortEntry ::=
       SEQUENCE {
           fsMIDot1dFutureBasePort
               Integer32,
	        fsMIDot1dBasePortAdminStatus
               INTEGER,
           fsMIDot1dBasePortOperStatus
               INTEGER,
           fsMIDot1dBasePortBcastStatus
               INTEGER,
           fsMIDot1dBasePortFilterNumber
               Integer32,
           fsMIDot1dBasePortMcastNumber
               Integer32,      
           fsMIDot1dBasePortBcastOutFrames
                 Counter32,
           fsMIDot1dBasePortMcastOutFrames
               Counter32
       }

   fsMIDot1dFutureBasePort OBJECT-TYPE
       SYNTAX  Integer32 (1..65535)
       MAX-ACCESS  not-accessible
       STATUS  current
       DESCRIPTION
		"This object specifies the port number of the port for which this entry contains
		bridge management information "
       ::= { fsMIDot1dFutureBasePortEntry 1 }

     fsMIDot1dBasePortAdminStatus OBJECT-TYPE
       SYNTAX  INTEGER{
               up (1),
               down (2)
              }
       MAX-ACCESS  read-create
       STATUS  current
       DESCRIPTION
      "This object specifies the Control for Bridging services for this interface.
      An entry in the fsDot1dBasePortTable, fsDot1dStpPortTable and 
      fsDot1dTpPortTable will be created during the first indication 
      of this Interface Oper Up. Such a created Interface can be 
      made BasePortAdminUp or BasePortAdminDown by setting this 
      object to  up (1) or down (2) respectively.

      When this object is configured with fsDot1dBasePortCircuit         
      equal to 0xffff, the value specified is assigned to all
      circuits corresponding to the interface identified by 
      the fsDot1dBasePortIndex."


       DEFVAL { up }
       ::= { fsMIDot1dFutureBasePortEntry 2 }

   fsMIDot1dBasePortOperStatus OBJECT-TYPE
       SYNTAX  INTEGER{
               up (1),
               down (2)
              }
       MAX-ACCESS  read-only
       STATUS  current
       DESCRIPTION
      "This object specifies the operational counterpart of the fsDot1dBasePortAdminStatus. 
       This object is valid only if the administration status of the
       corresponding interface is up (1)."
       ::= { fsMIDot1dFutureBasePortEntry 3 }

   fsMIDot1dBasePortBcastStatus OBJECT-TYPE
       SYNTAX  INTEGER{
               up (1),
               down (2)
              }
       MAX-ACCESS  read-create
       STATUS  current
       DESCRIPTION
               "This object specifies the Control for Broadcast frame forwarding over this 
      interface.  Setting this object to down (2) restricts forwarding
      Broadcast frames over this interface."
       DEFVAL { up }
       ::= { fsMIDot1dFutureBasePortEntry 4 }


   fsMIDot1dBasePortFilterNumber OBJECT-TYPE
       SYNTAX  Integer32 (0..99)
       MAX-ACCESS  read-create
       STATUS  current
       DESCRIPTION
           "This object specifies the no. specifying the set of filter entries (fsDot1dFilterEntry)
           to be used on this interface.  Setting this object to zero 
           deassigns the filter table entries assigned to this interface."
       DEFVAL  { 0 }
       ::=  { fsMIDot1dFutureBasePortEntry 5 }

   fsMIDot1dBasePortMcastNumber  OBJECT-TYPE
       SYNTAX  Integer32 (0..99)
       MAX-ACCESS  read-create
       STATUS  current
       DESCRIPTION
           "This object specifies the number specifying the set of multicast entries 
           (fsDot1dMCastEntry) to be used on this interface.  Setting this 
           object to zero deassigns the multicast table entries assigned 
           to this interface."
       DEFVAL  { 0 }
       ::=  { fsMIDot1dFutureBasePortEntry 6 }

   fsMIDot1dBasePortBcastOutFrames  OBJECT-TYPE
         SYNTAX  Counter32
         MAX-ACCESS  read-only
         STATUS  current
         DESCRIPTION
             "This object specifies the Count of broadcasted frame that are transmitted through
            this interface. This object is updated only for frames with
            broadcast destination address (ff.ff.ff.ff.ff.ff) and frames 
            which are broadcasted because of no learned entry in the 
            fsDot1dTpFdbTable."
         ::=  { fsMIDot1dFutureBasePortEntry 7 }

   fsMIDot1dBasePortMcastOutFrames  OBJECT-TYPE
         SYNTAX  Counter32
         MAX-ACCESS  read-only
         STATUS  current
         DESCRIPTION
             "This object specifies the Count of frames transmitted through this interface with 
             destination address in which the Mac layer multicast bit set.
             This object is not updated for frames transmitted with broadcast
             destination address (i.e ff.ff.ff.ff.ff.ff)."
         ::=  { fsMIDot1dFutureBasePortEntry 8 }


   -- the fsMIDot1dTp group
   --  Port Table for Transparent Bridges

   fsMIDot1dFutureTpPortTable OBJECT-TYPE
       SYNTAX  SEQUENCE OF FsMIDot1dFutureTpPortEntry
       MAX-ACCESS  not-accessible
       STATUS  current
       DESCRIPTION
               "This table contains information about every
               port that is associated with this transparent
               bridge."
       ::= { fsMIDot1dFutureTp 1 }

   fsMIDot1dFutureTpPortEntry OBJECT-TYPE
       SYNTAX  FsMIDot1dFutureTpPortEntry
       MAX-ACCESS  not-accessible
       STATUS  current
       DESCRIPTION
               "This object specifies a list of information for each port of a
               transparent bridge."
       INDEX   { fsMIDot1dFutureTpPort }
       ::= { fsMIDot1dFutureTpPortTable 1 }

   FsMIDot1dFutureTpPortEntry ::=
       SEQUENCE {
           fsMIDot1dFutureTpPort
               Integer32,
	        fsMIDot1dTpPortInProtoDiscards
               Counter32,
           fsMIDot1dTpPortInFilterDiscards 
               Counter32,
           fsMIDot1dTpPortProtocolFilterMask
               Integer32
       }

   fsMIDot1dFutureTpPort OBJECT-TYPE
       SYNTAX  Integer32 (1..65535)
       MAX-ACCESS  not-accessible
       STATUS  current
       DESCRIPTION
                "This object specifies the port number of the port for which this entry contains
                Transparent Bridging management information."
       ::= { fsMIDot1dFutureTpPortEntry 1 }

   fsMIDot1dTpPortInProtoDiscards OBJECT-TYPE
       SYNTAX   Counter32
       MAX-ACCESS   read-only
       STATUS   current
       DESCRIPTION
               "This object specifies the Count of valid frames received by this port
               which were discarded  due to the protocol filter mask
               (fsDot1dTpPortProtocolFilterMask)."
       ::= { fsMIDot1dFutureTpPortEntry 2 }


   fsMIDot1dTpPortInFilterDiscards OBJECT-TYPE
       SYNTAX   Counter32
       MAX-ACCESS   read-only
       STATUS   current
       DESCRIPTION
               "This object specifies the Count of valid frames received which were
               discarded  (i.e filtered) by the forwarding process
                 this  includes frames discarded by Max-Size
                 and frames discarded by protocol filter mask."
       ::= { fsMIDot1dFutureTpPortEntry 3 }

   fsMIDot1dTpPortProtocolFilterMask OBJECT-TYPE
       SYNTAX  Integer32
       MAX-ACCESS  read-create
       STATUS  current
       DESCRIPTION
            "This object specifies the protocol type filtering mask for this interface.
                 The possible  masks are :
            IP          0x0004
            IPX         0x0008
            XNS         0x0010
            DECNET      0x0020
            CLNP        0x0040
            ATALK       0x0080
            PPPOE       0x0100 
	     For eg. to filter IP and IPX  frames, set the  
            fsDot1dTpPortProtocolFilterMask to ( IP | IPX )."
       DEFVAL { 0 }
       ::= { fsMIDot1dFutureTpPortEntry 4 }


--The Bridge Filter MIB

-- Destination and Source address based filtering.
-- This filtering scheme is an Egress filtering where the defined filter is
-- applied only on potential transmission ports.

--This consists of two tables, one for the actual filter list entries and the
--other one for assigning a particular filter to a particular interface.


fsMIDot1dFilterTable   OBJECT-TYPE
   SYNTAX   SEQUENCE OF FsMIDot1dFilterEntry
   MAX-ACCESS   not-accessible
   STATUS   current
   DESCRIPTION
      "This object specifies the entity's Bridge Filter Table. This table maintains 
      context ID as one more index to support Multiple Instances."
   ::= {fsMIDot1dFilter 1}

fsMIDot1dFilterEntry   OBJECT-TYPE
   SYNTAX   FsMIDot1dFilterEntry
   MAX-ACCESS   not-accessible
   STATUS   current
   DESCRIPTION
      "This object specifies the information about the packets to be filtered."
   INDEX   { fsMIDot1dFutureBaseContextId, fsMIDot1dFilterNumber,
        fsMIDot1dFilterSrcAddress,
        fsMIDot1dFilterDstAddress }
   ::= { fsMIDot1dFilterTable 1 }

FsMIDot1dFilterEntry   ::=    SEQUENCE {
   fsMIDot1dFilterNumber   
Integer32,
   fsMIDot1dFilterSrcAddress   
MacAddress,
   fsMIDot1dFilterSrcMask   
MacAddress,
   fsMIDot1dFilterDstAddress   
MacAddress,
   fsMIDot1dFilterDstMask   
MacAddress,
   fsMIDot1dFilterPermiss   
INTEGER
   }

fsMIDot1dFilterNumber   OBJECT-TYPE
   SYNTAX   Integer32 (1..99)
   MAX-ACCESS   not-accessible
   STATUS   current
   DESCRIPTION
      "This object specifies the number assigned to this particular filter table."
   ::= { fsMIDot1dFilterEntry 1 }

fsMIDot1dFilterSrcAddress   OBJECT-TYPE
   SYNTAX   MacAddress
   MAX-ACCESS   not-accessible
   STATUS   current
   DESCRIPTION
      "This object specifies the Source address of the packet to be filtered."
   ::= { fsMIDot1dFilterEntry 2 }

fsMIDot1dFilterSrcMask   OBJECT-TYPE
   SYNTAX   MacAddress
   MAX-ACCESS   read-create
   STATUS   current
   DESCRIPTION
      "This object specifies the Mask to be used with the Source address. F's in the mask
      correspond to bits to be ignored while comparing the source
      address in the packet with that in the filter entry."
   DEFVAL   { 'FFFFFFFFFFFF'h }
   ::= { fsMIDot1dFilterEntry 3 }

fsMIDot1dFilterDstAddress   OBJECT-TYPE
   SYNTAX   MacAddress
   MAX-ACCESS   not-accessible
   STATUS   current
   DESCRIPTION
      "This object specifies the Destination address of the packet to be filtered."
   ::= { fsMIDot1dFilterEntry 4 }

fsMIDot1dFilterDstMask   OBJECT-TYPE
   SYNTAX   MacAddress
   MAX-ACCESS   read-create
   STATUS   current
   DESCRIPTION
      "This object specifies the Mask to be used with the Destination address. F's in 
      the mask correspond to bits to be ignored while comparing the 
      destination address in the packet with that in the filter 
      entry."
   DEFVAL   { 'FFFFFFFFFFFF'h }
   ::= { fsMIDot1dFilterEntry 5 }

fsMIDot1dFilterPermiss   OBJECT-TYPE
   SYNTAX   INTEGER { 
      block   (1),
      allow   (2), 
      invalid (3)
      }
   MAX-ACCESS   read-create
   STATUS   current
   DESCRIPTION
      "This object specifies Specifies whether to discard the packet or not when a match
      occurs with the source and destination addresses of this filter
      entry. Setting this variable to 'invalid' amounts to 
      invalidating the filter list entry."
        DEFVAL { allow }
   ::= { fsMIDot1dFilterEntry 6 }


-- The Bridge Multicast List MIB

-- Multicast List number for an interface (member of a group) allows 
-- to transmit only a specified set of multicast frames through an interface
-- (member of a group).
-- A frame in which the destination address with multicast bit set is 
-- allowed(excluding  broadcast address) to forward through an interface 
-- (member of a group) only if the multicast address is one among the set 
-- of multicast addresses assigned  to the interface through the multicast 
-- list number. Assigning a multicast list number of zero to the 
-- interface removes the multicast frame filtering for the interface 
-- (member of a group).

-- Each multicast list number is associated with a set of Multicast addresses.


fsMIDot1dMcastTable   OBJECT-TYPE
    SYNTAX   SEQUENCE OF FsMIDot1dMcastEntry
    MAX-ACCESS   not-accessible
    STATUS   current
    DESCRIPTION
        "This object specifies the entity's Bridge Multicast table. This table maintains 
	context ID as one more index to support Multiple Instances."
    ::=  { fsMIDot1dMcast 1 }

fsMIDot1dMcastEntry   OBJECT-TYPE
    SYNTAX   FsMIDot1dMcastEntry
    MAX-ACCESS   not-accessible
    STATUS   current
    DESCRIPTION
        "This object specifies the Contains the multicast address."
    INDEX   { fsMIDot1dFutureBaseContextId, fsMIDot1dMcastMacaddress, 
              fsMIDot1dMlistNumber        }
    ::= { fsMIDot1dMcastTable 1 }

FsMIDot1dMcastEntry       ::=    SEQUENCE {
    fsMIDot1dMlistNumber        
Integer32,
    fsMIDot1dMcastMacaddress    
MacAddress,
    fsMIDot1dMcastPermiss       
INTEGER
    } 

fsMIDot1dMlistNumber   OBJECT-TYPE
    SYNTAX   Integer32 (1..99)
    MAX-ACCESS   not-accessible
    STATUS   current
    DESCRIPTION
        "This object specifies the Number assigned to this particular multicast table."
    ::=  { fsMIDot1dMcastEntry 1 }

fsMIDot1dMcastMacaddress   OBJECT-TYPE
    SYNTAX   MacAddress
    MAX-ACCESS   not-accessible
    STATUS   current
    DESCRIPTION
        "This object specifies the multicast macaddress that is valid for an interface."
    ::=  { fsMIDot1dMcastEntry 2 }

fsMIDot1dMcastPermiss     OBJECT-TYPE
   SYNTAX   INTEGER { 
      block   (1),
      allow   (2), 
      invalid (3)
      }
   MAX-ACCESS   read-create
   STATUS   current
   DESCRIPTION
      "This object Specifies whether to discard the packet with this multicast address
      or to forward it.  Setting this variable to 'invalid' amounts to 
      invalidating the multicast entry."
 DEFVAL { allow }
   ::= { fsMIDot1dMcastEntry  3 }

END

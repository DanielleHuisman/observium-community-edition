-- Copyright (C) 2006-2016 Aricent. All Rights Reserved

-- $Id: fseoamex.mib,v 1.8 2016/03/24 10:16:12 siva Exp $

-- EOAM Proprietary MIB Definition 
 
-- This MIB contains tables used to configure a switch running 
-- EOAM in addition to the standard MIB.
 
   EOAM-MIB DEFINITIONS ::= BEGIN 
 
   IMPORTS 
      MODULE-IDENTITY, OBJECT-TYPE,  
      enterprises, Integer32, Unsigned32       FROM SNMPv2-SMI 
      TEXTUAL-CONVENTION                       FROM SNMPv2-TC;
      --ifIndex                                  FROM IF-MIB; 
 
      fseoam MODULE-IDENTITY 
         LAST-UPDATED "201209050000Z" 
         ORGANIZATION "ARICENT COMMUNICATIONS SOFTWARE" 
         CONTACT-INFO "support@aricent.com"
         DESCRIPTION 
            " The proprietary MIB module for EOAM. " 
	 REVISION "201209050000Z"
         DESCRIPTION 
            " The proprietary MIB module for EOAM. " 
      ::=  { enterprises futuresoftware (2076) 121 } 
  
 --
 -- Textual conventions for OAM MIB
 --
 EoamOui ::= TEXTUAL-CONVENTION
       STATUS       current
       DESCRIPTION 
         "24-bit Organizationally Unique Identifier.  Information on
         OUIs can be found in IEEE 802-2001 [802-2001] Clause 9."
       SYNTAX       OCTET STRING(SIZE(3))
 
-- ------------------------------------------------------------  
-- groups in the MIB  
-- ------------------------------------------------------------ 
 
      fsEoamSystem  OBJECT IDENTIFIER ::= { fseoam 1 } 
 
-- ------------------------------------------------------------------ 
-- The EOAM System Group 
-- ------------------------------------------------------------------ 
 
      fsEoamSystemControl OBJECT-TYPE 
          SYNTAX      INTEGER  { start(1), shutdown(2) } 
          MAX-ACCESS  read-write 
          STATUS      current 
          DESCRIPTION 
              "This object specifies the administrative system control status of Ethernet
               OAM module. The value 'start' (1) indicates that all
               resources required by EOAM module should be allocated 
               and EOAM should be supported in the device on all ports. 
               The value 'shutdown' (2) indicates that EOAM should be 
               shutdown in the device on all ports and all allocated 
               memory must be released."   
          DEFVAL  { start }
          ::= { fsEoamSystem 1 } 
          
      fsEoamModuleStatus OBJECT-TYPE 
          SYNTAX      INTEGER  { enabled(1), disabled(2) } 
          MAX-ACCESS  read-write
          STATUS      current 
          DESCRIPTION 
             "This object specifies the administrative module status of Ethernet OAM module. 
              This enables or disables EOAM in the system. A value of 
              'enabled' (1) indicates that EOAM is enabled in the device
              and can be enabled port-wise. A value of 'disabled' (2) 
              indicates that EOAM is disabled in the device and also
              disabled on all ports." 
          DEFVAL  { disabled }
          ::= { fsEoamSystem 2 } 

      fsEoamErrorEventResend OBJECT-TYPE 
          SYNTAX      Unsigned32 (1..10) 
          MAX-ACCESS  read-write 
          STATUS      current 
          DESCRIPTION 
             "This object specifies the number of times an error
              event OAMPDU will be sent repeatedly. To avoid loss of 
              OAMPDUs on faulty links, the events like symbol period,
              frame -period, frame, frame-secs-summary and organisation
              specific event are sent repeatedly."
          DEFVAL  { 10 } 
          ::= { fsEoamSystem 3 } 
  
       fsEoamOui OBJECT-TYPE
          SYNTAX      EoamOui
          MAX-ACCESS  read-write
          STATUS      current
          DESCRIPTION 
             "This object specifies the Organizational Unique Identifier of the local EOAM 
              Client. This will be sent in the Information OAMPDU in 
              Local Information TLV.
              Default for this object will be the first three bytes 
              of system MAC address."
          ::= { fsEoamSystem 4 }

      fsEoamTraceOption OBJECT-TYPE 
          SYNTAX      Integer32
          MAX-ACCESS  read-write 
          STATUS      current 
          DESCRIPTION 
             "This object is used to enable trace statements in  
              Ethernet OAM module. 
              A four byte integer is used for enabling the trace level.  
              Each bit in the four byte integer represents a particular  
              trace level.  
              The mapping between the bit positions & the trace level is  
              as follows:  
                  Bit 0 - Init and Shutdown traces 
                  Bit 1 - Management traces 
                  Bit 2 - Data Path traces 
                  Bit 3 - Control Plane traces 
                  Bit 4 - Packet Dump traces 
                  Bit 5 - Traces related to all resources except buffers 
                  Bit 6 - All Failure traces 
                  Bit 7 - Buffer allocation/release traces 
 
                  Bit 16 - EOAM Function Entry traces
                  Bit 17 - EOAM Function Exit traces
                  Bit 18 - EOAM Critical traces 
                  Bit 19 - EOAM Discovery traces 
                  Bit 20 - EOAM Remote loopback traces 
                  Bit 21 - EOAM Link monitoring module traces 
                  Bit 22 - EOAM MIB variable req/response traces 
                  Bit 23 - EOAM Remote Failure Indication traces 
                  Bit 24 - EOAM Multiplexer / Parser traces 
                  Bit 25 - EOAM Redundancy traces 
 
              The remaining bits are unused. Combination of levels are  
              also allowed. 
 
              For example if the bits 19 and 20 are set, then the trace 
              statement related to discovery and remote loopback related
              messages will be printed. 
 
              The user has to enter the corresponding integer value for the 
              bits set. For example if bits 8 and 9 are to be set, then user
              has to give the value 0x300." 
       DEFVAL { '00040000'H }
          ::= { fsEoamSystem 5 } 

 END

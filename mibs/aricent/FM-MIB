-- Copyright (C) 2006-2012 Aricent Group . All Rights Reserved

-- $Id: fsfm.mib,v 1.6 2013/11/05 10:57:52 siva Exp $

-- Fault Management Proprietary MIB Definition 
 
-- This MIB contains tables used to configure a switch running FM

 
   FM-MIB DEFINITIONS ::= BEGIN 
 
   IMPORTS 
      MODULE-IDENTITY, OBJECT-TYPE,  
      enterprises, Integer32, Unsigned32       FROM SNMPv2-SMI 
      DisplayString                            FROM SNMPv2-TC 
      ifIndex                                  FROM IF-MIB; 
 
 
      fsfm MODULE-IDENTITY 
         LAST-UPDATED "201209050000Z" 
         ORGANIZATION "ARICENT COMMUNICATIONS SOFTWARE" 
         CONTACT-INFO "support@aricent.com"
         DESCRIPTION 
            " The proprietary MIB module for FM module. " 
	 REVISION "201209050000Z"
         DESCRIPTION 
            " The proprietary MIB module for FM module. " 
      ::=  { enterprises futuresoftware (2076) 122 } 
 
 
-- ------------------------------------------------------------  
-- groups in the MIB  
-- ------------------------------------------------------------ 
 
      fsFmSystem       OBJECT IDENTIFIER ::= { fsfm 1 } 
      fsFmLinkEvent    OBJECT IDENTIFIER ::= { fsfm 2 } 
      fsFmLoopback     OBJECT IDENTIFIER ::= { fsfm 3 } 
      fsFmVarRetrieval OBJECT IDENTIFIER ::= { fsfm 4 } 

      fsFmSystemControl OBJECT-TYPE 
          SYNTAX      INTEGER  { start(1),
                                 shutdown(2) } 
          MAX-ACCESS  read-write 
          STATUS      current 
          DESCRIPTION 
              "Fault Management module is shutdown or started through 
               this object. 
               When set to 'start', resources required by the  
               FM module is allocated and the module starts running.   
               When set to 'shutdown', all the resources are released back 
               to the system and the module stops running."
          DEFVAL  { shutdown }
          ::= { fsFmSystem 1 } 
          
      fsFmModuleStatus OBJECT-TYPE 
          SYNTAX      INTEGER  { enabled(1), 
                                 disabled(2) } 
          MAX-ACCESS  read-write
          STATUS      current 
          DESCRIPTION 
             "The module status of the Fault Management module.
              The value enabled(1) indicates the Fault Management module 
              is currently enabled in the system.
              The value disabled(2) indicates the Fault Management module
              is currently disabled in the system."
          DEFVAL  { disabled }
          ::= { fsFmSystem 2 } 

      fsFmTraceOption OBJECT-TYPE 
          SYNTAX      Integer32
          MAX-ACCESS  read-write 
          STATUS      current 
          DESCRIPTION 
             "This object is used to enable trace statements in  
              Fault Management module. 
              A four byte integer is used for enabling the trace level.  
              Each bit in the four byte integer represents a particular  
              trace level.  
              The mapping between the bit positions & the trace level is  
              as follows:  
                  Bit  0 - Init and Shutdown traces 
                  Bit  1 - Management traces 
                  Bit  2 - Reserved 
                  Bit  3 - Control plane traces
                  Bit  4 - Packet Dump traces 
                  Bit  5 - Traces related to all resources except buffers 
                  Bit  6 - All Failure traces 
                  Bit  7 - Buffer allocation/release traces 
 
                  Bit 16 - Function Entry traces
                  Bit 17 - Function exit traces
                  Bit 18 - Critical traces 
                  Bit 19 - Remote Loopback test 
                  Bit 20 - Fault Event trigger traces 
                  Bit 21 - Event reception traces
                  Bit 22 - Variable request/response traces 
 
              The remaining bits are unused. Combination of levels are  
              also allowed. 
 
              For example if the bits 19 and 20 are set, then the trace 
              statement related to remote loopback test and event trigger
              trace messages will be printed. 
 
              The user has to enter the corresponding integer value for the 
              bits set. For example if bits 8 and 9 are to be set, then user
              has to give the value 0x300." 

       DEFVAL { '00040000'H }
          ::= { fsFmSystem 3 } 
          
-- ------------------------------------------------------------------ 
-- The FM Link Event Group
-- ------------------------------------------------------------------ 
 
      fsFmLinkEventTable OBJECT-TYPE 
          SYNTAX      SEQUENCE OF FsFmLinkEventEntry 
          MAX-ACCESS  not-accessible 
          STATUS      current 
          DESCRIPTION 
            "This table contains objects to configure Link Events 
             on the interfaces." 
          ::= { fsFmLinkEvent 1 } 
 
      fsFmLinkEventEntry OBJECT-TYPE 
          SYNTAX      FsFmLinkEventEntry 
          MAX-ACCESS  not-accessible 
          STATUS      current 
          DESCRIPTION 
            "This table contains action to be taken for each link 
             event."
             INDEX       { ifIndex }
          ::= { fsFmLinkEventTable 1 } 
 
      FsFmLinkEventEntry ::= SEQUENCE { 
          fsFmSymPeriodAction            INTEGER,
          fsFmFrameAction                INTEGER,
          fsFmFramePeriodAction          INTEGER,
          fsFmFrameSecSummAction         INTEGER,
          fsFmCriticalEventAction        INTEGER,
          fsFmDyingGaspAction            INTEGER,
          fsFmLinkFaultAction            INTEGER
        } 
             
      fsFmSymPeriodAction   OBJECT-TYPE 
          SYNTAX      INTEGER { none (1), 
                                warning (2) } 
          MAX-ACCESS  read-write
          STATUS      current 
          DESCRIPTION 
            "Action to be taken when a Symbol Period Event Notification
             is received. 
             'none' specifies no action will be taken when this event 
             is received.
             'warning' specifies that a syslog message will be generated
             when this event is received."
          DEFVAL { warning }
          ::= { fsFmLinkEventEntry 1 }
            
      fsFmFrameAction   OBJECT-TYPE 
          SYNTAX      INTEGER { none (1), 
                                warning (2) } 
          MAX-ACCESS  read-write
          STATUS      current 
          DESCRIPTION 
            "Action to be taken when a Frame Event Notification
             is received. 
             'none' specifies no action will be taken when this event 
             is received.
             'warning' specifies that a syslog message will be generated
             when this event is received."
          DEFVAL { warning }
          ::= { fsFmLinkEventEntry 2 }
           
      fsFmFramePeriodAction   OBJECT-TYPE 
          SYNTAX      INTEGER { none (1), 
                                warning (2) } 
          MAX-ACCESS  read-write
          STATUS      current 
          DESCRIPTION 
            "Action to be taken when a Frame Period Event Notification
             is received. 
             'none' specifies no action will be taken when this event 
             is received.
             'warning' specifies that a syslog message will be generated
             when this event is received."
          DEFVAL { warning }
          ::= { fsFmLinkEventEntry 3 }

      fsFmFrameSecSummAction   OBJECT-TYPE 
          SYNTAX      INTEGER { none (1), 
                                warning (2) } 
          MAX-ACCESS  read-write
          STATUS      current 
          DESCRIPTION 
            "Action to be taken when a Frame Seconds summary Event 
             Notification is received. 
             'none' specifies no action will be taken when this event 
             is received.
             'warning' specifies that a syslog message will be generated
             when this event is received."
          DEFVAL { warning }
          ::= { fsFmLinkEventEntry 4 }
          
      fsFmCriticalEventAction   OBJECT-TYPE 
          SYNTAX      INTEGER { none (1), 
                                warning (2),
                                block (3) } 
          MAX-ACCESS  read-write
          STATUS      current 
          DESCRIPTION 
            "Action to be taken when a Critical Event occurs at the
             local interface and notification is received from
             remote interface.
             'none' specifies no action will be taken when this event 
             is received.
             'warning' specifies that a syslog message will be generated
             when this event is received.
	     'block' specifies that block the data tarffic except the OAM
             PDU when this event is received."
          DEFVAL { warning }
          ::= { fsFmLinkEventEntry 5 }
        
      fsFmDyingGaspAction      OBJECT-TYPE 
          SYNTAX      INTEGER { none (1), 
                                warning (2),
                                block (3) } 
          MAX-ACCESS  read-write
          STATUS      current 
          DESCRIPTION 
            "Action to be taken when a Dying Gasp event occurs at the
             local interface and notification is received from
             remote interface.
             'none' specifies no action will be taken when this event 
             is received.
             'warning' specifies that a syslog message will be generated
             when this event is received.
	     'block' specifies that block the data tarffic except the OAM
             PDU when this event is received."
          DEFVAL { warning }
          ::= { fsFmLinkEventEntry 6 }
         
      fsFmLinkFaultAction   OBJECT-TYPE 
          SYNTAX      INTEGER { none (1), 
                                warning (2),
                                block (3) } 
          MAX-ACCESS  read-write
          STATUS      current 
          DESCRIPTION 
            "Action to be taken when a Link Fault Event occurs at the
             local interface and notification is received from
             remote interface.
             'none' specifies no action will be taken when this event 
             is received.
             'warning' specifies that a syslog message will be generated
             when this event is received.
	     'block' specifies that block the data tarffic except the OAM
             PDU when this event is received."
          DEFVAL { warning }
          ::= { fsFmLinkEventEntry 7 }
         
-- ------------------------------------------------------------------ 
-- The FM Loopback Group 
-- ------------------------------------------------------------------ 
 
-- Loopback test configuration and current statistics table
      fsFmLoopbackTable OBJECT-TYPE 
          SYNTAX      SEQUENCE OF FsFmLoopbackEntry 
          MAX-ACCESS  not-accessible 
          STATUS      current 
          DESCRIPTION 
            "This table contains objects to configure Remote Loopback
             mode and loopback tests." 
          ::= { fsFmLoopback 1 } 
 
      fsFmLoopbackEntry OBJECT-TYPE 
          SYNTAX      FsFmLoopbackEntry 
          MAX-ACCESS  not-accessible 
          STATUS      current 
          DESCRIPTION 
            "This table contains remote loopback configuration and
             loopback test configuration."
             INDEX       { ifIndex }
          ::= { fsFmLoopbackTable 1 } 
 
      FsFmLoopbackEntry ::= SEQUENCE { 
          fsFmLoopbackStatus             INTEGER,
          fsFmLBTestPattern              OCTET STRING,
          fsFmLBTestPktSize              Unsigned32,
          fsFmLBTestCount                Unsigned32,
          fsFmLBTestWaitTime             Integer32,
          fsFmLBTestCommand              INTEGER,
          fsFmLBTestStatus               INTEGER,
          fsFmLBTestStartTimestamp       DisplayString,
          fsFmLBTestEndTimestamp         DisplayString,
          fsFmLBTestTxCount              Unsigned32,
          fsFmLBTestRxCount              Unsigned32,
          fsFmLBTestMatchCount           Unsigned32
        } 
            
      fsFmLoopbackStatus OBJECT-TYPE 
          SYNTAX      INTEGER { noLoopback (1), 
                                remoteLoopback (2),
                                unknown (3) } 
 
          MAX-ACCESS  read-only 
          STATUS      current 
          DESCRIPTION 
            "The loopback status of the local interface. This status is
             obtained from the local EOAM Client. When operating in 
             normal mode with no loopback in progress, the status reads
             noLoopback(1).  
             If the local OAM client knows that the remote OAM entity is in
             loopback mode , the status is remoteLoopback(2).    
             The unknown(3) status indicates the loopback status is not
             known." 
          DEFVAL { unknown }
          ::= { fsFmLoopbackEntry 1 }

      fsFmLBTestPattern OBJECT-TYPE 
          SYNTAX      OCTET STRING (SIZE (4))
          MAX-ACCESS  read-write
          STATUS      current 
          DESCRIPTION 
            "Test Pattern for the remote loopback test. The default pattern
             of the test data will be 'F0F0F0F0'H " 
          ::= { fsFmLoopbackEntry 2 }

      fsFmLBTestPktSize OBJECT-TYPE 
          SYNTAX      Unsigned32 (64..1500)
          MAX-ACCESS  read-write
          STATUS      current 
          DESCRIPTION 
            "Test packet size for the remote loopback test" 
          DEFVAL { 64 }
          ::= { fsFmLoopbackEntry 3 }

      fsFmLBTestCount OBJECT-TYPE 
          SYNTAX      Unsigned32 (1..1000)
          MAX-ACCESS  read-write
          STATUS      current 
          DESCRIPTION 
            "Number of Test packets to be sent for the remote
             loopback test" 
          DEFVAL { 10 }
          ::= { fsFmLoopbackEntry 4 }
  
      fsFmLBTestWaitTime OBJECT-TYPE 
          SYNTAX      Integer32 (1..10) 
          MAX-ACCESS  read-write 
          STATUS      current 
          DESCRIPTION 
             "This timer is started after sending the last test packet.
              The Fault management module will wait until this timer
              expires or the packet reception counter is equal to the 
              transmission counter. This timer (in seconds) denotes the
              maximum time a packet can take to get looped back." 
          DEFVAL  { 5 } 
          ::= { fsFmLoopbackEntry 5 } 
            

      fsFmLBTestCommand OBJECT-TYPE 
          SYNTAX      INTEGER  { noLoopbackTest(1),
                                 startLoopbackTest(2) }
          MAX-ACCESS  read-write
          STATUS      current 
          DESCRIPTION 
            "This attribute initiates remote loopback test with
             an EOAM peer.  Writing startLoopbackTest(2) to this attribute
             cause the fault management send loopback test packets with
             defined test pattern, size and count.
             Writing noLoopbackTest to this attribute has no effect.  
      
             Writes to this attribute are ignored unless the fsFmLoopbackStatus
             of this interface is 'remoteLoopback'.
                              
             The attribute always returns noLoopbackTest on a read.
             " 
          ::= { fsFmLoopbackEntry 6 } 
            
      fsFmLBTestStatus OBJECT-TYPE 
          SYNTAX      INTEGER  { notInitiated(1), 
                                 loopbackTestInprogress(2),
                                 loopbackTestCompleted(3) }
          MAX-ACCESS  read-only
          STATUS      current 
          DESCRIPTION 
            "This attribute indicates the status of the remote loopback 
             test.
             'notInitiated' indicates that the loopback has not been 
             initiated yet.
             'loopbackbTestInprogress' indicates that the loopback test is in
             progress.
             'loopbackbTestCompleted' indicates that the loopback test has been
             completed."

          ::= { fsFmLoopbackEntry 7 } 
  
      fsFmLBTestStartTimestamp OBJECT-TYPE 
          SYNTAX      DisplayString (SIZE(40))
          MAX-ACCESS  read-only
          STATUS      current 
          DESCRIPTION 
            "Start timestamp of the current loopback test." 
          ::= { fsFmLoopbackEntry 8 }
  
      fsFmLBTestEndTimestamp OBJECT-TYPE 
          SYNTAX      DisplayString (SIZE(40))
          MAX-ACCESS  read-only
          STATUS      current 
          DESCRIPTION 
            "End timestamp of the current loopback test." 
          ::= { fsFmLoopbackEntry 9 }

      fsFmLBTestTxCount OBJECT-TYPE 
          SYNTAX      Unsigned32
          MAX-ACCESS  read-only
          STATUS      current 
          DESCRIPTION 
            "Statistics of number of Test packets transmitted during
             current loopback test." 
          ::= { fsFmLoopbackEntry 10 }
 
      fsFmLBTestRxCount OBJECT-TYPE 
          SYNTAX      Unsigned32
          MAX-ACCESS  read-only
          STATUS      current 
          DESCRIPTION 
           "Statistics of number of Test packets received during
            current loopback test." 
          ::= { fsFmLoopbackEntry 11 }
 
      fsFmLBTestMatchCount OBJECT-TYPE 
          SYNTAX      Unsigned32
          MAX-ACCESS  read-only
          STATUS      current 
          DESCRIPTION 
            "Statistics of number of Test packets that matched with the
             test pattern sent during current loopback test."
          ::= { fsFmLoopbackEntry 12 }
 
-- Loopback test previous session statistics table
      fsFmLBStatsTable OBJECT-TYPE 
          SYNTAX      SEQUENCE OF FsFmLBStatsEntry 
          MAX-ACCESS  not-accessible 
          STATUS      current 
          DESCRIPTION 
            "This table contains statistics of the last remote loopback
             test." 
          ::= { fsFmLoopback 2 } 
 
      fsFmLBStatsEntry OBJECT-TYPE 
          SYNTAX      FsFmLBStatsEntry 
          MAX-ACCESS  not-accessible 
          STATUS      current 
          DESCRIPTION 
            "This table contains remote loopback test results of the
             last session. This table is updated every time a new loopback
             test session is started. The current fsFmLBTestTxCount,
             fsFmLBTestRxCount and fsFmLBTestMatchCount are copied to
             this table before starting the new test."
             INDEX       { ifIndex }
          ::= { fsFmLBStatsTable 1 } 
 
      FsFmLBStatsEntry ::= SEQUENCE { 
          fsFmLBStatsStartTimestamp      DisplayString,
          fsFmLBStatsEndTimestamp        DisplayString,
          fsFmLBStatsTxCount             Unsigned32,
          fsFmLBStatsRxCount             Unsigned32,
          fsFmLBStatsMatchCount          Unsigned32
        } 
  
      fsFmLBStatsStartTimestamp OBJECT-TYPE 
          SYNTAX      DisplayString (SIZE(40))
          MAX-ACCESS  read-only
          STATUS      current 
          DESCRIPTION 
            "Start timestamp of the current loopback test." 
          ::= { fsFmLBStatsEntry 1 }
  
      fsFmLBStatsEndTimestamp OBJECT-TYPE 
          SYNTAX       DisplayString (SIZE(40))
          MAX-ACCESS  read-only
          STATUS      current 
          DESCRIPTION 
            "End timestamp of the current loopback test." 
          ::= { fsFmLBStatsEntry 2 }

 
      fsFmLBStatsTxCount OBJECT-TYPE 
          SYNTAX      Unsigned32
          MAX-ACCESS  read-only
          STATUS      current 
          DESCRIPTION 
            "Statistics of number of Test packets transmitted during
             last loopback test." 
          ::= { fsFmLBStatsEntry 3 }
 
      fsFmLBStatsRxCount OBJECT-TYPE 
          SYNTAX      Unsigned32
          MAX-ACCESS  read-only
          STATUS      current 
          DESCRIPTION 
           "Statistics of number of Test packets received during
            last loopback test." 
          ::= { fsFmLBStatsEntry 4 }
 
      fsFmLBStatsMatchCount OBJECT-TYPE 
          SYNTAX      Unsigned32
          MAX-ACCESS  read-only
          STATUS      current 
          DESCRIPTION 
            "Statistics of number of Test packets that matched with the
             test pattern sent."
          ::= { fsFmLBStatsEntry 5 }
 

-- ------------------------------------------------------------------ 
-- The FM Variable Retrieval Group 
-- ------------------------------------------------------------------ 

-- This table contains objects configure the variable request and to
-- clear variable response table

      fsFmVarRetrievalTable OBJECT-TYPE 
          SYNTAX      SEQUENCE OF FsFmVarRetrievalEntry 
          MAX-ACCESS  not-accessible 
          STATUS      current 
          DESCRIPTION 
            "This table contains objects to configure MIB  variable 
             requests to be sent and clear variable response table" 
          ::= { fsFmVarRetrieval 1 } 
 
      fsFmVarRetrievalEntry OBJECT-TYPE 
          SYNTAX      FsFmVarRetrievalEntry 
          MAX-ACCESS  not-accessible 
          STATUS      current 
          DESCRIPTION 
            "This table contains the list of Branch and Leaves
             to be sent out for a Variable Request"
             INDEX       { ifIndex}
          ::= { fsFmVarRetrievalTable 1 } 
 
      FsFmVarRetrievalEntry ::= SEQUENCE { 
          fsFmVarRetrievalMaxVar               Unsigned32,
          fsFmVarRetrievalRequest              DisplayString,
          fsFmVarRetrievalClearResponse        INTEGER
        } 
 
       fsFmVarRetrievalMaxVar OBJECT-TYPE 
          SYNTAX      Unsigned32 (1..100)
          MAX-ACCESS  read-write
          STATUS      current 
          DESCRIPTION 
             "This attribute specifies the maximum number of Variable
              descriptors that can be sent on the interface" 
 
          DEFVAL  { 10 } 
          ::= { fsFmVarRetrievalEntry 1 }
 
      fsFmVarRetrievalRequest  OBJECT-TYPE 
          SYNTAX      DisplayString (SIZE(1..255))
          MAX-ACCESS  read-write
          STATUS      current 
          DESCRIPTION 
             "This attribute specifies the Variable descriptor string
              that will be sent in the Variable Request OAMPDU. Setting 
              this attribute also sends the variable request OAMPDU.

              The format of the string should be 'BL:BL:...:00', where
              'B' - stands for CMIP Branch (one-byte) 
              'L' - stands for CMIP Leaf (two bytes) of the CMIP variable defined 
                    under Clause 30 of IEEE specification."
          ::= { fsFmVarRetrievalEntry 2 }

      fsFmVarRetrievalClearResponse OBJECT-TYPE 
          SYNTAX      INTEGER { notCleared(1),
                                clearResponseLog(2) }
          MAX-ACCESS  read-write
          STATUS      current 
          DESCRIPTION 
             "This attribute clears the variable response log on
              the specified interface. Writing 'clearResponseLog' to 
              this variable cause the 'fsFmVarResponseTable' to be cleared.
              Writing 'notCleared' to this attribute has no effect.  
     
              This attribute always returns 'notCleared' on a read." 
 
          ::= { fsFmVarRetrievalEntry 3 }

-- This table contains objects to store the variable responses
-- received

      fsFmVarResponseTable OBJECT-TYPE 
          SYNTAX      SEQUENCE OF FsFmVarResponseEntry 
          MAX-ACCESS  not-accessible 
          STATUS      current 
          DESCRIPTION 
            "This table contains the log of the Variable responses 
             received" 
          ::= { fsFmVarRetrieval 3 } 
 
      fsFmVarResponseEntry OBJECT-TYPE 
          SYNTAX      FsFmVarResponseEntry 
          MAX-ACCESS  not-accessible 
          STATUS      current 
          DESCRIPTION 
            "This table contains the list of Variable responses
             received on each interface. If the response is too long,
             it is split and stored in multiple parts"
             INDEX       { ifIndex, fsFmVarResponseId }
          ::= { fsFmVarResponseTable 1 } 
 
      FsFmVarResponseEntry ::= SEQUENCE { 
          fsFmVarResponseId                  Unsigned32,
          fsFmVarResponseRx1                 DisplayString,
          fsFmVarResponseRx2                 DisplayString,
          fsFmVarResponseRx3                 DisplayString,
          fsFmVarResponseRx4                 DisplayString,
          fsFmVarResponseRx5                 DisplayString,
          fsFmVarResponseRx6                 DisplayString
        } 
 
      fsFmVarResponseId  OBJECT-TYPE 
          SYNTAX      Unsigned32
          MAX-ACCESS  not-accessible
          STATUS      current 
          DESCRIPTION 
             "An arbitrary integer for identifiying more than one
              Response received on an interface"
          ::= { fsFmVarResponseEntry 1 } 

      fsFmVarResponseRx1  OBJECT-TYPE 
          SYNTAX      DisplayString (SIZE(1..255))
          MAX-ACCESS  read-only 
          STATUS      current 
          DESCRIPTION 
             "This is the data received on the Variable response. If the
              received response is more than 255 bytes, it will split into
              multiple parts and stored"
          ::= { fsFmVarResponseEntry 2 } 
 
      fsFmVarResponseRx2  OBJECT-TYPE 
          SYNTAX      DisplayString (SIZE(1..255))
          MAX-ACCESS  read-only 
          STATUS      current 
          DESCRIPTION 
             "This is the data received on the Variable response. If the
              received response is more than 255 bytes, it will split into
              multiple parts and stored"
          ::= { fsFmVarResponseEntry 3 } 

      fsFmVarResponseRx3  OBJECT-TYPE 
          SYNTAX      DisplayString (SIZE(1..255))
          MAX-ACCESS  read-only 
          STATUS      current 
          DESCRIPTION 
             "This is the data received on the Variable response. If the
              received response is more than 255 bytes, it will split into
              multiple parts and stored"
          ::= { fsFmVarResponseEntry 4 } 

      fsFmVarResponseRx4  OBJECT-TYPE 
          SYNTAX      DisplayString (SIZE(1..255))
          MAX-ACCESS  read-only 
          STATUS      current 
          DESCRIPTION 
             "This is the data received on the Variable response. If the
              received response is more than 255 bytes, it will split into
              multiple parts and stored"
          ::= { fsFmVarResponseEntry 5 } 

      fsFmVarResponseRx5  OBJECT-TYPE 
          SYNTAX      DisplayString (SIZE(1..255))
          MAX-ACCESS  read-only 
          STATUS      current 
          DESCRIPTION 
             "This is the data received on the Variable response. If the
              received response is more than 255 bytes, it will split into
              multiple parts and stored"
          ::= { fsFmVarResponseEntry 6 } 
 
      fsFmVarResponseRx6  OBJECT-TYPE 
          SYNTAX      DisplayString (SIZE(1..255))
          MAX-ACCESS  read-only 
          STATUS      current 
          DESCRIPTION 
             "This is the data received on the Variable response. If the
              received response is more than 255 bytes, it will split into
              multiple parts and stored"
          ::= { fsFmVarResponseEntry 7 } 
END

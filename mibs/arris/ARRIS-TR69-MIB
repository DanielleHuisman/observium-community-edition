ARRIS-TR69-MIB DEFINITIONS ::= BEGIN

IMPORTS
   MODULE-IDENTITY,
   OBJECT-TYPE,
   Integer32,
   Unsigned32,
   Counter32,
   Counter64,
   IpAddress
      FROM SNMPv2-SMI
   arrisProdIdCM
      FROM ARRIS-MIB
   TruthValue, DisplayString, TimeStamp, DateAndTime, TEXTUAL-CONVENTION
      FROM SNMPv2-TC
   -- SnmpAdminString
   --    FROM SNMP-FRAMEWORK-MIB;
   InetVersion
      FROM INET-ADDRESS-MIB;

   arrisTR69Mib MODULE-IDENTITY
      LAST-UPDATED    "1311040000Z"  -- November 04, 2013
      ORGANIZATION    "ARRIS Broadband"
      CONTACT-INFO    "Rodney Osborne
                       Postal: ARRIS Broadband
                       3871 Lakefield Drive
                       Suite 300
                       Suwanee, GA 30024-1242
                       U.S.A.
                       Phone:  +1 770-473-5120
                       E-mail: rodney.osborne@arrisi.com"
      DESCRIPTION
       "This MIB module supplies the basic proprietary
        management objects for ARRIS modems."

      -- Revision history
      REVISION    "1507070000Z"  -- July 16, 2015
         DESCRIPTION
      "Add arrisTR69AcsDiscoveryDhcpOption"
      REVISION    "1502120000Z"  -- February 12, 2015
         DESCRIPTION
      "Add arrisTR69DataModelSelectIgnoreNonPuma5"
      REVISION    "1311040000Z"  -- November 04, 2013
         DESCRIPTION
      "Add arrisTR181DeviceInfo and arrisTR181DeviceInfoFirstUseDate"
      REVISION    "1304300000Z"  -- April 30, 2013
         DESCRIPTION
      "Move arrisTR69ParameterKey to OID 8 to match puma5 mib"
      REVISION    "1302050000Z"  -- January 05, 2013
         DESCRIPTION
      "NOTE: This file is now compiled under the GW SNMP Subagent
             however due to this file being defined in the Docsis vob,
             a link is supplied in the GW directories to allow this compiliation.
             Changes to this file should still be made to the
             /vobs/ti_docsis/docsis/src/common/management/snmp/
             src/mibs/vendor/arris_tr69.mib file."
      REVISION    "1304110000Z"  -- April 11, 2013
         DESCRIPTION
      "Add arrisTR69RootCertObjInstance"
      REVISION    "1303040000Z"  -- March 04, 2013
         DESCRIPTION
      "Add arrisTR69ValidateManagementServerCertificate, arrisTR69RootCertificateNumberOfEntries
          and arrisTR69RootCertificateTable"
      REVISION    "1208010000Z"  -- August 01, 2012
         DESCRIPTION
      "Used to determine the runtime data-model to be used"
      REVISION    "1201190000Z"  -- January 19, 2012
         DESCRIPTION
      "Added interface selection mib"
      REVISION    "1107180000Z"  -- July 18, 2011
         DESCRIPTION
      "Initial version"
::= { arrisProdIdCM 7 }

-- This MIB module contains the following groups.
arrisTR69MibObjects          OBJECT IDENTIFIER ::= { arrisTR69Mib 1 }
arrisTR69Base                OBJECT IDENTIFIER ::= { arrisTR69MibObjects 1 }
arrisTR69Setup               OBJECT IDENTIFIER ::= { arrisTR69MibObjects 2 }
arrisTR69Authentication        OBJECT IDENTIFIER ::= { arrisTR69MibObjects 3 }
arrisTR181MibObjects         OBJECT IDENTIFIER ::= { arrisTR69Mib 2 }
arrisTR181DeviceInfo         OBJECT IDENTIFIER ::= { arrisTR181MibObjects 1 }
arrisTR181DeviceInfoMemoryStatus         OBJECT IDENTIFIER ::= { arrisTR181DeviceInfo 2 }
arrisTR181DeviceInfoProcessStatus        OBJECT IDENTIFIER ::= { arrisTR181DeviceInfo 3 }
arrisTR181DeviceInfoProcessStatusProcess         OBJECT IDENTIFIER ::= { arrisTR181DeviceInfo 4 }

arrisTR69EnableCWMP OBJECT-TYPE
     SYNTAX INTEGER {
        disable(0),
        enable(1)
     }
     MAX-ACCESS read-write
     STATUS current
     DESCRIPTION
     "Used for overall control of the CPE's support of TR-069.
      A value of disable(0) will disable CPE support of TR-069; the TR-069
      client will not be allowed to start.
      A value of enable(1) will enable CPE support of TR-069."
      ::= { arrisTR69Base 1 }

arrisTR69AcsUrl  OBJECT-TYPE
    SYNTAX  OCTET STRING (SIZE (1..256))
    MAX-ACCESS  read-write
    STATUS      current
    DESCRIPTION
    "The URL used by the TR-069 client to connect to the ACS.
     MUST be a valid HTTP or HTTPS format."
      ::= { arrisTR69Base 2 }

arrisTR69AcsUserName  OBJECT-TYPE
    SYNTAX  OCTET STRING (SIZE (1..256))
    MAX-ACCESS  read-write
    STATUS      current
    DESCRIPTION
    "The username used by the TR-069 client for HTTP based authentication
     with the ACS."
      ::= { arrisTR69Base 3 }

arrisTR69AcsPassword  OBJECT-TYPE
    SYNTAX  OCTET STRING (SIZE (1..256))
    MAX-ACCESS  read-write
    STATUS      current
    DESCRIPTION
    "The password used by the TR-069 client for HTTP based authentication
     with the ACS.  This MIB object always returns an empty string when read."
      ::= { arrisTR69Base 4 }

arrisTR69PeriodicInformEnable OBJECT-TYPE
     SYNTAX INTEGER {
        disable(0),
        enable(1)
     }
     MAX-ACCESS read-write
     STATUS current
     DESCRIPTION
     "Determines whether or not the TR-069 client will periodically send information
      to the ACS in an Inform method call."
     ::= { arrisTR69Base 5 }

arrisTR69PeriodicInformInterval OBJECT-TYPE
     SYNTAX Unsigned32
     MAX-ACCESS read-write
     STATUS current
     DESCRIPTION
     "The interval in seconds used to periodically send information to the ACS in an
      Inform method call."
     ::= { arrisTR69Base 6 }

arrisTR69PeriodicInformTime OBJECT-TYPE
     SYNTAX DisplayString(SIZE(0..50))
     MAX-ACCESS read-write
     STATUS current
     DESCRIPTION
     "The absolute time when the TR-069 client will send periodic Inform method calls.
      Each Inform call must occur at this reference time plus or minus an integer multiple of PeriodicInformInterval.
      String format is 0000-00-00T00:00:00."
     ::= { arrisTR69Base 7 }
	 
arrisTR69ParameterKey OBJECT-TYPE
     SYNTAX  OCTET STRING (SIZE (1..32))
     MAX-ACCESS read-write
     STATUS current
     DESCRIPTION
     "ParameterKey provides the ACS a reliable and extensible means to track changes made by the ACS."
     ::= { arrisTR69Base 8 }

arrisTR69ConnectionRequestUrl  OBJECT-TYPE
    SYNTAX  OCTET STRING (SIZE (1..256))
    MAX-ACCESS  read-write
    STATUS      current
    DESCRIPTION
            "The URL used by the ACS to initiate a connection request session
             with the TR-069 client.
             MUST be an HTTP URL.      Format:  http://host:port/path
             An HTTPS URL is not valid."
      ::= { arrisTR69Base 9 }

arrisTR69ConnectionRequestUserName  OBJECT-TYPE
    SYNTAX  OCTET STRING (SIZE (1..256))
    MAX-ACCESS  read-write
    STATUS      current
    DESCRIPTION
    "The username used by the ACS for HTTP based authentication
     with the TR-069 client."
      ::= { arrisTR69Base 10 }

arrisTR69ConnectionRequestPassword  OBJECT-TYPE
    SYNTAX  OCTET STRING (SIZE (1..256))
    MAX-ACCESS  read-write
    STATUS      current
    DESCRIPTION
    "The username used by the ACS for HTTP based authentication with the 
     TR-069 client.  This MIB object always returns an empty string when read."
      ::= { arrisTR69Base 11 }

arrisTR69PersistEnable OBJECT-TYPE
     SYNTAX INTEGER {
        disable(0),
        enable(1)
     }
     MAX-ACCESS read-write
     STATUS current
     DESCRIPTION
     "Used to determine whether ACS information from the 
      configuration file is saved in dynamic non-vol memory."
     ::= { arrisTR69Setup 1 }

arrisTR69TransportInterface OBJECT-TYPE
     SYNTAX INTEGER {
        gwInterface(1),
        cmInterface(2)
     }
     MAX-ACCESS read-write
     STATUS current
     DESCRIPTION
     "Used to determine the transport interface used for all TR69
      communications"
     DEFVAL { 1 }
     ::= { arrisTR69Base 12 }

arrisTR69CwmpPort OBJECT-TYPE
     SYNTAX Unsigned32
     MAX-ACCESS read-write
     STATUS current
     DESCRIPTION
     "The port assigned for ACS initiated messaging.  This port number
     is normally included as part of the Connection Request URL.  This MIB
     object is intended to overwrite the port used in the URL."
     ::= { arrisTR69Base 13 }

arrisTR69NameSpacePriOverride OBJECT-TYPE
     SYNTAX INTEGER {
        default(1),
        cwmp10(2),
        cwmp11(3),
        cwmp12(4),
        cwmp13(5)
      }
     MAX-ACCESS read-write
     STATUS current
     DESCRIPTION
     "Used to override the default TR-069 Primary Namespace.
     The choices are as follows:
     (1) default
     (2) urn:dslforum-org:cwmp-1-0
     (3) urn:dslforum-org:cwmp-1-1
     (4) urn:dslforum-org:cwmp-1-2
     (5) urn:dslforum-org:cwmp-1-3"
     ::= { arrisTR69Base 14 }

arrisTR69NameSpaceSecOverride OBJECT-TYPE
     SYNTAX INTEGER {
        null(1),
        cwmp10(2),
        cwmp11(3),
        cwmp12(4),
        cwmp13(5)
     }
     MAX-ACCESS read-write
     STATUS current
     DESCRIPTION
     "Used to override the default TR-069 Secondary Namespace.
     The choices are as follows:
     (1) NULL
     (2) urn:dslforum-org:cwmp-1-0
     (3) urn:dslforum-org:cwmp-1-1
     (4) urn:dslforum-org:cwmp-1-2
     (5) urn:dslforum-org:cwmp-1-3"
     ::= { arrisTR69Base 15 }

arrisTR69DataModelSelect OBJECT-TYPE
     SYNTAX INTEGER {
        tr098(0),
        tr181(1)
     }
     MAX-ACCESS read-write
     STATUS current
     DESCRIPTION
     "Determine the runtime data-model utilized by the TR69 Client."
     ::= { arrisTR69Base 16 }

arrisTR69RetryMinimumWaitInterval OBJECT-TYPE
     SYNTAX Unsigned32
     MAX-ACCESS read-write
     STATUS current
     DESCRIPTION
     "Used to override CWMPRetryMinimumWaitInterval
     range minInclusive=1 maxInclusive=65535"
     ::= { arrisTR69Base 17 }

arrisTR69RetryIntervalMultiplier OBJECT-TYPE
     SYNTAX Unsigned32
     MAX-ACCESS read-write
     STATUS current
     DESCRIPTION
     "Used to override CWMPRetryIntervalMultiplier
     range minInclusive=1000 maxInclusive=65535"
     ::= { arrisTR69Base 18 }

arrisTR69ConnectRequestRealm OBJECT-TYPE
     SYNTAX DisplayString (SIZE(0..255))
     MAX-ACCESS read-write
     STATUS current
     DESCRIPTION
     "Used to override TR69 ACS connect request authentication realm"
     ::= { arrisTR69Base 19 }

arrisTR69AcsPwdAlgorithm OBJECT-TYPE
     SYNTAX INTEGER {
        hmac-sha1(1),
        hmac-sha256(2)
     }
     MAX-ACCESS read-write
     STATUS current
     DESCRIPTION
     "This object represents the Hash Based Message Authentication code (HMAC) to use 
     in the algorithm to calculate the default TR-069  managementServer.Password.  
	 The choices are HMAC-SHA1 or HMAC-SHA256.  
	 The trio of MIB objectsnecessary for this algorithm are arrisTR69AcsPwdAlgorithm, 
	 arrisTR69AcsPwdAlgorithmText, and arrisTR69AcsPwdAlgorithmKey."
     ::= { arrisTR69Base 20 }

arrisTR69AcsPwdAlgorithmText OBJECT-TYPE
     SYNTAX DisplayString (SIZE(0..255))
     MAX-ACCESS read-write
     STATUS current
     DESCRIPTION
     "This object represents the TEXT component to use in the HMAC-SHA1/HMAC-SHA256 algorithm 
     to calculate the default TR-069 managementServer.Password.  
     The trio of MIB objects necessary for this algorithm are arrisTR69AcsPwdAlgorithm, arrisTR69AcsPwdAlgorithmText, and arrisTR69AcsPwdAlgorithmKey"
     ::= { arrisTR69Base 21 }

arrisTR69AcsPwdAlgorithmKey OBJECT-TYPE
     SYNTAX DisplayString (SIZE(0..255))
     MAX-ACCESS read-write
     STATUS current
     DESCRIPTION
     "This object represents the KEY component to use in the HMAC-SHA1/HMAC-SHA256 algorithm 
     to calculate the default TR-069 managementServer.Password. 
     The trio of MIB objects necessary for this algorithm are arrisTR69AcsPwdAlgorithm, arrisTR69AcsPwdAlgorithmText, and arrisTR69AcsPwdAlgorithmKey"
     ::= { arrisTR69Base 22 }

arrisTR69TransportIPVersion OBJECT-TYPE
     SYNTAX     InetVersion
     MAX-ACCESS read-write
     STATUS current
     DESCRIPTION
     "Used to determine the IP version for TR69 transport on the gwInterface(1).  
     The options include:
     Unknown - version will be selected automatically, with preference to IPv6 if available
     IPv4 - IPv4 only
     IPv6 - IPv6 only"
     ::= { arrisTR69Base 23 }
	 
arrisTR69ProvisioningCode OBJECT-TYPE
     SYNTAX  OCTET STRING (SIZE (1..256))
     MAX-ACCESS read-write
     STATUS current
     DESCRIPTION
     "Identifier of the primary service provider and other provisioning information, 
     which MAY be used by the ACS to determine service 
     provider-specific customization and provisioning parameters."
     ::= { arrisTR69Base 24 }

arrisTR69DefaultActiveNotificationThrottle OBJECT-TYPE
     SYNTAX Unsigned32
     MAX-ACCESS read-write
     STATUS current
     DESCRIPTION
     "This parameter is used to control throttling of active notifications sent by the CPE to the ACS. 
     It defines the minimum number of seconds that the CPE MUST wait since the end of the last session 
     with the ACS before establishing a new session for the purpose of delivering an active notification"
     ::= { arrisTR69Base 25 }

arrisTR69DataModelSelectIgnoreNonPuma5 OBJECT-TYPE
     SYNTAX INTEGER {
        disable(0),
        enable(1)
     }

     MAX-ACCESS read-write
     STATUS current
     DESCRIPTION
     "Ignore the mib arrisTR69DataModelSelect  if the HW model is Puma6-based or later vintage .
      Enable(1) will ignore the arrisTR69DataModelSelect  value and force the value to TR181
      Disable(0) will allow configured value for arrisTR69DataModelSelect."
     DEFVAL { disable }
     ::= { arrisTR69Base 26 }
     
arrisTR69AcsDiscoveryDhcpOption OBJECT-TYPE
     SYNTAX INTEGER {
         none(0),
         option60(1),
         option124(2)
      }
      
      MAX-ACCESS read-write
      STATUS current
      DESCRIPTION
      "The gateway identifies itself to the DHCP server as supporting acs discovery via DHCP
      by including the string dslforum.org in DHCPv4 option 60 or 124, or DHCPv6 option 16. The
      value of this MIB selects which DHCP option carries the dslforum.org string to the dhcp
      server. A value of none indicates that neither DHCPv4 nor DHCPv6 will be used for acs
      discovery. "
      DEFVAL { none }
      ::= { arrisTR69Base 27 }

arrisTR69ValidateManagementServerCertificate OBJECT-TYPE
     SYNTAX INTEGER {
        false(0),
        true(1)
     }
     MAX-ACCESS read-write
     STATUS current
     DESCRIPTION
     "Enables or disable validation of certificates presented by SSL/TLS management servers."
     ::= { arrisTR69Authentication 1 }

arrisTR69ValidateDownloadServerCertificate OBJECT-TYPE
     SYNTAX INTEGER {
        false(0),
        true(1)
     }
     MAX-ACCESS read-write
     STATUS current
     DESCRIPTION
     "Enables or disable validation of certificates presented by SSL/TLS download servers."
     ::= { arrisTR69Authentication 2 }
	 
arrisTR69RootCertificateNumberOfEntries OBJECT-TYPE
     SYNTAX Unsigned32
     MAX-ACCESS read-only
     STATUS current
     DESCRIPTION
     "The number of entries in the X_TWC_COM_RootCertificate table."
     ::= { arrisTR69Authentication 3 }
	 
-- the Arris TR69 Root Certificate Table
arrisTR69RootCertificateTable OBJECT-TYPE
   SYNTAX      SEQUENCE OF ArrisTR69RootCertificateEntry
   MAX-ACCESS  not-accessible
   STATUS      current
   DESCRIPTION
           ""
   ::= { arrisTR69Authentication 4 }

arrisTR69RootCertificateEntry OBJECT-TYPE
   SYNTAX      ArrisTR69RootCertificateEntry
   MAX-ACCESS  not-accessible
   STATUS      current
   DESCRIPTION
           "" 
   INDEX   { arrisTR69RootCertIndex }
   ::= { arrisTR69RootCertificateTable 1 }

ArrisTR69RootCertificateEntry ::=
   SEQUENCE {
       arrisTR69RootCertIndex                 Unsigned32,
       arrisTR69RootCertEnabled               INTEGER,  
       arrisTR69RootCertCertificate           OCTET STRING,
       arrisTR69RootCertLastModif             TimeStamp,
       arrisTR69RootCertSerialNumber          DisplayString,
       arrisTR69RootCertIssuer                OCTET STRING,
       arrisTR69RootCertNotBefore             OCTET STRING,
       arrisTR69RootCertNotAfter              OCTET STRING,
       arrisTR69RootCertSubject               OCTET STRING,
       arrisTR69RootCertSubjectAlt            OCTET STRING,
       arrisTR69RootCertSignatureAlgorithm    OCTET STRING,
       arrisTR69RootCertObjInstance           Unsigned32
   }

arrisTR69RootCertIndex OBJECT-TYPE
     SYNTAX      Unsigned32
     MAX-ACCESS  not-accessible
     STATUS      current
     DESCRIPTION "Index of arrisTR69RootCertificateTable."
     ::= { arrisTR69RootCertificateEntry 1 }
   
arrisTR69RootCertEnabled OBJECT-TYPE
     SYNTAX INTEGER {
        false(0),
        true(1)
     }
     MAX-ACCESS read-write
     STATUS current
     DESCRIPTION
     "Enables or disables the use of this root certificate for validity checking."
     ::= { arrisTR69RootCertificateEntry 2 }
	 
arrisTR69RootCertCertificate OBJECT-TYPE
     SYNTAX OCTET STRING (SIZE(0..4096))
     MAX-ACCESS read-write
     STATUS current
     DESCRIPTION
     "The DER encoded certificate."
     ::= { arrisTR69RootCertificateEntry 3 }
	 
arrisTR69RootCertLastModif OBJECT-TYPE
     SYNTAX TimeStamp
     MAX-ACCESS read-create
     STATUS current
     DESCRIPTION
     "The last modification time of this certificate."
     ::= { arrisTR69RootCertificateEntry 4 }
	 
arrisTR69RootCertSerialNumber OBJECT-TYPE
     SYNTAX DisplayString (SIZE(0..64))
     MAX-ACCESS read-create
     STATUS current
     DESCRIPTION
     "The Serial Number field in an X.509 certificate, see [RFC5280]."
     ::= { arrisTR69RootCertificateEntry 5 }
	 
arrisTR69RootCertIssuer OBJECT-TYPE
     SYNTAX OCTET STRING (SIZE(0..256))
     MAX-ACCESS read-create
     STATUS current
     DESCRIPTION
     "The Issuer field in an X.509 certificate, see [RFC5280]; 
	 i.e. the Distinguished Name (DN) of the entity who has signed the certificate."
     ::= { arrisTR69RootCertificateEntry 6 }
	 
arrisTR69RootCertNotBefore OBJECT-TYPE
     SYNTAX OCTET STRING (SIZE(0..256))
     MAX-ACCESS read-create
     STATUS current
     DESCRIPTION
     "The beginning of the certificate validity period; 
	 i.e. the Not Before field in an X.509 certificate, see [RFC5280]."
     ::= { arrisTR69RootCertificateEntry 7 }
	 
arrisTR69RootCertNotAfter OBJECT-TYPE
     SYNTAX OCTET STRING (SIZE(0..256))
     MAX-ACCESS read-create
     STATUS current
     DESCRIPTION
     "The end of the certificate validity period; 
	 i.e., the Not After field in an X.509 certificate, see [RFC5280]."
     ::= { arrisTR69RootCertificateEntry 8 }
	 
arrisTR69RootCertSubject OBJECT-TYPE
     SYNTAX OCTET STRING (SIZE(0..256))
     MAX-ACCESS read-create
     STATUS current
     DESCRIPTION
     "The Distinguished Name (DN) of the entity associated with the Public Key; 
	 i.e., the Subject field in an X.509 certificate, see [RFC5280]."
     ::= { arrisTR69RootCertificateEntry 9 }
	 
arrisTR69RootCertSubjectAlt OBJECT-TYPE
     SYNTAX OCTET STRING (SIZE(0..256))
     MAX-ACCESS read-create
     STATUS current
     DESCRIPTION
     "Comma-separated list (maximum length 256) of strings. Each item is a DNS Name.

     The Subject Alternative Names extension field in an X.509 certificate, see [RFC5280]."
     ::= { arrisTR69RootCertificateEntry 10 }
	 
arrisTR69RootCertSignatureAlgorithm OBJECT-TYPE
     SYNTAX OCTET STRING (SIZE(0..256))
     MAX-ACCESS read-create
     STATUS current
     DESCRIPTION
     "The algorithm used in signing the certificate; 
	 i.e. the Signature Algorithm field in an X.509 certificate, see [RFC5280]."
     ::= { arrisTR69RootCertificateEntry 11 }
	 
arrisTR69RootCertObjInstance OBJECT-TYPE
     SYNTAX Unsigned32
     MAX-ACCESS read-write
     STATUS current
     DESCRIPTION "The TR69/TR181 Object index value"
     ::= { arrisTR69RootCertificateEntry 12 }	 
	 
arrisTR181DeviceInfoFirstUseDate OBJECT-TYPE
     SYNTAX DateAndTime
     MAX-ACCESS read-only
     STATUS current
     DESCRIPTION
     "Date and time in UTC that the CPE first both successfully established 
      an IP-layer network connection and acquired an absolute time reference 
      using NTP or equivalent over that network connection. The CPE MAY 
      reset this date after a factory reset.  If NTP or equivalent is not 
      available, this parameter, if present, SHOULD be set to the Unknown Time value."
     ::= { arrisTR181DeviceInfo 1 }	 

arrisTR181DeviceInfoMemoryStatusTotal OBJECT-TYPE
     SYNTAX Unsigned32
     MAX-ACCESS read-only
     STATUS current
     DESCRIPTION
     "The total physical RAM, in kilobytes, installed on the device."
     ::= { arrisTR181DeviceInfoMemoryStatus 1 }

arrisTR181DeviceInfoMemoryStatusFree OBJECT-TYPE
     SYNTAX Unsigned32
     MAX-ACCESS read-only
     STATUS current
     DESCRIPTION
     "The free physical RAM, in kilobytes, currently available on the device."
      ::= { arrisTR181DeviceInfoMemoryStatus 2 }

arrisTR181DeviceInfoProcessStatusCPUUsage OBJECT-TYPE
     SYNTAX Unsigned32 (0..100)
     MAX-ACCESS read-only
     STATUS current
     DESCRIPTION
     "The total amount of the CPU, in percent, rounded up to the nearest whole percent. In the 
      case that multiple CPU are present, this value represents the average of all CPU."
      ::= { arrisTR181DeviceInfoProcessStatus 1 }

-- arrisTR181DeviceInfoProcessStatusProcess MIB objects --

arrisTR181DeviceInfoProcessStatusProcessTable OBJECT-TYPE
     SYNTAX      SEQUENCE OF ArrisTR181DeviceInfoProcessStatusProcessEntry
     MAX-ACCESS  not-accessible
     STATUS      current
     DESCRIPTION
     "List of all processes running on the device.
      At most one entry in this table can exist with a
      given value for PID."
     ::= { arrisTR181DeviceInfoProcessStatusProcess 1 }

arrisTR181DeviceInfoProcessStatusProcessEntry OBJECT-TYPE
     SYNTAX      ArrisTR181DeviceInfoProcessStatusProcessEntry
     MAX-ACCESS  not-accessible
     STATUS      current
     DESCRIPTION
     "List of all processes running on the device.
      At most one entry in this table can exist with a
      given value for PID."
     INDEX { arrisTR181DeviceInfoProcessStatusProcessIndex  }
     ::= {  arrisTR181DeviceInfoProcessStatusProcessTable 1 }

ArrisTR181DeviceInfoProcessStatusProcessEntry ::= SEQUENCE {
         arrisTR181DeviceInfoProcessStatusProcessIndex    INTEGER,
         arrisTR181DeviceInfoProcessStatusProcessPID      Unsigned32,
         arrisTR181DeviceInfoProcessStatusProcessCommand  OCTET STRING,
         arrisTR181DeviceInfoProcessStatusProcessSize     Unsigned32,
         arrisTR181DeviceInfoProcessStatusProcessPriority Unsigned32,
         arrisTR181DeviceInfoProcessStatusProcessCPUTime  Unsigned32,
         arrisTR181DeviceInfoProcessStatusProcessState    OCTET STRING
     }

arrisTR181DeviceInfoProcessStatusProcessIndex OBJECT-TYPE
     SYNTAX      INTEGER (1..150)
     MAX-ACCESS  not-accessible
     STATUS      current
     DESCRIPTION
     "Index used to order the arrisTR181DeviceInfoProcessStatusProcessTable 
      entries"
     ::= { arrisTR181DeviceInfoProcessStatusProcessEntry 1 }

arrisTR181DeviceInfoProcessStatusProcessPID OBJECT-TYPE
     SYNTAX Unsigned32
     MAX-ACCESS read-only
     STATUS current
     DESCRIPTION
     "The Process Identifier."
      ::= { arrisTR181DeviceInfoProcessStatusProcessEntry 2 }

arrisTR181DeviceInfoProcessStatusProcessCommand OBJECT-TYPE
     SYNTAX  OCTET STRING (SIZE (1..256))
     MAX-ACCESS  read-only
     STATUS      current
     DESCRIPTION
     "The name of the command that has caused the process to exist."
     ::= { arrisTR181DeviceInfoProcessStatusProcessEntry 3 }

arrisTR181DeviceInfoProcessStatusProcessSize OBJECT-TYPE
     SYNTAX Unsigned32
     MAX-ACCESS read-only
     STATUS current
     DESCRIPTION
     "The size in kilobytes of the memory occupied by the process."
      ::= { arrisTR181DeviceInfoProcessStatusProcessEntry 4 }

arrisTR181DeviceInfoProcessStatusProcessPriority OBJECT-TYPE
     SYNTAX Unsigned32  (0..99)
     MAX-ACCESS read-only
     STATUS current
     DESCRIPTION
     "The priority of the process where 0 is highest."
      ::= { arrisTR181DeviceInfoProcessStatusProcessEntry 5 }

arrisTR181DeviceInfoProcessStatusProcessCPUTime OBJECT-TYPE
     SYNTAX Unsigned32
     MAX-ACCESS read-only
     STATUS current
     DESCRIPTION
     "The amount of time in milliseconds that the process has 
      spent taking up CPU time since the process was started."
      ::= { arrisTR181DeviceInfoProcessStatusProcessEntry 6 }

arrisTR181DeviceInfoProcessStatusProcessState OBJECT-TYPE
     SYNTAX  OCTET STRING (SIZE (1..32))
     MAX-ACCESS  read-only
     STATUS      current
     DESCRIPTION
     "The current state that the process is in. 
      Enumeration of:
        Running
        Sleeping
        Stopped
        Idle (OPTIONAL)
        Uninterruptible (OPTIONAL)
        Zombie (OPTIONAL)."
      ::= { arrisTR181DeviceInfoProcessStatusProcessEntry 7 }
END

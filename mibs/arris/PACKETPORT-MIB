PACKETPORT-MIB DEFINITIONS ::= BEGIN

IMPORTS
 MODULE-IDENTITY, OBJECT-TYPE, Integer32, IpAddress
  FROM SNMPv2-SMI
 arris
  FROM ARRIS-MIB
 OBJECT-GROUP 
  FROM SNMPv2-CONF
 TruthValue, DisplayString, TEXTUAL-CONVENTION
  FROM SNMPv2-TC;
-- TRAP-TYPE
--  FROM RFC-1215
-- ifPhysAddress
--  FROM IF-MIB
-- ipAdEntAddr
--  FROM IP-MIB;
-- docsDevSerialNumber, docsDevEvText
--  FROM DOCS-CABLE-DEVICE-MIB;

packetPortMib MODULE-IDENTITY
    LAST-UPDATED    "1410160000Z" -- Oct 15, 2014
    ORGANIZATION    "Arris Interactive"
    CONTACT-INFO
  "Robert Coley
   Postal: Arris Interactive
    3871 Lakefield Drive
    Suite 300
    Suwanee, GA 30024-1242
    U.S.A.
   Phone:  +1 770 622 8500
   E-mail: robert.coley@arris-i.com

   Initial MIB creator: Angela Lyda
   Postal: Arris Interactive
    3871 Lakefield Drive
    Suite 300
    Suwanee, GA 30024-1242
    U.S.A.
   Phone:  +1 770 622 8500
   E-mail: angela.lyda@arris-i.com"
    DESCRIPTION
      "This is the portion of the Arris enterprise MIB that applies
       to the Packetport."

-- Revision history
    REVISION    "1410160000Z" -- Oct 15, 2014
    DESCRIPTION
        "Added 'unitedKingdom(36) and romania(37)' to CountryCode Textual-Convention."
	
    REVISION    "1310090000Z" -- Oct 09, 2013
    DESCRIPTION
        "Modified description for ppCfgMtaCallpFeatureSwitch."

    REVISION    "1005200000Z" -- May 20, 2010
    DESCRIPTION
        "Added 'chileT (35)' to CountryCode Textual-Convention."

    REVISION    "0903160000Z" -- March 16, 2009
    DESCRIPTION
        "Added 'slovenia (34)' to CountryCode Textual-Convention."
        
    REVISION    "0808040000Z" -- August 4, 2008
    DESCRIPTION
        "Added 'argentina (33)' to CountryCode Textual-Convention."

    REVISION    "0802130000Z" -- February 13, 2008
    DESCRIPTION
        "Updated description for CallpFeatureSwitch."

    REVISION    "0710240000Z" -- October 24, 2007
    DESCRIPTION
        "Updated description for CallpFeatureSwitch."

    REVISION    "0710190000Z" -- October 19, 2007
    DESCRIPTION
        "Added 'northAmerica66 (32)' to CountryCode Textual-Convention."

    REVISION    "0705030000Z" -- May 3, 2007
    DESCRIPTION
        "Added 'germany2 (31)' to CountryCode Textual-Convention."

    REVISION    "0610160000Z" -- October 16, 2006
    DESCRIPTION
        "Added 'poland1010 (30)' to CountryCode Textual-Convention."

    REVISION    "0605040000Z" -- May 4, 2006
    DESCRIPTION
        "Sync'd MTA Feature Switch with Cust5 streams"

    REVISION    "0512010000Z" -- December 1, 2005
    DESCRIPTION
        "Added 'swiss (29)' to CountryCode Textual-Convention."

    REVISION    "0509090000Z" -- September 9, 2005
    DESCRIPTION
        "Added 'mexicoC (28)' to CountryCode Textual-Convention."

    REVISION    "0506140000Z" -- June 14, 2005
    DESCRIPTION
        "Added 'mexico (26) and panama (27)' to CountryCode Textual-Convention."

    REVISION    "0502240000Z" -- February 24, 2005
    DESCRIPTION
        "Added 'Japan600_412 (25)' to CountryCode Textual-Convention."

    REVISION    "0502050000Z" -- February 5, 2005
    DESCRIPTION
        "Added 'Hungary (21), Sweden (22), Norway (23), and 
         Slovakia (24)' to CountryCode Textual-Convention."

    REVISION    "0412170000Z" -- December 12, 2004
    DESCRIPTION
        "Added 'Japan600 (20)' to CountryCode
         Textual-Convention."

    REVISION    "0408040000Z" -- August 4, 2004
    DESCRIPTION
        "Added 'netherlands09' to CountryCode
         Textual-Convention."

    REVISION    "0403100000Z" -- March 10, 2004
    DESCRIPTION
        "Obsoleted multiple objects that are defined vis standards
         mibs or ones that are no longer used."

    REVISION    "0306160000Z" -- June 16, 2003
    DESCRIPTION
        "Added ppCfgMtaDevSecurity MIB Group and 
         ppCfgMtaDevServiceProviderTestRootCert MIB objects"
        
    REVISION    "0305140000Z" -- May 14, 2003
    DESCRIPTION
        "Modified the SYNTAX of 'ppCfgMtaClientSeed'.  Changed MAX-ACCESS 
         of 'ppSurvMtaDevCorrelationId' from read-write to read-only.
         STATUS of 'ppCfgMtaClientSeed' changed to 'obsolete'.  STATUS 
         of 'ppCfgMtaHTTPAdvLink' changed to 'obsolete'."
         
    REVISION    "0304170000Z" -- April 17, 2003
    DESCRIPTION
        "Modified range and default for ppCfgPortTxGainControl
        and ppCfgPortRxGainControl"
        
    REVISION    "0304020000Z" -- April 2, 2003
    DESCRIPTION
        "Added 'northAmerica09'(18) enumeration,
         changed enumeration descriptions for
         northAmericaHigh(17) to 'northAmerica33'and 
         northAmericaStandard(1) to 'northAmerica57'."
        
    REVISION    "0302120000Z" -- February 12, 2003
    DESCRIPTION
        "Added 'ppCfgPortDialingMethod' object."
        
    REVISION    "0206220000Z" -- June 21, 2002
    DESCRIPTION
        "Added 'InternetIsolationState' object."

    REVISION    "0202260000Z" -- February 26, 2002
    DESCRIPTION
        "Modified enumerations for 'PacketizationPeriodType' object."

    REVISION    "0111210000Z" -- November 21, 2001
    DESCRIPTION
        "Modified enumerations for 'ppSurvMtaPowerSupplyTele' object."

    REVISION    "0109100000Z" -- September 10, 2001
    DESCRIPTION
        "Added 'PpCallServerType' Textual-Convention and
        'ppCfgMtaCallServerType' object, and 'northAmericaHigh(17)'
        in country codes."

    REVISION    "0104300000Z"
    DESCRIPTION
        "Added the following objects:
         'PpDebugReportingLevel' Textual-Convention,  
         'ppSurvMtaDevDebugLevelControlTable' object,
         'ppSurvMtaDevAlarmRetryTimer' object."
         
    REVISION    "0003090100Z"
    DESCRIPTION
        "Added 'ppCfgMtaCallpFeatureSwitch' object"   
        
    REVISION    "0012110000Z"
    DESCRIPTION
        "Added 'poland', 'israel' and 'czechRepublic' to CountryCode
         Textual-Convention."
        
    REVISION    "0011140000Z"
    DESCRIPTION
        "Added 'Belgium' to Textual Convention CountryCode."
        
    REVISION    "0010120000Z"
    DESCRIPTION
        "Added 'ppSurvMtaBoxIdentifier' object.
         Added 'PacketizationPeriodType' Textual-Convention.
         Added the following objects to the ppCfgPortTable:
         'ppCfgPortPacketizationPeriod', 'ppCfgPortCodec'."
         
    REVISION    "0008110000Z"
    DESCRIPTION
        "Added additional countries to the CountryCode Textual-Convention.
         Added the following object to the ppCfgPortTable:
     'ppCfgPortLocUserIndication'."
    ::= { arris 10 }

-- Arris (Rod) Temporary fix for 5.0 merge problem
DocsX509ASN1DEREncodedCertificate ::= TEXTUAL-CONVENTION
        STATUS    current
        DESCRIPTION
            "An X509 digital certificate encoded as an ASN.1 DER
        object."
        SYNTAX    OCTET STRING (SIZE (0..4096))

CodecType ::= TEXTUAL-CONVENTION
 STATUS obsolete
 DESCRIPTION "These are the various types of codecs that
              may be supported."
 SYNTAX INTEGER{
               g711u(1),
               g711a(2),
               g7231(3),
               g729(4),
               g729a(5),
               g729e(6),
               g726(7),
               g728(8)
               }

PacketizationPeriodType ::= TEXTUAL-CONVENTION
 STATUS obsolete
 DESCRIPTION "The packetization periods supported by the PacketPort."
 SYNTAX INTEGER{
               ten(10),
               twenty(20),
               thirty(30)
               }

SignalingProtocol ::= TEXTUAL-CONVENTION
  STATUS obsolete
  DESCRIPTION "These are the various signaling protocols
              that may be supported."
  SYNTAX INTEGER{
            none(0),
            ncs(1)}

CountryCode ::= TEXTUAL-CONVENTION
  STATUS current
  DESCRIPTION "These are the countries for the country 
               code template object."
  SYNTAX INTEGER{
      northAmerica57(1),
      chile(2),
      japan (3),
      australia(4),
      austria(5),
      france(6),
      germany(7),
      ireland(8),
      netherlands(9),
      portugal(10),
      spain(11),
      belgium(12),
      poland(13),
      israel(14),
      czechRepublic(15),
      brazil(16),
      northAmerica33(17),
      northAmerica09(18),
      netherlands09(19),
      japan600(20),
      hungary(21),
      sweden(22),
      norway(23),
      slovakia(24),
      japan600L412(25),
      mexico(26),
      panama(27),
      mexicoC(28),
      swiss(29),
      poland1010(30),
      germany2(31),
      northAmerica66(32),
      argentina(33),
      slovenia(34),
      chileT(35),
      unitedKingdom(36),
      romania(37)
  } 
PpDebugReportingLevel ::= TEXTUAL-CONVENTION
  STATUS current
  DESCRIPTION "These are the debug message reporting levels that are supported."
  SYNTAX INTEGER {
                  off(0),                               
                  level1(1),  
                  level2(2),
                  level3(3),
                  level4(4),
                  level5(5),
                  level6(6),
                  level7(7),
                  level8(8),
                  level9(9),
                  level10(10)                  
                 }                
  
PpCallServerType ::= TEXTUAL-CONVENTION
  STATUS obsolete
  DESCRIPTION "These are the various call servers that are supported."
  SYNTAX INTEGER {
     standard(0),
     sn03(1),
     tropico(2),
     tb200gr303(3),
     tb200v52(4),
     clarent(5),
     pktcable(6)
  }

ppConfiguration OBJECT IDENTIFIER ::= { packetPortMib 1 }
ppSurveillance OBJECT IDENTIFIER ::= { packetPortMib 2 }
ppCfgMtaDevSecurity OBJECT IDENTIFIER ::= { ppConfiguration 29 }

--=====================================================================
-- Packetport per port configuration data
--=====================================================================
--=====================================================================
-- Port Protocol Table
--=====================================================================
ppCfgPortTable OBJECT-TYPE
 SYNTAX SEQUENCE OF PpCfgPortEntry
 MAX-ACCESS not-accessible
 STATUS current
 DESCRIPTION
  "This table is used to define the configurable data on a per port basis."
 ::= { ppConfiguration 1 }

ppCfgPortEntry OBJECT-TYPE
 SYNTAX PpCfgPortEntry
 MAX-ACCESS not-accessible
 STATUS current
 DESCRIPTION
  "An entry in the Configuration Port table."
 INDEX { ppCfgPortPortNumber }
 ::= { ppCfgPortTable 1 }

PpCfgPortEntry ::= SEQUENCE{
  ppCfgPortPortNumber Integer32,   -- INDEX item
  ppCfgPortAdminState INTEGER,
  ppCfgPortCallAgentName DisplayString,
  ppCfgPortCallAgentIpAddress IpAddress,
  ppCfgPortProvSignalingProt SignalingProtocol,
  ppCfgPortLoopCurrent INTEGER,
  ppCfgPortTpar Integer32,
  ppCfgPortTcrit Integer32,
  ppCfgPortBusyToneTimeOut Integer32,
  ppCfgPortDialToneTimeOut Integer32,
  ppCfgPortMsgWaitTimeOut Integer32,
  ppCfgPortOffHookWarnTimeOut Integer32,
  ppCfgPortRingingTimeOut Integer32,
  ppCfgPortRingBackTimeOut Integer32,
  ppCfgPortReorderTimeOut Integer32,
  ppCfgPortStutterDialToneTimeOut Integer32,
  ppCfgPortMaxWaitDelay Integer32,
  ppCfgPortCallAgentUdpPort Integer32,
  ppCfgPortTxGainControl Integer32,
  ppCfgPortRxGainControl Integer32,
  ppCfgPortLocUserIndication INTEGER,
  ppCfgPortPacketizationPeriod PacketizationPeriodType,
  ppCfgPortCodec CodecType,
  ppCfgPortDialingMethod INTEGER,
  ppCfgPortT38MaxDatagram Integer32
 }

ppCfgPortPortNumber OBJECT-TYPE
 SYNTAX Integer32
 MAX-ACCESS not-accessible
 STATUS current
 DESCRIPTION "The unique value which identifies the port."
 ::= { ppCfgPortEntry 1 }

ppCfgPortAdminState OBJECT-TYPE
 SYNTAX INTEGER { oos(1),is(2) }
 MAX-ACCESS read-only
 STATUS current
 DESCRIPTION "The administrative state of the line."
 ::= { ppCfgPortEntry 2 }

ppCfgPortCallAgentName OBJECT-TYPE
 SYNTAX DisplayString
 MAX-ACCESS read-only
 STATUS current
 DESCRIPTION "Call agent domain name."
 ::= { ppCfgPortEntry 3 }

ppCfgPortCallAgentIpAddress OBJECT-TYPE
 SYNTAX IpAddress
 MAX-ACCESS read-only
 STATUS obsolete
 DESCRIPTION "Call Agent IP address."
 ::= { ppCfgPortEntry 4 }

ppCfgPortProvSignalingProt OBJECT-TYPE
 SYNTAX SignalingProtocol
 MAX-ACCESS read-only
 STATUS obsolete
 DESCRIPTION "The provisioned signaling protocol on the port."
 ::= { ppCfgPortEntry 5 }

ppCfgPortLoopCurrent OBJECT-TYPE
 SYNTAX INTEGER{ normal(1), high(2) }
 MAX-ACCESS read-write
 STATUS current
 DESCRIPTION "This object provides the ability to set the
              loop current high or low."
 ::= { ppCfgPortEntry 6 }

ppCfgPortTpar OBJECT-TYPE
 SYNTAX Integer32(12..20)
 MAX-ACCESS read-only
 STATUS obsolete
 DESCRIPTION "This object contains the maximum value of partial dial
              timeout in seconds."
 DEFVAL { 16 }
 ::= { ppCfgPortEntry 7 }

ppCfgPortTcrit OBJECT-TYPE
 SYNTAX Integer32(3..5)
 MAX-ACCESS read-only
 STATUS obsolete
 DESCRIPTION "This object contains the maximum value of critical dial
              timeout in seconds."
 DEFVAL { 4 }
 ::= { ppCfgPortEntry 8 }

ppCfgPortBusyToneTimeOut OBJECT-TYPE
 SYNTAX Integer32(23..37)
 MAX-ACCESS read-only
 STATUS obsolete
 DESCRIPTION "Busy tone time out value."
 DEFVAL { 30 }
 ::= { ppCfgPortEntry 9 }

ppCfgPortDialToneTimeOut OBJECT-TYPE
 SYNTAX Integer32(12..20)
 MAX-ACCESS read-only
 STATUS obsolete
 DESCRIPTION "Dial tone time out value."
 DEFVAL { 16 }
 ::= { ppCfgPortEntry 10 }

ppCfgPortMsgWaitTimeOut OBJECT-TYPE
 SYNTAX Integer32(12..20)
 MAX-ACCESS read-only
 STATUS obsolete
 DESCRIPTION "Message waiting time out value."
 DEFVAL { 16 }
 ::= { ppCfgPortEntry 11 }

ppCfgPortOffHookWarnTimeOut OBJECT-TYPE
 SYNTAX Integer32(0..60)
 MAX-ACCESS read-only
 STATUS obsolete
 DESCRIPTION "Off hook warning time out value."
 DEFVAL { 0 }
 ::= { ppCfgPortEntry 12 }


ppCfgPortRingingTimeOut OBJECT-TYPE
 SYNTAX Integer32(135..225)
 MAX-ACCESS read-only
 STATUS obsolete
 DESCRIPTION "Ringing time out value."
 DEFVAL { 180 }
 ::= { ppCfgPortEntry 13 }

ppCfgPortRingBackTimeOut OBJECT-TYPE
 SYNTAX Integer32(135..225)
 MAX-ACCESS read-only
 STATUS obsolete
 DESCRIPTION "RingBack time out value."
 DEFVAL { 180 }
 ::= { ppCfgPortEntry 14 }

ppCfgPortReorderTimeOut OBJECT-TYPE
 SYNTAX Integer32(23..37)
 MAX-ACCESS read-only
 STATUS obsolete
 DESCRIPTION "Reorder time out value."
 DEFVAL { 30 }
 ::= { ppCfgPortEntry 15 }

ppCfgPortStutterDialToneTimeOut OBJECT-TYPE
 SYNTAX Integer32(12..20)
 MAX-ACCESS read-only
 STATUS obsolete
 DESCRIPTION "Stutter dial tone time out value"
 DEFVAL { 16 }
 ::= { ppCfgPortEntry 16 }

ppCfgPortMaxWaitDelay OBJECT-TYPE
 SYNTAX Integer32(450..750)
 MAX-ACCESS read-only
 STATUS obsolete
 DESCRIPTION "This object contains the maximum number
              of seconds a MTA waits after a restart."
 DEFVAL { 600 }
 ::= { ppCfgPortEntry 17 }

ppCfgPortCallAgentUdpPort OBJECT-TYPE
 SYNTAX Integer32(1025..65535)
 MAX-ACCESS read-only
 STATUS current
 DESCRIPTION " This object contains the call agent udp port that is
               being used for this instance of call signaling."
 DEFVAL { 2427 }
 ::= { ppCfgPortEntry 18 }

ppCfgPortTxGainControl OBJECT-TYPE
  SYNTAX Integer32(-2..2)
  MAX-ACCESS read-write
  STATUS current
  DESCRIPTION "The gain control setting (dB) in the upstream, or A-to-D,
               direction. Setting this value for either line will take
               affect on ALL telephony lines."
  DEFVAL { 0 }
  ::= { ppCfgPortEntry 19 }

ppCfgPortRxGainControl OBJECT-TYPE
  SYNTAX Integer32(-2..2)
  MAX-ACCESS read-write
  STATUS current
  DESCRIPTION "The gain control setting (dB) in the downstream, or D-to-A,
               direction. Setting this value for either line will take
               affect on ALL telephony lines."
  DEFVAL { 0 }
  ::= { ppCfgPortEntry 20 }

ppCfgPortLocUserIndication OBJECT-TYPE
 SYNTAX INTEGER { silence(0), reorderTone(1) }
 MAX-ACCESS read-write
 STATUS current
 DESCRIPTION "Treatement/Tone applied in loss of communication (LOC) scenarios."
 DEFVAL { reorderTone }
 ::= { ppCfgPortEntry 21 }

ppCfgPortPacketizationPeriod OBJECT-TYPE
 SYNTAX PacketizationPeriodType
 UNITS "milliseconds"
 MAX-ACCESS read-only
 STATUS obsolete
 DESCRIPTION "The per line packetization period for codec type."
 DEFVAL { ten }
 ::= { ppCfgPortEntry 22 }

ppCfgPortCodec OBJECT-TYPE
 SYNTAX CodecType
 MAX-ACCESS read-only
 STATUS obsolete
 DESCRIPTION "The per line codec type gxxxx."
 DEFVAL { g711a }
 ::= { ppCfgPortEntry 23 }
  
ppCfgPortDialingMethod OBJECT-TYPE
 SYNTAX INTEGER { tone(1), pulse(2), toneAndPulse(3), pulseWithDTMFRelay(4), toneAndPulseWithDTMFRelay(5) }
 MAX-ACCESS read-write
 STATUS deprecated
 DESCRIPTION "Indicates the method used to dial the digits for this telephony
              endpoint.  If tone(1), tone dialing (DTMF) is used. If pulse(2),
              dial-pulse signaling is used to dial the digits, Tone dialing(DTMF) is
              disabled. If Tone & Pulse(3), tone dialing(DTMF) and dial-pulse signaling
              is used to dial the digits. If Pulse with DTMF relay(4), Tone dialing(DTMF)
              is disabled, and pulse dialed digits will be relayed in-band to the media
              gateway.  If Tone & Pulse with DTMF relay(5), Tone dialing (DTMF) is enable,
              and pulse dialed digits will be relayed in-band to the media gateway.
              NOTE: (4) & (5) will require IPDT solution as well as DTMF support by the
              Media gateway. The default value for this object is tone(1)."
 DEFVAL { tone }
 ::= { ppCfgPortEntry 24 }  

ppCfgPortT38MaxDatagram OBJECT-TYPE
 SYNTAX Integer32(160..65535)
 MAX-ACCESS read-write
 STATUS current
 DESCRIPTION "Specifies the T38 Max Datagram size for incoming T38 packets.  If this is used to
              allow larger incoming T38 packets then the Call Agent must allocate more bandwidth
	      accordingly"
 DEFVAL { 160 }
 ::= { ppCfgPortEntry 25 }

--====================================================================
-- PacketPort Device Level configuration data
--====================================================================
ppCfgMtaAdminState OBJECT-TYPE
 SYNTAX INTEGER { oos(1), is(2) }
 MAX-ACCESS read-only
 STATUS current
 DESCRIPTION "The administrative state of the packetport."
 ::= { ppConfiguration 2 }

ppCfgMtaTeleSyslogServIpAddr OBJECT-TYPE
 SYNTAX IpAddress
 MAX-ACCESS read-write
 STATUS current
 DESCRIPTION "The MTA's telephony syslog server IP address."
 ::= { ppConfiguration 3 }

ppCfgMtaTeleSyslogServName OBJECT-TYPE
 SYNTAX DisplayString
 MAX-ACCESS read-write
 STATUS current
 DESCRIPTION "The MTA's telephony syslog server domain name."
 ::= { ppConfiguration 4 }

ppCfgMtaTeleFullyQualName OBJECT-TYPE
 SYNTAX DisplayString
 MAX-ACCESS read-only -- this is temporary
 STATUS obsolete
 DESCRIPTION "MTA fully qualified domain name."
 ::= { ppConfiguration 5 }

ppCfgMtaTeleServProvServIpAddr OBJECT-TYPE
 SYNTAX IpAddress
 MAX-ACCESS read-only -- this is temporary to ease implementation
 STATUS obsolete
 DESCRIPTION "The telephony service provider provisioning server IP address.  
              This object returns 0.0.0.0 if the provisioning server IP 
              address is unknown or unassigned."
 ::= { ppConfiguration 6 }

ppCfgMtaTeleServProvServName OBJECT-TYPE
 SYNTAX DisplayString
 MAX-ACCESS read-only -- this is temporary to ease implementation
 STATUS obsolete
 DESCRIPTION "The telephony service provider provisioning server domain name.
              This object returns a (zero-length) string if the provisioning
              server domain name is unknown or unassigned."
 ::= { ppConfiguration 7 }

ppCfgMtaTeleServProvDhcpIpAddr OBJECT-TYPE
 SYNTAX IpAddress
 MAX-ACCESS read-only -- this is temporary to ease implementation
 STATUS obsolete
 DESCRIPTION "The telephony service provider DHCP IP address."
 ::= { ppConfiguration 8 }

ppCfgMtaTeleServProvDhcpName OBJECT-TYPE
 SYNTAX DisplayString
 MAX-ACCESS read-only -- this is temporary to ease implementation
 STATUS obsolete
 DESCRIPTION "The telephony service provider DHCP domain name."
 ::= { ppConfiguration 9 }

ppCfgMtaPrimTeleNetDnsAddr OBJECT-TYPE
 SYNTAX IpAddress
 MAX-ACCESS read-only
 STATUS obsolete
 DESCRIPTION "Primary telephony provisioning DNS address."
 ::= { ppConfiguration 10 }

ppCfgMtaSecTeleNetDnsAddr OBJECT-TYPE
 SYNTAX IpAddress
 MAX-ACCESS read-only
 STATUS obsolete
 DESCRIPTION "Secondary telephony provisioning DNS address."
 ::= { ppConfiguration 11 }

ppCfgMtaCableTvEnable OBJECT-TYPE
 SYNTAX INTEGER { on(1), off(2) }
 MAX-ACCESS read-write
 STATUS current
 DESCRIPTION "This object provides the ability to turn the cable off and on."
 ::= { ppConfiguration 12 }

ppCfgMtaConfigFileAccName OBJECT-TYPE
 SYNTAX DisplayString
 MAX-ACCESS read-only
 STATUS obsolete
 DESCRIPTION "The filename of the config file."
 ::= { ppConfiguration 13 }

ppCfgMtaCountryTemplate OBJECT-TYPE
 SYNTAX CountryCode
 MAX-ACCESS read-write
 STATUS current
 DESCRIPTION "The country code template."
 ::= { ppConfiguration 14 }

ppCfgMtaProvMethodIndicator OBJECT-TYPE
 SYNTAX INTEGER { singleFile(1), dualFile(2) }
 MAX-ACCESS read-only
 STATUS obsolete
 DESCRIPTION "The telephony provisioning method indicator."
 ::= { ppConfiguration 15 }

ppCfgMtaTeleConfigServerIpAddr OBJECT-TYPE
 SYNTAX IpAddress
 MAX-ACCESS read-only
 STATUS obsolete
 DESCRIPTION "The telephony configuration server IP address, in our
              case the telephony TFTP server."
 ::= { ppConfiguration 16 }

ppCfgMtaTeleConfigServerName OBJECT-TYPE
 SYNTAX DisplayString
 MAX-ACCESS read-only
 STATUS obsolete
 DESCRIPTION "The telephony configuration server DN, in our case the
              telephony TFTP server."
 ::= { ppConfiguration 17 }

ppCfgMtaNcsCallSigTos OBJECT-TYPE
  SYNTAX Integer32(0..63)
  MAX-ACCESS read-only
  STATUS obsolete
  DESCRIPTION "The default value used in the IP header
               for setting the TOS value for NCS call
               signalling."
  ::= { ppConfiguration 18 }

ppCfgMtaDataInterface OBJECT-TYPE
 SYNTAX INTEGER { eth10baset(1),
                  hpna1mbps(2),
                  hpna10mbps(3),
                  eth100baset4(4),
                  eth100basex(5) }
 MAX-ACCESS read-write
 STATUS current
 DESCRIPTION "The data interface type."
 ::= { ppConfiguration 19 }
                                           
ppCfgMtaCallpFeatureSwitch OBJECT-TYPE
 SYNTAX Integer32 
 MAX-ACCESS read-write
 STATUS current
 DESCRIPTION "Callp Feature Switch activates certain functionality
              and compliancies in callp. 
              WARNING: Changes can result into loss of communication
                       to the Callagent or loss of the voicepath.
                       Please read documentation before changing!

0x00000001 // Transmit piggyback mode if set.
0x00000002 // Allow endpoint to go into lockstep mode.
0x00000004 // Allow endpoint to send MGCP error code messages.
0x00000008 // Reduce the capability descriptor in the SDP to T38 only.
0x00000010 // SDP compliancy if set.
0x00000020 // Use increased DQoS DS Max Traffic Rate if NOT set; otherwise use PacketCable defined value.
0x00000040 // Apply auto OSI to both originating and terminating side for NCS calls (used to be CPFS_COMMENTS - optional comments in NCS messages).
0x00000080 // Don't include the mptime parameter in the sdp if bit is set to 1. Used for older Cisco BTS systems that edited the sdp causing calls to fail. (used to be CPFS_ANYFQDNOK - allow any MTA FQND in NCS message).
0x00000100 // Suppress capability attribute parameters in the SDP if set to 1. 
0x00000200 // OK to transmit wildcarded NCS messages.
0x00000400 // Ignore format-specific SDP attribute lines referring to payload types not listed in media description (m= line).
0x00000800 // Force the use of DQoS.  Reject service if not used (used to be CPFS_DIGIT_MAP - use hard-coded digit map).
0x00001000 // Need to use rfc-2833 rtp messages for Nuera, ie ABCD signalling.
0x00002000 // Don't play local ringback tone once voice is detected for a sendrecv connection.
0x00004000 // If this flag is set then perform DSX DQoS only.
0x00008000 // Allow the endpoint to send provisional responses.
0x00010000 // Enable Payload Header Suppression.
0x00020000 // Disallows multiple connections per line.
0x00040000 // Use increased DQoS Tolerated Grant Jitter (for the Cisco CMTS).
0x00080000 // Need to use rfc-2833 rtp messages LUCENT payload 94.
0x00100000 // Disables RTP and RTCP security.
0x00200000 // Commit both US and DS SFs for connection modes recvonly, sendonly, and replicate when set; for full DQOS this should never be set.
0x00400000 // Allow redirect with no IPsec.
0x00800000 // Add brackets around IP for MTA FQDN when communicating with the call server when bit is enabled (default disabled).
0x01000000 // Send dtmf digits via RFC2833 with payload 101 (enabled if set - default disabled).
0x02000000 // Allow use of provisioned ring cadences (for non NA countries).
0x04000000 // Use hard-coded values for Flash timing (90 - 800 ms).
0x08000000 // Present CID in alternate (non sequential) order.
0x10000000 // Delay DLCX response on a connection that exists on an onhook only line.  This gives the TTM time to process RTP packets in the jitter buffer.  This addresses a VMWI issue at Videotron.
0x20000000 // MTA generates automatic OSI upon deletion of last connection on the line (if set, default off).
0x40000000 // Enable VAD.
0x80000000 // Do not set this bit.  It's used to detect an invalid CPFS setting.  Some provisioning servers will pad the CPFS value with leading 1's!

---------- Docsis3.0 ppCfgMtaCallpFeatureSwitch Bit descriptions ----------

0x00000001 // Stop piggybacked transmissions of NCS messages
0x00000002 // Prevent endpoint to enter the Lockstep quarantine mode
0x00000004 // If line is not provisioned show OOS rather than IDLE for arrisMtaDevLineCardState.
0x00000008 // Reduce the capability descriptor in the SDP to T38 only.
0x00000010 // NO LONGER USED
0x00000020 // NO LONGER USED
0x00000040 // Apply auto OSI to both originating and terminating side for NCS calls..
0x00000080 // Don't include the mptime parameter in the sdp if bit is set to 1. Used for older Cisco BTS systems that edited the sdp causing calls to fail. (used to be CPFS_ANYFQDNOK - allow any MTA FQND in NCS message)
0x00000100 // Suppress capability attribute parameters in the SDP if set to 1. 
0x00000200 // NO LONGER USED
0x00000400 // Ignore format-specific SDP attribute lines referring to payload types not listed in media description (m= line).
0x00000800 // Reject CRCX or MDCX if no gate ID ever provided. 
0x00001000 // need to use rfc-2833 rtp messages for Nuera, ie ABCD signalling
0x00002000 // NO LONGER USED
0x00004000 // If this flag is set then perform DSX DQoS only.
0x00008000 // Disable endpoint from sending provisional responses. 
0x00010000 // Enable Payload Header Suppression
0x00020000 // NO LONGER USED
0x00040000 // NO LONGER USED
0x00080000 // need to use rfc-2833 rtp messages LUCENT payload 94
0x00100000 // Disables RTP and RTCP security
0x00200000 // NO LONGER USED
0x00400000 // Allow redirect with no IPsec.
0x00800000 // Add brackets around IP for MTA FQDN when communicating with the call server when bit is enabled (default disabled)
0x01000000 // Send dtmf digits via RFC2833 with payload 101 (enabled if set - default disabled)
0x02000000 // NO LONGER USED
0x04000000 // NO LONGER USED
0x08000000 // Present CID in alternate (non sequential) order.
0x10000000 // Delay DLCX response on a connection that exists on an onhook only line.  This give the TTM time to process RTP packets in the jitter buffer.  This addresses a VMWI issue at Videotron.
0x20000000 // MTA generates automatic OSI upon deletion of last connection on the line (if set, default off)
0x40000000 // NO LONGER USED
0x80000000 // Do not set this bit.  It's used to detect an invalid CPFS setting.  Some provisioning servers will pad the CPFS value with leading 1's!"
 ::= { ppConfiguration 20 }
           
ppCfgMtaCallServerType OBJECT-TYPE
 SYNTAX PpCallServerType
 MAX-ACCESS read-only
 STATUS obsolete
 DESCRIPTION "Call Server Type that packeport is interfacing to."
 ::= { ppConfiguration 21 }

ppCfgMtaInternetIsolationState OBJECT-TYPE
 SYNTAX INTEGER { off-InActiveMode(1), on-ActiveMode(2) }
 MAX-ACCESS read-only
 STATUS obsolete
 DESCRIPTION "This object provides the ability to turn the Internet isolation
              off, on and auto"
 ::= { ppConfiguration 22 }

ppCfgRfc2833DigitPayloadType OBJECT-TYPE
 SYNTAX Integer32(96..127)
 MAX-ACCESS read-write
 STATUS current
 DESCRIPTION "This object is used to define the payload type used for 2833 digit events
              when enabled via setting the bit in the Callp Feature Switch."
 DEFVAL { 101 }              
 ::= { ppConfiguration 23 }

ppCfgMtaFeatureSwitch OBJECT-TYPE
 SYNTAX Integer32 
 MAX-ACCESS read-write
 STATUS current
 DESCRIPTION "MTA Feature Switch activates certain functionality and compliancies in the MTA.

 hashBypass(1):   Disable cfg file Hash checking during provisioning sequence.
 maxCPEBypass(2): MTA MAC address will not be entered in the CPE table
                  or counted against the MaxCpeAllowed variable.
 mtaFilterBypass(4): MTA packets will not be filtered with CPE filtered packets.
 proprietaryCoex(8): Enable the Arris proprietary version of MTA coexistence 
                     and notifications
 kdcLoadBalancerSkip(16): Skips the IP check of the KDC load balancer IP forwarding 
                          feature.
 usmUserCompareSkip(32): Skips the comparison of the Pcable USM User Name with User Name 
                         in received in a SNMPv3 packet.
 snmpInformBypass(64): Skips the verification of the SNMP inform.
 ifIndexShiftEnable(128): Shift to using endpoint indices 9&10 to 10&11.
 pktcVersionSelector(256):  Used to select PacketCable 1.5 support.
 mtaProvHaltNoTod(512):  Halt PacketCable Provisioning when no TOD server available.
 diagLoopRingerTestLowWarning(2048): Enable the display of Low Warning result of 
                                      Linecard Loop Diags Ringer Test.
 mtaSafeReset(4096): mta will not reset via snmpset pktcMtaDevResetNow until all the lines are in idle.
 ---------- Docsis3.0 ppCfgMtaFeatureSwitch Bit descriptions ----------

 0x00000001 Disable cfg file Hash checking during provisioning sequence.
 0x00000002 MTA MAC address will not be counted against the MaxCpeAllowed variable.
 0x00000004 UNUSED
 0x00000008 UNUSED
 0x00000010 Skips the IP check of the KDC load balancer IP forwarding feature.
 0x00000020 UNUSED
 0x00000040 Skips the verification of the SNMP inform.
 0x00000080 UNUSED
 0x00000100 UNUSED
 0x00000200 UNUSED
 0x00000400 Do not strip leading '/' from the MTA config file name.
 0x00000800 Report Warning if Loop Diags Ringer Test result is below minimum criteria.
 0x00001000 mta will not be reset until all the lines are in idle.
 0x80000000 Do not set this bit.  It is used to detect an invalid MTA Feature Switch setting. Some 
            provisioning servers pad the MTA Feature Switch value with leading 1's!

All other bits are unused."
 ::= { ppConfiguration 24 }

ppCfgMtaBatteryReplaceReporting OBJECT-TYPE
 SYNTAX INTEGER { immediate(1), delayed(2) }
 MAX-ACCESS read-write
 STATUS current
 DESCRIPTION
     "Determines how the REPLACE BATTERY condition for a TM02DG102 Hardware
      rev. 6 is reported.  Choices are:
      - Same criteria as for all other battery units (value == 1)
      - Reports only after a degraded battery condition persists for at least
        72 hours. (value == 2)"
 ::= { ppConfiguration 25 }
 
ppCfgNsePayloadType OBJECT-TYPE
 SYNTAX Integer32(97..127)
 MAX-ACCESS read-write
 STATUS current
 DESCRIPTION "This object is used to define the payload type used for NSE messages
              when enabled via setting the bit in the Callp Feature Switch."
 DEFVAL { 100 }              
 ::= { ppConfiguration 26 } 

 ppCfgMtaCallpFeatureSwitch2 OBJECT-TYPE
 SYNTAX Integer32 
 MAX-ACCESS read-write
 STATUS current
 DESCRIPTION "This object is like ppCfgMtaCallpFeatureSwitch. It is used to activates 
              certain functionality and compliancies in callp. 

0x00000001 // Treat osi signal as bz signal (This bit is used for NCS only).
0x00000002 // Ignore handling TDD tone detection
0x00000004 // change the codec list behaviour,example:with this bit set, change a=rtpmap:8 PCMA/8000/1 to a=rtpmap:8 PCMA/8000
0x00000008 // Ignore handling Fax/Modem tone detection
0x00000010 // Unused
0x00000020 // Unused
0x00000040 // Unused
0x00000080 // Unused
0x00000100 // Unused 
0x00000200 // Unused
0x00000400 // Unused
0x00000800 // Unused
0x00001000 // Unused
0x00002000 // Unused
0x00004000 // Unused
0x00008000 // Unused
0x00010000 // Unused
0x00020000 // Unused
0x00040000 // Unused
0x00080000 // Unused
0x00100000 // Unused
0x00200000 // Unused
0x00400000 // Unused
0x00800000 // Unused
0x01000000 // Unused
0x02000000 // Unused
0x04000000 // Unused
0x08000000 // Unused
0x10000000 // Unused
0x20000000 // Unused
0x40000000 // Unused
0x80000000 // Unused"
 ::= { ppConfiguration 27 } 


ppCfgMtaDevServiceProviderTestRootCert OBJECT IDENTIFIER ::= { ppCfgMtaDevSecurity 1 }

ppCfgMtaDevSPTestRootCertServer OBJECT-TYPE
 SYNTAX IpAddress
 MAX-ACCESS read-write
 STATUS current
 DESCRIPTION
     "The IP address of the TFTP server used for downloading Service 
      Provider Test Root Certificates to this device.  Returns 0.0.0.0 
      if the TFTP server address is unknown or unassigned.  This object 
      can only be changed by the configuration file."
 ::= { ppCfgMtaDevServiceProviderTestRootCert 1 }
 
ppCfgMtaDevSPTestRootCertFilename OBJECT-TYPE
 SYNTAX DisplayString (SIZE (0..255))
 MAX-ACCESS read-write
 STATUS current
 DESCRIPTION
     "The file name of the Service Provider Test Root Certificate to be 
      downloaded to this device from the TFTP server.  Returns an empty 
      string if the certificate filename is unknown or unassigned.  This 
      object can only be changed by the configuration file."
 ::= { ppCfgMtaDevServiceProviderTestRootCert 2 }
 
ppCfgMtaDevSPTestRootCertAdminStatus OBJECT-TYPE
 SYNTAX INTEGER {
    ignoreCertSettings(0),
    useEmbeddedTestRootCert(1),
    downloadTestRootCert(2)
 }
 MAX-ACCESS read-write
 STATUS current
 DESCRIPTION
     "Controls the usage of Root Certificates by the MTA device.  
      If set to downloadTestRootCert(2), the MTA will download the 
      Service Provider Test Root Certificate specified by 
      'ppCfgMtaDevSPTestRootCertFilename' from the TFTP server 
      specified by 'ppCfgMtaDevSPTestRootCertServer'.  If set to 
      useEmbeddedTestRootCert(1), the MTA will use the factory-installed 
      CableLabs Service Provider Test Root Certificate embedded in the 
      device.  If the value of this object is ignoreCertSettings(0), all 
      of the Test Root Certificate settings (i.e. TestRootCertServer, 
      TestRootCertFilename) are ignored and the MTA will, by default, use 
      the factory-installed CableLabs Service Provider Real Root Certificate 
      embedded in the device.  This object can only be changed by the 
      configuration file.  At initial startup, this object has a default 
      value of ignoreCertSettings(0)."
 DEFVAL { ignoreCertSettings }
 ::= { ppCfgMtaDevServiceProviderTestRootCert 3 }
 
ppCfgMtaDevSPTestRootCertDownloadState OBJECT-TYPE
 SYNTAX INTEGER {
    noDownload(0),
    downloadRequested(1), 
    inProgress(2), 
    completed(3), 
    failed(4)
 }
 MAX-ACCESS read-only
 STATUS current
 DESCRIPTION
     "This object indicates the current state of the Service Provider Test 
      Root Certificate download process.  noDownload(0) indicates that no 
      certificate download has been requested.  downloadRequested(1) indicates 
      a Test Root Certificate download is desired, most likely as a result of 
      a downloadTestRootCert request.  inProgress(2) indicates that a TFTP 
      download is underway.  completed(3) indicates that the last Test Root 
      Certificate download was completed successfully.  failed(4) indicates 
      that the last attempted download failed.
      At initial startup, this object has a default value of noDownload(0)."
 DEFVAL { noDownload }
 ::= { ppCfgMtaDevServiceProviderTestRootCert 4 }
 

ppCfgDevHttp OBJECT IDENTIFIER ::= { ppConfiguration 30 }

ppCfgMtaLanHttpAccess OBJECT-TYPE
 SYNTAX INTEGER { off(1), 
                  basic(2), 
                  advanced(3),
                  until-registered(4) }
 MAX-ACCESS read-write
 STATUS deprecated
 DESCRIPTION "Controls the level of LAN-side HTTP access to the modem.  
              The levels are described as:
              off(1) - LAN-side access is denied,
              basic(2) - DOCSIS-only access,
              advanced(3) - ARRIS proprietary access,
              until-registered(4) - allows basic access until the modem is 
              registered.  At initial startup, the default value is 
              until-registered(4).
              **NOTE: this object is deprecated and replaced by 
              arrisCmDevHttpLanAccess in the ARRIS-CM-DEVICE-MIB."
  DEFVAL { until-registered } 
  ::= {ppCfgDevHttp 1}
  
ppCfgMtaWanHttpAccess OBJECT-TYPE
 SYNTAX INTEGER { off(1), 
                  basic(2), 
                  advanced(3) }
 MAX-ACCESS read-write
 STATUS deprecated
 DESCRIPTION "Controls the level of WAN-side HTTP access to the modem.  
              The levels are described as:
              off(1) - WAN-side access is denied,
              basic(2) - DOCSIS-only access,
              advanced(3) - ARRIS proprietary access.
              **NOTE: this object is deprecated and replaced by 
              arrisCmDevHttpWanAccess in the ARRIS-CM-DEVICE-MIB."

  DEFVAL { off }          
  ::= {ppCfgDevHttp 2}

ppCfgMtaClientSeed OBJECT-TYPE
 SYNTAX OCTET STRING (SIZE(8))
 MAX-ACCESS read-write
 STATUS obsolete
 DESCRIPTION "The current client provided seed that will be used to 
              generate the HTTP WEB Access Advanced Pages password.              
              **NOTE: this object has been replaced by 
              'arrisCmDevHttpClientSeed' in the ARRIS-CM-DEVICE-MIB."

 ::= { ppCfgDevHttp 3 }

ppCfgMtaHTTPAdvLink OBJECT-TYPE
 SYNTAX INTEGER { non-restricted(1), restricted(2) }
 MAX-ACCESS read-write
 STATUS obsolete
 DESCRIPTION "This object provides the ability to show or hide the ADV link 
              on the Basic Page of the HTTP Web Page.
              **NOTE: this object is obsolete."

 DEFVAL { restricted }
 ::= { ppCfgDevHttp 4 }

--=======================================================================
-- Packetport per port surveillance data
--=====================================================================

--=====================================================================
-- Port Protocol Table
--=====================================================================
ppSurvPortTable OBJECT-TYPE
 SYNTAX SEQUENCE OF PpSurvPortEntry
 MAX-ACCESS not-accessible
 STATUS current
 DESCRIPTION
  "This table is used to define the surveillance data on a per port basis."
 ::= { ppSurveillance 1 }

ppSurvPortEntry OBJECT-TYPE
 SYNTAX PpSurvPortEntry
 MAX-ACCESS not-accessible
 STATUS current
 DESCRIPTION
  "An entry in the Configuration Port table."
 INDEX { ppSurvPortNumber }
 ::= { ppSurvPortTable 1 }

PpSurvPortEntry ::= SEQUENCE{
 ppSurvPortNumber Integer32,
 ppSurvPortMaintState INTEGER,
 ppSurvPortDigitMap DisplayString,
 ppSurvPortLcDiagRequest TruthValue,
 ppSurvPortDeprovRequest TruthValue,
 ppSurvPortLcDiagLastResult INTEGER
 }

ppSurvPortNumber OBJECT-TYPE
 SYNTAX Integer32
 MAX-ACCESS not-accessible
 STATUS current
 DESCRIPTION "The unique value which identifies the port."
 ::= { ppSurvPortEntry 1 }

ppSurvPortMaintState OBJECT-TYPE
 SYNTAX INTEGER{isnr(1),isnr-trafbsy(2),
                istrbl-mismatch(3),istrbl-fef(4),
                istrbl-tstf(5), istrbl-diag(6),
                istrbl-lcprt(7), oosnr-unprov(8),
                oosnr(9), oostrbl(10),oostrbl-tstf(11),
                oostrbl-diag(12), oostrbl-lcprt(13)}
 MAX-ACCESS read-only
 STATUS current
 DESCRIPTION "The maintenance state of the line."
 ::= { ppSurvPortEntry 2 }

ppSurvPortDigitMap OBJECT-TYPE
 SYNTAX DisplayString
 MAX-ACCESS read-only
 STATUS obsolete
 DESCRIPTION "The digit map set by the call agent."
 ::= { ppSurvPortEntry 3 }

ppSurvPortLcDiagRequest OBJECT-TYPE
 SYNTAX TruthValue
 MAX-ACCESS read-write
 STATUS current
 DESCRIPTION "Setting this value to true will send a
              diagnostics request on the line.  Reading this
              value will always return false.  The
              maintenance state of the line indicates
              if diagnostics are being run on the line."
 ::= { ppSurvPortEntry 4 }

ppSurvPortDeprovRequest OBJECT-TYPE
 SYNTAX TruthValue
 MAX-ACCESS read-write
 STATUS current
 DESCRIPTION "Setting this value to true will send a
              deprovisioning request on the line.  Reading this
              value will always return false.  The maintenance
              state of the line will indicate if the
              line is deprovisioned."
 ::= { ppSurvPortEntry 5 }

ppSurvPortLcDiagLastResult OBJECT-TYPE
 SYNTAX INTEGER{diagnostics-passed(1),slac-revision-failure(2),
                mpi-failure(3),power-or-clock-failure(4),
                pcm-failure(5), standby-hook-failure(6),
                active-hook-failure(7), vf-failure(8),
                ringing-failure(9), invalid-state-to-init-diags(10),
                line-is-unprovisioned(11), diagnostics-results-pending(12)}
 MAX-ACCESS read-only
 STATUS current
 DESCRIPTION "The last result of diags for this line.  If diagnostics
              are in progress it will return results pending."
 ::= { ppSurvPortEntry 6 }

--=====================================================================
-- PacketPort Device Level surveillance data
--=====================================================================

--===================== Codec Support Table ===========================
ppSurvMtaCodecCapTable OBJECT-TYPE
 SYNTAX SEQUENCE OF PpSurvMtaCodecCapEntry
 MAX-ACCESS not-accessible
 STATUS obsolete
 DESCRIPTION "This table describes the codec capabilities
              of the Packetport."
 ::= { ppSurveillance 2}

ppSurvMtaCodecCapEntry OBJECT-TYPE
 SYNTAX PpSurvMtaCodecCapEntry
 MAX-ACCESS not-accessible
 STATUS obsolete
 DESCRIPTION "An entry in the MTA codec capabilities table."
 INDEX { ppSurvMtaCodecCapIndex }
 ::= { ppSurvMtaCodecCapTable 1 }

PpSurvMtaCodecCapEntry ::= SEQUENCE{
 ppSurvMtaCodecCapIndex Integer32,
 ppSurvMtaCodecCapType CodecType}

ppSurvMtaCodecCapIndex OBJECT-TYPE
 SYNTAX Integer32
 MAX-ACCESS not-accessible
 STATUS obsolete
 DESCRIPTION "The index for this table."
 ::= { ppSurvMtaCodecCapEntry 1 }

ppSurvMtaCodecCapType OBJECT-TYPE
 SYNTAX CodecType
 MAX-ACCESS read-only
 STATUS obsolete
 DESCRIPTION "A codec type supported by this device."
 ::= { ppSurvMtaCodecCapEntry 2 }

--================= Signaling Capabilities Table ===================

ppSurvMtaSigCapTable OBJECT-TYPE
 SYNTAX SEQUENCE OF PpSurvMtaSigCapEntry
 MAX-ACCESS not-accessible
 STATUS obsolete
 DESCRIPTION "A table of the signaling capabilities of the Packetport."
 ::= { ppSurveillance 3 }

ppSurvMtaSigCapEntry OBJECT-TYPE
 SYNTAX PpSurvMtaSigCapEntry
 MAX-ACCESS not-accessible
 STATUS obsolete
 DESCRIPTION "An entry in the signaling capabilities table."
 INDEX { ppSurvMtaSigCapIndex }
 ::= { ppSurvMtaSigCapTable 1 }

PpSurvMtaSigCapEntry ::= SEQUENCE{
 ppSurvMtaSigCapIndex    Integer32,
 ppSurvMtaSigCapProtocol SignalingProtocol}

ppSurvMtaSigCapIndex OBJECT-TYPE
 SYNTAX Integer32
 MAX-ACCESS not-accessible
 STATUS obsolete
 DESCRIPTION "The index for this table."
 ::= { ppSurvMtaSigCapEntry 1 }

ppSurvMtaSigCapProtocol OBJECT-TYPE
 SYNTAX SignalingProtocol
 MAX-ACCESS read-only
 STATUS obsolete
 DESCRIPTION "A signaling protocol this device supports."
 ::= { ppSurvMtaSigCapEntry 2 }
--===================================================================
ppSurvMtaNumberPorts OBJECT-TYPE
 SYNTAX Integer32
 MAX-ACCESS read-only
 STATUS current
 DESCRIPTION "The number of RJ11s."
 ::= { ppSurveillance 4 }

ppSurvMtaActiveSwBank OBJECT-TYPE
 SYNTAX INTEGER{ a(1), b(2) }
 MAX-ACCESS read-only
 STATUS obsolete
 DESCRIPTION "The active sw bank."
 ::= { ppSurveillance 5 }

ppSurvMtaPowerSupplyTele OBJECT-TYPE
 SYNTAX INTEGER{ tlm-unavailable(0),tlm-invalid(1),tlm-shutdown-warning(2),
                 tlm-batt-reversed-shorted(3),tlm-batt-low-replace-ac-fail(4),
                 tlm-batt-low-replace(5),tlm-batt-low-ac-fail(6),tlm-batt-low(7), 
                 tlm-batt-missing(8),tlm-ac-fail-batt-replace(9),tlm-replace-batt(10),
                 tlm-ac-fail(11), tlm-normal(12), testInProgress(13) }
 MAX-ACCESS read-only
 STATUS current
 DESCRIPTION "The battery telemetry state."
 ::= { ppSurveillance 6 }

ppSurvMtaSoftwareLoadBankA OBJECT-TYPE
 SYNTAX DisplayString(SIZE(0..64))
 MAX-ACCESS read-only
STATUS obsolete
 DESCRIPTION "The current software load in bank A."
 ::= { ppSurveillance 7 }

ppSurvMtaSoftwareLoadBankB OBJECT-TYPE
 SYNTAX DisplayString(SIZE(0..64))
 MAX-ACCESS read-only
 STATUS obsolete
 DESCRIPTION "The current software load in bank B."
 ::= { ppSurveillance 8 }

ppSurvMtaPeccode OBJECT-TYPE
 SYNTAX DisplayString(SIZE(8))
 MAX-ACCESS read-only
 STATUS obsolete
 DESCRIPTION "The peccode of the PacketPort."
 ::= { ppSurveillance 9 }

ppSurvMtaMaintState OBJECT-TYPE
 SYNTAX INTEGER{ isnr(1), istrbl(2), oos(3) }
 MAX-ACCESS read-only
 STATUS current
 DESCRIPTION "The maintenance state of the PacketPort."
 ::= { ppSurveillance 10 }

ppSurvMtaDeviceIdentifier OBJECT-TYPE
 SYNTAX DisplayString
 MAX-ACCESS read-only
 STATUS current
 DESCRIPTION "The device identifier string that is sent in the DHCP offer."
 ::= { ppSurveillance 11 }

ppSurvMtaInitialProvAck OBJECT-TYPE
 SYNTAX TruthValue
 MAX-ACCESS read-only
 STATUS obsolete
 DESCRIPTION "The acknowledgement object for the initial provisioning trap
              ppInitialProvTrap."
 ::= { ppSurveillance 12 }

ppSurvMtaCurrSwFilename OBJECT-TYPE
 SYNTAX DisplayString(SIZE(0..64))
 MAX-ACCESS read-only
 STATUS current
 DESCRIPTION "The filename of the software load currently on
              the device.  This is temporary until the cable modem
              is DOCSIS 1.1 compliant."
 ::= { ppSurveillance 13 }

ppSurvMtaProvStatusAck OBJECT-TYPE
 SYNTAX TruthValue
 MAX-ACCESS read-only
 STATUS obsolete
 DESCRIPTION "The acknowledgement object for the provisioning status trap."
 ::= { ppSurveillance 14 }

ppSurvMtaProvState OBJECT-TYPE
 SYNTAX INTEGER { pass(1),
                  inProgress(2),
                  fail(3)
                }
 MAX-ACCESS read-only
 STATUS obsolete
 DESCRIPTION "This object indicates the completion state of the telephony
              provisioning process.  Pass or Fail states occur after the
              processing of the telephony configuration file is complete.
              InProgress occurs from boot time until config file processing
              is complete.  Fail state requires manual intervention."
 ::= { ppSurveillance 15 }

ppSurvMtaDevCorrelationId OBJECT-TYPE
 SYNTAX Integer32
 MAX-ACCESS read-only
 STATUS obsolete
 DESCRIPTION "Unique value used to correlate provisioning status trap to
              initial provisioning trap."
 ::= { ppSurveillance 16 }

ppSurvMtaBoxIdentifier OBJECT-TYPE
 SYNTAX Integer32
 MAX-ACCESS read-only
 STATUS current
 DESCRIPTION "Identifies the overall Rev level of the PacketPort.  This
              includes all hardware components that make up the box."
 ::= { ppSurveillance 17 }    

 
-- The following group describes the debug objects in the Packet Port MIB

ppSurvMtaDevDebug OBJECT IDENTIFIER ::= { ppSurveillance 18 }

ppSurvMtaDevDebugLevelControlTable OBJECT-TYPE
 SYNTAX SEQUENCE OF PpSurvMtaDevDebugLevelControlEntry
 MAX-ACCESS not-accessible
 STATUS current
 DESCRIPTION "This table allows control of the reporting of debug messages in 
              the PacketPort device. For each system module (i.e. subsystem) 
              of the device, a specific reporting level may be chosen."
 ::= { ppSurvMtaDevDebug 1 }

ppSurvMtaDevDebugLevelControlEntry OBJECT-TYPE
 SYNTAX PpSurvMtaDevDebugLevelControlEntry
 MAX-ACCESS not-accessible
 STATUS current
 DESCRIPTION "Allows configuration of the reporting of debug messages for a 
              particular system module in the PacketPort device."
 INDEX { ppSurvMtaDevDebugModule }
 ::= { ppSurvMtaDevDebugLevelControlTable 1 }
 
PpSurvMtaDevDebugLevelControlEntry ::= SEQUENCE {
     ppSurvMtaDevDebugModule INTEGER,
     ppSurvMtaDevDebugReportingLevel PpDebugReportingLevel
  } 
  
  ppSurvMtaDevDebugModule OBJECT-TYPE
         SYNTAX INTEGER {	
               generic(1),
               callP(2),
               dsp(3),
               lineCard(4),
               ppMtc(5),
               rtp(6)
         }
         MAX-ACCESS not-accessible
         STATUS current
         DESCRIPTION
             "The system module to which this entry applies."
         ::= { ppSurvMtaDevDebugLevelControlEntry 1 }
         
ppSurvMtaDevDebugReportingLevel OBJECT-TYPE
        SYNTAX PpDebugReportingLevel
        MAX-ACCESS read-write
        STATUS     current
        DESCRIPTION
            "Controls the level of debugging output for a particular 
             system module."     
        ::= { ppSurvMtaDevDebugLevelControlEntry 2 }   
        

-- The following group describes the alarm objects in the Packet Port MIB

ppSurvMtaDevAlarms OBJECT IDENTIFIER ::= { ppSurveillance 19 }

ppSurvMtaDevAlarmRetryTimer OBJECT-TYPE
     SYNTAX INTEGER {noRetry(0),
                     thirty(30)
--                     sixty(60)
                    }
     UNITS "seconds"
     MAX-ACCESS read-write
     STATUS current
     DESCRIPTION
         "The amount of time to wait before resending an unACKnowledged alarm."    
     REFERENCE 
         "Packet Port High-Level Design, Issue 0.3, October 1, 1999"  
     DEFVAL { thirty }    
     ::= { ppSurvMtaDevAlarms 1 }
     
-- =========================================================================
-- ppInitialProvTrap TRAP-TYPE
-- ENTERPRISE arris
-- VARIABLES { ppSurvMtaPeccode,
--             ifPhysAddress,  MAC ADDRESS
--             ipAdEntAddr,  IP ADDRESS
--             docsDevSerialNumber,  ESN
--             ppSurvMtaCurrSwFilename,
--             ppSurvMtaDeviceIdentifier,
--             ppCfgMtaProvMethodIndicator,
--             ppSurvMtaDevCorrelationId }
-- DESCRIPTION "This is the initial provisioning trap
--              that indicates DOCSIS provisioning is complete."
-- ::= 100

-- ppProvStatusTrap TRAP-TYPE
-- ENTERPRISE arris
-- VARIABLES { ifPhysAddress,  MAC ADDRESS
--            ppSurvMtaDevCorrelationId,  correlation id
--            ipAdEntAddr,  IP ADDRESS
--            ppSurvMtaProvState  provisionioning state
--          }
-- DESCRIPTION "This trap is issued to confirm the completion
--              of the telephony provisioning process, and indicate
--              the completion state."
-- ::= 101

-- ppLogEventTrap TRAP-TYPE
-- ENTERPRISE arris
-- VARIABLES { ifPhysAddress,  MAC ADDRESS
--             docsDevEvText
--           }
-- DESCRIPTION "This is the generic trap for all
--              PacketPort logs."
-- ::= 200

END

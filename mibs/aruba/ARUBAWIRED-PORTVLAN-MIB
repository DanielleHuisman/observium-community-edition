--**MOD+************************************************************************
--* Module:    ARUBAWIRED-PORTVLAN-MIB :Port VLAN MIB file
--*
--* (c) Copyright 2020 Hewlett Packard Enterprise Development LP
--* All Rights Reserved.
--*
--* The contents of this software are proprietary and confidential
--* to the Hewlett-Packard Development Company, L.P.  No part of this
--* program may be photocopied, reproduced, or translated into another
--* programming language without prior written consent of the
--* Hewlett-Packard Development Company, L.P.
--*
--* Purpose: This file contains MIB definition of ARUBAWIRED-PORTVLAN-MIB
--*
--**MOD-************************************************************************

ARUBAWIRED-PORTVLAN-MIB DEFINITIONS ::= BEGIN

IMPORTS
    MODULE-IDENTITY, OBJECT-TYPE
        FROM SNMPv2-SMI
    MODULE-COMPLIANCE, OBJECT-GROUP
        FROM SNMPv2-CONF
    InterfaceIndex
        FROM IF-MIB
    wndFeatures
        FROM ARUBAWIRED-NETWORKING-OID;

arubaWiredPortVlanMIB MODULE-IDENTITY
    LAST-UPDATED "202011200000Z" -- November 20, 2020
    ORGANIZATION "HPE/Aruba Networking Division"
    CONTACT-INFO "Hewlett Packard Company 8000 Foothills Blvd. Roseville,
                  CA 95747"

    DESCRIPTION   "This MIB module describes objects used to manage the
                   association between physical port and Virtual Local
                   Area Network (VLAN) feature"

    REVISION     "202011200000Z" -- November 20, 2020
    DESCRIPTION  "Initial Revision"
    ::= { wndFeatures 18 }

arubaWiredPortVlanNotifications OBJECT IDENTIFIER ::= { arubaWiredPortVlanMIB 0 }
arubaWiredPortVlanObjects       OBJECT IDENTIFIER ::= { arubaWiredPortVlanMIB 1 }
arubaWiredPortVlanConfig        OBJECT IDENTIFIER ::= { arubaWiredPortVlanObjects 0 }
arubaWiredPortVlanStatus        OBJECT IDENTIFIER ::= { arubaWiredPortVlanObjects 1 }

--*************************************************************
--*    arubaWiredPortVlanMemberTable
--*************************************************************

arubaWiredPortVlanMemberTable OBJECT-TYPE
    SYNTAX      SEQUENCE OF ArubaWiredPortVlanMemberEntry
    MAX-ACCESS  not-accessible
    STATUS      current
    DESCRIPTION "This table contains information about the L2 port associated with
                 VLAN"
    ::= { arubaWiredPortVlanStatus 1 }

arubaWiredPortVlanMemberEntry OBJECT-TYPE
    SYNTAX      ArubaWiredPortVlanMemberEntry
    MAX-ACCESS  not-accessible
    STATUS      current
    DESCRIPTION "A row in the PortVlan member table"
    INDEX   { arubaWiredPortVlanMemberIndex }
    ::= { arubaWiredPortVlanMemberTable 1 }

ArubaWiredPortVlanMemberEntry ::=
    SEQUENCE {
             arubaWiredPortVlanMemberIndex    InterfaceIndex,
             arubaWiredPortVlanMemberMode     INTEGER
             }

arubaWiredPortVlanMemberIndex OBJECT-TYPE
    SYNTAX      InterfaceIndex
    MAX-ACCESS  not-accessible
    STATUS      current
    DESCRIPTION "Port ifindex"
    ::= { arubaWiredPortVlanMemberEntry 1 }

arubaWiredPortVlanMemberMode OBJECT-TYPE
    SYNTAX      INTEGER {
                          trunk  (1),
                          access (2)
                        }
    MAX-ACCESS read-only
    STATUS current
    DESCRIPTION
        "Port VLAN membership mode"
    ::= { arubaWiredPortVlanMemberEntry 2 }

arubaWiredPortVlanConformance OBJECT IDENTIFIER::= { arubaWiredPortVlanMIB 2 }
arubaWiredPortVlanCompliances OBJECT IDENTIFIER::= { arubaWiredPortVlanConformance 1 }
arubaWiredPortVlanGroups      OBJECT IDENTIFIER::= { arubaWiredPortVlanConformance 2 }

arubaWiredPortVlanMemberTableGroup OBJECT-GROUP
    OBJECTS   {
              arubaWiredPortVlanMemberMode
              }
    STATUS      current
    DESCRIPTION "A collection of VLAN table objects."
    ::= { arubaWiredPortVlanGroups 1 }

arubaWiredPortVlanMibCompliance MODULE-COMPLIANCE
    STATUS      current
    DESCRIPTION "The compliance statement for devices implementing the
                 ARUBA WIRED PortVlan Mib."
    MODULE
    MANDATORY-GROUPS {
                     arubaWiredPortVlanMemberTableGroup
                     }
    ::= { arubaWiredPortVlanCompliances 1 }
END

IONLINE-MIB DEFINITIONS ::= BEGIN

IMPORTS
    IpAddress,
    MODULE-IDENTITY,
    OBJECT-TYPE,
    NOTIFICATION-TYPE,
    snmpModules,
    OBJECT-IDENTITY,
    enterprises,
    Counter32,
    Integer32
        FROM SNMPv2-SMI
    DisplayString,
    TEXTUAL-CONVENTION,
    TruthValue,
    DateAndTime
        FROM SNMPv2-TC;


elite   MODULE-IDENTITY
      LAST-UPDATED  "201208220000Z"
      ORGANIZATION  "E Technologies"
      CONTACT-INFO
                        "
                        Postal: XXX
                        E-mail: i@o.c
                        "
      DESCRIPTION
                        "
                        This MIB module defines MIB objects which provide
                            mechanisms to remotely configure the parameters used
                            by 24Online Agent for the generation of SNMP messages.
                        "
    ::= { enterprises 21068 }

--1.3.6.4.1.21068

ionline OBJECT-IDENTITY
    STATUS     current
    DESCRIPTION "This is ionline Description"
    ::= { elite 1 }
--1.3.6.4.1.21068.3

ioPoolStatus    OBJECT IDENTIFIER ::= { ionline 3 }

ioPoolUsage  OBJECT-TYPE
    SYNTAX          Integer32
    MAX-ACCESS      read-write
    STATUS          current
    DESCRIPTION     "% pool usage"
    ::= { ioPoolStatus 1 }

-- Updated Below

ioPoolTable OBJECT-TYPE
    SYNTAX     SEQUENCE OF IoPoolEntry
    MAX-ACCESS not-accessible
    STATUS     current
    DESCRIPTION
            "The (conceptual) table listing the capabilities of
            the local SNMP application acting as a command
            responder with respect to various MIB modules.
            SNMP entities having dynamically-configurable support
            of MIB modules will have a dynamically-varying number
            of conceptual rows."
   ::= {elite 2}

IoPoolEntry ::= SEQUENCE {
    ioPoolORId        OBJECT IDENTIFIER,
    ioPoolORDescr     DisplayString
}

ioPoolEntry OBJECT-TYPE
    SYNTAX     IoPoolEntry
    MAX-ACCESS not-accessible
    STATUS     current
    DESCRIPTION
            "An entry (conceptual row) in the sysORTable."
    INDEX      { sysORIndex }
    ::= { ioPoolTable 1 }

ioPoolORId OBJECT-TYPE
    SYNTAX     OBJECT IDENTIFIER
    MAX-ACCESS read-write
    STATUS     current
    DESCRIPTION
            "An authoritative identification of a capabilities
            statement with respect to various MIB modules supported
            by the local SNMP application acting as a command
            responder."
    ::= { ioPoolEntry 2 }

ioPoolORDescr OBJECT-TYPE
    SYNTAX     DisplayString
    MAX-ACCESS read-only
    STATUS     current
    DESCRIPTION
            "A textual description of the capabilities identified
            by the corresponding instance of sysORID."
    ::= { ioPoolEntry 3 }

-- Updated Above
END

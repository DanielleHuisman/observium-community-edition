-- ATEN International Co., Ltd.
-- 20050913 modified to form a basic frame
-- this file only provides a product-level description, no product-specific allowed
-- if want to know the details of certain products, refer to other documents
-- 20151222 - Add overip 8 for vlstrap purpose
--          - Add kvmoverip 13 for KNGeneric
--          - Modify kvmoverip 3 (KN4140) to KNTrap
--          - Modify kvmoverip 11 (KN1108v/1116v) to KN1108v/1116v Trap
--          - Modify kvmoverip 12 (CN8600) to CN8600 Trap
--          - Remove CCVSR from {software 2}
-- 20180125 - Add poweroverip 3 for pe2 purpose
--          - Modify KL1516Ai to kl1516ai
--          - Modify KH1516Ai to kh1516ai
--          - Modify KNTrap to knTrap
--          - Modify KH2516Ai to kh2516ai
--          - Modify CS1716i to cs1716i
--          - Modify CN8000 to cn8000
--          - Modify KN1001 to kn1001
--          - Modify IP8000 to ip8000
--          - Modify KN1000 to kn1000
--          - Modify KN9016/9008 to kn9016-9008
--          - Modify KN1108v/1116v Trap to kn1108v-1116v-trap
--          - Modify CN8600 Trap to cn8600-trap
--          - Modify KNGeneric to knGeneric
--          - Modify pn7320/7212/5320/5212 to pn7320-7212-5320-5212
--          - Modify PN5101 to pn5101

ATEN-PRODUCTS-MIB DEFINITIONS ::= BEGIN

IMPORTS
    atenProducts
        FROM ATEN-SMI;

--products layer begins
public      OBJECT IDENTIFIER ::= { atenProducts 1 }
software    OBJECT IDENTIFIER ::= { atenProducts 2 }
overip      OBJECT IDENTIFIER ::= { atenProducts 3 }
kvm         OBJECT IDENTIFIER ::= { atenProducts 4 }
video       OBJECT IDENTIFIER ::= { atenProducts 5 }
usb         OBJECT IDENTIFIER ::= { atenProducts 6 }
firewire    OBJECT IDENTIFIER ::= { atenProducts 7 }
--products layer ends
 
-- software layer begins
cc2000   OBJECT IDENTIFIER ::= { software 1 }
-- software layer ends

-- kvm layer begins
matrix    OBJECT IDENTIFIER ::= { kvm 1 }
-- kvm layer ends

-- matrix layer begins
kmxx32    OBJECT IDENTIFIER ::= { matrix 1 }
-- kvm layer ends

--overip layer begins
kvmoverip       OBJECT IDENTIFIER ::= { overip 1 }
poweroverip     OBJECT IDENTIFIER ::= { overip 2 }
serialoverip    OBJECT IDENTIFIER ::= { overip 3 }
vlsoverip       OBJECT IDENTIFIER ::= { overip 8 }
--overip layers ends

--kvmoverip layers begins
kl1516ai              OBJECT IDENTIFIER ::= { kvmoverip 1  }
kh1516ai              OBJECT IDENTIFIER ::= { kvmoverip 2  }
knTrap                OBJECT IDENTIFIER ::= { kvmoverip 3  }
kh2516ai              OBJECT IDENTIFIER ::= { kvmoverip 4  }
cs1716i               OBJECT IDENTIFIER ::= { kvmoverip 5  }
cn8000                OBJECT IDENTIFIER ::= { kvmoverip 6  }
kn1001                OBJECT IDENTIFIER ::= { kvmoverip 7  }
ip8000                OBJECT IDENTIFIER ::= { kvmoverip 8  }
kn1000                OBJECT IDENTIFIER ::= { kvmoverip 9  }
kn9016-9008           OBJECT IDENTIFIER ::= { kvmoverip 10 }
kn1108v-1116v-trap    OBJECT IDENTIFIER ::= { kvmoverip 11 }
cn8600-trap           OBJECT IDENTIFIER ::= { kvmoverip 12 }
knGeneric             OBJECT IDENTIFIER ::= { kvmoverip 13 }
--kvmoverip layers ends

--poweroverip layers begins
pn9108                   OBJECT IDENTIFIER ::= { poweroverip 1  }
pe                       OBJECT IDENTIFIER ::= { poweroverip 2  }
pe2                      OBJECT IDENTIFIER ::= { poweroverip 3  }
pn7320-7212-5320-5212    OBJECT IDENTIFIER ::= { poweroverip 30 }
pn5101                   OBJECT IDENTIFIER ::= { poweroverip 35 }
--poweroverip layers ends

--serialoverip layers begins
sn0116a    OBJECT IDENTIFIER ::= { serialoverip 1 }
sn3101     OBJECT IDENTIFIER ::= { serialoverip 2 }
sn0148     OBJECT IDENTIFIER ::= { serialoverip 3 }
--serialoverip layers ends

END

ATMEDIA-MIB DEFINITIONS ::= BEGIN

--
-- MIB definied by ATMedia GmbH
-- for use with ATMedia Encryptors
-- (c) 2002-2007 ATMedia GmbH
--

IMPORTS
    OBJECT-TYPE, TimeTicks, Counter32,
    Gauge32, Counter64, enterprises        FROM SNMPv2-SMI

    DateAndTime                            FROM SNMPv2-TC;

DisplayString ::= OCTET STRING

atmedia            OBJECT IDENTIFIER ::= { enterprises 13458 }

atmcrypt           OBJECT IDENTIFIER ::= { atmedia 1 }

acMachine         OBJECT IDENTIFIER ::= { atmcrypt 1 }
acSoftware        OBJECT IDENTIFIER ::= { atmcrypt 2 }
acHardware        OBJECT IDENTIFIER ::= { atmcrypt 3 }
acStatus          OBJECT IDENTIFIER ::= { atmcrypt 4 }
acMaintenance     OBJECT IDENTIFIER ::= { atmcrypt 5 }
acTransmission    OBJECT IDENTIFIER ::= { atmcrypt 6 }

acInterfaces      OBJECT IDENTIFIER ::= { acHardware 3 }
acEncryptors      OBJECT IDENTIFIER ::= { acHardware 4 }

acInterfaceStatus OBJECT IDENTIFIER ::= { acStatus 1 }
acEncryptorStatus OBJECT IDENTIFIER ::= { acStatus 2 }

-- media dependend status / alarm counter

acSonet           OBJECT IDENTIFIER ::= { acTransmission 1 }
acE3              OBJECT IDENTIFIER ::= { acTransmission 2 }
acE1              OBJECT IDENTIFIER ::= { acTransmission 3 }
acGigabit         OBJECT IDENTIFIER ::= { acTransmission 4 }
acFibrechannel    OBJECT IDENTIFIER ::= { acTransmission 5 }

acSonetStatus      OBJECT IDENTIFIER ::= { acSonet 1 }
acSonetAlarms      OBJECT IDENTIFIER ::= { acSonet 2 }
acSonetErrCounter  OBJECT IDENTIFIER ::= { acSonet 3 }
acSonetEtsCounter  OBJECT IDENTIFIER ::= { acSonet 4 }

acE3Status        OBJECT IDENTIFIER ::= { acE3 1 }
acE3Alarms        OBJECT IDENTIFIER ::= { acE3 2 }
acE3ErrCounter    OBJECT IDENTIFIER ::= { acE3 3 }
acE3EtsCounter    OBJECT IDENTIFIER ::= { acE3 4 }

acE1Status        OBJECT IDENTIFIER ::= { acE1 1 }
acE1Alarms        OBJECT IDENTIFIER ::= { acE1 2 }
acE1ErrCounter    OBJECT IDENTIFIER ::= { acE1 3 }
acE1EtsCounter    OBJECT IDENTIFIER ::= { acE1 4 }

acGigabitStatus        OBJECT IDENTIFIER ::= { acGigabit 1 }
acGigabitAlarms        OBJECT IDENTIFIER ::= { acGigabit 2 }
acGigabitErrCounter    OBJECT IDENTIFIER ::= { acGigabit 3 }
acGigabitEtsCounter    OBJECT IDENTIFIER ::= { acGigabit 4 }

acFibrechannelStatus        OBJECT IDENTIFIER ::= { acFibrechannel 1 }
acFibrechannelAlarms        OBJECT IDENTIFIER ::= { acFibrechannel 2 }
acFibrechannelErrCounter    OBJECT IDENTIFIER ::= { acFibrechannel 3 }
acFibrechannelEtsCounter    OBJECT IDENTIFIER ::= { acFibrechannel 4 }

--
-- acMachine part
-- 

acProductID OBJECT-TYPE
    SYNTAX      DisplayString
    MAX-ACCESS  read-only
    STATUS      current
    DESCRIPTION
	"The product identifier of the ATMedia Encryptor device."
    ::= { acMachine 1 }

acSerialNumber OBJECT-TYPE
    SYNTAX      DisplayString
    MAX-ACCESS  read-only
    STATUS      current
    DESCRIPTION
	"The serial number of the ATMedia Encryptor device."
    ::= { acMachine 2 }

acHostname OBJECT-TYPE
    SYNTAX      DisplayString
    MAX-ACCESS  read-only
    STATUS      current
    DESCRIPTION
	"The actual host name of the ATMedia Encryptor device."
    ::= { acMachine 3 }

acContact OBJECT-TYPE
    SYNTAX      DisplayString
    MAX-ACCESS  read-only
    STATUS      current
    DESCRIPTION
	"The contact person for ATMedia Encryptor administration."
    ::= { acMachine 4 }

acLocation OBJECT-TYPE
    SYNTAX      DisplayString
    MAX-ACCESS  read-only
    STATUS      current
    DESCRIPTION
	"The location of the ATMedia Encryptor device."
    ::= { acMachine 5 }

acDescr OBJECT-TYPE
    SYNTAX      DisplayString
    MAX-ACCESS  read-only
    STATUS      current
    DESCRIPTION
	"The description of the ATMedia Encryptor device."
    ::= { acMachine 6 }


--
-- acSoftware part
-- 

acSoftVersion OBJECT-TYPE
    SYNTAX      DisplayString
    MAX-ACCESS  read-only
    STATUS      current
    DESCRIPTION
	"The software version running on the ATMedia Encryptor device."
    ::= { acSoftware 1 }

acSoftDescr OBJECT-TYPE
    SYNTAX      DisplayString
    MAX-ACCESS  read-only
    STATUS      current
    DESCRIPTION
	"Description of the ATMedia Encryptor software."
    ::= { acSoftware 2 }

    
--
-- acHardware part
-- 

acHardVersion OBJECT-TYPE
    SYNTAX      DisplayString
    MAX-ACCESS  read-only
    STATUS      current
    DESCRIPTION
	"The hardware version of the ATMedia Encryptor device."
    ::= { acHardware 1 }

acHardDescr OBJECT-TYPE
    SYNTAX      DisplayString
    MAX-ACCESS  read-only
    STATUS      current
    DESCRIPTION
	"Description of the ATMedia Encryptor hardware."
    ::= { acHardware 2 }


--
-- acInterfaces part
--

acIfNumber OBJECT-TYPE
    SYNTAX      INTEGER
    MAX-ACCESS  read-only
    STATUS      current
    DESCRIPTION
        "The number of physical ATMedia Encryptor interfaces."
    ::= { acInterfaces 1 }

acIfTable OBJECT-TYPE
    SYNTAX      SEQUENCE OF AcIfEntry
    MAX-ACCESS  not-accessible
    STATUS      current
    DESCRIPTION
            "A list of physical ATMedia Encryptor interfaces.  
	    The number of entries is given by the value 
	    of acsIfNumber."
    ::= { acInterfaces 2 }

acIfEntry OBJECT-TYPE
    SYNTAX      AcIfEntry
    MAX-ACCESS  not-accessible
    STATUS      current
    DESCRIPTION
            "An entry containing management information 
	    applicable to a particular physical interface."
    INDEX   { acIfIndex }
    ::= { acIfTable 1 }

AcIfEntry ::=
    SEQUENCE {
        acIfIndex                 INTEGER,
        acIfDescr                 DisplayString,
        acIfPhyType               INTEGER,
        acIfSpeed                 Gauge32,
        acIfRevision              DisplayString
    }

acIfIndex OBJECT-TYPE
    SYNTAX      INTEGER
    MAX-ACCESS  read-only
    STATUS      current
    DESCRIPTION
            "A unique value, greater than zero, for each physical
	    interface.  It is recommended that values are assigned
	    contiguously starting from 1.  The value for each interface
            must remain constant at least from one re-initialization of
            the entity's network management system to the next re-
            initialization."
    ::= { acIfEntry 1 }
    
acIfDescr OBJECT-TYPE    
    SYNTAX      DisplayString
    MAX-ACCESS  read-only
    STATUS      current
    DESCRIPTION
	    "Description of the physical interface."
    ::= { acIfEntry 2 } 
    
acIfPhyType OBJECT-TYPE    
    SYNTAX      INTEGER {
	          other(0),   -- none of the following
                  sonet(1),   -- SONET/SDH standard
                  e3(2),      -- PDH standard E3
                  ds3(3),     -- PDH standard DS3
                  e1(4),      -- E1 standard
                  ds1(5),     -- DS1/T1 standard
                  gigabit(6), -- 1000Base-X (IEEE 802.3z)
                  sonetlink(7), -- SONET/SDH link
                  fibrechannel(8), -- Fibrechannel
                  ethernet(9) -- Ethernet 10/100
                }
    MAX-ACCESS  read-only
    STATUS      current
    DESCRIPTION
	    "Type of the physical interface."
    ::= { acIfEntry 3 } 
    
acIfSpeed OBJECT-TYPE    
    SYNTAX      Gauge32
    MAX-ACCESS  read-only
    STATUS      current
    DESCRIPTION
	    "Speed of the physical interface in bps."
    ::= { acIfEntry 4 } 
    
acIfRevision OBJECT-TYPE    
    SYNTAX      DisplayString
    MAX-ACCESS  read-only
    STATUS      current
    DESCRIPTION
	    "Revision of the physical interface."
    ::= { acIfEntry 5 } 
    
--
-- acEncryptors part
--

acEcNumber OBJECT-TYPE
    SYNTAX      INTEGER
    MAX-ACCESS  read-only
    STATUS      current
    DESCRIPTION
        "The number of ATMedia encryptor engines."
    ::= { acEncryptors 1 }

acEcTable OBJECT-TYPE
    SYNTAX      SEQUENCE OF AcEcEntry
    MAX-ACCESS  not-accessible
    STATUS      current
    DESCRIPTION
            "A list of ATMedia encryptor engines. The number 
	    of entries is given by the value of acsEcNumber."
    ::= { acEncryptors 2 }

acEcEntry OBJECT-TYPE
    SYNTAX      AcEcEntry
    MAX-ACCESS  not-accessible
    STATUS      current
    DESCRIPTION
            "An entry containing management information 
	    applicable to a particular encryptor engine."
    INDEX   { acEcIndex }
    ::= { acEcTable 1 }

AcEcEntry ::=
    SEQUENCE {
        acEcIndex                 INTEGER,
        acEcDescr                 DisplayString,
        acEcRevision              DisplayString
    }

acEcIndex OBJECT-TYPE
    SYNTAX      INTEGER
    MAX-ACCESS  read-only
    STATUS      current
    DESCRIPTION
            "A unique value, greater than zero, for each encryptor
	    engine.  It is recommended that values are assigned
	    contiguously starting from 1.  The value for each encryptor
            must remain constant at least from one re-initialization of
            the entity's network management system to the next re-
            initialization."
    ::= { acEcEntry 1 }
    
acEcDescr OBJECT-TYPE    
    SYNTAX      DisplayString
    MAX-ACCESS  read-only
    STATUS      current
    DESCRIPTION
	    "Description of the encryptor engine."
    ::= { acEcEntry 2 } 
    
acEcRevision OBJECT-TYPE    
    SYNTAX      DisplayString
    MAX-ACCESS  read-only
    STATUS      current
    DESCRIPTION
	    "Revision of the encryptor engine."
    ::= { acEcEntry 3 } 
    
--
-- acInterfaceStatus part
--

acInterfaceStatusNumber OBJECT-TYPE
    SYNTAX      INTEGER
    MAX-ACCESS  read-only
    STATUS      current
    DESCRIPTION
        "The number of ATMedia Encryptor physical interfaces."
    ::= { acInterfaceStatus 1 }

acInterfaceStatusTable OBJECT-TYPE
    SYNTAX      SEQUENCE OF AcInterfaceStatusEntry
    MAX-ACCESS  not-accessible
    STATUS      current
    DESCRIPTION
            "A list of interface cell counter informations. The number
	    of entries is given by the value of acInferfaceStatusNumber."
    ::= { acInterfaceStatus 2 }

acInterfaceStatusEntry OBJECT-TYPE
    SYNTAX      AcInterfaceStatusEntry
    MAX-ACCESS  not-accessible
    STATUS      current
    DESCRIPTION
            "An entry containing alarm informations applicable
	    to a particular physical interface."
    INDEX   { acInterfaceStatusIndex }
    ::= { acInterfaceStatusTable 1 }

AcInterfaceStatusEntry ::=
    SEQUENCE {
        acInterfaceStatusIndex               INTEGER,
        acInterfaceStatusState               INTEGER, 
        acInterfaceStatusLastChange          TimeTicks,
        acInterfaceStatusDescr               DisplayString, 
	acInterfaceStatusRxCells             Counter64,
	acInterfaceStatusTxCells             Counter64,
	acInterfaceStatusRxBytes             Counter64,
	acInterfaceStatusTxBytes             Counter64,
	acInterfaceStatusRxRate              Gauge32,
	acInterfaceStatusTxRate              Gauge32
    }

acInterfaceStatusIndex OBJECT-TYPE
    SYNTAX      INTEGER
    MAX-ACCESS  read-only
    STATUS      current
    DESCRIPTION
            "A unique value, greater than zero, for each physical
	    interface.  It is recommended that values are assigned
	    contiguously starting from 1.  The value for each interface
            must remain constant at least from one re-initialization of
            the entity's network management system to the next re-
            initialization."
    ::= { acInterfaceStatusEntry 1 }
    
acInterfaceStatusState OBJECT-TYPE
    SYNTAX      INTEGER { 
                  up(1),    -- ready to pass packets
                  down(2)
                }
    MAX-ACCESS  read-only
    STATUS      current
    DESCRIPTION
            "The current operational state of the interface."
    ::= { acInterfaceStatusEntry 2 }
    
acInterfaceStatusLastChange OBJECT-TYPE
    SYNTAX      TimeTicks
    MAX-ACCESS  read-only
    STATUS      current
    DESCRIPTION
            "The value of sysUpTime at the time the interface
            entered its current operational state."
    ::= { acInterfaceStatusEntry 3 }
    
acInterfaceStatusDescr OBJECT-TYPE    
    SYNTAX      DisplayString
    MAX-ACCESS  read-only
    STATUS      current
    DESCRIPTION
	    "Description of the encryptor engine status."
    ::= { acInterfaceStatusEntry 4 } 
    
acInterfaceStatusRxCells OBJECT-TYPE
    SYNTAX      Counter64
    MAX-ACCESS  read-only
    STATUS      current
    DESCRIPTION
             "Number of cells received by the physical interface."
    ::= { acInterfaceStatusEntry 5 }

acInterfaceStatusTxCells OBJECT-TYPE
    SYNTAX      Counter64
    MAX-ACCESS  read-only
    STATUS      current
    DESCRIPTION
             "Number of cells sent by the physical interface."
    ::= { acInterfaceStatusEntry 6 }

acInterfaceStatusRxBytes OBJECT-TYPE
    SYNTAX      Counter64
    MAX-ACCESS  read-only
    STATUS      current
    DESCRIPTION
             "Number of bytes received by the physical interface."
    ::= { acInterfaceStatusEntry 7 }

acInterfaceStatusTxBytes OBJECT-TYPE
    SYNTAX      Counter64
    MAX-ACCESS  read-only
    STATUS      current
    DESCRIPTION
             "Number of bytes sent by the physical interface."
    ::= { acInterfaceStatusEntry 8 }

acInterfaceStatusRxRate OBJECT-TYPE
    SYNTAX      Gauge32
    MAX-ACCESS  read-only
    STATUS      current
    DESCRIPTION
             "Data rate with which cells are received by the
	     physical interface."
    ::= { acInterfaceStatusEntry 9 }

acInterfaceStatusTxRate OBJECT-TYPE
    SYNTAX      Gauge32
    MAX-ACCESS  read-only
    STATUS      current
    DESCRIPTION
             "Data rate with which cells are sent by the physical
	     interface."
    ::= { acInterfaceStatusEntry 10 }

--
-- acEncryptors part
--

acEncryptorStatusNumber OBJECT-TYPE
    SYNTAX      INTEGER
    MAX-ACCESS  read-only
    STATUS      current
    DESCRIPTION
        "The number of ATMedia encryptor engines."
    ::= { acEncryptorStatus 1 }

acEncryptorStatusTable OBJECT-TYPE
    SYNTAX      SEQUENCE OF AcEncryptorStatusEntry
    MAX-ACCESS  not-accessible
    STATUS      current
    DESCRIPTION
            "A list of ATMedia encryptor engine status
	    informations. The number of entries is given
	    by the value of acsEcstatNumber."
    ::= { acEncryptorStatus 2 }

acEncryptorStatusEntry OBJECT-TYPE
    SYNTAX      AcEncryptorStatusEntry
    MAX-ACCESS  not-accessible
    STATUS      current
    DESCRIPTION
            "An entry containing status information 
	    applicable to a particular encryptor engine."
    INDEX   { acEncryptorStatusIndex }
    ::= { acEncryptorStatusTable 1 }

AcEncryptorStatusEntry ::=
    SEQUENCE {
        acEncryptorStatusIndex             INTEGER,
	acEncryptorStatusState             INTEGER,
        acEncryptorStatusLastChange        TimeTicks,
        acEncryptorStatusDescr             DisplayString
    }

acEncryptorStatusIndex OBJECT-TYPE
    SYNTAX      INTEGER
    MAX-ACCESS  read-only
    STATUS      current
    DESCRIPTION
            "A unique value, greater than zero, for each encryptor
	    engine.  It is recommended that values are assigned
	    contiguously starting from 1.  The value for each encryptor
            must remain constant at least from one re-initialization of
            the entity's network management system to the next re-
            initialization."
    ::= { acEncryptorStatusEntry 1 }
    
acEncryptorStatusState OBJECT-TYPE    
    SYNTAX      INTEGER {
                  up(1),         -- encryptor running
                  down(2),       -- encryptor stopped
                  plain(3)       -- plaintext (version 2.1)
                }
    MAX-ACCESS  read-only
    STATUS      current
    DESCRIPTION
	    "Status of the encryptor engine. Since version 2.1 all encryptors
       will distinguish between crypt (running) and plaintext mode"
    ::= { acEncryptorStatusEntry 2 } 
    
acEncryptorStatusLastChange OBJECT-TYPE
    SYNTAX      TimeTicks
    MAX-ACCESS  read-only
    STATUS      current
    DESCRIPTION
            "The value of sysUpTime at the time the encryptor
            entered its current operational state."
    ::= { acEncryptorStatusEntry 3 }
    
acEncryptorStatusDescr OBJECT-TYPE    
    SYNTAX      DisplayString
    MAX-ACCESS  read-only
    STATUS      current
    DESCRIPTION
	    "Description of the encryptor engine status."
    ::= { acEncryptorStatusEntry 4 } 
    
--
-- acMaintenance part
--

acMaUptime OBJECT-TYPE
    SYNTAX      TimeTicks
    MAX-ACCESS  read-only
    STATUS      current
    DESCRIPTION
        "Hundredth of seconds since system start."
    ::= { acMaintenance 1 }

acMaLastBoot OBJECT-TYPE
    SYNTAX      TimeTicks
    MAX-ACCESS  read-only
    STATUS      current
    DESCRIPTION
        "Hundredth of seconds since last reboot."
    ::= { acMaintenance 2 }

acMaSystime OBJECT-TYPE
    SYNTAX      DateAndTime
    MAX-ACCESS  read-only
    STATUS      current
    DESCRIPTION
        "System Date/Time of ATMedia Encryptor device (UTC)."
    ::= { acMaintenance 3 }

acMaTemperature OBJECT-TYPE
    SYNTAX      Gauge32
    MAX-ACCESS  read-only
    STATUS      current
    DESCRIPTION
        "Temperature of ATMedia Encryptor device in hundredth of degree celsius."
    ::= { acMaintenance 4 }

acMaCpuTemperature1 OBJECT-TYPE
    SYNTAX      Gauge32
    MAX-ACCESS  read-only
    STATUS      current
    DESCRIPTION
        "Temperature of the first CPU of the ATMedia Encryptor device 
	in hundredth of degree celsius."
    ::= { acMaintenance 5 }

acMaCpuTemperature2 OBJECT-TYPE
    SYNTAX      Gauge32
    MAX-ACCESS  read-only
    STATUS      current
    DESCRIPTION
        "Temperature of the second CPU of the ATMedia Encryptor device 
	in hundredth of degree celsius."
    ::= { acMaintenance 6 }

acMaFanSpeed1 OBJECT-TYPE
    SYNTAX      Gauge32
    MAX-ACCESS  read-only
    STATUS      current
    DESCRIPTION
        "Speed of the first fan of the ATMedia Encryptor device in rpm
	(revolutions per minute)"
    ::= { acMaintenance 7 }

acMaFanSpeed2 OBJECT-TYPE
    SYNTAX      Gauge32
    MAX-ACCESS  read-only
    STATUS      current
    DESCRIPTION
        "Speed of the second fan of the ATMedia Encryptor device in rpm
	(revolutions per minute)"
    ::= { acMaintenance 8 }

acMaFanSpeed3 OBJECT-TYPE
    SYNTAX      Gauge32
    MAX-ACCESS  read-only
    STATUS      current
    DESCRIPTION
        "Speed of the third fan of the ATMedia Encryptor device in rpm
	(revolutions per minute)"
    ::= { acMaintenance 9 }

acMaFanSpeed4 OBJECT-TYPE
    SYNTAX      Gauge32
    MAX-ACCESS  read-only
    STATUS      current
    DESCRIPTION
        "Speed of the fourth fan of the ATMedia Encryptor device in rpm
	(revolutions per minute)"
    ::= { acMaintenance 10 }
    
acMaPowerState OBJECT-TYPE
    SYNTAX      INTEGER { 
                  unknown(0),       -- unknown state
	          up(1),            -- power supply ok
                  down(2)           -- power failure detected
                }
    MAX-ACCESS  read-only
    STATUS      current
    DESCRIPTION
        "State of the power supply of the ATMedia Encryptor device"
    ::= { acMaintenance 11 }
    
acMaPowerLastChange OBJECT-TYPE
    SYNTAX      TimeTicks
    MAX-ACCESS  read-only
    STATUS      current
    DESCRIPTION
            "The value of sysUpTime at the time the power supply
            entered its current state."
    ::= { acMaintenance 12 }

--
-- acSonetStatus part
--

acSonetStatusNumber OBJECT-TYPE
    SYNTAX      INTEGER
    MAX-ACCESS  read-only
    STATUS      current
    DESCRIPTION
        "The number of physical Sonet interfaces."
    ::= { acSonetStatus 1 }

acSonetStatusTable OBJECT-TYPE
    SYNTAX      SEQUENCE OF AcSonetStatusEntry
    MAX-ACCESS  not-accessible
    STATUS      current
    DESCRIPTION
            "A list of physical Sonet interface status
	    informations. The number of entries is given by
	    the value of acsIfstatNumber."
    ::= { acSonetStatus 2 }

acSonetStatusEntry OBJECT-TYPE
    SYNTAX      AcSonetStatusEntry
    MAX-ACCESS  not-accessible
    STATUS      current
    DESCRIPTION
            "An entry containing status information 
	    applicable to a particular Sonet physical interface."
    INDEX   { acSonetStatusIndex }
    ::= { acSonetStatusTable 1 }

AcSonetStatusEntry ::=
    SEQUENCE {
        acSonetStatusIndex         INTEGER,
	acSonetStatusState         INTEGER,
	acSonetStatusLOS           INTEGER,
	acSonetStatusOOF           INTEGER,
	acSonetStatusLOC           INTEGER,
	acSonetStatusLineAIS       INTEGER,
	acSonetStatusLineRDI       INTEGER,
	acSonetStatusPathAIS       INTEGER,
	acSonetStatusPathYellow    INTEGER,
	acSonetStatusCustom        INTEGER,
        acSonetStatusDescr         DisplayString
    }

acSonetStatusIndex OBJECT-TYPE
    SYNTAX      INTEGER
    MAX-ACCESS  read-only
    STATUS      current
    DESCRIPTION
            "A unique value, greater than zero, for each physical
	    interface.  It is recommended that values are assigned
	    contiguously starting from 1.  The value for each interface
            must remain constant at least from one re-initialization of
            the entity's network management system to the next re-
            initialization."
    ::= { acSonetStatusEntry 1 }
    
acSonetStatusState OBJECT-TYPE    
    SYNTAX      INTEGER { 
	          up(1),         -- interface running
                  down(2),       -- interface not running
                  failure(3)     -- some error detected
                }
    MAX-ACCESS  read-only
    STATUS      current
    DESCRIPTION
	    "Status of the physical Sonet interface."
    ::= { acSonetStatusEntry 2 } 
    
acSonetStatusLOS OBJECT-TYPE
    SYNTAX      INTEGER {
	          active(1),     -- alarm set
                  inactive(2)    -- alarm not set
                }
    MAX-ACCESS  read-only
    STATUS      current
    DESCRIPTION
             "Alarm condition of type LOS at the 
	     physical Sonet interface."
    ::= { acSonetStatusEntry 3 }

acSonetStatusOOF OBJECT-TYPE
    SYNTAX      INTEGER {
	          active(1),     -- alarm set
                  inactive(2)    -- alarm not set
                }
    MAX-ACCESS  read-only
    STATUS      current
    DESCRIPTION
             "Alarm condition of type OOF at the 
	     physical Sonet interface."
    ::= { acSonetStatusEntry 4 }

acSonetStatusLOC OBJECT-TYPE
    SYNTAX      INTEGER {
	          active(1),     -- alarm set
                  inactive(2)    -- alarm not set
                }
    MAX-ACCESS  read-only
    STATUS      current
    DESCRIPTION
             "Alarm condition of type LOC at the 
	     physical Sonet interface."
    ::= { acSonetStatusEntry 5 }

acSonetStatusLineAIS OBJECT-TYPE
    SYNTAX      INTEGER {
	          active(1),     -- alarm set
                  inactive(2)    -- alarm not set
                }
    MAX-ACCESS  read-only
    STATUS      current
    DESCRIPTION
             "Alarm condition of type LineAIS at the 
	     physical Sonet interface."
    ::= { acSonetStatusEntry 6 }

acSonetStatusLineRDI OBJECT-TYPE
    SYNTAX      INTEGER {
	          active(1),     -- alarm set
                  inactive(2)    -- alarm not set
                }
    MAX-ACCESS  read-only
    STATUS      current
    DESCRIPTION
             "Alarm condition of type LineRDI at the 
	     physical Sonet interface."
    ::= { acSonetStatusEntry 7 }

acSonetStatusPathAIS OBJECT-TYPE
    SYNTAX      INTEGER {
	          active(1),     -- alarm set
                  inactive(2)    -- alarm not set
                }
    MAX-ACCESS  read-only
    STATUS      current
    DESCRIPTION
             "Alarm condition of type PathAIS at the 
	     physical Sonet interface."
    ::= { acSonetStatusEntry 8 }

acSonetStatusPathYellow OBJECT-TYPE
    SYNTAX      INTEGER {
	          active(1),     -- alarm set
                  inactive(2)    -- alarm not set
                }
    MAX-ACCESS  read-only
    STATUS      current
    DESCRIPTION
             "Alarm condition of type PathYellow at the 
	     physical Sonet interface."
    ::= { acSonetStatusEntry 9 }

acSonetStatusCustom OBJECT-TYPE
    SYNTAX      INTEGER
    MAX-ACCESS  read-only
    STATUS      current
    DESCRIPTION
              "Numerical status information of the physical 
              Sonet interface.  The AcSonetStatusCustom is a 
              bit map represented as a sum, therefore,
              it can represent multiple defects simultaneously.

              The various bit positions are:
                0x0001  STATUS_LOS
                0x0002  STATUS_LOP
                0x0004  STATUS_LINE_AIS
                0x0008  STATUS_PATH_AIS
                0x0010  STATUS_PATH_YELLOW
                0x0020  STATUS_STS_OOF
                0x0040  STATUS_STS_LOF
                0x0080  STATUS_STS_LOF23
                0x0100  STATUS_LOC
                0x0200  STATUS_LINE_FERF
                0x1000  STATUS_PATH_FERF"
    ::= { acSonetStatusEntry 10 }

acSonetStatusDescr OBJECT-TYPE    
    SYNTAX      DisplayString
    MAX-ACCESS  read-only
    STATUS      current
    DESCRIPTION
	    "Textual description of the status of the physical 
	    Sonet interface."
    ::= { acSonetStatusEntry 11 } 


--
-- acSonetAlarms part
--

acSonetAlarmsNumber OBJECT-TYPE
    SYNTAX      INTEGER
    MAX-ACCESS  read-only
    STATUS      current
    DESCRIPTION
        "The number of physical Sonet interfaces."
    ::= { acSonetAlarms 1 }

acSonetAlarmsTable OBJECT-TYPE
    SYNTAX      SEQUENCE OF AcSonetAlarmsEntry
    MAX-ACCESS  not-accessible
    STATUS      current
    DESCRIPTION
            "A list of Sonet interface alarm informations. The number
	    of entries is given by the value of acSonetAlarmsNumber."
    ::= { acSonetAlarms 2 }

acSonetAlarmsEntry OBJECT-TYPE
    SYNTAX      AcSonetAlarmsEntry
    MAX-ACCESS  not-accessible
    STATUS      current
    DESCRIPTION
            "An entry containing alarm informations applicable
	    to a particular physical Sonet interface."
    INDEX   { acSonetAlarmsIndex }
    ::= { acSonetAlarmsTable 1 }

AcSonetAlarmsEntry ::=
    SEQUENCE {
        acSonetAlarmsIndex             INTEGER,
	acSonetAlarmsLOS               Counter64,
	acSonetAlarmsLineAIS           Counter64,
	acSonetAlarmsLineRDI           Counter64,
	acSonetAlarmsPathAIS           Counter64,
	acSonetAlarmsPathYellow        Counter64
    }

acSonetAlarmsIndex OBJECT-TYPE
    SYNTAX      INTEGER
    MAX-ACCESS  read-only
    STATUS      current
    DESCRIPTION
            "A unique value, greater than zero, for each physical
	    interface.  It is recommended that values are assigned
	    contiguously starting from 1.  The value for each interface
            must remain constant at least from one re-initialization of
            the entity's network management system to the next re-
            initialization."
    ::= { acSonetAlarmsEntry 1 }
    
acSonetAlarmsLOS OBJECT-TYPE
    SYNTAX      Counter64
    MAX-ACCESS  read-only
    STATUS      current
    DESCRIPTION
             "Number of alarm conditions of type LOS at the 
	     physical interface."
    ::= { acSonetAlarmsEntry 2 }

acSonetAlarmsLineAIS OBJECT-TYPE
    SYNTAX      Counter64
    MAX-ACCESS  read-only
    STATUS      current
    DESCRIPTION
             "Number of alarm conditions of type LineAIS at the 
	     physical interface."
    ::= { acSonetAlarmsEntry 3 }

acSonetAlarmsLineRDI OBJECT-TYPE
    SYNTAX      Counter64
    MAX-ACCESS  read-only
    STATUS      current
    DESCRIPTION
             "Number of alarm conditions of type LineRDI at the 
	     physical interface."
    ::= { acSonetAlarmsEntry 4 }

acSonetAlarmsPathAIS OBJECT-TYPE
    SYNTAX      Counter64
    MAX-ACCESS  read-only
    STATUS      current
    DESCRIPTION
             "Number of alarm conditions of type PathAIS at the 
	     physical interface."
    ::= { acSonetAlarmsEntry 5 }

acSonetAlarmsPathYellow OBJECT-TYPE
    SYNTAX      Counter64
    MAX-ACCESS  read-only
    STATUS      current
    DESCRIPTION
             "Number of alarm conditions of type PathYellow at the 
	     physical interface."
    ::= { acSonetAlarmsEntry 6 }

--
-- acSonetErrCounter part
--

acSonetErrCounterNumber OBJECT-TYPE
    SYNTAX      INTEGER
    MAX-ACCESS  read-only
    STATUS      current
    DESCRIPTION
        "The number of physical Sonet interfaces."
    ::= { acSonetErrCounter 1 }

acSonetErrCounterTable OBJECT-TYPE
    SYNTAX      SEQUENCE OF AcSonetErrCounterEntry
    MAX-ACCESS  not-accessible
    STATUS      current
    DESCRIPTION
            "A list of Sonet interface alarm informations. The number
	    of entries is given by the value of acSonetErrCounterNumber."
    ::= { acSonetErrCounter 2 }

acSonetErrCounterEntry OBJECT-TYPE
    SYNTAX      AcSonetErrCounterEntry
    MAX-ACCESS  not-accessible
    STATUS      current
    DESCRIPTION
            "An entry containing alarm informations applicable
	    to a particular physical Sonet interface."
    INDEX   { acSonetErrCounterIndex }
    ::= { acSonetErrCounterTable 1 }

AcSonetErrCounterEntry ::=
    SEQUENCE {
        acSonetErrCounterIndex             INTEGER,
	acSonetErrCounterOOF               Counter64,
	acSonetErrCounterLOC               Counter64,
	acSonetErrCounterB1BIP             Counter64,
	acSonetErrCounterB2BIP             Counter64,
	acSonetErrCounterB3BIP             Counter64,
	acSonetErrCounterLineFEBE          Counter64,
	acSonetErrCounterPathFEBE          Counter64,
	acSonetErrCounterHEC               Counter64
    }

acSonetErrCounterIndex OBJECT-TYPE
    SYNTAX      INTEGER
    MAX-ACCESS  read-only
    STATUS      current
    DESCRIPTION
            "A unique value, greater than zero, for each physical
	    interface.  It is recommended that values are assigned
	    contiguously starting from 1.  The value for each interface
            must remain constant at least from one re-initialization of
            the entity's network management system to the next re-
            initialization."
    ::= { acSonetErrCounterEntry 1 }
    
acSonetErrCounterOOF OBJECT-TYPE
    SYNTAX      Counter64
    MAX-ACCESS  read-only
    STATUS      current
    DESCRIPTION
             "Number of error conditions of type OOF at the 
	     physical interface."
    ::= { acSonetErrCounterEntry 2 }

acSonetErrCounterLOC OBJECT-TYPE
    SYNTAX      Counter64
    MAX-ACCESS  read-only
    STATUS      current
    DESCRIPTION
             "Number of error conditions of type LOC at the 
	     physical interface."
    ::= { acSonetErrCounterEntry 3 }

acSonetErrCounterB1BIP OBJECT-TYPE
    SYNTAX      Counter64
    MAX-ACCESS  read-only
    STATUS      current
    DESCRIPTION
             "Number of error conditions of type B1BIP at the 
	     physical interface."
    ::= { acSonetErrCounterEntry 4 }

acSonetErrCounterB2BIP OBJECT-TYPE
    SYNTAX      Counter64
    MAX-ACCESS  read-only
    STATUS      current
    DESCRIPTION
             "Number of error conditions of type B2BIP at the 
	     physical interface."
    ::= { acSonetErrCounterEntry 5 }

acSonetErrCounterB3BIP      OBJECT-TYPE
    SYNTAX      Counter64
    MAX-ACCESS  read-only
    STATUS      current
    DESCRIPTION
             "Number of error conditions of type B3BIP at the 
	     physical interface."
    ::= { acSonetErrCounterEntry 6 }

acSonetErrCounterLineFEBE OBJECT-TYPE
    SYNTAX      Counter64
    MAX-ACCESS  read-only
    STATUS      current
    DESCRIPTION
             "Number of error conditions of type LineFEBE at the 
	     physical interface."
    ::= { acSonetErrCounterEntry 7 }

acSonetErrCounterPathFEBE OBJECT-TYPE
    SYNTAX      Counter64
    MAX-ACCESS  read-only
    STATUS      current
    DESCRIPTION
             "Number of error conditions of type PathFEBE at the 
	     physical interface."
    ::= { acSonetErrCounterEntry 8 }

acSonetErrCounterHEC OBJECT-TYPE
    SYNTAX      Counter64
    MAX-ACCESS  read-only
    STATUS      current
    DESCRIPTION
             "Number of error conditions of type HEC at the 
	     physical interface."
    ::= { acSonetErrCounterEntry 9 }

--
-- acSonetEtsCounter part
--

acSonetEtsCounterNumber OBJECT-TYPE
    SYNTAX      INTEGER
    MAX-ACCESS  read-only
    STATUS      current
    DESCRIPTION
        "The number of physical Sonet interfaces."
    ::= { acSonetEtsCounter 1 }

acSonetEtsCounterTable OBJECT-TYPE
    SYNTAX      SEQUENCE OF AcSonetEtsCounterEntry
    MAX-ACCESS  not-accessible
    STATUS      current
    DESCRIPTION
            "A list of Sonet interface alarm informations. The number
	    of entries is given by the value of acSonetEtsCounterNumber."
    ::= { acSonetEtsCounter 2 }

acSonetEtsCounterEntry OBJECT-TYPE
    SYNTAX      AcSonetEtsCounterEntry
    MAX-ACCESS  not-accessible
    STATUS      current
    DESCRIPTION
            "An entry containing alarm informations applicable
	    to a particular physical Sonet interface."
    INDEX   { acSonetEtsCounterIndex }
    ::= { acSonetEtsCounterTable 1 }

AcSonetEtsCounterEntry ::=
    SEQUENCE {
        acSonetEtsCounterIndex             INTEGER,
	acSonetEtsCounterOOF               Counter64,
	acSonetEtsCounterLOC               Counter64,
	acSonetEtsCounterB1BIP             Counter64,
	acSonetEtsCounterB2BIP             Counter64,
	acSonetEtsCounterB3BIP             Counter64,
	acSonetEtsCounterLineFEBE          Counter64,
	acSonetEtsCounterPathFEBE          Counter64,
	acSonetEtsCounterHEC               Counter64
    }

acSonetEtsCounterIndex OBJECT-TYPE
    SYNTAX      INTEGER
    MAX-ACCESS  read-only
    STATUS      current
    DESCRIPTION
            "A unique value, greater than zero, for each physical
	    interface.  It is recommended that values are assigned
	    contiguously starting from 1.  The value for each interface
            must remain constant at least from one re-initialization of
            the entity's network management system to the next re-
            initialization."
    ::= { acSonetEtsCounterEntry 1 }
    
acSonetEtsCounterOOF OBJECT-TYPE
    SYNTAX      Counter64
    MAX-ACCESS  read-only
    STATUS      current
    DESCRIPTION
             "Number of error conditions of type OOF at the 
	     physical interface."
    ::= { acSonetEtsCounterEntry 2 }

acSonetEtsCounterLOC OBJECT-TYPE
    SYNTAX      Counter64
    MAX-ACCESS  read-only
    STATUS      current
    DESCRIPTION
             "Number of error conditions of type LOC at the 
	     physical interface."
    ::= { acSonetEtsCounterEntry 3 }

acSonetEtsCounterB1BIP OBJECT-TYPE
    SYNTAX      Counter64
    MAX-ACCESS  read-only
    STATUS      current
    DESCRIPTION
             "Number of error conditions of type B1BIP at the 
	     physical interface."
    ::= { acSonetEtsCounterEntry 4 }

acSonetEtsCounterB2BIP OBJECT-TYPE
    SYNTAX      Counter64
    MAX-ACCESS  read-only
    STATUS      current
    DESCRIPTION
             "Number of error conditions of type B2BIP at the 
	     physical interface."
    ::= { acSonetEtsCounterEntry 5 }

acSonetEtsCounterB3BIP      OBJECT-TYPE
    SYNTAX      Counter64
    MAX-ACCESS  read-only
    STATUS      current
    DESCRIPTION
             "Number of error conditions of type B3BIP at the 
	     physical interface."
    ::= { acSonetEtsCounterEntry 6 }

acSonetEtsCounterLineFEBE OBJECT-TYPE
    SYNTAX      Counter64
    MAX-ACCESS  read-only
    STATUS      current
    DESCRIPTION
             "Number of error conditions of type LineFEBE at the 
	     physical interface."
    ::= { acSonetEtsCounterEntry 7 }

acSonetEtsCounterPathFEBE OBJECT-TYPE
    SYNTAX      Counter64
    MAX-ACCESS  read-only
    STATUS      current
    DESCRIPTION
             "Number of error conditions of type PathFEBE at the 
	     physical interface."
    ::= { acSonetEtsCounterEntry 8 }

acSonetEtsCounterHEC OBJECT-TYPE
    SYNTAX      Counter64
    MAX-ACCESS  read-only
    STATUS      current
    DESCRIPTION
             "Number of error conditions of type HEC at the 
	     physical interface."
    ::= { acSonetEtsCounterEntry 9 }

--
-- acE3Status part
--

acE3StatusNumber OBJECT-TYPE
    SYNTAX      INTEGER
    MAX-ACCESS  read-only
    STATUS      current
    DESCRIPTION
        "The number of physical E3 interfaces."
    ::= { acE3Status 1 }

acE3StatusTable OBJECT-TYPE
    SYNTAX      SEQUENCE OF AcE3StatusEntry
    MAX-ACCESS  not-accessible
    STATUS      current
    DESCRIPTION
            "A list of physical E3 interface status
	    informations. The number of entries is given by
	    the value of acE3StatusNumber."
    ::= { acE3Status 2 }

acE3StatusEntry OBJECT-TYPE
    SYNTAX      AcE3StatusEntry
    MAX-ACCESS  not-accessible
    STATUS      current
    DESCRIPTION
            "An entry containing status information 
	    applicable to a particular E3 physical interface."
    INDEX   { acE3StatusIndex }
    ::= { acE3StatusTable 1 }

AcE3StatusEntry ::=
    SEQUENCE {
        acE3StatusIndex         INTEGER,
	acE3StatusState         INTEGER,
	acE3StatusLOS           INTEGER,
	acE3StatusOOF           INTEGER,
	acE3StatusLOC           INTEGER,
	acE3StatusAIS           INTEGER,
	acE3StatusMAFERF        INTEGER,
	acE3StatusCustom        INTEGER,
        acE3StatusDescr         DisplayString
    }

acE3StatusIndex OBJECT-TYPE
    SYNTAX      INTEGER
    MAX-ACCESS  read-only
    STATUS      current
    DESCRIPTION
            "A unique value, greater than zero, for each physical
	    interface.  It is recommended that values are assigned
	    contiguously starting from 1.  The value for each interface
            must remain constant at least from one re-initialization of
            the entity's network management system to the next re-
            initialization."
    ::= { acE3StatusEntry 1 }
    
acE3StatusState OBJECT-TYPE    
    SYNTAX      INTEGER { 
	          up(1),         -- interface running
                  down(2),       -- interface not running
                  failure(3)     -- some error detected
                }
    MAX-ACCESS  read-only
    STATUS      current
    DESCRIPTION
	    "Status of the physical E3 interface."
    ::= { acE3StatusEntry 2 } 
    
acE3StatusLOS OBJECT-TYPE
    SYNTAX      INTEGER {
	          active(1),     -- alarm set
                  inactive(2)    -- alarm not set
                }
    MAX-ACCESS  read-only
    STATUS      current
    DESCRIPTION
             "Alarm condition of type LOS at the 
	     physical E3 interface."
    ::= { acE3StatusEntry 3 }

acE3StatusOOF OBJECT-TYPE
    SYNTAX      INTEGER {
	          active(1),     -- alarm set
                  inactive(2)    -- alarm not set
                }
    MAX-ACCESS  read-only
    STATUS      current
    DESCRIPTION
             "Alarm condition of type OOF at the 
	     physical E3 interface."
    ::= { acE3StatusEntry 4 }

acE3StatusLOC OBJECT-TYPE
    SYNTAX      INTEGER {
	          active(1),     -- alarm set
                  inactive(2)    -- alarm not set
                }
    MAX-ACCESS  read-only
    STATUS      current
    DESCRIPTION
             "Alarm condition of type LOC at the 
	     physical E3 interface."
    ::= { acE3StatusEntry 5 }

acE3StatusAIS OBJECT-TYPE
    SYNTAX      INTEGER {
	          active(1),     -- alarm set
                  inactive(2)    -- alarm not set
                }
    MAX-ACCESS  read-only
    STATUS      current
    DESCRIPTION
             "Alarm condition of type AIS at the 
	     physical E3 interface."
    ::= { acE3StatusEntry 6 }

acE3StatusMAFERF OBJECT-TYPE
    SYNTAX      INTEGER {
	          active(1),     -- alarm set
                  inactive(2)    -- alarm not set
                }
    MAX-ACCESS  read-only
    STATUS      current
    DESCRIPTION
             "Alarm condition of type MAFERF at the 
	     physical E3 interface."
    ::= { acE3StatusEntry 7 }

acE3StatusCustom OBJECT-TYPE
    SYNTAX      INTEGER
    MAX-ACCESS  read-only
    STATUS      current
    DESCRIPTION
              "Numerical status information of the physical 
              E3 interface.  The AcE3StatusCustom is a 
              bit map represented as a sum, therefore,
              it can represent multiple defects simultaneously.

              The various bit positions are:
                0x0001  STATUS_LOS
                0x0004  STATUS_E3_AIS
                0x0020  STATUS_E3_OOF
                0x0040  STATUS_E3_LOF         
                0x0080  STATUS_E3_LOF23
                0x0100  STATUS_LOC
                0x1000  STATUS_MA_FERF"
                
    ::= { acE3StatusEntry 8 }

acE3StatusDescr OBJECT-TYPE    
    SYNTAX      DisplayString
    MAX-ACCESS  read-only
    STATUS      current
    DESCRIPTION
	    "Textual description of the status of the physical 
	    E3 interface."
    ::= { acE3StatusEntry 9 } 


--
-- acE3Alarms part
--

acE3AlarmsNumber OBJECT-TYPE
    SYNTAX      INTEGER
    MAX-ACCESS  read-only
    STATUS      current
    DESCRIPTION
        "The number of physical E3 interfaces."
    ::= { acE3Alarms 1 }

acE3AlarmsTable OBJECT-TYPE
    SYNTAX      SEQUENCE OF AcE3AlarmsEntry
    MAX-ACCESS  not-accessible
    STATUS      current
    DESCRIPTION
            "A list of E3 interface alarm informations. The number
	    of entries is given by the value of acE3AlarmsNumber."
    ::= { acE3Alarms 2 }

acE3AlarmsEntry OBJECT-TYPE
    SYNTAX      AcE3AlarmsEntry
    MAX-ACCESS  not-accessible
    STATUS      current
    DESCRIPTION
            "An entry containing alarm informations applicable
	    to a particular physical E3 interface."
    INDEX   { acE3AlarmsIndex }
    ::= { acE3AlarmsTable 1 }

AcE3AlarmsEntry ::=
    SEQUENCE {
        acE3AlarmsIndex             INTEGER,
	acE3AlarmsLOS               Counter64,
	acE3AlarmsAIS               Counter64,
	acE3AlarmsMAFERF            Counter64
    }

acE3AlarmsIndex OBJECT-TYPE
    SYNTAX      INTEGER
    MAX-ACCESS  read-only
    STATUS      current
    DESCRIPTION
            "A unique value, greater than zero, for each physical
	    interface.  It is recommended that values are assigned
	    contiguously starting from 1.  The value for each interface
            must remain constant at least from one re-initialization of
            the entity's network management system to the next re-
            initialization."
    ::= { acE3AlarmsEntry 1 }
    
acE3AlarmsLOS OBJECT-TYPE
    SYNTAX      Counter64
    MAX-ACCESS  read-only
    STATUS      current
    DESCRIPTION
             "Number of alarm conditions of type LOS at the 
	     physical interface."
    ::= { acE3AlarmsEntry 2 }

acE3AlarmsAIS OBJECT-TYPE
    SYNTAX      Counter64
    MAX-ACCESS  read-only
    STATUS      current
    DESCRIPTION
             "Number of alarm conditions of type AIS at the 
	     physical interface."
    ::= { acE3AlarmsEntry 3 }

acE3AlarmsMAFERF OBJECT-TYPE
    SYNTAX      Counter64
    MAX-ACCESS  read-only
    STATUS      current
    DESCRIPTION
             "Number of alarm conditions of type MAFERF at the 
	     physical interface."
    ::= { acE3AlarmsEntry 4 }

--
-- acE3ErrCounter part
--

acE3ErrCounterNumber OBJECT-TYPE
    SYNTAX      INTEGER
    MAX-ACCESS  read-only
    STATUS      current
    DESCRIPTION
        "The number of physical E3 interfaces."
    ::= { acE3ErrCounter 1 }

acE3ErrCounterTable OBJECT-TYPE
    SYNTAX      SEQUENCE OF AcE3ErrCounterEntry
    MAX-ACCESS  not-accessible
    STATUS      current
    DESCRIPTION
            "A list of E3 interface alarm informations. The number
	    of entries is given by the value of acE3ErrCounterNumber."
    ::= { acE3ErrCounter 2 }

acE3ErrCounterEntry OBJECT-TYPE
    SYNTAX      AcE3ErrCounterEntry
    MAX-ACCESS  not-accessible
    STATUS      current
    DESCRIPTION
            "An entry containing alarm informations applicable
	    to a particular physical E3 interface."
    INDEX   { acE3ErrCounterIndex }
    ::= { acE3ErrCounterTable 1 }

AcE3ErrCounterEntry ::=
    SEQUENCE {
        acE3ErrCounterIndex             INTEGER,
	acE3ErrCounterLCV               Counter64,
	acE3ErrCounterOOF               Counter64,
	acE3ErrCounterLOC               Counter64,
	acE3ErrCounterBIP               Counter64,
	acE3ErrCounterMAFEBE            Counter64,
	acE3ErrCounterHEC               Counter64
    }

acE3ErrCounterIndex OBJECT-TYPE
    SYNTAX      INTEGER
    MAX-ACCESS  read-only
    STATUS      current
    DESCRIPTION
            "A unique value, greater than zero, for each physical
	    interface.  It is recommended that values are assigned
	    contiguously starting from 1.  The value for each interface
            must remain constant at least from one re-initialization of
            the entity's network management system to the next re-
            initialization."
    ::= { acE3ErrCounterEntry 1 }
    
acE3ErrCounterLCV OBJECT-TYPE
    SYNTAX      Counter64
    MAX-ACCESS  read-only
    STATUS      current
    DESCRIPTION
             "Number of error conditions of type LCV at the 
	     physical interface."
    ::= { acE3ErrCounterEntry 2 }

acE3ErrCounterOOF OBJECT-TYPE
    SYNTAX      Counter64
    MAX-ACCESS  read-only
    STATUS      current
    DESCRIPTION
             "Number of error conditions of type OOF at the 
	     physical interface."
    ::= { acE3ErrCounterEntry 3 }

acE3ErrCounterLOC OBJECT-TYPE
    SYNTAX      Counter64
    MAX-ACCESS  read-only
    STATUS      current
    DESCRIPTION
             "Number of error conditions of type LOC at the 
	     physical interface."
    ::= { acE3ErrCounterEntry 4 }

acE3ErrCounterBIP OBJECT-TYPE
    SYNTAX      Counter64
    MAX-ACCESS  read-only
    STATUS      current
    DESCRIPTION
             "Number of error conditions of type B1BIP at the 
	     physical interface."
    ::= { acE3ErrCounterEntry 5 }

acE3ErrCounterMAFEBE OBJECT-TYPE
    SYNTAX      Counter64
    MAX-ACCESS  read-only
    STATUS      current
    DESCRIPTION
             "Number of error conditions of type MAFEBE at the 
	     physical interface."
    ::= { acE3ErrCounterEntry 6 }

acE3ErrCounterHEC OBJECT-TYPE
    SYNTAX      Counter64
    MAX-ACCESS  read-only
    STATUS      current
    DESCRIPTION
             "Number of error conditions of type HEC at the 
	     physical interface."
    ::= { acE3ErrCounterEntry 7 }

--
-- acE3EtsCounter part
--

acE3EtsCounterNumber OBJECT-TYPE
    SYNTAX      INTEGER
    MAX-ACCESS  read-only
    STATUS      current
    DESCRIPTION
        "The number of physical E3 interfaces."
    ::= { acE3EtsCounter 1 }

acE3EtsCounterTable OBJECT-TYPE
    SYNTAX      SEQUENCE OF AcE3EtsCounterEntry
    MAX-ACCESS  not-accessible
    STATUS      current
    DESCRIPTION
            "A list of E3 interface alarm informations. The number
	    of entries is given by the value of acE3EtsCounterNumber."
    ::= { acE3EtsCounter 2 }

acE3EtsCounterEntry OBJECT-TYPE
    SYNTAX      AcE3EtsCounterEntry
    MAX-ACCESS  not-accessible
    STATUS      current
    DESCRIPTION
            "An entry containing alarm informations applicable
	    to a particular physical E3 interface."
    INDEX   { acE3EtsCounterIndex }
    ::= { acE3EtsCounterTable 1 }

AcE3EtsCounterEntry ::=
    SEQUENCE {
        acE3EtsCounterIndex             INTEGER,
	acE3EtsCounterLCV               Counter64,
	acE3EtsCounterOOF               Counter64,
	acE3EtsCounterLOC               Counter64,
	acE3EtsCounterBIP               Counter64,
	acE3EtsCounterMAFEBE            Counter64,
	acE3EtsCounterHEC               Counter64
    }

acE3EtsCounterIndex OBJECT-TYPE
    SYNTAX      INTEGER
    MAX-ACCESS  read-only
    STATUS      current
    DESCRIPTION
            "A unique value, greater than zero, for each physical
	    interface.  It is recommended that values are assigned
	    contiguously starting from 1.  The value for each interface
            must remain constant at least from one re-initialization of
            the entity's network management system to the next re-
            initialization."
    ::= { acE3EtsCounterEntry 1 }
    
acE3EtsCounterLCV OBJECT-TYPE
    SYNTAX      Counter64
    MAX-ACCESS  read-only
    STATUS      current
    DESCRIPTION
             "Number of error conditions of type LCV at the 
	     physical interface."
    ::= { acE3EtsCounterEntry 2 }

acE3EtsCounterOOF OBJECT-TYPE
    SYNTAX      Counter64
    MAX-ACCESS  read-only
    STATUS      current
    DESCRIPTION
             "Number of error conditions of type OOF at the 
	     physical interface."
    ::= { acE3EtsCounterEntry 3 }

acE3EtsCounterLOC OBJECT-TYPE
    SYNTAX      Counter64
    MAX-ACCESS  read-only
    STATUS      current
    DESCRIPTION
             "Number of error conditions of type LOC at the 
	     physical interface."
    ::= { acE3EtsCounterEntry 4 }

acE3EtsCounterBIP OBJECT-TYPE
    SYNTAX      Counter64
    MAX-ACCESS  read-only
    STATUS      current
    DESCRIPTION
             "Number of error conditions of type B1BIP at the 
	     physical interface."
    ::= { acE3EtsCounterEntry 5 }

acE3EtsCounterMAFEBE OBJECT-TYPE
    SYNTAX      Counter64
    MAX-ACCESS  read-only
    STATUS      current
    DESCRIPTION
             "Number of error conditions of type MAFEBE at the 
	     physical interface."
    ::= { acE3EtsCounterEntry 6 }

acE3EtsCounterHEC OBJECT-TYPE
    SYNTAX      Counter64
    MAX-ACCESS  read-only
    STATUS      current
    DESCRIPTION
             "Number of error conditions of type HEC at the 
	     physical interface."
    ::= { acE3EtsCounterEntry 7 }
    
--
-- acGigabitStatus part
--

acGigabitStatusNumber OBJECT-TYPE
    SYNTAX      INTEGER
    MAX-ACCESS  read-only
    STATUS      current
    DESCRIPTION
        "The number of physical Gigabit interfaces."
    ::= { acGigabitStatus 1 }

acGigabitStatusTable OBJECT-TYPE
    SYNTAX      SEQUENCE OF AcGigabitStatusEntry
    MAX-ACCESS  not-accessible
    STATUS      current
    DESCRIPTION
            "A list of physical Gigabit interface status
	    informations. The number of entries is given by
	    the value of acsGigabitStatusNumber."
    ::= { acGigabitStatus 2 }

acGigabitStatusEntry OBJECT-TYPE
    SYNTAX      AcGigabitStatusEntry
    MAX-ACCESS  not-accessible
    STATUS      current
    DESCRIPTION
            "An entry containing status information 
	    applicable to a particular Gigabit physical interface."
    INDEX   { acGigabitStatusIndex }
    ::= { acGigabitStatusTable 1 }
    
    -- TODO

AcGigabitStatusEntry ::=
    SEQUENCE {
        acGigabitStatusIndex         INTEGER,
	acGigabitStatusState         INTEGER,
	acGigabitStatusLOS           INTEGER,
	acGigabitStatusLossofSync    INTEGER,
	acGigabitStatusLinkDown      INTEGER,
	acGigabitStatusCustom        INTEGER,
        acGigabitStatusDescr         DisplayString
    }

acGigabitStatusIndex OBJECT-TYPE
    SYNTAX      INTEGER
    MAX-ACCESS  read-only
    STATUS      current
    DESCRIPTION
            "A unique value, greater than zero, for each physical
	    interface.  It is recommended that values are assigned
	    contiguously starting from 1.  The value for each interface
            must remain constant at least from one re-initialization of
            the entity's network management system to the next re-
            initialization."
    ::= { acGigabitStatusEntry 1 }
    
acGigabitStatusState OBJECT-TYPE    
    SYNTAX      INTEGER { 
	          up(1),         -- interface running
                  down(2),       -- interface not running
                  failure(3)     -- some error detected
                }
    MAX-ACCESS  read-only
    STATUS      current
    DESCRIPTION
	    "Status of the physical Gigabit interface."
    ::= { acGigabitStatusEntry 2 } 
    
acGigabitStatusLOS OBJECT-TYPE
    SYNTAX      INTEGER {
	          active(1),     -- alarm set
                  inactive(2)    -- alarm not set
                }
    MAX-ACCESS  read-only
    STATUS      current
    DESCRIPTION
             "Alarm condition of type LOS at the 
	     physical Gigabit interface."
    ::= { acGigabitStatusEntry 3 }

acGigabitStatusLossofSync OBJECT-TYPE
    SYNTAX      INTEGER {
	          active(1),     -- alarm set
                  inactive(2)    -- alarm not set
                }
    MAX-ACCESS  read-only
    STATUS      current
    DESCRIPTION
             "Alarm condition of type LossofSync at the 
	     physical Gigabit interface."
    ::= { acGigabitStatusEntry 4 }

acGigabitStatusLinkDown OBJECT-TYPE
    SYNTAX      INTEGER {
	          active(1),     -- alarm set
                  inactive(2)    -- alarm not set
                }
    MAX-ACCESS  read-only
    STATUS      current
    DESCRIPTION
             "Alarm condition of type LinkDown at the 
	     physical Gigabit interface."
    ::= { acGigabitStatusEntry 5 }

acGigabitStatusCustom OBJECT-TYPE
    SYNTAX      INTEGER
    MAX-ACCESS  read-only
    STATUS      current
    DESCRIPTION
              "Numerical status information of the physical 
              Gigabit interface.  The AcSonetStatusCustom is a 
              bit map represented as a sum, therefore,
              it can represent multiple defects simultaneously.

              The various bit positions are:
                0x0001  STATUS_LOS
                0x0002  STATUS_LossofSync
                0x0004  STATUS_LinkDown"
    ::= { acGigabitStatusEntry 6 }

acGigabitStatusDescr OBJECT-TYPE    
    SYNTAX      DisplayString
    MAX-ACCESS  read-only
    STATUS      current
    DESCRIPTION
	    "Textual description of the status of the physical 
	    Gigabit interface."
    ::= { acGigabitStatusEntry 7 } 


--
-- acGigabitAlarms part
--

acGigabitAlarmsNumber OBJECT-TYPE
    SYNTAX      INTEGER
    MAX-ACCESS  read-only
    STATUS      current
    DESCRIPTION
        "The number of physical Gigabit interfaces."
    ::= { acGigabitAlarms 1 }

acGigabitAlarmsTable OBJECT-TYPE
    SYNTAX      SEQUENCE OF AcGigabitAlarmsEntry
    MAX-ACCESS  not-accessible
    STATUS      current
    DESCRIPTION
            "A list of Gigabit interface alarm informations. The number
	    of entries is given by the value of acGigabitAlarmsNumber."
    ::= { acGigabitAlarms 2 }

acGigabitAlarmsEntry OBJECT-TYPE
    SYNTAX      AcGigabitAlarmsEntry
    MAX-ACCESS  not-accessible
    STATUS      current
    DESCRIPTION
            "An entry containing alarm informations applicable
	    to a particular physical Gigabit interface."
    INDEX   { acGigabitAlarmsIndex }
    ::= { acGigabitAlarmsTable 1 }

AcGigabitAlarmsEntry ::=
    SEQUENCE {
        acGigabitAlarmsIndex             INTEGER,
	acGigabitAlarmsLOS               Counter64,
	acGigabitAlarmsLinkDown          Counter64
    }

acGigabitAlarmsIndex OBJECT-TYPE
    SYNTAX      INTEGER
    MAX-ACCESS  read-only
    STATUS      current
    DESCRIPTION
            "A unique value, greater than zero, for each physical
	    interface.  It is recommended that values are assigned
	    contiguously starting from 1.  The value for each interface
            must remain constant at least from one re-initialization of
            the entity's network management system to the next re-
            initialization."
    ::= { acGigabitAlarmsEntry 1 }
    
acGigabitAlarmsLOS OBJECT-TYPE
    SYNTAX      Counter64
    MAX-ACCESS  read-only
    STATUS      current
    DESCRIPTION
             "Number of alarm conditions of type LOS at the 
	     physical interface."
    ::= { acGigabitAlarmsEntry 2 }

acGigabitAlarmsLinkDown OBJECT-TYPE
    SYNTAX      Counter64
    MAX-ACCESS  read-only
    STATUS      current
    DESCRIPTION
             "Number of alarm conditions of type LinkDown at the 
	     physical interface."
    ::= { acGigabitAlarmsEntry 3 }

--
-- acGigabitErrCounter part
--

acGigabitErrCounterNumber OBJECT-TYPE
    SYNTAX      INTEGER
    MAX-ACCESS  read-only
    STATUS      current
    DESCRIPTION
        "The number of physical Gigabit interfaces."
    ::= { acGigabitErrCounter 1 }

acGigabitErrCounterTable OBJECT-TYPE
    SYNTAX      SEQUENCE OF AcGigabitErrCounterEntry
    MAX-ACCESS  not-accessible
    STATUS      current
    DESCRIPTION
            "A list of Gigabit interface alarm informations. The number
	    of entries is given by the value of acGigabitErrCounterNumber."
    ::= { acGigabitErrCounter 2 }

acGigabitErrCounterEntry OBJECT-TYPE
    SYNTAX      AcGigabitErrCounterEntry
    MAX-ACCESS  not-accessible
    STATUS      current
    DESCRIPTION
            "An entry containing alarm informations applicable
	    to a particular physical Gigabit interface."
    INDEX   { acGigabitErrCounterIndex }
    ::= { acGigabitErrCounterTable 1 }

AcGigabitErrCounterEntry ::=
    SEQUENCE {
        acGigabitErrCounterIndex             INTEGER,
	acGigabitErrCounterTotalFrame        Counter64,
	acGigabitErrCounterErroredFrame      Counter64,
	acGigabitErrCounterFalseCarrier      Counter64,
	acGigabitErrCounterLossofSync        Counter64, 
	acGigabitErrCounterLineError         Counter64 
    }

acGigabitErrCounterIndex OBJECT-TYPE
    SYNTAX      INTEGER
    MAX-ACCESS  read-only
    STATUS      current
    DESCRIPTION
            "A unique value, greater than zero, for each physical
	    interface.  It is recommended that values are assigned
	    contiguously starting from 1.  The value for each interface
            must remain constant at least from one re-initialization of
            the entity's network management system to the next re-
            initialization."
    ::= { acGigabitErrCounterEntry 1 }
    
acGigabitErrCounterTotalFrame OBJECT-TYPE
    SYNTAX      Counter64
    MAX-ACCESS  read-only
    STATUS      current
    DESCRIPTION
             "Number of total frames at the physical interface."
    ::= { acGigabitErrCounterEntry 2 }

acGigabitErrCounterErroredFrame OBJECT-TYPE
    SYNTAX      Counter64
    MAX-ACCESS  read-only
    STATUS      current
    DESCRIPTION
             "Number of errored frames at the physical interface."
    ::= { acGigabitErrCounterEntry 3 }

acGigabitErrCounterFalseCarrier OBJECT-TYPE
    SYNTAX      Counter64
    MAX-ACCESS  read-only
    STATUS      current
    DESCRIPTION
             "Number of error conditions of type FalseCarrier at the 
	     physical interface."
    ::= { acGigabitErrCounterEntry 4 }

acGigabitErrCounterLossofSync OBJECT-TYPE
    SYNTAX      Counter64
    MAX-ACCESS  read-only
    STATUS      current
    DESCRIPTION
             "Number of error conditions of type LossofSync at the 
	     physical interface."
    ::= { acGigabitErrCounterEntry 5 }

acGigabitErrCounterLineError OBJECT-TYPE
    SYNTAX      Counter64
    MAX-ACCESS  read-only
    STATUS      current
    DESCRIPTION
             "Number of error conditions of type LineError at the 
	     physical interface."
    ::= { acGigabitErrCounterEntry 6 }

--
-- acGigabitEtsCounter part
--

acGigabitEtsCounterNumber OBJECT-TYPE
    SYNTAX      INTEGER
    MAX-ACCESS  read-only
    STATUS      current
    DESCRIPTION
        "The number of physical Gigabit interfaces."
    ::= { acGigabitEtsCounter 1 }

acGigabitEtsCounterTable OBJECT-TYPE
    SYNTAX      SEQUENCE OF AcGigabitEtsCounterEntry
    MAX-ACCESS  not-accessible
    STATUS      current
    DESCRIPTION
            "A list of Gigabit interface alarm informations. The number
	    of entries is given by the value of acGigabitEtsCounterNumber."
    ::= { acGigabitEtsCounter 2 }

acGigabitEtsCounterEntry OBJECT-TYPE
    SYNTAX      AcGigabitEtsCounterEntry
    MAX-ACCESS  not-accessible
    STATUS      current
    DESCRIPTION
            "An entry containing alarm informations applicable
	    to a particular physical Gigabit interface."
    INDEX   { acGigabitEtsCounterIndex }
    ::= { acGigabitEtsCounterTable 1 }

AcGigabitEtsCounterEntry ::=
    SEQUENCE {
        acGigabitEtsCounterIndex             INTEGER,
	acGigabitEtsCounterTotalFrame        Counter64,
	acGigabitEtsCounterErroredFrame      Counter64,
	acGigabitEtsCounterFalseCarrier      Counter64,
	acGigabitEtsCounterLossofSync        Counter64,
	acGigabitEtsCounterLineError         Counter64
    }

acGigabitEtsCounterIndex OBJECT-TYPE
    SYNTAX      INTEGER
    MAX-ACCESS  read-only
    STATUS      current
    DESCRIPTION
            "A unique value, greater than zero, for each physical
	    interface.  It is recommended that values are assigned
	    contiguously starting from 1.  The value for each interface
            must remain constant at least from one re-initialization of
            the entity's network management system to the next re-
            initialization."
    ::= { acGigabitEtsCounterEntry 1 }
    
acGigabitEtsCounterTotalFrame OBJECT-TYPE
    SYNTAX      Counter64
    MAX-ACCESS  read-only
    STATUS      current
    DESCRIPTION
             "not defined."
    ::= { acGigabitEtsCounterEntry 2 }

acGigabitEtsCounterErroredFrame OBJECT-TYPE
    SYNTAX      Counter64
    MAX-ACCESS  read-only
    STATUS      current
    DESCRIPTION
             "Number of errored frames at the physical interface."
    ::= { acGigabitEtsCounterEntry 3 }

acGigabitEtsCounterFalseCarrier OBJECT-TYPE
    SYNTAX      Counter64
    MAX-ACCESS  read-only
    STATUS      current
    DESCRIPTION
             "Number of error conditions of type FalseCarrier at the 
	     physical interface."
    ::= { acGigabitEtsCounterEntry 4 }

acGigabitEtsCounterLossofSync OBJECT-TYPE
    SYNTAX      Counter64
    MAX-ACCESS  read-only
    STATUS      current
    DESCRIPTION
             "Number of error conditions of type LossofSync at the 
	     physical interface."
    ::= { acGigabitEtsCounterEntry 5 }

acGigabitEtsCounterLineError OBJECT-TYPE
    SYNTAX      Counter64
    MAX-ACCESS  read-only
    STATUS      current
    DESCRIPTION
             "Number of error conditions of type LineError at the 
	     physical interface."
    ::= { acGigabitEtsCounterEntry 6 }


--
-- acFibrechannelStatus part
--

acFibrechannelStatusNumber OBJECT-TYPE
    SYNTAX      INTEGER
    MAX-ACCESS  read-only
    STATUS      current
    DESCRIPTION
        "The number of physical Fibrechannel interfaces."
    ::= { acFibrechannelStatus 1 }

acFibrechannelStatusTable OBJECT-TYPE
    SYNTAX      SEQUENCE OF AcFibrechannelStatusEntry
    MAX-ACCESS  not-accessible
    STATUS      current
    DESCRIPTION
            "A list of physical Fibrechannel interface status
	    informations. The number of entries is given by
	    the value of acsFibrechannelStatusNumber."
    ::= { acFibrechannelStatus 2 }

acFibrechannelStatusEntry OBJECT-TYPE
    SYNTAX      AcFibrechannelStatusEntry
    MAX-ACCESS  not-accessible
    STATUS      current
    DESCRIPTION
            "An entry containing status information 
	    applicable to a particular Fibrechannel physical interface."
    INDEX   { acFibrechannelStatusIndex }
    ::= { acFibrechannelStatusTable 1 }
    
    -- TODO

AcFibrechannelStatusEntry ::=
    SEQUENCE {
        acFibrechannelStatusIndex         INTEGER,
	acFibrechannelStatusState         INTEGER,
	acFibrechannelStatusLOS           INTEGER,
	acFibrechannelStatusLossofSync    INTEGER,
	acFibrechannelStatusLinkDown      INTEGER,
	acFibrechannelStatusCustom        INTEGER,
        acFibrechannelStatusDescr         DisplayString
    }

acFibrechannelStatusIndex OBJECT-TYPE
    SYNTAX      INTEGER
    MAX-ACCESS  read-only
    STATUS      current
    DESCRIPTION
            "A unique value, greater than zero, for each physical
	    interface.  It is recommended that values are assigned
	    contiguously starting from 1.  The value for each interface
            must remain constant at least from one re-initialization of
            the entity's network management system to the next re-
            initialization."
    ::= { acFibrechannelStatusEntry 1 }
    
acFibrechannelStatusState OBJECT-TYPE    
    SYNTAX      INTEGER { 
	          up(1),         -- interface running
                  down(2),       -- interface not running
                  failure(3)     -- some error detected
                }
    MAX-ACCESS  read-only
    STATUS      current
    DESCRIPTION
	    "Status of the physical Fibrechannel interface."
    ::= { acFibrechannelStatusEntry 2 } 
    
acFibrechannelStatusLOS OBJECT-TYPE
    SYNTAX      INTEGER {
	          active(1),     -- alarm set
                  inactive(2)    -- alarm not set
                }
    MAX-ACCESS  read-only
    STATUS      current
    DESCRIPTION
             "Alarm condition of type LOS at the 
	     physical Fibrechannel interface."
    ::= { acFibrechannelStatusEntry 3 }

acFibrechannelStatusLossofSync OBJECT-TYPE
    SYNTAX      INTEGER {
	          active(1),     -- alarm set
                  inactive(2)    -- alarm not set
                }
    MAX-ACCESS  read-only
    STATUS      current
    DESCRIPTION
             "Alarm condition of type LossofSync at the 
	     physical Fibrechannel interface."
    ::= { acFibrechannelStatusEntry 4 }

acFibrechannelStatusLinkDown OBJECT-TYPE
    SYNTAX      INTEGER {
	          active(1),     -- alarm set
                  inactive(2)    -- alarm not set
                }
    MAX-ACCESS  read-only
    STATUS      current
    DESCRIPTION
             "Alarm condition of type LinkDown at the 
	     physical Fibrechannel interface."
    ::= { acFibrechannelStatusEntry 5 }

acFibrechannelStatusCustom OBJECT-TYPE
    SYNTAX      INTEGER
    MAX-ACCESS  read-only
    STATUS      current
    DESCRIPTION
              "Numerical status information of the physical 
              Fibrechannel interface.  The AcSonetStatusCustom is a 
              bit map represented as a sum, therefore,
              it can represent multiple defects simultaneously.

              The various bit positions are:
                0x0001  STATUS_LOS
                0x0002  STATUS_LossofSync
                0x0004  STATUS_LinkDown"
    ::= { acFibrechannelStatusEntry 6 }

acFibrechannelStatusDescr OBJECT-TYPE    
    SYNTAX      DisplayString
    MAX-ACCESS  read-only
    STATUS      current
    DESCRIPTION
	    "Textual description of the status of the physical 
	    Fibrechannel interface."
    ::= { acFibrechannelStatusEntry 7 } 


--
-- acFibrechannelAlarms part
--

acFibrechannelAlarmsNumber OBJECT-TYPE
    SYNTAX      INTEGER
    MAX-ACCESS  read-only
    STATUS      current
    DESCRIPTION
        "The number of physical Fibrechannel interfaces."
    ::= { acFibrechannelAlarms 1 }

acFibrechannelAlarmsTable OBJECT-TYPE
    SYNTAX      SEQUENCE OF AcFibrechannelAlarmsEntry
    MAX-ACCESS  not-accessible
    STATUS      current
    DESCRIPTION
            "A list of Fibrechannel interface alarm informations. The number
	    of entries is given by the value of acFibrechannelAlarmsNumber."
    ::= { acFibrechannelAlarms 2 }

acFibrechannelAlarmsEntry OBJECT-TYPE
    SYNTAX      AcFibrechannelAlarmsEntry
    MAX-ACCESS  not-accessible
    STATUS      current
    DESCRIPTION
            "An entry containing alarm informations applicable
	    to a particular physical Fibrechannel interface."
    INDEX   { acFibrechannelAlarmsIndex }
    ::= { acFibrechannelAlarmsTable 1 }

AcFibrechannelAlarmsEntry ::=
    SEQUENCE {
        acFibrechannelAlarmsIndex             INTEGER,
	acFibrechannelAlarmsLOS               Counter64,
	acFibrechannelAlarmsLinkDown          Counter64
    }

acFibrechannelAlarmsIndex OBJECT-TYPE
    SYNTAX      INTEGER
    MAX-ACCESS  read-only
    STATUS      current
    DESCRIPTION
            "A unique value, greater than zero, for each physical
	    interface.  It is recommended that values are assigned
	    contiguously starting from 1.  The value for each interface
            must remain constant at least from one re-initialization of
            the entity's network management system to the next re-
            initialization."
    ::= { acFibrechannelAlarmsEntry 1 }
    
acFibrechannelAlarmsLOS OBJECT-TYPE
    SYNTAX      Counter64
    MAX-ACCESS  read-only
    STATUS      current
    DESCRIPTION
             "Number of alarm conditions of type LOS at the 
	     physical interface."
    ::= { acFibrechannelAlarmsEntry 2 }

acFibrechannelAlarmsLinkDown OBJECT-TYPE
    SYNTAX      Counter64
    MAX-ACCESS  read-only
    STATUS      current
    DESCRIPTION
             "Number of alarm conditions of type LinkDown at the 
	     physical interface."
    ::= { acFibrechannelAlarmsEntry 3 }

--
-- acFibrechannelErrCounter part
--

acFibrechannelErrCounterNumber OBJECT-TYPE
    SYNTAX      INTEGER
    MAX-ACCESS  read-only
    STATUS      current
    DESCRIPTION
        "The number of physical Fibrechannel interfaces."
    ::= { acFibrechannelErrCounter 1 }

acFibrechannelErrCounterTable OBJECT-TYPE
    SYNTAX      SEQUENCE OF AcFibrechannelErrCounterEntry
    MAX-ACCESS  not-accessible
    STATUS      current
    DESCRIPTION
            "A list of Fibrechannel interface alarm informations. The number
	    of entries is given by the value of acFibrechannelErrCounterNumber."
    ::= { acFibrechannelErrCounter 2 }

acFibrechannelErrCounterEntry OBJECT-TYPE
    SYNTAX      AcFibrechannelErrCounterEntry
    MAX-ACCESS  not-accessible
    STATUS      current
    DESCRIPTION
            "An entry containing alarm informations applicable
	    to a particular physical Fibrechannel interface."
    INDEX   { acFibrechannelErrCounterIndex }
    ::= { acFibrechannelErrCounterTable 1 }

AcFibrechannelErrCounterEntry ::=
    SEQUENCE {
      acFibrechannelErrCounterIndex             INTEGER,
	acFibrechannelErrCounterTotalFrame        Counter64,
	acFibrechannelErrCounterErroredFrame      Counter64,
	acFibrechannelErrCounterDiscardFrame      Counter64,
	acFibrechannelErrCounterLossofSync        Counter64, 
	acFibrechannelErrCounterLineError         Counter64,
   acFibrechannelErrCounterFCSError          Counter64,
   acFibrechannelErrCounterCheckError        Counter64
    }

acFibrechannelErrCounterIndex OBJECT-TYPE
    SYNTAX      INTEGER
    MAX-ACCESS  read-only
    STATUS      current
    DESCRIPTION
            "A unique value, greater than zero, for each physical
	    interface.  It is recommended that values are assigned
	    contiguously starting from 1.  The value for each interface
            must remain constant at least from one re-initialization of
            the entity's network management system to the next re-
            initialization."
    ::= { acFibrechannelErrCounterEntry 1 }
    
acFibrechannelErrCounterTotalFrame OBJECT-TYPE
    SYNTAX      Counter64
    MAX-ACCESS  read-only
    STATUS      current
    DESCRIPTION
             "Number of total frames at the physical interface."
    ::= { acFibrechannelErrCounterEntry 2 }

acFibrechannelErrCounterErroredFrame OBJECT-TYPE
    SYNTAX      Counter64
    MAX-ACCESS  read-only
    STATUS      current
    DESCRIPTION
             "Number of errored frames at the physical interface."
    ::= { acFibrechannelErrCounterEntry 3 }

acFibrechannelErrCounterDiscardFrame OBJECT-TYPE
    SYNTAX      Counter64
    MAX-ACCESS  read-only
    STATUS      current
    DESCRIPTION
             "Number of discarded frames at the physical interface."
    ::= { acFibrechannelErrCounterEntry 4 }

acFibrechannelErrCounterLossofSync OBJECT-TYPE
    SYNTAX      Counter64
    MAX-ACCESS  read-only
    STATUS      current
    DESCRIPTION
             "Number of error conditions of type LossofSync at the 
	     physical interface."
    ::= { acFibrechannelErrCounterEntry 5 }

acFibrechannelErrCounterLineError OBJECT-TYPE
    SYNTAX      Counter64
    MAX-ACCESS  read-only
    STATUS      current
    DESCRIPTION
             "Number of error conditions of type LineError at the 
	     physical interface."
    ::= { acFibrechannelErrCounterEntry 6 }

acFibrechannelErrCounterFCSError OBJECT-TYPE
    SYNTAX      Counter64
    MAX-ACCESS  read-only
    STATUS      current
    DESCRIPTION
             "Number of error conditions of type FCSError at the 
	     physical interface."
    ::= { acFibrechannelErrCounterEntry 7 }

acFibrechannelErrCounterCheckError OBJECT-TYPE
    SYNTAX      Counter64
    MAX-ACCESS  read-only
    STATUS      current
    DESCRIPTION
             "Number of error conditions of type CheckError at the 
	     physical interface."
    ::= { acFibrechannelErrCounterEntry 8 }

--
-- acFibrechannelEtsCounter part
--

acFibrechannelEtsCounterNumber OBJECT-TYPE
    SYNTAX      INTEGER
    MAX-ACCESS  read-only
    STATUS      current
    DESCRIPTION
        "The number of physical Fibrechannel interfaces."
    ::= { acFibrechannelEtsCounter 1 }

acFibrechannelEtsCounterTable OBJECT-TYPE
    SYNTAX      SEQUENCE OF AcFibrechannelEtsCounterEntry
    MAX-ACCESS  not-accessible
    STATUS      current
    DESCRIPTION
            "A list of Fibrechannel interface alarm informations. The number
	    of entries is given by the value of acFibrechannelEtsCounterNumber."
    ::= { acFibrechannelEtsCounter 2 }

acFibrechannelEtsCounterEntry OBJECT-TYPE
    SYNTAX      AcFibrechannelEtsCounterEntry
    MAX-ACCESS  not-accessible
    STATUS      current
    DESCRIPTION
            "An entry containing alarm informations applicable
	    to a particular physical Fibrechannel interface."
    INDEX   { acFibrechannelEtsCounterIndex }
    ::= { acFibrechannelEtsCounterTable 1 }

AcFibrechannelEtsCounterEntry ::=
    SEQUENCE {
        acFibrechannelEtsCounterIndex             INTEGER,
	acFibrechannelEtsCounterTotalFrame        Counter64,
	acFibrechannelEtsCounterErroredFrame      Counter64,
	acFibrechannelEtsCounterDiscardFrame      Counter64,
	acFibrechannelEtsCounterLossofSync        Counter64,
	acFibrechannelEtsCounterLineError         Counter64,
	acFibrechannelEtsCounterFCSError          Counter64,
	acFibrechannelEtsCounterCheckError        Counter64
    }

acFibrechannelEtsCounterIndex OBJECT-TYPE
    SYNTAX      INTEGER
    MAX-ACCESS  read-only
    STATUS      current
    DESCRIPTION
            "A unique value, greater than zero, for each physical
	    interface.  It is recommended that values are assigned
	    contiguously starting from 1.  The value for each interface
            must remain constant at least from one re-initialization of
            the entity's network management system to the next re-
            initialization."
    ::= { acFibrechannelEtsCounterEntry 1 }
    
acFibrechannelEtsCounterTotalFrame OBJECT-TYPE
    SYNTAX      Counter64
    MAX-ACCESS  read-only
    STATUS      current
    DESCRIPTION
             "not defined."
    ::= { acFibrechannelEtsCounterEntry 2 }

acFibrechannelEtsCounterErroredFrame OBJECT-TYPE
    SYNTAX      Counter64
    MAX-ACCESS  read-only
    STATUS      current
    DESCRIPTION
             "Number of errored frames at the physical interface."
    ::= { acFibrechannelEtsCounterEntry 3 }

acFibrechannelEtsCounterDiscardFrame OBJECT-TYPE
    SYNTAX      Counter64
    MAX-ACCESS  read-only
    STATUS      current
    DESCRIPTION
             "Number of discarded frames at the physical interface."
    ::= { acFibrechannelEtsCounterEntry 4 }

acFibrechannelEtsCounterLossofSync OBJECT-TYPE
    SYNTAX      Counter64
    MAX-ACCESS  read-only
    STATUS      current
    DESCRIPTION
             "Number of error conditions of type LossofSync at the 
	     physical interface."
    ::= { acFibrechannelEtsCounterEntry 5 }

acFibrechannelEtsCounterLineError OBJECT-TYPE
    SYNTAX      Counter64
    MAX-ACCESS  read-only
    STATUS      current
    DESCRIPTION
             "Number of error conditions of type LineError at the 
	     physical interface."
    ::= { acFibrechannelEtsCounterEntry 6 }

acFibrechannelEtsCounterFCSError OBJECT-TYPE
    SYNTAX      Counter64
    MAX-ACCESS  read-only
    STATUS      current
    DESCRIPTION
             "Number of error conditions of type FCSError at the 
	     physical interface."
    ::= { acFibrechannelEtsCounterEntry 7 }

acFibrechannelEtsCounterCheckError OBJECT-TYPE
    SYNTAX      Counter64
    MAX-ACCESS  read-only
    STATUS      current
    DESCRIPTION
             "Number of error conditions of type CheckError at the 
	     physical interface."
    ::= { acFibrechannelEtsCounterEntry 8 }


END

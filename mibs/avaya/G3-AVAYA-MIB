-- G3-AVAYA-MIB Version 6.3
--
-- Copyright (C) 2006 - 2013 by Avaya Inc. All rights reserved.
--
-- Contact: Avaya Customer Services
--
-- Postal: Avaya, Inc.
--         211 Mt Airy Rd.
--         Basking Ridge, NJ 07920
--         USA
--
-- Tel: +1 908 953 6000
--
-- WWW: http://www.avaya.com
--

G3-AVAYA-MIB DEFINITIONS ::= BEGIN

    IMPORTS
        OBJECT-TYPE, DisplayString
            FROM RFC1213-MIB
        OBJECT-TYPE, NetworkAddress, IpAddress,  Counter, Gauge, TimeTicks
            FROM RFC1155-SMI
        MODULE-IDENTITY, enterprises
            FROM SNMPv2-SMI;

--  The following may be defined elsewhere. If problems occur when trying
--  to load this MIB, some of the lines below may need to be commented
--  out if another MIB has already been loaded that defines these points
--  in the enterprise MIB branch. Furthermore, if an Avaya enterprise
--  specific MIB has already been loaded then the line defining the
--  the Avaya MIB branch may also need to be commented out (possibly
--  along with the lines defining the mibs and products sub-branches
--  underneath avaya).

    avaya           OBJECT IDENTIFIER ::= { enterprises 6889 }
    mibs            OBJECT IDENTIFIER ::= { avaya 2 }
    definity	    OBJECT IDENTIFIER ::= { mibs 8 }
    g3-mib	    OBJECT IDENTIFIER ::= { definity 1 }
    g3proxmib	    OBJECT IDENTIFIER ::= { definity 2 }
    
    products        OBJECT IDENTIFIER ::= { avaya 1 } 
    def-products    OBJECT IDENTIFIER ::= { products 8 }
    g3-products     OBJECT IDENTIFIER ::= { def-products 1 }
    
    -- product identifiers for proxy agent, switches, and boards
    
    definity-proxy          OBJECT IDENTIFIER ::= { g3-products 40 }
    definity-g3             OBJECT IDENTIFIER ::= { g3-products 41 }
    definity-ecs            OBJECT IDENTIFIER ::= { g3-products 42 }
    definity-mcu            OBJECT IDENTIFIER ::= { g3-products 43 }
    val-board               OBJECT IDENTIFIER ::= { g3-products 45 }
    clan-board              OBJECT IDENTIFIER ::= { g3-products 46 }
    definity-one            OBJECT IDENTIFIER ::= { g3-products 47 }
    definity-ip600          OBJECT IDENTIFIER ::= { g3-products 48 }
    avaya-s8700m            OBJECT IDENTIFIER ::= { g3-products 49 }
    avaya-s8300             OBJECT IDENTIFIER ::= { g3-products 50 }
    avaya-s8700i            OBJECT IDENTIFIER ::= { g3-products 51 }
    avaya-s8500             OBJECT IDENTIFIER ::= { g3-products 52 }
    crossfire-board         OBJECT IDENTIFIER ::= { g3-products 53 }
    blade-server            OBJECT IDENTIFIER ::= { g3-products 55 }
    avaya-s8400             OBJECT IDENTIFIER ::= { g3-products 56 }
    cm-on-xen               OBJECT IDENTIFIER ::= { g3-products 57 }
    avaya-aura-cm           OBJECT IDENTIFIER ::= { g3-products 58 }
    avaya-aura-cm-vm        OBJECT IDENTIFIER ::= { g3-products 59 }


    -- object groups for G3 Proxy MIB

    g3client	OBJECT IDENTIFIER ::= { g3proxmib 1 }
    g3agent	OBJECT IDENTIFIER ::= { g3proxmib 2 }
    g3trap	OBJECT IDENTIFIER ::= { g3proxmib 3 }
    g3filter	OBJECT IDENTIFIER ::= { g3proxmib 4 }
    g3maintobj	OBJECT IDENTIFIER ::= { g3proxmib 5 }
    g3category	OBJECT IDENTIFIER ::= { g3proxmib 6 }
    g3platsrc	OBJECT IDENTIFIER ::= { g3proxmib 7 }
    g3platfilt	OBJECT IDENTIFIER ::= { g3proxmib 8 }
    g3rstfilt	OBJECT IDENTIFIER ::= { g3proxmib 9 }


    -- object groups for G3 MIB

    g3connect	OBJECT IDENTIFIER ::= { g3-mib 1 }
    g3vintage	OBJECT IDENTIFIER ::= { g3-mib 2 }
    g3config	OBJECT IDENTIFIER ::= { g3-mib 3 }
    g3alarms	OBJECT IDENTIFIER ::= { g3-mib 4 }
    g3errors	OBJECT IDENTIFIER ::= { g3-mib 5 }
    g3health	OBJECT IDENTIFIER ::= { g3-mib 6 }
    g3cabinet	OBJECT IDENTIFIER ::= { g3-mib 7 }
    g3cabtype	OBJECT IDENTIFIER ::= { g3-mib 8 }
    g3cartype	OBJECT IDENTIFIER ::= { g3-mib 9 }
    g3port	OBJECT IDENTIFIER ::= { g3-mib 10 }
    g3station	OBJECT IDENTIFIER ::= { g3-mib 11 }
    g3statsta	OBJECT IDENTIFIER ::= { g3-mib 12 }
    g3trunkmem	OBJECT IDENTIFIER ::= { g3-mib 13 }
    g3trunksta	OBJECT IDENTIFIER ::= { g3-mib 14 }
    g3datamod	OBJECT IDENTIFIER ::= { g3-mib 15 }
    g3datamsta	OBJECT IDENTIFIER ::= { g3-mib 16 }
    g3timedate	OBJECT IDENTIFIER ::= { g3-mib 18 }
    g3busytrk	OBJECT IDENTIFIER ::= { g3-mib 19 }
    g3busybrd	OBJECT IDENTIFIER ::= { g3-mib 20 }
    g3servalm	OBJECT IDENTIFIER ::= { g3-mib 21 }
    g3msgalm	OBJECT IDENTIFIER ::= { g3-mib 22 }
    g3ipevt	OBJECT IDENTIFIER ::= { g3-mib 23 }
    g3platcmds	OBJECT IDENTIFIER ::= { g3-mib 24 }
    g3version	OBJECT IDENTIFIER ::= { g3-mib 25 }
    g3update	OBJECT IDENTIFIER ::= { g3-mib 26 }
    g3partition	OBJECT IDENTIFIER ::= { g3-mib 27 }
    g3ds1cfg	OBJECT IDENTIFIER ::= { g3-mib 30 }
    g3extdev	OBJECT IDENTIFIER ::= { g3-mib 31 }
    g3trunkgrp	OBJECT IDENTIFIER ::= { g3-mib 32 }
    g3bulletin	OBJECT IDENTIFIER ::= { g3-mib 33 }
    g3ds1	OBJECT IDENTIFIER ::= { g3-mib 34 }
    g3atmpnc	OBJECT IDENTIFIER ::= { g3-mib 35 }
    g3pnchealth	OBJECT IDENTIFIER ::= { g3-mib 36 }
    g3siggroup	OBJECT IDENTIFIER ::= { g3-mib 37 }
    g3restart	OBJECT IDENTIFIER ::= { g3-mib 38 }
    g3fiberlink	OBJECT IDENTIFIER ::= { g3-mib 39 }
    g3routepattern	OBJECT IDENTIFIER ::= { g3-mib 40 }
    g3trunkcfg	OBJECT IDENTIFIER ::= { g3-mib 41 }
    g3stationcfg	OBJECT IDENTIFIER ::= { g3-mib 42 }
    g3atmcfg	OBJECT IDENTIFIER ::= { g3-mib 43 }
    g3aca	OBJECT IDENTIFIER ::= { g3-mib 44 }
    g3atmtrunk	OBJECT IDENTIFIER ::= { g3-mib 45 }
    g3atmportpg1	OBJECT IDENTIFIER ::= { g3-mib 46 }
    g3atmportpg2	OBJECT IDENTIFIER ::= { g3-mib 47 }
    g3atmportpg3	OBJECT IDENTIFIER ::= { g3-mib 48 }
    g3dmodule	OBJECT IDENTIFIER ::= { g3-mib 49 }
    g3occsum	OBJECT IDENTIFIER ::= { g3-mib 50 }
    g3attdgrp	OBJECT IDENTIFIER ::= { g3-mib 51 }
    g3attdpos	OBJECT IDENTIFIER ::= { g3-mib 52 }
    g3trunksum	OBJECT IDENTIFIER ::= { g3-mib 53 }
    g3pktrunksum	OBJECT IDENTIFIER ::= { g3-mib 54 }
    g3trunkwbsum	OBJECT IDENTIFIER ::= { g3-mib 55 }
    g3pktrunkwbsum	OBJECT IDENTIFIER ::= { g3-mib 56 }
    g3pktrunkout	OBJECT IDENTIFIER ::= { g3-mib 57 }
    g3pktrunklight	OBJECT IDENTIFIER ::= { g3-mib 58 }
    g3pnblock	OBJECT IDENTIFIER ::= { g3-mib 59 }
    g3pkpnblock	OBJECT IDENTIFIER ::= { g3-mib 60 }
    g3snblock	OBJECT IDENTIFIER ::= { g3-mib 61 }
    g3pksnblock	OBJECT IDENTIFIER ::= { g3-mib 62 }
    g3hunt	OBJECT IDENTIFIER ::= { g3-mib 63 }
    g3pkhunt	OBJECT IDENTIFIER ::= { g3-mib 64 }
    g3huntlist	OBJECT IDENTIFIER ::= { g3-mib 65 }
    g3tonerec	OBJECT IDENTIFIER ::= { g3-mib 66 }
    g3pktonerec	OBJECT IDENTIFIER ::= { g3-mib 67 }
    g3tonerecsum	OBJECT IDENTIFIER ::= { g3-mib 68 }
    g3pktonerecsum	OBJECT IDENTIFIER ::= { g3-mib 69 }
    g3rpatcfg	OBJECT IDENTIFIER ::= { g3-mib 70 }
    g3rpat	OBJECT IDENTIFIER ::= { g3-mib 71 }
    g3pkrpat	OBJECT IDENTIFIER ::= { g3-mib 72 }
    g3secviolate	OBJECT IDENTIFIER ::= { g3-mib 73 }
    g3cbctrunk	OBJECT IDENTIFIER ::= { g3-mib 74 }
    g3deftime	OBJECT IDENTIFIER ::= { g3-mib 75 }
    g3trunkout	OBJECT IDENTIFIER ::= { g3-mib 76 }
    g3trunklight	OBJECT IDENTIFIER ::= { g3-mib 77 }
    g3loadtotal	OBJECT IDENTIFIER ::= { g3-mib 78 }
    g3loadint	OBJECT IDENTIFIER ::= { g3-mib 79 }
    g3loadinc	OBJECT IDENTIFIER ::= { g3-mib 80 }
    g3loadout	OBJECT IDENTIFIER ::= { g3-mib 81 }
    g3loadtan	OBJECT IDENTIFIER ::= { g3-mib 82 }
    g3pkloadtotal	OBJECT IDENTIFIER ::= { g3-mib 83 }
    g3pkloadint	OBJECT IDENTIFIER ::= { g3-mib 84 }
    g3pkloadinc	OBJECT IDENTIFIER ::= { g3-mib 85 }
    g3pkloadout	OBJECT IDENTIFIER ::= { g3-mib 86 }
    g3pkloadtan	OBJECT IDENTIFIER ::= { g3-mib 87 }
    g3atmlatency	OBJECT IDENTIFIER ::= { g3-mib 88 }
    g3pkatmlatency	OBJECT IDENTIFIER ::= { g3-mib 89 }
    g3ipcodecsum	OBJECT IDENTIFIER ::= { g3-mib 90 }
    g3pkipcodecsum	OBJECT IDENTIFIER ::= { g3-mib 91 }
    g3ipregion	OBJECT IDENTIFIER ::= { g3-mib 92 }
    g3ipdspsum	OBJECT IDENTIFIER ::= { g3-mib 93 }
    g3pkipdspsum	OBJECT IDENTIFIER ::= { g3-mib 94 }
    g3ipsignal	OBJECT IDENTIFIER ::= { g3-mib 95 }
    g3pkipsignal	OBJECT IDENTIFIER ::= { g3-mib 96 }
    g3annall	OBJECT IDENTIFIER ::= { g3-mib 97 }
    g3pkannall	OBJECT IDENTIFIER ::= { g3-mib 98 }
    g3anninteg	OBJECT IDENTIFIER ::= { g3-mib 99 }
    g3pkanninteg	OBJECT IDENTIFIER ::= { g3-mib 100 }
    g3nodename	OBJECT IDENTIFIER ::= { g3-mib 101 }
    g3trkgrpmem	OBJECT IDENTIFIER ::= { g3-mib 102 }
    g3ipinterface	OBJECT IDENTIFIER ::= { g3-mib 103 }
    g3gateway	OBJECT IDENTIFIER ::= { g3-mib 104 }
    g3mediacfg	OBJECT IDENTIFIER ::= { g3-mib 105 }
    g3stamedia	OBJECT IDENTIFIER ::= { g3-mib 106 }
    g3stamgann	OBJECT IDENTIFIER ::= { g3-mib 107 }
    g3ipserver	OBJECT IDENTIFIER ::= { g3-mib 108 }
    g3regipstat	OBJECT IDENTIFIER ::= { g3-mib 109 }
    g3callratedata	OBJECT IDENTIFIER ::= { g3-mib 110 }
    g3callratevoice	OBJECT IDENTIFIER ::= { g3-mib 111 }
    g3callratesrv	OBJECT IDENTIFIER ::= { g3-mib 112 }
    g3callratemedia	OBJECT IDENTIFIER ::= { g3-mib 113 }
    g3callratetotal	OBJECT IDENTIFIER ::= { g3-mib 114 }
    g3clansocsum	OBJECT IDENTIFIER ::= { g3-mib 115 }
    g3pkclansocsum	OBJECT IDENTIFIER ::= { g3-mib 116 }
    g3clanether	OBJECT IDENTIFIER ::= { g3-mib 117 }
    g3clanppp	OBJECT IDENTIFIER ::= { g3-mib 118 }
    g3mmisum	OBJECT IDENTIFIER ::= { g3-mib 119 }
    g3pkmmisum	OBJECT IDENTIFIER ::= { g3-mib 120 }
    g3esmsum	OBJECT IDENTIFIER ::= { g3-mib 121 }
    g3pkesmsum	OBJECT IDENTIFIER ::= { g3-mib 122 }
    g3voicesum	OBJECT IDENTIFIER ::= { g3-mib 123 }
    g3pkvoicesum	OBJECT IDENTIFIER ::= { g3-mib 124 }
    g3ipintlist	OBJECT IDENTIFIER ::= { g3-mib 125 }
    g3stamedlist	OBJECT IDENTIFIER ::= { g3-mib 126 }
    g3lsplist	OBJECT IDENTIFIER ::= { g3-mib 127 }
    g3eventhour	OBJECT IDENTIFIER ::= { g3-mib 128 }
    g3eventday	OBJECT IDENTIFIER ::= { g3-mib 129 }
    g3statregion	OBJECT IDENTIFIER ::= { g3-mib 130 }
    g3ipnetregion	OBJECT IDENTIFIER ::= { g3-mib 131 }
    g3statmedpro	OBJECT IDENTIFIER ::= { g3-mib 132 }
    g3ipunreg	OBJECT IDENTIFIER ::= { g3-mib 133 }
    g3commlink	OBJECT IDENTIFIER ::= { g3-mib 134 }
    g3statlink	OBJECT IDENTIFIER ::= { g3-mib 135 }
    g3covpath	OBJECT IDENTIFIER ::= { g3-mib 136 }
    g3pkcovpath	OBJECT IDENTIFIER ::= { g3-mib 137 }
    g3principal	OBJECT IDENTIFIER ::= { g3-mib 138 }
    g3pkprincipal	OBJECT IDENTIFIER ::= { g3-mib 139 }
    g3esmain	OBJECT IDENTIFIER ::= { g3-mib 140 }
    g3esservers	OBJECT IDENTIFIER ::= { g3-mib 141 }
    g3esparms	OBJECT IDENTIFIER ::= { g3-mib 142 }
    g3mgrecrule	OBJECT IDENTIFIER ::= { g3-mib 143 }
    g3commproc	OBJECT IDENTIFIER ::= { g3-mib 144 }
    g3intvl	OBJECT IDENTIFIER ::= { g3-mib 145 }
    g3jitter	OBJECT IDENTIFIER ::= { g3-mib 146 }
    g3pktloss	OBJECT IDENTIFIER ::= { g3-mib 147 }
    g3rtdelay	OBJECT IDENTIFIER ::= { g3-mib 148 }
    g3esmainsrv	OBJECT IDENTIFIER ::= { g3-mib 149 }
    g3survprocess	OBJECT IDENTIFIER ::= { g3-mib 150 }
    g3nodenameipv4	OBJECT IDENTIFIER ::= { g3-mib 151 }
    g3nodenameipv6	OBJECT IDENTIFIER ::= { g3-mib 152 }
    g3lspall	OBJECT IDENTIFIER ::= { g3-mib 153 }
    g3trunkstaOptions	OBJECT IDENTIFIER ::= { g3-mib 154 }
    g3statstaOptions	OBJECT IDENTIFIER ::= { g3-mib 155 }
    g3busyrls	OBJECT IDENTIFIER ::= { g3-mib 250 }

    -- the connect group

    g3connectState	OBJECT-TYPE
        SYNTAX    INTEGER
		  {
			other(1),	-- none of the following
			off(2),		-- connection is disabled
			down(3),	-- connection is down
			init(4),	-- connection is initializing
			up(5),		-- connection is up
			idle(6)		-- connection is idle
		  }
        ACCESS    read-write
        STATUS    mandatory
        DESCRIPTION
            "The current state of the switch connection; this object
            cat be set to 'off' to disable the connection and can be
            set to 'init' to re-initialize the connection. It can also
	    be set to 'idle', if the g3connectType is 'dynamic', to
	    put turn off the connection until a request is received."
        ::= { g3connect 1 }

    g3connectTimeUp	OBJECT-TYPE
        SYNTAX    INTEGER
        ACCESS    read-only
        STATUS    mandatory
        DESCRIPTION
            "The elapsed time since the connection was established"
        ::= { g3connect 2 }

    g3connectTimeUnused	OBJECT-TYPE
        SYNTAX    INTEGER
        ACCESS    read-only
        STATUS    mandatory
        DESCRIPTION
            "The elapsed time since the connection was last used"
        ::= { g3connect 3 }

    g3connectAttempts	OBJECT-TYPE
        SYNTAX    Counter
        ACCESS    read-only
        STATUS    mandatory
        DESCRIPTION
            "The number of connection attempts"
        ::= { g3connect 4 }

    g3connectSuccess	OBJECT-TYPE
        SYNTAX    Counter
        ACCESS    read-only
        STATUS    mandatory
        DESCRIPTION
            "The number of successful connections"
        ::= { g3connect 5 }

    g3connectRequests	OBJECT-TYPE
        SYNTAX    Counter
        ACCESS    read-only
        STATUS    mandatory
        DESCRIPTION
            "The number of switch data requests"
        ::= { g3connect 6 }

    g3connectResponses	OBJECT-TYPE
        SYNTAX    Counter
        ACCESS    read-only
        STATUS    mandatory
        DESCRIPTION
            "The number of switch data responses"
        ::= { g3connect 7 }

    g3connectErrors	OBJECT-TYPE
        SYNTAX    Counter
        ACCESS    read-only
        STATUS    mandatory
        DESCRIPTION
            "The number of switch connection errors"
        ::= { g3connect 8 }

    g3connectQueued	OBJECT-TYPE
        SYNTAX    INTEGER
        ACCESS    read-only
        STATUS    mandatory
        DESCRIPTION
            "The number switch requests in the input queue"
        ::= { g3connect 9 }

    g3connectDelay	OBJECT-TYPE
        SYNTAX    INTEGER
        ACCESS    read-only
        STATUS    mandatory
        DESCRIPTION
            "The expected delay in retrieving switch data"
        ::= { g3connect 10 }
        
    g3connectAlarmForward	OBJECT-TYPE
        SYNTAX    INTEGER
		  {
			other(1),    -- none of the following
			ok(2),	     -- all alarms have been forwarded
			failed(3)    -- alarm forwarding failure has occured 
                  }
        ACCESS    read-write
        STATUS    mandatory
        DESCRIPTION
            "This object serves as a flag to indicate if a failure has 
            occured in forwarding alarms received from the switch on to
            another destination." 
        ::= { g3connect 11 }

    g3connectTimeReset OBJECT-TYPE
        SYNTAX    INTEGER
        ACCESS    read-write
        STATUS    mandatory
        DESCRIPTION
            "The elapsed time since the connection counters were last reset.
	    Setting this object to zero will reset the counters."
        ::= { g3connect 12 }

    g3connectType	OBJECT-TYPE
        SYNTAX    INTEGER
		  {
			static(1),	-- connection type is static
			dynamic(2)	-- connection type is dynamic
		  }
        ACCESS    read-only
        STATUS    mandatory
        DESCRIPTION
            "The type of the switch connection; it is either 'static'
	    which will stay up continuously or 'dynamic' which will be
	    dropped after the connection is idle for a period of time."
        ::= { g3connect 13 }

    g3connectTimeout	OBJECT-TYPE
        SYNTAX    INTEGER
        ACCESS    read-only
        STATUS    mandatory
        DESCRIPTION
            "The number of idle minutes a 'dynamic' connection will stay
	    connected before being dropped. For a 'static' connection
	    this field is not applicable an contains a value of zero"
        ::= { g3connect 14 }

    -- the g3vintage group

    g3vintageTage	OBJECT-TYPE
        SYNTAX    INTEGER
        ACCESS    read-only
        STATUS    mandatory
        DESCRIPTION
            "The number of timeticks since the vintage data was last
            extracted from the switch by the G3 Proxy Agent. This object
            along with the g3vintageTintvl object allows the Network Manager
            to determine the validity of the vintage data in the
            cache and to control when the proxy agent extracts the
            vintage data from the switch."
        ::= { g3vintage 1 }

    g3vintageTintvl	OBJECT-TYPE
        SYNTAX    INTEGER
        ACCESS    read-write
        STATUS    mandatory
        DESCRIPTION
            "An object containing the interval for which the vintage data
            extracted from the switch is considered valid by the proxy agent.
            When a GET or GET-NEXT request for vintage objects is received
            by the agent it uses the g3vintageTage and g3vintageTintvl objects
            to determine whether it should refresh the cached vintage data.
            If g3vintageTstmp + g3vintageTintvl is less than the current value
            of the sysUpTime object then the agent refreshes the vintage data
            cache.  In either case it responds to the requests it receives
            with the data it currently has in the cache."
        ::= { g3vintage 2 }

    g3vintageTdelay	OBJECT-TYPE
        SYNTAX    INTEGER
        ACCESS    read-only
        STATUS    mandatory
        DESCRIPTION
            "An object containing the delay encountered in updating
            the cached data"
        ::= { g3vintage 3 }

    g3vintageTretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3vintage 4 }

    g3vintageSpeArelease	OBJECT-TYPE
        SYNTAX    DisplayString (SIZE (0..18))
        ACCESS    read-only
        STATUS    mandatory
        DESCRIPTION
            "A DisplayString Object that contains the release number for
            SPE A."
        ::= { g3vintage 5 }

    g3vintageSpeBrelease	OBJECT-TYPE
        SYNTAX    DisplayString (SIZE (0..18))
        ACCESS    read-only
        STATUS    mandatory
        DESCRIPTION
            "A DisplayString Object that contains the release number for
            SPE B."
        ::= { g3vintage 6 }

    g3vintageCurMemory	OBJECT-TYPE
        SYNTAX    DisplayString (SIZE (0..12))
        ACCESS    read-only
        STATUS    mandatory
        DESCRIPTION
            "A DisplayString Object that contains the current memory
            configuration."
        ::= { g3vintage 7 }

    g3vintageSpeAupID	OBJECT-TYPE
        SYNTAX    DisplayString (SIZE (0..10))
        ACCESS    read-only
        STATUS    mandatory
        DESCRIPTION
            "A DisplayString Object that contains the update identifier for SPE A."
        ::= { g3vintage 8 }

    g3vintageSpeBupID	OBJECT-TYPE
        SYNTAX    DisplayString (SIZE (0..10))
        ACCESS    read-only
        STATUS    mandatory
        DESCRIPTION
            "A DisplayString Object that contains the update identifier for SPE B."
        ::= { g3vintage 9 }

    g3vintageSpeAupState1	OBJECT-TYPE
        SYNTAX    DisplayString (SIZE (0..26))
        ACCESS    read-only
        STATUS    mandatory
        DESCRIPTION
            "A DisplayString Object that contains the first part of the update
            state for SPE A."
        ::= { g3vintage 10 }

    g3vintageSpeBupState1	OBJECT-TYPE
        SYNTAX    DisplayString (SIZE (0..26))
        ACCESS    read-only
        STATUS    mandatory
        DESCRIPTION
            "A DisplayString Object that contains the first part of the update
            state for SPE B."
        ::= { g3vintage 11 }

    g3vintageSpeAupState2	OBJECT-TYPE
        SYNTAX    DisplayString (SIZE (0..18))
        ACCESS    read-only
        STATUS    mandatory
        DESCRIPTION
            "A DisplayString Object that contains the second part of the update
            state for SPE A."
        ::= { g3vintage 12 }

    g3vintageSpeBupState2	OBJECT-TYPE
        SYNTAX    DisplayString (SIZE (0..18))
        ACCESS    read-only
        STATUS    mandatory
        DESCRIPTION
            "A DisplayString Object that contains the second part of the update
            state for SPE B."
        ::= { g3vintage 13 }

    g3vintageVSPacketBus	OBJECT-TYPE
        SYNTAX    DisplayString (SIZE (0..1))
        ACCESS    read-only
        STATUS    mandatory
        DESCRIPTION
            "A DisplayString Object that contains the a flag indicating whether
            packet bus is available on a G3vs system."
        ::= { g3vintage 14 }

    g3vintageOfferCategory	OBJECT-TYPE
        SYNTAX    DisplayString (SIZE (0..12))
        ACCESS    read-only
        STATUS    mandatory
        DESCRIPTION
            "A DisplayString Object that contains the current Offer Category
            ('A', 'B', or '?')."
        ::= { g3vintage 15 }

    g3vintageATMPnc	OBJECT-TYPE
        SYNTAX    DisplayString (SIZE (0..1))
        ACCESS    read-only
        STATUS    mandatory
        DESCRIPTION
            "A DisplayString Object that contains the current ATM PNC Customer
            Option ('y', or 'n')."
        ::= { g3vintage 16 }

    g3vintageProductID	OBJECT-TYPE
        SYNTAX    DisplayString (SIZE (0..10))
        ACCESS    read-only
        STATUS    mandatory
        DESCRIPTION
            "A DisplayString Object that contains the Product Identification
            number for the Definity switch."
        ::= { g3vintage 17 }

    g3vintageOSSNumber1	OBJECT-TYPE
        SYNTAX    DisplayString (SIZE (0..16))
        ACCESS    read-only
        STATUS    mandatory
        DESCRIPTION
            "A DisplayString Object that contains the first OSS telephone
            number."
        ::= { g3vintage 18 }

    g3vintageAbbAlmRep1	OBJECT-TYPE
        SYNTAX    DisplayString (SIZE (0..1))
        ACCESS    read-only
        STATUS    mandatory
        DESCRIPTION
            "A DisplayString Object that contains the Abbreviated Alarm Report
            for the first OSS Number ('y' or 'n')."
        ::= { g3vintage 19 }

    g3vintageOSSNumber2	OBJECT-TYPE
        SYNTAX    DisplayString (SIZE (0..16))
        ACCESS    read-only
        STATUS    mandatory
        DESCRIPTION
            "A DisplayString Object that contains the second OSS telephone
            number."
        ::= { g3vintage 20 }

    g3vintageAbbAlmRep2	OBJECT-TYPE
        SYNTAX    DisplayString (SIZE (0..1))
        ACCESS    read-only
        STATUS    mandatory
        DESCRIPTION
            "A DisplayString Object that contains the Abbreviated Alarm Report
            for the second OSS Number ('y' or 'n')."
        ::= { g3vintage 21 }

    g3vintageAOActivate	OBJECT-TYPE
        SYNTAX    DisplayString (SIZE (0..1))
        ACCESS    read-only
        STATUS    mandatory
        DESCRIPTION
            "A DisplayString Object that contains Alarm Origination
            Activation status ('y' or 'n')."
        ::= { g3vintage 22 }

    g3vintageCANotify	OBJECT-TYPE
        SYNTAX    DisplayString (SIZE (0..1))
        ACCESS    read-only
        STATUS    mandatory
        DESCRIPTION
            "A DisplayString Object that contains Cleared Alarm Notification
            status ('y' or 'n')."
        ::= { g3vintage 23 }

    g3vintageResNotify	OBJECT-TYPE
        SYNTAX    DisplayString (SIZE (0..1))
        ACCESS    read-only
        STATUS    mandatory
        DESCRIPTION
            "A DisplayString Object that contains Restart Notification
            status ('y' or 'n')."
        ::= { g3vintage 24 }

    g3vintagePbxID	OBJECT-TYPE
        SYNTAX    INTEGER
        ACCESS    read-only
        STATUS    mandatory
        DESCRIPTION
            "An INTEGER Object containing the Local Node Number for pre R11"
        ::= { g3vintage 25 }

    g3vintageACAFlag	OBJECT-TYPE
        SYNTAX    DisplayString (SIZE (0..1))
        ACCESS    read-only
        STATUS    mandatory
        DESCRIPTION
            "A DisplayString Object that contains the current ACA Enabled
            Option ('y', or 'n')."
        ::= { g3vintage 26 }

    g3vintageIPAddress1	OBJECT-TYPE
        SYNTAX    DisplayString (SIZE (0..3))
        ACCESS    read-only
        STATUS    mandatory
        DESCRIPTION
            "An object that contains the first octet of IP address"
        ::= { g3vintage 27 }

    g3vintageIPAddress2	OBJECT-TYPE
        SYNTAX    DisplayString (SIZE (0..3))
        ACCESS    read-only
        STATUS    mandatory
        DESCRIPTION
            "An object that contains the second octet of IP address"
        ::= { g3vintage 28 }

    g3vintageIPAddress3	OBJECT-TYPE
        SYNTAX    DisplayString (SIZE (0..3))
        ACCESS    read-only
        STATUS    mandatory
        DESCRIPTION
            "An object that contains the third octet of IP address"
        ::= { g3vintage 29 }

    g3vintageIPAddress4	OBJECT-TYPE
        SYNTAX    DisplayString (SIZE (0..3))
        ACCESS    read-only
        STATUS    mandatory
        DESCRIPTION
            "An object that contains the fourth octet of IP address"
        ::= { g3vintage 30 }

    g3vintagePortNetSupport	OBJECT-TYPE
        SYNTAX    DisplayString (SIZE (0..1))
        ACCESS    read-only
        STATUS    mandatory
        DESCRIPTION
            "An object that contains"
        ::= { g3vintage 31 }

    g3vintageLocalSpareProc	OBJECT-TYPE
        SYNTAX    DisplayString (SIZE (0..1))
        ACCESS    read-only
        STATUS    mandatory
        DESCRIPTION
            "An object that contains"
        ::= { g3vintage 32 }

    g3vintagePlatform	OBJECT-TYPE
        SYNTAX    DisplayString (SIZE (0..5))
        ACCESS    read-only
        STATUS    mandatory
        DESCRIPTION
            "An object that contains"
        ::= { g3vintage 33 }

    g3vintageLocalNodeNbr	OBJECT-TYPE
        SYNTAX    INTEGER
        ACCESS    read-only
        STATUS    mandatory
        DESCRIPTION
            "An INTEGER Object containing the Local Node Number on R11 and beyond"
        ::= { g3vintage 34 }

    g3vintageIPStaReg	OBJECT-TYPE
        SYNTAX    INTEGER
        ACCESS    read-only
        STATUS    mandatory
        DESCRIPTION
            "An object that contains the number of current registered IP stations
            on the media server."
        ::= { g3vintage 35 }

    g3vintageIPStaAvail	OBJECT-TYPE
        SYNTAX    INTEGER
        ACCESS    read-only
        STATUS    mandatory
        DESCRIPTION
            "An object that contains the number of concurrent IP stations still
            available on the media server."
        ::= { g3vintage 36 }

    g3vintageIPStaLimit	OBJECT-TYPE
        SYNTAX    INTEGER
        ACCESS    read-only
        STATUS    mandatory
        DESCRIPTION
            "An object that contains the total system limit of concurrent IP
            stations on the media server."
        ::= { g3vintage 37 }

    g3vintageIPAttdReg	OBJECT-TYPE
        SYNTAX    INTEGER
        ACCESS    read-only
        STATUS    mandatory
        DESCRIPTION
            "An object that contains the number of current registered IP
            attendant consoles on the media server."
        ::= { g3vintage 38 }

    g3vintageIPAttdAvail	OBJECT-TYPE
        SYNTAX    INTEGER
        ACCESS    read-only
        STATUS    mandatory
        DESCRIPTION
            "An object that contains the number of concurrent IP attendant
            consoles still available on the media server."
        ::= { g3vintage 39 }

    g3vintageIPAttdLimit	OBJECT-TYPE
        SYNTAX    INTEGER
        ACCESS    read-only
        STATUS    mandatory
        DESCRIPTION
            "An object that contains the total system limit of concurrent IP
            attendant consoles on the media server."
        ::= { g3vintage 40 }

    g3vintageRemoteOffReg	OBJECT-TYPE
        SYNTAX    INTEGER
        ACCESS    read-only
        STATUS    mandatory
        DESCRIPTION
            "An object that contains the number of current registered remote
            office stations on the media server."
        ::= { g3vintage 41 }

    g3vintageRemoteOffAvail	OBJECT-TYPE
        SYNTAX    INTEGER
        ACCESS    read-only
        STATUS    mandatory
        DESCRIPTION
            "An object that contains the number of concurrent remote office
            stations still available on the media server."
        ::= { g3vintage 42 }

    g3vintageRemoteOffLimit	OBJECT-TYPE
        SYNTAX    INTEGER
        ACCESS    read-only
        STATUS    mandatory
        DESCRIPTION
            "An object that contains the total system limit of concurrent remote
            office stations on the media server."
        ::= { g3vintage 43 }


    -- the g3config group

    g3configTage	OBJECT-TYPE
        SYNTAX    INTEGER
        ACCESS    read-only
        STATUS    mandatory
        DESCRIPTION
            "The number of timeticks since the configuration data was last
            extracted from the switch by the G3 Proxy Agent. This object
            along with the g3configTintvl object allows the Network Manager
            to determine the validity of the configuration data in the
            cache and to control when the proxy agent extracts the
            configuration data from the switch."
        ::= { g3config 1 }

    g3configTintvl	OBJECT-TYPE
        SYNTAX    INTEGER
        ACCESS    read-write
        STATUS    mandatory
        DESCRIPTION
            "An object containing the interval for which the configuration data
            extracted from the switch is considered valid by the proxy agent.
            When a GET or GET-NEXT request for configuration objects is
            received by the agent it uses the g3configTage and g3configTintvl
            objects to determine whether it should refresh the cached
            configTable.  If g3configTstmp + g3configTintvl is less than the
            current value of the sysUpTime object then the agent refreshes
            the configTable cache.  In either case it responds to the requests
            it receives with the data it currently has in the cache."
        ::= { g3config 2 }

    g3configTdelay	OBJECT-TYPE
        SYNTAX    INTEGER
        ACCESS    read-only
        STATUS    mandatory
        DESCRIPTION
            "An object containing the delay encountered in updating
            the cached data"
        ::= { g3config 3 }

    g3configTretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3config 4 }

    g3configTcount	OBJECT-TYPE
        SYNTAX    Gauge
        ACCESS    read-only
        STATUS    mandatory
        DESCRIPTION
            "A Gauge object containing the number of data records in the
            cache."
        ::= { g3config 5 }

    g3configTable	OBJECT-TYPE
        SYNTAX    SEQUENCE OF G3configEntry
        ACCESS    not-accessible
        STATUS    mandatory
        DESCRIPTION
            "A list of g3config entries."
        ::= { g3config 6 }

    g3configEntry	OBJECT-TYPE
        SYNTAX    G3configEntry
        ACCESS    not-accessible
        STATUS    mandatory
        DESCRIPTION
            "A g3config entry containing objects of the
            g3config information sent by the switch."
        INDEX    { g3configBoardNum, g3configIndex }
        ::= { g3configTable 1 }

    G3configEntry ::= SEQUENCE {
        g3configBoardNum
            DisplayString,
        g3configIndex
            INTEGER,
        g3configBoardType
            DisplayString,
        g3configCode
            DisplayString,
        g3configSuffix
            DisplayString,
        g3configVintage
            DisplayString,
        g3configPort1
            DisplayString,
        g3configPort2
            DisplayString,
        g3configPort3
            DisplayString,
        g3configPort4
            DisplayString,
        g3configPort5
            DisplayString,
        g3configPort6
            DisplayString,
        g3configPort7
            DisplayString,
        g3configPort8
            DisplayString,
        g3configPort9
            DisplayString,
        g3configPort10
            DisplayString,
        g3configPort11
            DisplayString,
        g3configPort12
            DisplayString,
        g3configPort13
            DisplayString,
        g3configPort14
            DisplayString,
        g3configPort15
            DisplayString,
        g3configPort16
            DisplayString,
        g3configPort17
            DisplayString,
        g3configPort18
            DisplayString,
        g3configPort19
            DisplayString,
        g3configPort20
            DisplayString,
        g3configPort21
            DisplayString,
        g3configPort22
            DisplayString,
        g3configPort23
            DisplayString,
        g3configPort24
            DisplayString,
        g3configPort25
            DisplayString,
        g3configPort26
            DisplayString,
        g3configPort27
            DisplayString,
        g3configPort28
            DisplayString,
        g3configPort29
            DisplayString,
        g3configPort30
            DisplayString,
        g3configPort31
            DisplayString,
        g3configPort32
            DisplayString
        }

    g3configBoardNum	OBJECT-TYPE
        SYNTAX    DisplayString (SIZE (0..5))
        ACCESS    read-only
        STATUS    mandatory
        DESCRIPTION
            "A DisplayString Object that uniquely identifies a board based on
            its location in the system. The syntax for the Board Number is as
            follows: cabinet(01-44):carrier(A-E):slot(01-20)."
        ::= { g3configEntry 1 }

    g3configIndex	OBJECT-TYPE
        SYNTAX    INTEGER
        ACCESS    read-only
        STATUS    mandatory
        DESCRIPTION
            "An INTEGER object containing an index numbering the config entry
            for the board specified in BoardNum. This object along with
            BoardNum will serve as the instance identifier for boardEntry."
        ::= { g3configEntry 2 }

    g3configBoardType	OBJECT-TYPE
        SYNTAX    DisplayString (SIZE (0..19))
        ACCESS    read-only
        STATUS    mandatory
        DESCRIPTION
            "A DisplayString Object that contains a text description of the
            type of board."
        ::= { g3configEntry 3 }

    g3configCode	OBJECT-TYPE
        SYNTAX    DisplayString (SIZE (0..8))
        ACCESS    read-only
        STATUS    mandatory
        DESCRIPTION
            "A DisplayString Object that contains the code that defines the
            type of board."
        ::= { g3configEntry 4 }

    g3configSuffix	OBJECT-TYPE
        SYNTAX    DisplayString (SIZE (0..2))
        ACCESS    read-only
        STATUS    mandatory
        DESCRIPTION
            "A DisplayString Object that contains the suffix to the code
            (object configCode) that defines the type of board."
        ::= { g3configEntry 5 }

    g3configVintage	OBJECT-TYPE
        SYNTAX    DisplayString (SIZE (0..10))
        ACCESS    read-only
        STATUS    mandatory
        DESCRIPTION
            "An DisplayString Object that contains the vintage of the board."
        ::= { g3configEntry 6 }

    g3configPort1	OBJECT-TYPE
        SYNTAX    DisplayString (SIZE (0..3))
        ACCESS    read-only
        STATUS    mandatory
        DESCRIPTION
            "A DisplayString Object that specifies the assignment of the
            port. A string representing an integer identical to the port
            number indicates that the port is assigned. The string (u)
            indicates that the port is unassigned. The string (t) indicates
            that the port is assigned via the TTI feature. A null string
            indicates that the port does not exist on that board."
        ::= { g3configEntry 7 }

    g3configPort2	OBJECT-TYPE
        SYNTAX    DisplayString (SIZE (0..3))
        ACCESS    read-only
        STATUS    mandatory
        DESCRIPTION
            "See DESCRIPTION of configPort1."
        ::= { g3configEntry 8 }

    g3configPort3	OBJECT-TYPE
        SYNTAX    DisplayString (SIZE (0..3))
        ACCESS    read-only
        STATUS    mandatory
        DESCRIPTION
            "See DESCRIPTION of configPort1."
        ::= { g3configEntry 9 }

    g3configPort4	OBJECT-TYPE
        SYNTAX    DisplayString (SIZE (0..3))
        ACCESS    read-only
        STATUS    mandatory
        DESCRIPTION
            "See DESCRIPTION of configPort1."
        ::= { g3configEntry 10 }

    g3configPort5	OBJECT-TYPE
        SYNTAX    DisplayString (SIZE (0..3))
        ACCESS    read-only
        STATUS    mandatory
        DESCRIPTION
            "See DESCRIPTION of configPort1."
        ::= { g3configEntry 11 }

    g3configPort6	OBJECT-TYPE
        SYNTAX    DisplayString (SIZE (0..3))
        ACCESS    read-only
        STATUS    mandatory
        DESCRIPTION
            "See DESCRIPTION of configPort1."
        ::= { g3configEntry 12 }

    g3configPort7	OBJECT-TYPE
        SYNTAX    DisplayString (SIZE (0..3))
        ACCESS    read-only
        STATUS    mandatory
        DESCRIPTION
            "See DESCRIPTION of configPort1."
        ::= { g3configEntry 13 }

    g3configPort8	OBJECT-TYPE
        SYNTAX    DisplayString (SIZE (0..3))
        ACCESS    read-only
        STATUS    mandatory
        DESCRIPTION
            "See DESCRIPTION of configPort1."
        ::= { g3configEntry 14 }

    g3configPort9	OBJECT-TYPE
        SYNTAX    DisplayString (SIZE (0..3))
        ACCESS    read-only
        STATUS    mandatory
        DESCRIPTION
            "See DESCRIPTION of configPort1."
        ::= { g3configEntry 15 }

    g3configPort10	OBJECT-TYPE
        SYNTAX    DisplayString (SIZE (0..3))
        ACCESS    read-only
        STATUS    mandatory
        DESCRIPTION
            "See DESCRIPTION of configPort1."
        ::= { g3configEntry 16 }

    g3configPort11	OBJECT-TYPE
        SYNTAX    DisplayString (SIZE (0..3))
        ACCESS    read-only
        STATUS    mandatory
        DESCRIPTION
            "See DESCRIPTION of configPort1."
        ::= { g3configEntry 17 }

    g3configPort12	OBJECT-TYPE
        SYNTAX    DisplayString (SIZE (0..3))
        ACCESS    read-only
        STATUS    mandatory
        DESCRIPTION
            "See DESCRIPTION of configPort1."
        ::= { g3configEntry 18 }

    g3configPort13	OBJECT-TYPE
        SYNTAX    DisplayString (SIZE (0..3))
        ACCESS    read-only
        STATUS    mandatory
        DESCRIPTION
            "See DESCRIPTION of configPort1."
        ::= { g3configEntry 19 }

    g3configPort14	OBJECT-TYPE
        SYNTAX    DisplayString (SIZE (0..3))
        ACCESS    read-only
        STATUS    mandatory
        DESCRIPTION
            "See DESCRIPTION of configPort1."
        ::= { g3configEntry 20 }

    g3configPort15	OBJECT-TYPE
        SYNTAX    DisplayString (SIZE (0..3))
        ACCESS    read-only
        STATUS    mandatory
        DESCRIPTION
            "See DESCRIPTION of configPort1."
        ::= { g3configEntry 21 }

    g3configPort16	OBJECT-TYPE
        SYNTAX    DisplayString (SIZE (0..3))
        ACCESS    read-only
        STATUS    mandatory
        DESCRIPTION
            "See DESCRIPTION of configPort1."
        ::= { g3configEntry 22 }

    g3configPort17	OBJECT-TYPE
        SYNTAX    DisplayString (SIZE (0..3))
        ACCESS    read-only
        STATUS    mandatory
        DESCRIPTION
            "See DESCRIPTION of configPort1."
        ::= { g3configEntry 23 }

    g3configPort18	OBJECT-TYPE
        SYNTAX    DisplayString (SIZE (0..3))
        ACCESS    read-only
        STATUS    mandatory
        DESCRIPTION
            "See DESCRIPTION of configPort1."
        ::= { g3configEntry 24 }

    g3configPort19	OBJECT-TYPE
        SYNTAX    DisplayString (SIZE (0..3))
        ACCESS    read-only
        STATUS    mandatory
        DESCRIPTION
            "See DESCRIPTION of configPort1."
        ::= { g3configEntry 25 }

    g3configPort20	OBJECT-TYPE
        SYNTAX    DisplayString (SIZE (0..3))
        ACCESS    read-only
        STATUS    mandatory
        DESCRIPTION
            "See DESCRIPTION of configPort1."
        ::= { g3configEntry 26 }

    g3configPort21	OBJECT-TYPE
        SYNTAX    DisplayString (SIZE (0..3))
        ACCESS    read-only
        STATUS    mandatory
        DESCRIPTION
            "See DESCRIPTION of configPort1."
        ::= { g3configEntry 27 }

    g3configPort22	OBJECT-TYPE
        SYNTAX    DisplayString (SIZE (0..3))
        ACCESS    read-only
        STATUS    mandatory
        DESCRIPTION
            "See DESCRIPTION of configPort1."
        ::= { g3configEntry 28 }

    g3configPort23	OBJECT-TYPE
        SYNTAX    DisplayString (SIZE (0..3))
        ACCESS    read-only
        STATUS    mandatory
        DESCRIPTION
            "See DESCRIPTION of configPort1."
        ::= { g3configEntry 29 }

    g3configPort24	OBJECT-TYPE
        SYNTAX    DisplayString (SIZE (0..3))
        ACCESS    read-only
        STATUS    mandatory
        DESCRIPTION
            "See DESCRIPTION of configPort1."
        ::= { g3configEntry 30 }

    g3configPort25	OBJECT-TYPE
        SYNTAX    DisplayString (SIZE (0..3))
        ACCESS    read-only
        STATUS    mandatory
        DESCRIPTION
            "See DESCRIPTION of configPort1."
        ::= { g3configEntry 31 }

    g3configPort26	OBJECT-TYPE
        SYNTAX    DisplayString (SIZE (0..3))
        ACCESS    read-only
        STATUS    mandatory
        DESCRIPTION
            "See DESCRIPTION of configPort1."
        ::= { g3configEntry 32 }

    g3configPort27	OBJECT-TYPE
        SYNTAX    DisplayString (SIZE (0..3))
        ACCESS    read-only
        STATUS    mandatory
        DESCRIPTION
            "See DESCRIPTION of configPort1."
        ::= { g3configEntry 33 }

    g3configPort28	OBJECT-TYPE
        SYNTAX    DisplayString (SIZE (0..3))
        ACCESS    read-only
        STATUS    mandatory
        DESCRIPTION
            "See DESCRIPTION of configPort1."
        ::= { g3configEntry 34 }

    g3configPort29	OBJECT-TYPE
        SYNTAX    DisplayString (SIZE (0..3))
        ACCESS    read-only
        STATUS    mandatory
        DESCRIPTION
            "See DESCRIPTION of configPort1."
        ::= { g3configEntry 35 }

    g3configPort30	OBJECT-TYPE
        SYNTAX    DisplayString (SIZE (0..3))
        ACCESS    read-only
        STATUS    mandatory
        DESCRIPTION
            "See DESCRIPTION of configPort1."
        ::= { g3configEntry 36 }

    g3configPort31	OBJECT-TYPE
        SYNTAX    DisplayString (SIZE (0..3))
        ACCESS    read-only
        STATUS    mandatory
        DESCRIPTION
            "See DESCRIPTION of configPort1."
        ::= { g3configEntry 37 }

    g3configPort32	OBJECT-TYPE
        SYNTAX    DisplayString (SIZE (0..3))
        ACCESS    read-only
        STATUS    mandatory
        DESCRIPTION
            "See DESCRIPTION of configPort1."
        ::= { g3configEntry 38 }


    -- the g3alarms group

    g3alarmsTage	OBJECT-TYPE
        SYNTAX    INTEGER
        ACCESS    read-only
        STATUS    mandatory
        DESCRIPTION
            "The number of timeticks since the alarm data was last
            extracted from the switch by the G3 Proxy Agent. This object
            along with the g3alarmsTintvl object allows the Network Manager
            to determine the validity of the alarm data in the
            cache and to control when the proxy agent extracts the
            alarm data from the switch."
        ::= { g3alarms 1 }

    g3alarmsTintvl	OBJECT-TYPE
        SYNTAX    INTEGER
        ACCESS    read-write
        STATUS    mandatory
        DESCRIPTION
            "An object containing the interval for which the alarm data
            extracted from the switch is considered valid by the proxy agent.
            When a GET or GET-NEXT request for alarm objects is received by
            the agent it uses the g3alarmsTage and g3alarmsTintvl objects
            to determine whether it should refresh the cached alarmsTable.
            If g3alarmsTstmp + g3alarmsTintvl is less than the current value
            of the sysUpTime object then the agent refreshes the alarmsTable
            cache.  In either case it responds to the requests it receives
            with the data it currently has in the cache."
        ::= { g3alarms 2 }

    g3alarmsTdelay	OBJECT-TYPE
        SYNTAX    INTEGER
        ACCESS    read-only
        STATUS    mandatory
        DESCRIPTION
            "An object containing the delay encountered in updating
            the cached data"
        ::= { g3alarms 3 }

    g3alarmsTretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3alarms 4 }

    g3alarmsTcount	OBJECT-TYPE
        SYNTAX    Gauge
        ACCESS    read-only
        STATUS    mandatory
        DESCRIPTION
            "A Gauge object containing the number of data records in the
            cache."
        ::= { g3alarms 5 }

    g3alarmsTable	OBJECT-TYPE
        SYNTAX    SEQUENCE OF G3alarmsEntry
        ACCESS    not-accessible
        STATUS    mandatory
        DESCRIPTION
            "A list of g3alarms entries."
        ::= { g3alarms 6 }

    g3alarmsEntry	OBJECT-TYPE
        SYNTAX    G3alarmsEntry
        ACCESS    not-accessible
        STATUS    mandatory
        DESCRIPTION
            "A g3alarms entry containing objects of the
            g3alarms information sent by the switch."
        INDEX    { g3alarmsPort, g3alarmsIndex }
        ::= { g3alarmsTable 1 }

    G3alarmsEntry ::= SEQUENCE {
        g3alarmsPort
            DisplayString,
        g3alarmsIndex
            INTEGER,
        g3alarmsMaintName
            DisplayString,
        g3alarmsOnBrd
            DisplayString,
        g3alarmsAltName
            DisplayString,
        g3alarmsAlarmType
            DisplayString,
        g3alarmsSvcState
            DisplayString,
        g3alarmsAck
            DisplayString,
        g3alarmsMonthAlrmd
            DisplayString,
        g3alarmsDayAlrmd
            DisplayString,
        g3alarmsHourAlrmd
            DisplayString,
        g3alarmsMinAlrmd
            DisplayString,
        g3alarmsMonthRslvd
            DisplayString,
        g3alarmsDayRslvd
            DisplayString,
        g3alarmsHourRslvd
            DisplayString,
        g3alarmsMinRslvd
            DisplayString,
        g3alarmsAlarmNumber
            DisplayString,
        g3alarmsProductID
            DisplayString,
        g3alarmsAck2
            DisplayString,
        g3alarmsSrcIPAddr
            DisplayString,
        g3alarmsSrcMACAddr
            DisplayString,
        g3alarmsDestIPAddr
            DisplayString,
        g3alarmsDestPort
            DisplayString,
        g3alarmsProtocol
            DisplayString,
        g3alarmsCount
            DisplayString,
        g3alarmsIPAddress
            DisplayString,
        g3alarmsCategory
            DisplayString,
        g3alarmsErrorCodes
            DisplayString,
        g3alarmsViolationType
            DisplayString,
        g3alarmsCode
            DisplayString,
        g3alarmsData
            DisplayString,
        g3alarmsICMPType
            DisplayString,
        g3alarmsEventID
            DisplayString,
        g3alarmsStatus
            DisplayString
        }

    g3alarmsPort	OBJECT-TYPE
        SYNTAX    DisplayString (SIZE (0..1024))
        ACCESS    read-only
        STATUS    mandatory
        DESCRIPTION
            "A DisplayString Object that uniquely identifies a port based on
            its location in the system. The syntax for the Port number is as
            follows: cabinet(01-44):carrier(A-E):slot(01-20):port(01-32).
            This object along with alIndex will serve as the instance
            identifier for alarmsEntry."
        ::= { g3alarmsEntry 1 }

    g3alarmsIndex	OBJECT-TYPE
        SYNTAX    INTEGER
        ACCESS    read-only
        STATUS    mandatory
        DESCRIPTION
            "An INTEGER object containing an index numbering the alarm entry
            for the port specified in alarmsPort. This object along with
            alarmsPort will serve as the instance identifier for alarmsEntry."
        ::= { g3alarmsEntry 2 }

    g3alarmsMaintName	OBJECT-TYPE
        SYNTAX    DisplayString (SIZE (0..8))
        ACCESS    read-only
        STATUS    mandatory
        DESCRIPTION
            "A DisplayString Object containing the Maintenance Object Name."
        ::= { g3alarmsEntry 3 }

    g3alarmsOnBrd	OBJECT-TYPE
        SYNTAX    DisplayString (SIZE (0..1))
        ACCESS    read-only
        STATUS    mandatory
        DESCRIPTION
            "A DisplayString Object specifying whether or not the alarm
            indicates an on board fault."
        ::= { g3alarmsEntry 4 }

    g3alarmsAltName	OBJECT-TYPE
        SYNTAX    DisplayString (SIZE (0..7))
        ACCESS    read-only
        STATUS    mandatory
        DESCRIPTION
            "A DisplayString Object containing the alternate name of the
            alarmed object. Alternate names can consist of extension numbers,
            trunk group numbers or other identifying data."
        ::= { g3alarmsEntry 5 }

    g3alarmsAlarmType	OBJECT-TYPE
        SYNTAX    DisplayString (SIZE (0..7))
        ACCESS    read-only
        STATUS    mandatory
        DESCRIPTION
            "A DisplayString Object specifying the alarm type (or severity)."
        ::= { g3alarmsEntry 6 }

    g3alarmsSvcState	OBJECT-TYPE
        SYNTAX    DisplayString (SIZE (0..3))
        ACCESS    read-only
        STATUS    mandatory
        DESCRIPTION
            "A DisplayString Object specifying the service state of the
            alarmed object. Service States can be IN or OUT {any others?}."
        ::= { g3alarmsEntry 7 }

    g3alarmsAck	OBJECT-TYPE
        SYNTAX    DisplayString (SIZE (0..1))
        ACCESS    read-only
        STATUS    mandatory
        DESCRIPTION
            "A DisplayString Object indicating whether or not the alarm has
            been acknowledged by the alarm receiver."
        ::= { g3alarmsEntry 8 }

    g3alarmsMonthAlrmd	OBJECT-TYPE
        SYNTAX    DisplayString (SIZE (0..2))
        ACCESS    read-only
        STATUS    mandatory
        DESCRIPTION
            "A DisplayString Object containing the month the alarm was
            created."
        ::= { g3alarmsEntry 9 }

    g3alarmsDayAlrmd	OBJECT-TYPE
        SYNTAX    DisplayString (SIZE (0..2))
        ACCESS    read-only
        STATUS    mandatory
        DESCRIPTION
            "A DisplayString Object containing the day the alarm was created."
        ::= { g3alarmsEntry 10 }

    g3alarmsHourAlrmd	OBJECT-TYPE
        SYNTAX    DisplayString (SIZE (0..2))
        ACCESS    read-only
        STATUS    mandatory
        DESCRIPTION
            "A DisplayString Object containing the hour the alarm was created."
        ::= { g3alarmsEntry 11 }

    g3alarmsMinAlrmd	OBJECT-TYPE
        SYNTAX    DisplayString (SIZE (0..2))
        ACCESS    read-only
        STATUS    mandatory
        DESCRIPTION
            "A DisplayString Object containing the minute the alarm was
            created."
        ::= { g3alarmsEntry 12 }

    g3alarmsMonthRslvd	OBJECT-TYPE
        SYNTAX    DisplayString (SIZE (0..2))
        ACCESS    read-only
        STATUS    mandatory
        DESCRIPTION
            "A DisplayString Object containing the month the alarm was
            resolved.  This object will always contain the value (00) because
            this table only contains open alarms.  This object is included
            in the table for future enhancements and for completeness."
        ::= { g3alarmsEntry 13 }

    g3alarmsDayRslvd	OBJECT-TYPE
        SYNTAX    DisplayString (SIZE (0..2))
        ACCESS    read-only
        STATUS    mandatory
        DESCRIPTION
            "A DisplayString Object containing the day the alarm was resolved.
            This object will always contain the value (00) because this table
            only contains open alarms.  This object is included in the table
            for future enhancements and for completeness."
        ::= { g3alarmsEntry 14 }

    g3alarmsHourRslvd	OBJECT-TYPE
        SYNTAX    DisplayString (SIZE (0..2))
        ACCESS    read-only
        STATUS    mandatory
        DESCRIPTION
            "A DisplayString Object containing the hour the alarm was resolved.
            This object will always contain the value (00) because this table
            only contains open alarms.  This object is included in the table
            for future enhancements and for completeness."
        ::= { g3alarmsEntry 15 }

    g3alarmsMinRslvd	OBJECT-TYPE
        SYNTAX    DisplayString (SIZE (0..2))
        ACCESS    read-only
        STATUS    mandatory
        DESCRIPTION
            "A DisplayString Object containing the minute the alarm was
            resolved.  This object will always contain the value (00) because
            this table only contains open alarms.  This object is included
            in the table for future enhancements and for completeness."
        ::= { g3alarmsEntry 16 }

    g3alarmsAlarmNumber	OBJECT-TYPE
        SYNTAX    DisplayString (SIZE (0..50))
        ACCESS    read-only
        STATUS    mandatory
        DESCRIPTION
            "A DisplayString Object containing the Alarm Number of the alarm.
            This is just a place holder for a field populated in alarm traps.
            Nothing is populated in this field. For traps supported by this 
            MIB, it is populated with a unique alarm identifier of the form 
            FPA:<filter number>:<month alarmed><day alarmed><hour alarmed>:
            <minute alarmed><second alarmed>:<month resolved><day resolved> 
            <hour resolved><minute resolved><second resolved>:
            <alternate name field>:<new/modified flag>. The filter number
            field either contains the alarm filter number associated with
            the trap being generated or '00000' if a filter number is not
            applicable. The time resolved fields are populated with '0000000000', 
            if the alarm has not been resolved. For some alarms the alternate 
            name may not contain any information. The new/mod flag either 
            contains an 'N' for a new alarm or a 'M' for a modified alarm. 
            The above field format only applies to CM 3.1 and greater releases."
        ::= { g3alarmsEntry 17 }

    g3alarmsProductID	OBJECT-TYPE
        SYNTAX    DisplayString (SIZE (0..20))
        ACCESS    read-only
        STATUS    mandatory
        DESCRIPTION
            "A DisplayString Object containing the Product ID of the alarm.
            This is just a place holder for a field populated in alarm traps.
            Nothing is populated in this field."
        ::= { g3alarmsEntry 18 }

    g3alarmsAck2	OBJECT-TYPE
        SYNTAX    DisplayString (SIZE (0..1))
        ACCESS    read-only
        STATUS    mandatory
        DESCRIPTION
            "Another DisplayString Object indicating whether or not the alarm has
            been acknowledged."
        ::= { g3alarmsEntry 19 }

    g3alarmsSrcIPAddr	OBJECT-TYPE
        SYNTAX    DisplayString (SIZE (0..50))
        ACCESS    read-only
        STATUS    mandatory
        DESCRIPTION
            "A DisplayString Object containing the IP address that is the source
            of a security attack. This is just a place holder for a field 
            populated in alarm traps. Nothing is populated in this field."
        ::= { g3alarmsEntry 20 }

    g3alarmsSrcMACAddr	OBJECT-TYPE
        SYNTAX    DisplayString (SIZE (0..50))
        ACCESS    read-only
        STATUS    mandatory
        DESCRIPTION
            "A DisplayString Object containing the IP address that is the MAC
            address that is the source of a security attack. This is just a 
            place holder for a field populated in alarm traps. Nothing is 
            populated in this field."
        ::= { g3alarmsEntry 21 }

    g3alarmsDestIPAddr	OBJECT-TYPE
        SYNTAX    DisplayString (SIZE (0..50))
        ACCESS    read-only
        STATUS    mandatory
        DESCRIPTION
            "A DisplayString Object containing the IP address that is the
            destination of a security attack. This is just a place holder for 
            a field populated in alarm traps. Nothing is populated in this field."
        ::= { g3alarmsEntry 22 }

    g3alarmsDestPort	OBJECT-TYPE
        SYNTAX    DisplayString (SIZE (0..50))
        ACCESS    read-only
        STATUS    mandatory
        DESCRIPTION
            "A DisplayString Object containing the IP port that is the
            destination of a security attack. This is just a place holder for 
            a field populated in alarm traps. Nothing is populated in this field."
        ::= { g3alarmsEntry 23 }

    g3alarmsProtocol	OBJECT-TYPE
        SYNTAX    DisplayString (SIZE (0..50))
        ACCESS    read-only
        STATUS    mandatory
        DESCRIPTION
            "A DisplayString Object containing the protocol that a security
            attack is utilizing. This is just a place holder for a field 
            populated in alarm traps. Nothing is populated in this field."
        ::= { g3alarmsEntry 24 }

    g3alarmsCount	OBJECT-TYPE
        SYNTAX    DisplayString (SIZE (0..50))
        ACCESS    read-only
        STATUS    mandatory
        DESCRIPTION
            "A DisplayString Object containing the number of occurrences at the
            time that a trap was sent during a security attack. This is just a 
            place holder for a field populated in alarm traps. Nothing is 
            populated in this field."
        ::= { g3alarmsEntry 25 }

    g3alarmsIPAddress	OBJECT-TYPE
        SYNTAX    DisplayString (SIZE (0..40))
        ACCESS    read-only
        STATUS    mandatory
        DESCRIPTION
            "A DisplayString Object containing the IP address of the server.
            This is just a place holder for a field populated in alarm traps. 
            Nothing is populated in this field."
        ::= { g3alarmsEntry 26 }

    g3alarmsCategory	OBJECT-TYPE
        SYNTAX    DisplayString (SIZE (0..25))
        ACCESS    read-only
        STATUS    mandatory
        DESCRIPTION
            "A DisplayString Object containing the the alarm category that
            the alarm belongs to. This is just a place holder for a field 
            populated in alarm traps. Nothing is populated in this field."
        ::= { g3alarmsEntry 27 }

    g3alarmsErrorCodes	OBJECT-TYPE
        SYNTAX    DisplayString (SIZE (0..100))
        ACCESS    read-only
        STATUS    mandatory
        DESCRIPTION
            "A DisplayString Object containing a list of up to 16 error codes
            that could have caused the alarm. Not all of the error codes may
            be the actually cause. This is just a place holder for a field 
            populated in alarm traps. Nothing is populated in this field."
        ::= { g3alarmsEntry 28 }

    g3alarmsViolationType	OBJECT-TYPE
        SYNTAX    DisplayString (SIZE (0..50))
        ACCESS    read-only
        STATUS    mandatory
        DESCRIPTION
            "A DisplayString Object containing the violation type associated with
            a security attack. This is just a place holder for a field populated 
            in alarm traps. Nothing is populated in this field."
        ::= { g3alarmsEntry 29 }

    g3alarmsCode	OBJECT-TYPE
        SYNTAX    DisplayString (SIZE (0..50))
        ACCESS    read-only
        STATUS    mandatory
        DESCRIPTION
            "A DisplayString Object containing the code associated with
            a security attack. This is just a place holder for a field populated 
            in alarm traps. Nothing is populated in this field."
        ::= { g3alarmsEntry 30 }

    g3alarmsData	OBJECT-TYPE
        SYNTAX    DisplayString (SIZE (0..50))
        ACCESS    read-only
        STATUS    mandatory
        DESCRIPTION
            "A DisplayString Object containing the data field associated with
            a security attack. This is just a place holder for a field populated 
            in alarm traps. Nothing is populated in this field."
        ::= { g3alarmsEntry 31 }

    g3alarmsICMPType	OBJECT-TYPE
        SYNTAX    DisplayString (SIZE (0..50))
        ACCESS    read-only
        STATUS    mandatory
        DESCRIPTION
            "A DisplayString Object containing the ICMP type associated with
            a security attack. This is just a place holder for a field populated 
            in alarm traps. Nothing is populated in this field."
        ::= { g3alarmsEntry 32 }

    g3alarmsEventID	OBJECT-TYPE
        SYNTAX    DisplayString (SIZE (0..50))
        ACCESS    read-only
        STATUS    mandatory
        DESCRIPTION
            "A DisplayString Object containing the event ID associated with
            a security attack. This is just a place holder for a field populated 
            in alarm traps. Nothing is populated in this field."
        ::= { g3alarmsEntry 33 }

    g3alarmsStatus	OBJECT-TYPE
        SYNTAX    DisplayString (SIZE (0..50))
        ACCESS    read-only
        STATUS    mandatory
        DESCRIPTION
            "A DisplayString Object containing the status associated with
            a security attack. This is just a place holder for a field populated 
            in alarm traps. Nothing is populated in this field."
        ::= { g3alarmsEntry 34 }


    -- the g3errors group

    g3errorsTage	OBJECT-TYPE
        SYNTAX    INTEGER
        ACCESS    read-only
        STATUS    mandatory
        DESCRIPTION
            "The number of timeticks since the error log was last
            extracted from the switch by the G3 Proxy Agent. This object
            along with the g3errorsTintvl object allows the Network Manager
            to determine the validity of the error log in the
            cache and to control when the proxy agent extracts the
            error log data from the switch."
        ::= { g3errors 1 }

    g3errorsTintvl	OBJECT-TYPE
        SYNTAX    INTEGER
        ACCESS    read-write
        STATUS    mandatory
        DESCRIPTION
            "An object containing the interval for which the error data
            extracted from the switch is considered valid by the proxy agent.
            When a GET or GET-NEXT request for error objects is received by
            the agent it uses the g3errorsTage and g3errorsTintvl objects
            to determine whether it should refresh the cached errorsTable.
            If g3errorsTstmp + g3errorsTintvl is less than the current value
            of the sysUpTime object then the agent refreshes the errorsTable
            cache.  In either case it responds to the requests it receives
            with the data it currently has in the cache."
        ::= { g3errors 2 }

    g3errorsTdelay	OBJECT-TYPE
        SYNTAX    INTEGER
        ACCESS    read-only
        STATUS    mandatory
        DESCRIPTION
            "An object containing the delay encountered in updating
            the cached data"
        ::= { g3errors 3 }

    g3errorsTretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3errors 4 }

    g3errorsTcount	OBJECT-TYPE
        SYNTAX    Gauge
        ACCESS    read-only
        STATUS    mandatory
        DESCRIPTION
            "A Gauge object containing the number of data records in the
            cache."
        ::= { g3errors 5 }

    g3errorsTable	OBJECT-TYPE
        SYNTAX    SEQUENCE OF G3errorsEntry
        ACCESS    not-accessible
        STATUS    mandatory
        DESCRIPTION
            "A list of g3errors entries."
        ::= { g3errors 6 }

    g3errorsEntry	OBJECT-TYPE
        SYNTAX    G3errorsEntry
        ACCESS    not-accessible
        STATUS    mandatory
        DESCRIPTION
            "A g3errors entry containing objects of the
            g3errors information sent by the switch."
        INDEX    { g3errorsPort, g3errorsIndex }
        ::= { g3errorsTable 1 }

    G3errorsEntry ::= SEQUENCE {
        g3errorsPort
            DisplayString,
        g3errorsIndex
            INTEGER,
        g3errorsMaintName
            DisplayString,
        g3errorsAltName
            DisplayString,
        g3errorsErrType
            DisplayString,
        g3errorsAuxData
            DisplayString,
        g3errorsMonthFirst
            DisplayString,
        g3errorsDayFirst
            DisplayString,
        g3errorsHourFirst
            DisplayString,
        g3errorsMinFirst
            DisplayString,
        g3errorsMonthLast
            DisplayString,
        g3errorsDayLast
            DisplayString,
        g3errorsHourLast
            DisplayString,
        g3errorsMinLast
            DisplayString,
        g3errorsErrCnt
            DisplayString,
        g3errorsErrRt
            DisplayString,
        g3errorsRtperHr
            DisplayString,
        g3errorsAlSt
            DisplayString,
        g3errorsAck
            DisplayString
        }

    g3errorsPort	OBJECT-TYPE
        SYNTAX    DisplayString (SIZE (0..9))
        ACCESS    read-only
        STATUS    mandatory
        DESCRIPTION
            "A DisplayString Object that uniquely identifies a port based on
            its location in the system. The syntax for the Port Location is as
            follows: cabinet(01-44):carrier(A-E):slot(01-20):port(01-32).
            This object along with errorsIndex will serve as the instance
            identifier for errorsEntry."
        ::= { g3errorsEntry 1 }

    g3errorsIndex	OBJECT-TYPE
        SYNTAX    INTEGER
        ACCESS    read-only
        STATUS    mandatory
        DESCRIPTION
            "An INTEGER object containing an index numbering the error entry
            for the port specified in errorsPort. This object along with
            errorsPort will serve as the instance identifier for errorsEntry."
        ::= { g3errorsEntry 2 }

    g3errorsMaintName	OBJECT-TYPE
        SYNTAX    DisplayString (SIZE (0..8))
        ACCESS    read-only
        STATUS    mandatory
        DESCRIPTION
            "A DisplayString Object containing the Maintenance Object Name."
        ::= { g3errorsEntry 3 }

    g3errorsAltName	OBJECT-TYPE
        SYNTAX    DisplayString (SIZE (0..7))
        ACCESS    read-only
        STATUS    mandatory
        DESCRIPTION
            "A DisplayString Object containing the alternate name of the
            errored object. Alternate names can consist of extension numbers,
            trunk group numbers or other identifying data."
        ::= { g3errorsEntry 4 }

    g3errorsErrType	OBJECT-TYPE
        SYNTAX    DisplayString (SIZE (0..5))
        ACCESS    read-only
        STATUS    mandatory
        DESCRIPTION
            "A DisplayString Object containing a specific error type numeric
            code used to determine the type of error."
        ::= { g3errorsEntry 5 }

    g3errorsAuxData	OBJECT-TYPE
        SYNTAX    DisplayString (SIZE (0..5))
        ACCESS    read-only
        STATUS    mandatory
        DESCRIPTION
            "A DisplayString Object containing an auxiliary numeric code used
            with the errType to troubleshoot the problem."
        ::= { g3errorsEntry 6 }

    g3errorsMonthFirst	OBJECT-TYPE
        SYNTAX    DisplayString (SIZE (0..2))
        ACCESS    read-only
        STATUS    mandatory
        DESCRIPTION
            "A DisplayString Object containing the month that the error
            first occurred."
        ::= { g3errorsEntry 7 }

    g3errorsDayFirst	OBJECT-TYPE
        SYNTAX    DisplayString (SIZE (0..2))
        ACCESS    read-only
        STATUS    mandatory
        DESCRIPTION
            "A DisplayString Object containing the day that the error
            first occurred."
        ::= { g3errorsEntry 8 }

    g3errorsHourFirst	OBJECT-TYPE
        SYNTAX    DisplayString (SIZE (0..2))
        ACCESS    read-only
        STATUS    mandatory
        DESCRIPTION
            "A DisplayString Object containing the hour that the error
            first occurred."
        ::= { g3errorsEntry 9 }

    g3errorsMinFirst	OBJECT-TYPE
        SYNTAX    DisplayString (SIZE (0..2))
        ACCESS    read-only
        STATUS    mandatory
        DESCRIPTION
            "A DisplayString Object containing the minute that the error
            first occurred."
        ::= { g3errorsEntry 10 }

    g3errorsMonthLast	OBJECT-TYPE
        SYNTAX    DisplayString (SIZE (0..2))
        ACCESS    read-only
        STATUS    mandatory
        DESCRIPTION
            "A DisplayString Object containing the month that the error
            last occurred."
        ::= { g3errorsEntry 11 }

    g3errorsDayLast	OBJECT-TYPE
        SYNTAX    DisplayString (SIZE (0..2))
        ACCESS    read-only
        STATUS    mandatory
        DESCRIPTION
            "A DisplayString Object containing the day that the error
            last occurred."
        ::= { g3errorsEntry 12 }

    g3errorsHourLast	OBJECT-TYPE
        SYNTAX    DisplayString (SIZE (0..2))
        ACCESS    read-only
        STATUS    mandatory
        DESCRIPTION
            "A DisplayString Object containing the hour that the error
            last occurred."
        ::= { g3errorsEntry 13 }

    g3errorsMinLast	OBJECT-TYPE
        SYNTAX    DisplayString (SIZE (0..2))
        ACCESS    read-only
        STATUS    mandatory
        DESCRIPTION
            "A DisplayString Object containing the minute that the error
            last occurred."
        ::= { g3errorsEntry 14 }

    g3errorsErrCnt	OBJECT-TYPE
        SYNTAX    DisplayString (SIZE (0..3))
        ACCESS    read-only
        STATUS    mandatory
        DESCRIPTION
            "A DisplayString Object containing a numeric count of the
            occurrences of the error."
        ::= { g3errorsEntry 15 }

    g3errorsErrRt	OBJECT-TYPE
        SYNTAX    DisplayString (SIZE (0..3))
        ACCESS    read-only
        STATUS    mandatory
        DESCRIPTION
            "A DisplayString Object containing the error rate
            occurrences of the error."
        ::= { g3errorsEntry 16 }

    g3errorsRtperHr	OBJECT-TYPE
        SYNTAX    DisplayString (SIZE (0..3))
        ACCESS    read-only
        STATUS    mandatory
        DESCRIPTION
            "A DisplayString Object containing the error rate per hour."
        ::= { g3errorsEntry 17 }

    g3errorsAlSt	OBJECT-TYPE
        SYNTAX    DisplayString (SIZE (0..1))
        ACCESS    read-only
        STATUS    mandatory
        DESCRIPTION
            "A DisplayString Object containing the alarm state of the error."
        ::= { g3errorsEntry 18 }

    g3errorsAck	OBJECT-TYPE
        SYNTAX    DisplayString (SIZE (0..1))
        ACCESS    read-only
        STATUS    mandatory
        DESCRIPTION
            "A DisplayString Object indicating whether or not the alarm has
            been acknowledged by the alarm receiver."
        ::= { g3errorsEntry 19 }


    -- the g3health group

    g3healthTage	OBJECT-TYPE
        SYNTAX    INTEGER
        ACCESS    read-only
        STATUS    mandatory
        DESCRIPTION
            "The number of timeticks since the health data was last
            extracted from the switch by the G3 Proxy Agent. This object
            along with the g3healthTintvl object allows the Network Manager
            to determine the validity of the health data in the
            cache and to control when the proxy agent extracts the
            health data from the switch."
        ::= { g3health 1 }

    g3healthTintvl	OBJECT-TYPE
        SYNTAX    INTEGER
        ACCESS    read-write
        STATUS    mandatory
        DESCRIPTION
            "An object containing the interval for which the health data
            extracted from the switch is considered valid by the proxy agent.
            When a GET or GET-NEXT request for health objects is received by
            the agent it uses the g3healthTage and g3healthTintvl objects
            to determine whether it should refresh the cached healthTable.
            If g3healthTstmp + g3healthTintvl is less than the current value
            of the sysUpTime object then the agent refreshes the healthTable
            cache.  In either case it responds to the requests it receives
            with the data it currently has in the cache."
        ::= { g3health 2 }

    g3healthTdelay	OBJECT-TYPE
        SYNTAX    INTEGER
        ACCESS    read-only
        STATUS    mandatory
        DESCRIPTION
            "An object containing the delay encountered in updating
            the cached data"
        ::= { g3health 3 }

    g3healthTretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3health 4 }

    g3healthMajor	OBJECT-TYPE
        SYNTAX    Gauge
        ACCESS    read-only
        STATUS    mandatory
        DESCRIPTION
            "A Gauge object containing the number of logged major alarms."
        ::= { g3health 5 }

    g3healthMinor	OBJECT-TYPE
        SYNTAX    Gauge
        ACCESS    read-only
        STATUS    mandatory
        DESCRIPTION
            "A Gauge object containing the number of logged minor alarms."
        ::= { g3health 6 }

    g3healthWarning	OBJECT-TYPE
        SYNTAX    Gauge
        ACCESS    read-only
        STATUS    mandatory
        DESCRIPTION
            "A Gauge object containing the number of logged warnings."
        ::= { g3health 7 }

    g3healthTrkBusy	OBJECT-TYPE
        SYNTAX    Gauge
        ACCESS    read-only
        STATUS    mandatory
        DESCRIPTION
            "A Gauge object containing the number of trunks busied out."
        ::= { g3health 8 }

    g3healthStnBusy	OBJECT-TYPE
        SYNTAX    Gauge
        ACCESS    read-only
        STATUS    mandatory
        DESCRIPTION
            "A Gauge object containing the number of stations busied out."
        ::= { g3health 9 }

    g3healthOthBusy	OBJECT-TYPE
        SYNTAX    Gauge
        ACCESS    read-only
        STATUS    mandatory
        DESCRIPTION
            "A Gauge object containing the number of objects busied out
            except trunks and stations."
        ::= { g3health 10 }

    g3healthStaticOcc	OBJECT-TYPE
        SYNTAX    Gauge
        ACCESS    read-only
        STATUS    mandatory
        DESCRIPTION
            "A Gauge object containing the proportion of the CPU which
            is currently dedicated to high priority items (e.g. the
            operating system).  This percentage is rounded to the
            nearest integer, therefore a percentage of 0 means
            that the occupancy is less than one half of a percent
            (e.g. an occupancy of 89.6% would be displayed as 90%)."
        ::= { g3health 11 }

    g3healthCallpOcc	OBJECT-TYPE
        SYNTAX    Gauge
        ACCESS    read-only
        STATUS    mandatory
        DESCRIPTION
            "A Gauge object containing the proportion of the CPU
            which is currently dedicated to call processing.  This
            occupancy has priority over SM and IDLE occupancy
            categories and if needed, will take processor time
            away from these occupancy categories.  This
            percentage is rounded to the nearest integer,
            therefore a percentage of 0 means that the occupancy
            is less than one half of a percent (e.g. an occupancy
            of 89.6% would be displayed as 90%)."
        ::= { g3health 12 }

    g3healthSysMgmtOcc	OBJECT-TYPE
        SYNTAX    Gauge
        ACCESS    read-only
        STATUS    mandatory
        DESCRIPTION
            "A Gauge object containing the proportion of the CPU which
            is currently dedicated to system management or periodic
            and scheduled maintenance.  Therefore, if there is a
            large amount of periodic or scheduled maintenance
            testing being performed, this occupancy percentage
            can be high without affecting service.  This
            percentage is rounded to the nearest integer,
            therefore a percentage of 0 means that the occupancy
            is less than one half of a percent (e.g. an occupancy
            of 89.6% would be displayed as 90%)."
        ::= { g3health 13 }

    g3healthIdleOcc	OBJECT-TYPE
        SYNTAX    Gauge
        ACCESS    read-only
        STATUS    mandatory
        DESCRIPTION
            "A Gauge object containing the proportion of the CPU
            which is currently available for use.  This percentage
            is rounded to the nearest integer, therefore a
            percentage of 0 means that the occupancy is less than
            one half of a percent (e.g. an occupancy of 89.6%
            would be displayed as 90%)."
        ::= { g3health 14 }

    g3healthActiveSPE	OBJECT-TYPE
        SYNTAX    DisplayString (SIZE (0..6))
        ACCESS    read-only
        STATUS    mandatory
        DESCRIPTION
            "A DisplayString Object containing the active SPE (A or B)
            followed by the interchange mode (auto or lock)."
        ::= { g3health 15 }

    g3healthActivePNC	OBJECT-TYPE
        SYNTAX    DisplayString (SIZE (0..10))
        ACCESS    read-only
        STATUS    mandatory
        DESCRIPTION
            "A DisplayString Object containing the active PNC (A-PNC
            or B-PNC) followed by the interchange mode (auto or lock)."
        ::= { g3health 16 }

    g3healthDupSPE	OBJECT-TYPE
        SYNTAX    DisplayString (SIZE (0..1))
        ACCESS    read-only
        STATUS    mandatory
        DESCRIPTION
            "A DisplayString Object containing the duplication status
            of the SPE (y or n)."
        ::= { g3health 17 }

    g3healthDupPNC	OBJECT-TYPE
        SYNTAX    DisplayString (SIZE (0..1))
        ACCESS    read-only
        STATUS    mandatory
        DESCRIPTION
            "A DisplayString Object containing the duplication status
            of the PNC (y or n)."
        ::= { g3health 18 }

    g3healthPower	OBJECT-TYPE
        SYNTAX    DisplayString (SIZE (0..10))
        ACCESS    read-only
        STATUS    mandatory
        DESCRIPTION
            "A DisplayString Object containing the power source for
            the SPE (commercial or backup)."
        ::= { g3health 19 }

    g3healthTimeSource	OBJECT-TYPE
        SYNTAX    DisplayString (SIZE (0..9))
        ACCESS    read-only
        STATUS    mandatory
        DESCRIPTION
            "A DisplayString Object containing the time source for the
            SPE (external, internal, primary, secondary, or local)."
        ::= { g3health 20 }

    g3healthLogins	OBJECT-TYPE
        SYNTAX    Gauge
        ACCESS    read-only
        STATUS    mandatory
        DESCRIPTION
            "A Gauge object containing the number of active logins."
        ::= { g3health 21 }

    g3healthCab1	OBJECT-TYPE
        SYNTAX    INTEGER
        ACCESS    read-only
        STATUS    mandatory
        DESCRIPTION
            "An INTEGER Object containing the number of the 1st cabinet."
        ::= { g3health 22 }

    g3healthCab2	OBJECT-TYPE
        SYNTAX    INTEGER
        ACCESS    read-only
        STATUS    mandatory
        DESCRIPTION
            "An INTEGER Object containing the number of the 2nd cabinet."
        ::= { g3health 23 }

    g3healthCab3	OBJECT-TYPE
        SYNTAX    INTEGER
        ACCESS    read-only
        STATUS    mandatory
        DESCRIPTION
            "An INTEGER Object containing the number of the 3rd cabinet."
        ::= { g3health 24 }

    g3healthCab4	OBJECT-TYPE
        SYNTAX    INTEGER
        ACCESS    read-only
        STATUS    mandatory
        DESCRIPTION
            "An INTEGER Object containing the number of the 4th cabinet."
        ::= { g3health 25 }

    g3healthCab5	OBJECT-TYPE
        SYNTAX    INTEGER
        ACCESS    read-only
        STATUS    mandatory
        DESCRIPTION
            "An INTEGER Object containing the number of the 5th cabinet."
        ::= { g3health 26 }

    g3healthCab6	OBJECT-TYPE
        SYNTAX    INTEGER
        ACCESS    read-only
        STATUS    mandatory
        DESCRIPTION
            "An INTEGER Object containing the number of the 6th cabinet."
        ::= { g3health 27 }

    g3healthCab7	OBJECT-TYPE
        SYNTAX    INTEGER
        ACCESS    read-only
        STATUS    mandatory
        DESCRIPTION
            "An INTEGER Object containing the number of the 7th cabinet."
        ::= { g3health 28 }

    g3healthCab8	OBJECT-TYPE
        SYNTAX    INTEGER
        ACCESS    read-only
        STATUS    mandatory
        DESCRIPTION
            "An INTEGER Object containing the number of the 8th cabinet."
        ::= { g3health 29 }

    g3healthCab9	OBJECT-TYPE
        SYNTAX    INTEGER
        ACCESS    read-only
        STATUS    mandatory
        DESCRIPTION
            "An INTEGER Object containing the number of the 9th cabinet."
        ::= { g3health 30 }

    g3healthCab10	OBJECT-TYPE
        SYNTAX    INTEGER
        ACCESS    read-only
        STATUS    mandatory
        DESCRIPTION
            "An INTEGER Object containing the number of the 10th cabinet."
        ::= { g3health 31 }

    g3healthCab11	OBJECT-TYPE
        SYNTAX    INTEGER
        ACCESS    read-only
        STATUS    mandatory
        DESCRIPTION
            "An INTEGER Object containing the number of the 11th cabinet."
        ::= { g3health 32 }

    g3healthCab12	OBJECT-TYPE
        SYNTAX    INTEGER
        ACCESS    read-only
        STATUS    mandatory
        DESCRIPTION
            "An INTEGER Object containing the number of the 12th cabinet."
        ::= { g3health 33 }

    g3healthCab13	OBJECT-TYPE
        SYNTAX    INTEGER
        ACCESS    read-only
        STATUS    mandatory
        DESCRIPTION
            "An INTEGER Object containing the number of the 13th cabinet."
        ::= { g3health 34 }

    g3healthCab14	OBJECT-TYPE
        SYNTAX    INTEGER
        ACCESS    read-only
        STATUS    mandatory
        DESCRIPTION
            "An INTEGER Object containing the number of the 14th cabinet."
        ::= { g3health 35 }

    g3healthCab15	OBJECT-TYPE
        SYNTAX    INTEGER
        ACCESS    read-only
        STATUS    mandatory
        DESCRIPTION
            "An INTEGER Object containing the number of the 15th cabinet."
        ::= { g3health 36 }

    g3healthPncStat1	OBJECT-TYPE
        SYNTAX    DisplayString (SIZE (0..15))
        ACCESS    read-only
        STATUS    mandatory
        DESCRIPTION
            "A DisplayString Object containing the status of the PNC that is
            associated with the corresponding cabinet (CabX) field."
        ::= { g3health 37 }

    g3healthPncStat2	OBJECT-TYPE
        SYNTAX    DisplayString (SIZE (0..15))
        ACCESS    read-only
        STATUS    mandatory
        DESCRIPTION
            "A DisplayString Object containing the status of the PNC that is
            associated with the corresponding cabinet (CabX) field."
        ::= { g3health 38 }

    g3healthPncStat3	OBJECT-TYPE
        SYNTAX    DisplayString (SIZE (0..15))
        ACCESS    read-only
        STATUS    mandatory
        DESCRIPTION
            "A DisplayString Object containing the status of the PNC that is
            associated with the corresponding cabinet (CabX) field."
        ::= { g3health 39 }

    g3healthPncStat4	OBJECT-TYPE
        SYNTAX    DisplayString (SIZE (0..15))
        ACCESS    read-only
        STATUS    mandatory
        DESCRIPTION
            "A DisplayString Object containing the status of the PNC that is
            associated with the corresponding cabinet (CabX) field."
        ::= { g3health 40 }

    g3healthPncStat5	OBJECT-TYPE
        SYNTAX    DisplayString (SIZE (0..15))
        ACCESS    read-only
        STATUS    mandatory
        DESCRIPTION
            "A DisplayString Object containing the status of the PNC that is
            associated with the corresponding cabinet (CabX) field."
        ::= { g3health 41 }

    g3healthPncStat6	OBJECT-TYPE
        SYNTAX    DisplayString (SIZE (0..15))
        ACCESS    read-only
        STATUS    mandatory
        DESCRIPTION
            "A DisplayString Object containing the status of the PNC that is
            associated with the corresponding cabinet (CabX) field."
        ::= { g3health 42 }

    g3healthPncStat7	OBJECT-TYPE
        SYNTAX    DisplayString (SIZE (0..15))
        ACCESS    read-only
        STATUS    mandatory
        DESCRIPTION
            "A DisplayString Object containing the status of the PNC that is
            associated with the corresponding cabinet (CabX) field."
        ::= { g3health 43 }

    g3healthPncStat8	OBJECT-TYPE
        SYNTAX    DisplayString (SIZE (0..15))
        ACCESS    read-only
        STATUS    mandatory
        DESCRIPTION
            "A DisplayString Object containing the status of the PNC that is
            associated with the corresponding cabinet (CabX) field."
        ::= { g3health 44 }

    g3healthPncStat9	OBJECT-TYPE
        SYNTAX    DisplayString (SIZE (0..15))
        ACCESS    read-only
        STATUS    mandatory
        DESCRIPTION
            "A DisplayString Object containing the status of the PNC that is
            associated with the corresponding cabinet (CabX) field."
        ::= { g3health 45 }

    g3healthPncStat10	OBJECT-TYPE
        SYNTAX    DisplayString (SIZE (0..15))
        ACCESS    read-only
        STATUS    mandatory
        DESCRIPTION
            "A DisplayString Object containing the status of the PNC that is
            associated with the corresponding cabinet (CabX) field."
        ::= { g3health 46 }

    g3healthPncStat11	OBJECT-TYPE
        SYNTAX    DisplayString (SIZE (0..15))
        ACCESS    read-only
        STATUS    mandatory
        DESCRIPTION
            "A DisplayString Object containing the status of the PNC that is
            associated with the corresponding cabinet (CabX) field."
        ::= { g3health 47 }

    g3healthPncStat12	OBJECT-TYPE
        SYNTAX    DisplayString (SIZE (0..15))
        ACCESS    read-only
        STATUS    mandatory
        DESCRIPTION
            "A DisplayString Object containing the status of the PNC that is
            associated with the corresponding cabinet (CabX) field."
        ::= { g3health 48 }

    g3healthPncStat13	OBJECT-TYPE
        SYNTAX    DisplayString (SIZE (0..15))
        ACCESS    read-only
        STATUS    mandatory
        DESCRIPTION
            "A DisplayString Object containing the status of the PNC that is
            associated with the corresponding cabinet (CabX) field."
        ::= { g3health 49 }

    g3healthPncStat14	OBJECT-TYPE
        SYNTAX    DisplayString (SIZE (0..15))
        ACCESS    read-only
        STATUS    mandatory
        DESCRIPTION
            "A DisplayString Object containing the status of the PNC that is
            associated with the corresponding cabinet (CabX) field."
        ::= { g3health 50 }

    g3healthPncStat15	OBJECT-TYPE
        SYNTAX    DisplayString (SIZE (0..15))
        ACCESS    read-only
        STATUS    mandatory
        DESCRIPTION
            "A DisplayString Object containing the status of the PNC that is
            associated with the corresponding cabinet (CabX) field."
        ::= { g3health 51 }

    g3healthCab16	OBJECT-TYPE
        SYNTAX    INTEGER
        ACCESS    read-only
        STATUS    mandatory
        DESCRIPTION
            "An INTEGER Object containing the number of the 16th cabinet."
        ::= { g3health 52 }

    g3healthCab17	OBJECT-TYPE
        SYNTAX    INTEGER
        ACCESS    read-only
        STATUS    mandatory
        DESCRIPTION
            "An INTEGER Object containing the number of the 17th cabinet."
        ::= { g3health 53 }

    g3healthCab18	OBJECT-TYPE
        SYNTAX    INTEGER
        ACCESS    read-only
        STATUS    mandatory
        DESCRIPTION
            "An INTEGER Object containing the number of the 18th cabinet."
        ::= { g3health 54 }

    g3healthCab19	OBJECT-TYPE
        SYNTAX    INTEGER
        ACCESS    read-only
        STATUS    mandatory
        DESCRIPTION
            "An INTEGER Object containing the number of the 19th cabinet."
        ::= { g3health 55 }

    g3healthCab20	OBJECT-TYPE
        SYNTAX    INTEGER
        ACCESS    read-only
        STATUS    mandatory
        DESCRIPTION
            "An INTEGER Object containing the number of the 20th cabinet."
        ::= { g3health 56 }

    g3healthCab21	OBJECT-TYPE
        SYNTAX    INTEGER
        ACCESS    read-only
        STATUS    mandatory
        DESCRIPTION
            "An INTEGER Object containing the number of the 21st cabinet."
        ::= { g3health 57 }

    g3healthCab22	OBJECT-TYPE
        SYNTAX    INTEGER
        ACCESS    read-only
        STATUS    mandatory
        DESCRIPTION
            "An INTEGER Object containing the number of the 22nd cabinet."
        ::= { g3health 58 }

    g3healthCab23	OBJECT-TYPE
        SYNTAX    INTEGER
        ACCESS    read-only
        STATUS    mandatory
        DESCRIPTION
            "An INTEGER Object containing the number of the 23rd cabinet."
        ::= { g3health 59 }

    g3healthCab24	OBJECT-TYPE
        SYNTAX    INTEGER
        ACCESS    read-only
        STATUS    mandatory
        DESCRIPTION
            "An INTEGER Object containing the number of the 24th cabinet."
        ::= { g3health 60 }

    g3healthCab25	OBJECT-TYPE
        SYNTAX    INTEGER
        ACCESS    read-only
        STATUS    mandatory
        DESCRIPTION
            "An INTEGER Object containing the number of the 25th cabinet."
        ::= { g3health 61 }

    g3healthCab26	OBJECT-TYPE
        SYNTAX    INTEGER
        ACCESS    read-only
        STATUS    mandatory
        DESCRIPTION
            "An INTEGER Object containing the number of the 26th cabinet."
        ::= { g3health 62 }

    g3healthCab27	OBJECT-TYPE
        SYNTAX    INTEGER
        ACCESS    read-only
        STATUS    mandatory
        DESCRIPTION
            "An INTEGER Object containing the number of the 27th cabinet."
        ::= { g3health 63 }

    g3healthCab28	OBJECT-TYPE
        SYNTAX    INTEGER
        ACCESS    read-only
        STATUS    mandatory
        DESCRIPTION
            "An INTEGER Object containing the number of the 28th cabinet."
        ::= { g3health 64 }

    g3healthCab29	OBJECT-TYPE
        SYNTAX    INTEGER
        ACCESS    read-only
        STATUS    mandatory
        DESCRIPTION
            "An INTEGER Object containing the number of the 29th cabinet."
        ::= { g3health 65 }

    g3healthCab30	OBJECT-TYPE
        SYNTAX    INTEGER
        ACCESS    read-only
        STATUS    mandatory
        DESCRIPTION
            "An INTEGER Object containing the number of the 30th cabinet."
        ::= { g3health 66 }

    g3healthPncStat16	OBJECT-TYPE
        SYNTAX    DisplayString (SIZE (0..15))
        ACCESS    read-only
        STATUS    mandatory
        DESCRIPTION
            "A DisplayString Object containing the status of the PNC that is
            associated with the corresponding cabinet (CabX) field."
        ::= { g3health 67 }

    g3healthPncStat17	OBJECT-TYPE
        SYNTAX    DisplayString (SIZE (0..15))
        ACCESS    read-only
        STATUS    mandatory
        DESCRIPTION
            "A DisplayString Object containing the status of the PNC that is
            associated with the corresponding cabinet (CabX) field."
        ::= { g3health 68 }

    g3healthPncStat18	OBJECT-TYPE
        SYNTAX    DisplayString (SIZE (0..15))
        ACCESS    read-only
        STATUS    mandatory
        DESCRIPTION
            "A DisplayString Object containing the status of the PNC that is
            associated with the corresponding cabinet (CabX) field."
        ::= { g3health 69 }

    g3healthPncStat19	OBJECT-TYPE
        SYNTAX    DisplayString (SIZE (0..15))
        ACCESS    read-only
        STATUS    mandatory
        DESCRIPTION
            "A DisplayString Object containing the status of the PNC that is
            associated with the corresponding cabinet (CabX) field."
        ::= { g3health 70 }

    g3healthPncStat20	OBJECT-TYPE
        SYNTAX    DisplayString (SIZE (0..15))
        ACCESS    read-only
        STATUS    mandatory
        DESCRIPTION
            "A DisplayString Object containing the status of the PNC that is
            associated with the corresponding cabinet (CabX) field."
        ::= { g3health 71 }

    g3healthPncStat21	OBJECT-TYPE
        SYNTAX    DisplayString (SIZE (0..15))
        ACCESS    read-only
        STATUS    mandatory
        DESCRIPTION
            "A DisplayString Object containing the status of the PNC that is
            associated with the corresponding cabinet (CabX) field."
        ::= { g3health 72 }

    g3healthPncStat22	OBJECT-TYPE
        SYNTAX    DisplayString (SIZE (0..15))
        ACCESS    read-only
        STATUS    mandatory
        DESCRIPTION
            "A DisplayString Object containing the status of the PNC that is
            associated with the corresponding cabinet (CabX) field."
        ::= { g3health 73 }

    g3healthPncStat23	OBJECT-TYPE
        SYNTAX    DisplayString (SIZE (0..15))
        ACCESS    read-only
        STATUS    mandatory
        DESCRIPTION
            "A DisplayString Object containing the status of the PNC that is
            associated with the corresponding cabinet (CabX) field."
        ::= { g3health 74 }

    g3healthPncStat24	OBJECT-TYPE
        SYNTAX    DisplayString (SIZE (0..15))
        ACCESS    read-only
        STATUS    mandatory
        DESCRIPTION
            "A DisplayString Object containing the status of the PNC that is
            associated with the corresponding cabinet (CabX) field."
        ::= { g3health 75 }

    g3healthPncStat25	OBJECT-TYPE
        SYNTAX    DisplayString (SIZE (0..15))
        ACCESS    read-only
        STATUS    mandatory
        DESCRIPTION
            "A DisplayString Object containing the status of the PNC that is
            associated with the corresponding cabinet (CabX) field."
        ::= { g3health 76 }

    g3healthPncStat26	OBJECT-TYPE
        SYNTAX    DisplayString (SIZE (0..15))
        ACCESS    read-only
        STATUS    mandatory
        DESCRIPTION
            "A DisplayString Object containing the status of the PNC that is
            associated with the corresponding cabinet (CabX) field."
        ::= { g3health 77 }

    g3healthPncStat27	OBJECT-TYPE
        SYNTAX    DisplayString (SIZE (0..15))
        ACCESS    read-only
        STATUS    mandatory
        DESCRIPTION
            "A DisplayString Object containing the status of the PNC that is
            associated with the corresponding cabinet (CabX) field."
        ::= { g3health 78 }

    g3healthPncStat28	OBJECT-TYPE
        SYNTAX    DisplayString (SIZE (0..15))
        ACCESS    read-only
        STATUS    mandatory
        DESCRIPTION
            "A DisplayString Object containing the status of the PNC that is
            associated with the corresponding cabinet (CabX) field."
        ::= { g3health 79 }

    g3healthPncStat29	OBJECT-TYPE
        SYNTAX    DisplayString (SIZE (0..15))
        ACCESS    read-only
        STATUS    mandatory
        DESCRIPTION
            "A DisplayString Object containing the status of the PNC that is
            associated with the corresponding cabinet (CabX) field."
        ::= { g3health 80 }

    g3healthPncStat30	OBJECT-TYPE
        SYNTAX    DisplayString (SIZE (0..15))
        ACCESS    read-only
        STATUS    mandatory
        DESCRIPTION
            "A DisplayString Object containing the status of the PNC that is
            associated with the corresponding cabinet (CabX) field."
        ::= { g3health 81 }

    g3healthCab31	OBJECT-TYPE
        SYNTAX    INTEGER
        ACCESS    read-only
        STATUS    mandatory
        DESCRIPTION
            "An INTEGER Object containing the number of the 31st cabinet."
        ::= { g3health 82 }

    g3healthCab32	OBJECT-TYPE
        SYNTAX    INTEGER
        ACCESS    read-only
        STATUS    mandatory
        DESCRIPTION
            "An INTEGER Object containing the number of the 32nd cabinet."
        ::= { g3health 83 }

    g3healthCab33	OBJECT-TYPE
        SYNTAX    INTEGER
        ACCESS    read-only
        STATUS    mandatory
        DESCRIPTION
            "An INTEGER Object containing the number of the 33rd cabinet."
        ::= { g3health 84 }

    g3healthCab34	OBJECT-TYPE
        SYNTAX    INTEGER
        ACCESS    read-only
        STATUS    mandatory
        DESCRIPTION
            "An INTEGER Object containing the number of the 34th cabinet."
        ::= { g3health 85 }

    g3healthCab35	OBJECT-TYPE
        SYNTAX    INTEGER
        ACCESS    read-only
        STATUS    mandatory
        DESCRIPTION
            "An INTEGER Object containing the number of the 35th cabinet."
        ::= { g3health 86 }

    g3healthCab36	OBJECT-TYPE
        SYNTAX    INTEGER
        ACCESS    read-only
        STATUS    mandatory
        DESCRIPTION
            "An INTEGER Object containing the number of the 36th cabinet."
        ::= { g3health 87 }

    g3healthCab37	OBJECT-TYPE
        SYNTAX    INTEGER
        ACCESS    read-only
        STATUS    mandatory
        DESCRIPTION
            "An INTEGER Object containing the number of the 37th cabinet."
        ::= { g3health 88 }

    g3healthCab38	OBJECT-TYPE
        SYNTAX    INTEGER
        ACCESS    read-only
        STATUS    mandatory
        DESCRIPTION
            "An INTEGER Object containing the number of the 38th cabinet."
        ::= { g3health 89 }

    g3healthCab39	OBJECT-TYPE
        SYNTAX    INTEGER
        ACCESS    read-only
        STATUS    mandatory
        DESCRIPTION
            "An INTEGER Object containing the number of the 39th cabinet."
        ::= { g3health 90 }

    g3healthCab40	OBJECT-TYPE
        SYNTAX    INTEGER
        ACCESS    read-only
        STATUS    mandatory
        DESCRIPTION
            "An INTEGER Object containing the number of the 40th cabinet."
        ::= { g3health 91 }

    g3healthCab41	OBJECT-TYPE
        SYNTAX    INTEGER
        ACCESS    read-only
        STATUS    mandatory
        DESCRIPTION
            "An INTEGER Object containing the number of the 41st cabinet."
        ::= { g3health 92 }

    g3healthCab42	OBJECT-TYPE
        SYNTAX    INTEGER
        ACCESS    read-only
        STATUS    mandatory
        DESCRIPTION
            "An INTEGER Object containing the number of the 42nd cabinet."
        ::= { g3health 93 }

    g3healthCab43	OBJECT-TYPE
        SYNTAX    INTEGER
        ACCESS    read-only
        STATUS    mandatory
        DESCRIPTION
            "An INTEGER Object containing the number of the 43rd cabinet."
        ::= { g3health 94 }

    g3healthCab44	OBJECT-TYPE
        SYNTAX    INTEGER
        ACCESS    read-only
        STATUS    mandatory
        DESCRIPTION
            "An INTEGER Object containing the number of the 44th cabinet."
        ::= { g3health 95 }

    g3healthPncStat31	OBJECT-TYPE
        SYNTAX    DisplayString (SIZE (0..15))
        ACCESS    read-only
        STATUS    mandatory
        DESCRIPTION
            "A DisplayString Object containing the status of the PNC that is
            associated with the corresponding cabinet (CabX) field."
        ::= { g3health 96 }

    g3healthPncStat32	OBJECT-TYPE
        SYNTAX    DisplayString (SIZE (0..15))
        ACCESS    read-only
        STATUS    mandatory
        DESCRIPTION
            "A DisplayString Object containing the status of the PNC that is
            associated with the corresponding cabinet (CabX) field."
        ::= { g3health 97 }

    g3healthPncStat33	OBJECT-TYPE
        SYNTAX    DisplayString (SIZE (0..15))
        ACCESS    read-only
        STATUS    mandatory
        DESCRIPTION
            "A DisplayString Object containing the status of the PNC that is
            associated with the corresponding cabinet (CabX) field."
        ::= { g3health 98 }

    g3healthPncStat34	OBJECT-TYPE
        SYNTAX    DisplayString (SIZE (0..15))
        ACCESS    read-only
        STATUS    mandatory
        DESCRIPTION
            "A DisplayString Object containing the status of the PNC that is
            associated with the corresponding cabinet (CabX) field."
        ::= { g3health 99 }

    g3healthPncStat35	OBJECT-TYPE
        SYNTAX    DisplayString (SIZE (0..15))
        ACCESS    read-only
        STATUS    mandatory
        DESCRIPTION
            "A DisplayString Object containing the status of the PNC that is
            associated with the corresponding cabinet (CabX) field."
        ::= { g3health 100 }

    g3healthPncStat36	OBJECT-TYPE
        SYNTAX    DisplayString (SIZE (0..15))
        ACCESS    read-only
        STATUS    mandatory
        DESCRIPTION
            "A DisplayString Object containing the status of the PNC that is
            associated with the corresponding cabinet (CabX) field."
        ::= { g3health 101 }

    g3healthPncStat37	OBJECT-TYPE
        SYNTAX    DisplayString (SIZE (0..15))
        ACCESS    read-only
        STATUS    mandatory
        DESCRIPTION
            "A DisplayString Object containing the status of the PNC that is
            associated with the corresponding cabinet (CabX) field."
        ::= { g3health 102 }

    g3healthPncStat38	OBJECT-TYPE
        SYNTAX    DisplayString (SIZE (0..15))
        ACCESS    read-only
        STATUS    mandatory
        DESCRIPTION
            "A DisplayString Object containing the status of the PNC that is
            associated with the corresponding cabinet (CabX) field."
        ::= { g3health 103 }

    g3healthPncStat39	OBJECT-TYPE
        SYNTAX    DisplayString (SIZE (0..15))
        ACCESS    read-only
        STATUS    mandatory
        DESCRIPTION
            "A DisplayString Object containing the status of the PNC that is
            associated with the corresponding cabinet (CabX) field."
        ::= { g3health 104 }

    g3healthPncStat40	OBJECT-TYPE
        SYNTAX    DisplayString (SIZE (0..15))
        ACCESS    read-only
        STATUS    mandatory
        DESCRIPTION
            "A DisplayString Object containing the status of the PNC that is
            associated with the corresponding cabinet (CabX) field."
        ::= { g3health 105 }

    g3healthPncStat41	OBJECT-TYPE
        SYNTAX    DisplayString (SIZE (0..15))
        ACCESS    read-only
        STATUS    mandatory
        DESCRIPTION
            "A DisplayString Object containing the status of the PNC that is
            associated with the corresponding cabinet (CabX) field."
        ::= { g3health 106 }

    g3healthPncStat42	OBJECT-TYPE
        SYNTAX    DisplayString (SIZE (0..15))
        ACCESS    read-only
        STATUS    mandatory
        DESCRIPTION
            "A DisplayString Object containing the status of the PNC that is
            associated with the corresponding cabinet (CabX) field."
        ::= { g3health 107 }

    g3healthPncStat43	OBJECT-TYPE
        SYNTAX    DisplayString (SIZE (0..15))
        ACCESS    read-only
        STATUS    mandatory
        DESCRIPTION
            "A DisplayString Object containing the status of the PNC that is
            associated with the corresponding cabinet (CabX) field."
        ::= { g3health 108 }

    g3healthPncStat44	OBJECT-TYPE
        SYNTAX    DisplayString (SIZE (0..15))
        ACCESS    read-only
        STATUS    mandatory
        DESCRIPTION
            "A DisplayString Object containing the status of the PNC that is
            associated with the corresponding cabinet (CabX) field."
        ::= { g3health 109 }

    g3healthCab45	OBJECT-TYPE
        SYNTAX    INTEGER
        ACCESS    read-only
        STATUS    mandatory
        DESCRIPTION
            "An INTEGER Object containing the number of the 45th cabinet."
        ::= { g3health 110 }

    g3healthCab46	OBJECT-TYPE
        SYNTAX    INTEGER
        ACCESS    read-only
        STATUS    mandatory
        DESCRIPTION
            "An INTEGER Object containing the number of the 46th cabinet."
        ::= { g3health 111 }

    g3healthCab47	OBJECT-TYPE
        SYNTAX    INTEGER
        ACCESS    read-only
        STATUS    mandatory
        DESCRIPTION
            "An INTEGER Object containing the number of the 47th cabinet."
        ::= { g3health 112 }

    g3healthCab48	OBJECT-TYPE
        SYNTAX    INTEGER
        ACCESS    read-only
        STATUS    mandatory
        DESCRIPTION
            "An INTEGER Object containing the number of the 48th cabinet."
        ::= { g3health 113 }

    g3healthCab49	OBJECT-TYPE
        SYNTAX    INTEGER
        ACCESS    read-only
        STATUS    mandatory
        DESCRIPTION
            "An INTEGER Object containing the number of the 49th cabinet."
        ::= { g3health 114 }

    g3healthCab50	OBJECT-TYPE
        SYNTAX    INTEGER
        ACCESS    read-only
        STATUS    mandatory
        DESCRIPTION
            "An INTEGER Object containing the number of the 50th cabinet."
        ::= { g3health 115 }

    g3healthCab51	OBJECT-TYPE
        SYNTAX    INTEGER
        ACCESS    read-only
        STATUS    mandatory
        DESCRIPTION
            "An INTEGER Object containing the number of the 51st cabinet."
        ::= { g3health 116 }

    g3healthCab52	OBJECT-TYPE
        SYNTAX    INTEGER
        ACCESS    read-only
        STATUS    mandatory
        DESCRIPTION
            "An INTEGER Object containing the number of the 52nd cabinet."
        ::= { g3health 117 }

    g3healthCab53	OBJECT-TYPE
        SYNTAX    INTEGER
        ACCESS    read-only
        STATUS    mandatory
        DESCRIPTION
            "An INTEGER Object containing the number of the 53rd cabinet."
        ::= { g3health 118 }

    g3healthCab54	OBJECT-TYPE
        SYNTAX    INTEGER
        ACCESS    read-only
        STATUS    mandatory
        DESCRIPTION
            "An INTEGER Object containing the number of the 54th cabinet."
        ::= { g3health 119 }

    g3healthCab55	OBJECT-TYPE
        SYNTAX    INTEGER
        ACCESS    read-only
        STATUS    mandatory
        DESCRIPTION
            "An INTEGER Object containing the number of the 55th cabinet."
        ::= { g3health 120 }

    g3healthCab56	OBJECT-TYPE
        SYNTAX    INTEGER
        ACCESS    read-only
        STATUS    mandatory
        DESCRIPTION
            "An INTEGER Object containing the number of the 56th cabinet."
        ::= { g3health 121 }

    g3healthCab57	OBJECT-TYPE
        SYNTAX    INTEGER
        ACCESS    read-only
        STATUS    mandatory
        DESCRIPTION
            "An INTEGER Object containing the number of the 57th cabinet."
        ::= { g3health 122 }

    g3healthCab58	OBJECT-TYPE
        SYNTAX    INTEGER
        ACCESS    read-only
        STATUS    mandatory
        DESCRIPTION
            "An INTEGER Object containing the number of the 58th cabinet."
        ::= { g3health 123 }

    g3healthCab59	OBJECT-TYPE
        SYNTAX    INTEGER
        ACCESS    read-only
        STATUS    mandatory
        DESCRIPTION
            "An INTEGER Object containing the number of the 59th cabinet."
        ::= { g3health 124 }

    g3healthCab60	OBJECT-TYPE
        SYNTAX    INTEGER
        ACCESS    read-only
        STATUS    mandatory
        DESCRIPTION
            "An INTEGER Object containing the number of the 60th cabinet."
        ::= { g3health 125 }

    g3healthCab61	OBJECT-TYPE
        SYNTAX    INTEGER
        ACCESS    read-only
        STATUS    mandatory
        DESCRIPTION
            "An INTEGER Object containing the number of the 61st cabinet."
        ::= { g3health 126 }

    g3healthCab62	OBJECT-TYPE
        SYNTAX    INTEGER
        ACCESS    read-only
        STATUS    mandatory
        DESCRIPTION
            "An INTEGER Object containing the number of the 62nd cabinet."
        ::= { g3health 127 }

    g3healthCab63	OBJECT-TYPE
        SYNTAX    INTEGER
        ACCESS    read-only
        STATUS    mandatory
        DESCRIPTION
            "An INTEGER Object containing the number of the 63rd cabinet."
        ::= { g3health 128 }

    g3healthCab64	OBJECT-TYPE
        SYNTAX    INTEGER
        ACCESS    read-only
        STATUS    mandatory
        DESCRIPTION
            "An INTEGER Object containing the number of the 64th cabinet."
        ::= { g3health 129 }

    g3healthPncStat45	OBJECT-TYPE
        SYNTAX    DisplayString (SIZE (0..15))
        ACCESS    read-only
        STATUS    mandatory
        DESCRIPTION
            "A DisplayString Object containing the status of the PNC that is
            associated with the corresponding cabinet (CabX) field."
        ::= { g3health 130 }

    g3healthPncStat46	OBJECT-TYPE
        SYNTAX    DisplayString (SIZE (0..15))
        ACCESS    read-only
        STATUS    mandatory
        DESCRIPTION
            "A DisplayString Object containing the status of the PNC that is
            associated with the corresponding cabinet (CabX) field."
        ::= { g3health 131 }

    g3healthPncStat47	OBJECT-TYPE
        SYNTAX    DisplayString (SIZE (0..15))
        ACCESS    read-only
        STATUS    mandatory
        DESCRIPTION
            "A DisplayString Object containing the status of the PNC that is
            associated with the corresponding cabinet (CabX) field."
        ::= { g3health 132 }

    g3healthPncStat48	OBJECT-TYPE
        SYNTAX    DisplayString (SIZE (0..15))
        ACCESS    read-only
        STATUS    mandatory
        DESCRIPTION
            "A DisplayString Object containing the status of the PNC that is
            associated with the corrresponding cabinet (CabX) field."
        ::= { g3health 133 }

    g3healthPncStat49	OBJECT-TYPE
        SYNTAX    DisplayString (SIZE (0..15))
        ACCESS    read-only
        STATUS    mandatory
        DESCRIPTION
            "A DisplayString Object containing the status of the PNC that is
            associated with the corrresponding cabinet (CabX) field."
        ::= { g3health 134 }

    g3healthPncStat50	OBJECT-TYPE
        SYNTAX    DisplayString (SIZE (0..15))
        ACCESS    read-only
        STATUS    mandatory
        DESCRIPTION
            "A DisplayString Object containing the status of the PNC that is
            associated with the corrresponding cabinet (CabX) field."
        ::= { g3health 135 }

    g3healthPncStat51	OBJECT-TYPE
        SYNTAX    DisplayString (SIZE (0..15))
        ACCESS    read-only
        STATUS    mandatory
        DESCRIPTION
            "A DisplayString Object containing the status of the PNC that is
            associated with the corrresponding cabinet (CabX) field."
        ::= { g3health 136 }

    g3healthPncStat52	OBJECT-TYPE
        SYNTAX    DisplayString (SIZE (0..15))
        ACCESS    read-only
        STATUS    mandatory
        DESCRIPTION
            "A DisplayString Object containing the status of the PNC that is
            associated with the corrresponding cabinet (CabX) field."
        ::= { g3health 137 }

    g3healthPncStat53	OBJECT-TYPE
        SYNTAX    DisplayString (SIZE (0..15))
        ACCESS    read-only
        STATUS    mandatory
        DESCRIPTION
            "A DisplayString Object containing the status of the PNC that is
            associated with the corrresponding cabinet (CabX) field."
        ::= { g3health 138 }

    g3healthPncStat54	OBJECT-TYPE
        SYNTAX    DisplayString (SIZE (0..15))
        ACCESS    read-only
        STATUS    mandatory
        DESCRIPTION
            "A DisplayString Object containing the status of the PNC that is
            associated with the corrresponding cabinet (CabX) field."
        ::= { g3health 139 }

    g3healthPncStat55	OBJECT-TYPE
        SYNTAX    DisplayString (SIZE (0..15))
        ACCESS    read-only
        STATUS    mandatory
        DESCRIPTION
            "A DisplayString Object containing the status of the PNC that is
            associated with the corrresponding cabinet (CabX) field."
        ::= { g3health 140 }

    g3healthPncStat56	OBJECT-TYPE
        SYNTAX    DisplayString (SIZE (0..15))
        ACCESS    read-only
        STATUS    mandatory
        DESCRIPTION
            "A DisplayString Object containing the status of the PNC that is
            associated with the corrresponding cabinet (CabX) field."
        ::= { g3health 141 }

    g3healthPncStat57	OBJECT-TYPE
        SYNTAX    DisplayString (SIZE (0..15))
        ACCESS    read-only
        STATUS    mandatory
        DESCRIPTION
            "A DisplayString Object containing the status of the PNC that is
            associated with the corrresponding cabinet (CabX) field."
        ::= { g3health 142 }

    g3healthPncStat58	OBJECT-TYPE
        SYNTAX    DisplayString (SIZE (0..15))
        ACCESS    read-only
        STATUS    mandatory
        DESCRIPTION
            "A DisplayString Object containing the status of the PNC that is
            associated with the corrresponding cabinet (CabX) field."
        ::= { g3health 143 }

    g3healthPncStat59	OBJECT-TYPE
        SYNTAX    DisplayString (SIZE (0..15))
        ACCESS    read-only
        STATUS    mandatory
        DESCRIPTION
            "A DisplayString Object containing the status of the PNC that is
            associated with the corrresponding cabinet (CabX) field."
        ::= { g3health 144 }

    g3healthPncStat60	OBJECT-TYPE
        SYNTAX    DisplayString (SIZE (0..15))
        ACCESS    read-only
        STATUS    mandatory
        DESCRIPTION
            "A DisplayString Object containing the status of the PNC that is
            associated with the corrresponding cabinet (CabX) field."
        ::= { g3health 145 }

    g3healthPncStat61	OBJECT-TYPE
        SYNTAX    DisplayString (SIZE (0..15))
        ACCESS    read-only
        STATUS    mandatory
        DESCRIPTION
            "A DisplayString Object containing the status of the PNC that is
            associated with the corrresponding cabinet (CabX) field."
        ::= { g3health 146 }

    g3healthPncStat62	OBJECT-TYPE
        SYNTAX    DisplayString (SIZE (0..15))
        ACCESS    read-only
        STATUS    mandatory
        DESCRIPTION
            "A DisplayString Object containing the status of the PNC that is
            associated with the corrresponding cabinet (CabX) field."
        ::= { g3health 147 }

    g3healthPncStat63	OBJECT-TYPE
        SYNTAX    DisplayString (SIZE (0..15))
        ACCESS    read-only
        STATUS    mandatory
        DESCRIPTION
            "A DisplayString Object containing the status of the PNC that is
            associated with the corrresponding cabinet (CabX) field."
        ::= { g3health 148 }

    g3healthPncStat64	OBJECT-TYPE
        SYNTAX    DisplayString (SIZE (0..15))
        ACCESS    read-only
        STATUS    mandatory
        DESCRIPTION
            "A DisplayString Object containing the status of the PNC that is
            associated with the corrresponding cabinet (CabX) field."
        ::= { g3health 149 }


    -- the g3cabinet group

    g3cabinetTage	OBJECT-TYPE
        SYNTAX    INTEGER
        ACCESS    read-only
        STATUS    mandatory
        DESCRIPTION
            "The number of timeticks since the cabinet data was last
            extracted from the switch by the G3 Proxy Agent. This object
            along with the g3cabinetTintvl object allows the Network Manager
            to determine the validity of the error log in the
            cache and to control when the proxy agent extracts the
            cabinet data from the switch."
        ::= { g3cabinet 1 }

    g3cabinetTintvl	OBJECT-TYPE
        SYNTAX    INTEGER
        ACCESS    read-write
        STATUS    mandatory
        DESCRIPTION
            "An object containing the interval for which the cabinet data
            extracted from the switch is considered valid by the proxy agent.
            When a GET or GET-NEXT request for cabinet objects is received by
            the agent it uses the g3cabinetTage and g3cabinetTintvl objects
            to determine whether it should refresh the cached cabinetTable.
            If g3cabinetTstmp + g3cabinetTintvl is less than the current value
            of the sysUpTime object then the agent refreshes the cabinetTable
            cache.  In either case it responds to the requests it receives
            with the data it currently has in the cache."
        ::= { g3cabinet 2 }

    g3cabinetTdelay	OBJECT-TYPE
        SYNTAX    INTEGER
        ACCESS    read-only
        STATUS    mandatory
        DESCRIPTION
            "An object containing the delay encountered in updating
            the cached data"
        ::= { g3cabinet 3 }

    g3cabinetTretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3cabinet 4 }

    g3cabinetTcount	OBJECT-TYPE
        SYNTAX    Gauge
        ACCESS    read-only
        STATUS    mandatory
        DESCRIPTION
            "A Gauge object containing the number of data records in the
            cache."
        ::= { g3cabinet 5 }

    g3cabinetTable	OBJECT-TYPE
        SYNTAX    SEQUENCE OF G3cabinetEntry
        ACCESS    not-accessible
        STATUS    mandatory
        DESCRIPTION
            "A list of g3cabinet entries."
        ::= { g3cabinet 6 }

    g3cabinetEntry	OBJECT-TYPE
        SYNTAX    G3cabinetEntry
        ACCESS    not-accessible
        STATUS    mandatory
        DESCRIPTION
            "A g3cabinet entry containing objects of the
            g3cabinet information sent by the switch."
        INDEX    { g3cabinetNum }
        ::= { g3cabinetTable 1 }

    G3cabinetEntry ::= SEQUENCE {
        g3cabinetNum
            INTEGER,
        g3cabinetType
            DisplayString,
        g3cabinetLayout
            DisplayString,
        g3cabinetRoom
            DisplayString,
        g3cabinetFloor
            DisplayString,
        g3cabinetBuilding
            DisplayString,
        g3cabinetCarAType
            DisplayString,
        g3cabinetCarAPNN
            INTEGER,
        g3cabinetCarBType
            DisplayString,
        g3cabinetCarBPNN
            INTEGER,
        g3cabinetCarCType
            DisplayString,
        g3cabinetCarCPNN
            INTEGER,
        g3cabinetCarDType
            DisplayString,
        g3cabinetCarDPNN
            INTEGER,
        g3cabinetCarEType
            DisplayString,
        g3cabinetCarEPNN
            INTEGER,
        g3cabinetSREPN
            DisplayString,
        g3cabinetSRProductID
            DisplayString,
        g3cabinetRack
            DisplayString,
        g3cabinetLocation
            DisplayString
        }

    g3cabinetNum	OBJECT-TYPE
        SYNTAX    INTEGER
        ACCESS    read-only
        STATUS    mandatory
        DESCRIPTION
            "An INTEGER Object that uniquely identifies a cabinet in the
            system."
        ::= { g3cabinetEntry 1 }

    g3cabinetType	OBJECT-TYPE
        SYNTAX    DisplayString (SIZE (0..22))
        ACCESS    read-only
        STATUS    mandatory
        DESCRIPTION
            "A DisplayString Object containing the type of cabinet (PPN or
            EPN)."
        ::= { g3cabinetEntry 2 }

    g3cabinetLayout	OBJECT-TYPE
        SYNTAX    DisplayString (SIZE (0..20))
        ACCESS    read-only
        STATUS    mandatory
        DESCRIPTION
            "A DisplayString Object containing the cabinet layout."
        ::= { g3cabinetEntry 3 }

    g3cabinetRoom	OBJECT-TYPE
        SYNTAX    DisplayString (SIZE (0..10))
        ACCESS    read-only
        STATUS    mandatory
        DESCRIPTION
            "A DisplayString Object containing the cabinet room number."
        ::= { g3cabinetEntry 4 }

    g3cabinetFloor	OBJECT-TYPE
        SYNTAX    DisplayString (SIZE (0..10))
        ACCESS    read-only
        STATUS    mandatory
        DESCRIPTION
            "A DisplayString Object containing the cabinet floor number."
        ::= { g3cabinetEntry 5 }

    g3cabinetBuilding	OBJECT-TYPE
        SYNTAX    DisplayString (SIZE (0..10))
        ACCESS    read-only
        STATUS    mandatory
        DESCRIPTION
            "A DisplayString Object containing the cabinet building name."
        ::= { g3cabinetEntry 6 }

    g3cabinetCarAType	OBJECT-TYPE
        SYNTAX    DisplayString (SIZE (0..17))
        ACCESS    read-only
        STATUS    mandatory
        DESCRIPTION
            "A DisplayString Object containing the type of carrier A."
        ::= { g3cabinetEntry 7 }

    g3cabinetCarAPNN	OBJECT-TYPE
        SYNTAX    INTEGER
        ACCESS    read-only
        STATUS    mandatory
        DESCRIPTION
            "An INTEGER Object containing the Port Network Number in
            carrier A."
        ::= { g3cabinetEntry 8 }

    g3cabinetCarBType	OBJECT-TYPE
        SYNTAX    DisplayString (SIZE (0..17))
        ACCESS    read-only
        STATUS    mandatory
        DESCRIPTION
            "A DisplayString Object containing the type of carrier B."
        ::= { g3cabinetEntry 9 }

    g3cabinetCarBPNN	OBJECT-TYPE
        SYNTAX    INTEGER
        ACCESS    read-only
        STATUS    mandatory
        DESCRIPTION
            "An INTEGER Object containing the Port Network Number in
            carrier B."
        ::= { g3cabinetEntry 10 }

    g3cabinetCarCType	OBJECT-TYPE
        SYNTAX    DisplayString (SIZE (0..17))
        ACCESS    read-only
        STATUS    mandatory
        DESCRIPTION
            "A DisplayString Object containing the type of carrier C."
        ::= { g3cabinetEntry 11 }

    g3cabinetCarCPNN	OBJECT-TYPE
        SYNTAX    INTEGER
        ACCESS    read-only
        STATUS    mandatory
        DESCRIPTION
            "An INTEGER Object containing the Port Network Number in
            carrier C."
        ::= { g3cabinetEntry 12 }

    g3cabinetCarDType	OBJECT-TYPE
        SYNTAX    DisplayString (SIZE (0..17))
        ACCESS    read-only
        STATUS    mandatory
        DESCRIPTION
            "A DisplayString Object containing the type of carrier D."
        ::= { g3cabinetEntry 13 }

    g3cabinetCarDPNN	OBJECT-TYPE
        SYNTAX    INTEGER
        ACCESS    read-only
        STATUS    mandatory
        DESCRIPTION
            "An INTEGER Object containing the Port Network Number in
            carrier D."
        ::= { g3cabinetEntry 14 }

    g3cabinetCarEType	OBJECT-TYPE
        SYNTAX    DisplayString (SIZE (0..17))
        ACCESS    read-only
        STATUS    mandatory
        DESCRIPTION
            "A DisplayString Object containing the type of carrier E."
        ::= { g3cabinetEntry 15 }

    g3cabinetCarEPNN	OBJECT-TYPE
        SYNTAX    INTEGER
        ACCESS    read-only
        STATUS    mandatory
        DESCRIPTION
            "An INTEGER Object containing the Port Network Number in
            carrier E."
        ::= { g3cabinetEntry 16 }

    g3cabinetSREPN	OBJECT-TYPE
        SYNTAX    DisplayString (SIZE (0..1))
        ACCESS    read-only
        STATUS    mandatory
        DESCRIPTION
            "A DisplayString Object that states whether the EPN is a
            survivable remote EPN (y or n)."
        ::= { g3cabinetEntry 17 }

    g3cabinetSRProductID	OBJECT-TYPE
        SYNTAX    DisplayString (SIZE (0..10))
        ACCESS    read-only
        STATUS    mandatory
        DESCRIPTION
            "A DisplayString Object containing the product ID of the survivable
            remote EPN (if the EPN is survivable remote)."
        ::= { g3cabinetEntry 18 }

    g3cabinetRack	OBJECT-TYPE
        SYNTAX    DisplayString (SIZE (0..6))
        ACCESS    read-only
        STATUS    mandatory
        DESCRIPTION
            "A DisplayString Object containing the rack-mount location."
        ::= { g3cabinetEntry 19 }

    g3cabinetLocation	OBJECT-TYPE
        SYNTAX    DisplayString (SIZE (0..3))
        ACCESS    read-only
        STATUS    mandatory
        DESCRIPTION
            "A DisplayString Object containing the network location of the
            cabinet."
        ::= { g3cabinetEntry 20 }


    -- the g3cabtype group

    g3cabtypeTage	OBJECT-TYPE
        SYNTAX    INTEGER
        ACCESS    read-only
        STATUS    mandatory
        DESCRIPTION
            "The number of timeticks since the cabtype data was last
            extracted from the switch by the G3 Proxy Agent. This object
            along with the g3cabtypeTintvl object allows the Network Manager
            to determine the validity of the cabtype data in the
            cache and to control when the proxy agent extracts the
            cabtype data from the switch."
        ::= { g3cabtype 1 }

    g3cabtypeTintvl	OBJECT-TYPE
        SYNTAX    INTEGER
        ACCESS    read-write
        STATUS    mandatory
        DESCRIPTION
            "An object containing the interval for which the cabtype data
            extracted from the switch is considered valid by the proxy agent.
            When a GET or GET-NEXT request for cabtype objects is received
            by the agent it uses the g3cabtypeTage and g3cabtypeTintvl objects
            to determine whether it should refresh the cached cabtype data.
            If g3cabtypeTstmp + g3cabtypeTintvl is less than the current value
            of the sysUpTime object then the agent refreshes the cabtype data
            cache.  In either case it responds to the requests it receives
            with the data it currently has in the cache."
        ::= { g3cabtype 2 }

    g3cabtypeTdelay	OBJECT-TYPE
        SYNTAX    INTEGER
        ACCESS    read-only
        STATUS    mandatory
        DESCRIPTION
            "An object containing the delay encountered in updating
            the cached data"
        ::= { g3cabtype 3 }

    g3cabtypeTretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3cabtype 4 }

    g3cabtypeCab1Type	OBJECT-TYPE
        SYNTAX    DisplayString (SIZE (0..4))
        ACCESS    read-only
        STATUS    mandatory
        DESCRIPTION
            "A DisplayString Object containing the type of cabinet 1."
        ::= { g3cabtype 5 }

    g3cabtypeCab2Type	OBJECT-TYPE
        SYNTAX    DisplayString (SIZE (0..4))
        ACCESS    read-only
        STATUS    mandatory
        DESCRIPTION
            "A DisplayString Object containing the type of cabinet 2."
        ::= { g3cabtype 6 }

    g3cabtypeCab3Type	OBJECT-TYPE
        SYNTAX    DisplayString (SIZE (0..4))
        ACCESS    read-only
        STATUS    mandatory
        DESCRIPTION
            "A DisplayString Object containing the type of cabinet 3."
        ::= { g3cabtype 7 }


    -- the g3cartype group

    g3cartypeTage	OBJECT-TYPE
        SYNTAX    INTEGER
        ACCESS    read-only
        STATUS    mandatory
        DESCRIPTION
            "The number of timeticks since the cartype data was last
            extracted from the switch by the G3 Proxy Agent. This object
            along with the g3cartypeTintvl object allows the Network Manager
            to determine the validity of the cartype data in the
            cache and to control when the proxy agent extracts the
            cartype data from the switch."
        ::= { g3cartype 1 }

    g3cartypeTintvl	OBJECT-TYPE
        SYNTAX    INTEGER
        ACCESS    read-write
        STATUS    mandatory
        DESCRIPTION
            "An object containing the interval for which the cartype data
            extracted from the switch is considered valid by the proxy agent.
            When a GET or GET-NEXT request for cartype objects is received
            by the agent it uses the g3cartypeTage and g3cartypeTintvl objects
            to determine whether it should refresh the cached cartype data.
            If g3cartypeTstmp + g3cartypeTintvl is less than the current value
            of the sysUpTime object then the agent refreshes the cartype data
            cache.  In either case it responds to the requests it receives
            with the data it currently has in the cache."
        ::= { g3cartype 2 }

    g3cartypeTdelay	OBJECT-TYPE
        SYNTAX    INTEGER
        ACCESS    read-only
        STATUS    mandatory
        DESCRIPTION
            "An object containing the delay encountered in updating
            the cached data"
        ::= { g3cartype 3 }

    g3cartypeTretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3cartype 4 }

    g3cartypeCab1CarAType	OBJECT-TYPE
        SYNTAX    DisplayString (SIZE (0..17))
        ACCESS    read-only
        STATUS    mandatory
        DESCRIPTION
            "A DisplayString Object containing the type of
            cabinet 1/carrier A."
        ::= { g3cartype 5 }

    g3cartypeCab1CarBType	OBJECT-TYPE
        SYNTAX    DisplayString (SIZE (0..17))
        ACCESS    read-only
        STATUS    mandatory
        DESCRIPTION
            "A DisplayString Object containing the type of
            cabinet 1/carrier B."
        ::= { g3cartype 6 }

    g3cartypeCab1CarCType	OBJECT-TYPE
        SYNTAX    DisplayString (SIZE (0..17))
        ACCESS    read-only
        STATUS    mandatory
        DESCRIPTION
            "A DisplayString Object containing the type of
            cabinet 1/carrier C."
        ::= { g3cartype 7 }

    g3cartypeCab1CarDType	OBJECT-TYPE
        SYNTAX    DisplayString (SIZE (0..17))
        ACCESS    read-only
        STATUS    mandatory
        DESCRIPTION
            "A DisplayString Object containing the type of
            cabinet 1/carrier D."
        ::= { g3cartype 8 }

    g3cartypeCab1CarEType	OBJECT-TYPE
        SYNTAX    DisplayString (SIZE (0..17))
        ACCESS    read-only
        STATUS    mandatory
        DESCRIPTION
            "A DisplayString Object containing the type of
            cabinet 1/carrier E."
        ::= { g3cartype 9 }

    g3cartypeCab2CarAType	OBJECT-TYPE
        SYNTAX    DisplayString (SIZE (0..17))
        ACCESS    read-only
        STATUS    mandatory
        DESCRIPTION
            "A DisplayString Object containing the type of
            cabinet 2/carrier A."
        ::= { g3cartype 10 }

    g3cartypeCab2CarBType	OBJECT-TYPE
        SYNTAX    DisplayString (SIZE (0..17))
        ACCESS    read-only
        STATUS    mandatory
        DESCRIPTION
            "A DisplayString Object containing the type of
            cabinet 2/carrier B."
        ::= { g3cartype 11 }

    g3cartypeCab2CarCType	OBJECT-TYPE
        SYNTAX    DisplayString (SIZE (0..17))
        ACCESS    read-only
        STATUS    mandatory
        DESCRIPTION
            "A DisplayString Object containing the type of
            cabinet 2/carrier C."
        ::= { g3cartype 12 }

    g3cartypeCab2CarDType	OBJECT-TYPE
        SYNTAX    DisplayString (SIZE (0..17))
        ACCESS    read-only
        STATUS    mandatory
        DESCRIPTION
            "A DisplayString Object containing the type of
            cabinet 2/carrier D."
        ::= { g3cartype 13 }

    g3cartypeCab2CarEType	OBJECT-TYPE
        SYNTAX    DisplayString (SIZE (0..17))
        ACCESS    read-only
        STATUS    mandatory
        DESCRIPTION
            "A DisplayString Object containing the type of
            cabinet 2/carrier E."
        ::= { g3cartype 14 }

    g3cartypeCab3CarAType	OBJECT-TYPE
        SYNTAX    DisplayString (SIZE (0..17))
        ACCESS    read-only
        STATUS    mandatory
        DESCRIPTION
            "A DisplayString Object containing the type of
            cabinet 3/carrier A."
        ::= { g3cartype 15 }

    g3cartypeCab3CarBType	OBJECT-TYPE
        SYNTAX    DisplayString (SIZE (0..17))
        ACCESS    read-only
        STATUS    mandatory
        DESCRIPTION
            "A DisplayString Object containing the type of
            cabinet 3/carrier B."
        ::= { g3cartype 16 }

    g3cartypeCab3CarCType	OBJECT-TYPE
        SYNTAX    DisplayString (SIZE (0..17))
        ACCESS    read-only
        STATUS    mandatory
        DESCRIPTION
            "A DisplayString Object containing the type of
            cabinet 3/carrier C."
        ::= { g3cartype 17 }

    g3cartypeCab3CarDType	OBJECT-TYPE
        SYNTAX    DisplayString (SIZE (0..17))
        ACCESS    read-only
        STATUS    mandatory
        DESCRIPTION
            "A DisplayString Object containing the type of
            cabinet 3/carrier D."
        ::= { g3cartype 18 }

    g3cartypeCab3CarEType	OBJECT-TYPE
        SYNTAX    DisplayString (SIZE (0..17))
        ACCESS    read-only
        STATUS    mandatory
        DESCRIPTION
            "A DisplayString Object containing the type of
            cabinet 3/carrier E."
        ::= { g3cartype 19 }


    -- the g3port group

    g3portTable	OBJECT-TYPE
        SYNTAX    SEQUENCE OF G3portEntry
        ACCESS    not-accessible
        STATUS    mandatory
        DESCRIPTION
            "A list of g3port entries."
        ::= { g3port 1 }

    g3portEntry	OBJECT-TYPE
        SYNTAX    G3portEntry
        ACCESS    not-accessible
        STATUS    mandatory
        DESCRIPTION
            "A g3port entry containing objects of the
            g3port information sent by the switch."
        INDEX    { g3portNumber }
        ::= { g3portTable 1 }

    G3portEntry ::= SEQUENCE {
        g3portNumber
            DisplayString,
        g3portEquipType
            DisplayString,
        g3portId
            DisplayString,
        g3portEquipType2
            DisplayString,
        g3portId2
            DisplayString
        }

    g3portNumber	OBJECT-TYPE
        SYNTAX    DisplayString (SIZE (0..9))
        ACCESS    read-only
        STATUS    mandatory
        DESCRIPTION
            "A DisplayString Object that uniquely identifies a port based on
            its location in the system. The syntax for the Port Location is as
            follows: cabinet(01-44):carrier(A-E):slot(01-20):port(01-32).
            This object will serve as the instance identifier for portEntry."
        ::= { g3portEntry 1 }

    g3portEquipType	OBJECT-TYPE
        SYNTAX    DisplayString (SIZE (0..24))
        ACCESS    read-only
        STATUS    mandatory
        DESCRIPTION
            "A DisplayString Object containing the equipment type for
            the port."
        ::= { g3portEntry 2 }

    g3portId	OBJECT-TYPE
        SYNTAX    DisplayString (SIZE (0..16))
        ACCESS    read-only
        STATUS    mandatory
        DESCRIPTION
            "A DisplayString Object containing the identifier associated
            with the equipment type."
        ::= { g3portEntry 3 }

    g3portEquipType2	OBJECT-TYPE
        SYNTAX    DisplayString (SIZE (0..24))
        ACCESS    read-only
        STATUS    mandatory
        DESCRIPTION
            "A DisplayString Object containing the equipment type for
            a second physical port."
        ::= { g3portEntry 4 }

    g3portId2	OBJECT-TYPE
        SYNTAX    DisplayString (SIZE (0..16))
        ACCESS    read-only
        STATUS    mandatory
        DESCRIPTION
            "A DisplayString Object containing the identifier associated
            with the equipment type for a second physical port."
        ::= { g3portEntry 5 }


    -- the g3station group

    g3stationTable	OBJECT-TYPE
        SYNTAX    SEQUENCE OF G3stationEntry
        ACCESS    not-accessible
        STATUS    mandatory
        DESCRIPTION
            "A list of g3station entries."
        ::= { g3station 1 }

    g3stationEntry	OBJECT-TYPE
        SYNTAX    G3stationEntry
        ACCESS    not-accessible
        STATUS    mandatory
        DESCRIPTION
            "A g3station entry containing objects of the
            g3station information sent by the switch."
        INDEX    { g3stationExtension }
        ::= { g3stationTable 1 }

    G3stationEntry ::= SEQUENCE {
        g3stationExtension
            DisplayString,
        g3stationType
            DisplayString,
        g3stationName
            DisplayString,
        g3stationBuilding
            DisplayString,
        g3stationFloor
            DisplayString,
        g3stationRoom
            DisplayString,
        g3stationCable
            DisplayString,
        g3stationJack
            DisplayString,
        g3stationDataExt
            DisplayString,
        g3stationDataName
            DisplayString,
        g3stationPort
            DisplayString
        }

    g3stationExtension	OBJECT-TYPE
        SYNTAX    DisplayString (SIZE (0..15))
        ACCESS    read-only
        STATUS    mandatory
        DESCRIPTION
            "A DisplayString Object that uniquely identifies an administered
            station."
        ::= { g3stationEntry 1 }

    g3stationType	OBJECT-TYPE
        SYNTAX    DisplayString (SIZE (0..7))
        ACCESS    read-only
        STATUS    mandatory
        DESCRIPTION
            "A DisplayString Object containing the station type."
        ::= { g3stationEntry 2 }

    g3stationName	OBJECT-TYPE
        SYNTAX    DisplayString (SIZE (0..27))
        ACCESS    read-only
        STATUS    mandatory
        DESCRIPTION
            "A DisplayString Object containing the name assigned to the
            station."
        ::= { g3stationEntry 3 }

    g3stationBuilding	OBJECT-TYPE
        SYNTAX    DisplayString (SIZE (0..10))
        ACCESS    read-only
        STATUS    mandatory
        DESCRIPTION
            "A DisplayString Object containing the building location of the
            station."
        ::= { g3stationEntry 4 }

    g3stationFloor	OBJECT-TYPE
        SYNTAX    DisplayString (SIZE (0..10))
        ACCESS    read-only
        STATUS    mandatory
        DESCRIPTION
            "A DisplayString Object containing the floor location of the
            station."
        ::= { g3stationEntry 5 }

    g3stationRoom	OBJECT-TYPE
        SYNTAX    DisplayString (SIZE (0..10))
        ACCESS    read-only
        STATUS    mandatory
        DESCRIPTION
            "A DisplayString Object containing the room location of the
            station."
        ::= { g3stationEntry 6 }

    g3stationCable	OBJECT-TYPE
        SYNTAX    DisplayString (SIZE (0..5))
        ACCESS    read-only
        STATUS    mandatory
        DESCRIPTION
            "A DisplayString Object containing the cable used by the station."
        ::= { g3stationEntry 7 }

    g3stationJack	OBJECT-TYPE
        SYNTAX    DisplayString (SIZE (0..5))
        ACCESS    read-only
        STATUS    mandatory
        DESCRIPTION
            "A DisplayString Object containing the jack used by the station."
        ::= { g3stationEntry 8 }

    g3stationDataExt	OBJECT-TYPE
        SYNTAX    DisplayString (SIZE (0..15))
        ACCESS    read-only
        STATUS    mandatory
        DESCRIPTION
            "A Display String Object containing the extension of the data
            module attached to the station."
        ::= { g3stationEntry 9 }

    g3stationDataName	OBJECT-TYPE
        SYNTAX    DisplayString (SIZE (0..5))
        ACCESS    read-only
        STATUS    mandatory
        DESCRIPTION
            "A DisplayString Object containing the name assigned to the data
            module attached to the station."
        ::= { g3stationEntry 10 }

    g3stationPort	OBJECT-TYPE
        SYNTAX    DisplayString (SIZE (0..7))
        ACCESS    read-only
        STATUS    mandatory
        DESCRIPTION
            "A DisplayString Object that uniquely identifies the station port
            based on its location in the system. The syntax for the Port Number
            is as follows: cabinet(1-22):carrier(A-E):slot(01-20)."
        ::= { g3stationEntry 11 }


    -- the g3statsta group

    g3statstaTable	OBJECT-TYPE
        SYNTAX    SEQUENCE OF G3statstaEntry
        ACCESS    not-accessible
        STATUS    mandatory
        DESCRIPTION
            "A list of g3statsta entries."
        ::= { g3statsta 1 }

    g3statstaEntry	OBJECT-TYPE
        SYNTAX    G3statstaEntry
        ACCESS    not-accessible
        STATUS    mandatory
        DESCRIPTION
            "A g3statsta entry containing objects of the
            g3statsta information sent by the switch."
        INDEX    { g3statstaExtension }
        ::= { g3statstaTable 1 }

    G3statstaEntry ::= SEQUENCE {
        g3statstaExtension
            DisplayString,
        g3statstaServiceState
            DisplayString,
        g3statstaMaintBusy
            DisplayString,
        g3statstaConnPort1
            DisplayString,
        g3statstaConnPort2
            DisplayString,
        g3statstaConnPort3
            DisplayString,
        g3statstaConnPort4
            DisplayString,
        g3statstaConnPort5
            DisplayString,
        g3statstaConnPort6
            DisplayString,
        g3statstaSACactive
            DisplayString,
        g3statstaCFdestExt
            DisplayString,
        g3statstaRingCutOff
            DisplayString,
        g3statstaSerialNbr
            DisplayString,
        g3statstaPartID
            DisplayString,
        g3statstaSwitchPort
            DisplayString,
        g3statstaSwitchIPAddr
            DisplayString,
        g3statstaSwitchIPPort
            DisplayString,
        g3statstaSetIPAddr
            DisplayString,
        g3statstaSetIPPort
            DisplayString
        }

    g3statstaExtension	OBJECT-TYPE
        SYNTAX    DisplayString (SIZE (0..15))
        ACCESS    read-only
        STATUS    mandatory
        DESCRIPTION
            "A DisplayString Object that uniquely identifies an administered
            station."
        ::= { g3statstaEntry 1 }

    g3statstaServiceState	OBJECT-TYPE
        SYNTAX    DisplayString (SIZE (0..22))
        ACCESS    read-only
        STATUS    mandatory
        DESCRIPTION
            "A DisplayString Object containing the service state of the
            station."
        ::= { g3statstaEntry 2 }

    g3statstaMaintBusy	OBJECT-TYPE
        SYNTAX    DisplayString (SIZE (0..4))
        ACCESS    read-only
        STATUS    mandatory
        DESCRIPTION
            "A DisplayString Object that indicates whether the station has
            been busied for maintenance."
        ::= { g3statstaEntry 3 }

    g3statstaConnPort1	OBJECT-TYPE
        SYNTAX    DisplayString (SIZE (0..10))
        ACCESS    read-only
        STATUS    mandatory
        DESCRIPTION
            "A DisplayString Object that contains the first port connected to
            the station."
        ::= { g3statstaEntry 4 }

    g3statstaConnPort2	OBJECT-TYPE
        SYNTAX    DisplayString (SIZE (0..10))
        ACCESS    read-only
        STATUS    mandatory
        DESCRIPTION
            "A DisplayString Object that contains the second port connected to
            the station."
        ::= { g3statstaEntry 5 }

    g3statstaConnPort3	OBJECT-TYPE
        SYNTAX    DisplayString (SIZE (0..10))
        ACCESS    read-only
        STATUS    mandatory
        DESCRIPTION
            "A DisplayString Object that contains the third port connected to
            the station."
        ::= { g3statstaEntry 6 }

    g3statstaConnPort4	OBJECT-TYPE
        SYNTAX    DisplayString (SIZE (0..10))
        ACCESS    read-only
        STATUS    mandatory
        DESCRIPTION
            "A DisplayString Object that contains the fourth port connected to
            the station."
        ::= { g3statstaEntry 7 }

    g3statstaConnPort5	OBJECT-TYPE
        SYNTAX    DisplayString (SIZE (0..10))
        ACCESS    read-only
        STATUS    mandatory
        DESCRIPTION
            "A DisplayString Object that contains the fifth port connected to
            the station."
        ::= { g3statstaEntry 8 }

    g3statstaConnPort6	OBJECT-TYPE
        SYNTAX    DisplayString (SIZE (0..10))
        ACCESS    read-only
        STATUS    mandatory
        DESCRIPTION
            "A DisplayString Object that contains the sixth port connected to
            the station."
        ::= { g3statstaEntry 9 }

    g3statstaSACactive	OBJECT-TYPE
        SYNTAX    DisplayString (SIZE (0..4))
        ACCESS    read-only
        STATUS    mandatory
        DESCRIPTION
            "A DisplayString Object that indicates whether SAC has been
            activated for the station."
        ::= { g3statstaEntry 10 }

    g3statstaCFdestExt	OBJECT-TYPE
        SYNTAX    DisplayString (SIZE (0..17))
        ACCESS    read-only
        STATUS    mandatory
        DESCRIPTION
            "A DisplayString Object that contains the CF Destination Extension
            for the station."
        ::= { g3statstaEntry 11 }

    g3statstaRingCutOff	OBJECT-TYPE
        SYNTAX    DisplayString (SIZE (0..8))
        ACCESS    read-only
        STATUS    mandatory
        DESCRIPTION
            "A DisplayString Object that indicates whether Ring Cut Off has
            been activated for the station."
        ::= { g3statstaEntry 12 }

    g3statstaSerialNbr	OBJECT-TYPE
        SYNTAX    DisplayString (SIZE (0..12))
        ACCESS    read-only
        STATUS    mandatory
        DESCRIPTION
            "A DisplayString Object that contains the serial number for the
            station."
        ::= { g3statstaEntry 13 }

    g3statstaPartID	OBJECT-TYPE
        SYNTAX    DisplayString (SIZE (0..11))
        ACCESS    read-only
        STATUS    mandatory
        DESCRIPTION
            "A DisplayString Object that contains the part id for the
            station."
        ::= { g3statstaEntry 14 }

    g3statstaSwitchPort	OBJECT-TYPE
        SYNTAX    DisplayString (SIZE (0..8))
        ACCESS    read-only
        STATUS    mandatory
        DESCRIPTION
            "A DisplayString Object that contains the switch port for the
            station."
        ::= { g3statstaEntry 15 }

    g3statstaSwitchIPAddr	OBJECT-TYPE
        SYNTAX    DisplayString (SIZE (0..40))
        ACCESS    read-only
        STATUS    mandatory
        DESCRIPTION
            "A DisplayString Object that contains the switch-end IP address for the
            station."
        ::= { g3statstaEntry 16 }

    g3statstaSwitchIPPort	OBJECT-TYPE
        SYNTAX    DisplayString (SIZE (0..6))
        ACCESS    read-only
        STATUS    mandatory
        DESCRIPTION
            "A DisplayString Object that contains the switch-end IP port nbr for the
            station."
        ::= { g3statstaEntry 17 }

    g3statstaSetIPAddr	OBJECT-TYPE
        SYNTAX    DisplayString (SIZE (0..40))
        ACCESS    read-only
        STATUS    mandatory
        DESCRIPTION
            "A DisplayString Object that contains the set-end IP address for the
            station."
        ::= { g3statstaEntry 18 }

    g3statstaSetIPPort	OBJECT-TYPE
        SYNTAX    DisplayString (SIZE (0..6))
        ACCESS    read-only
        STATUS    mandatory
        DESCRIPTION
            "A DisplayString Object that contains the set-end IP port nbr for the
            station."
        ::= { g3statstaEntry 19 }


    -- the g3trunkmem group

    g3trunkmemTable	OBJECT-TYPE
        SYNTAX    SEQUENCE OF G3trunkmemEntry
        ACCESS    not-accessible
        STATUS    mandatory
        DESCRIPTION
            "A list of g3trunkmem entries."
        ::= { g3trunkmem 1 }

    g3trunkmemEntry	OBJECT-TYPE
        SYNTAX    G3trunkmemEntry
        ACCESS    not-accessible
        STATUS    mandatory
        DESCRIPTION
            "A g3trunkmem entry containing objects of the
            g3trunkmem information sent by the switch."
        INDEX    { g3trunkmemGroup, g3trunkmemMember }
        ::= { g3trunkmemTable 1 }

    G3trunkmemEntry ::= SEQUENCE {
        g3trunkmemGroup
            INTEGER,
        g3trunkmemMember
            INTEGER,
        g3trunkmemName
            DisplayString,
        g3trunkmemType
            DisplayString,
        g3trunkmemSigGroup
            DisplayString,
        g3trunkmemPort
            DisplayString
        }

    g3trunkmemGroup	OBJECT-TYPE
        SYNTAX    INTEGER
        ACCESS    read-only
        STATUS    mandatory
        DESCRIPTION
            "An INTEGER Object that uniquely identifies an administered
            trunk group."
        ::= { g3trunkmemEntry 1 }

    g3trunkmemMember	OBJECT-TYPE
        SYNTAX    INTEGER
        ACCESS    read-only
        STATUS    mandatory
        DESCRIPTION
            "An INTEGER Object that uniquely identifies a trunk group member."
        ::= { g3trunkmemEntry 2 }

    g3trunkmemName	OBJECT-TYPE
        SYNTAX    DisplayString (SIZE (0..12))
        ACCESS    read-only
        STATUS    mandatory
        DESCRIPTION
            "A DisplayString Object containing the name assigned to the trunk
            group member."
        ::= { g3trunkmemEntry 3 }

    g3trunkmemType	OBJECT-TYPE
        SYNTAX    DisplayString (SIZE (0..7))
        ACCESS    read-only
        STATUS    mandatory
        DESCRIPTION
            "A DisplayString Object containing the Type of the trunk group member."
        ::= { g3trunkmemEntry 4 }

    g3trunkmemSigGroup	OBJECT-TYPE
        SYNTAX    DisplayString (SIZE (0..3))
        ACCESS    read-only
        STATUS    mandatory
        DESCRIPTION
            "A DisplayString Object containing the Signaling Group assigned
            to the trunk group member."
        ::= { g3trunkmemEntry 5 }

    g3trunkmemPort	OBJECT-TYPE
        SYNTAX    DisplayString (SIZE (0..7))
        ACCESS    read-only
        STATUS    mandatory
        DESCRIPTION
            "A DisplayString Object that uniquely identifies the trunk port
            based on its location in the system. The syntax for the Port Number
            is as follows: cabinet(1-22):carrier(A-E):slot(01-20)."
        ::= { g3trunkmemEntry 6 }


    -- the g3trunksta group

    g3trunkstaTable	OBJECT-TYPE
        SYNTAX    SEQUENCE OF G3trunkstaEntry
        ACCESS    not-accessible
        STATUS    mandatory
        DESCRIPTION
            "A list of g3trunksta entries."
        ::= { g3trunksta 1 }

    g3trunkstaEntry	OBJECT-TYPE
        SYNTAX    G3trunkstaEntry
        ACCESS    not-accessible
        STATUS    mandatory
        DESCRIPTION
            "A g3trunksta entry containing objects of the
            g3trunksta information sent by the switch."
        INDEX    { g3trunkstaTrunkGroup, g3trunkstaMember }
        ::= { g3trunkstaTable 1 }

    G3trunkstaEntry ::= SEQUENCE {
        g3trunkstaTrunkGroup
            INTEGER,
        g3trunkstaMember
            INTEGER,
        g3trunkstaServiceState
            DisplayString,
        g3trunkstaMaintBusy
            DisplayString,
        g3trunkstaConnPort1
            DisplayString,
        g3trunkstaConnPort2
            DisplayString,
        g3trunkstaConnPort3
            DisplayString,
        g3trunkstaConnPort4
            DisplayString,
        g3trunkstaConnPort5
            DisplayString,
        g3trunkstaConnPort6
            DisplayString,
        g3trunkstaConnPort7
            DisplayString,
        g3trunkstaConnPort8
            DisplayString,
        g3trunkstaConnPort9
            DisplayString
        }

    g3trunkstaTrunkGroup	OBJECT-TYPE
        SYNTAX    INTEGER
        ACCESS    read-only
        STATUS    mandatory
        DESCRIPTION
            "An INTEGER Object that uniquely identifies an administered
            trunk group."
        ::= { g3trunkstaEntry 1 }

    g3trunkstaMember	OBJECT-TYPE
        SYNTAX    INTEGER
        ACCESS    read-only
        STATUS    mandatory
        DESCRIPTION
            "An INTEGER Object that uniquely identifies a trunk group member."
        ::= { g3trunkstaEntry 2 }

    g3trunkstaServiceState	OBJECT-TYPE
        SYNTAX    DisplayString (SIZE (0..18))
        ACCESS    read-only
        STATUS    mandatory
        DESCRIPTION
            "A DisplayString Object containing the service state of the trunk."
        ::= { g3trunkstaEntry 3 }

    g3trunkstaMaintBusy	OBJECT-TYPE
        SYNTAX    DisplayString (SIZE (0..4))
        ACCESS    read-only
        STATUS    mandatory
        DESCRIPTION
            "A DisplayString Object that indicates whether the trunk has
            been busied for maintenance."
        ::= { g3trunkstaEntry 4 }

    g3trunkstaConnPort1	OBJECT-TYPE
        SYNTAX    DisplayString (SIZE (0..10))
        ACCESS    read-only
        STATUS    mandatory
        DESCRIPTION
            "A DisplayString Object that contains the first port connected to
            the trunk."
        ::= { g3trunkstaEntry 5 }

    g3trunkstaConnPort2	OBJECT-TYPE
        SYNTAX    DisplayString (SIZE (0..10))
        ACCESS    read-only
        STATUS    mandatory
        DESCRIPTION
            "A DisplayString Object that contains the second port connected to
            the trunk."
        ::= { g3trunkstaEntry 6 }

    g3trunkstaConnPort3	OBJECT-TYPE
        SYNTAX    DisplayString (SIZE (0..10))
        ACCESS    read-only
        STATUS    mandatory
        DESCRIPTION
            "A DisplayString Object that contains the third port connected to
            the trunk."
        ::= { g3trunkstaEntry 7 }

    g3trunkstaConnPort4	OBJECT-TYPE
        SYNTAX    DisplayString (SIZE (0..10))
        ACCESS    read-only
        STATUS    mandatory
        DESCRIPTION
            "A DisplayString Object that contains the fourth port connected to
            the trunk."
        ::= { g3trunkstaEntry 8 }

    g3trunkstaConnPort5	OBJECT-TYPE
        SYNTAX    DisplayString (SIZE (0..7))
        ACCESS    read-only
        STATUS    mandatory
        DESCRIPTION
            "A DisplayString Object that contains the fifth port connected to
            the trunk."
        ::= { g3trunkstaEntry 9 }

    g3trunkstaConnPort6	OBJECT-TYPE
        SYNTAX    DisplayString (SIZE (0..10))
        ACCESS    read-only
        STATUS    mandatory
        DESCRIPTION
            "A DisplayString Object that contains the sixth port connected to
            the trunk."
        ::= { g3trunkstaEntry 10 }

    g3trunkstaConnPort7	OBJECT-TYPE
        SYNTAX    DisplayString (SIZE (0..10))
        ACCESS    read-only
        STATUS    mandatory
        DESCRIPTION
            "A DisplayString Object that contains the seventh port connected to
            the trunk."
        ::= { g3trunkstaEntry 11 }

    g3trunkstaConnPort8	OBJECT-TYPE
        SYNTAX    DisplayString (SIZE (0..10))
        ACCESS    read-only
        STATUS    mandatory
        DESCRIPTION
            "A DisplayString Object that contains the eighth port connected to
            the trunk."
        ::= { g3trunkstaEntry 12 }

    g3trunkstaConnPort9	OBJECT-TYPE
        SYNTAX    DisplayString (SIZE (0..10))
        ACCESS    read-only
        STATUS    mandatory
        DESCRIPTION
            "A DisplayString Object that contains the ninth port connected to
            the trunk."
        ::= { g3trunkstaEntry 13 }


    -- the g3datamod group

    g3datamodTable	OBJECT-TYPE
        SYNTAX    SEQUENCE OF G3datamodEntry
        ACCESS    not-accessible
        STATUS    mandatory
        DESCRIPTION
            "A list of g3datamod entries."
        ::= { g3datamod 1 }

    g3datamodEntry	OBJECT-TYPE
        SYNTAX    G3datamodEntry
        ACCESS    not-accessible
        STATUS    mandatory
        DESCRIPTION
            "A g3datamod entry containing objects of the
            g3datamod information sent by the switch."
        INDEX    { g3datamodExtension }
        ::= { g3datamodTable 1 }

    G3datamodEntry ::= SEQUENCE {
        g3datamodExtension
            DisplayString,
        g3datamodType
            DisplayString,
        g3datamodName
            DisplayString
        }

    g3datamodExtension	OBJECT-TYPE
        SYNTAX    DisplayString (SIZE (0..15))
        ACCESS    read-only
        STATUS    mandatory
        DESCRIPTION
            "A DisplayString Object that uniquely identifies an administered
            data module."
        ::= { g3datamodEntry 1 }

    g3datamodType	OBJECT-TYPE
        SYNTAX    DisplayString (SIZE (0..12))
        ACCESS    read-only
        STATUS    mandatory
        DESCRIPTION
            "A DisplayString Object containing the data module type."
        ::= { g3datamodEntry 2 }

    g3datamodName	OBJECT-TYPE
        SYNTAX    DisplayString (SIZE (0..15))
        ACCESS    read-only
        STATUS    mandatory
        DESCRIPTION
            "A DisplayString Object containing the name assigned to the data
            module."
        ::= { g3datamodEntry 3 }


    -- the g3datamsta group

    g3datamstaTable	OBJECT-TYPE
        SYNTAX    SEQUENCE OF G3datamstaEntry
        ACCESS    not-accessible
        STATUS    mandatory
        DESCRIPTION
            "A list of g3datamsta entries."
        ::= { g3datamsta 1 }

    g3datamstaEntry	OBJECT-TYPE
        SYNTAX    G3datamstaEntry
        ACCESS    not-accessible
        STATUS    mandatory
        DESCRIPTION
            "A g3datamsta entry containing objects of the
            g3datamsta information sent by the switch."
        INDEX    { g3datamstaExtension }
        ::= { g3datamstaTable 1 }

    G3datamstaEntry ::= SEQUENCE {
        g3datamstaExtension
            DisplayString,
        g3datamstaServiceState
            DisplayString,
        g3datamstaMaintBusy
            DisplayString,
        g3datamstaConnPort1
            DisplayString,
        g3datamstaConnPort2
            DisplayString,
        g3datamstaConnPort3
            DisplayString,
        g3datamstaConnPort4
            DisplayString,
        g3datamstaConnPort5
            DisplayString,
        g3datamstaConnPort6
            DisplayString,
        g3datamstaConnPort7
            DisplayString,
        g3datamstaConnPort8
            DisplayString,
        g3datamstaConnPort9
            DisplayString,
        g3datamstaCFdestExt
            DisplayString
        }

    g3datamstaExtension	OBJECT-TYPE
        SYNTAX    DisplayString (SIZE (0..15))
        ACCESS    read-only
        STATUS    mandatory
        DESCRIPTION
            "A DisplayString Object that uniquely identifies an administered
            data module."
        ::= { g3datamstaEntry 1 }

    g3datamstaServiceState	OBJECT-TYPE
        SYNTAX    DisplayString (SIZE (0..20))
        ACCESS    read-only
        STATUS    mandatory
        DESCRIPTION
            "A DisplayString Object containing the service state of the
            data module."
        ::= { g3datamstaEntry 2 }

    g3datamstaMaintBusy	OBJECT-TYPE
        SYNTAX    DisplayString (SIZE (0..4))
        ACCESS    read-only
        STATUS    mandatory
        DESCRIPTION
            "A DisplayString Object that indicates whether the data module has
            been busied for maintenance."
        ::= { g3datamstaEntry 3 }

    g3datamstaConnPort1	OBJECT-TYPE
        SYNTAX    DisplayString (SIZE (0..10))
        ACCESS    read-only
        STATUS    mandatory
        DESCRIPTION
            "A DisplayString Object that contains the first port connected to
            the data module."
        ::= { g3datamstaEntry 4 }

    g3datamstaConnPort2	OBJECT-TYPE
        SYNTAX    DisplayString (SIZE (0..10))
        ACCESS    read-only
        STATUS    mandatory
        DESCRIPTION
            "A DisplayString Object that contains the second port connected to
            the data module."
        ::= { g3datamstaEntry 5 }

    g3datamstaConnPort3	OBJECT-TYPE
        SYNTAX    DisplayString (SIZE (0..10))
        ACCESS    read-only
        STATUS    mandatory
        DESCRIPTION
            "A DisplayString Object that contains the third port connected to
            the data module."
        ::= { g3datamstaEntry 6 }

    g3datamstaConnPort4	OBJECT-TYPE
        SYNTAX    DisplayString (SIZE (0..10))
        ACCESS    read-only
        STATUS    mandatory
        DESCRIPTION
            "A DisplayString Object that contains the fourth port connected to
            the data module."
        ::= { g3datamstaEntry 7 }

    g3datamstaConnPort5	OBJECT-TYPE
        SYNTAX    DisplayString (SIZE (0..10))
        ACCESS    read-only
        STATUS    mandatory
        DESCRIPTION
            "A DisplayString Object that contains the fifth port connected to
            the data module."
        ::= { g3datamstaEntry 8 }

    g3datamstaConnPort6	OBJECT-TYPE
        SYNTAX    DisplayString (SIZE (0..10))
        ACCESS    read-only
        STATUS    mandatory
        DESCRIPTION
            "A DisplayString Object that contains the sixth port connected to
            the data module."
        ::= { g3datamstaEntry 9 }

    g3datamstaConnPort7	OBJECT-TYPE
        SYNTAX    DisplayString (SIZE (0..10))
        ACCESS    read-only
        STATUS    mandatory
        DESCRIPTION
            "A DisplayString Object that contains the seventh port connected to
            the data module."
        ::= { g3datamstaEntry 10 }

    g3datamstaConnPort8	OBJECT-TYPE
        SYNTAX    DisplayString (SIZE (0..10))
        ACCESS    read-only
        STATUS    mandatory
        DESCRIPTION
            "A DisplayString Object that contains the eighth port connected to
            the data module."
        ::= { g3datamstaEntry 11 }

    g3datamstaConnPort9	OBJECT-TYPE
        SYNTAX    DisplayString (SIZE (0..10))
        ACCESS    read-only
        STATUS    mandatory
        DESCRIPTION
            "A DisplayString Object that contains the ninth port connected to
            the data module."
        ::= { g3datamstaEntry 12 }

    g3datamstaCFdestExt	OBJECT-TYPE
        SYNTAX    DisplayString (SIZE (0..17))
        ACCESS    read-only
        STATUS    mandatory
        DESCRIPTION
            "A DisplayString Object that contains the CF Destination Extension
            for the data module."
        ::= { g3datamstaEntry 13 }


    -- the g3timedate group

    g3timedateDayOfMonth	OBJECT-TYPE
        SYNTAX    INTEGER
        ACCESS    read-write
        STATUS    mandatory
        DESCRIPTION
            "An INTEGER object containing the current system time Day of the
            Month (1-31)."
        ::= { g3timedate 1 }

    g3timedateMonth	OBJECT-TYPE
        SYNTAX    DisplayString (SIZE (0..9))
        ACCESS    read-write
        STATUS    mandatory
        DESCRIPTION
            "A DisplayString Object that contains the name of the Month ('January',
            'February', 'March', 'April', 'May', 'June', 'July', 'August',
            'September', 'October', 'November', or 'December')."
        ::= { g3timedate 2 }

    g3timedateYear	OBJECT-TYPE
        SYNTAX    INTEGER
        ACCESS    read-write
        STATUS    mandatory
        DESCRIPTION
            "An INTEGER object containing the current system time Year (0000-9999)."
        ::= { g3timedate 3 }

    g3timedateDayOfWeek	OBJECT-TYPE
        SYNTAX    DisplayString (SIZE (0..9))
        ACCESS    read-write
        STATUS    mandatory
        DESCRIPTION
            "A DisplayString Object that contains the day of the week ('Monday',
            'Tuesday', 'Wednesday', 'Thursday', 'Friday', 'Saturday', or
            'Sunday')."
        ::= { g3timedate 4 }

    g3timedateHour	OBJECT-TYPE
        SYNTAX    INTEGER
        ACCESS    read-write
        STATUS    mandatory
        DESCRIPTION
            "An INTEGER object containing the current system time Hour (0-23)."
        ::= { g3timedate 5 }

    g3timedateMinute	OBJECT-TYPE
        SYNTAX    INTEGER
        ACCESS    read-write
        STATUS    mandatory
        DESCRIPTION
            "An INTEGER object containing the current system time Minute (0-59)."
        ::= { g3timedate 6 }

    g3timedateSecond	OBJECT-TYPE
        SYNTAX    INTEGER
        ACCESS    read-only
        STATUS    mandatory
        DESCRIPTION
            "An INTEGER object containing the current system time Second (0-59)."
        ::= { g3timedate 7 }

    g3timedateLastError1	OBJECT-TYPE
        SYNTAX    DisplayString (SIZE (0..100))
        ACCESS    read-only
        STATUS    mandatory
        DESCRIPTION
            "A DisplayString Object that contains the last error message
            encountered when attempting to set the system date/time."
        ::= { g3timedate 8 }

    g3timedateLastError2	OBJECT-TYPE
        SYNTAX    DisplayString (SIZE (0..100))
        ACCESS    read-only
        STATUS    mandatory
        DESCRIPTION
            "See DESCRIPTION of g3timedateLastError1."
        ::= { g3timedate 9 }

    g3timedateLastError3	OBJECT-TYPE
        SYNTAX    DisplayString (SIZE (0..100))
        ACCESS    read-only
        STATUS    mandatory
        DESCRIPTION
            "See DESCRIPTION of g3timedateLastError1."
        ::= { g3timedate 10 }

    g3timedateLastError4	OBJECT-TYPE
        SYNTAX    DisplayString (SIZE (0..100))
        ACCESS    read-only
        STATUS    mandatory
        DESCRIPTION
            "See DESCRIPTION of g3timedateLastError1."
        ::= { g3timedate 11 }

    g3timedateLastError5	OBJECT-TYPE
        SYNTAX    DisplayString (SIZE (0..100))
        ACCESS    read-only
        STATUS    mandatory
        DESCRIPTION
            "See DESCRIPTION of g3timedateLastError1."
        ::= { g3timedate 12 }

    g3timedateLastError6	OBJECT-TYPE
        SYNTAX    DisplayString (SIZE (0..100))
        ACCESS    read-only
        STATUS    mandatory
        DESCRIPTION
            "See DESCRIPTION of g3timedateLastError1."
        ::= { g3timedate 13 }


    -- the g3busytrk group

    g3busytrkTable	OBJECT-TYPE
        SYNTAX    SEQUENCE OF G3busytrkEntry
        ACCESS    not-accessible
        STATUS    mandatory
        DESCRIPTION
            "A list of g3busytrk entries."
        ::= { g3busytrk 1 }

    g3busytrkEntry	OBJECT-TYPE
        SYNTAX    G3busytrkEntry
        ACCESS    not-accessible
        STATUS    mandatory
        DESCRIPTION
            "A g3busytrk entry containing objects of the
            g3busytrk information sent by the switch."
        INDEX    { g3busytrkGroup, g3busytrkMember }
        ::= { g3busytrkTable 1 }

    G3busytrkEntry ::= SEQUENCE {
        g3busytrkAction
            DisplayString,
        g3busytrkObject
            DisplayString,
        g3busytrkGroup
            INTEGER,
        g3busytrkMember
            INTEGER,
        g3busytrkIndex
            INTEGER,
        g3busytrkPort
            DisplayString,
        g3busytrkMaintName
            DisplayString,
        g3busytrkAltName
            DisplayString,
        g3busytrkResult
            DisplayString,
        g3busytrkErrorCode
            DisplayString,
        g3busytrkLastError
            DisplayString,
        g3busytrkUDateStr
            DisplayString
        }

    g3busytrkAction	OBJECT-TYPE
        SYNTAX    DisplayString (SIZE (0..7))
        ACCESS    read-only
        STATUS    mandatory
        DESCRIPTION
            "A DisplayString Object that contains the last action performed on
            the trunk group and trunk member ('busyout' or 'release')."
        ::= { g3busytrkEntry 1 }

    g3busytrkObject	OBJECT-TYPE
        SYNTAX    DisplayString (SIZE (0..5))
        ACCESS    read-only
        STATUS    mandatory
        DESCRIPTION
            "A DisplayString Object that contains the switch object 'trunk'."
        ::= { g3busytrkEntry 2 }

    g3busytrkGroup	OBJECT-TYPE
        SYNTAX    INTEGER
        ACCESS    read-only
        STATUS    mandatory
        DESCRIPTION
            "An INTEGER Object that uniquely identifies an administered
            trunk group on which a 'busyout' or 'release' operation was last
            performed."
        ::= { g3busytrkEntry 3 }

    g3busytrkMember	OBJECT-TYPE
        SYNTAX    INTEGER
        ACCESS    read-only
        STATUS    mandatory
        DESCRIPTION
            "An INTEGER Object that uniquely identifies an administered trunk 
            member on which a 'busyout' or 'release' operation was last
            performed."
        ::= { g3busytrkEntry 4 }

    g3busytrkIndex	OBJECT-TYPE
        SYNTAX    INTEGER
        ACCESS    read-only
        STATUS    mandatory
        DESCRIPTION
            "An INTEGER Object that identifies an index number for the trunk
            group and member number record (currently always set to '1')."
        ::= { g3busytrkEntry 5 }

    g3busytrkPort	OBJECT-TYPE
        SYNTAX    DisplayString (SIZE (0..9))
        ACCESS    read-only
        STATUS    mandatory
        DESCRIPTION
            "A DisplayString Object that uniquely identifies a port based on
            its location in the system. The syntax for the Port Number is as
            follows: cabinet(01-44):carrier(A-E):slot(01-20):port(01-32)."
        ::= { g3busytrkEntry 6 }

    g3busytrkMaintName	OBJECT-TYPE
        SYNTAX    DisplayString (SIZE (0..8))
        ACCESS    read-only
        STATUS    mandatory
        DESCRIPTION
            "A DisplayString Object containing the maintenance object name."
        ::= { g3busytrkEntry 7 }

    g3busytrkAltName	OBJECT-TYPE
        SYNTAX    DisplayString (SIZE (0..7))
        ACCESS    read-only
        STATUS    mandatory
        DESCRIPTION
            "A DisplayString Object containing the alternate name of the object."
        ::= { g3busytrkEntry 8 }

    g3busytrkResult	OBJECT-TYPE
        SYNTAX    DisplayString (SIZE (0..15))
        ACCESS    read-only
        STATUS    mandatory
        DESCRIPTION
            "A DisplayString Object containing the result of the last 
            busyout/release operation."
        ::= { g3busytrkEntry 9 }

    g3busytrkErrorCode	OBJECT-TYPE
        SYNTAX    DisplayString (SIZE (0..6))
        ACCESS    read-only
        STATUS    mandatory
        DESCRIPTION
            "A DisplayString Object containing the error code associated with
            the result of the last busyout/release operation."
        ::= { g3busytrkEntry 10 }

    g3busytrkLastError	OBJECT-TYPE
        SYNTAX    DisplayString (SIZE (0..100))
        ACCESS    read-only
        STATUS    mandatory
        DESCRIPTION
            "A DisplayString Object that contains the error message 
            encountered on the last busyout/release operation. The string is
            blank if no command error was encountered on the last attempt."
        ::= { g3busytrkEntry 11 }

    g3busytrkUDateStr	OBJECT-TYPE
        SYNTAX    DisplayString (SIZE (0..12))
        ACCESS    read-only
        STATUS    mandatory
        DESCRIPTION
            "A DisplayString Object that contains the UNIX time stamp
            when the result of the busyout/release operation was received."
        ::= { g3busytrkEntry 12 }


    -- the g3busybrd group

    g3busybrdTable	OBJECT-TYPE
        SYNTAX    SEQUENCE OF G3busybrdEntry
        ACCESS    not-accessible
        STATUS    mandatory
        DESCRIPTION
            "A list of g3busybrd entries."
        ::= { g3busybrd 1 }

    g3busybrdEntry	OBJECT-TYPE
        SYNTAX    G3busybrdEntry
        ACCESS    not-accessible
        STATUS    mandatory
        DESCRIPTION
            "A g3busybrd entry containing objects of the
            g3busybrd information sent by the switch."
        INDEX    { g3busybrdBoardVal, g3busybrdPortVal }
        ::= { g3busybrdTable 1 }

    G3busybrdEntry ::= SEQUENCE {
        g3busybrdAction
            DisplayString,
        g3busybrdObject
            DisplayString,
        g3busybrdBoardVal
            DisplayString,
        g3busybrdPortVal
            INTEGER,
        g3busybrdIndex
            INTEGER,
        g3busybrdPort
            DisplayString,
        g3busybrdMaintName
            DisplayString,
        g3busybrdAltName
            DisplayString,
        g3busybrdResult
            DisplayString,
        g3busybrdErrorCode
            DisplayString,
        g3busybrdLastError
            DisplayString,
        g3busybrdUDateStr
            DisplayString
        }

    g3busybrdAction	OBJECT-TYPE
        SYNTAX    DisplayString (SIZE (0..7))
        ACCESS    read-only
        STATUS    mandatory
        DESCRIPTION
            "A DisplayString Object that contains the last action performed on
            the board or port on a board ('busyout' or 'release')."
        ::= { g3busybrdEntry 1 }

    g3busybrdObject	OBJECT-TYPE
        SYNTAX    DisplayString (SIZE (0..5))
        ACCESS    read-only
        STATUS    mandatory
        DESCRIPTION
            "A DisplayString Object that contains the switch object 'board'."
        ::= { g3busybrdEntry 2 }

    g3busybrdBoardVal	OBJECT-TYPE
        SYNTAX    DisplayString (SIZE (0..7))
        ACCESS    read-only
        STATUS    mandatory
        DESCRIPTION
            "A DisplayString Object that uniquely identifies a board based on
            its location in the system which a 'busyout' or 'release' operation
            was last performed. The syntax for the Board Number is as
            follows: cabinet(01-44):carrier(A-E):slot(01-20)."
        ::= { g3busybrdEntry 3 }

    g3busybrdPortVal	OBJECT-TYPE
        SYNTAX    INTEGER
        ACCESS    read-only
        STATUS    mandatory
        DESCRIPTION
            "An INTEGER Object that uniquely identifies an administered port 
            location on which a 'busyout' or 'release' operation was last
            performed."
        ::= { g3busybrdEntry 4 }

    g3busybrdIndex	OBJECT-TYPE
        SYNTAX    INTEGER
        ACCESS    read-only
        STATUS    mandatory
        DESCRIPTION
            "An INTEGER Object that identifies an index number for the board
            /port number record (currently always set to '1')."
        ::= { g3busybrdEntry 5 }

    g3busybrdPort	OBJECT-TYPE
        SYNTAX    DisplayString (SIZE (0..9))
        ACCESS    read-only
        STATUS    mandatory
        DESCRIPTION
            "A DisplayString Object that uniquely identifies a port based on
            its location in the system. The syntax for the Port Number is as
            follows: cabinet(01-44):carrier(A-E):slot(01-20):port(01-32)."
        ::= { g3busybrdEntry 6 }

    g3busybrdMaintName	OBJECT-TYPE
        SYNTAX    DisplayString (SIZE (0..8))
        ACCESS    read-only
        STATUS    mandatory
        DESCRIPTION
            "A DisplayString Object containing the maintenance object name."
        ::= { g3busybrdEntry 7 }

    g3busybrdAltName	OBJECT-TYPE
        SYNTAX    DisplayString (SIZE (0..7))
        ACCESS    read-only
        STATUS    mandatory
        DESCRIPTION
            "A DisplayString Object containing the alternate name of the object."
        ::= { g3busybrdEntry 8 }

    g3busybrdResult	OBJECT-TYPE
        SYNTAX    DisplayString (SIZE (0..15))
        ACCESS    read-only
        STATUS    mandatory
        DESCRIPTION
            "A DisplayString Object containing the result of the last 
            busyout/release operation."
        ::= { g3busybrdEntry 9 }

    g3busybrdErrorCode	OBJECT-TYPE
        SYNTAX    DisplayString (SIZE (0..6))
        ACCESS    read-only
        STATUS    mandatory
        DESCRIPTION
            "A DisplayString Object containing the error code associated with
            the result of the last busyout/release operation."
        ::= { g3busybrdEntry 10 }

    g3busybrdLastError	OBJECT-TYPE
        SYNTAX    DisplayString (SIZE (0..100))
        ACCESS    read-only
        STATUS    mandatory
        DESCRIPTION
            "A DisplayString Object that contains the error message 
            encountered on the last busyout/release operation. The string is
            blank if no command error was encountered on the last attempt."
        ::= { g3busybrdEntry 11 }

    g3busybrdUDateStr	OBJECT-TYPE
        SYNTAX    DisplayString (SIZE (0..12))
        ACCESS    read-only
        STATUS    mandatory
        DESCRIPTION
            "A DisplayString Object that contains the UNIX time stamp
            when the result of the busyout/release operation was received."
        ::= { g3busybrdEntry 12 }


    -- the g3servalm group

    g3servalmTable	OBJECT-TYPE
        SYNTAX    SEQUENCE OF G3servalmEntry
        ACCESS    not-accessible
        STATUS    mandatory
        DESCRIPTION
            "A list of g3servalm entries."
        ::= { g3servalm 1 }

    g3servalmEntry	OBJECT-TYPE
        SYNTAX    G3servalmEntry
        ACCESS    not-accessible
        STATUS    mandatory
        DESCRIPTION
            "A g3servalm entry containing objects of the
            g3servalm information sent by the switch."
        INDEX    { g3servalmID }
        ::= { g3servalmTable 1 }

    G3servalmEntry ::= SEQUENCE {
        g3servalmID
            INTEGER,
        g3servalmSource
            DisplayString,
        g3servalmEventID
            DisplayString,
        g3servalmLevel
            DisplayString,
        g3servalmAck
            DisplayString,
        g3servalmDate
            DisplayString,
        g3servalmDescription
            DisplayString
        }

    g3servalmID	OBJECT-TYPE
        SYNTAX    INTEGER
        ACCESS    read-only
        STATUS    mandatory
        DESCRIPTION
            "A DisplayString Object that uniquely identifies the server alarm."
        ::= { g3servalmEntry 1 }

    g3servalmSource	OBJECT-TYPE
        SYNTAX    DisplayString (SIZE (0..7))
        ACCESS    read-only
        STATUS    mandatory
        DESCRIPTION
            "A DisplayString Object containing the source of the alarm."
        ::= { g3servalmEntry 2 }

    g3servalmEventID	OBJECT-TYPE
        SYNTAX    DisplayString (SIZE (0..6))
        ACCESS    read-only
        STATUS    mandatory
        DESCRIPTION
            "A DisplayString Object containing the event id of the alarm."
        ::= { g3servalmEntry 3 }

    g3servalmLevel	OBJECT-TYPE
        SYNTAX    DisplayString (SIZE (0..4))
        ACCESS    read-only
        STATUS    mandatory
        DESCRIPTION
            "A DisplayString Object containing the level of the alarm."
        ::= { g3servalmEntry 4 }

    g3servalmAck	OBJECT-TYPE
        SYNTAX    DisplayString (SIZE (0..4))
        ACCESS    read-only
        STATUS    mandatory
        DESCRIPTION
            "A DisplayString Object containing the alarm acknowledged flag."
        ::= { g3servalmEntry 5 }

    g3servalmDate	OBJECT-TYPE
        SYNTAX    DisplayString (SIZE (0..25))
        ACCESS    read-only
        STATUS    mandatory
        DESCRIPTION
            "A DisplayString Object containing the date the alarm was generated."
        ::= { g3servalmEntry 6 }

    g3servalmDescription	OBJECT-TYPE
        SYNTAX    DisplayString (SIZE (0..120))
        ACCESS    read-only
        STATUS    mandatory
        DESCRIPTION
            "A DisplayString Object containing a description of the alarm."
        ::= { g3servalmEntry 7 }


    -- the g3msgalm group

    g3msgalmTable	OBJECT-TYPE
        SYNTAX    SEQUENCE OF G3msgalmEntry
        ACCESS    not-accessible
        STATUS    mandatory
        DESCRIPTION
            "A list of g3msgalm entries."
        ::= { g3msgalm 1 }

    g3msgalmEntry	OBJECT-TYPE
        SYNTAX    G3msgalmEntry
        ACCESS    not-accessible
        STATUS    mandatory
        DESCRIPTION
            "A g3msgalm entry containing objects of the
            g3msgalm information sent by the switch."
        INDEX    { g3msgalmID }
        ::= { g3msgalmTable 1 }

    G3msgalmEntry ::= SEQUENCE {
        g3msgalmID
            INTEGER,
        g3msgalmAPP
            DisplayString,
        g3msgalmSource
            DisplayString,
        g3msgalmEventID
            DisplayString,
        g3msgalmLevel
            DisplayString,
        g3msgalmAck
            DisplayString,
        g3msgalmLocation
            DisplayString,
        g3msgalmDate
            DisplayString,
        g3msgalmDescription
            DisplayString
        }

    g3msgalmID	OBJECT-TYPE
        SYNTAX    INTEGER
        ACCESS    read-only
        STATUS    mandatory
        DESCRIPTION
            "A DisplayString Object that uniquely identifies the messaging alarm."
        ::= { g3msgalmEntry 1 }

    g3msgalmAPP	OBJECT-TYPE
        SYNTAX    DisplayString (SIZE (0..4))
        ACCESS    read-only
        STATUS    mandatory
        DESCRIPTION
            "A DisplayString Object containing the alarm APP."
        ::= { g3msgalmEntry 2 }

    g3msgalmSource	OBJECT-TYPE
        SYNTAX    DisplayString (SIZE (0..8))
        ACCESS    read-only
        STATUS    mandatory
        DESCRIPTION
            "A DisplayString Object containing the source of the alarm."
        ::= { g3msgalmEntry 3 }

    g3msgalmEventID	OBJECT-TYPE
        SYNTAX    DisplayString (SIZE (0..6))
        ACCESS    read-only
        STATUS    mandatory
        DESCRIPTION
            "A DisplayString Object containing the event id of the alarm."
        ::= { g3msgalmEntry 4 }

    g3msgalmLevel	OBJECT-TYPE
        SYNTAX    DisplayString (SIZE (0..4))
        ACCESS    read-only
        STATUS    mandatory
        DESCRIPTION
            "A DisplayString Object containing the level of the alarm."
        ::= { g3msgalmEntry 5 }

    g3msgalmAck	OBJECT-TYPE
        SYNTAX    DisplayString (SIZE (0..4))
        ACCESS    read-only
        STATUS    mandatory
        DESCRIPTION
            "A DisplayString Object containing the alarm acknowledged flag."
        ::= { g3msgalmEntry 6 }

    g3msgalmLocation	OBJECT-TYPE
        SYNTAX    DisplayString (SIZE (0..10))
        ACCESS    read-only
        STATUS    mandatory
        DESCRIPTION
            "A DisplayString Object containing the location of the alarm."
        ::= { g3msgalmEntry 7 }

    g3msgalmDate	OBJECT-TYPE
        SYNTAX    DisplayString (SIZE (0..25))
        ACCESS    read-only
        STATUS    mandatory
        DESCRIPTION
            "A DisplayString Object containing the date the alarm was generated."
        ::= { g3msgalmEntry 8 }

    g3msgalmDescription	OBJECT-TYPE
        SYNTAX    DisplayString (SIZE (0..120))
        ACCESS    read-only
        STATUS    mandatory
        DESCRIPTION
            "A DisplayString Object containing a description of the alarm."
        ::= { g3msgalmEntry 9 }


    -- the g3ipevt group

    g3ipevtTable	OBJECT-TYPE
        SYNTAX    SEQUENCE OF G3ipevtEntry
        ACCESS    not-accessible
        STATUS    mandatory
        DESCRIPTION
            "A list of g3ipevt entries."
        ::= { g3ipevt 1 }

    g3ipevtEntry	OBJECT-TYPE
        SYNTAX    G3ipevtEntry
        ACCESS    not-accessible
        STATUS    mandatory
        DESCRIPTION
            "A g3ipevt entry containing objects of the
            g3ipevt information sent by the switch."
        INDEX    { g3ipevtIndex }
        ::= { g3ipevtTable 1 }

    G3ipevtEntry ::= SEQUENCE {
        g3ipevtIndex
            INTEGER,
        g3ipevtIPEvent
            DisplayString
        }

    g3ipevtIndex	OBJECT-TYPE
        SYNTAX    INTEGER
        ACCESS    read-only
        STATUS    mandatory
        DESCRIPTION
            "An INTEGER object containing a unique index for each event in the
            IP event log for the current day."
        ::= { g3ipevtEntry 1 }

    g3ipevtIPEvent	OBJECT-TYPE
        SYNTAX    DisplayString (SIZE (0..200))
        ACCESS    read-only
        STATUS    mandatory
        DESCRIPTION
            "A DisplayString Object that defines an event in the IP event
            log for the current day."
        ::= { g3ipevtEntry 2 }


    -- the g3platcmds group

    g3platcmdsTable	OBJECT-TYPE
        SYNTAX    SEQUENCE OF G3platcmdsEntry
        ACCESS    not-accessible
        STATUS    mandatory
        DESCRIPTION
            "A list of g3platcmds entries."
        ::= { g3platcmds 1 }

    g3platcmdsEntry	OBJECT-TYPE
        SYNTAX    G3platcmdsEntry
        ACCESS    not-accessible
        STATUS    mandatory
        DESCRIPTION
            "A g3platcmds entry containing objects of the
            g3platcmds information sent by the switch."
        INDEX    { g3platcmdsSeqNumber }
        ::= { g3platcmdsTable 1 }

    G3platcmdsEntry ::= SEQUENCE {
        g3platcmdsDate
            DisplayString,
        g3platcmdsTime
            DisplayString,
        g3platcmdsSeqNumber
            INTEGER,
        g3platcmdsPriority
            DisplayString,
        g3platcmdsServerName
            DisplayString,
        g3platcmdsLoginId
            DisplayString,
        g3platcmdsCommand
            DisplayString
        }

    g3platcmdsDate	OBJECT-TYPE
        SYNTAX    DisplayString (SIZE (0..8))
        ACCESS    read-only
        STATUS    mandatory
        DESCRIPTION
            "An object containing the date the command was issued."
        ::= { g3platcmdsEntry 1 }

    g3platcmdsTime	OBJECT-TYPE
        SYNTAX    DisplayString (SIZE (0..9))
        ACCESS    read-only
        STATUS    mandatory
        DESCRIPTION
            "An object containing the time that the command was issued."
        ::= { g3platcmdsEntry 2 }

    g3platcmdsSeqNumber	OBJECT-TYPE
        SYNTAX    INTEGER
        ACCESS    read-only
        STATUS    mandatory
        DESCRIPTION
            "An object containing the system-generated sequence number."
        ::= { g3platcmdsEntry 3 }

    g3platcmdsPriority	OBJECT-TYPE
        SYNTAX    DisplayString (SIZE (0..25))
        ACCESS    read-only
        STATUS    mandatory
        DESCRIPTION
            "An object containing the session priority."
        ::= { g3platcmdsEntry 4 }

    g3platcmdsServerName	OBJECT-TYPE
        SYNTAX    DisplayString (SIZE (0..25))
        ACCESS    read-only
        STATUS    mandatory
        DESCRIPTION
            "An object containing the server name on which the command was
            issued."
        ::= { g3platcmdsEntry 5 }

    g3platcmdsLoginId	OBJECT-TYPE
        SYNTAX    DisplayString (SIZE (0..25))
        ACCESS    read-only
        STATUS    mandatory
        DESCRIPTION
            "An object containing the login id of the user issuing the command."
        ::= { g3platcmdsEntry 6 }

    g3platcmdsCommand	OBJECT-TYPE
        SYNTAX    DisplayString (SIZE (0..200))
        ACCESS    read-only
        STATUS    mandatory
        DESCRIPTION
            "An object containing the command issued by the user."
        ::= { g3platcmdsEntry 7 }


    -- the g3version group

    g3versionOperSystem	OBJECT-TYPE
        SYNTAX    DisplayString (SIZE (0..50))
        ACCESS    read-only
        STATUS    mandatory
        DESCRIPTION
            "An object containing the operating system running on the server."
        ::= { g3version 1 }

    g3versionBuildDate	OBJECT-TYPE
        SYNTAX    DisplayString (SIZE (0..25))
        ACCESS    read-only
        STATUS    mandatory
        DESCRIPTION
            "An object containing operation system build date."
        ::= { g3version 2 }

    g3versionLoadNumber	OBJECT-TYPE
        SYNTAX    DisplayString (SIZE (0..15))
        ACCESS    read-only
        STATUS    mandatory
        DESCRIPTION
            "An object containing the current CM load number running on the
            server (e.g. 01.0.628.5)."
        ::= { g3version 3 }

    g3versionRlsNumber	OBJECT-TYPE
        SYNTAX    DisplayString (SIZE (0..25))
        ACCESS    read-only
        STATUS    mandatory
        DESCRIPTION
            "An object containing the current CM release number (e.g. 
            R013x.01.0.628.5)."
        ::= { g3version 4 }

    g3versionRlsString	OBJECT-TYPE
        SYNTAX    DisplayString (SIZE (0..25))
        ACCESS    read-only
        STATUS    mandatory
        DESCRIPTION
            "An object containing the CM release string (e.g.  S8720-013-01.0.628.5)."
        ::= { g3version 5 }

    g3versionTransSaved	OBJECT-TYPE
        SYNTAX    DisplayString (SIZE (0..20))
        ACCESS    read-only
        STATUS    mandatory
        DESCRIPTION
            "An object containing the date and time that translation was last
            saved on the CM server."
        ::= { g3version 6 }

    g3versionLicInstalled	OBJECT-TYPE
        SYNTAX    DisplayString (SIZE (0..20))
        ACCESS    read-only
        STATUS    mandatory
        DESCRIPTION
            "An object containing the date and time that the license was installed 
            on the CM server."
        ::= { g3version 7 }


    -- the g3update group

    g3updateTable	OBJECT-TYPE
        SYNTAX    SEQUENCE OF G3updateEntry
        ACCESS    not-accessible
        STATUS    mandatory
        DESCRIPTION
            "A list of g3update entries."
        ::= { g3update 1 }

    g3updateEntry	OBJECT-TYPE
        SYNTAX    G3updateEntry
        ACCESS    not-accessible
        STATUS    mandatory
        DESCRIPTION
            "A g3update entry containing objects of the
            g3update information sent by the switch."
        INDEX    { g3updateID }
        ::= { g3updateTable 1 }

    G3updateEntry ::= SEQUENCE {
        g3updateID
            DisplayString,
        g3updateStatus
            DisplayString,
        g3updateType
            DisplayString,
        g3updateDescription
            DisplayString
        }

    g3updateID	OBJECT-TYPE
        SYNTAX    DisplayString (SIZE (0..25))
        ACCESS    read-only
        STATUS    mandatory
        DESCRIPTION
            "An object containing the identifier for the installed update (e.g.
            01.0.628.5-7777)."
        ::= { g3updateEntry 1 }

    g3updateStatus	OBJECT-TYPE
        SYNTAX    DisplayString (SIZE (0..15))
        ACCESS    read-only
        STATUS    mandatory
        DESCRIPTION
            "An object containing current status of the update (e.g. unpacked)."
        ::= { g3updateEntry 2 }

    g3updateType	OBJECT-TYPE
        SYNTAX    DisplayString (SIZE (0..10))
        ACCESS    read-only
        STATUS    mandatory
        DESCRIPTION
            "An object containing the update type (e.g. cold)."
        ::= { g3updateEntry 3 }

    g3updateDescription	OBJECT-TYPE
        SYNTAX    DisplayString (SIZE (0..80))
        ACCESS    read-only
        STATUS    mandatory
        DESCRIPTION
            "An object containing a description about the update."
        ::= { g3updateEntry 4 }


    -- the g3partition group

    g3partitionTable	OBJECT-TYPE
        SYNTAX    SEQUENCE OF G3partitionEntry
        ACCESS    not-accessible
        STATUS    mandatory
        DESCRIPTION
            "A list of g3partition entries."
        ::= { g3partition 1 }

    g3partitionEntry	OBJECT-TYPE
        SYNTAX    G3partitionEntry
        ACCESS    not-accessible
        STATUS    mandatory
        DESCRIPTION
            "A g3partition entry containing objects of the
            g3partition information sent by the switch."
        INDEX    { g3partitionPhysPartition }
        ::= { g3partitionTable 1 }

    G3partitionEntry ::= SEQUENCE {
        g3partitionPhysPartition
            DisplayString,
        g3partitionSoftwareRls
            DisplayString,
        g3partitionBootPartition
            DisplayString,
        g3partitionActivePartition
            DisplayString
        }

    g3partitionPhysPartition	OBJECT-TYPE
        SYNTAX    DisplayString (SIZE (0..10))
        ACCESS    read-only
        STATUS    mandatory
        DESCRIPTION
            "An object containing the physical partition name (e.g. hda1)."
        ::= { g3partitionEntry 1 }

    g3partitionSoftwareRls	OBJECT-TYPE
        SYNTAX    DisplayString (SIZE (0..25))
        ACCESS    read-only
        STATUS    mandatory
        DESCRIPTION
            "An object containing CM software release on the partition (e.g.
            01.2.632.1)."
        ::= { g3partitionEntry 2 }

    g3partitionBootPartition	OBJECT-TYPE
        SYNTAX    DisplayString (SIZE (0..5))
        ACCESS    read-only
        STATUS    mandatory
        DESCRIPTION
            "An object indicating whether the partition is the boot partition
            or not (yes or no)."
        ::= { g3partitionEntry 3 }

    g3partitionActivePartition	OBJECT-TYPE
        SYNTAX    DisplayString (SIZE (0..5))
        ACCESS    read-only
        STATUS    mandatory
        DESCRIPTION
            "An object indicating whether the partition is the active partition
            or not (yes or no)."
        ::= { g3partitionEntry 4 }


    -- the g3ds1cfg group

    g3ds1cfgTage	OBJECT-TYPE
        SYNTAX    INTEGER
        ACCESS    read-only
        STATUS    mandatory
        DESCRIPTION
            "The number of timeticks since the ds1 configuration data was last
            extracted from the switch by the G3 Proxy Agent. This object
            along with the g3ds1cfgTintvl object allows the Network Manager
            to determine the validity of the ds1 configuration data in the
            cache and to control when the proxy agent extracts the
            ds1 configuration data from the switch."
        ::= { g3ds1cfg 1 }

    g3ds1cfgTintvl	OBJECT-TYPE
        SYNTAX    INTEGER
        ACCESS    read-write
        STATUS    mandatory
        DESCRIPTION
            "An object containing the interval for which the ds1 configuration
            data extracted from the switch is considered valid by the proxy
            agent. When a GET or GET-NEXT request for ds1 configuration objects
            is received by the agent it uses the g3ds1cfgTage and g3ds1cfgTintvl
            objects to determine whether it should refresh the cached
            ds1cfgTable.  If g3ds1cfgTstmp + g3ds1cfgTintvl is less than the
            current value of the sysUpTime object then the agent refreshes
            the ds1cfgTable cache.  In either case it responds to the requests
            it receives with the data it currently has in the cache."
        ::= { g3ds1cfg 2 }

    g3ds1cfgTdelay	OBJECT-TYPE
        SYNTAX    INTEGER
        ACCESS    read-only
        STATUS    mandatory
        DESCRIPTION
            "An object containing the delay encountered in updating
            the cached data"
        ::= { g3ds1cfg 3 }

    g3ds1cfgTretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3ds1cfg 4 }

    g3ds1cfgTcount	OBJECT-TYPE
        SYNTAX    Gauge
        ACCESS    read-only
        STATUS    mandatory
        DESCRIPTION
            "A Gauge object containing the number of data records in the
            cache."
        ::= { g3ds1cfg 5 }

    g3ds1cfgTable	OBJECT-TYPE
        SYNTAX    SEQUENCE OF G3ds1cfgEntry
        ACCESS    not-accessible
        STATUS    mandatory
        DESCRIPTION
            "A list of g3ds1cfg entries."
        ::= { g3ds1cfg 6 }

    g3ds1cfgEntry	OBJECT-TYPE
        SYNTAX    G3ds1cfgEntry
        ACCESS    not-accessible
        STATUS    mandatory
        DESCRIPTION
            "A g3ds1cfg entry containing objects of the
            g3ds1cfg information sent by the switch."
        INDEX    { g3ds1cfgBoardNum }
        ::= { g3ds1cfgTable 1 }

    G3ds1cfgEntry ::= SEQUENCE {
        g3ds1cfgBoardNum
            DisplayString,
        g3ds1cfgCode
            DisplayString,
        g3ds1cfgSuffix
            DisplayString,
        g3ds1cfgVintage
            DisplayString,
        g3ds1cfgSignaling
            DisplayString,
        g3ds1cfgName
            DisplayString,
        g3ds1cfgCsuMod
            DisplayString
        }

    g3ds1cfgBoardNum	OBJECT-TYPE
        SYNTAX    DisplayString (SIZE (0..7))
        ACCESS    read-only
        STATUS    mandatory
        DESCRIPTION
            "A DisplayString Object that uniquely identifies a board based on
            its location in the system. The syntax for the Board Number is as
            follows: cabinet(01-44):carrier(A-E):slot(01-20)."
        ::= { g3ds1cfgEntry 1 }

    g3ds1cfgCode	OBJECT-TYPE
        SYNTAX    DisplayString (SIZE (0..8))
        ACCESS    read-only
        STATUS    mandatory
        DESCRIPTION
            "A DisplayString Object that contains the code that defines the
            type of board."
        ::= { g3ds1cfgEntry 2 }

    g3ds1cfgSuffix	OBJECT-TYPE
        SYNTAX    DisplayString (SIZE (0..2))
        ACCESS    read-only
        STATUS    mandatory
        DESCRIPTION
            "A DisplayString Object that contains the suffix to the code"
        ::= { g3ds1cfgEntry 3 }

    g3ds1cfgVintage	OBJECT-TYPE
        SYNTAX    DisplayString (SIZE (0..10))
        ACCESS    read-only
        STATUS    mandatory
        DESCRIPTION
            "A DisplayString Object that contains the vintage of the board.
            (object ds1cfgCode) that defines the type of board."
        ::= { g3ds1cfgEntry 4 }

    g3ds1cfgSignaling	OBJECT-TYPE
        SYNTAX    DisplayString (SIZE (0..11))
        ACCESS    read-only
        STATUS    mandatory
        DESCRIPTION
            "A DisplayString Object that contains the signaling of the board."
        ::= { g3ds1cfgEntry 5 }

    g3ds1cfgName	OBJECT-TYPE
        SYNTAX    DisplayString (SIZE (0..16))
        ACCESS    read-only
        STATUS    mandatory
        DESCRIPTION
            "A DisplayString Object that contains the name of the board."
        ::= { g3ds1cfgEntry 6 }

    g3ds1cfgCsuMod	OBJECT-TYPE
        SYNTAX    DisplayString (SIZE (0..7))
        ACCESS    read-only
        STATUS    mandatory
        DESCRIPTION
            "A DisplayString Object that contains the type of CSU Mod."
        ::= { g3ds1cfgEntry 7 }


    -- the g3extdev group

    g3extdevTage	OBJECT-TYPE
        SYNTAX    INTEGER
        ACCESS    read-only
        STATUS    mandatory
        DESCRIPTION
            "The number of timeticks since the external device data was last
            extracted from the switch by the G3 Proxy Agent. This object
            along with the g3extdevintvl object allows the Network Manager
            to determine the validity of the external device data in the
            cache and to control when the proxy agent extracts the
            external device data from the switch."
        ::= { g3extdev 1 }

    g3extdevTintvl	OBJECT-TYPE
        SYNTAX    INTEGER
        ACCESS    read-write
        STATUS    mandatory
        DESCRIPTION
            "An object containing the interval for which the external device data
            extracted from the switch is considered valid by the proxy agent.
            When a GET or GET-NEXT request for external device objects is
            received by the agent it uses the g3extdevage and g3extdevintvl
            objects to determine whether it should refresh the cached
            extdevTable.  If g3extdevstmp + g3extdevintvl is less than the
            current value of the sysUpTime object then the agent refreshes
            the extdevTable cache.  In either case it responds to the requests
            it receives with the data it currently has in the cache."
        ::= { g3extdev 2 }

    g3extdevTdelay	OBJECT-TYPE
        SYNTAX    INTEGER
        ACCESS    read-only
        STATUS    mandatory
        DESCRIPTION
            "An object containing the delay encountered in updating
            the cached data"
        ::= { g3extdev 3 }

    g3extdevTretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3extdev 4 }

    g3extdevTcount	OBJECT-TYPE
        SYNTAX    Gauge
        ACCESS    read-only
        STATUS    mandatory
        DESCRIPTION
            "A Gauge object containing the number of data records in the
            cache."
        ::= { g3extdev 5 }

    g3extdevTable	OBJECT-TYPE
        SYNTAX    SEQUENCE OF G3extdevEntry
        ACCESS    not-accessible
        STATUS    mandatory
        DESCRIPTION
            "A list of g3extdev entries."
        ::= { g3extdev 6 }

    g3extdevEntry	OBJECT-TYPE
        SYNTAX    G3extdevEntry
        ACCESS    not-accessible
        STATUS    mandatory
        DESCRIPTION
            "A g3extdev entry containing objects of the
            g3extdev information sent by the switch."
        INDEX    { g3extdevPort }
        ::= { g3extdevTable 1 }

    G3extdevEntry ::= SEQUENCE {
        g3extdevPort
            DisplayString,
        g3extdevType
            DisplayString,
        g3extdevAltName
            DisplayString,
        g3extdevDescription
            DisplayString,
        g3extdevID
            DisplayString,
        g3extdevBuilding
            DisplayString,
        g3extdevAddress
            DisplayString
        }

    g3extdevPort	OBJECT-TYPE
        SYNTAX    DisplayString (SIZE (0..9))
        ACCESS    read-only
        STATUS    mandatory
        DESCRIPTION
            "A DisplayString Object that uniquely identifies a port based on
            its location in the system. The syntax for the Port Number is as
            follows: cabinet(01-44):carrier(A-E):slot(01-20):port(01-32)."
        ::= { g3extdevEntry 1 }

    g3extdevType	OBJECT-TYPE
        SYNTAX    DisplayString (SIZE (0..7))
        ACCESS    read-only
        STATUS    mandatory
        DESCRIPTION
            "A DisplayString Object that defines the type of the device."
        ::= { g3extdevEntry 2 }

    g3extdevAltName	OBJECT-TYPE
        SYNTAX    DisplayString (SIZE (0..7))
        ACCESS    read-only
        STATUS    mandatory
        DESCRIPTION
            "A DisplayString Object that contains the alternate name for the
            device."
        ::= { g3extdevEntry 3 }

    g3extdevDescription	OBJECT-TYPE
        SYNTAX    DisplayString (SIZE (0..43))
        ACCESS    read-only
        STATUS    mandatory
        DESCRIPTION
            "A DisplayString Object that describes the external device."
        ::= { g3extdevEntry 4 }

    g3extdevID	OBJECT-TYPE
        SYNTAX    DisplayString (SIZE (0..10))
        ACCESS    read-only
        STATUS    mandatory
        DESCRIPTION
            "A DisplayString Object that contains the product identifier of
            the external device."
        ::= { g3extdevEntry 5 }

    g3extdevBuilding	OBJECT-TYPE
        SYNTAX    DisplayString (SIZE (0..40))
        ACCESS    read-only
        STATUS    mandatory
        DESCRIPTION
            "A DisplayString Object that contains the building location of the
            external device."
        ::= { g3extdevEntry 6 }

    g3extdevAddress	OBJECT-TYPE
        SYNTAX    DisplayString (SIZE (0..40))
        ACCESS    read-only
        STATUS    mandatory
        DESCRIPTION
            "A DisplayString Object that contains the address of the external
            device."
        ::= { g3extdevEntry 7 }


    -- the g3trunkgrp group

    g3trunkgrpTage	OBJECT-TYPE
        SYNTAX    INTEGER
        ACCESS    read-only
        STATUS    mandatory
        DESCRIPTION
            "The number of timeticks since the trunk group data was last
            extracted from the switch by the G3 Proxy Agent. This object
            along with the g3trunkgrpintvl object allows the Network Manager
            to determine the validity of the trunk group data in the
            cache and to control when the proxy agent extracts the
            trunk group data from the switch."
        ::= { g3trunkgrp 1 }

    g3trunkgrpTintvl	OBJECT-TYPE
        SYNTAX    INTEGER
        ACCESS    read-write
        STATUS    mandatory
        DESCRIPTION
            "An object containing the interval for which the trunk group data
            extracted from the switch is considered valid by the proxy agent.
            When a GET or GET-NEXT request for trunk group objects is
            received by the agent it uses the g3trunkgrpage and g3trunkgrpintvl
            objects to determine whether it should refresh the cached
            trunkgrpTable.  If g3trunkgrpstmp + g3trunkgrpintvl is less than the
            current value of the sysUpTime object then the agent refreshes
            the trunkgrpTable cache.  In either case it responds to the requests
            it receives with the data it currently has in the cache."
        ::= { g3trunkgrp 2 }

    g3trunkgrpTdelay	OBJECT-TYPE
        SYNTAX    INTEGER
        ACCESS    read-only
        STATUS    mandatory
        DESCRIPTION
            "An object containing the delay encountered in updating
            the cached data"
        ::= { g3trunkgrp 3 }

    g3trunkgrpTretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3trunkgrp 4 }

    g3trunkgrpTcount	OBJECT-TYPE
        SYNTAX    Gauge
        ACCESS    read-only
        STATUS    mandatory
        DESCRIPTION
            "A Gauge object containing the number of data records in the
            cache."
        ::= { g3trunkgrp 5 }

    g3trunkgrpTable	OBJECT-TYPE
        SYNTAX    SEQUENCE OF G3trunkgrpEntry
        ACCESS    not-accessible
        STATUS    mandatory
        DESCRIPTION
            "A list of g3trunkgrp entries."
        ::= { g3trunkgrp 6 }

    g3trunkgrpEntry	OBJECT-TYPE
        SYNTAX    G3trunkgrpEntry
        ACCESS    not-accessible
        STATUS    mandatory
        DESCRIPTION
            "A g3trunkgrp entry containing objects of the
            g3trunkgrp information sent by the switch."
        INDEX    { g3trunkgrpNumber }
        ::= { g3trunkgrpTable 1 }

    G3trunkgrpEntry ::= SEQUENCE {
        g3trunkgrpNumber
            INTEGER,
        g3trunkgrpType
            DisplayString,
        g3trunkgrpName
            DisplayString,
        g3trunkgrpDirection
            DisplayString,
        g3trunkgrpServiceType
            DisplayString,
        g3trunkgrpCommType
            DisplayString,
        g3trunkgrpTrunkType
            DisplayString,
        g3trunkgrpSize
            INTEGER,
        g3trunkgrpUsageAlloc
            DisplayString,
        g3trunkgrpTAC
            INTEGER,
        g3trunkgrpWideSupport
            DisplayString,
        g3trunkgrpDCSFlag
            DisplayString,
        g3trunkgrpPbxID
            INTEGER,
        g3trunkgrpDCSSigType
            DisplayString,
        g3trunkgrpSigType
            DisplayString,
        g3trunkgrpACAFlag
            DisplayString,
        g3trunkgrpLongHold
            INTEGER,
        g3trunkgrpShortHold
            INTEGER,
        g3trunkgrpShortThreshold
            INTEGER,
        g3trunkgrpQsigValueAdd
            DisplayString,
        g3trunkgrpSuppServProt
            DisplayString
        }

    g3trunkgrpNumber	OBJECT-TYPE
        SYNTAX    INTEGER
        ACCESS    read-only
        STATUS    mandatory
        DESCRIPTION
            "An INTEGER Object that uniquely identifies an administered
            trunk group."
        ::= { g3trunkgrpEntry 1 }

    g3trunkgrpType	OBJECT-TYPE
        SYNTAX    DisplayString (SIZE (0..13))
        ACCESS    read-only
        STATUS    mandatory
        DESCRIPTION
            "A DisplayString Object containing the trunk group type."
        ::= { g3trunkgrpEntry 2 }

    g3trunkgrpName	OBJECT-TYPE
        SYNTAX    DisplayString (SIZE (0..15))
        ACCESS    read-only
        STATUS    mandatory
        DESCRIPTION
            "A DisplayString Object containing the name assigned to the trunk
            group."
        ::= { g3trunkgrpEntry 3 }

    g3trunkgrpDirection	OBJECT-TYPE
        SYNTAX    DisplayString (SIZE (0..8))
        ACCESS    read-only
        STATUS    mandatory
        DESCRIPTION
            "A DisplayString Object containing the trunk group direction."
        ::= { g3trunkgrpEntry 4 }

    g3trunkgrpServiceType	OBJECT-TYPE
        SYNTAX    DisplayString (SIZE (0..16))
        ACCESS    read-only
        STATUS    mandatory
        DESCRIPTION
            "A DisplayString Object containing the trunk group service type."
        ::= { g3trunkgrpEntry 5 }

    g3trunkgrpCommType	OBJECT-TYPE
        SYNTAX    DisplayString (SIZE (0..5))
        ACCESS    read-only
        STATUS    mandatory
        DESCRIPTION
            "A DisplayString Object containing the trunk group communications
            type."
        ::= { g3trunkgrpEntry 6 }

    g3trunkgrpTrunkType	OBJECT-TYPE
        SYNTAX    DisplayString (SIZE (0..12))
        ACCESS    read-only
        STATUS    mandatory
        DESCRIPTION
            "A DisplayString Object containing the trunk group trunk type."
        ::= { g3trunkgrpEntry 7 }

    g3trunkgrpSize	OBJECT-TYPE
        SYNTAX    INTEGER
        ACCESS    read-only
        STATUS    mandatory
        DESCRIPTION
            "An INTEGER Object containing the number of trunk group members."
        ::= { g3trunkgrpEntry 8 }

    g3trunkgrpUsageAlloc	OBJECT-TYPE
        SYNTAX    DisplayString (SIZE (0..1))
        ACCESS    read-only
        STATUS    mandatory
        DESCRIPTION
            "A DisplayString Object containing a y/n flag for usage allocation."
        ::= { g3trunkgrpEntry 9 }

    g3trunkgrpTAC	OBJECT-TYPE
        SYNTAX    INTEGER
        ACCESS    read-only
        STATUS    mandatory
        DESCRIPTION
            "An object containing the Access Code for the trunk group."
        ::= { g3trunkgrpEntry 10 }

    g3trunkgrpWideSupport	OBJECT-TYPE
        SYNTAX    DisplayString (SIZE (0..1))
        ACCESS    read-only
        STATUS    mandatory
        DESCRIPTION
            "A DisplayString Object containing a wideband support flag."
        ::= { g3trunkgrpEntry 11 }

    g3trunkgrpDCSFlag	OBJECT-TYPE
        SYNTAX    DisplayString (SIZE (0..1))
        ACCESS    read-only
        STATUS    mandatory
        DESCRIPTION
            "A DisplayString Object containing the flag that shows whether
            the trunk is used for DCS (y or n)."
        ::= { g3trunkgrpEntry 12 }

    g3trunkgrpPbxID	OBJECT-TYPE
        SYNTAX    INTEGER
        ACCESS    read-only
        STATUS    mandatory
        DESCRIPTION
            "An INTEGER Object containing the identifier of the PBX."
        ::= { g3trunkgrpEntry 13 }

    g3trunkgrpDCSSigType	OBJECT-TYPE
        SYNTAX    DisplayString (SIZE (0..6))
        ACCESS    read-only
        STATUS    mandatory
        DESCRIPTION
            "A DisplayString Object containing the DCS signaling type."
        ::= { g3trunkgrpEntry 14 }

    g3trunkgrpSigType	OBJECT-TYPE
        SYNTAX    DisplayString (SIZE (0..4))
        ACCESS    read-only
        STATUS    mandatory
        DESCRIPTION
            "A DisplayString Object containing the trunk signaling type."
        ::= { g3trunkgrpEntry 15 }

    g3trunkgrpACAFlag	OBJECT-TYPE
        SYNTAX    DisplayString (SIZE (0..1))
        ACCESS    read-only
        STATUS    mandatory
        DESCRIPTION
            "A DisplayString Object containing the flag that shows whether
            the trunk is used for ACA (y or n)."
        ::= { g3trunkgrpEntry 16 }

    g3trunkgrpLongHold	OBJECT-TYPE
        SYNTAX    INTEGER
        ACCESS    read-only
        STATUS    mandatory
        DESCRIPTION
            "An INTEGER Object containing the long holding time in hours."
        ::= { g3trunkgrpEntry 17 }

    g3trunkgrpShortHold	OBJECT-TYPE
        SYNTAX    INTEGER
        ACCESS    read-only
        STATUS    mandatory
        DESCRIPTION
            "An INTEGER Object containing the short holding time in seconds."
        ::= { g3trunkgrpEntry 18 }

    g3trunkgrpShortThreshold	OBJECT-TYPE
        SYNTAX    INTEGER
        ACCESS    read-only
        STATUS    mandatory
        DESCRIPTION
            "An INTEGER Object containing the short hold time threshold."
        ::= { g3trunkgrpEntry 19 }

    g3trunkgrpQsigValueAdd	OBJECT-TYPE
        SYNTAX    DisplayString (SIZE (0..1))
        ACCESS    read-only
        STATUS    mandatory
        DESCRIPTION
            "A DisplayString Object containing a flag that indicates whether
            or not QSIG Value-Added is in use (y or n)."
        ::= { g3trunkgrpEntry 20 }

    g3trunkgrpSuppServProt	OBJECT-TYPE
        SYNTAX    DisplayString (SIZE (0..1))
        ACCESS    read-only
        STATUS    mandatory
        DESCRIPTION
            "A DisplayString Object specifying which supplementary server
            protocol is being used (can have a value of a-g)."
        ::= { g3trunkgrpEntry 21 }


    -- the g3bulletin group

    g3bulletinTage	OBJECT-TYPE
        SYNTAX    INTEGER
        ACCESS    read-only
        STATUS    mandatory
        DESCRIPTION
            "The number of timeticks since the bulletin board data was last
            extracted from the switch by the G3 Proxy Agent. This object
            along with the g3bulletinintvl object allows the Network Manager
            to determine the validity of the bulletin board data in the
            cache and to control when the proxy agent extracts the
            bulletin board data from the switch."
        ::= { g3bulletin 1 }

    g3bulletinTintvl	OBJECT-TYPE
        SYNTAX    INTEGER
        ACCESS    read-write
        STATUS    mandatory
        DESCRIPTION
            "An object containing the interval for which the bulletin board data
            extracted from the switch is considered valid by the proxy agent.
            When a GET or GET-NEXT request for bulletin board objects is
            received by the agent it uses the g3bulletinage and g3bulletinintvl
            objects to determine whether it should refresh the cached
            bulletinTable.  If g3bulletinstmp + g3bulletinintvl is less than the
            current value of the sysUpTime object then the agent refreshes
            the bulletinTable cache.  In either case it responds to the requests
            it receives with the data it currently has in the cache."
        ::= { g3bulletin 2 }

    g3bulletinTdelay	OBJECT-TYPE
        SYNTAX    INTEGER
        ACCESS    read-only
        STATUS    mandatory
        DESCRIPTION
            "An object containing the delay encountered in updating
            the cached data"
        ::= { g3bulletin 3 }

    g3bulletinTretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3bulletin 4 }

    g3bulletinMessage1	OBJECT-TYPE
        SYNTAX    DisplayString (SIZE (0..40))
        ACCESS    read-only
        STATUS    mandatory
        DESCRIPTION
            "A DisplayString Object containing a bulletin board message. A message
            posted to the bulletin board can consist of one or more Message fields 
            entered by the user. The Message fields can contain any character
            string that the user can enter on the keyboard. The Message field 
            can also be blank."
        ::= { g3bulletin 5 }

    g3bulletinMessage2	OBJECT-TYPE
        SYNTAX    DisplayString (SIZE (0..40))
        ACCESS    read-only
        STATUS    mandatory
        DESCRIPTION
            "See DESCRIPTION of g3bulletinMessage1."
        ::= { g3bulletin 6 }

    g3bulletinMessage3	OBJECT-TYPE
        SYNTAX    DisplayString (SIZE (0..40))
        ACCESS    read-only
        STATUS    mandatory
        DESCRIPTION
            "See DESCRIPTION of g3bulletinMessage1."
        ::= { g3bulletin 7 }

    g3bulletinMessage4	OBJECT-TYPE
        SYNTAX    DisplayString (SIZE (0..40))
        ACCESS    read-only
        STATUS    mandatory
        DESCRIPTION
            "See DESCRIPTION of g3bulletinMessage1."
        ::= { g3bulletin 8 }

    g3bulletinMessage5	OBJECT-TYPE
        SYNTAX    DisplayString (SIZE (0..40))
        ACCESS    read-only
        STATUS    mandatory
        DESCRIPTION
            "See DESCRIPTION of g3bulletinMessage1."
        ::= { g3bulletin 9 }

    g3bulletinMessage6	OBJECT-TYPE
        SYNTAX    DisplayString (SIZE (0..40))
        ACCESS    read-only
        STATUS    mandatory
        DESCRIPTION
            "See DESCRIPTION of g3bulletinMessage1."
        ::= { g3bulletin 10 }

    g3bulletinMessage7	OBJECT-TYPE
        SYNTAX    DisplayString (SIZE (0..40))
        ACCESS    read-only
        STATUS    mandatory
        DESCRIPTION
            "See DESCRIPTION of g3bulletinMessage1."
        ::= { g3bulletin 11 }

    g3bulletinMessage8	OBJECT-TYPE
        SYNTAX    DisplayString (SIZE (0..40))
        ACCESS    read-only
        STATUS    mandatory
        DESCRIPTION
            "See DESCRIPTION of g3bulletinMessage1."
        ::= { g3bulletin 12 }

    g3bulletinMessage9	OBJECT-TYPE
        SYNTAX    DisplayString (SIZE (0..40))
        ACCESS    read-only
        STATUS    mandatory
        DESCRIPTION
            "See DESCRIPTION of g3bulletinMessage1."
        ::= { g3bulletin 13 }

    g3bulletinMessage10	OBJECT-TYPE
        SYNTAX    DisplayString (SIZE (0..40))
        ACCESS    read-only
        STATUS    mandatory
        DESCRIPTION
            "See DESCRIPTION of g3bulletinMessage1."
        ::= { g3bulletin 14 }

    g3bulletinMessage11	OBJECT-TYPE
        SYNTAX    DisplayString (SIZE (0..40))
        ACCESS    read-only
        STATUS    mandatory
        DESCRIPTION
            "See DESCRIPTION of g3bulletinMessage1."
        ::= { g3bulletin 15 }

    g3bulletinMessage12	OBJECT-TYPE
        SYNTAX    DisplayString (SIZE (0..40))
        ACCESS    read-only
        STATUS    mandatory
        DESCRIPTION
            "See DESCRIPTION of g3bulletinMessage1."
        ::= { g3bulletin 16 }

    g3bulletinMessage13	OBJECT-TYPE
        SYNTAX    DisplayString (SIZE (0..40))
        ACCESS    read-only
        STATUS    mandatory
        DESCRIPTION
            "See DESCRIPTION of g3bulletinMessage1."
        ::= { g3bulletin 17 }

    g3bulletinMessage14	OBJECT-TYPE
        SYNTAX    DisplayString (SIZE (0..40))
        ACCESS    read-only
        STATUS    mandatory
        DESCRIPTION
            "See DESCRIPTION of g3bulletinMessage1."
        ::= { g3bulletin 18 }

    g3bulletinMessage15	OBJECT-TYPE
        SYNTAX    DisplayString (SIZE (0..40))
        ACCESS    read-only
        STATUS    mandatory
        DESCRIPTION
            "See DESCRIPTION of g3bulletinMessage1."
        ::= { g3bulletin 19 }

    g3bulletinMessage16	OBJECT-TYPE
        SYNTAX    DisplayString (SIZE (0..40))
        ACCESS    read-only
        STATUS    mandatory
        DESCRIPTION
            "See DESCRIPTION of g3bulletinMessage1."
        ::= { g3bulletin 20 }

    g3bulletinMessage17	OBJECT-TYPE
        SYNTAX    DisplayString (SIZE (0..40))
        ACCESS    read-only
        STATUS    mandatory
        DESCRIPTION
            "See DESCRIPTION of g3bulletinMessage1."
        ::= { g3bulletin 21 }

    g3bulletinMessage18	OBJECT-TYPE
        SYNTAX    DisplayString (SIZE (0..40))
        ACCESS    read-only
        STATUS    mandatory
        DESCRIPTION
            "See DESCRIPTION of g3bulletinMessage1."
        ::= { g3bulletin 22 }

    g3bulletinMessage19	OBJECT-TYPE
        SYNTAX    DisplayString (SIZE (0..40))
        ACCESS    read-only
        STATUS    mandatory
        DESCRIPTION
            "See DESCRIPTION of g3bulletinMessage1."
        ::= { g3bulletin 23 }

    g3bulletinMessage20	OBJECT-TYPE
        SYNTAX    DisplayString (SIZE (0..40))
        ACCESS    read-only
        STATUS    mandatory
        DESCRIPTION
            "See DESCRIPTION of g3bulletinMessage1."
        ::= { g3bulletin 24 }

    g3bulletinMessage21	OBJECT-TYPE
        SYNTAX    DisplayString (SIZE (0..40))
        ACCESS    read-only
        STATUS    mandatory
        DESCRIPTION
            "See DESCRIPTION of g3bulletinMessage1."
        ::= { g3bulletin 25 }

    g3bulletinMessage22	OBJECT-TYPE
        SYNTAX    DisplayString (SIZE (0..40))
        ACCESS    read-only
        STATUS    mandatory
        DESCRIPTION
            "See DESCRIPTION of g3bulletinMessage1."
        ::= { g3bulletin 26 }

    g3bulletinMessage23	OBJECT-TYPE
        SYNTAX    DisplayString (SIZE (0..40))
        ACCESS    read-only
        STATUS    mandatory
        DESCRIPTION
            "See DESCRIPTION of g3bulletinMessage1."
        ::= { g3bulletin 27 }

    g3bulletinMessage24	OBJECT-TYPE
        SYNTAX    DisplayString (SIZE (0..40))
        ACCESS    read-only
        STATUS    mandatory
        DESCRIPTION
            "See DESCRIPTION of g3bulletinMessage1."
        ::= { g3bulletin 28 }

    g3bulletinMessage25	OBJECT-TYPE
        SYNTAX    DisplayString (SIZE (0..40))
        ACCESS    read-only
        STATUS    mandatory
        DESCRIPTION
            "See DESCRIPTION of g3bulletinMessage1."
        ::= { g3bulletin 29 }

    g3bulletinMessage26	OBJECT-TYPE
        SYNTAX    DisplayString (SIZE (0..40))
        ACCESS    read-only
        STATUS    mandatory
        DESCRIPTION
            "See DESCRIPTION of g3bulletinMessage1."
        ::= { g3bulletin 30 }

    g3bulletinMessage27	OBJECT-TYPE
        SYNTAX    DisplayString (SIZE (0..40))
        ACCESS    read-only
        STATUS    mandatory
        DESCRIPTION
            "See DESCRIPTION of g3bulletinMessage1."
        ::= { g3bulletin 31 }

    g3bulletinMessage28	OBJECT-TYPE
        SYNTAX    DisplayString (SIZE (0..40))
        ACCESS    read-only
        STATUS    mandatory
        DESCRIPTION
            "See DESCRIPTION of g3bulletinMessage1."
        ::= { g3bulletin 32 }

    g3bulletinMessage29	OBJECT-TYPE
        SYNTAX    DisplayString (SIZE (0..40))
        ACCESS    read-only
        STATUS    mandatory
        DESCRIPTION
            "See DESCRIPTION of g3bulletinMessage1."
        ::= { g3bulletin 33 }

    g3bulletinMessage30	OBJECT-TYPE
        SYNTAX    DisplayString (SIZE (0..40))
        ACCESS    read-only
        STATUS    mandatory
        DESCRIPTION
            "See DESCRIPTION of g3bulletinMessage1."
        ::= { g3bulletin 34 }

    g3bulletinMessage31	OBJECT-TYPE
        SYNTAX    DisplayString (SIZE (0..40))
        ACCESS    read-only
        STATUS    mandatory
        DESCRIPTION
            "See DESCRIPTION of g3bulletinMessage1."
        ::= { g3bulletin 35 }

    g3bulletinMessage32	OBJECT-TYPE
        SYNTAX    DisplayString (SIZE (0..40))
        ACCESS    read-only
        STATUS    mandatory
        DESCRIPTION
            "See DESCRIPTION of g3bulletinMessage1."
        ::= { g3bulletin 36 }

    g3bulletinMessage33	OBJECT-TYPE
        SYNTAX    DisplayString (SIZE (0..40))
        ACCESS    read-only
        STATUS    mandatory
        DESCRIPTION
            "See DESCRIPTION of g3bulletinMessage1."
        ::= { g3bulletin 37 }

    g3bulletinMessage34	OBJECT-TYPE
        SYNTAX    DisplayString (SIZE (0..40))
        ACCESS    read-only
        STATUS    mandatory
        DESCRIPTION
            "See DESCRIPTION of g3bulletinMessage1."
        ::= { g3bulletin 38 }

    g3bulletinMessage35	OBJECT-TYPE
        SYNTAX    DisplayString (SIZE (0..40))
        ACCESS    read-only
        STATUS    mandatory
        DESCRIPTION
            "See DESCRIPTION of g3bulletinMessage1."
        ::= { g3bulletin 39 }

    g3bulletinMessage36	OBJECT-TYPE
        SYNTAX    DisplayString (SIZE (0..40))
        ACCESS    read-only
        STATUS    mandatory
        DESCRIPTION
            "See DESCRIPTION of g3bulletinMessage1."
        ::= { g3bulletin 40 }

    g3bulletinMessage37	OBJECT-TYPE
        SYNTAX    DisplayString (SIZE (0..40))
        ACCESS    read-only
        STATUS    mandatory
        DESCRIPTION
            "See DESCRIPTION of g3bulletinMessage1."
        ::= { g3bulletin 41 }

    g3bulletinMessage38	OBJECT-TYPE
        SYNTAX    DisplayString (SIZE (0..40))
        ACCESS    read-only
        STATUS    mandatory
        DESCRIPTION
            "See DESCRIPTION of g3bulletinMessage1."
        ::= { g3bulletin 42 }

    g3bulletinMessage39	OBJECT-TYPE
        SYNTAX    DisplayString (SIZE (0..40))
        ACCESS    read-only
        STATUS    mandatory
        DESCRIPTION
            "See DESCRIPTION of g3bulletinMessage1."
        ::= { g3bulletin 43 }

    g3bulletinMessage40	OBJECT-TYPE
        SYNTAX    DisplayString (SIZE (0..40))
        ACCESS    read-only
        STATUS    mandatory
        DESCRIPTION
            "See DESCRIPTION of g3bulletinMessage1."
        ::= { g3bulletin 44 }

    g3bulletinMessage41	OBJECT-TYPE
        SYNTAX    DisplayString (SIZE (0..40))
        ACCESS    read-only
        STATUS    mandatory
        DESCRIPTION
            "See DESCRIPTION of g3bulletinMessage1."
        ::= { g3bulletin 45 }

    g3bulletinMessage42	OBJECT-TYPE
        SYNTAX    DisplayString (SIZE (0..40))
        ACCESS    read-only
        STATUS    mandatory
        DESCRIPTION
            "See DESCRIPTION of g3bulletinMessage1."
        ::= { g3bulletin 46 }

    g3bulletinMessage43	OBJECT-TYPE
        SYNTAX    DisplayString (SIZE (0..40))
        ACCESS    read-only
        STATUS    mandatory
        DESCRIPTION
            "See DESCRIPTION of g3bulletinMessage1."
        ::= { g3bulletin 47 }

    g3bulletinMessage44	OBJECT-TYPE
        SYNTAX    DisplayString (SIZE (0..40))
        ACCESS    read-only
        STATUS    mandatory
        DESCRIPTION
            "See DESCRIPTION of g3bulletinMessage1."
        ::= { g3bulletin 48 }

    g3bulletinMessage45	OBJECT-TYPE
        SYNTAX    DisplayString (SIZE (0..40))
        ACCESS    read-only
        STATUS    mandatory
        DESCRIPTION
            "See DESCRIPTION of g3bulletinMessage1."
        ::= { g3bulletin 49 }

    g3bulletinMessage46	OBJECT-TYPE
        SYNTAX    DisplayString (SIZE (0..40))
        ACCESS    read-only
        STATUS    mandatory
        DESCRIPTION
            "See DESCRIPTION of g3bulletinMessage1."
        ::= { g3bulletin 50 }

    g3bulletinMessage47	OBJECT-TYPE
        SYNTAX    DisplayString (SIZE (0..40))
        ACCESS    read-only
        STATUS    mandatory
        DESCRIPTION
            "See DESCRIPTION of g3bulletinMessage1."
        ::= { g3bulletin 51 }

    g3bulletinMessage48	OBJECT-TYPE
        SYNTAX    DisplayString (SIZE (0..40))
        ACCESS    read-only
        STATUS    mandatory
        DESCRIPTION
            "See DESCRIPTION of g3bulletinMessage1."
        ::= { g3bulletin 52 }

    g3bulletinMessage49	OBJECT-TYPE
        SYNTAX    DisplayString (SIZE (0..40))
        ACCESS    read-only
        STATUS    mandatory
        DESCRIPTION
            "See DESCRIPTION of g3bulletinMessage1."
        ::= { g3bulletin 53 }

    g3bulletinMessage50	OBJECT-TYPE
        SYNTAX    DisplayString (SIZE (0..40))
        ACCESS    read-only
        STATUS    mandatory
        DESCRIPTION
            "See DESCRIPTION of g3bulletinMessage1."
        ::= { g3bulletin 54 }

    g3bulletinMessage51	OBJECT-TYPE
        SYNTAX    DisplayString (SIZE (0..40))
        ACCESS    read-only
        STATUS    mandatory
        DESCRIPTION
            "See DESCRIPTION of g3bulletinMessage1."
        ::= { g3bulletin 55 }

    g3bulletinMessage52	OBJECT-TYPE
        SYNTAX    DisplayString (SIZE (0..40))
        ACCESS    read-only
        STATUS    mandatory
        DESCRIPTION
            "See DESCRIPTION of g3bulletinMessage1."
        ::= { g3bulletin 56 }

    g3bulletinMessage53	OBJECT-TYPE
        SYNTAX    DisplayString (SIZE (0..40))
        ACCESS    read-only
        STATUS    mandatory
        DESCRIPTION
            "See DESCRIPTION of g3bulletinMessage1."
        ::= { g3bulletin 57 }

    g3bulletinMessage54	OBJECT-TYPE
        SYNTAX    DisplayString (SIZE (0..40))
        ACCESS    read-only
        STATUS    mandatory
        DESCRIPTION
            "See DESCRIPTION of g3bulletinMessage1."
        ::= { g3bulletin 58 }

    g3bulletinMessage55	OBJECT-TYPE
        SYNTAX    DisplayString (SIZE (0..40))
        ACCESS    read-only
        STATUS    mandatory
        DESCRIPTION
            "See DESCRIPTION of g3bulletinMessage1."
        ::= { g3bulletin 59 }

    g3bulletinMessage56	OBJECT-TYPE
        SYNTAX    DisplayString (SIZE (0..40))
        ACCESS    read-only
        STATUS    mandatory
        DESCRIPTION
            "See DESCRIPTION of g3bulletinMessage1."
        ::= { g3bulletin 60 }

    g3bulletinMessage57	OBJECT-TYPE
        SYNTAX    DisplayString (SIZE (0..40))
        ACCESS    read-only
        STATUS    mandatory
        DESCRIPTION
            "See DESCRIPTION of g3bulletinMessage1."
        ::= { g3bulletin 61 }

    g3bulletinMessage58	OBJECT-TYPE
        SYNTAX    DisplayString (SIZE (0..40))
        ACCESS    read-only
        STATUS    mandatory
        DESCRIPTION
            "See DESCRIPTION of g3bulletinMessage1."
        ::= { g3bulletin 62 }

    g3bulletinMessage59	OBJECT-TYPE
        SYNTAX    DisplayString (SIZE (0..40))
        ACCESS    read-only
        STATUS    mandatory
        DESCRIPTION
            "See DESCRIPTION of g3bulletinMessage1."
        ::= { g3bulletin 63 }

    g3bulletinDate1	OBJECT-TYPE
        SYNTAX    DisplayString (SIZE (0..10))
        ACCESS    read-only
        STATUS    mandatory
        DESCRIPTION
            "A DisplayString Object containing a bulletin board Date. Each Date
            field is associated with a Message field. If the associated Message
            field is not blank, the Date field identifies the date on which the
            bulletin board message was posted. If the associated Message field
            is blank, then the Date field will be blank."
        ::= { g3bulletin 64 }

    g3bulletinDate2	OBJECT-TYPE
        SYNTAX    DisplayString (SIZE (0..10))
        ACCESS    read-only
        STATUS    mandatory
        DESCRIPTION
            "See DESCRIPTION of g3bulletinDate1."
        ::= { g3bulletin 65 }

    g3bulletinDate3	OBJECT-TYPE
        SYNTAX    DisplayString (SIZE (0..10))
        ACCESS    read-only
        STATUS    mandatory
        DESCRIPTION
            "See DESCRIPTION of g3bulletinDate1."
        ::= { g3bulletin 66 }

    g3bulletinDate4	OBJECT-TYPE
        SYNTAX    DisplayString (SIZE (0..10))
        ACCESS    read-only
        STATUS    mandatory
        DESCRIPTION
            "See DESCRIPTION of g3bulletinDate1."
        ::= { g3bulletin 67 }

    g3bulletinDate5	OBJECT-TYPE
        SYNTAX    DisplayString (SIZE (0..10))
        ACCESS    read-only
        STATUS    mandatory
        DESCRIPTION
            "See DESCRIPTION of g3bulletinDate1."
        ::= { g3bulletin 68 }

    g3bulletinDate6	OBJECT-TYPE
        SYNTAX    DisplayString (SIZE (0..10))
        ACCESS    read-only
        STATUS    mandatory
        DESCRIPTION
            "See DESCRIPTION of g3bulletinDate1."
        ::= { g3bulletin 69 }

    g3bulletinDate7	OBJECT-TYPE
        SYNTAX    DisplayString (SIZE (0..10))
        ACCESS    read-only
        STATUS    mandatory
        DESCRIPTION
            "See DESCRIPTION of g3bulletinDate1."
        ::= { g3bulletin 70 }

    g3bulletinDate8	OBJECT-TYPE
        SYNTAX    DisplayString (SIZE (0..10))
        ACCESS    read-only
        STATUS    mandatory
        DESCRIPTION
            "See DESCRIPTION of g3bulletinDate1."
        ::= { g3bulletin 71 }

    g3bulletinDate9	OBJECT-TYPE
        SYNTAX    DisplayString (SIZE (0..10))
        ACCESS    read-only
        STATUS    mandatory
        DESCRIPTION
            "See DESCRIPTION of g3bulletinDate1."
        ::= { g3bulletin 72 }

    g3bulletinDate10	OBJECT-TYPE
        SYNTAX    DisplayString (SIZE (0..10))
        ACCESS    read-only
        STATUS    mandatory
        DESCRIPTION
            "See DESCRIPTION of g3bulletinDate1."
        ::= { g3bulletin 73 }

    g3bulletinDate11	OBJECT-TYPE
        SYNTAX    DisplayString (SIZE (0..10))
        ACCESS    read-only
        STATUS    mandatory
        DESCRIPTION
            "See DESCRIPTION of g3bulletinDate1."
        ::= { g3bulletin 74 }

    g3bulletinDate12	OBJECT-TYPE
        SYNTAX    DisplayString (SIZE (0..10))
        ACCESS    read-only
        STATUS    mandatory
        DESCRIPTION
            "See DESCRIPTION of g3bulletinDate1."
        ::= { g3bulletin 75 }

    g3bulletinDate13	OBJECT-TYPE
        SYNTAX    DisplayString (SIZE (0..10))
        ACCESS    read-only
        STATUS    mandatory
        DESCRIPTION
            "See DESCRIPTION of g3bulletinDate1."
        ::= { g3bulletin 76 }

    g3bulletinDate14	OBJECT-TYPE
        SYNTAX    DisplayString (SIZE (0..10))
        ACCESS    read-only
        STATUS    mandatory
        DESCRIPTION
            "See DESCRIPTION of g3bulletinDate1."
        ::= { g3bulletin 77 }

    g3bulletinDate15	OBJECT-TYPE
        SYNTAX    DisplayString (SIZE (0..10))
        ACCESS    read-only
        STATUS    mandatory
        DESCRIPTION
            "See DESCRIPTION of g3bulletinDate1."
        ::= { g3bulletin 78 }

    g3bulletinDate16	OBJECT-TYPE
        SYNTAX    DisplayString (SIZE (0..10))
        ACCESS    read-only
        STATUS    mandatory
        DESCRIPTION
            "See DESCRIPTION of g3bulletinDate1."
        ::= { g3bulletin 79 }

    g3bulletinDate17	OBJECT-TYPE
        SYNTAX    DisplayString (SIZE (0..10))
        ACCESS    read-only
        STATUS    mandatory
        DESCRIPTION
            "See DESCRIPTION of g3bulletinDate1."
        ::= { g3bulletin 80 }

    g3bulletinDate18	OBJECT-TYPE
        SYNTAX    DisplayString (SIZE (0..10))
        ACCESS    read-only
        STATUS    mandatory
        DESCRIPTION
            "See DESCRIPTION of g3bulletinDate1."
        ::= { g3bulletin 81 }

    g3bulletinDate19	OBJECT-TYPE
        SYNTAX    DisplayString (SIZE (0..10))
        ACCESS    read-only
        STATUS    mandatory
        DESCRIPTION
            "See DESCRIPTION of g3bulletinDate1."
        ::= { g3bulletin 82 }

    g3bulletinDate20	OBJECT-TYPE
        SYNTAX    DisplayString (SIZE (0..10))
        ACCESS    read-only
        STATUS    mandatory
        DESCRIPTION
            "See DESCRIPTION of g3bulletinDate1."
        ::= { g3bulletin 83 }

    g3bulletinDate21	OBJECT-TYPE
        SYNTAX    DisplayString (SIZE (0..10))
        ACCESS    read-only
        STATUS    mandatory
        DESCRIPTION
            "See DESCRIPTION of g3bulletinDate1."
        ::= { g3bulletin 84 }

    g3bulletinDate22	OBJECT-TYPE
        SYNTAX    DisplayString (SIZE (0..10))
        ACCESS    read-only
        STATUS    mandatory
        DESCRIPTION
            "See DESCRIPTION of g3bulletinDate1."
        ::= { g3bulletin 85 }

    g3bulletinDate23	OBJECT-TYPE
        SYNTAX    DisplayString (SIZE (0..10))
        ACCESS    read-only
        STATUS    mandatory
        DESCRIPTION
            "See DESCRIPTION of g3bulletinDate1."
        ::= { g3bulletin 86 }

    g3bulletinDate24	OBJECT-TYPE
        SYNTAX    DisplayString (SIZE (0..10))
        ACCESS    read-only
        STATUS    mandatory
        DESCRIPTION
            "See DESCRIPTION of g3bulletinDate1."
        ::= { g3bulletin 87 }

    g3bulletinDate25	OBJECT-TYPE
        SYNTAX    DisplayString (SIZE (0..10))
        ACCESS    read-only
        STATUS    mandatory
        DESCRIPTION
            "See DESCRIPTION of g3bulletinDate1."
        ::= { g3bulletin 88 }

    g3bulletinDate26	OBJECT-TYPE
        SYNTAX    DisplayString (SIZE (0..10))
        ACCESS    read-only
        STATUS    mandatory
        DESCRIPTION
            "See DESCRIPTION of g3bulletinDate1."
        ::= { g3bulletin 89 }

    g3bulletinDate27	OBJECT-TYPE
        SYNTAX    DisplayString (SIZE (0..10))
        ACCESS    read-only
        STATUS    mandatory
        DESCRIPTION
            "See DESCRIPTION of g3bulletinDate1."
        ::= { g3bulletin 90 }

    g3bulletinDate28	OBJECT-TYPE
        SYNTAX    DisplayString (SIZE (0..10))
        ACCESS    read-only
        STATUS    mandatory
        DESCRIPTION
            "See DESCRIPTION of g3bulletinDate1."
        ::= { g3bulletin 91 }

    g3bulletinDate29	OBJECT-TYPE
        SYNTAX    DisplayString (SIZE (0..10))
        ACCESS    read-only
        STATUS    mandatory
        DESCRIPTION
            "See DESCRIPTION of g3bulletinDate1."
        ::= { g3bulletin 92 }

    g3bulletinDate30	OBJECT-TYPE
        SYNTAX    DisplayString (SIZE (0..10))
        ACCESS    read-only
        STATUS    mandatory
        DESCRIPTION
            "See DESCRIPTION of g3bulletinDate1."
        ::= { g3bulletin 93 }

    g3bulletinDate31	OBJECT-TYPE
        SYNTAX    DisplayString (SIZE (0..10))
        ACCESS    read-only
        STATUS    mandatory
        DESCRIPTION
            "See DESCRIPTION of g3bulletinDate1."
        ::= { g3bulletin 94 }

    g3bulletinDate32	OBJECT-TYPE
        SYNTAX    DisplayString (SIZE (0..10))
        ACCESS    read-only
        STATUS    mandatory
        DESCRIPTION
            "See DESCRIPTION of g3bulletinDate1."
        ::= { g3bulletin 95 }

    g3bulletinDate33	OBJECT-TYPE
        SYNTAX    DisplayString (SIZE (0..10))
        ACCESS    read-only
        STATUS    mandatory
        DESCRIPTION
            "See DESCRIPTION of g3bulletinDate1."
        ::= { g3bulletin 96 }

    g3bulletinDate34	OBJECT-TYPE
        SYNTAX    DisplayString (SIZE (0..10))
        ACCESS    read-only
        STATUS    mandatory
        DESCRIPTION
            "See DESCRIPTION of g3bulletinDate1."
        ::= { g3bulletin 97 }

    g3bulletinDate35	OBJECT-TYPE
        SYNTAX    DisplayString (SIZE (0..10))
        ACCESS    read-only
        STATUS    mandatory
        DESCRIPTION
            "See DESCRIPTION of g3bulletinDate1."
        ::= { g3bulletin 98 }

    g3bulletinDate36	OBJECT-TYPE
        SYNTAX    DisplayString (SIZE (0..10))
        ACCESS    read-only
        STATUS    mandatory
        DESCRIPTION
            "See DESCRIPTION of g3bulletinDate1."
        ::= { g3bulletin 99 }

    g3bulletinDate37	OBJECT-TYPE
        SYNTAX    DisplayString (SIZE (0..10))
        ACCESS    read-only
        STATUS    mandatory
        DESCRIPTION
            "See DESCRIPTION of g3bulletinDate1."
        ::= { g3bulletin 100 }

    g3bulletinDate38	OBJECT-TYPE
        SYNTAX    DisplayString (SIZE (0..10))
        ACCESS    read-only
        STATUS    mandatory
        DESCRIPTION
            "See DESCRIPTION of g3bulletinDate1."
        ::= { g3bulletin 101 }

    g3bulletinDate39	OBJECT-TYPE
        SYNTAX    DisplayString (SIZE (0..10))
        ACCESS    read-only
        STATUS    mandatory
        DESCRIPTION
            "See DESCRIPTION of g3bulletinDate1."
        ::= { g3bulletin 102 }

    g3bulletinDate40	OBJECT-TYPE
        SYNTAX    DisplayString (SIZE (0..10))
        ACCESS    read-only
        STATUS    mandatory
        DESCRIPTION
            "See DESCRIPTION of g3bulletinDate1."
        ::= { g3bulletin 103 }

    g3bulletinDate41	OBJECT-TYPE
        SYNTAX    DisplayString (SIZE (0..10))
        ACCESS    read-only
        STATUS    mandatory
        DESCRIPTION
            "See DESCRIPTION of g3bulletinDate1."
        ::= { g3bulletin 104 }

    g3bulletinDate42	OBJECT-TYPE
        SYNTAX    DisplayString (SIZE (0..10))
        ACCESS    read-only
        STATUS    mandatory
        DESCRIPTION
            "See DESCRIPTION of g3bulletinDate1."
        ::= { g3bulletin 105 }

    g3bulletinDate43	OBJECT-TYPE
        SYNTAX    DisplayString (SIZE (0..10))
        ACCESS    read-only
        STATUS    mandatory
        DESCRIPTION
            "See DESCRIPTION of g3bulletinDate1."
        ::= { g3bulletin 106 }

    g3bulletinDate44	OBJECT-TYPE
        SYNTAX    DisplayString (SIZE (0..10))
        ACCESS    read-only
        STATUS    mandatory
        DESCRIPTION
            "See DESCRIPTION of g3bulletinDate1."
        ::= { g3bulletin 107 }

    g3bulletinDate45	OBJECT-TYPE
        SYNTAX    DisplayString (SIZE (0..10))
        ACCESS    read-only
        STATUS    mandatory
        DESCRIPTION
            "See DESCRIPTION of g3bulletinDate1."
        ::= { g3bulletin 108 }

    g3bulletinDate46	OBJECT-TYPE
        SYNTAX    DisplayString (SIZE (0..10))
        ACCESS    read-only
        STATUS    mandatory
        DESCRIPTION
            "See DESCRIPTION of g3bulletinDate1."
        ::= { g3bulletin 109 }

    g3bulletinDate47	OBJECT-TYPE
        SYNTAX    DisplayString (SIZE (0..10))
        ACCESS    read-only
        STATUS    mandatory
        DESCRIPTION
            "See DESCRIPTION of g3bulletinDate1."
        ::= { g3bulletin 110 }

    g3bulletinDate48	OBJECT-TYPE
        SYNTAX    DisplayString (SIZE (0..10))
        ACCESS    read-only
        STATUS    mandatory
        DESCRIPTION
            "See DESCRIPTION of g3bulletinDate1."
        ::= { g3bulletin 111 }

    g3bulletinDate49	OBJECT-TYPE
        SYNTAX    DisplayString (SIZE (0..10))
        ACCESS    read-only
        STATUS    mandatory
        DESCRIPTION
            "See DESCRIPTION of g3bulletinDate1."
        ::= { g3bulletin 112 }

    g3bulletinDate50	OBJECT-TYPE
        SYNTAX    DisplayString (SIZE (0..10))
        ACCESS    read-only
        STATUS    mandatory
        DESCRIPTION
            "See DESCRIPTION of g3bulletinDate1."
        ::= { g3bulletin 113 }

    g3bulletinDate51	OBJECT-TYPE
        SYNTAX    DisplayString (SIZE (0..10))
        ACCESS    read-only
        STATUS    mandatory
        DESCRIPTION
            "See DESCRIPTION of g3bulletinDate1."
        ::= { g3bulletin 114 }

    g3bulletinDate52	OBJECT-TYPE
        SYNTAX    DisplayString (SIZE (0..10))
        ACCESS    read-only
        STATUS    mandatory
        DESCRIPTION
            "See DESCRIPTION of g3bulletinDate1."
        ::= { g3bulletin 115 }

    g3bulletinDate53	OBJECT-TYPE
        SYNTAX    DisplayString (SIZE (0..10))
        ACCESS    read-only
        STATUS    mandatory
        DESCRIPTION
            "See DESCRIPTION of g3bulletinDate1."
        ::= { g3bulletin 116 }

    g3bulletinDate54	OBJECT-TYPE
        SYNTAX    DisplayString (SIZE (0..10))
        ACCESS    read-only
        STATUS    mandatory
        DESCRIPTION
            "See DESCRIPTION of g3bulletinDate1."
        ::= { g3bulletin 117 }

    g3bulletinDate55	OBJECT-TYPE
        SYNTAX    DisplayString (SIZE (0..10))
        ACCESS    read-only
        STATUS    mandatory
        DESCRIPTION
            "See DESCRIPTION of g3bulletinDate1."
        ::= { g3bulletin 118 }

    g3bulletinDate56	OBJECT-TYPE
        SYNTAX    DisplayString (SIZE (0..10))
        ACCESS    read-only
        STATUS    mandatory
        DESCRIPTION
            "See DESCRIPTION of g3bulletinDate1."
        ::= { g3bulletin 119 }

    g3bulletinDate57	OBJECT-TYPE
        SYNTAX    DisplayString (SIZE (0..10))
        ACCESS    read-only
        STATUS    mandatory
        DESCRIPTION
            "See DESCRIPTION of g3bulletinDate1."
        ::= { g3bulletin 120 }

    g3bulletinDate58	OBJECT-TYPE
        SYNTAX    DisplayString (SIZE (0..10))
        ACCESS    read-only
        STATUS    mandatory
        DESCRIPTION
            "See DESCRIPTION of g3bulletinDate1."
        ::= { g3bulletin 121 }

    g3bulletinDate59	OBJECT-TYPE
        SYNTAX    DisplayString (SIZE (0..10))
        ACCESS    read-only
        STATUS    mandatory
        DESCRIPTION
            "See DESCRIPTION of g3bulletinDate1."
        ::= { g3bulletin 122 }


    -- the g3ds1 group

    g3ds1Tage	OBJECT-TYPE
        SYNTAX    INTEGER
        ACCESS    read-only
        STATUS    mandatory
        DESCRIPTION
            "The number of timeticks since the ds1 data was last
            extracted from the switch by the G3 Proxy Agent. This object
            along with the g3ds1intvl object allows the Network Manager
            to determine the validity of the ds1 data in the
            cache and to control when the proxy agent extracts the
            ds1 data from the switch."
        ::= { g3ds1 1 }

    g3ds1Tintvl	OBJECT-TYPE
        SYNTAX    INTEGER
        ACCESS    read-write
        STATUS    mandatory
        DESCRIPTION
            "An object containing the interval for which the ds1 data
            extracted from the switch is considered valid by the proxy agent.
            When a GET or GET-NEXT request for ds1 objects is
            received by the agent it uses the g3ds1age and g3ds1intvl
            objects to determine whether it should refresh the cached
            ds1Table.  If g3ds1stmp + g3ds1intvl is less than the
            current value of the sysUpTime object then the agent refreshes
            the ds1Table cache.  In either case it responds to the requests
            it receives with the data it currently has in the cache."
        ::= { g3ds1 2 }

    g3ds1Tdelay	OBJECT-TYPE
        SYNTAX    INTEGER
        ACCESS    read-only
        STATUS    mandatory
        DESCRIPTION
            "An object containing the delay encountered in updating
            the cached data"
        ::= { g3ds1 3 }

    g3ds1Tretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3ds1 4 }

    g3ds1Tcount	OBJECT-TYPE
        SYNTAX    Gauge
        ACCESS    read-only
        STATUS    mandatory
        DESCRIPTION
            "A Gauge object containing the number of data records in the
            cache."
        ::= { g3ds1 5 }

    g3ds1Table	OBJECT-TYPE
        SYNTAX    SEQUENCE OF G3ds1Entry
        ACCESS    not-accessible
        STATUS    mandatory
        DESCRIPTION
            "A list of g3ds1 entries."
        ::= { g3ds1 6 }

    g3ds1Entry	OBJECT-TYPE
        SYNTAX    G3ds1Entry
        ACCESS    not-accessible
        STATUS    mandatory
        DESCRIPTION
            "A g3ds1 entry containing objects of the
            g3ds1 information sent by the switch."
        INDEX    { g3ds1Location }
        ::= { g3ds1Table 1 }

    G3ds1Entry ::= SEQUENCE {
        g3ds1Location
            DisplayString,
        g3ds1BitRate
            DisplayString,
        g3ds1Signaling
            DisplayString,
        g3ds1Name
            DisplayString
        }

    g3ds1Location	OBJECT-TYPE
        SYNTAX    DisplayString (SIZE (0..7))
        ACCESS    read-only
        STATUS    mandatory
        DESCRIPTION
            "A DisplayString Object that uniquely identifies a DS1 port board based 
            on its location in the system. The syntax for the Port Location is as
            follows: cabinet(01-44):carrier(A-E):slot(01-20)."
        ::= { g3ds1Entry 1 }

    g3ds1BitRate	OBJECT-TYPE
        SYNTAX    DisplayString (SIZE (0..5))
        ACCESS    read-only
        STATUS    mandatory
        DESCRIPTION
            "A DisplayString Object containing the Bit Rate for the DS1 board."
        ::= { g3ds1Entry 2 }

    g3ds1Signaling	OBJECT-TYPE
        SYNTAX    DisplayString (SIZE (0..11))
        ACCESS    read-only
        STATUS    mandatory
        DESCRIPTION
            "A DisplayString Object that contains the signaling of the board"
        ::= { g3ds1Entry 3 }

    g3ds1Name	OBJECT-TYPE
        SYNTAX    DisplayString (SIZE (0..15))
        ACCESS    read-only
        STATUS    mandatory
        DESCRIPTION
            "A DisplayString Object that contains the name of the board"
        ::= { g3ds1Entry 4 }


    -- the g3atmpnc group

    g3atmpncTage	OBJECT-TYPE
        SYNTAX    INTEGER
        ACCESS    read-only
        STATUS    mandatory
        DESCRIPTION
            "The number of timeticks since the ATM PNC data was last
            extracted from the switch by the G3 Proxy Agent. This object
            along with the g3atmpncintvl object allows the Network Manager
            to determine the validity of the ATM PNC data in the
            cache and to control when the proxy agent extracts the
            ATM PNC data from the switch."
        ::= { g3atmpnc 1 }

    g3atmpncTintvl	OBJECT-TYPE
        SYNTAX    INTEGER
        ACCESS    read-write
        STATUS    mandatory
        DESCRIPTION
            "An object containing the interval for which the ATM PNC group data
            extracted from the switch is considered valid by the proxy agent.
            When a GET or GET-NEXT request for ATM PNC objects is
            received by the agent it uses the g3atmpncage and g3atmpncintvl
            objects to determine whether it should refresh the cached
            atmpncTable.  If g3atmpncage + g3atmpncintvl is less than the
            current value of the sysUpTime object then the agent refreshes
            the atmpncTable cache.  In either case it responds to the requests
            it receives with the data it currently has in the cache."
        ::= { g3atmpnc 2 }

    g3atmpncTdelay	OBJECT-TYPE
        SYNTAX    INTEGER
        ACCESS    read-only
        STATUS    mandatory
        DESCRIPTION
            "An object containing the delay encountered in updating
            the cached data"
        ::= { g3atmpnc 3 }

    g3atmpncTretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3atmpnc 4 }

    g3atmpncTcount	OBJECT-TYPE
        SYNTAX    Gauge
        ACCESS    read-only
        STATUS    mandatory
        DESCRIPTION
            "A Gauge object containing the number of data records in the
            cache."
        ::= { g3atmpnc 5 }

    g3atmpncTable	OBJECT-TYPE
        SYNTAX    SEQUENCE OF G3atmpncEntry
        ACCESS    not-accessible
        STATUS    mandatory
        DESCRIPTION
            "A list of g3atmpnc entries."
        ::= { g3atmpnc 6 }

    g3atmpncEntry	OBJECT-TYPE
        SYNTAX    G3atmpncEntry
        ACCESS    not-accessible
        STATUS    mandatory
        DESCRIPTION
            "A g3atmpnc entry containing objects of the
            g3atmpnc information sent by the switch."
        INDEX    { g3atmpncconnection }
        ::= { g3atmpncTable 1 }

    G3atmpncEntry ::= SEQUENCE {
        g3atmpncconnection
            INTEGER,
        g3atmpncPncLocA
            DisplayString,
        g3atmpncPncNameA
            DisplayString,
        g3atmpncPncAddFmtA
            DisplayString,
        g3atmpncPncAFIA
            DisplayString,
        g3atmpncPncE164A
            DisplayString,
        g3atmpncPncDCIA
            DisplayString,
        g3atmpncPncHoDsp1A
            DisplayString,
        g3atmpncPncHoDsp2A
            DisplayString,
        g3atmpncPncESIA
            DisplayString,
        g3atmpncPncSELA
            DisplayString,
        g3atmpncPncLocB
            DisplayString,
        g3atmpncPncNameB
            DisplayString,
        g3atmpncPncAddFmtB
            DisplayString,
        g3atmpncPncAFIB
            DisplayString,
        g3atmpncPncE164B
            DisplayString,
        g3atmpncPncDCIB
            DisplayString,
        g3atmpncPncHoDsp1B
            DisplayString,
        g3atmpncPncHoDsp2B
            DisplayString,
        g3atmpncPncESIB
            DisplayString,
        g3atmpncPncSELB
            DisplayString
        }

    g3atmpncconnection	OBJECT-TYPE
        SYNTAX    INTEGER
        ACCESS    read-only
        STATUS    mandatory
        DESCRIPTION
            "An INTEGER Object that uniquely identifies an administered
            ATM PNC connection."
        ::= { g3atmpncEntry 1 }

    g3atmpncPncLocA	OBJECT-TYPE
        SYNTAX    DisplayString (SIZE (0..5))
        ACCESS    read-only
        STATUS    mandatory
        DESCRIPTION
            "An DisplayString Object that contains the ATM PNC location A
            port network location (exp 02A24)."
        ::= { g3atmpncEntry 2 }

    g3atmpncPncNameA	OBJECT-TYPE
        SYNTAX    DisplayString (SIZE (0..15))
        ACCESS    read-only
        STATUS    mandatory
        DESCRIPTION
            "An DisplayString Object that contains the name of the ATM PNC
            location A name (15 alphanumeric characters)."
        ::= { g3atmpncEntry 3 }

    g3atmpncPncAddFmtA	OBJECT-TYPE
        SYNTAX    DisplayString (SIZE (0..17))
        ACCESS    read-only
        STATUS    mandatory
        DESCRIPTION
            "An DisplayString Object that contains the address format of the ATM PNC
            location A (DCC ATM, E.164 ATM Private, or ICD ATM)."
        ::= { g3atmpncEntry 4 }

    g3atmpncPncAFIA	OBJECT-TYPE
        SYNTAX    DisplayString (SIZE (0..2))
        ACCESS    read-only
        STATUS    mandatory
        DESCRIPTION
            "An DisplayString Object that contains the AFI value of the ATM PNC
            location A AFI field (39 for DCC, 45 for E.164 ATM Private, or 47
            for ICD ATM)."
        ::= { g3atmpncEntry 5 }

    g3atmpncPncE164A	OBJECT-TYPE
        SYNTAX    DisplayString (SIZE (0..16))
        ACCESS    read-only
        STATUS    mandatory
        DESCRIPTION
            "An DisplayString Object that contains the hexidecimal value of the 
            ATM PNC location A E.164 field (16 hexidecimal digits)."
        ::= { g3atmpncEntry 6 }

    g3atmpncPncDCIA	OBJECT-TYPE
        SYNTAX    DisplayString (SIZE (0..4))
        ACCESS    read-only
        STATUS    mandatory
        DESCRIPTION
            "An DisplayString Object that contains the hexidecimal value of the 
            ATM PNC location A DCC/ICD field (4 hexidecimal digits)."
        ::= { g3atmpncEntry 7 }

    g3atmpncPncHoDsp1A	OBJECT-TYPE
        SYNTAX    DisplayString (SIZE (0..8))
        ACCESS    read-only
        STATUS    mandatory
        DESCRIPTION
            "An DisplayString Object that contains the hexidecimal value of the 
            ATM PNC location A HO-DSP1 field (8 hexidecimal digits)."
        ::= { g3atmpncEntry 8 }

    g3atmpncPncHoDsp2A	OBJECT-TYPE
        SYNTAX    DisplayString (SIZE (0..20))
        ACCESS    read-only
        STATUS    mandatory
        DESCRIPTION
            "An DisplayString Object that contains the hexidecimal value of the 
            ATM PNC location A HO-DSP2 field (20 hexidecimal digits)."
        ::= { g3atmpncEntry 9 }

    g3atmpncPncESIA	OBJECT-TYPE
        SYNTAX    DisplayString (SIZE (0..12))
        ACCESS    read-only
        STATUS    mandatory
        DESCRIPTION
            "An DisplayString Object that contains the hexidecimal value of the 
            ATM PNC location A ESI field (12 hexidecimal digits)."
        ::= { g3atmpncEntry 10 }

    g3atmpncPncSELA	OBJECT-TYPE
        SYNTAX    DisplayString (SIZE (0..2))
        ACCESS    read-only
        STATUS    mandatory
        DESCRIPTION
            "An DisplayString Object that contains the hexidecimal value of the 
            ATM PNC location A SEL field (2 hexidecimal digits)."
        ::= { g3atmpncEntry 11 }

    g3atmpncPncLocB	OBJECT-TYPE
        SYNTAX    DisplayString (SIZE (0..5))
        ACCESS    read-only
        STATUS    mandatory
        DESCRIPTION
            "An DisplayString Object that contains the ATM PNC location B
            port network location (exp 03A24)."
        ::= { g3atmpncEntry 12 }

    g3atmpncPncNameB	OBJECT-TYPE
        SYNTAX    DisplayString (SIZE (0..15))
        ACCESS    read-only
        STATUS    mandatory
        DESCRIPTION
            "An DisplayString Object that contains the name of the ATM PNC
            location B name (15 alphanumeric characters)."
        ::= { g3atmpncEntry 13 }

    g3atmpncPncAddFmtB	OBJECT-TYPE
        SYNTAX    DisplayString (SIZE (0..17))
        ACCESS    read-only
        STATUS    mandatory
        DESCRIPTION
            "An DisplayString Object that contains the address format of the ATM PNC
            location B (DCC ATM, E.164 ATM Private, or ICD ATM)."
        ::= { g3atmpncEntry 14 }

    g3atmpncPncAFIB	OBJECT-TYPE
        SYNTAX    DisplayString (SIZE (0..2))
        ACCESS    read-only
        STATUS    mandatory
        DESCRIPTION
            "An DisplayString Object that contains the AFI value of the ATM PNC
            location B AFI field (39 for DCC, 45 for E.164 ATM Private, or 47
            for ICD ATM)."
        ::= { g3atmpncEntry 15 }

    g3atmpncPncE164B	OBJECT-TYPE
        SYNTAX    DisplayString (SIZE (0..16))
        ACCESS    read-only
        STATUS    mandatory
        DESCRIPTION
            "An DisplayString Object that contains the hexidecimal value of the 
            ATM PNC location B E.164 field (16 hexidecimal digits)."
        ::= { g3atmpncEntry 16 }

    g3atmpncPncDCIB	OBJECT-TYPE
        SYNTAX    DisplayString (SIZE (0..4))
        ACCESS    read-only
        STATUS    mandatory
        DESCRIPTION
            "An DisplayString Object that contains the hexidecimal value of the 
            ATM PNC location B DCC/ICD field (4 hexidecimal digits)."
        ::= { g3atmpncEntry 17 }

    g3atmpncPncHoDsp1B	OBJECT-TYPE
        SYNTAX    DisplayString (SIZE (0..8))
        ACCESS    read-only
        STATUS    mandatory
        DESCRIPTION
            "An DisplayString Object that contains the hexidecimal value of the 
            ATM PNC location B HO-DSP1 field (8 hexidecimal digits)."
        ::= { g3atmpncEntry 18 }

    g3atmpncPncHoDsp2B	OBJECT-TYPE
        SYNTAX    DisplayString (SIZE (0..20))
        ACCESS    read-only
        STATUS    mandatory
        DESCRIPTION
            "An DisplayString Object that contains the hexidecimal value of the 
            ATM PNC location B HO-DSP2 field (20 hexidecimal digits)."
        ::= { g3atmpncEntry 19 }

    g3atmpncPncESIB	OBJECT-TYPE
        SYNTAX    DisplayString (SIZE (0..12))
        ACCESS    read-only
        STATUS    mandatory
        DESCRIPTION
            "An DisplayString Object that contains the hexidecimal value of the 
            ATM PNC location B ESI field (12 hexidecimal digits)."
        ::= { g3atmpncEntry 20 }

    g3atmpncPncSELB	OBJECT-TYPE
        SYNTAX    DisplayString (SIZE (0..2))
        ACCESS    read-only
        STATUS    mandatory
        DESCRIPTION
            "An DisplayString Object that contains the hexidecimal value of the 
            ATM PNC location B SEL field (2 hexidecimal digits)."
        ::= { g3atmpncEntry 21 }


    -- the g3pnchealth group

    g3pnchealthTage	OBJECT-TYPE
        SYNTAX    INTEGER
        ACCESS    read-only
        STATUS    mandatory
        DESCRIPTION
            "The number of timeticks since the pnc health data was last
            extracted from the switch by the G3 Proxy Agent. This object
            along with the g3pnchealthTintvl object allows the Network Manager
            to determine the validity of the pnc health data in the
            cache and to control when the proxy agent extracts the
            pnc health data from the switch."
        ::= { g3pnchealth 1 }

    g3pnchealthTintvl	OBJECT-TYPE
        SYNTAX    INTEGER
        ACCESS    read-write
        STATUS    mandatory
        DESCRIPTION
            "An object containing the interval for which the pnc health data
            extracted from the switch is considered valid by the proxy agent.
            When a GET or GET-NEXT request for pnc health objects is received by
            the agent it uses the g3pnchealthTage and g3pnchealthTintvl objects
            to determine whether it should refresh the cached pnchealthTable.
            If g3pnchealthTstmp + g3pnchealthTintvl is less than the current value
            of the sysUpTime object then the agent refreshes the pnchealthTable
            cache.  In either case it responds to the requests it receives
            with the data it currently has in the cache."
        ::= { g3pnchealth 2 }

    g3pnchealthTdelay	OBJECT-TYPE
        SYNTAX    INTEGER
        ACCESS    read-only
        STATUS    mandatory
        DESCRIPTION
            "An object containing the delay encountered in updating
            the cached data"
        ::= { g3pnchealth 3 }

    g3pnchealthTretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3pnchealth 4 }

    g3pnchealthSoftwreLck	OBJECT-TYPE
        SYNTAX    DisplayString (SIZE (0..4))
        ACCESS    read-only
        STATUS    mandatory
        DESCRIPTION
            "A DisplayString Object containing the Software Locked 
            status (yes or no)."
        ::= { g3pnchealth 5 }

    g3pnchealthStandbyBusd	OBJECT-TYPE
        SYNTAX    DisplayString (SIZE (0..4))
        ACCESS    read-only
        STATUS    mandatory
        DESCRIPTION
            "A DisplayString Object containing the Standby Busied
            status (yes or no)."
        ::= { g3pnchealth 6 }

    g3pnchealthStndbyRfsh	OBJECT-TYPE
        SYNTAX    DisplayString (SIZE (0..4))
        ACCESS    read-only
        STATUS    mandatory
        DESCRIPTION
            "A DisplayString Object containing the Standby Refresh
            status (yes or no)."
        ::= { g3pnchealth 7 }

    g3pnchealthIntchDisble	OBJECT-TYPE
        SYNTAX    DisplayString (SIZE (0..4))
        ACCESS    read-only
        STATUS    mandatory
        DESCRIPTION
            "A DisplayString Object containing the Interchange Disable
            status (yes or no)."
        ::= { g3pnchealth 8 }

    g3pnchealthPncAMode	OBJECT-TYPE
        SYNTAX    DisplayString (SIZE (0..7))
        ACCESS    read-only
        STATUS    mandatory
        DESCRIPTION
            "A DisplayString Object containing the current mode of 
            PNC A."
        ::= { g3pnchealth 9 }

    g3pnchealthPncBMode	OBJECT-TYPE
        SYNTAX    DisplayString (SIZE (0..7))
        ACCESS    read-only
        STATUS    mandatory
        DESCRIPTION
            "A DisplayString Object containing the current mode of 
            PNC B."
        ::= { g3pnchealth 10 }

    g3pnchealthPncAHealth	OBJECT-TYPE
        SYNTAX    DisplayString (SIZE (0..21))
        ACCESS    read-only
        STATUS    mandatory
        DESCRIPTION
            "A DisplayString Object containing the current state of health of
            PNC A."
        ::= { g3pnchealth 11 }

    g3pnchealthPncBHealth	OBJECT-TYPE
        SYNTAX    DisplayString (SIZE (0..21))
        ACCESS    read-only
        STATUS    mandatory
        DESCRIPTION
            "A DisplayString Object containing the current state of health of
            PNC B."
        ::= { g3pnchealth 12 }

    g3pnchealthPncAIntrIdx	OBJECT-TYPE
        SYNTAX    DisplayString (SIZE (0..15))
        ACCESS    read-only
        STATUS    mandatory
        DESCRIPTION
            "A DisplayString Object containing the current PN Interchange Index
            for PNC A."
        ::= { g3pnchealth 13 }

    g3pnchealthPncBIntrIdx	OBJECT-TYPE
        SYNTAX    DisplayString (SIZE (0..15))
        ACCESS    read-only
        STATUS    mandatory
        DESCRIPTION
            "A DisplayString Object containing the current PN Interchange Index
            for PNC B."
        ::= { g3pnchealth 14 }

    g3pnchealthPncAMajor	OBJECT-TYPE
        SYNTAX    Gauge
        ACCESS    read-only
        STATUS    mandatory
        DESCRIPTION
            "A Gauge object containing the number of logged major alarms
            for PNC A."
        ::= { g3pnchealth 15 }

    g3pnchealthPncBMajor	OBJECT-TYPE
        SYNTAX    Gauge
        ACCESS    read-only
        STATUS    mandatory
        DESCRIPTION
            "A Gauge object containing the number of logged major alarms
            for PNC B."
        ::= { g3pnchealth 16 }

    g3pnchealthPncAMinor	OBJECT-TYPE
        SYNTAX    Gauge
        ACCESS    read-only
        STATUS    mandatory
        DESCRIPTION
            "A Gauge object containing the number of logged minor alarms
            for PNC A."
        ::= { g3pnchealth 17 }

    g3pnchealthPncBMinor	OBJECT-TYPE
        SYNTAX    Gauge
        ACCESS    read-only
        STATUS    mandatory
        DESCRIPTION
            "A Gauge object containing the number of logged minor alarms
            for PNC B."
        ::= { g3pnchealth 18 }

    g3pnchealthPncAWarning	OBJECT-TYPE
        SYNTAX    Gauge
        ACCESS    read-only
        STATUS    mandatory
        DESCRIPTION
            "A Gauge object containing the number of logged warning alarms
            for PNC A."
        ::= { g3pnchealth 19 }

    g3pnchealthPncBWarning	OBJECT-TYPE
        SYNTAX    Gauge
        ACCESS    read-only
        STATUS    mandatory
        DESCRIPTION
            "A Gauge object containing the number of logged warning alarms
            for PNC B."
        ::= { g3pnchealth 20 }

    g3pnchealthPncASNIntrIdx	OBJECT-TYPE
        SYNTAX    DisplayString (SIZE (0..15))
        ACCESS    read-only
        STATUS    mandatory
        DESCRIPTION
            "A DisplayString Object containing the current SN Interchange Index
            for PNC A."
        ::= { g3pnchealth 21 }

    g3pnchealthPncBSNIntrIdx	OBJECT-TYPE
        SYNTAX    DisplayString (SIZE (0..15))
        ACCESS    read-only
        STATUS    mandatory
        DESCRIPTION
            "A DisplayString Object containing the current SN Interchange Index
            for PNC B."
        ::= { g3pnchealth 22 }


    -- the g3siggroup group

    g3siggroupTage	OBJECT-TYPE
        SYNTAX    INTEGER
        ACCESS    read-only
        STATUS    mandatory
        DESCRIPTION
            "The number of timeticks since the signaling group data was
            extracted from the switch by the G3 Proxy Agent. This object
            along with the g3siggroupTintvl object allows the Network Manager
            to determine the validity of the signaling group data in the
            cache and to control when the proxy agent extracts the
            signaling group data from the switch."
        ::= { g3siggroup 1 }

    g3siggroupTintvl	OBJECT-TYPE
        SYNTAX    INTEGER
        ACCESS    read-write
        STATUS    mandatory
        DESCRIPTION
            "An object containing the interval for which the signaling group
            data extracted from the switch is considered valid by the 
            proxy agent.  When a GET or GET-NEXT request for signaling group
            data objects is received by the agent it uses the g3siggroupTage 
            and g3siggroupTintvl objects to determine whether it should refresh 
            the cached siggroupTable.  If g3siggroupTstmp + g3siggroupTintvl
            is less than the current value of the sysUpTime object then the agent 
            refreshes the siggroupTable cache.  In either case it responds to the 
            requests it receives with the data it currently has in the cache."
        ::= { g3siggroup 2 }

    g3siggroupTdelay	OBJECT-TYPE
        SYNTAX    INTEGER
        ACCESS    read-only
        STATUS    mandatory
        DESCRIPTION
            "An object containing the delay encountered in updating
            the cached data"
        ::= { g3siggroup 3 }

    g3siggroupTretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3siggroup 4 }

    g3siggroupTcount	OBJECT-TYPE
        SYNTAX    Gauge
        ACCESS    read-only
        STATUS    mandatory
        DESCRIPTION
            "A Gauge object containing the number of data records in the
            cache."
        ::= { g3siggroup 5 }

    g3siggroupTable	OBJECT-TYPE
        SYNTAX    SEQUENCE OF G3siggroupEntry
        ACCESS    not-accessible
        STATUS    mandatory
        DESCRIPTION
            "A list of g3siggroup entries."
        ::= { g3siggroup 6 }

    g3siggroupEntry	OBJECT-TYPE
        SYNTAX    G3siggroupEntry
        ACCESS    not-accessible
        STATUS    mandatory
        DESCRIPTION
            "A g3siggroup entry containing objects of the
            g3siggroup information sent by the switch."
        INDEX    { g3siggroupGrpNbr }
        ::= { g3siggroupTable 1 }

    G3siggroupEntry ::= SEQUENCE {
        g3siggroupGrpNbr
            INTEGER,
        g3siggroupPriDChannel
            DisplayString,
        g3siggroupSecDChannel
            DisplayString,
        g3siggroupBoard1
            DisplayString,
        g3siggroupBoard2
            DisplayString,
        g3siggroupBoard3
            DisplayString,
        g3siggroupBoard4
            DisplayString,
        g3siggroupBoard5
            DisplayString,
        g3siggroupBoard6
            DisplayString,
        g3siggroupBoard7
            DisplayString,
        g3siggroupBoard8
            DisplayString,
        g3siggroupBoard9
            DisplayString,
        g3siggroupBoard10
            DisplayString,
        g3siggroupBoard11
            DisplayString,
        g3siggroupBoard12
            DisplayString,
        g3siggroupBoard13
            DisplayString,
        g3siggroupBoard14
            DisplayString,
        g3siggroupBoard15
            DisplayString,
        g3siggroupBoard16
            DisplayString,
        g3siggroupBoard17
            DisplayString,
        g3siggroupBoard18
            DisplayString,
        g3siggroupBoard19
            DisplayString,
        g3siggroupBoard20
            DisplayString,
        g3siggroupIntfNum1
            INTEGER,
        g3siggroupIntfNum2
            INTEGER,
        g3siggroupIntfNum3
            INTEGER,
        g3siggroupIntfNum4
            INTEGER,
        g3siggroupIntfNum5
            INTEGER,
        g3siggroupIntfNum6
            INTEGER,
        g3siggroupIntfNum7
            INTEGER,
        g3siggroupIntfNum8
            INTEGER,
        g3siggroupIntfNum9
            INTEGER,
        g3siggroupIntfNum10
            INTEGER,
        g3siggroupIntfNum11
            INTEGER,
        g3siggroupIntfNum12
            INTEGER,
        g3siggroupIntfNum13
            INTEGER,
        g3siggroupIntfNum14
            INTEGER,
        g3siggroupIntfNum15
            INTEGER,
        g3siggroupIntfNum16
            INTEGER,
        g3siggroupIntfNum17
            INTEGER,
        g3siggroupIntfNum18
            INTEGER,
        g3siggroupIntfNum19
            INTEGER,
        g3siggroupIntfNum20
            INTEGER,
        g3siggroupAsocSignal
            DisplayString
        }

    g3siggroupGrpNbr	OBJECT-TYPE
        SYNTAX    INTEGER
        ACCESS    read-only
        STATUS    mandatory
        DESCRIPTION
            "An INTEGER Object that uniquely identifies an administered
            Signaling Group."
        ::= { g3siggroupEntry 1 }

    g3siggroupPriDChannel	OBJECT-TYPE
        SYNTAX    DisplayString (SIZE (0..9))
        ACCESS    read-only
        STATUS    mandatory
        DESCRIPTION
            "A DisplayString Object that uniquely identifies the Primary D
            channel adminstered for this Signaling Group.  The syntax for the
            Primary D Channel is as follows: cabinet(01-44):carrier(A-E):slot(01-20)
            port(01-32)."
        ::= { g3siggroupEntry 2 }

    g3siggroupSecDChannel	OBJECT-TYPE
        SYNTAX    DisplayString (SIZE (0..9))
        ACCESS    read-only
        STATUS    mandatory
        DESCRIPTION
            "A DisplayString Object that uniquely identifies the Secondary D
            channel adminstered for this Signaling Group.  The syntax for the
            Secondary D Channel is as follows: cabinet(01-44):carrier(A-E):
            slot(01-20):port(01-32)."
        ::= { g3siggroupEntry 3 }

    g3siggroupBoard1	OBJECT-TYPE
        SYNTAX    DisplayString (SIZE (0..7))
        ACCESS    read-only
        STATUS    mandatory
        DESCRIPTION
            "A DisplayString Object that uniquely identifies a board based on
            its location in the system. The syntax for the Board Location is as
            follows: cabinet(01-44):carrier(A-E):slot(01-20)."
        ::= { g3siggroupEntry 4 }

    g3siggroupBoard2	OBJECT-TYPE
        SYNTAX    DisplayString (SIZE (0..7))
        ACCESS    read-only
        STATUS    mandatory
        DESCRIPTION
            "See DESCRIPTION of g3siggroupBoard1."
        ::= { g3siggroupEntry 5 }

    g3siggroupBoard3	OBJECT-TYPE
        SYNTAX    DisplayString (SIZE (0..7))
        ACCESS    read-only
        STATUS    mandatory
        DESCRIPTION
            "See DESCRIPTION of g3siggroupBoard1."
        ::= { g3siggroupEntry 6 }

    g3siggroupBoard4	OBJECT-TYPE
        SYNTAX    DisplayString (SIZE (0..7))
        ACCESS    read-only
        STATUS    mandatory
        DESCRIPTION
            "See DESCRIPTION of g3siggroupBoard1."
        ::= { g3siggroupEntry 7 }

    g3siggroupBoard5	OBJECT-TYPE
        SYNTAX    DisplayString (SIZE (0..7))
        ACCESS    read-only
        STATUS    mandatory
        DESCRIPTION
            "See DESCRIPTION of g3siggroupBoard1."
        ::= { g3siggroupEntry 8 }

    g3siggroupBoard6	OBJECT-TYPE
        SYNTAX    DisplayString (SIZE (0..7))
        ACCESS    read-only
        STATUS    mandatory
        DESCRIPTION
            "See DESCRIPTION of g3siggroupBoard1."
        ::= { g3siggroupEntry 9 }

    g3siggroupBoard7	OBJECT-TYPE
        SYNTAX    DisplayString (SIZE (0..7))
        ACCESS    read-only
        STATUS    mandatory
        DESCRIPTION
            "See DESCRIPTION of g3siggroupBoard1."
        ::= { g3siggroupEntry 10 }

    g3siggroupBoard8	OBJECT-TYPE
        SYNTAX    DisplayString (SIZE (0..7))
        ACCESS    read-only
        STATUS    mandatory
        DESCRIPTION
            "See DESCRIPTION of g3siggroupBoard1."
        ::= { g3siggroupEntry 11 }

    g3siggroupBoard9	OBJECT-TYPE
        SYNTAX    DisplayString (SIZE (0..7))
        ACCESS    read-only
        STATUS    mandatory
        DESCRIPTION
            "See DESCRIPTION of g3siggroupBoard1."
        ::= { g3siggroupEntry 12 }

    g3siggroupBoard10	OBJECT-TYPE
        SYNTAX    DisplayString (SIZE (0..7))
        ACCESS    read-only
        STATUS    mandatory
        DESCRIPTION
            "See DESCRIPTION of g3siggroupBoard1."
        ::= { g3siggroupEntry 13 }

    g3siggroupBoard11	OBJECT-TYPE
        SYNTAX    DisplayString (SIZE (0..7))
        ACCESS    read-only
        STATUS    mandatory
        DESCRIPTION
            "See DESCRIPTION of g3siggroupBoard1."
        ::= { g3siggroupEntry 14 }

    g3siggroupBoard12	OBJECT-TYPE
        SYNTAX    DisplayString (SIZE (0..7))
        ACCESS    read-only
        STATUS    mandatory
        DESCRIPTION
            "See DESCRIPTION of g3siggroupBoard1."
        ::= { g3siggroupEntry 15 }

    g3siggroupBoard13	OBJECT-TYPE
        SYNTAX    DisplayString (SIZE (0..7))
        ACCESS    read-only
        STATUS    mandatory
        DESCRIPTION
            "See DESCRIPTION of g3siggroupBoard1."
        ::= { g3siggroupEntry 16 }

    g3siggroupBoard14	OBJECT-TYPE
        SYNTAX    DisplayString (SIZE (0..7))
        ACCESS    read-only
        STATUS    mandatory
        DESCRIPTION
            "See DESCRIPTION of g3siggroupBoard1."
        ::= { g3siggroupEntry 17 }

    g3siggroupBoard15	OBJECT-TYPE
        SYNTAX    DisplayString (SIZE (0..7))
        ACCESS    read-only
        STATUS    mandatory
        DESCRIPTION
            "See DESCRIPTION of g3siggroupBoard1."
        ::= { g3siggroupEntry 18 }

    g3siggroupBoard16	OBJECT-TYPE
        SYNTAX    DisplayString (SIZE (0..7))
        ACCESS    read-only
        STATUS    mandatory
        DESCRIPTION
            "See DESCRIPTION of g3siggroupBoard1."
        ::= { g3siggroupEntry 19 }

    g3siggroupBoard17	OBJECT-TYPE
        SYNTAX    DisplayString (SIZE (0..7))
        ACCESS    read-only
        STATUS    mandatory
        DESCRIPTION
            "See DESCRIPTION of g3siggroupBoard1."
        ::= { g3siggroupEntry 20 }

    g3siggroupBoard18	OBJECT-TYPE
        SYNTAX    DisplayString (SIZE (0..7))
        ACCESS    read-only
        STATUS    mandatory
        DESCRIPTION
            "See DESCRIPTION of g3siggroupBoard1."
        ::= { g3siggroupEntry 21 }

    g3siggroupBoard19	OBJECT-TYPE
        SYNTAX    DisplayString (SIZE (0..7))
        ACCESS    read-only
        STATUS    mandatory
        DESCRIPTION
            "See DESCRIPTION of g3siggroupBoard1."
        ::= { g3siggroupEntry 22 }

    g3siggroupBoard20	OBJECT-TYPE
        SYNTAX    DisplayString (SIZE (0..7))
        ACCESS    read-only
        STATUS    mandatory
        DESCRIPTION
            "See DESCRIPTION of g3siggroupBoard1."
        ::= { g3siggroupEntry 23 }

    g3siggroupIntfNum1	OBJECT-TYPE
        SYNTAX    INTEGER
        ACCESS    read-only
        STATUS    mandatory
        DESCRIPTION
            "An INTEGER object containing the Signaling Group Interface
            Number using this board."
        ::= { g3siggroupEntry 24 }

    g3siggroupIntfNum2	OBJECT-TYPE
        SYNTAX    INTEGER
        ACCESS    read-only
        STATUS    mandatory
        DESCRIPTION
            "See DESCRIPTION of g3siggroupIntfNum1."
        ::= { g3siggroupEntry 25 }

    g3siggroupIntfNum3	OBJECT-TYPE
        SYNTAX    INTEGER
        ACCESS    read-only
        STATUS    mandatory
        DESCRIPTION
            "See DESCRIPTION of g3siggroupIntfNum1."
        ::= { g3siggroupEntry 26 }

    g3siggroupIntfNum4	OBJECT-TYPE
        SYNTAX    INTEGER
        ACCESS    read-only
        STATUS    mandatory
        DESCRIPTION
            "See DESCRIPTION of g3siggroupIntfNum1."
        ::= { g3siggroupEntry 27 }

    g3siggroupIntfNum5	OBJECT-TYPE
        SYNTAX    INTEGER
        ACCESS    read-only
        STATUS    mandatory
        DESCRIPTION
            "See DESCRIPTION of g3siggroupIntfNum1."
        ::= { g3siggroupEntry 28 }

    g3siggroupIntfNum6	OBJECT-TYPE
        SYNTAX    INTEGER
        ACCESS    read-only
        STATUS    mandatory
        DESCRIPTION
            "See DESCRIPTION of g3siggroupIntfNum1."
        ::= { g3siggroupEntry 29 }

    g3siggroupIntfNum7	OBJECT-TYPE
        SYNTAX    INTEGER
        ACCESS    read-only
        STATUS    mandatory
        DESCRIPTION
            "See DESCRIPTION of g3siggroupIntfNum1."
        ::= { g3siggroupEntry 30 }

    g3siggroupIntfNum8	OBJECT-TYPE
        SYNTAX    INTEGER
        ACCESS    read-only
        STATUS    mandatory
        DESCRIPTION
            "See DESCRIPTION of g3siggroupIntfNum1."
        ::= { g3siggroupEntry 31 }

    g3siggroupIntfNum9	OBJECT-TYPE
        SYNTAX    INTEGER
        ACCESS    read-only
        STATUS    mandatory
        DESCRIPTION
            "See DESCRIPTION of g3siggroupIntfNum1."
        ::= { g3siggroupEntry 32 }

    g3siggroupIntfNum10	OBJECT-TYPE
        SYNTAX    INTEGER
        ACCESS    read-only
        STATUS    mandatory
        DESCRIPTION
            "See DESCRIPTION of g3siggroupIntfNum1."
        ::= { g3siggroupEntry 33 }

    g3siggroupIntfNum11	OBJECT-TYPE
        SYNTAX    INTEGER
        ACCESS    read-only
        STATUS    mandatory
        DESCRIPTION
            "See DESCRIPTION of g3siggroupIntfNum1."
        ::= { g3siggroupEntry 34 }

    g3siggroupIntfNum12	OBJECT-TYPE
        SYNTAX    INTEGER
        ACCESS    read-only
        STATUS    mandatory
        DESCRIPTION
            "See DESCRIPTION of g3siggroupIntfNum1."
        ::= { g3siggroupEntry 35 }

    g3siggroupIntfNum13	OBJECT-TYPE
        SYNTAX    INTEGER
        ACCESS    read-only
        STATUS    mandatory
        DESCRIPTION
            "See DESCRIPTION of g3siggroupIntfNum1."
        ::= { g3siggroupEntry 36 }

    g3siggroupIntfNum14	OBJECT-TYPE
        SYNTAX    INTEGER
        ACCESS    read-only
        STATUS    mandatory
        DESCRIPTION
            "See DESCRIPTION of g3siggroupIntfNum1."
        ::= { g3siggroupEntry 37 }

    g3siggroupIntfNum15	OBJECT-TYPE
        SYNTAX    INTEGER
        ACCESS    read-only
        STATUS    mandatory
        DESCRIPTION
            "See DESCRIPTION of g3siggroupIntfNum1."
        ::= { g3siggroupEntry 38 }

    g3siggroupIntfNum16	OBJECT-TYPE
        SYNTAX    INTEGER
        ACCESS    read-only
        STATUS    mandatory
        DESCRIPTION
            "See DESCRIPTION of g3siggroupIntfNum1."
        ::= { g3siggroupEntry 39 }

    g3siggroupIntfNum17	OBJECT-TYPE
        SYNTAX    INTEGER
        ACCESS    read-only
        STATUS    mandatory
        DESCRIPTION
            "See DESCRIPTION of g3siggroupIntfNum1."
        ::= { g3siggroupEntry 40 }

    g3siggroupIntfNum18	OBJECT-TYPE
        SYNTAX    INTEGER
        ACCESS    read-only
        STATUS    mandatory
        DESCRIPTION
            "See DESCRIPTION of g3siggroupIntfNum1."
        ::= { g3siggroupEntry 41 }

    g3siggroupIntfNum19	OBJECT-TYPE
        SYNTAX    INTEGER
        ACCESS    read-only
        STATUS    mandatory
        DESCRIPTION
            "See DESCRIPTION of g3siggroupIntfNum1."
        ::= { g3siggroupEntry 42 }

    g3siggroupIntfNum20	OBJECT-TYPE
        SYNTAX    INTEGER
        ACCESS    read-only
        STATUS    mandatory
        DESCRIPTION
            "See DESCRIPTION of g3siggroupIntfNum1."
        ::= { g3siggroupEntry 43 }

    g3siggroupAsocSignal	OBJECT-TYPE
        SYNTAX    DisplayString (SIZE (0..2))
        ACCESS    read-only
        STATUS    mandatory
        DESCRIPTION
            "A DisplayString Object containing the Associated Signaling
            status (y or n)."
        ::= { g3siggroupEntry 44 }


    -- the g3restart group

    g3restartTage	OBJECT-TYPE
        SYNTAX    INTEGER
        ACCESS    read-only
        STATUS    mandatory
        DESCRIPTION
            "The number of timeticks since the system restart data was
            extracted from the switch by the G3 Proxy Agent. This object
            along with the g3restartTintvl object allows the Network Manager
            to determine the validity of the system restart data in the
            cache and to control when the proxy agent extracts the
            system restart data from the switch."
        ::= { g3restart 1 }

    g3restartTintvl	OBJECT-TYPE
        SYNTAX    INTEGER
        ACCESS    read-write
        STATUS    mandatory
        DESCRIPTION
            "An object containing the interval for which the system restart
            data extracted from the switch is considered valid by the 
            proxy agent.  When a GET or GET-NEXT request for system restart
            data objects is received by the agent it uses the g3restartTage 
            and g3restartTintvl objects to determine whether it should refresh 
            the cached restartTable.  If g3restartTstmp + g3restartTintvl
            is less than the current value of the sysUpTime object then the agent 
            refreshes the restartTable cache.  In either case it responds to the 
            requests it receives with the data it currently has in the cache."
        ::= { g3restart 2 }

    g3restartTdelay	OBJECT-TYPE
        SYNTAX    INTEGER
        ACCESS    read-only
        STATUS    mandatory
        DESCRIPTION
            "An object containing the delay encountered in updating
            the cached data."
        ::= { g3restart 3 }

    g3restartTretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3restart 4 }

    g3restartTcount	OBJECT-TYPE
        SYNTAX    Gauge
        ACCESS    read-only
        STATUS    mandatory
        DESCRIPTION
            "A Gauge object containing the number of data records in the
            cache."
        ::= { g3restart 5 }

    g3restartTable	OBJECT-TYPE
        SYNTAX    SEQUENCE OF G3restartEntry
        ACCESS    not-accessible
        STATUS    mandatory
        DESCRIPTION
            "A list of g3restart entries."
        ::= { g3restart 6 }

    g3restartEntry	OBJECT-TYPE
        SYNTAX    G3restartEntry
        ACCESS    not-accessible
        STATUS    mandatory
        DESCRIPTION
            "A g3restart entry containing objects of the
            g3restart information sent by the switch."
        INDEX    { g3restartMonth, g3restartDay, g3restartHour, g3restartMinute, g3restartIndex }
        ::= { g3restartTable 1 }

    G3restartEntry ::= SEQUENCE {
        g3restartMonth
            INTEGER,
        g3restartDay
            INTEGER,
        g3restartHour
            INTEGER,
        g3restartMinute
            INTEGER,
        g3restartDateTime
            DisplayString,
        g3restartLevel
            DisplayString,
        g3restartCarrier
            DisplayString,
        g3restartCraftDemand
            DisplayString,
        g3restartEscalated
            DisplayString,
        g3restartInterchange
            DisplayString,
        g3restartUnavailable
            DisplayString,
        g3restartCause
            DisplayString,
        g3restartIndex
            INTEGER
        }

    g3restartMonth	OBJECT-TYPE
        SYNTAX    INTEGER
        ACCESS    read-only
        STATUS    mandatory
        DESCRIPTION
            "An INTEGER Object that uniquely identifies the Month (01-12) in 
            which a system restart occurred."
        ::= { g3restartEntry 1 }

    g3restartDay	OBJECT-TYPE
        SYNTAX    INTEGER
        ACCESS    read-only
        STATUS    mandatory
        DESCRIPTION
            "An INTEGER Object that uniquely identifies the Day (01-31) in 
            which a system restart occurred."
        ::= { g3restartEntry 2 }

    g3restartHour	OBJECT-TYPE
        SYNTAX    INTEGER
        ACCESS    read-only
        STATUS    mandatory
        DESCRIPTION
            "An INTEGER Object that uniquely identifies the Hour (00-23) in 
            which a system restart occurred."
        ::= { g3restartEntry 3 }

    g3restartMinute	OBJECT-TYPE
        SYNTAX    INTEGER
        ACCESS    read-only
        STATUS    mandatory
        DESCRIPTION
            "An INTEGER Object that uniquely identifies the Minute (00-59) in 
            which a system restart occurred."
        ::= { g3restartEntry 4 }

    g3restartDateTime	OBJECT-TYPE
        SYNTAX    DisplayString (SIZE (0..12))
        ACCESS    read-only
        STATUS    mandatory
        DESCRIPTION
            "A DisplayString object containing the date and time (of the form
            MM/DD HH:MM) in which a system restart occurred."
        ::= { g3restartEntry 5 }

    g3restartLevel	OBJECT-TYPE
        SYNTAX    DisplayString (SIZE (0..10))
        ACCESS    read-only
        STATUS    mandatory
        DESCRIPTION
            "A DisplayString object containing the level of the restart (WARM, 
            COLD1, COLD2, REBOOT, or XREBOOT)."
        ::= { g3restartEntry 6 }

    g3restartCarrier	OBJECT-TYPE
        SYNTAX    DisplayString (SIZE (0..10))
        ACCESS    read-only
        STATUS    mandatory
        DESCRIPTION
            "A DisplayString object containing the carrier (A or B) on which
            the restart occurred."
        ::= { g3restartEntry 7 }

    g3restartCraftDemand	OBJECT-TYPE
        SYNTAX    DisplayString (SIZE (0..20))
        ACCESS    read-only
        STATUS    mandatory
        DESCRIPTION
            "A DisplayString object containing a flag (Y or N) indicating
            whether or not the restart was craft demanded."
        ::= { g3restartEntry 8 }

    g3restartEscalated	OBJECT-TYPE
        SYNTAX    DisplayString (SIZE (0..3))
        ACCESS    read-only
        STATUS    mandatory
        DESCRIPTION
            "A DisplayString object containing a flag (Y or N) indicating
            whether or not the restart was escalated."
        ::= { g3restartEntry 9 }

    g3restartInterchange	OBJECT-TYPE
        SYNTAX    DisplayString (SIZE (0..10))
        ACCESS    read-only
        STATUS    mandatory
        DESCRIPTION
            "A DisplayString object containing a flag (Y or N) indicating
            whether or not an interchange took place."
        ::= { g3restartEntry 10 }

    g3restartUnavailable	OBJECT-TYPE
        SYNTAX    DisplayString (SIZE (0..10))
        ACCESS    read-only
        STATUS    mandatory
        DESCRIPTION
            "A DisplayString object containing the amount of time (of the form
            HH:MM:SS) the system was unavailable due to the restart."
        ::= { g3restartEntry 11 }

    g3restartCause	OBJECT-TYPE
        SYNTAX    DisplayString (SIZE (0..20))
        ACCESS    read-only
        STATUS    mandatory
        DESCRIPTION
            "A DisplayString object containing the cause of the system restart."
        ::= { g3restartEntry 12 }

    g3restartIndex	OBJECT-TYPE
        SYNTAX    INTEGER
        ACCESS    read-only
        STATUS    mandatory
        DESCRIPTION
            "An INTEGER Object that provides a secondary key for multiple
            restarts occurring in the same minute."
        ::= { g3restartEntry 13 }


    -- the g3fiberlink group

    g3fiberlinkTage	OBJECT-TYPE
        SYNTAX    INTEGER
        ACCESS    read-only
        STATUS    mandatory
        DESCRIPTION
            "The number of timeticks since the fiberlink data was
            extracted from the switch by the G3 Proxy Agent. This object
            along with the g3fiberlinkTintvl object allows the Network Manager
            to determine the validity of the fiberlink data in the
            cache and to control when the proxy agent extracts the
            fiberlink data from the switch."
        ::= { g3fiberlink 1 }

    g3fiberlinkTintvl	OBJECT-TYPE
        SYNTAX    INTEGER
        ACCESS    read-write
        STATUS    mandatory
        DESCRIPTION
            "An object containing the interval for which the fiberlink data extracted 
            from	the switch is considered valid by the proxy agent.  When a GET or
            GET-NEXT request for fiberlink data objects is received by the agent it 
            uses	the g3fiberlinkTage and g3fiberlinkTintvl objects to determine
            whether it should refresh the cached fiberlinkTable.  If
            g3fiberlinkTstmp + g3fiberlinkTintvl is less than the current
            value of the sysUpTime object then the agent refreshes the
            fiberlinkTable cache.  In either case it responds to the 
            requests it receives with the data it currently has in the cache."
        ::= { g3fiberlink 2 }

    g3fiberlinkTdelay	OBJECT-TYPE
        SYNTAX    INTEGER
        ACCESS    read-only
        STATUS    mandatory
        DESCRIPTION
            "An object containing the delay encountered in updating
            the cached data"
        ::= { g3fiberlink 3 }

    g3fiberlinkTretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3fiberlink 4 }

    g3fiberlinkTcount	OBJECT-TYPE
        SYNTAX    Gauge
        ACCESS    read-only
        STATUS    mandatory
        DESCRIPTION
            "A Gauge object containing the number of data records in the cache."
        ::= { g3fiberlink 5 }

    g3fiberlinkTable	OBJECT-TYPE
        SYNTAX    SEQUENCE OF G3fiberlinkEntry
        ACCESS    not-accessible
        STATUS    mandatory
        DESCRIPTION
            "A list of g3fiberlink entries."
        ::= { g3fiberlink 6 }

    g3fiberlinkEntry	OBJECT-TYPE
        SYNTAX    G3fiberlinkEntry
        ACCESS    not-accessible
        STATUS    mandatory
        DESCRIPTION
            "A g3fiberlink entry containing objects of the
            g3fiberlink information sent by the switch."
        INDEX    { g3fiberlinkFLNumber }
        ::= { g3fiberlinkTable 1 }

    G3fiberlinkEntry ::= SEQUENCE {
        g3fiberlinkFLNumber
            INTEGER,
        g3fiberlinkDS1Type
            DisplayString,
        g3fiberlinkE1Type
            DisplayString,
        g3fiberlinkE2Type
            DisplayString,
        g3fiberlinkE1ABoard
            DisplayString,
        g3fiberlinkE2ABoard
            DisplayString,
        g3fiberlinkE1BBoard
            DisplayString,
        g3fiberlinkE2BBoard
            DisplayString,
        g3fiberlinkE1ADs1Board
            DisplayString,
        g3fiberlinkE2ADs1Board
            DisplayString,
        g3fiberlinkE1BDs1Board
            DisplayString,
        g3fiberlinkE2BDs1Board
            DisplayString
        }

    g3fiberlinkFLNumber	OBJECT-TYPE
        SYNTAX    INTEGER
        ACCESS    read-only
        STATUS    mandatory
        DESCRIPTION
            "An INTEGER Object that uniquely identifies an administered
            Fiber Link."
        ::= { g3fiberlinkEntry 1 }

    g3fiberlinkDS1Type	OBJECT-TYPE
        SYNTAX    DisplayString (SIZE (0..6))
        ACCESS    read-only
        STATUS    mandatory
        DESCRIPTION
            "A DisplayString Object that identifies the type of DS1 Converter
            board used if a DS1 converter is used (TNXXXX)."
        ::= { g3fiberlinkEntry 2 }

    g3fiberlinkE1Type	OBJECT-TYPE
        SYNTAX    DisplayString (SIZE (0..3))
        ACCESS    read-only
        STATUS    mandatory
        DESCRIPTION
            "A DisplayString Object that identifies the type of the Endpoint
            for Endpoint 1 (sni or ei)."
        ::= { g3fiberlinkEntry 3 }

    g3fiberlinkE2Type	OBJECT-TYPE
        SYNTAX    DisplayString (SIZE (0..3))
        ACCESS    read-only
        STATUS    mandatory
        DESCRIPTION
            "A DisplayString Object that identifies the type of the Endpoint
            for Endpoint 1 (sni or ei)."
        ::= { g3fiberlinkEntry 4 }

    g3fiberlinkE1ABoard	OBJECT-TYPE
        SYNTAX    DisplayString (SIZE (0..5))
        ACCESS    read-only
        STATUS    mandatory
        DESCRIPTION
            "A DisplayString Object that uniquely identifies the Endpoint 1
            A-PNC SNI or EI board based on its location in the system. The
            syntax for the Board Location is as follows:
            cabinet(01-44):carrier(A-E):slot(01-20)."
        ::= { g3fiberlinkEntry 5 }

    g3fiberlinkE2ABoard	OBJECT-TYPE
        SYNTAX    DisplayString (SIZE (0..5))
        ACCESS    read-only
        STATUS    mandatory
        DESCRIPTION
            "A DisplayString Object that uniquely identifies the Endpoint 2
            A-PNC SNI or EI board based on its location in the system. The
            syntax for the Board Location is as follows:
            cabinet(01-44):carrier(A-E):slot(01-20)."
        ::= { g3fiberlinkEntry 6 }

    g3fiberlinkE1BBoard	OBJECT-TYPE
        SYNTAX    DisplayString (SIZE (0..5))
        ACCESS    read-only
        STATUS    mandatory
        DESCRIPTION
            "A DisplayString Object that uniquely identifies the Endpoint 1
            B-PNC SNI or EI board based on its location in the system. The
            syntax for the Board Location is as follows:
            cabinet(01-44):carrier(A-E):slot(01-20)."
        ::= { g3fiberlinkEntry 7 }

    g3fiberlinkE2BBoard	OBJECT-TYPE
        SYNTAX    DisplayString (SIZE (0..5))
        ACCESS    read-only
        STATUS    mandatory
        DESCRIPTION
            "A DisplayString Object that uniquely identifies the Endpoint 2
            B-PNC SNI or EI board based on its location in the system. The
            syntax for the Board Location is as follows:
            cabinet(01-44):carrier(A-E):slot(01-20)."
        ::= { g3fiberlinkEntry 8 }

    g3fiberlinkE1ADs1Board	OBJECT-TYPE
        SYNTAX    DisplayString (SIZE (0..5))
        ACCESS    read-only
        STATUS    mandatory
        DESCRIPTION
            "A DisplayString Object that uniquely identifies the Endpoint 1
            A-PNC DS1 board based on its location in the system. The
            syntax for the Board Location is as follows:
            cabinet(01-44):carrier(A-E):slot(01-20)."
        ::= { g3fiberlinkEntry 9 }

    g3fiberlinkE2ADs1Board	OBJECT-TYPE
        SYNTAX    DisplayString (SIZE (0..5))
        ACCESS    read-only
        STATUS    mandatory
        DESCRIPTION
            "A DisplayString Object that uniquely identifies the Endpoint 2
            A-PNC DS1 board based on its location in the system. The
            syntax for the Board Location is as follows:
            cabinet(01-44):carrier(A-E):slot(01-20)."
        ::= { g3fiberlinkEntry 10 }

    g3fiberlinkE1BDs1Board	OBJECT-TYPE
        SYNTAX    DisplayString (SIZE (0..5))
        ACCESS    read-only
        STATUS    mandatory
        DESCRIPTION
            "A DisplayString Object that uniquely identifies the Endpoint 1
            B-PNC DS1 board based on its location in the system. The
            syntax for the Board Location is as follows:
            cabinet(01-44):carrier(A-E):slot(01-20)."
        ::= { g3fiberlinkEntry 11 }

    g3fiberlinkE2BDs1Board	OBJECT-TYPE
        SYNTAX    DisplayString (SIZE (0..5))
        ACCESS    read-only
        STATUS    mandatory
        DESCRIPTION
            "A DisplayString Object that uniquely identifies the Endpoint 2
            B-PNC DS1 board based on its location in the system. The
            syntax for the Board Location is as follows:
            cabinet(01-44):carrier(A-E):slot(01-20)."
        ::= { g3fiberlinkEntry 12 }


    -- the g3routepattern group

    g3routepatternTage	OBJECT-TYPE
        SYNTAX    INTEGER
        ACCESS    read-only
        STATUS    mandatory
        DESCRIPTION
            "The number of timeticks since the routepattern data was
            extracted from the switch by the G3 Proxy Agent. This object
            along with the g3routepatternTintvl object allows the Network Manager
            to determine the validity of the routepattern data in the
            cache and to control when the proxy agent extracts the
            routepattern data from the switch."
        ::= { g3routepattern 1 }

    g3routepatternTintvl	OBJECT-TYPE
        SYNTAX    INTEGER
        ACCESS    read-write
        STATUS    mandatory
        DESCRIPTION
            "An object containing the interval for which the routepattern data 
            extracted from	the switch is considered valid by the proxy agent.  When 
            a GET or	GET-NEXT request for routepattern data objects is received by 
            the agent it uses	the g3routepatternTage and g3routepatternTintvl objects 
            to determine	whether it should refresh the cached routepatternTable.  
            If	g3routepatternTstmp + g3routepatternTintvl is less than the current
            value of the sysUpTime object then the agent refreshes the
            routepatternTable cache.  In either case it responds to the 
            requests it receives with the data it currently has in the cache."
        ::= { g3routepattern 2 }

    g3routepatternTdelay	OBJECT-TYPE
        SYNTAX    INTEGER
        ACCESS    read-only
        STATUS    mandatory
        DESCRIPTION
            "An object containing the delay encountered in updating
            the cached data"
        ::= { g3routepattern 3 }

    g3routepatternTretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3routepattern 4 }

    g3routepatternTcount	OBJECT-TYPE
        SYNTAX    Gauge
        ACCESS    read-only
        STATUS    mandatory
        DESCRIPTION
            "A Gauge object containing the number of data records in the cache."
        ::= { g3routepattern 5 }

    g3routepatternTable	OBJECT-TYPE
        SYNTAX    SEQUENCE OF G3routepatternEntry
        ACCESS    not-accessible
        STATUS    mandatory
        DESCRIPTION
            "A list of g3routepattern entries."
        ::= { g3routepattern 6 }

    g3routepatternEntry	OBJECT-TYPE
        SYNTAX    G3routepatternEntry
        ACCESS    not-accessible
        STATUS    mandatory
        DESCRIPTION
            "A g3routepattern entry containing objects of the
            g3routepattern information sent by the switch."
        INDEX    { g3routepatternRPNumber }
        ::= { g3routepatternTable 1 }

    G3routepatternEntry ::= SEQUENCE {
        g3routepatternRPNumber
            INTEGER,
        g3routepatternTGNumber1
            INTEGER,
        g3routepatternTGNumber2
            INTEGER,
        g3routepatternTGNumber3
            INTEGER,
        g3routepatternTGNumber4
            INTEGER,
        g3routepatternTGNumber5
            INTEGER,
        g3routepatternTGNumber6
            INTEGER,
        g3routepatternTGNumber7
            INTEGER,
        g3routepatternTGNumber8
            INTEGER,
        g3routepatternTGNumber9
            INTEGER,
        g3routepatternTGNumber10
            INTEGER,
        g3routepatternTGNumber11
            INTEGER,
        g3routepatternTGNumber12
            INTEGER,
        g3routepatternTGNumber13
            INTEGER,
        g3routepatternTGNumber14
            INTEGER,
        g3routepatternTGNumber15
            INTEGER,
        g3routepatternTGNumber16
            INTEGER
        }

    g3routepatternRPNumber	OBJECT-TYPE
        SYNTAX    INTEGER
        ACCESS    read-only
        STATUS    mandatory
        DESCRIPTION
            "An INTEGER Object that uniquely identifies an administered
            Route Pattern."
        ::= { g3routepatternEntry 1 }

    g3routepatternTGNumber1	OBJECT-TYPE
        SYNTAX    INTEGER
        ACCESS    read-only
        STATUS    mandatory
        DESCRIPTION
            "An INTEGER Object that uniquely identifies the trunk group
            associated with group number 1."
        ::= { g3routepatternEntry 2 }

    g3routepatternTGNumber2	OBJECT-TYPE
        SYNTAX    INTEGER
        ACCESS    read-only
        STATUS    mandatory
        DESCRIPTION
            "An INTEGER Object that uniquely identifies the trunk group
            associated with group number 2."
        ::= { g3routepatternEntry 3 }

    g3routepatternTGNumber3	OBJECT-TYPE
        SYNTAX    INTEGER
        ACCESS    read-only
        STATUS    mandatory
        DESCRIPTION
            "An INTEGER Object that uniquely identifies the trunk group
            associated with group number 3."
        ::= { g3routepatternEntry 4 }

    g3routepatternTGNumber4	OBJECT-TYPE
        SYNTAX    INTEGER
        ACCESS    read-only
        STATUS    mandatory
        DESCRIPTION
            "An INTEGER Object that uniquely identifies the trunk group
            associated with group number 4."
        ::= { g3routepatternEntry 5 }

    g3routepatternTGNumber5	OBJECT-TYPE
        SYNTAX    INTEGER
        ACCESS    read-only
        STATUS    mandatory
        DESCRIPTION
            "An INTEGER Object that uniquely identifies the trunk group
            associated with group number 5."
        ::= { g3routepatternEntry 6 }

    g3routepatternTGNumber6	OBJECT-TYPE
        SYNTAX    INTEGER
        ACCESS    read-only
        STATUS    mandatory
        DESCRIPTION
            "An INTEGER Object that uniquely identifies the trunk group
            associated with group number 6."
        ::= { g3routepatternEntry 7 }

    g3routepatternTGNumber7	OBJECT-TYPE
        SYNTAX    INTEGER
        ACCESS    read-only
        STATUS    mandatory
        DESCRIPTION
            "An INTEGER Object that uniquely identifies the trunk group
            associated with group number 7."
        ::= { g3routepatternEntry 8 }

    g3routepatternTGNumber8	OBJECT-TYPE
        SYNTAX    INTEGER
        ACCESS    read-only
        STATUS    mandatory
        DESCRIPTION
            "An INTEGER Object that uniquely identifies the trunk group
            associated with group number 8."
        ::= { g3routepatternEntry 9 }

    g3routepatternTGNumber9	OBJECT-TYPE
        SYNTAX    INTEGER
        ACCESS    read-only
        STATUS    mandatory
        DESCRIPTION
            "An INTEGER Object that uniquely identifies the trunk group
            associated with group number 9."
        ::= { g3routepatternEntry 10 }

    g3routepatternTGNumber10	OBJECT-TYPE
        SYNTAX    INTEGER
        ACCESS    read-only
        STATUS    mandatory
        DESCRIPTION
            "An INTEGER Object that uniquely identifies the trunk group
            associated with group number 10."
        ::= { g3routepatternEntry 11 }

    g3routepatternTGNumber11	OBJECT-TYPE
        SYNTAX    INTEGER
        ACCESS    read-only
        STATUS    mandatory
        DESCRIPTION
            "An INTEGER Object that uniquely identifies the trunk group
            associated with group number 11."
        ::= { g3routepatternEntry 12 }

    g3routepatternTGNumber12	OBJECT-TYPE
        SYNTAX    INTEGER
        ACCESS    read-only
        STATUS    mandatory
        DESCRIPTION
            "An INTEGER Object that uniquely identifies the trunk group
            associated with group number 12."
        ::= { g3routepatternEntry 13 }

    g3routepatternTGNumber13	OBJECT-TYPE
        SYNTAX    INTEGER
        ACCESS    read-only
        STATUS    mandatory
        DESCRIPTION
            "An INTEGER Object that uniquely identifies the trunk group
            associated with group number 13."
        ::= { g3routepatternEntry 14 }

    g3routepatternTGNumber14	OBJECT-TYPE
        SYNTAX    INTEGER
        ACCESS    read-only
        STATUS    mandatory
        DESCRIPTION
            "An INTEGER Object that uniquely identifies the trunk group
            associated with group number 14."
        ::= { g3routepatternEntry 15 }

    g3routepatternTGNumber15	OBJECT-TYPE
        SYNTAX    INTEGER
        ACCESS    read-only
        STATUS    mandatory
        DESCRIPTION
            "An INTEGER Object that uniquely identifies the trunk group
            associated with group number 15."
        ::= { g3routepatternEntry 16 }

    g3routepatternTGNumber16	OBJECT-TYPE
        SYNTAX    INTEGER
        ACCESS    read-only
        STATUS    mandatory
        DESCRIPTION
            "An INTEGER Object that uniquely identifies the trunk group
            associated with group number 16."
        ::= { g3routepatternEntry 17 }


    -- the g3trunkcfg group

    g3trunkcfgTage	OBJECT-TYPE
        SYNTAX    INTEGER
        ACCESS    read-only
        STATUS    mandatory
        DESCRIPTION
            "The number of timeticks since the trunk config data was
            extracted from the switch by the G3 Proxy Agent. This object
            along with the g3trunkcfgTintvl object allows the Network Manager
            to determine the validity of the trunk config  data in the
            cache and to control when the proxy agent extracts the
            trunk config data from the switch."
        ::= { g3trunkcfg 1 }

    g3trunkcfgTintvl	OBJECT-TYPE
        SYNTAX    INTEGER
        ACCESS    read-write
        STATUS    mandatory
        DESCRIPTION
            "An object containing the interval for which the trunk config data 
            extracted from the switch is considered valid by the proxy agent.  When a  
            GET or GET-NEXT request for trunk config data objects is received by the 
            agent it uses the g3trunkcfgTage and g3trunkcfgTintvl objects to determine
            whether it should refresh the cached trunkcfgTable.  If
            g3trunkcfgTstmp + g3trunkcfgTintvl is less than the current
            value of the sysUpTime object then the agent refreshes the
            trunkcfgTable cache.  In either case it responds to the 
            requests it receives with the data it currently has in the cache."
        ::= { g3trunkcfg 2 }

    g3trunkcfgTdelay	OBJECT-TYPE
        SYNTAX    INTEGER
        ACCESS    read-only
        STATUS    mandatory
        DESCRIPTION
            "An object containing the delay encountered in updating
            the cached data"
        ::= { g3trunkcfg 3 }

    g3trunkcfgTretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3trunkcfg 4 }

    g3trunkcfgTcount	OBJECT-TYPE
        SYNTAX    Gauge
        ACCESS    read-only
        STATUS    mandatory
        DESCRIPTION
            "A Gauge object containing the number of data records in the cache."
        ::= { g3trunkcfg 5 }

    g3trunkcfgTable	OBJECT-TYPE
        SYNTAX    SEQUENCE OF G3trunkcfgEntry
        ACCESS    not-accessible
        STATUS    mandatory
        DESCRIPTION
            "A list of g3trunkcfg entries."
        ::= { g3trunkcfg 6 }

    g3trunkcfgEntry	OBJECT-TYPE
        SYNTAX    G3trunkcfgEntry
        ACCESS    not-accessible
        STATUS    mandatory
        DESCRIPTION
            "A g3trunkcfg entry containing objects of the
            g3trunkcfg information sent by the switch."
        INDEX    { g3trunkcfgBoardNum }
        ::= { g3trunkcfgTable 1 }

    G3trunkcfgEntry ::= SEQUENCE {
        g3trunkcfgBoardNum
            DisplayString,
        g3trunkcfgBoardType
            DisplayString,
        g3trunkcfgCode
            DisplayString,
        g3trunkcfgVintage
            DisplayString,
        g3trunkcfgSuffix
            DisplayString
        }

    g3trunkcfgBoardNum	OBJECT-TYPE
        SYNTAX    DisplayString (SIZE (0..7))
        ACCESS    read-only
        STATUS    mandatory
        DESCRIPTION
            "A DisplayString Object that uniquely identifies a trunk board based
            on its location in the system. The syntax for the Board Number is as
            follows: cabinet(01-44):carrier(A-E):slot(01-20)."
        ::= { g3trunkcfgEntry 1 }

    g3trunkcfgBoardType	OBJECT-TYPE
        SYNTAX    DisplayString (SIZE (0..19))
        ACCESS    read-only
        STATUS    mandatory
        DESCRIPTION
            "A DisplayString Object that contains a text description of the
            type of trunk board."
        ::= { g3trunkcfgEntry 2 }

    g3trunkcfgCode	OBJECT-TYPE
        SYNTAX    DisplayString (SIZE (0..8))
        ACCESS    read-only
        STATUS    mandatory
        DESCRIPTION
            "A DisplayString Object that contains the code that defines the
            type of trunk board."
        ::= { g3trunkcfgEntry 3 }

    g3trunkcfgVintage	OBJECT-TYPE
        SYNTAX    DisplayString (SIZE (0..10))
        ACCESS    read-only
        STATUS    mandatory
        DESCRIPTION
            "A DisplayString Object that contains the vintage of the trunk board."
        ::= { g3trunkcfgEntry 4 }

    g3trunkcfgSuffix	OBJECT-TYPE
        SYNTAX    DisplayString (SIZE (0..2))
        ACCESS    read-only
        STATUS    mandatory
        DESCRIPTION
            "A DisplayString Object that contains the suffix to the code"
        ::= { g3trunkcfgEntry 5 }


    -- the g3stationcfg group

    g3stationcfgTage	OBJECT-TYPE
        SYNTAX    INTEGER
        ACCESS    read-only
        STATUS    mandatory
        DESCRIPTION
            "The number of timeticks since the station config data was
            extracted from the switch by the G3 Proxy Agent. This object
            along with the g3stationcfgTintvl object allows the Network Manager
            to determine the validity of the station config data in the
            cache and to control when the proxy agent extracts the
            station config data from the switch."
        ::= { g3stationcfg 1 }

    g3stationcfgTintvl	OBJECT-TYPE
        SYNTAX    INTEGER
        ACCESS    read-write
        STATUS    mandatory
        DESCRIPTION
            "An object containing the interval for which the station config data 
            extracted from the switch is considered valid by the proxy agent.  When a 
            GET or GET-NEXT request for station config data objects is received by the 
            agent it uses	the g3stationcfgTage and g3stationcfgTintvl objects to 
            determine	whether it should refresh the cached stationcfgTable.  If
            g3stationcfgTstmp + g3stationcfgTintvl is less than the current
            value of the sysUpTime object then the agent refreshes the
            stationcfgTable cache.  In either case it responds to the 
            requests it receives with the data it currently has in the cache."
        ::= { g3stationcfg 2 }

    g3stationcfgTdelay	OBJECT-TYPE
        SYNTAX    INTEGER
        ACCESS    read-only
        STATUS    mandatory
        DESCRIPTION
            "An object containing the delay encountered in updating
            the cached data"
        ::= { g3stationcfg 3 }

    g3stationcfgTretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3stationcfg 4 }

    g3stationcfgTcount	OBJECT-TYPE
        SYNTAX    Gauge
        ACCESS    read-only
        STATUS    mandatory
        DESCRIPTION
            "A Gauge object containing the number of data records in the cache."
        ::= { g3stationcfg 5 }

    g3stationcfgTable	OBJECT-TYPE
        SYNTAX    SEQUENCE OF G3stationcfgEntry
        ACCESS    not-accessible
        STATUS    mandatory
        DESCRIPTION
            "A list of g3stationcfg entries."
        ::= { g3stationcfg 6 }

    g3stationcfgEntry	OBJECT-TYPE
        SYNTAX    G3stationcfgEntry
        ACCESS    not-accessible
        STATUS    mandatory
        DESCRIPTION
            "A g3stationcfg entry containing objects of the
            g3stationcfg information sent by the switch."
        INDEX    { g3stationcfgBoardNum }
        ::= { g3stationcfgTable 1 }

    G3stationcfgEntry ::= SEQUENCE {
        g3stationcfgBoardNum
            DisplayString,
        g3stationcfgBoardType
            DisplayString,
        g3stationcfgCode
            DisplayString,
        g3stationcfgVintage
            DisplayString,
        g3stationcfgSuffix
            DisplayString
        }

    g3stationcfgBoardNum	OBJECT-TYPE
        SYNTAX    DisplayString (SIZE (0..7))
        ACCESS    read-only
        STATUS    mandatory
        DESCRIPTION
            "A DisplayString Object that uniquely identifies a station board based
            on its location in the system. The syntax for the Board Number is as
            follows: cabinet(01-44):carrier(A-E):slot(01-20)."
        ::= { g3stationcfgEntry 1 }

    g3stationcfgBoardType	OBJECT-TYPE
        SYNTAX    DisplayString (SIZE (0..19))
        ACCESS    read-only
        STATUS    mandatory
        DESCRIPTION
            "A DisplayString Object that contains a text description of the
            type of station board."
        ::= { g3stationcfgEntry 2 }

    g3stationcfgCode	OBJECT-TYPE
        SYNTAX    DisplayString (SIZE (0..8))
        ACCESS    read-only
        STATUS    mandatory
        DESCRIPTION
            "A DisplayString Object that contains the code that defines the
            type of station board."
        ::= { g3stationcfgEntry 3 }

    g3stationcfgVintage	OBJECT-TYPE
        SYNTAX    DisplayString (SIZE (0..10))
        ACCESS    read-only
        STATUS    mandatory
        DESCRIPTION
            "A DisplayString Object that contains the vintage of the station board."
        ::= { g3stationcfgEntry 4 }

    g3stationcfgSuffix	OBJECT-TYPE
        SYNTAX    DisplayString (SIZE (0..2))
        ACCESS    read-only
        STATUS    mandatory
        DESCRIPTION
            "A DisplayString Object that contains the suffix to the code"
        ::= { g3stationcfgEntry 5 }


    -- the g3atmcfg group

    g3atmcfgTage	OBJECT-TYPE
        SYNTAX    INTEGER
        ACCESS    read-only
        STATUS    mandatory
        DESCRIPTION
            "The number of timeticks since the atm config data was
            extracted from the switch by the G3 Proxy Agent. This object
            along with the g3atmcfgTintvl object allows the Network Manager
            to determine the validity of the atm config  data in the
            cache and to control when the proxy agent extracts the
            atm config  data from the switch."
        ::= { g3atmcfg 1 }

    g3atmcfgTintvl	OBJECT-TYPE
        SYNTAX    INTEGER
        ACCESS    read-write
        STATUS    mandatory
        DESCRIPTION
            "An object containing the interval for which the atm config data extracted 
            from	the switch is considered valid by the proxy agent.  When a GET or
            GET-NEXT request for atm config data objects is received by the agent it 
            uses	the g3atmcfgTage and g3atmcfgTintvl objects to determine
            whether it should refresh the cached atmcfgTable.  If
            g3atmcfgTstmp + g3atmcfgTintvl is less than the current
            value of the sysUpTime object then the agent refreshes the
            atmcfgTable cache.  In either case it responds to the 
            requests it receives with the data it currently has in the cache."
        ::= { g3atmcfg 2 }

    g3atmcfgTdelay	OBJECT-TYPE
        SYNTAX    INTEGER
        ACCESS    read-only
        STATUS    mandatory
        DESCRIPTION
            "An object containing the delay encountered in updating
            the cached data"
        ::= { g3atmcfg 3 }

    g3atmcfgTretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3atmcfg 4 }

    g3atmcfgTcount	OBJECT-TYPE
        SYNTAX    Gauge
        ACCESS    read-only
        STATUS    mandatory
        DESCRIPTION
            "A Gauge object containing the number of data records in the cache."
        ::= { g3atmcfg 5 }

    g3atmcfgTable	OBJECT-TYPE
        SYNTAX    SEQUENCE OF G3atmcfgEntry
        ACCESS    not-accessible
        STATUS    mandatory
        DESCRIPTION
            "A list of g3atmcfg entries."
        ::= { g3atmcfg 6 }

    g3atmcfgEntry	OBJECT-TYPE
        SYNTAX    G3atmcfgEntry
        ACCESS    not-accessible
        STATUS    mandatory
        DESCRIPTION
            "A g3atmcfg entry containing objects of the
            g3atmcfg information sent by the switch."
        INDEX    { g3atmcfgBoardNum }
        ::= { g3atmcfgTable 1 }

    G3atmcfgEntry ::= SEQUENCE {
        g3atmcfgBoardNum
            DisplayString,
        g3atmcfgCode
            DisplayString,
        g3atmcfgBoardType
            DisplayString,
        g3atmcfgVintage
            DisplayString,
        g3atmcfgName
            DisplayString,
        g3atmcfgSuffix
            DisplayString
        }

    g3atmcfgBoardNum	OBJECT-TYPE
        SYNTAX    DisplayString (SIZE (0..7))
        ACCESS    read-only
        STATUS    mandatory
        DESCRIPTION
            "A DisplayString Object that uniquely identifies a board used
            for ATM connectivity based on its location in the system. The
            syntax for the Board Number is as follows:
            cabinet(01-44):carrier(A-E):slot(01-20)."
        ::= { g3atmcfgEntry 1 }

    g3atmcfgCode	OBJECT-TYPE
        SYNTAX    DisplayString (SIZE (0..8))
        ACCESS    read-only
        STATUS    mandatory
        DESCRIPTION
            "A DisplayString Object that contains the code that defines the
            type of ATM connectivity board."
        ::= { g3atmcfgEntry 2 }

    g3atmcfgBoardType	OBJECT-TYPE
        SYNTAX    DisplayString (SIZE (0..19))
        ACCESS    read-only
        STATUS    mandatory
        DESCRIPTION
            "A DisplayString Object that contains a text description of the
            type of ATM connectivity board."
        ::= { g3atmcfgEntry 3 }

    g3atmcfgVintage	OBJECT-TYPE
        SYNTAX    DisplayString (SIZE (0..10))
        ACCESS    read-only
        STATUS    mandatory
        DESCRIPTION
            "A DisplayString Object that contains the vintage of the ATM
            connectivity board."
        ::= { g3atmcfgEntry 4 }

    g3atmcfgName	OBJECT-TYPE
        SYNTAX    DisplayString (SIZE (0..15))
        ACCESS    read-only
        STATUS    mandatory
        DESCRIPTION
            "A DisplayString Object that contains the name of the ATM
            connectivity board."
        ::= { g3atmcfgEntry 5 }

    g3atmcfgSuffix	OBJECT-TYPE
        SYNTAX    DisplayString (SIZE (0..2))
        ACCESS    read-only
        STATUS    mandatory
        DESCRIPTION
            "A DisplayString Object that contains the suffix to the code"
        ::= { g3atmcfgEntry 6 }


    -- the g3aca group

    g3acaTage	OBJECT-TYPE
        SYNTAX    INTEGER
        ACCESS    read-only
        STATUS    mandatory
        DESCRIPTION
            "The number of timeticks since the data was last
            extracted from the switch by the Proxy Agent.  This object
            along with the g3acaintvl object allows the Network Manager
            to determine the validity of the data in the cache and to control
            when the Proxy Agent extracts the data from the switch."
        ::= { g3aca 1 }

    g3acaTintvl	OBJECT-TYPE
        SYNTAX    INTEGER
        ACCESS    read-write
        STATUS    mandatory
        DESCRIPTION
            "An object containing the interval for which the
            data extracted from the switch is considered valid by the
            Proxy Agent.  When a GET or GET-NEXT request for these data
            objects is received by the agent it uses the g3acaage
            and g3acaintvl objects to determine whether it should refresh
            the cached acaTable.  If g3acastmp + g3acaintvl
            is less than the current value of the sysUpTime object then the agent
            refreshes the acaTable cache.  In either case it responds to
            the requests it receives with the data it currently has in the cache."
        ::= { g3aca 2 }

    g3acaTdelay	OBJECT-TYPE
        SYNTAX    INTEGER
        ACCESS    read-only
        STATUS    mandatory
        DESCRIPTION
            "An object containing the delay encountered in updating
            the cached data."
        ::= { g3aca 3 }

    g3acaTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3aca 4 }

    g3acaTcount	OBJECT-TYPE
        SYNTAX    Gauge
        ACCESS    read-only
        STATUS    mandatory
        DESCRIPTION
            "A Gauge object containing the number of data records in the cache."
        ::= { g3aca 5 }

    g3acaTable	OBJECT-TYPE
        SYNTAX    SEQUENCE OF G3acaEntry
        ACCESS    not-accessible
        STATUS    mandatory
        DESCRIPTION
            "A list of g3aca entries."
        ::= { g3aca 6 }

    g3acaEntry	OBJECT-TYPE
        SYNTAX    G3acaEntry
        ACCESS    not-accessible
        STATUS    mandatory
        DESCRIPTION
            "A g3aca entry containing objects of the
            g3aca information sent by the switch."
        INDEX    { g3acaTGNumber, g3acaTGMember, g3acaDayTime }
        ::= { g3acaTable 1 }

    G3acaEntry ::= SEQUENCE {
        g3acaTGNumber
            INTEGER,
        g3acaTGMember
            INTEGER,
        g3acaDayTime
            DisplayString,
        g3acaYear
            INTEGER,
        g3acaMonth
            INTEGER,
        g3acaDay
            INTEGER,
        g3acaHour
            INTEGER,
        g3acaTGAccess
            INTEGER,
        g3acaRefType
            DisplayString,
        g3acaWideBand
            DisplayString
        }

    g3acaTGNumber	OBJECT-TYPE
        SYNTAX    INTEGER
        ACCESS    read-only
        STATUS    mandatory
        DESCRIPTION
            "An object containing the trunk group number."
        ::= { g3acaEntry 1 }

    g3acaTGMember	OBJECT-TYPE
        SYNTAX    INTEGER
        ACCESS    read-only
        STATUS    mandatory
        DESCRIPTION
            "An object containing the trunk group member number."
        ::= { g3acaEntry 2 }

    g3acaDayTime	OBJECT-TYPE
        SYNTAX    DisplayString (SIZE (0..8))
        ACCESS    read-only
        STATUS    mandatory
        DESCRIPTION
            "A DisplayString Object that contains the day and time at which
            either the threshold for short holding time calls was exceeded
            or long holding time call was reached and a referral call was
            placed."
        ::= { g3acaEntry 3 }

    g3acaYear	OBJECT-TYPE
        SYNTAX    INTEGER
        ACCESS    read-only
        STATUS    mandatory
        DESCRIPTION
            "An object containing the Year the command was executed."
        ::= { g3acaEntry 4 }

    g3acaMonth	OBJECT-TYPE
        SYNTAX    INTEGER
        ACCESS    read-only
        STATUS    mandatory
        DESCRIPTION
            "An object containing the Month the command was executed."
        ::= { g3acaEntry 5 }

    g3acaDay	OBJECT-TYPE
        SYNTAX    INTEGER
        ACCESS    read-only
        STATUS    mandatory
        DESCRIPTION
            "An object containing the Day the command was executed."
        ::= { g3acaEntry 6 }

    g3acaHour	OBJECT-TYPE
        SYNTAX    INTEGER
        ACCESS    read-only
        STATUS    mandatory
        DESCRIPTION
            "An object containing the Hour the command was executed."
        ::= { g3acaEntry 7 }

    g3acaTGAccess	OBJECT-TYPE
        SYNTAX    INTEGER
        ACCESS    read-only
        STATUS    mandatory
        DESCRIPTION
            "An object containing the trunk access code for the trunk group."
        ::= { g3acaEntry 8 }

    g3acaRefType	OBJECT-TYPE
        SYNTAX    DisplayString (SIZE (0..5))
        ACCESS    read-only
        STATUS    mandatory
        DESCRIPTION
            "A DisplayString Object that indicates whether the referral
            occurred as the result of too many short holding time calls
            or an excessively long holding time call."
        ::= { g3acaEntry 9 }

    g3acaWideBand	OBJECT-TYPE
        SYNTAX    DisplayString (SIZE (0..1))
        ACCESS    read-only
        STATUS    mandatory
        DESCRIPTION
            "A DisplayString Object that indicates whether the call
            was a wideband call."
        ::= { g3acaEntry 10 }


    -- the g3atmtrunk group

    g3atmtrunkTage	OBJECT-TYPE
        SYNTAX    INTEGER
        ACCESS    read-only
        STATUS    mandatory
        DESCRIPTION
            "The number of timeticks since the atm trunk data was
            extracted from the switch by the G3 Proxy Agent. This object
            along with the g3atmtrunkTintvl object allows the Network Manager
            to determine the validity of the atm trunk  data in the
            cache and to control when the proxy agent extracts the
            atm trunk  data from the switch."
        ::= { g3atmtrunk 1 }

    g3atmtrunkTintvl	OBJECT-TYPE
        SYNTAX    INTEGER
        ACCESS    read-write
        STATUS    mandatory
        DESCRIPTION
            "An object containing the interval for which the atm trunk data extracted 
            from	the switch is considered valid by the proxy agent.  When a GET or
            GET-NEXT request for atm trunk data objects is received by the agent it 
            uses	the g3atmtrunkTage and g3atmtrunkTintvl objects to determine
            whether it should refresh the cached atmtrunkTable.  If
            g3atmtrunkTstmp + g3atmtrunkTintvl is less than the current
            value of the sysUpTime object then the agent refreshes the
            atmtrunkTable cache.  In either case it responds to the 
            requests it receives with the data it currently has in the cache."
        ::= { g3atmtrunk 2 }

    g3atmtrunkTdelay	OBJECT-TYPE
        SYNTAX    INTEGER
        ACCESS    read-only
        STATUS    mandatory
        DESCRIPTION
            "An object containing the delay encountered in updating
            the cached data"
        ::= { g3atmtrunk 3 }

    g3atmtrunkTretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3atmtrunk 4 }

    g3atmtrunkTcount	OBJECT-TYPE
        SYNTAX    Gauge
        ACCESS    read-only
        STATUS    mandatory
        DESCRIPTION
            "A Gauge object containing the number of data records in the cache."
        ::= { g3atmtrunk 5 }

    g3atmtrunkTable	OBJECT-TYPE
        SYNTAX    SEQUENCE OF G3atmtrunkEntry
        ACCESS    not-accessible
        STATUS    mandatory
        DESCRIPTION
            "A list of g3atmtrunk entries."
        ::= { g3atmtrunk 6 }

    g3atmtrunkEntry	OBJECT-TYPE
        SYNTAX    G3atmtrunkEntry
        ACCESS    not-accessible
        STATUS    mandatory
        DESCRIPTION
            "A g3atmtrunk entry containing objects of the
            g3atmtrunk information sent by the switch."
        INDEX    { g3atmtrunkLocation }
        ::= { g3atmtrunkTable 1 }

    G3atmtrunkEntry ::= SEQUENCE {
        g3atmtrunkLocation
            DisplayString,
        g3atmtrunkName
            DisplayString,
        g3atmtrunkSynch
            DisplayString
        }

    g3atmtrunkLocation	OBJECT-TYPE
        SYNTAX    DisplayString (SIZE (0..5))
        ACCESS    read-only
        STATUS    mandatory
        DESCRIPTION
            "A DisplayString Object that uniquely identifies the ATM trunk
            board based on its location in the system. The syntax for the
            Board Number is as follows: cabinet(01-44):carrier(A-E):slot(01-20)."
        ::= { g3atmtrunkEntry 1 }

    g3atmtrunkName	OBJECT-TYPE
        SYNTAX    DisplayString (SIZE (0..15))
        ACCESS    read-only
        STATUS    mandatory
        DESCRIPTION
            "A DisplayString Object that identifies the ATM trunk board
            by name."
        ::= { g3atmtrunkEntry 2 }

    g3atmtrunkSynch	OBJECT-TYPE
        SYNTAX    DisplayString (SIZE (0..1))
        ACCESS    read-only
        STATUS    mandatory
        DESCRIPTION
            "A DisplayString Object that identifies whether the ATM trunk
            is synchronization capable (y or n)."
        ::= { g3atmtrunkEntry 3 }


    -- the g3atmportpg1 group

    g3atmportpg1Tage	OBJECT-TYPE
        SYNTAX    INTEGER
        ACCESS    read-only
        STATUS    mandatory
        DESCRIPTION
            "The number of timeticks since the atm port data was
            extracted from the switch by the G3 Proxy Agent. This object
            along with the g3atmportpg1Tintvl object allows the Network Manager
            to determine the validity of the atm port data in the
            cache and to control when the proxy agent extracts the
            atm port data from the switch."
        ::= { g3atmportpg1 1 }

    g3atmportpg1Tintvl	OBJECT-TYPE
        SYNTAX    INTEGER
        ACCESS    read-write
        STATUS    mandatory
        DESCRIPTION
            "An object containing the interval for which the atm port data extracted 
            from	the switch is considered valid by the proxy agent.  When a GET or
            GET-NEXT request for atm port data objects is received by the agent it 
            uses	the g3atmportpg1sTage and g3atmportpg1sTintvl objects to determine
            whether it should refresh the cached atmportpg1sTable.  If
            g3atmportpg1sTstmp + g3atmportpg1sTintvl is less than the current
            value of the sysUpTime object then the agent refreshes the
            atmportpg1sTable cache.  In either case it responds to the 
            requests it receives with the data it currently has in the cache."
        ::= { g3atmportpg1 2 }

    g3atmportpg1Tdelay	OBJECT-TYPE
        SYNTAX    INTEGER
        ACCESS    read-only
        STATUS    mandatory
        DESCRIPTION
            "An object containing the delay encountered in updating
            the cached data"
        ::= { g3atmportpg1 3 }

    g3atmportpg1Tretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3atmportpg1 4 }

    g3atmportpg1Tcount	OBJECT-TYPE
        SYNTAX    Gauge
        ACCESS    read-only
        STATUS    mandatory
        DESCRIPTION
            "A Gauge object containing the number of data records in the cache."
        ::= { g3atmportpg1 5 }

    g3atmportpg1Table	OBJECT-TYPE
        SYNTAX    SEQUENCE OF G3atmportpg1Entry
        ACCESS    not-accessible
        STATUS    mandatory
        DESCRIPTION
            "A list of g3atmportpg1 entries."
        ::= { g3atmportpg1 6 }

    g3atmportpg1Entry	OBJECT-TYPE
        SYNTAX    G3atmportpg1Entry
        ACCESS    not-accessible
        STATUS    mandatory
        DESCRIPTION
            "A g3atmportpg1 entry containing objects of the
            g3atmportpg1 information sent by the switch."
        INDEX    { g3atmportpg1Location }
        ::= { g3atmportpg1Table 1 }

    G3atmportpg1Entry ::= SEQUENCE {
        g3atmportpg1Location
            DisplayString,
        g3atmportpg1SGNumber1
            INTEGER,
        g3atmportpg1SGNumber2
            INTEGER,
        g3atmportpg1SGNumber3
            INTEGER,
        g3atmportpg1SGNumber4
            INTEGER,
        g3atmportpg1SGNumber5
            INTEGER,
        g3atmportpg1SGNumber6
            INTEGER,
        g3atmportpg1SGNumber7
            INTEGER,
        g3atmportpg1SGNumber8
            INTEGER,
        g3atmportpg1SGNumber9
            INTEGER,
        g3atmportpg1SGNumber10
            INTEGER,
        g3atmportpg1SGNumber11
            INTEGER,
        g3atmportpg1SGNumber12
            INTEGER,
        g3atmportpg1SGNumber13
            INTEGER,
        g3atmportpg1SGNumber14
            INTEGER,
        g3atmportpg1SGNumber15
            INTEGER,
        g3atmportpg1SGNumber16
            INTEGER,
        g3atmportpg1SGNumber17
            INTEGER,
        g3atmportpg1SGNumber18
            INTEGER,
        g3atmportpg1SGNumber19
            INTEGER,
        g3atmportpg1SGNumber20
            INTEGER,
        g3atmportpg1SGNumber21
            INTEGER,
        g3atmportpg1SGNumber22
            INTEGER,
        g3atmportpg1SGNumber23
            INTEGER,
        g3atmportpg1SGNumber24
            INTEGER,
        g3atmportpg1SGNumber25
            INTEGER,
        g3atmportpg1SGNumber26
            INTEGER,
        g3atmportpg1SGNumber27
            INTEGER,
        g3atmportpg1SGNumber28
            INTEGER,
        g3atmportpg1SGNumber29
            INTEGER,
        g3atmportpg1SGNumber30
            INTEGER,
        g3atmportpg1SGNumber31
            INTEGER,
        g3atmportpg1SGNumber32
            INTEGER,
        g3atmportpg1SGNumber33
            INTEGER,
        g3atmportpg1SGNumber34
            INTEGER,
        g3atmportpg1SGNumber35
            INTEGER,
        g3atmportpg1SGNumber36
            INTEGER,
        g3atmportpg1SGNumber37
            INTEGER,
        g3atmportpg1SGNumber38
            INTEGER,
        g3atmportpg1SGNumber39
            INTEGER,
        g3atmportpg1SGNumber40
            INTEGER,
        g3atmportpg1SGNumber41
            INTEGER,
        g3atmportpg1SGNumber42
            INTEGER,
        g3atmportpg1SGNumber43
            INTEGER,
        g3atmportpg1SGNumber44
            INTEGER,
        g3atmportpg1SGNumber45
            INTEGER,
        g3atmportpg1SGNumber46
            INTEGER,
        g3atmportpg1SGNumber47
            INTEGER,
        g3atmportpg1SGNumber48
            INTEGER,
        g3atmportpg1SGNumber49
            INTEGER,
        g3atmportpg1SGNumber50
            INTEGER,
        g3atmportpg1SGNumber51
            INTEGER,
        g3atmportpg1SGNumber52
            INTEGER,
        g3atmportpg1SGNumber53
            INTEGER,
        g3atmportpg1SGNumber54
            INTEGER,
        g3atmportpg1SGNumber55
            INTEGER,
        g3atmportpg1SGNumber56
            INTEGER,
        g3atmportpg1SGNumber57
            INTEGER,
        g3atmportpg1SGNumber58
            INTEGER,
        g3atmportpg1SGNumber59
            INTEGER,
        g3atmportpg1SGNumber60
            INTEGER,
        g3atmportpg1SGNumber61
            INTEGER,
        g3atmportpg1SGNumber62
            INTEGER,
        g3atmportpg1SGNumber63
            INTEGER,
        g3atmportpg1SGNumber64
            INTEGER,
        g3atmportpg1SGNumber65
            INTEGER,
        g3atmportpg1SGNumber66
            INTEGER,
        g3atmportpg1SGNumber67
            INTEGER,
        g3atmportpg1SGNumber68
            INTEGER,
        g3atmportpg1SGNumber69
            INTEGER,
        g3atmportpg1SGNumber70
            INTEGER,
        g3atmportpg1SGNumber71
            INTEGER,
        g3atmportpg1SGNumber72
            INTEGER,
        g3atmportpg1SGNumber73
            INTEGER,
        g3atmportpg1SGNumber74
            INTEGER,
        g3atmportpg1SGNumber75
            INTEGER,
        g3atmportpg1SGNumber76
            INTEGER,
        g3atmportpg1SGNumber77
            INTEGER,
        g3atmportpg1SGNumber78
            INTEGER,
        g3atmportpg1SGNumber79
            INTEGER,
        g3atmportpg1SGNumber80
            INTEGER,
        g3atmportpg1SGNumber81
            INTEGER,
        g3atmportpg1SGNumber82
            INTEGER,
        g3atmportpg1SGNumber83
            INTEGER,
        g3atmportpg1SGNumber84
            INTEGER,
        g3atmportpg1SGNumber85
            INTEGER,
        g3atmportpg1SGNumber86
            INTEGER,
        g3atmportpg1SGNumber87
            INTEGER,
        g3atmportpg1SGNumber88
            INTEGER,
        g3atmportpg1SGNumber89
            INTEGER,
        g3atmportpg1SGNumber90
            INTEGER,
        g3atmportpg1TGNumber1
            INTEGER,
        g3atmportpg1TGNumber2
            INTEGER,
        g3atmportpg1TGNumber3
            INTEGER,
        g3atmportpg1TGNumber4
            INTEGER,
        g3atmportpg1TGNumber5
            INTEGER,
        g3atmportpg1TGNumber6
            INTEGER,
        g3atmportpg1TGNumber7
            INTEGER,
        g3atmportpg1TGNumber8
            INTEGER,
        g3atmportpg1TGNumber9
            INTEGER,
        g3atmportpg1TGNumber10
            INTEGER,
        g3atmportpg1TGNumber11
            INTEGER,
        g3atmportpg1TGNumber12
            INTEGER,
        g3atmportpg1TGNumber13
            INTEGER,
        g3atmportpg1TGNumber14
            INTEGER,
        g3atmportpg1TGNumber15
            INTEGER,
        g3atmportpg1TGNumber16
            INTEGER,
        g3atmportpg1TGNumber17
            INTEGER,
        g3atmportpg1TGNumber18
            INTEGER,
        g3atmportpg1TGNumber19
            INTEGER,
        g3atmportpg1TGNumber20
            INTEGER,
        g3atmportpg1TGNumber21
            INTEGER,
        g3atmportpg1TGNumber22
            INTEGER,
        g3atmportpg1TGNumber23
            INTEGER,
        g3atmportpg1TGNumber24
            INTEGER,
        g3atmportpg1TGNumber25
            INTEGER,
        g3atmportpg1TGNumber26
            INTEGER,
        g3atmportpg1TGNumber27
            INTEGER,
        g3atmportpg1TGNumber28
            INTEGER,
        g3atmportpg1TGNumber29
            INTEGER,
        g3atmportpg1TGNumber30
            INTEGER,
        g3atmportpg1TGNumber31
            INTEGER,
        g3atmportpg1TGNumber32
            INTEGER,
        g3atmportpg1TGNumber33
            INTEGER,
        g3atmportpg1TGNumber34
            INTEGER,
        g3atmportpg1TGNumber35
            INTEGER,
        g3atmportpg1TGNumber36
            INTEGER,
        g3atmportpg1TGNumber37
            INTEGER,
        g3atmportpg1TGNumber38
            INTEGER,
        g3atmportpg1TGNumber39
            INTEGER,
        g3atmportpg1TGNumber40
            INTEGER,
        g3atmportpg1TGNumber41
            INTEGER,
        g3atmportpg1TGNumber42
            INTEGER,
        g3atmportpg1TGNumber43
            INTEGER,
        g3atmportpg1TGNumber44
            INTEGER,
        g3atmportpg1TGNumber45
            INTEGER,
        g3atmportpg1TGNumber46
            INTEGER,
        g3atmportpg1TGNumber47
            INTEGER,
        g3atmportpg1TGNumber48
            INTEGER,
        g3atmportpg1TGNumber49
            INTEGER,
        g3atmportpg1TGNumber50
            INTEGER,
        g3atmportpg1TGNumber51
            INTEGER,
        g3atmportpg1TGNumber52
            INTEGER,
        g3atmportpg1TGNumber53
            INTEGER,
        g3atmportpg1TGNumber54
            INTEGER,
        g3atmportpg1TGNumber55
            INTEGER,
        g3atmportpg1TGNumber56
            INTEGER,
        g3atmportpg1TGNumber57
            INTEGER,
        g3atmportpg1TGNumber58
            INTEGER,
        g3atmportpg1TGNumber59
            INTEGER,
        g3atmportpg1TGNumber60
            INTEGER,
        g3atmportpg1TGNumber61
            INTEGER,
        g3atmportpg1TGNumber62
            INTEGER,
        g3atmportpg1TGNumber63
            INTEGER,
        g3atmportpg1TGNumber64
            INTEGER,
        g3atmportpg1TGNumber65
            INTEGER,
        g3atmportpg1TGNumber66
            INTEGER,
        g3atmportpg1TGNumber67
            INTEGER,
        g3atmportpg1TGNumber68
            INTEGER,
        g3atmportpg1TGNumber69
            INTEGER,
        g3atmportpg1TGNumber70
            INTEGER,
        g3atmportpg1TGNumber71
            INTEGER,
        g3atmportpg1TGNumber72
            INTEGER,
        g3atmportpg1TGNumber73
            INTEGER,
        g3atmportpg1TGNumber74
            INTEGER,
        g3atmportpg1TGNumber75
            INTEGER,
        g3atmportpg1TGNumber76
            INTEGER,
        g3atmportpg1TGNumber77
            INTEGER,
        g3atmportpg1TGNumber78
            INTEGER,
        g3atmportpg1TGNumber79
            INTEGER,
        g3atmportpg1TGNumber80
            INTEGER,
        g3atmportpg1TGNumber81
            INTEGER,
        g3atmportpg1TGNumber82
            INTEGER,
        g3atmportpg1TGNumber83
            INTEGER,
        g3atmportpg1TGNumber84
            INTEGER,
        g3atmportpg1TGNumber85
            INTEGER,
        g3atmportpg1TGNumber86
            INTEGER,
        g3atmportpg1TGNumber87
            INTEGER,
        g3atmportpg1TGNumber88
            INTEGER,
        g3atmportpg1TGNumber89
            INTEGER,
        g3atmportpg1TGNumber90
            INTEGER
        }

    g3atmportpg1Location	OBJECT-TYPE
        SYNTAX    DisplayString (SIZE (0..7))
        ACCESS    read-only
        STATUS    mandatory
        DESCRIPTION
            "A DisplayString Object that uniquely identifies the ATM trunk
            board based on its location in the system. The syntax for the
            Board Number is as follows: cabinet(01-44):carrier(A-E):slot(01-20)."
        ::= { g3atmportpg1Entry 1 }

    g3atmportpg1SGNumber1	OBJECT-TYPE
        SYNTAX    INTEGER
        ACCESS    read-only
        STATUS    mandatory
        DESCRIPTION
            "An INTEGER Object that uniquely identifies the signaling group
            associated with the ATM ports (1 to 90) on page 1 of the form."
        ::= { g3atmportpg1Entry 2 }

    g3atmportpg1SGNumber2	OBJECT-TYPE
        SYNTAX    INTEGER
        ACCESS    read-only
        STATUS    mandatory
        DESCRIPTION
            "See DESCRIPTION of g3atmportpg1SGNumber1."
        ::= { g3atmportpg1Entry 3 }

    g3atmportpg1SGNumber3	OBJECT-TYPE
        SYNTAX    INTEGER
        ACCESS    read-only
        STATUS    mandatory
        DESCRIPTION
            "See DESCRIPTION of g3atmportpg1SGNumber1."
        ::= { g3atmportpg1Entry 4 }

    g3atmportpg1SGNumber4	OBJECT-TYPE
        SYNTAX    INTEGER
        ACCESS    read-only
        STATUS    mandatory
        DESCRIPTION
            "See DESCRIPTION of g3atmportpg1SGNumber1."
        ::= { g3atmportpg1Entry 5 }

    g3atmportpg1SGNumber5	OBJECT-TYPE
        SYNTAX    INTEGER
        ACCESS    read-only
        STATUS    mandatory
        DESCRIPTION
            "See DESCRIPTION of g3atmportpg1SGNumber1."
        ::= { g3atmportpg1Entry 6 }

    g3atmportpg1SGNumber6	OBJECT-TYPE
        SYNTAX    INTEGER
        ACCESS    read-only
        STATUS    mandatory
        DESCRIPTION
            "See DESCRIPTION of g3atmportpg1SGNumber1."
        ::= { g3atmportpg1Entry 7 }

    g3atmportpg1SGNumber7	OBJECT-TYPE
        SYNTAX    INTEGER
        ACCESS    read-only
        STATUS    mandatory
        DESCRIPTION
            "See DESCRIPTION of g3atmportpg1SGNumber1."
        ::= { g3atmportpg1Entry 8 }

    g3atmportpg1SGNumber8	OBJECT-TYPE
        SYNTAX    INTEGER
        ACCESS    read-only
        STATUS    mandatory
        DESCRIPTION
            "See DESCRIPTION of g3atmportpg1SGNumber1."
        ::= { g3atmportpg1Entry 9 }

    g3atmportpg1SGNumber9	OBJECT-TYPE
        SYNTAX    INTEGER
        ACCESS    read-only
        STATUS    mandatory
        DESCRIPTION
            "See DESCRIPTION of g3atmportpg1SGNumber1."
        ::= { g3atmportpg1Entry 10 }

    g3atmportpg1SGNumber10	OBJECT-TYPE
        SYNTAX    INTEGER
        ACCESS    read-only
        STATUS    mandatory
        DESCRIPTION
            "See DESCRIPTION of g3atmportpg1SGNumber1."
        ::= { g3atmportpg1Entry 11 }

    g3atmportpg1SGNumber11	OBJECT-TYPE
        SYNTAX    INTEGER
        ACCESS    read-only
        STATUS    mandatory
        DESCRIPTION
            "See DESCRIPTION of g3atmportpg1SGNumber1."
        ::= { g3atmportpg1Entry 12 }

    g3atmportpg1SGNumber12	OBJECT-TYPE
        SYNTAX    INTEGER
        ACCESS    read-only
        STATUS    mandatory
        DESCRIPTION
            "See DESCRIPTION of g3atmportpg1SGNumber1."
        ::= { g3atmportpg1Entry 13 }

    g3atmportpg1SGNumber13	OBJECT-TYPE
        SYNTAX    INTEGER
        ACCESS    read-only
        STATUS    mandatory
        DESCRIPTION
            "See DESCRIPTION of g3atmportpg1SGNumber1."
        ::= { g3atmportpg1Entry 14 }

    g3atmportpg1SGNumber14	OBJECT-TYPE
        SYNTAX    INTEGER
        ACCESS    read-only
        STATUS    mandatory
        DESCRIPTION
            "See DESCRIPTION of g3atmportpg1SGNumber1."
        ::= { g3atmportpg1Entry 15 }

    g3atmportpg1SGNumber15	OBJECT-TYPE
        SYNTAX    INTEGER
        ACCESS    read-only
        STATUS    mandatory
        DESCRIPTION
            "See DESCRIPTION of g3atmportpg1SGNumber1."
        ::= { g3atmportpg1Entry 16 }

    g3atmportpg1SGNumber16	OBJECT-TYPE
        SYNTAX    INTEGER
        ACCESS    read-only
        STATUS    mandatory
        DESCRIPTION
            "See DESCRIPTION of g3atmportpg1SGNumber1."
        ::= { g3atmportpg1Entry 17 }

    g3atmportpg1SGNumber17	OBJECT-TYPE
        SYNTAX    INTEGER
        ACCESS    read-only
        STATUS    mandatory
        DESCRIPTION
            "See DESCRIPTION of g3atmportpg1SGNumber1."
        ::= { g3atmportpg1Entry 18 }

    g3atmportpg1SGNumber18	OBJECT-TYPE
        SYNTAX    INTEGER
        ACCESS    read-only
        STATUS    mandatory
        DESCRIPTION
            "See DESCRIPTION of g3atmportpg1SGNumber1."
        ::= { g3atmportpg1Entry 19 }

    g3atmportpg1SGNumber19	OBJECT-TYPE
        SYNTAX    INTEGER
        ACCESS    read-only
        STATUS    mandatory
        DESCRIPTION
            "See DESCRIPTION of g3atmportpg1SGNumber1."
        ::= { g3atmportpg1Entry 20 }

    g3atmportpg1SGNumber20	OBJECT-TYPE
        SYNTAX    INTEGER
        ACCESS    read-only
        STATUS    mandatory
        DESCRIPTION
            "See DESCRIPTION of g3atmportpg1SGNumber1."
        ::= { g3atmportpg1Entry 21 }

    g3atmportpg1SGNumber21	OBJECT-TYPE
        SYNTAX    INTEGER
        ACCESS    read-only
        STATUS    mandatory
        DESCRIPTION
            "See DESCRIPTION of g3atmportpg1SGNumber1."
        ::= { g3atmportpg1Entry 22 }

    g3atmportpg1SGNumber22	OBJECT-TYPE
        SYNTAX    INTEGER
        ACCESS    read-only
        STATUS    mandatory
        DESCRIPTION
            "See DESCRIPTION of g3atmportpg1SGNumber1."
        ::= { g3atmportpg1Entry 23 }

    g3atmportpg1SGNumber23	OBJECT-TYPE
        SYNTAX    INTEGER
        ACCESS    read-only
        STATUS    mandatory
        DESCRIPTION
            "See DESCRIPTION of g3atmportpg1SGNumber1."
        ::= { g3atmportpg1Entry 24 }

    g3atmportpg1SGNumber24	OBJECT-TYPE
        SYNTAX    INTEGER
        ACCESS    read-only
        STATUS    mandatory
        DESCRIPTION
            "See DESCRIPTION of g3atmportpg1SGNumber1."
        ::= { g3atmportpg1Entry 25 }

    g3atmportpg1SGNumber25	OBJECT-TYPE
        SYNTAX    INTEGER
        ACCESS    read-only
        STATUS    mandatory
        DESCRIPTION
            "See DESCRIPTION of g3atmportpg1SGNumber1."
        ::= { g3atmportpg1Entry 26 }

    g3atmportpg1SGNumber26	OBJECT-TYPE
        SYNTAX    INTEGER
        ACCESS    read-only
        STATUS    mandatory
        DESCRIPTION
            "See DESCRIPTION of g3atmportpg1SGNumber1."
        ::= { g3atmportpg1Entry 27 }

    g3atmportpg1SGNumber27	OBJECT-TYPE
        SYNTAX    INTEGER
        ACCESS    read-only
        STATUS    mandatory
        DESCRIPTION
            "See DESCRIPTION of g3atmportpg1SGNumber1."
        ::= { g3atmportpg1Entry 28 }

    g3atmportpg1SGNumber28	OBJECT-TYPE
        SYNTAX    INTEGER
        ACCESS    read-only
        STATUS    mandatory
        DESCRIPTION
            "See DESCRIPTION of g3atmportpg1SGNumber1."
        ::= { g3atmportpg1Entry 29 }

    g3atmportpg1SGNumber29	OBJECT-TYPE
        SYNTAX    INTEGER
        ACCESS    read-only
        STATUS    mandatory
        DESCRIPTION
            "See DESCRIPTION of g3atmportpg1SGNumber1."
        ::= { g3atmportpg1Entry 30 }

    g3atmportpg1SGNumber30	OBJECT-TYPE
        SYNTAX    INTEGER
        ACCESS    read-only
        STATUS    mandatory
        DESCRIPTION
            "See DESCRIPTION of g3atmportpg1SGNumber1."
        ::= { g3atmportpg1Entry 31 }

    g3atmportpg1SGNumber31	OBJECT-TYPE
        SYNTAX    INTEGER
        ACCESS    read-only
        STATUS    mandatory
        DESCRIPTION
            "See DESCRIPTION of g3atmportpg1SGNumber1."
        ::= { g3atmportpg1Entry 32 }

    g3atmportpg1SGNumber32	OBJECT-TYPE
        SYNTAX    INTEGER
        ACCESS    read-only
        STATUS    mandatory
        DESCRIPTION
            "See DESCRIPTION of g3atmportpg1SGNumber1."
        ::= { g3atmportpg1Entry 33 }

    g3atmportpg1SGNumber33	OBJECT-TYPE
        SYNTAX    INTEGER
        ACCESS    read-only
        STATUS    mandatory
        DESCRIPTION
            "See DESCRIPTION of g3atmportpg1SGNumber1."
        ::= { g3atmportpg1Entry 34 }

    g3atmportpg1SGNumber34	OBJECT-TYPE
        SYNTAX    INTEGER
        ACCESS    read-only
        STATUS    mandatory
        DESCRIPTION
            "See DESCRIPTION of g3atmportpg1SGNumber1."
        ::= { g3atmportpg1Entry 35 }

    g3atmportpg1SGNumber35	OBJECT-TYPE
        SYNTAX    INTEGER
        ACCESS    read-only
        STATUS    mandatory
        DESCRIPTION
            "See DESCRIPTION of g3atmportpg1SGNumber1."
        ::= { g3atmportpg1Entry 36 }

    g3atmportpg1SGNumber36	OBJECT-TYPE
        SYNTAX    INTEGER
        ACCESS    read-only
        STATUS    mandatory
        DESCRIPTION
            "See DESCRIPTION of g3atmportpg1SGNumber1."
        ::= { g3atmportpg1Entry 37 }

    g3atmportpg1SGNumber37	OBJECT-TYPE
        SYNTAX    INTEGER
        ACCESS    read-only
        STATUS    mandatory
        DESCRIPTION
            "See DESCRIPTION of g3atmportpg1SGNumber1."
        ::= { g3atmportpg1Entry 38 }

    g3atmportpg1SGNumber38	OBJECT-TYPE
        SYNTAX    INTEGER
        ACCESS    read-only
        STATUS    mandatory
        DESCRIPTION
            "See DESCRIPTION of g3atmportpg1SGNumber1."
        ::= { g3atmportpg1Entry 39 }

    g3atmportpg1SGNumber39	OBJECT-TYPE
        SYNTAX    INTEGER
        ACCESS    read-only
        STATUS    mandatory
        DESCRIPTION
            "See DESCRIPTION of g3atmportpg1SGNumber1."
        ::= { g3atmportpg1Entry 40 }

    g3atmportpg1SGNumber40	OBJECT-TYPE
        SYNTAX    INTEGER
        ACCESS    read-only
        STATUS    mandatory
        DESCRIPTION
            "See DESCRIPTION of g3atmportpg1SGNumber1."
        ::= { g3atmportpg1Entry 41 }

    g3atmportpg1SGNumber41	OBJECT-TYPE
        SYNTAX    INTEGER
        ACCESS    read-only
        STATUS    mandatory
        DESCRIPTION
            "See DESCRIPTION of g3atmportpg1SGNumber1."
        ::= { g3atmportpg1Entry 42 }

    g3atmportpg1SGNumber42	OBJECT-TYPE
        SYNTAX    INTEGER
        ACCESS    read-only
        STATUS    mandatory
        DESCRIPTION
            "See DESCRIPTION of g3atmportpg1SGNumber1."
        ::= { g3atmportpg1Entry 43 }

    g3atmportpg1SGNumber43	OBJECT-TYPE
        SYNTAX    INTEGER
        ACCESS    read-only
        STATUS    mandatory
        DESCRIPTION
            "See DESCRIPTION of g3atmportpg1SGNumber1."
        ::= { g3atmportpg1Entry 44 }

    g3atmportpg1SGNumber44	OBJECT-TYPE
        SYNTAX    INTEGER
        ACCESS    read-only
        STATUS    mandatory
        DESCRIPTION
            "See DESCRIPTION of g3atmportpg1SGNumber1."
        ::= { g3atmportpg1Entry 45 }

    g3atmportpg1SGNumber45	OBJECT-TYPE
        SYNTAX    INTEGER
        ACCESS    read-only
        STATUS    mandatory
        DESCRIPTION
            "See DESCRIPTION of g3atmportpg1SGNumber1."
        ::= { g3atmportpg1Entry 46 }

    g3atmportpg1SGNumber46	OBJECT-TYPE
        SYNTAX    INTEGER
        ACCESS    read-only
        STATUS    mandatory
        DESCRIPTION
            "See DESCRIPTION of g3atmportpg1SGNumber1."
        ::= { g3atmportpg1Entry 47 }

    g3atmportpg1SGNumber47	OBJECT-TYPE
        SYNTAX    INTEGER
        ACCESS    read-only
        STATUS    mandatory
        DESCRIPTION
            "See DESCRIPTION of g3atmportpg1SGNumber1."
        ::= { g3atmportpg1Entry 48 }

    g3atmportpg1SGNumber48	OBJECT-TYPE
        SYNTAX    INTEGER
        ACCESS    read-only
        STATUS    mandatory
        DESCRIPTION
            "See DESCRIPTION of g3atmportpg1SGNumber1."
        ::= { g3atmportpg1Entry 49 }

    g3atmportpg1SGNumber49	OBJECT-TYPE
        SYNTAX    INTEGER
        ACCESS    read-only
        STATUS    mandatory
        DESCRIPTION
            "See DESCRIPTION of g3atmportpg1SGNumber1."
        ::= { g3atmportpg1Entry 50 }

    g3atmportpg1SGNumber50	OBJECT-TYPE
        SYNTAX    INTEGER
        ACCESS    read-only
        STATUS    mandatory
        DESCRIPTION
            "See DESCRIPTION of g3atmportpg1SGNumber1."
        ::= { g3atmportpg1Entry 51 }

    g3atmportpg1SGNumber51	OBJECT-TYPE
        SYNTAX    INTEGER
        ACCESS    read-only
        STATUS    mandatory
        DESCRIPTION
            "See DESCRIPTION of g3atmportpg1SGNumber1."
        ::= { g3atmportpg1Entry 52 }

    g3atmportpg1SGNumber52	OBJECT-TYPE
        SYNTAX    INTEGER
        ACCESS    read-only
        STATUS    mandatory
        DESCRIPTION
            "See DESCRIPTION of g3atmportpg1SGNumber1."
        ::= { g3atmportpg1Entry 53 }

    g3atmportpg1SGNumber53	OBJECT-TYPE
        SYNTAX    INTEGER
        ACCESS    read-only
        STATUS    mandatory
        DESCRIPTION
            "See DESCRIPTION of g3atmportpg1SGNumber1."
        ::= { g3atmportpg1Entry 54 }

    g3atmportpg1SGNumber54	OBJECT-TYPE
        SYNTAX    INTEGER
        ACCESS    read-only
        STATUS    mandatory
        DESCRIPTION
            "See DESCRIPTION of g3atmportpg1SGNumber1."
        ::= { g3atmportpg1Entry 55 }

    g3atmportpg1SGNumber55	OBJECT-TYPE
        SYNTAX    INTEGER
        ACCESS    read-only
        STATUS    mandatory
        DESCRIPTION
            "See DESCRIPTION of g3atmportpg1SGNumber1."
        ::= { g3atmportpg1Entry 56 }

    g3atmportpg1SGNumber56	OBJECT-TYPE
        SYNTAX    INTEGER
        ACCESS    read-only
        STATUS    mandatory
        DESCRIPTION
            "See DESCRIPTION of g3atmportpg1SGNumber1."
        ::= { g3atmportpg1Entry 57 }

    g3atmportpg1SGNumber57	OBJECT-TYPE
        SYNTAX    INTEGER
        ACCESS    read-only
        STATUS    mandatory
        DESCRIPTION
            "See DESCRIPTION of g3atmportpg1SGNumber1."
        ::= { g3atmportpg1Entry 58 }

    g3atmportpg1SGNumber58	OBJECT-TYPE
        SYNTAX    INTEGER
        ACCESS    read-only
        STATUS    mandatory
        DESCRIPTION
            "See DESCRIPTION of g3atmportpg1SGNumber1."
        ::= { g3atmportpg1Entry 59 }

    g3atmportpg1SGNumber59	OBJECT-TYPE
        SYNTAX    INTEGER
        ACCESS    read-only
        STATUS    mandatory
        DESCRIPTION
            "See DESCRIPTION of g3atmportpg1SGNumber1."
        ::= { g3atmportpg1Entry 60 }

    g3atmportpg1SGNumber60	OBJECT-TYPE
        SYNTAX    INTEGER
        ACCESS    read-only
        STATUS    mandatory
        DESCRIPTION
            "See DESCRIPTION of g3atmportpg1SGNumber1."
        ::= { g3atmportpg1Entry 61 }

    g3atmportpg1SGNumber61	OBJECT-TYPE
        SYNTAX    INTEGER
        ACCESS    read-only
        STATUS    mandatory
        DESCRIPTION
            "See DESCRIPTION of g3atmportpg1SGNumber1."
        ::= { g3atmportpg1Entry 62 }

    g3atmportpg1SGNumber62	OBJECT-TYPE
        SYNTAX    INTEGER
        ACCESS    read-only
        STATUS    mandatory
        DESCRIPTION
            "See DESCRIPTION of g3atmportpg1SGNumber1."
        ::= { g3atmportpg1Entry 63 }

    g3atmportpg1SGNumber63	OBJECT-TYPE
        SYNTAX    INTEGER
        ACCESS    read-only
        STATUS    mandatory
        DESCRIPTION
            "See DESCRIPTION of g3atmportpg1SGNumber1."
        ::= { g3atmportpg1Entry 64 }

    g3atmportpg1SGNumber64	OBJECT-TYPE
        SYNTAX    INTEGER
        ACCESS    read-only
        STATUS    mandatory
        DESCRIPTION
            "See DESCRIPTION of g3atmportpg1SGNumber1."
        ::= { g3atmportpg1Entry 65 }

    g3atmportpg1SGNumber65	OBJECT-TYPE
        SYNTAX    INTEGER
        ACCESS    read-only
        STATUS    mandatory
        DESCRIPTION
            "See DESCRIPTION of g3atmportpg1SGNumber1."
        ::= { g3atmportpg1Entry 66 }

    g3atmportpg1SGNumber66	OBJECT-TYPE
        SYNTAX    INTEGER
        ACCESS    read-only
        STATUS    mandatory
        DESCRIPTION
            "See DESCRIPTION of g3atmportpg1SGNumber1."
        ::= { g3atmportpg1Entry 67 }

    g3atmportpg1SGNumber67	OBJECT-TYPE
        SYNTAX    INTEGER
        ACCESS    read-only
        STATUS    mandatory
        DESCRIPTION
            "See DESCRIPTION of g3atmportpg1SGNumber1."
        ::= { g3atmportpg1Entry 68 }

    g3atmportpg1SGNumber68	OBJECT-TYPE
        SYNTAX    INTEGER
        ACCESS    read-only
        STATUS    mandatory
        DESCRIPTION
            "See DESCRIPTION of g3atmportpg1SGNumber1."
        ::= { g3atmportpg1Entry 69 }

    g3atmportpg1SGNumber69	OBJECT-TYPE
        SYNTAX    INTEGER
        ACCESS    read-only
        STATUS    mandatory
        DESCRIPTION
            "See DESCRIPTION of g3atmportpg1SGNumber1."
        ::= { g3atmportpg1Entry 70 }

    g3atmportpg1SGNumber70	OBJECT-TYPE
        SYNTAX    INTEGER
        ACCESS    read-only
        STATUS    mandatory
        DESCRIPTION
            "See DESCRIPTION of g3atmportpg1SGNumber1."
        ::= { g3atmportpg1Entry 71 }

    g3atmportpg1SGNumber71	OBJECT-TYPE
        SYNTAX    INTEGER
        ACCESS    read-only
        STATUS    mandatory
        DESCRIPTION
            "See DESCRIPTION of g3atmportpg1SGNumber1."
        ::= { g3atmportpg1Entry 72 }

    g3atmportpg1SGNumber72	OBJECT-TYPE
        SYNTAX    INTEGER
        ACCESS    read-only
        STATUS    mandatory
        DESCRIPTION
            "See DESCRIPTION of g3atmportpg1SGNumber1."
        ::= { g3atmportpg1Entry 73 }

    g3atmportpg1SGNumber73	OBJECT-TYPE
        SYNTAX    INTEGER
        ACCESS    read-only
        STATUS    mandatory
        DESCRIPTION
            "See DESCRIPTION of g3atmportpg1SGNumber1."
        ::= { g3atmportpg1Entry 74 }

    g3atmportpg1SGNumber74	OBJECT-TYPE
        SYNTAX    INTEGER
        ACCESS    read-only
        STATUS    mandatory
        DESCRIPTION
            "See DESCRIPTION of g3atmportpg1SGNumber1."
        ::= { g3atmportpg1Entry 75 }

    g3atmportpg1SGNumber75	OBJECT-TYPE
        SYNTAX    INTEGER
        ACCESS    read-only
        STATUS    mandatory
        DESCRIPTION
            "See DESCRIPTION of g3atmportpg1SGNumber1."
        ::= { g3atmportpg1Entry 76 }

    g3atmportpg1SGNumber76	OBJECT-TYPE
        SYNTAX    INTEGER
        ACCESS    read-only
        STATUS    mandatory
        DESCRIPTION
            "See DESCRIPTION of g3atmportpg1SGNumber1."
        ::= { g3atmportpg1Entry 77 }

    g3atmportpg1SGNumber77	OBJECT-TYPE
        SYNTAX    INTEGER
        ACCESS    read-only
        STATUS    mandatory
        DESCRIPTION
            "See DESCRIPTION of g3atmportpg1SGNumber1."
        ::= { g3atmportpg1Entry 78 }

    g3atmportpg1SGNumber78	OBJECT-TYPE
        SYNTAX    INTEGER
        ACCESS    read-only
        STATUS    mandatory
        DESCRIPTION
            "See DESCRIPTION of g3atmportpg1SGNumber1."
        ::= { g3atmportpg1Entry 79 }

    g3atmportpg1SGNumber79	OBJECT-TYPE
        SYNTAX    INTEGER
        ACCESS    read-only
        STATUS    mandatory
        DESCRIPTION
            "See DESCRIPTION of g3atmportpg1SGNumber1."
        ::= { g3atmportpg1Entry 80 }

    g3atmportpg1SGNumber80	OBJECT-TYPE
        SYNTAX    INTEGER
        ACCESS    read-only
        STATUS    mandatory
        DESCRIPTION
            "See DESCRIPTION of g3atmportpg1SGNumber1."
        ::= { g3atmportpg1Entry 81 }

    g3atmportpg1SGNumber81	OBJECT-TYPE
        SYNTAX    INTEGER
        ACCESS    read-only
        STATUS    mandatory
        DESCRIPTION
            "See DESCRIPTION of g3atmportpg1SGNumber1."
        ::= { g3atmportpg1Entry 82 }

    g3atmportpg1SGNumber82	OBJECT-TYPE
        SYNTAX    INTEGER
        ACCESS    read-only
        STATUS    mandatory
        DESCRIPTION
            "See DESCRIPTION of g3atmportpg1SGNumber1."
        ::= { g3atmportpg1Entry 83 }

    g3atmportpg1SGNumber83	OBJECT-TYPE
        SYNTAX    INTEGER
        ACCESS    read-only
        STATUS    mandatory
        DESCRIPTION
            "See DESCRIPTION of g3atmportpg1SGNumber1."
        ::= { g3atmportpg1Entry 84 }

    g3atmportpg1SGNumber84	OBJECT-TYPE
        SYNTAX    INTEGER
        ACCESS    read-only
        STATUS    mandatory
        DESCRIPTION
            "See DESCRIPTION of g3atmportpg1SGNumber1."
        ::= { g3atmportpg1Entry 85 }

    g3atmportpg1SGNumber85	OBJECT-TYPE
        SYNTAX    INTEGER
        ACCESS    read-only
        STATUS    mandatory
        DESCRIPTION
            "See DESCRIPTION of g3atmportpg1SGNumber1."
        ::= { g3atmportpg1Entry 86 }

    g3atmportpg1SGNumber86	OBJECT-TYPE
        SYNTAX    INTEGER
        ACCESS    read-only
        STATUS    mandatory
        DESCRIPTION
            "See DESCRIPTION of g3atmportpg1SGNumber1."
        ::= { g3atmportpg1Entry 87 }

    g3atmportpg1SGNumber87	OBJECT-TYPE
        SYNTAX    INTEGER
        ACCESS    read-only
        STATUS    mandatory
        DESCRIPTION
            "See DESCRIPTION of g3atmportpg1SGNumber1."
        ::= { g3atmportpg1Entry 88 }

    g3atmportpg1SGNumber88	OBJECT-TYPE
        SYNTAX    INTEGER
        ACCESS    read-only
        STATUS    mandatory
        DESCRIPTION
            "See DESCRIPTION of g3atmportpg1SGNumber1."
        ::= { g3atmportpg1Entry 89 }

    g3atmportpg1SGNumber89	OBJECT-TYPE
        SYNTAX    INTEGER
        ACCESS    read-only
        STATUS    mandatory
        DESCRIPTION
            "See DESCRIPTION of g3atmportpg1SGNumber1."
        ::= { g3atmportpg1Entry 90 }

    g3atmportpg1SGNumber90	OBJECT-TYPE
        SYNTAX    INTEGER
        ACCESS    read-only
        STATUS    mandatory
        DESCRIPTION
            "See DESCRIPTION of g3atmportpg1SGNumber1."
        ::= { g3atmportpg1Entry 91 }

    g3atmportpg1TGNumber1	OBJECT-TYPE
        SYNTAX    INTEGER
        ACCESS    read-only
        STATUS    mandatory
        DESCRIPTION
            "An INTEGER Object that uniquely identifies the trunk group
            associated with the ATM ports (1 to 90) on page 1 of the form."
        ::= { g3atmportpg1Entry 92 }

    g3atmportpg1TGNumber2	OBJECT-TYPE
        SYNTAX    INTEGER
        ACCESS    read-only
        STATUS    mandatory
        DESCRIPTION
            "See DESCRIPTION of g3atmportpg1TGNumber1."
        ::= { g3atmportpg1Entry 93 }

    g3atmportpg1TGNumber3	OBJECT-TYPE
        SYNTAX    INTEGER
        ACCESS    read-only
        STATUS    mandatory
        DESCRIPTION
            "See DESCRIPTION of g3atmportpg1TGNumber1."
        ::= { g3atmportpg1Entry 94 }

    g3atmportpg1TGNumber4	OBJECT-TYPE
        SYNTAX    INTEGER
        ACCESS    read-only
        STATUS    mandatory
        DESCRIPTION
            "See DESCRIPTION of g3atmportpg1TGNumber1."
        ::= { g3atmportpg1Entry 95 }

    g3atmportpg1TGNumber5	OBJECT-TYPE
        SYNTAX    INTEGER
        ACCESS    read-only
        STATUS    mandatory
        DESCRIPTION
            "See DESCRIPTION of g3atmportpg1TGNumber1."
        ::= { g3atmportpg1Entry 96 }

    g3atmportpg1TGNumber6	OBJECT-TYPE
        SYNTAX    INTEGER
        ACCESS    read-only
        STATUS    mandatory
        DESCRIPTION
            "See DESCRIPTION of g3atmportpg1TGNumber1."
        ::= { g3atmportpg1Entry 97 }

    g3atmportpg1TGNumber7	OBJECT-TYPE
        SYNTAX    INTEGER
        ACCESS    read-only
        STATUS    mandatory
        DESCRIPTION
            "See DESCRIPTION of g3atmportpg1TGNumber1."
        ::= { g3atmportpg1Entry 98 }

    g3atmportpg1TGNumber8	OBJECT-TYPE
        SYNTAX    INTEGER
        ACCESS    read-only
        STATUS    mandatory
        DESCRIPTION
            "See DESCRIPTION of g3atmportpg1TGNumber1."
        ::= { g3atmportpg1Entry 99 }

    g3atmportpg1TGNumber9	OBJECT-TYPE
        SYNTAX    INTEGER
        ACCESS    read-only
        STATUS    mandatory
        DESCRIPTION
            "See DESCRIPTION of g3atmportpg1TGNumber1."
        ::= { g3atmportpg1Entry 100 }

    g3atmportpg1TGNumber10	OBJECT-TYPE
        SYNTAX    INTEGER
        ACCESS    read-only
        STATUS    mandatory
        DESCRIPTION
            "See DESCRIPTION of g3atmportpg1TGNumber1."
        ::= { g3atmportpg1Entry 101 }

    g3atmportpg1TGNumber11	OBJECT-TYPE
        SYNTAX    INTEGER
        ACCESS    read-only
        STATUS    mandatory
        DESCRIPTION
            "See DESCRIPTION of g3atmportpg1TGNumber1."
        ::= { g3atmportpg1Entry 102 }

    g3atmportpg1TGNumber12	OBJECT-TYPE
        SYNTAX    INTEGER
        ACCESS    read-only
        STATUS    mandatory
        DESCRIPTION
            "See DESCRIPTION of g3atmportpg1TGNumber1."
        ::= { g3atmportpg1Entry 103 }

    g3atmportpg1TGNumber13	OBJECT-TYPE
        SYNTAX    INTEGER
        ACCESS    read-only
        STATUS    mandatory
        DESCRIPTION
            "See DESCRIPTION of g3atmportpg1TGNumber1."
        ::= { g3atmportpg1Entry 104 }

    g3atmportpg1TGNumber14	OBJECT-TYPE
        SYNTAX    INTEGER
        ACCESS    read-only
        STATUS    mandatory
        DESCRIPTION
            "See DESCRIPTION of g3atmportpg1TGNumber1."
        ::= { g3atmportpg1Entry 105 }

    g3atmportpg1TGNumber15	OBJECT-TYPE
        SYNTAX    INTEGER
        ACCESS    read-only
        STATUS    mandatory
        DESCRIPTION
            "See DESCRIPTION of g3atmportpg1TGNumber1."
        ::= { g3atmportpg1Entry 106 }

    g3atmportpg1TGNumber16	OBJECT-TYPE
        SYNTAX    INTEGER
        ACCESS    read-only
        STATUS    mandatory
        DESCRIPTION
            "See DESCRIPTION of g3atmportpg1TGNumber1."
        ::= { g3atmportpg1Entry 107 }

    g3atmportpg1TGNumber17	OBJECT-TYPE
        SYNTAX    INTEGER
        ACCESS    read-only
        STATUS    mandatory
        DESCRIPTION
            "See DESCRIPTION of g3atmportpg1TGNumber1."
        ::= { g3atmportpg1Entry 108 }

    g3atmportpg1TGNumber18	OBJECT-TYPE
        SYNTAX    INTEGER
        ACCESS    read-only
        STATUS    mandatory
        DESCRIPTION
            "See DESCRIPTION of g3atmportpg1TGNumber1."
        ::= { g3atmportpg1Entry 109 }

    g3atmportpg1TGNumber19	OBJECT-TYPE
        SYNTAX    INTEGER
        ACCESS    read-only
        STATUS    mandatory
        DESCRIPTION
            "See DESCRIPTION of g3atmportpg1TGNumber1."
        ::= { g3atmportpg1Entry 110 }

    g3atmportpg1TGNumber20	OBJECT-TYPE
        SYNTAX    INTEGER
        ACCESS    read-only
        STATUS    mandatory
        DESCRIPTION
            "See DESCRIPTION of g3atmportpg1TGNumber1."
        ::= { g3atmportpg1Entry 111 }

    g3atmportpg1TGNumber21	OBJECT-TYPE
        SYNTAX    INTEGER
        ACCESS    read-only
        STATUS    mandatory
        DESCRIPTION
            "See DESCRIPTION of g3atmportpg1TGNumber1."
        ::= { g3atmportpg1Entry 112 }

    g3atmportpg1TGNumber22	OBJECT-TYPE
        SYNTAX    INTEGER
        ACCESS    read-only
        STATUS    mandatory
        DESCRIPTION
            "See DESCRIPTION of g3atmportpg1TGNumber1."
        ::= { g3atmportpg1Entry 113 }

    g3atmportpg1TGNumber23	OBJECT-TYPE
        SYNTAX    INTEGER
        ACCESS    read-only
        STATUS    mandatory
        DESCRIPTION
            "See DESCRIPTION of g3atmportpg1TGNumber1."
        ::= { g3atmportpg1Entry 114 }

    g3atmportpg1TGNumber24	OBJECT-TYPE
        SYNTAX    INTEGER
        ACCESS    read-only
        STATUS    mandatory
        DESCRIPTION
            "See DESCRIPTION of g3atmportpg1TGNumber1."
        ::= { g3atmportpg1Entry 115 }

    g3atmportpg1TGNumber25	OBJECT-TYPE
        SYNTAX    INTEGER
        ACCESS    read-only
        STATUS    mandatory
        DESCRIPTION
            "See DESCRIPTION of g3atmportpg1TGNumber1."
        ::= { g3atmportpg1Entry 116 }

    g3atmportpg1TGNumber26	OBJECT-TYPE
        SYNTAX    INTEGER
        ACCESS    read-only
        STATUS    mandatory
        DESCRIPTION
            "See DESCRIPTION of g3atmportpg1TGNumber1."
        ::= { g3atmportpg1Entry 117 }

    g3atmportpg1TGNumber27	OBJECT-TYPE
        SYNTAX    INTEGER
        ACCESS    read-only
        STATUS    mandatory
        DESCRIPTION
            "See DESCRIPTION of g3atmportpg1TGNumber1."
        ::= { g3atmportpg1Entry 118 }

    g3atmportpg1TGNumber28	OBJECT-TYPE
        SYNTAX    INTEGER
        ACCESS    read-only
        STATUS    mandatory
        DESCRIPTION
            "See DESCRIPTION of g3atmportpg1TGNumber1."
        ::= { g3atmportpg1Entry 119 }

    g3atmportpg1TGNumber29	OBJECT-TYPE
        SYNTAX    INTEGER
        ACCESS    read-only
        STATUS    mandatory
        DESCRIPTION
            "See DESCRIPTION of g3atmportpg1TGNumber1."
        ::= { g3atmportpg1Entry 120 }

    g3atmportpg1TGNumber30	OBJECT-TYPE
        SYNTAX    INTEGER
        ACCESS    read-only
        STATUS    mandatory
        DESCRIPTION
            "See DESCRIPTION of g3atmportpg1TGNumber1."
        ::= { g3atmportpg1Entry 121 }

    g3atmportpg1TGNumber31	OBJECT-TYPE
        SYNTAX    INTEGER
        ACCESS    read-only
        STATUS    mandatory
        DESCRIPTION
            "See DESCRIPTION of g3atmportpg1TGNumber1."
        ::= { g3atmportpg1Entry 122 }

    g3atmportpg1TGNumber32	OBJECT-TYPE
        SYNTAX    INTEGER
        ACCESS    read-only
        STATUS    mandatory
        DESCRIPTION
            "See DESCRIPTION of g3atmportpg1TGNumber1."
        ::= { g3atmportpg1Entry 123 }

    g3atmportpg1TGNumber33	OBJECT-TYPE
        SYNTAX    INTEGER
        ACCESS    read-only
        STATUS    mandatory
        DESCRIPTION
            "See DESCRIPTION of g3atmportpg1TGNumber1."
        ::= { g3atmportpg1Entry 124 }

    g3atmportpg1TGNumber34	OBJECT-TYPE
        SYNTAX    INTEGER
        ACCESS    read-only
        STATUS    mandatory
        DESCRIPTION
            "See DESCRIPTION of g3atmportpg1TGNumber1."
        ::= { g3atmportpg1Entry 125 }

    g3atmportpg1TGNumber35	OBJECT-TYPE
        SYNTAX    INTEGER
        ACCESS    read-only
        STATUS    mandatory
        DESCRIPTION
            "See DESCRIPTION of g3atmportpg1TGNumber1."
        ::= { g3atmportpg1Entry 126 }

    g3atmportpg1TGNumber36	OBJECT-TYPE
        SYNTAX    INTEGER
        ACCESS    read-only
        STATUS    mandatory
        DESCRIPTION
            "See DESCRIPTION of g3atmportpg1TGNumber1."
        ::= { g3atmportpg1Entry 127 }

    g3atmportpg1TGNumber37	OBJECT-TYPE
        SYNTAX    INTEGER
        ACCESS    read-only
        STATUS    mandatory
        DESCRIPTION
            "See DESCRIPTION of g3atmportpg1TGNumber1."
        ::= { g3atmportpg1Entry 128 }

    g3atmportpg1TGNumber38	OBJECT-TYPE
        SYNTAX    INTEGER
        ACCESS    read-only
        STATUS    mandatory
        DESCRIPTION
            "See DESCRIPTION of g3atmportpg1TGNumber1."
        ::= { g3atmportpg1Entry 129 }

    g3atmportpg1TGNumber39	OBJECT-TYPE
        SYNTAX    INTEGER
        ACCESS    read-only
        STATUS    mandatory
        DESCRIPTION
            "See DESCRIPTION of g3atmportpg1TGNumber1."
        ::= { g3atmportpg1Entry 130 }

    g3atmportpg1TGNumber40	OBJECT-TYPE
        SYNTAX    INTEGER
        ACCESS    read-only
        STATUS    mandatory
        DESCRIPTION
            "See DESCRIPTION of g3atmportpg1TGNumber1."
        ::= { g3atmportpg1Entry 131 }

    g3atmportpg1TGNumber41	OBJECT-TYPE
        SYNTAX    INTEGER
        ACCESS    read-only
        STATUS    mandatory
        DESCRIPTION
            "See DESCRIPTION of g3atmportpg1TGNumber1."
        ::= { g3atmportpg1Entry 132 }

    g3atmportpg1TGNumber42	OBJECT-TYPE
        SYNTAX    INTEGER
        ACCESS    read-only
        STATUS    mandatory
        DESCRIPTION
            "See DESCRIPTION of g3atmportpg1TGNumber1."
        ::= { g3atmportpg1Entry 133 }

    g3atmportpg1TGNumber43	OBJECT-TYPE
        SYNTAX    INTEGER
        ACCESS    read-only
        STATUS    mandatory
        DESCRIPTION
            "See DESCRIPTION of g3atmportpg1TGNumber1."
        ::= { g3atmportpg1Entry 134 }

    g3atmportpg1TGNumber44	OBJECT-TYPE
        SYNTAX    INTEGER
        ACCESS    read-only
        STATUS    mandatory
        DESCRIPTION
            "See DESCRIPTION of g3atmportpg1TGNumber1."
        ::= { g3atmportpg1Entry 135 }

    g3atmportpg1TGNumber45	OBJECT-TYPE
        SYNTAX    INTEGER
        ACCESS    read-only
        STATUS    mandatory
        DESCRIPTION
            "See DESCRIPTION of g3atmportpg1TGNumber1."
        ::= { g3atmportpg1Entry 136 }

    g3atmportpg1TGNumber46	OBJECT-TYPE
        SYNTAX    INTEGER
        ACCESS    read-only
        STATUS    mandatory
        DESCRIPTION
            "See DESCRIPTION of g3atmportpg1TGNumber1."
        ::= { g3atmportpg1Entry 137 }

    g3atmportpg1TGNumber47	OBJECT-TYPE
        SYNTAX    INTEGER
        ACCESS    read-only
        STATUS    mandatory
        DESCRIPTION
            "See DESCRIPTION of g3atmportpg1TGNumber1."
        ::= { g3atmportpg1Entry 138 }

    g3atmportpg1TGNumber48	OBJECT-TYPE
        SYNTAX    INTEGER
        ACCESS    read-only
        STATUS    mandatory
        DESCRIPTION
            "See DESCRIPTION of g3atmportpg1TGNumber1."
        ::= { g3atmportpg1Entry 139 }

    g3atmportpg1TGNumber49	OBJECT-TYPE
        SYNTAX    INTEGER
        ACCESS    read-only
        STATUS    mandatory
        DESCRIPTION
            "See DESCRIPTION of g3atmportpg1TGNumber1."
        ::= { g3atmportpg1Entry 140 }

    g3atmportpg1TGNumber50	OBJECT-TYPE
        SYNTAX    INTEGER
        ACCESS    read-only
        STATUS    mandatory
        DESCRIPTION
            "See DESCRIPTION of g3atmportpg1TGNumber1."
        ::= { g3atmportpg1Entry 141 }

    g3atmportpg1TGNumber51	OBJECT-TYPE
        SYNTAX    INTEGER
        ACCESS    read-only
        STATUS    mandatory
        DESCRIPTION
            "See DESCRIPTION of g3atmportpg1TGNumber1."
        ::= { g3atmportpg1Entry 142 }

    g3atmportpg1TGNumber52	OBJECT-TYPE
        SYNTAX    INTEGER
        ACCESS    read-only
        STATUS    mandatory
        DESCRIPTION
            "See DESCRIPTION of g3atmportpg1TGNumber1."
        ::= { g3atmportpg1Entry 143 }

    g3atmportpg1TGNumber53	OBJECT-TYPE
        SYNTAX    INTEGER
        ACCESS    read-only
        STATUS    mandatory
        DESCRIPTION
            "See DESCRIPTION of g3atmportpg1TGNumber1."
        ::= { g3atmportpg1Entry 144 }

    g3atmportpg1TGNumber54	OBJECT-TYPE
        SYNTAX    INTEGER
        ACCESS    read-only
        STATUS    mandatory
        DESCRIPTION
            "See DESCRIPTION of g3atmportpg1TGNumber1."
        ::= { g3atmportpg1Entry 145 }

    g3atmportpg1TGNumber55	OBJECT-TYPE
        SYNTAX    INTEGER
        ACCESS    read-only
        STATUS    mandatory
        DESCRIPTION
            "See DESCRIPTION of g3atmportpg1TGNumber1."
        ::= { g3atmportpg1Entry 146 }

    g3atmportpg1TGNumber56	OBJECT-TYPE
        SYNTAX    INTEGER
        ACCESS    read-only
        STATUS    mandatory
        DESCRIPTION
            "See DESCRIPTION of g3atmportpg1TGNumber1."
        ::= { g3atmportpg1Entry 147 }

    g3atmportpg1TGNumber57	OBJECT-TYPE
        SYNTAX    INTEGER
        ACCESS    read-only
        STATUS    mandatory
        DESCRIPTION
            "See DESCRIPTION of g3atmportpg1TGNumber1."
        ::= { g3atmportpg1Entry 148 }

    g3atmportpg1TGNumber58	OBJECT-TYPE
        SYNTAX    INTEGER
        ACCESS    read-only
        STATUS    mandatory
        DESCRIPTION
            "See DESCRIPTION of g3atmportpg1TGNumber1."
        ::= { g3atmportpg1Entry 149 }

    g3atmportpg1TGNumber59	OBJECT-TYPE
        SYNTAX    INTEGER
        ACCESS    read-only
        STATUS    mandatory
        DESCRIPTION
            "See DESCRIPTION of g3atmportpg1TGNumber1."
        ::= { g3atmportpg1Entry 150 }

    g3atmportpg1TGNumber60	OBJECT-TYPE
        SYNTAX    INTEGER
        ACCESS    read-only
        STATUS    mandatory
        DESCRIPTION
            "See DESCRIPTION of g3atmportpg1TGNumber1."
        ::= { g3atmportpg1Entry 151 }

    g3atmportpg1TGNumber61	OBJECT-TYPE
        SYNTAX    INTEGER
        ACCESS    read-only
        STATUS    mandatory
        DESCRIPTION
            "See DESCRIPTION of g3atmportpg1TGNumber1."
        ::= { g3atmportpg1Entry 152 }

    g3atmportpg1TGNumber62	OBJECT-TYPE
        SYNTAX    INTEGER
        ACCESS    read-only
        STATUS    mandatory
        DESCRIPTION
            "See DESCRIPTION of g3atmportpg1TGNumber1."
        ::= { g3atmportpg1Entry 153 }

    g3atmportpg1TGNumber63	OBJECT-TYPE
        SYNTAX    INTEGER
        ACCESS    read-only
        STATUS    mandatory
        DESCRIPTION
            "See DESCRIPTION of g3atmportpg1TGNumber1."
        ::= { g3atmportpg1Entry 154 }

    g3atmportpg1TGNumber64	OBJECT-TYPE
        SYNTAX    INTEGER
        ACCESS    read-only
        STATUS    mandatory
        DESCRIPTION
            "See DESCRIPTION of g3atmportpg1TGNumber1."
        ::= { g3atmportpg1Entry 155 }

    g3atmportpg1TGNumber65	OBJECT-TYPE
        SYNTAX    INTEGER
        ACCESS    read-only
        STATUS    mandatory
        DESCRIPTION
            "See DESCRIPTION of g3atmportpg1TGNumber1."
        ::= { g3atmportpg1Entry 156 }

    g3atmportpg1TGNumber66	OBJECT-TYPE
        SYNTAX    INTEGER
        ACCESS    read-only
        STATUS    mandatory
        DESCRIPTION
            "See DESCRIPTION of g3atmportpg1TGNumber1."
        ::= { g3atmportpg1Entry 157 }

    g3atmportpg1TGNumber67	OBJECT-TYPE
        SYNTAX    INTEGER
        ACCESS    read-only
        STATUS    mandatory
        DESCRIPTION
            "See DESCRIPTION of g3atmportpg1TGNumber1."
        ::= { g3atmportpg1Entry 158 }

    g3atmportpg1TGNumber68	OBJECT-TYPE
        SYNTAX    INTEGER
        ACCESS    read-only
        STATUS    mandatory
        DESCRIPTION
            "See DESCRIPTION of g3atmportpg1TGNumber1."
        ::= { g3atmportpg1Entry 159 }

    g3atmportpg1TGNumber69	OBJECT-TYPE
        SYNTAX    INTEGER
        ACCESS    read-only
        STATUS    mandatory
        DESCRIPTION
            "See DESCRIPTION of g3atmportpg1TGNumber1."
        ::= { g3atmportpg1Entry 160 }

    g3atmportpg1TGNumber70	OBJECT-TYPE
        SYNTAX    INTEGER
        ACCESS    read-only
        STATUS    mandatory
        DESCRIPTION
            "See DESCRIPTION of g3atmportpg1TGNumber1."
        ::= { g3atmportpg1Entry 161 }

    g3atmportpg1TGNumber71	OBJECT-TYPE
        SYNTAX    INTEGER
        ACCESS    read-only
        STATUS    mandatory
        DESCRIPTION
            "See DESCRIPTION of g3atmportpg1TGNumber1."
        ::= { g3atmportpg1Entry 162 }

    g3atmportpg1TGNumber72	OBJECT-TYPE
        SYNTAX    INTEGER
        ACCESS    read-only
        STATUS    mandatory
        DESCRIPTION
            "See DESCRIPTION of g3atmportpg1TGNumber1."
        ::= { g3atmportpg1Entry 163 }

    g3atmportpg1TGNumber73	OBJECT-TYPE
        SYNTAX    INTEGER
        ACCESS    read-only
        STATUS    mandatory
        DESCRIPTION
            "See DESCRIPTION of g3atmportpg1TGNumber1."
        ::= { g3atmportpg1Entry 164 }

    g3atmportpg1TGNumber74	OBJECT-TYPE
        SYNTAX    INTEGER
        ACCESS    read-only
        STATUS    mandatory
        DESCRIPTION
            "See DESCRIPTION of g3atmportpg1TGNumber1."
        ::= { g3atmportpg1Entry 165 }

    g3atmportpg1TGNumber75	OBJECT-TYPE
        SYNTAX    INTEGER
        ACCESS    read-only
        STATUS    mandatory
        DESCRIPTION
            "See DESCRIPTION of g3atmportpg1TGNumber1."
        ::= { g3atmportpg1Entry 166 }

    g3atmportpg1TGNumber76	OBJECT-TYPE
        SYNTAX    INTEGER
        ACCESS    read-only
        STATUS    mandatory
        DESCRIPTION
            "See DESCRIPTION of g3atmportpg1TGNumber1."
        ::= { g3atmportpg1Entry 167 }

    g3atmportpg1TGNumber77	OBJECT-TYPE
        SYNTAX    INTEGER
        ACCESS    read-only
        STATUS    mandatory
        DESCRIPTION
            "See DESCRIPTION of g3atmportpg1TGNumber1."
        ::= { g3atmportpg1Entry 168 }

    g3atmportpg1TGNumber78	OBJECT-TYPE
        SYNTAX    INTEGER
        ACCESS    read-only
        STATUS    mandatory
        DESCRIPTION
            "See DESCRIPTION of g3atmportpg1TGNumber1."
        ::= { g3atmportpg1Entry 169 }

    g3atmportpg1TGNumber79	OBJECT-TYPE
        SYNTAX    INTEGER
        ACCESS    read-only
        STATUS    mandatory
        DESCRIPTION
            "See DESCRIPTION of g3atmportpg1TGNumber1."
        ::= { g3atmportpg1Entry 170 }

    g3atmportpg1TGNumber80	OBJECT-TYPE
        SYNTAX    INTEGER
        ACCESS    read-only
        STATUS    mandatory
        DESCRIPTION
            "See DESCRIPTION of g3atmportpg1TGNumber1."
        ::= { g3atmportpg1Entry 171 }

    g3atmportpg1TGNumber81	OBJECT-TYPE
        SYNTAX    INTEGER
        ACCESS    read-only
        STATUS    mandatory
        DESCRIPTION
            "See DESCRIPTION of g3atmportpg1TGNumber1."
        ::= { g3atmportpg1Entry 172 }

    g3atmportpg1TGNumber82	OBJECT-TYPE
        SYNTAX    INTEGER
        ACCESS    read-only
        STATUS    mandatory
        DESCRIPTION
            "See DESCRIPTION of g3atmportpg1TGNumber1."
        ::= { g3atmportpg1Entry 173 }

    g3atmportpg1TGNumber83	OBJECT-TYPE
        SYNTAX    INTEGER
        ACCESS    read-only
        STATUS    mandatory
        DESCRIPTION
            "See DESCRIPTION of g3atmportpg1TGNumber1."
        ::= { g3atmportpg1Entry 174 }

    g3atmportpg1TGNumber84	OBJECT-TYPE
        SYNTAX    INTEGER
        ACCESS    read-only
        STATUS    mandatory
        DESCRIPTION
            "See DESCRIPTION of g3atmportpg1TGNumber1."
        ::= { g3atmportpg1Entry 175 }

    g3atmportpg1TGNumber85	OBJECT-TYPE
        SYNTAX    INTEGER
        ACCESS    read-only
        STATUS    mandatory
        DESCRIPTION
            "See DESCRIPTION of g3atmportpg1TGNumber1."
        ::= { g3atmportpg1Entry 176 }

    g3atmportpg1TGNumber86	OBJECT-TYPE
        SYNTAX    INTEGER
        ACCESS    read-only
        STATUS    mandatory
        DESCRIPTION
            "See DESCRIPTION of g3atmportpg1TGNumber1."
        ::= { g3atmportpg1Entry 177 }

    g3atmportpg1TGNumber87	OBJECT-TYPE
        SYNTAX    INTEGER
        ACCESS    read-only
        STATUS    mandatory
        DESCRIPTION
            "See DESCRIPTION of g3atmportpg1TGNumber1."
        ::= { g3atmportpg1Entry 178 }

    g3atmportpg1TGNumber88	OBJECT-TYPE
        SYNTAX    INTEGER
        ACCESS    read-only
        STATUS    mandatory
        DESCRIPTION
            "See DESCRIPTION of g3atmportpg1TGNumber1."
        ::= { g3atmportpg1Entry 179 }

    g3atmportpg1TGNumber89	OBJECT-TYPE
        SYNTAX    INTEGER
        ACCESS    read-only
        STATUS    mandatory
        DESCRIPTION
            "See DESCRIPTION of g3atmportpg1TGNumber1."
        ::= { g3atmportpg1Entry 180 }

    g3atmportpg1TGNumber90	OBJECT-TYPE
        SYNTAX    INTEGER
        ACCESS    read-only
        STATUS    mandatory
        DESCRIPTION
            "See DESCRIPTION of g3atmportpg1TGNumber1."
        ::= { g3atmportpg1Entry 181 }


    -- the g3atmportpg2 group

    g3atmportpg2Tage	OBJECT-TYPE
        SYNTAX    INTEGER
        ACCESS    read-only
        STATUS    mandatory
        DESCRIPTION
            "The number of timeticks since the atm port data was
            extracted from the switch by the G3 Proxy Agent. This object
            along with the g3atmportpg2Tintvl object allows the Network Manager
            to determine the validity of the atm port data in the
            cache and to control when the proxy agent extracts the
            atm port data from the switch."
        ::= { g3atmportpg2 1 }

    g3atmportpg2Tintvl	OBJECT-TYPE
        SYNTAX    INTEGER
        ACCESS    read-write
        STATUS    mandatory
        DESCRIPTION
            "An object containing the interval for which the atm port data extracted 
            from	the switch is considered valid by the proxy agent.  When a GET or
            GET-NEXT request for atm port data objects is received by the agent it 
            Uses the g3atmportpg2Tage and g3atmportpg2Tintvl objects to determine
            whether it should refresh the cached atmportpg2Table.  If
            g3atmportpg2Tstmp + g3atmportpg2Tintvl is less than the current
            value of the sysUpTime object then the agent refreshes the
            atmportpg2Table cache.  In either case it responds to the 
            requests it receives with the data it currently has in the cache."
        ::= { g3atmportpg2 2 }

    g3atmportpg2Tdelay	OBJECT-TYPE
        SYNTAX    INTEGER
        ACCESS    read-only
        STATUS    mandatory
        DESCRIPTION
            "An object containing the delay encountered in updating
            the cached data"
        ::= { g3atmportpg2 3 }

    g3atmportpg2Tretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3atmportpg2 4 }

    g3atmportpg2Tcount	OBJECT-TYPE
        SYNTAX    Gauge
        ACCESS    read-only
        STATUS    mandatory
        DESCRIPTION
            "A Gauge object containing the number of data records in the cache."
        ::= { g3atmportpg2 5 }

    g3atmportpg2Table	OBJECT-TYPE
        SYNTAX    SEQUENCE OF G3atmportpg2Entry
        ACCESS    not-accessible
        STATUS    mandatory
        DESCRIPTION
            "A list of g3atmportpg2 entries."
        ::= { g3atmportpg2 6 }

    g3atmportpg2Entry	OBJECT-TYPE
        SYNTAX    G3atmportpg2Entry
        ACCESS    not-accessible
        STATUS    mandatory
        DESCRIPTION
            "A g3atmportpg2 entry containing objects of the
            g3atmportpg2 information sent by the switch."
        INDEX    { g3atmportpg2Location }
        ::= { g3atmportpg2Table 1 }

    G3atmportpg2Entry ::= SEQUENCE {
        g3atmportpg2Location
            DisplayString,
        g3atmportpg2SGNumber91
            INTEGER,
        g3atmportpg2SGNumber92
            INTEGER,
        g3atmportpg2SGNumber93
            INTEGER,
        g3atmportpg2SGNumber94
            INTEGER,
        g3atmportpg2SGNumber95
            INTEGER,
        g3atmportpg2SGNumber96
            INTEGER,
        g3atmportpg2SGNumber97
            INTEGER,
        g3atmportpg2SGNumber98
            INTEGER,
        g3atmportpg2SGNumber99
            INTEGER,
        g3atmportpg2SGNumber100
            INTEGER,
        g3atmportpg2SGNumber101
            INTEGER,
        g3atmportpg2SGNumber102
            INTEGER,
        g3atmportpg2SGNumber103
            INTEGER,
        g3atmportpg2SGNumber104
            INTEGER,
        g3atmportpg2SGNumber105
            INTEGER,
        g3atmportpg2SGNumber106
            INTEGER,
        g3atmportpg2SGNumber107
            INTEGER,
        g3atmportpg2SGNumber108
            INTEGER,
        g3atmportpg2SGNumber109
            INTEGER,
        g3atmportpg2SGNumber110
            INTEGER,
        g3atmportpg2SGNumber111
            INTEGER,
        g3atmportpg2SGNumber112
            INTEGER,
        g3atmportpg2SGNumber113
            INTEGER,
        g3atmportpg2SGNumber114
            INTEGER,
        g3atmportpg2SGNumber115
            INTEGER,
        g3atmportpg2SGNumber116
            INTEGER,
        g3atmportpg2SGNumber117
            INTEGER,
        g3atmportpg2SGNumber118
            INTEGER,
        g3atmportpg2SGNumber119
            INTEGER,
        g3atmportpg2SGNumber120
            INTEGER,
        g3atmportpg2SGNumber121
            INTEGER,
        g3atmportpg2SGNumber122
            INTEGER,
        g3atmportpg2SGNumber123
            INTEGER,
        g3atmportpg2SGNumber124
            INTEGER,
        g3atmportpg2SGNumber125
            INTEGER,
        g3atmportpg2SGNumber126
            INTEGER,
        g3atmportpg2SGNumber127
            INTEGER,
        g3atmportpg2SGNumber128
            INTEGER,
        g3atmportpg2SGNumber129
            INTEGER,
        g3atmportpg2SGNumber130
            INTEGER,
        g3atmportpg2SGNumber131
            INTEGER,
        g3atmportpg2SGNumber132
            INTEGER,
        g3atmportpg2SGNumber133
            INTEGER,
        g3atmportpg2SGNumber134
            INTEGER,
        g3atmportpg2SGNumber135
            INTEGER,
        g3atmportpg2SGNumber136
            INTEGER,
        g3atmportpg2SGNumber137
            INTEGER,
        g3atmportpg2SGNumber138
            INTEGER,
        g3atmportpg2SGNumber139
            INTEGER,
        g3atmportpg2SGNumber140
            INTEGER,
        g3atmportpg2SGNumber141
            INTEGER,
        g3atmportpg2SGNumber142
            INTEGER,
        g3atmportpg2SGNumber143
            INTEGER,
        g3atmportpg2SGNumber144
            INTEGER,
        g3atmportpg2SGNumber145
            INTEGER,
        g3atmportpg2SGNumber146
            INTEGER,
        g3atmportpg2SGNumber147
            INTEGER,
        g3atmportpg2SGNumber148
            INTEGER,
        g3atmportpg2SGNumber149
            INTEGER,
        g3atmportpg2SGNumber150
            INTEGER,
        g3atmportpg2SGNumber151
            INTEGER,
        g3atmportpg2SGNumber152
            INTEGER,
        g3atmportpg2SGNumber153
            INTEGER,
        g3atmportpg2SGNumber154
            INTEGER,
        g3atmportpg2SGNumber155
            INTEGER,
        g3atmportpg2SGNumber156
            INTEGER,
        g3atmportpg2SGNumber157
            INTEGER,
        g3atmportpg2SGNumber158
            INTEGER,
        g3atmportpg2SGNumber159
            INTEGER,
        g3atmportpg2SGNumber160
            INTEGER,
        g3atmportpg2SGNumber161
            INTEGER,
        g3atmportpg2SGNumber162
            INTEGER,
        g3atmportpg2SGNumber163
            INTEGER,
        g3atmportpg2SGNumber164
            INTEGER,
        g3atmportpg2SGNumber165
            INTEGER,
        g3atmportpg2SGNumber166
            INTEGER,
        g3atmportpg2SGNumber167
            INTEGER,
        g3atmportpg2SGNumber168
            INTEGER,
        g3atmportpg2SGNumber169
            INTEGER,
        g3atmportpg2SGNumber170
            INTEGER,
        g3atmportpg2SGNumber171
            INTEGER,
        g3atmportpg2SGNumber172
            INTEGER,
        g3atmportpg2SGNumber173
            INTEGER,
        g3atmportpg2SGNumber174
            INTEGER,
        g3atmportpg2SGNumber175
            INTEGER,
        g3atmportpg2SGNumber176
            INTEGER,
        g3atmportpg2SGNumber177
            INTEGER,
        g3atmportpg2SGNumber178
            INTEGER,
        g3atmportpg2SGNumber179
            INTEGER,
        g3atmportpg2SGNumber180
            INTEGER,
        g3atmportpg2TGNumber91
            INTEGER,
        g3atmportpg2TGNumber92
            INTEGER,
        g3atmportpg2TGNumber93
            INTEGER,
        g3atmportpg2TGNumber94
            INTEGER,
        g3atmportpg2TGNumber95
            INTEGER,
        g3atmportpg2TGNumber96
            INTEGER,
        g3atmportpg2TGNumber97
            INTEGER,
        g3atmportpg2TGNumber98
            INTEGER,
        g3atmportpg2TGNumber99
            INTEGER,
        g3atmportpg2TGNumber100
            INTEGER,
        g3atmportpg2TGNumber101
            INTEGER,
        g3atmportpg2TGNumber102
            INTEGER,
        g3atmportpg2TGNumber103
            INTEGER,
        g3atmportpg2TGNumber104
            INTEGER,
        g3atmportpg2TGNumber105
            INTEGER,
        g3atmportpg2TGNumber106
            INTEGER,
        g3atmportpg2TGNumber107
            INTEGER,
        g3atmportpg2TGNumber108
            INTEGER,
        g3atmportpg2TGNumber109
            INTEGER,
        g3atmportpg2TGNumber110
            INTEGER,
        g3atmportpg2TGNumber111
            INTEGER,
        g3atmportpg2TGNumber112
            INTEGER,
        g3atmportpg2TGNumber113
            INTEGER,
        g3atmportpg2TGNumber114
            INTEGER,
        g3atmportpg2TGNumber115
            INTEGER,
        g3atmportpg2TGNumber116
            INTEGER,
        g3atmportpg2TGNumber117
            INTEGER,
        g3atmportpg2TGNumber118
            INTEGER,
        g3atmportpg2TGNumber119
            INTEGER,
        g3atmportpg2TGNumber120
            INTEGER,
        g3atmportpg2TGNumber121
            INTEGER,
        g3atmportpg2TGNumber122
            INTEGER,
        g3atmportpg2TGNumber123
            INTEGER,
        g3atmportpg2TGNumber124
            INTEGER,
        g3atmportpg2TGNumber125
            INTEGER,
        g3atmportpg2TGNumber126
            INTEGER,
        g3atmportpg2TGNumber127
            INTEGER,
        g3atmportpg2TGNumber128
            INTEGER,
        g3atmportpg2TGNumber129
            INTEGER,
        g3atmportpg2TGNumber130
            INTEGER,
        g3atmportpg2TGNumber131
            INTEGER,
        g3atmportpg2TGNumber132
            INTEGER,
        g3atmportpg2TGNumber133
            INTEGER,
        g3atmportpg2TGNumber134
            INTEGER,
        g3atmportpg2TGNumber135
            INTEGER,
        g3atmportpg2TGNumber136
            INTEGER,
        g3atmportpg2TGNumber137
            INTEGER,
        g3atmportpg2TGNumber138
            INTEGER,
        g3atmportpg2TGNumber139
            INTEGER,
        g3atmportpg2TGNumber140
            INTEGER,
        g3atmportpg2TGNumber141
            INTEGER,
        g3atmportpg2TGNumber142
            INTEGER,
        g3atmportpg2TGNumber143
            INTEGER,
        g3atmportpg2TGNumber144
            INTEGER,
        g3atmportpg2TGNumber145
            INTEGER,
        g3atmportpg2TGNumber146
            INTEGER,
        g3atmportpg2TGNumber147
            INTEGER,
        g3atmportpg2TGNumber148
            INTEGER,
        g3atmportpg2TGNumber149
            INTEGER,
        g3atmportpg2TGNumber150
            INTEGER,
        g3atmportpg2TGNumber151
            INTEGER,
        g3atmportpg2TGNumber152
            INTEGER,
        g3atmportpg2TGNumber153
            INTEGER,
        g3atmportpg2TGNumber154
            INTEGER,
        g3atmportpg2TGNumber155
            INTEGER,
        g3atmportpg2TGNumber156
            INTEGER,
        g3atmportpg2TGNumber157
            INTEGER,
        g3atmportpg2TGNumber158
            INTEGER,
        g3atmportpg2TGNumber159
            INTEGER,
        g3atmportpg2TGNumber160
            INTEGER,
        g3atmportpg2TGNumber161
            INTEGER,
        g3atmportpg2TGNumber162
            INTEGER,
        g3atmportpg2TGNumber163
            INTEGER,
        g3atmportpg2TGNumber164
            INTEGER,
        g3atmportpg2TGNumber165
            INTEGER,
        g3atmportpg2TGNumber166
            INTEGER,
        g3atmportpg2TGNumber167
            INTEGER,
        g3atmportpg2TGNumber168
            INTEGER,
        g3atmportpg2TGNumber169
            INTEGER,
        g3atmportpg2TGNumber170
            INTEGER,
        g3atmportpg2TGNumber171
            INTEGER,
        g3atmportpg2TGNumber172
            INTEGER,
        g3atmportpg2TGNumber173
            INTEGER,
        g3atmportpg2TGNumber174
            INTEGER,
        g3atmportpg2TGNumber175
            INTEGER,
        g3atmportpg2TGNumber176
            INTEGER,
        g3atmportpg2TGNumber177
            INTEGER,
        g3atmportpg2TGNumber178
            INTEGER,
        g3atmportpg2TGNumber179
            INTEGER,
        g3atmportpg2TGNumber180
            INTEGER
        }

    g3atmportpg2Location	OBJECT-TYPE
        SYNTAX    DisplayString (SIZE (0..7))
        ACCESS    read-only
        STATUS    mandatory
        DESCRIPTION
            "A DisplayString Object that uniquely identifies the ATM trunk
            board based on its location in the system. The syntax for the
            Board Number is as follows: cabinet(01-44):carrier(A-E):slot(01-20)."
        ::= { g3atmportpg2Entry 1 }

    g3atmportpg2SGNumber91	OBJECT-TYPE
        SYNTAX    INTEGER
        ACCESS    read-only
        STATUS    mandatory
        DESCRIPTION
            "An INTEGER Object that uniquely identifies the signaling group
            associated with the ATM ports (91 to 180) on page 2 of the form."
        ::= { g3atmportpg2Entry 2 }

    g3atmportpg2SGNumber92	OBJECT-TYPE
        SYNTAX    INTEGER
        ACCESS    read-only
        STATUS    mandatory
        DESCRIPTION
            "See DESCRIPTION of g3atmportpg2SGNumber91."
        ::= { g3atmportpg2Entry 3 }

    g3atmportpg2SGNumber93	OBJECT-TYPE
        SYNTAX    INTEGER
        ACCESS    read-only
        STATUS    mandatory
        DESCRIPTION
            "See DESCRIPTION of g3atmportpg2SGNumber91."
        ::= { g3atmportpg2Entry 4 }

    g3atmportpg2SGNumber94	OBJECT-TYPE
        SYNTAX    INTEGER
        ACCESS    read-only
        STATUS    mandatory
        DESCRIPTION
            "See DESCRIPTION of g3atmportpg2SGNumber91."
        ::= { g3atmportpg2Entry 5 }

    g3atmportpg2SGNumber95	OBJECT-TYPE
        SYNTAX    INTEGER
        ACCESS    read-only
        STATUS    mandatory
        DESCRIPTION
            "See DESCRIPTION of g3atmportpg2SGNumber91."
        ::= { g3atmportpg2Entry 6 }

    g3atmportpg2SGNumber96	OBJECT-TYPE
        SYNTAX    INTEGER
        ACCESS    read-only
        STATUS    mandatory
        DESCRIPTION
            "See DESCRIPTION of g3atmportpg2SGNumber91."
        ::= { g3atmportpg2Entry 7 }

    g3atmportpg2SGNumber97	OBJECT-TYPE
        SYNTAX    INTEGER
        ACCESS    read-only
        STATUS    mandatory
        DESCRIPTION
            "See DESCRIPTION of g3atmportpg2SGNumber91."
        ::= { g3atmportpg2Entry 8 }

    g3atmportpg2SGNumber98	OBJECT-TYPE
        SYNTAX    INTEGER
        ACCESS    read-only
        STATUS    mandatory
        DESCRIPTION
            "See DESCRIPTION of g3atmportpg2SGNumber91."
        ::= { g3atmportpg2Entry 9 }

    g3atmportpg2SGNumber99	OBJECT-TYPE
        SYNTAX    INTEGER
        ACCESS    read-only
        STATUS    mandatory
        DESCRIPTION
            "See DESCRIPTION of g3atmportpg2SGNumber91."
        ::= { g3atmportpg2Entry 10 }

    g3atmportpg2SGNumber100	OBJECT-TYPE
        SYNTAX    INTEGER
        ACCESS    read-only
        STATUS    mandatory
        DESCRIPTION
            "See DESCRIPTION of g3atmportpg2SGNumber91."
        ::= { g3atmportpg2Entry 11 }

    g3atmportpg2SGNumber101	OBJECT-TYPE
        SYNTAX    INTEGER
        ACCESS    read-only
        STATUS    mandatory
        DESCRIPTION
            "See DESCRIPTION of g3atmportpg2SGNumber91."
        ::= { g3atmportpg2Entry 12 }

    g3atmportpg2SGNumber102	OBJECT-TYPE
        SYNTAX    INTEGER
        ACCESS    read-only
        STATUS    mandatory
        DESCRIPTION
            "See DESCRIPTION of g3atmportpg2SGNumber91."
        ::= { g3atmportpg2Entry 13 }

    g3atmportpg2SGNumber103	OBJECT-TYPE
        SYNTAX    INTEGER
        ACCESS    read-only
        STATUS    mandatory
        DESCRIPTION
            "See DESCRIPTION of g3atmportpg2SGNumber91."
        ::= { g3atmportpg2Entry 14 }

    g3atmportpg2SGNumber104	OBJECT-TYPE
        SYNTAX    INTEGER
        ACCESS    read-only
        STATUS    mandatory
        DESCRIPTION
            "See DESCRIPTION of g3atmportpg2SGNumber91."
        ::= { g3atmportpg2Entry 15 }

    g3atmportpg2SGNumber105	OBJECT-TYPE
        SYNTAX    INTEGER
        ACCESS    read-only
        STATUS    mandatory
        DESCRIPTION
            "See DESCRIPTION of g3atmportpg2SGNumber91."
        ::= { g3atmportpg2Entry 16 }

    g3atmportpg2SGNumber106	OBJECT-TYPE
        SYNTAX    INTEGER
        ACCESS    read-only
        STATUS    mandatory
        DESCRIPTION
            "See DESCRIPTION of g3atmportpg2SGNumber91."
        ::= { g3atmportpg2Entry 17 }

    g3atmportpg2SGNumber107	OBJECT-TYPE
        SYNTAX    INTEGER
        ACCESS    read-only
        STATUS    mandatory
        DESCRIPTION
            "See DESCRIPTION of g3atmportpg2SGNumber91."
        ::= { g3atmportpg2Entry 18 }

    g3atmportpg2SGNumber108	OBJECT-TYPE
        SYNTAX    INTEGER
        ACCESS    read-only
        STATUS    mandatory
        DESCRIPTION
            "See DESCRIPTION of g3atmportpg2SGNumber91."
        ::= { g3atmportpg2Entry 19 }

    g3atmportpg2SGNumber109	OBJECT-TYPE
        SYNTAX    INTEGER
        ACCESS    read-only
        STATUS    mandatory
        DESCRIPTION
            "See DESCRIPTION of g3atmportpg2SGNumber91."
        ::= { g3atmportpg2Entry 20 }

    g3atmportpg2SGNumber110	OBJECT-TYPE
        SYNTAX    INTEGER
        ACCESS    read-only
        STATUS    mandatory
        DESCRIPTION
            "See DESCRIPTION of g3atmportpg2SGNumber91."
        ::= { g3atmportpg2Entry 21 }

    g3atmportpg2SGNumber111	OBJECT-TYPE
        SYNTAX    INTEGER
        ACCESS    read-only
        STATUS    mandatory
        DESCRIPTION
            "See DESCRIPTION of g3atmportpg2SGNumber91."
        ::= { g3atmportpg2Entry 22 }

    g3atmportpg2SGNumber112	OBJECT-TYPE
        SYNTAX    INTEGER
        ACCESS    read-only
        STATUS    mandatory
        DESCRIPTION
            "See DESCRIPTION of g3atmportpg2SGNumber91."
        ::= { g3atmportpg2Entry 23 }

    g3atmportpg2SGNumber113	OBJECT-TYPE
        SYNTAX    INTEGER
        ACCESS    read-only
        STATUS    mandatory
        DESCRIPTION
            "See DESCRIPTION of g3atmportpg2SGNumber91."
        ::= { g3atmportpg2Entry 24 }

    g3atmportpg2SGNumber114	OBJECT-TYPE
        SYNTAX    INTEGER
        ACCESS    read-only
        STATUS    mandatory
        DESCRIPTION
            "See DESCRIPTION of g3atmportpg2SGNumber91."
        ::= { g3atmportpg2Entry 25 }

    g3atmportpg2SGNumber115	OBJECT-TYPE
        SYNTAX    INTEGER
        ACCESS    read-only
        STATUS    mandatory
        DESCRIPTION
            "See DESCRIPTION of g3atmportpg2SGNumber91."
        ::= { g3atmportpg2Entry 26 }

    g3atmportpg2SGNumber116	OBJECT-TYPE
        SYNTAX    INTEGER
        ACCESS    read-only
        STATUS    mandatory
        DESCRIPTION
            "See DESCRIPTION of g3atmportpg2SGNumber91."
        ::= { g3atmportpg2Entry 27 }

    g3atmportpg2SGNumber117	OBJECT-TYPE
        SYNTAX    INTEGER
        ACCESS    read-only
        STATUS    mandatory
        DESCRIPTION
            "See DESCRIPTION of g3atmportpg2SGNumber91."
        ::= { g3atmportpg2Entry 28 }

    g3atmportpg2SGNumber118	OBJECT-TYPE
        SYNTAX    INTEGER
        ACCESS    read-only
        STATUS    mandatory
        DESCRIPTION
            "See DESCRIPTION of g3atmportpg2SGNumber91."
        ::= { g3atmportpg2Entry 29 }

    g3atmportpg2SGNumber119	OBJECT-TYPE
        SYNTAX    INTEGER
        ACCESS    read-only
        STATUS    mandatory
        DESCRIPTION
            "See DESCRIPTION of g3atmportpg2SGNumber91."
        ::= { g3atmportpg2Entry 30 }

    g3atmportpg2SGNumber120	OBJECT-TYPE
        SYNTAX    INTEGER
        ACCESS    read-only
        STATUS    mandatory
        DESCRIPTION
            "See DESCRIPTION of g3atmportpg2SGNumber91."
        ::= { g3atmportpg2Entry 31 }

    g3atmportpg2SGNumber121	OBJECT-TYPE
        SYNTAX    INTEGER
        ACCESS    read-only
        STATUS    mandatory
        DESCRIPTION
            "See DESCRIPTION of g3atmportpg2SGNumber91."
        ::= { g3atmportpg2Entry 32 }

    g3atmportpg2SGNumber122	OBJECT-TYPE
        SYNTAX    INTEGER
        ACCESS    read-only
        STATUS    mandatory
        DESCRIPTION
            "See DESCRIPTION of g3atmportpg2SGNumber91."
        ::= { g3atmportpg2Entry 33 }

    g3atmportpg2SGNumber123	OBJECT-TYPE
        SYNTAX    INTEGER
        ACCESS    read-only
        STATUS    mandatory
        DESCRIPTION
            "See DESCRIPTION of g3atmportpg2SGNumber91."
        ::= { g3atmportpg2Entry 34 }

    g3atmportpg2SGNumber124	OBJECT-TYPE
        SYNTAX    INTEGER
        ACCESS    read-only
        STATUS    mandatory
        DESCRIPTION
            "See DESCRIPTION of g3atmportpg2SGNumber91."
        ::= { g3atmportpg2Entry 35 }

    g3atmportpg2SGNumber125	OBJECT-TYPE
        SYNTAX    INTEGER
        ACCESS    read-only
        STATUS    mandatory
        DESCRIPTION
            "See DESCRIPTION of g3atmportpg2SGNumber91."
        ::= { g3atmportpg2Entry 36 }

    g3atmportpg2SGNumber126	OBJECT-TYPE
        SYNTAX    INTEGER
        ACCESS    read-only
        STATUS    mandatory
        DESCRIPTION
            "See DESCRIPTION of g3atmportpg2SGNumber91."
        ::= { g3atmportpg2Entry 37 }

    g3atmportpg2SGNumber127	OBJECT-TYPE
        SYNTAX    INTEGER
        ACCESS    read-only
        STATUS    mandatory
        DESCRIPTION
            "See DESCRIPTION of g3atmportpg2SGNumber91."
        ::= { g3atmportpg2Entry 38 }

    g3atmportpg2SGNumber128	OBJECT-TYPE
        SYNTAX    INTEGER
        ACCESS    read-only
        STATUS    mandatory
        DESCRIPTION
            "See DESCRIPTION of g3atmportpg2SGNumber91."
        ::= { g3atmportpg2Entry 39 }

    g3atmportpg2SGNumber129	OBJECT-TYPE
        SYNTAX    INTEGER
        ACCESS    read-only
        STATUS    mandatory
        DESCRIPTION
            "See DESCRIPTION of g3atmportpg2SGNumber91."
        ::= { g3atmportpg2Entry 40 }

    g3atmportpg2SGNumber130	OBJECT-TYPE
        SYNTAX    INTEGER
        ACCESS    read-only
        STATUS    mandatory
        DESCRIPTION
            "See DESCRIPTION of g3atmportpg2SGNumber91."
        ::= { g3atmportpg2Entry 41 }

    g3atmportpg2SGNumber131	OBJECT-TYPE
        SYNTAX    INTEGER
        ACCESS    read-only
        STATUS    mandatory
        DESCRIPTION
            "See DESCRIPTION of g3atmportpg2SGNumber91."
        ::= { g3atmportpg2Entry 42 }

    g3atmportpg2SGNumber132	OBJECT-TYPE
        SYNTAX    INTEGER
        ACCESS    read-only
        STATUS    mandatory
        DESCRIPTION
            "See DESCRIPTION of g3atmportpg2SGNumber91."
        ::= { g3atmportpg2Entry 43 }

    g3atmportpg2SGNumber133	OBJECT-TYPE
        SYNTAX    INTEGER
        ACCESS    read-only
        STATUS    mandatory
        DESCRIPTION
            "See DESCRIPTION of g3atmportpg2SGNumber91."
        ::= { g3atmportpg2Entry 44 }

    g3atmportpg2SGNumber134	OBJECT-TYPE
        SYNTAX    INTEGER
        ACCESS    read-only
        STATUS    mandatory
        DESCRIPTION
            "See DESCRIPTION of g3atmportpg2SGNumber91."
        ::= { g3atmportpg2Entry 45 }

    g3atmportpg2SGNumber135	OBJECT-TYPE
        SYNTAX    INTEGER
        ACCESS    read-only
        STATUS    mandatory
        DESCRIPTION
            "See DESCRIPTION of g3atmportpg2SGNumber91."
        ::= { g3atmportpg2Entry 46 }

    g3atmportpg2SGNumber136	OBJECT-TYPE
        SYNTAX    INTEGER
        ACCESS    read-only
        STATUS    mandatory
        DESCRIPTION
            "See DESCRIPTION of g3atmportpg2SGNumber91."
        ::= { g3atmportpg2Entry 47 }

    g3atmportpg2SGNumber137	OBJECT-TYPE
        SYNTAX    INTEGER
        ACCESS    read-only
        STATUS    mandatory
        DESCRIPTION
            "See DESCRIPTION of g3atmportpg2SGNumber91."
        ::= { g3atmportpg2Entry 48 }

    g3atmportpg2SGNumber138	OBJECT-TYPE
        SYNTAX    INTEGER
        ACCESS    read-only
        STATUS    mandatory
        DESCRIPTION
            "See DESCRIPTION of g3atmportpg2SGNumber91."
        ::= { g3atmportpg2Entry 49 }

    g3atmportpg2SGNumber139	OBJECT-TYPE
        SYNTAX    INTEGER
        ACCESS    read-only
        STATUS    mandatory
        DESCRIPTION
            "See DESCRIPTION of g3atmportpg2SGNumber91."
        ::= { g3atmportpg2Entry 50 }

    g3atmportpg2SGNumber140	OBJECT-TYPE
        SYNTAX    INTEGER
        ACCESS    read-only
        STATUS    mandatory
        DESCRIPTION
            "See DESCRIPTION of g3atmportpg2SGNumber91."
        ::= { g3atmportpg2Entry 51 }

    g3atmportpg2SGNumber141	OBJECT-TYPE
        SYNTAX    INTEGER
        ACCESS    read-only
        STATUS    mandatory
        DESCRIPTION
            "See DESCRIPTION of g3atmportpg2SGNumber91."
        ::= { g3atmportpg2Entry 52 }

    g3atmportpg2SGNumber142	OBJECT-TYPE
        SYNTAX    INTEGER
        ACCESS    read-only
        STATUS    mandatory
        DESCRIPTION
            "See DESCRIPTION of g3atmportpg2SGNumber91."
        ::= { g3atmportpg2Entry 53 }

    g3atmportpg2SGNumber143	OBJECT-TYPE
        SYNTAX    INTEGER
        ACCESS    read-only
        STATUS    mandatory
        DESCRIPTION
            "See DESCRIPTION of g3atmportpg2SGNumber91."
        ::= { g3atmportpg2Entry 54 }

    g3atmportpg2SGNumber144	OBJECT-TYPE
        SYNTAX    INTEGER
        ACCESS    read-only
        STATUS    mandatory
        DESCRIPTION
            "See DESCRIPTION of g3atmportpg2SGNumber91."
        ::= { g3atmportpg2Entry 55 }

    g3atmportpg2SGNumber145	OBJECT-TYPE
        SYNTAX    INTEGER
        ACCESS    read-only
        STATUS    mandatory
        DESCRIPTION
            "See DESCRIPTION of g3atmportpg2SGNumber91."
        ::= { g3atmportpg2Entry 56 }

    g3atmportpg2SGNumber146	OBJECT-TYPE
        SYNTAX    INTEGER
        ACCESS    read-only
        STATUS    mandatory
        DESCRIPTION
            "See DESCRIPTION of g3atmportpg2SGNumber91."
        ::= { g3atmportpg2Entry 57 }

    g3atmportpg2SGNumber147	OBJECT-TYPE
        SYNTAX    INTEGER
        ACCESS    read-only
        STATUS    mandatory
        DESCRIPTION
            "See DESCRIPTION of g3atmportpg2SGNumber91."
        ::= { g3atmportpg2Entry 58 }

    g3atmportpg2SGNumber148	OBJECT-TYPE
        SYNTAX    INTEGER
        ACCESS    read-only
        STATUS    mandatory
        DESCRIPTION
            "See DESCRIPTION of g3atmportpg2SGNumber91."
        ::= { g3atmportpg2Entry 59 }

    g3atmportpg2SGNumber149	OBJECT-TYPE
        SYNTAX    INTEGER
        ACCESS    read-only
        STATUS    mandatory
        DESCRIPTION
            "See DESCRIPTION of g3atmportpg2SGNumber91."
        ::= { g3atmportpg2Entry 60 }

    g3atmportpg2SGNumber150	OBJECT-TYPE
        SYNTAX    INTEGER
        ACCESS    read-only
        STATUS    mandatory
        DESCRIPTION
            "See DESCRIPTION of g3atmportpg2SGNumber91."
        ::= { g3atmportpg2Entry 61 }

    g3atmportpg2SGNumber151	OBJECT-TYPE
        SYNTAX    INTEGER
        ACCESS    read-only
        STATUS    mandatory
        DESCRIPTION
            "See DESCRIPTION of g3atmportpg2SGNumber91."
        ::= { g3atmportpg2Entry 62 }

    g3atmportpg2SGNumber152	OBJECT-TYPE
        SYNTAX    INTEGER
        ACCESS    read-only
        STATUS    mandatory
        DESCRIPTION
            "See DESCRIPTION of g3atmportpg2SGNumber91."
        ::= { g3atmportpg2Entry 63 }

    g3atmportpg2SGNumber153	OBJECT-TYPE
        SYNTAX    INTEGER
        ACCESS    read-only
        STATUS    mandatory
        DESCRIPTION
            "See DESCRIPTION of g3atmportpg2SGNumber91."
        ::= { g3atmportpg2Entry 64 }

    g3atmportpg2SGNumber154	OBJECT-TYPE
        SYNTAX    INTEGER
        ACCESS    read-only
        STATUS    mandatory
        DESCRIPTION
            "See DESCRIPTION of g3atmportpg2SGNumber91."
        ::= { g3atmportpg2Entry 65 }

    g3atmportpg2SGNumber155	OBJECT-TYPE
        SYNTAX    INTEGER
        ACCESS    read-only
        STATUS    mandatory
        DESCRIPTION
            "See DESCRIPTION of g3atmportpg2SGNumber91."
        ::= { g3atmportpg2Entry 66 }

    g3atmportpg2SGNumber156	OBJECT-TYPE
        SYNTAX    INTEGER
        ACCESS    read-only
        STATUS    mandatory
        DESCRIPTION
            "See DESCRIPTION of g3atmportpg2SGNumber91."
        ::= { g3atmportpg2Entry 67 }

    g3atmportpg2SGNumber157	OBJECT-TYPE
        SYNTAX    INTEGER
        ACCESS    read-only
        STATUS    mandatory
        DESCRIPTION
            "See DESCRIPTION of g3atmportpg2SGNumber91."
        ::= { g3atmportpg2Entry 68 }

    g3atmportpg2SGNumber158	OBJECT-TYPE
        SYNTAX    INTEGER
        ACCESS    read-only
        STATUS    mandatory
        DESCRIPTION
            "See DESCRIPTION of g3atmportpg2SGNumber91."
        ::= { g3atmportpg2Entry 69 }

    g3atmportpg2SGNumber159	OBJECT-TYPE
        SYNTAX    INTEGER
        ACCESS    read-only
        STATUS    mandatory
        DESCRIPTION
            "See DESCRIPTION of g3atmportpg2SGNumber91."
        ::= { g3atmportpg2Entry 70 }

    g3atmportpg2SGNumber160	OBJECT-TYPE
        SYNTAX    INTEGER
        ACCESS    read-only
        STATUS    mandatory
        DESCRIPTION
            "See DESCRIPTION of g3atmportpg2SGNumber91."
        ::= { g3atmportpg2Entry 71 }

    g3atmportpg2SGNumber161	OBJECT-TYPE
        SYNTAX    INTEGER
        ACCESS    read-only
        STATUS    mandatory
        DESCRIPTION
            "See DESCRIPTION of g3atmportpg2SGNumber91."
        ::= { g3atmportpg2Entry 72 }

    g3atmportpg2SGNumber162	OBJECT-TYPE
        SYNTAX    INTEGER
        ACCESS    read-only
        STATUS    mandatory
        DESCRIPTION
            "See DESCRIPTION of g3atmportpg2SGNumber91."
        ::= { g3atmportpg2Entry 73 }

    g3atmportpg2SGNumber163	OBJECT-TYPE
        SYNTAX    INTEGER
        ACCESS    read-only
        STATUS    mandatory
        DESCRIPTION
            "See DESCRIPTION of g3atmportpg2SGNumber91."
        ::= { g3atmportpg2Entry 74 }

    g3atmportpg2SGNumber164	OBJECT-TYPE
        SYNTAX    INTEGER
        ACCESS    read-only
        STATUS    mandatory
        DESCRIPTION
            "See DESCRIPTION of g3atmportpg2SGNumber91."
        ::= { g3atmportpg2Entry 75 }

    g3atmportpg2SGNumber165	OBJECT-TYPE
        SYNTAX    INTEGER
        ACCESS    read-only
        STATUS    mandatory
        DESCRIPTION
            "See DESCRIPTION of g3atmportpg2SGNumber91."
        ::= { g3atmportpg2Entry 76 }

    g3atmportpg2SGNumber166	OBJECT-TYPE
        SYNTAX    INTEGER
        ACCESS    read-only
        STATUS    mandatory
        DESCRIPTION
            "See DESCRIPTION of g3atmportpg2SGNumber91."
        ::= { g3atmportpg2Entry 77 }

    g3atmportpg2SGNumber167	OBJECT-TYPE
        SYNTAX    INTEGER
        ACCESS    read-only
        STATUS    mandatory
        DESCRIPTION
            "See DESCRIPTION of g3atmportpg2SGNumber91."
        ::= { g3atmportpg2Entry 78 }

    g3atmportpg2SGNumber168	OBJECT-TYPE
        SYNTAX    INTEGER
        ACCESS    read-only
        STATUS    mandatory
        DESCRIPTION
            "See DESCRIPTION of g3atmportpg2SGNumber91."
        ::= { g3atmportpg2Entry 79 }

    g3atmportpg2SGNumber169	OBJECT-TYPE
        SYNTAX    INTEGER
        ACCESS    read-only
        STATUS    mandatory
        DESCRIPTION
            "See DESCRIPTION of g3atmportpg2SGNumber91."
        ::= { g3atmportpg2Entry 80 }

    g3atmportpg2SGNumber170	OBJECT-TYPE
        SYNTAX    INTEGER
        ACCESS    read-only
        STATUS    mandatory
        DESCRIPTION
            "See DESCRIPTION of g3atmportpg2SGNumber91."
        ::= { g3atmportpg2Entry 81 }

    g3atmportpg2SGNumber171	OBJECT-TYPE
        SYNTAX    INTEGER
        ACCESS    read-only
        STATUS    mandatory
        DESCRIPTION
            "See DESCRIPTION of g3atmportpg2SGNumber91."
        ::= { g3atmportpg2Entry 82 }

    g3atmportpg2SGNumber172	OBJECT-TYPE
        SYNTAX    INTEGER
        ACCESS    read-only
        STATUS    mandatory
        DESCRIPTION
            "See DESCRIPTION of g3atmportpg2SGNumber91."
        ::= { g3atmportpg2Entry 83 }

    g3atmportpg2SGNumber173	OBJECT-TYPE
        SYNTAX    INTEGER
        ACCESS    read-only
        STATUS    mandatory
        DESCRIPTION
            "See DESCRIPTION of g3atmportpg2SGNumber91."
        ::= { g3atmportpg2Entry 84 }

    g3atmportpg2SGNumber174	OBJECT-TYPE
        SYNTAX    INTEGER
        ACCESS    read-only
        STATUS    mandatory
        DESCRIPTION
            "See DESCRIPTION of g3atmportpg2SGNumber91."
        ::= { g3atmportpg2Entry 85 }

    g3atmportpg2SGNumber175	OBJECT-TYPE
        SYNTAX    INTEGER
        ACCESS    read-only
        STATUS    mandatory
        DESCRIPTION
            "See DESCRIPTION of g3atmportpg2SGNumber91."
        ::= { g3atmportpg2Entry 86 }

    g3atmportpg2SGNumber176	OBJECT-TYPE
        SYNTAX    INTEGER
        ACCESS    read-only
        STATUS    mandatory
        DESCRIPTION
            "See DESCRIPTION of g3atmportpg2SGNumber91."
        ::= { g3atmportpg2Entry 87 }

    g3atmportpg2SGNumber177	OBJECT-TYPE
        SYNTAX    INTEGER
        ACCESS    read-only
        STATUS    mandatory
        DESCRIPTION
            "See DESCRIPTION of g3atmportpg2SGNumber91."
        ::= { g3atmportpg2Entry 88 }

    g3atmportpg2SGNumber178	OBJECT-TYPE
        SYNTAX    INTEGER
        ACCESS    read-only
        STATUS    mandatory
        DESCRIPTION
            "See DESCRIPTION of g3atmportpg2SGNumber91."
        ::= { g3atmportpg2Entry 89 }

    g3atmportpg2SGNumber179	OBJECT-TYPE
        SYNTAX    INTEGER
        ACCESS    read-only
        STATUS    mandatory
        DESCRIPTION
            "See DESCRIPTION of g3atmportpg2SGNumber91."
        ::= { g3atmportpg2Entry 90 }

    g3atmportpg2SGNumber180	OBJECT-TYPE
        SYNTAX    INTEGER
        ACCESS    read-only
        STATUS    mandatory
        DESCRIPTION
            "See DESCRIPTION of g3atmportpg2SGNumber91."
        ::= { g3atmportpg2Entry 91 }

    g3atmportpg2TGNumber91	OBJECT-TYPE
        SYNTAX    INTEGER
        ACCESS    read-only
        STATUS    mandatory
        DESCRIPTION
            "An INTEGER Object that uniquely identifies the trunk group
            associated with the ATM ports (91 to 180) on page 2 of the form."
        ::= { g3atmportpg2Entry 92 }

    g3atmportpg2TGNumber92	OBJECT-TYPE
        SYNTAX    INTEGER
        ACCESS    read-only
        STATUS    mandatory
        DESCRIPTION
            "See DESCRIPTION of g3atmportpg2TGNumber91."
        ::= { g3atmportpg2Entry 93 }

    g3atmportpg2TGNumber93	OBJECT-TYPE
        SYNTAX    INTEGER
        ACCESS    read-only
        STATUS    mandatory
        DESCRIPTION
            "See DESCRIPTION of g3atmportpg2TGNumber91."
        ::= { g3atmportpg2Entry 94 }

    g3atmportpg2TGNumber94	OBJECT-TYPE
        SYNTAX    INTEGER
        ACCESS    read-only
        STATUS    mandatory
        DESCRIPTION
            "See DESCRIPTION of g3atmportpg2TGNumber91."
        ::= { g3atmportpg2Entry 95 }

    g3atmportpg2TGNumber95	OBJECT-TYPE
        SYNTAX    INTEGER
        ACCESS    read-only
        STATUS    mandatory
        DESCRIPTION
            "See DESCRIPTION of g3atmportpg2TGNumber91."
        ::= { g3atmportpg2Entry 96 }

    g3atmportpg2TGNumber96	OBJECT-TYPE
        SYNTAX    INTEGER
        ACCESS    read-only
        STATUS    mandatory
        DESCRIPTION
            "See DESCRIPTION of g3atmportpg2TGNumber91."
        ::= { g3atmportpg2Entry 97 }

    g3atmportpg2TGNumber97	OBJECT-TYPE
        SYNTAX    INTEGER
        ACCESS    read-only
        STATUS    mandatory
        DESCRIPTION
            "See DESCRIPTION of g3atmportpg2TGNumber91."
        ::= { g3atmportpg2Entry 98 }

    g3atmportpg2TGNumber98	OBJECT-TYPE
        SYNTAX    INTEGER
        ACCESS    read-only
        STATUS    mandatory
        DESCRIPTION
            "See DESCRIPTION of g3atmportpg2TGNumber91."
        ::= { g3atmportpg2Entry 99 }

    g3atmportpg2TGNumber99	OBJECT-TYPE
        SYNTAX    INTEGER
        ACCESS    read-only
        STATUS    mandatory
        DESCRIPTION
            "See DESCRIPTION of g3atmportpg2TGNumber91."
        ::= { g3atmportpg2Entry 100 }

    g3atmportpg2TGNumber100	OBJECT-TYPE
        SYNTAX    INTEGER
        ACCESS    read-only
        STATUS    mandatory
        DESCRIPTION
            "See DESCRIPTION of g3atmportpg2TGNumber91."
        ::= { g3atmportpg2Entry 101 }

    g3atmportpg2TGNumber101	OBJECT-TYPE
        SYNTAX    INTEGER
        ACCESS    read-only
        STATUS    mandatory
        DESCRIPTION
            "See DESCRIPTION of g3atmportpg2TGNumber91."
        ::= { g3atmportpg2Entry 102 }

    g3atmportpg2TGNumber102	OBJECT-TYPE
        SYNTAX    INTEGER
        ACCESS    read-only
        STATUS    mandatory
        DESCRIPTION
            "See DESCRIPTION of g3atmportpg2TGNumber91."
        ::= { g3atmportpg2Entry 103 }

    g3atmportpg2TGNumber103	OBJECT-TYPE
        SYNTAX    INTEGER
        ACCESS    read-only
        STATUS    mandatory
        DESCRIPTION
            "See DESCRIPTION of g3atmportpg2TGNumber91."
        ::= { g3atmportpg2Entry 104 }

    g3atmportpg2TGNumber104	OBJECT-TYPE
        SYNTAX    INTEGER
        ACCESS    read-only
        STATUS    mandatory
        DESCRIPTION
            "See DESCRIPTION of g3atmportpg2TGNumber91."
        ::= { g3atmportpg2Entry 105 }

    g3atmportpg2TGNumber105	OBJECT-TYPE
        SYNTAX    INTEGER
        ACCESS    read-only
        STATUS    mandatory
        DESCRIPTION
            "See DESCRIPTION of g3atmportpg2TGNumber91."
        ::= { g3atmportpg2Entry 106 }

    g3atmportpg2TGNumber106	OBJECT-TYPE
        SYNTAX    INTEGER
        ACCESS    read-only
        STATUS    mandatory
        DESCRIPTION
            "See DESCRIPTION of g3atmportpg2TGNumber91."
        ::= { g3atmportpg2Entry 107 }

    g3atmportpg2TGNumber107	OBJECT-TYPE
        SYNTAX    INTEGER
        ACCESS    read-only
        STATUS    mandatory
        DESCRIPTION
            "See DESCRIPTION of g3atmportpg2TGNumber91."
        ::= { g3atmportpg2Entry 108 }

    g3atmportpg2TGNumber108	OBJECT-TYPE
        SYNTAX    INTEGER
        ACCESS    read-only
        STATUS    mandatory
        DESCRIPTION
            "See DESCRIPTION of g3atmportpg2TGNumber91."
        ::= { g3atmportpg2Entry 109 }

    g3atmportpg2TGNumber109	OBJECT-TYPE
        SYNTAX    INTEGER
        ACCESS    read-only
        STATUS    mandatory
        DESCRIPTION
            "See DESCRIPTION of g3atmportpg2TGNumber91."
        ::= { g3atmportpg2Entry 110 }

    g3atmportpg2TGNumber110	OBJECT-TYPE
        SYNTAX    INTEGER
        ACCESS    read-only
        STATUS    mandatory
        DESCRIPTION
            "See DESCRIPTION of g3atmportpg2TGNumber91."
        ::= { g3atmportpg2Entry 111 }

    g3atmportpg2TGNumber111	OBJECT-TYPE
        SYNTAX    INTEGER
        ACCESS    read-only
        STATUS    mandatory
        DESCRIPTION
            "See DESCRIPTION of g3atmportpg2TGNumber91."
        ::= { g3atmportpg2Entry 112 }

    g3atmportpg2TGNumber112	OBJECT-TYPE
        SYNTAX    INTEGER
        ACCESS    read-only
        STATUS    mandatory
        DESCRIPTION
            "See DESCRIPTION of g3atmportpg2TGNumber91."
        ::= { g3atmportpg2Entry 113 }

    g3atmportpg2TGNumber113	OBJECT-TYPE
        SYNTAX    INTEGER
        ACCESS    read-only
        STATUS    mandatory
        DESCRIPTION
            "See DESCRIPTION of g3atmportpg2TGNumber91."
        ::= { g3atmportpg2Entry 114 }

    g3atmportpg2TGNumber114	OBJECT-TYPE
        SYNTAX    INTEGER
        ACCESS    read-only
        STATUS    mandatory
        DESCRIPTION
            "See DESCRIPTION of g3atmportpg2TGNumber91."
        ::= { g3atmportpg2Entry 115 }

    g3atmportpg2TGNumber115	OBJECT-TYPE
        SYNTAX    INTEGER
        ACCESS    read-only
        STATUS    mandatory
        DESCRIPTION
            "See DESCRIPTION of g3atmportpg2TGNumber91."
        ::= { g3atmportpg2Entry 116 }

    g3atmportpg2TGNumber116	OBJECT-TYPE
        SYNTAX    INTEGER
        ACCESS    read-only
        STATUS    mandatory
        DESCRIPTION
            "See DESCRIPTION of g3atmportpg2TGNumber91."
        ::= { g3atmportpg2Entry 117 }

    g3atmportpg2TGNumber117	OBJECT-TYPE
        SYNTAX    INTEGER
        ACCESS    read-only
        STATUS    mandatory
        DESCRIPTION
            "See DESCRIPTION of g3atmportpg2TGNumber91."
        ::= { g3atmportpg2Entry 118 }

    g3atmportpg2TGNumber118	OBJECT-TYPE
        SYNTAX    INTEGER
        ACCESS    read-only
        STATUS    mandatory
        DESCRIPTION
            "See DESCRIPTION of g3atmportpg2TGNumber91."
        ::= { g3atmportpg2Entry 119 }

    g3atmportpg2TGNumber119	OBJECT-TYPE
        SYNTAX    INTEGER
        ACCESS    read-only
        STATUS    mandatory
        DESCRIPTION
            "See DESCRIPTION of g3atmportpg2TGNumber91."
        ::= { g3atmportpg2Entry 120 }

    g3atmportpg2TGNumber120	OBJECT-TYPE
        SYNTAX    INTEGER
        ACCESS    read-only
        STATUS    mandatory
        DESCRIPTION
            "See DESCRIPTION of g3atmportpg2TGNumber91."
        ::= { g3atmportpg2Entry 121 }

    g3atmportpg2TGNumber121	OBJECT-TYPE
        SYNTAX    INTEGER
        ACCESS    read-only
        STATUS    mandatory
        DESCRIPTION
            "See DESCRIPTION of g3atmportpg2TGNumber91."
        ::= { g3atmportpg2Entry 122 }

    g3atmportpg2TGNumber122	OBJECT-TYPE
        SYNTAX    INTEGER
        ACCESS    read-only
        STATUS    mandatory
        DESCRIPTION
            "See DESCRIPTION of g3atmportpg2TGNumber91."
        ::= { g3atmportpg2Entry 123 }

    g3atmportpg2TGNumber123	OBJECT-TYPE
        SYNTAX    INTEGER
        ACCESS    read-only
        STATUS    mandatory
        DESCRIPTION
            "See DESCRIPTION of g3atmportpg2TGNumber91."
        ::= { g3atmportpg2Entry 124 }

    g3atmportpg2TGNumber124	OBJECT-TYPE
        SYNTAX    INTEGER
        ACCESS    read-only
        STATUS    mandatory
        DESCRIPTION
            "See DESCRIPTION of g3atmportpg2TGNumber91."
        ::= { g3atmportpg2Entry 125 }

    g3atmportpg2TGNumber125	OBJECT-TYPE
        SYNTAX    INTEGER
        ACCESS    read-only
        STATUS    mandatory
        DESCRIPTION
            "See DESCRIPTION of g3atmportpg2TGNumber91."
        ::= { g3atmportpg2Entry 126 }

    g3atmportpg2TGNumber126	OBJECT-TYPE
        SYNTAX    INTEGER
        ACCESS    read-only
        STATUS    mandatory
        DESCRIPTION
            "See DESCRIPTION of g3atmportpg2TGNumber91."
        ::= { g3atmportpg2Entry 127 }

    g3atmportpg2TGNumber127	OBJECT-TYPE
        SYNTAX    INTEGER
        ACCESS    read-only
        STATUS    mandatory
        DESCRIPTION
            "See DESCRIPTION of g3atmportpg2TGNumber91."
        ::= { g3atmportpg2Entry 128 }

    g3atmportpg2TGNumber128	OBJECT-TYPE
        SYNTAX    INTEGER
        ACCESS    read-only
        STATUS    mandatory
        DESCRIPTION
            "See DESCRIPTION of g3atmportpg2TGNumber91."
        ::= { g3atmportpg2Entry 129 }

    g3atmportpg2TGNumber129	OBJECT-TYPE
        SYNTAX    INTEGER
        ACCESS    read-only
        STATUS    mandatory
        DESCRIPTION
            "See DESCRIPTION of g3atmportpg2TGNumber91."
        ::= { g3atmportpg2Entry 130 }

    g3atmportpg2TGNumber130	OBJECT-TYPE
        SYNTAX    INTEGER
        ACCESS    read-only
        STATUS    mandatory
        DESCRIPTION
            "See DESCRIPTION of g3atmportpg2TGNumber91."
        ::= { g3atmportpg2Entry 131 }

    g3atmportpg2TGNumber131	OBJECT-TYPE
        SYNTAX    INTEGER
        ACCESS    read-only
        STATUS    mandatory
        DESCRIPTION
            "See DESCRIPTION of g3atmportpg2TGNumber91."
        ::= { g3atmportpg2Entry 132 }

    g3atmportpg2TGNumber132	OBJECT-TYPE
        SYNTAX    INTEGER
        ACCESS    read-only
        STATUS    mandatory
        DESCRIPTION
            "See DESCRIPTION of g3atmportpg2TGNumber91."
        ::= { g3atmportpg2Entry 133 }

    g3atmportpg2TGNumber133	OBJECT-TYPE
        SYNTAX    INTEGER
        ACCESS    read-only
        STATUS    mandatory
        DESCRIPTION
            "See DESCRIPTION of g3atmportpg2TGNumber91."
        ::= { g3atmportpg2Entry 134 }

    g3atmportpg2TGNumber134	OBJECT-TYPE
        SYNTAX    INTEGER
        ACCESS    read-only
        STATUS    mandatory
        DESCRIPTION
            "See DESCRIPTION of g3atmportpg2TGNumber91."
        ::= { g3atmportpg2Entry 135 }

    g3atmportpg2TGNumber135	OBJECT-TYPE
        SYNTAX    INTEGER
        ACCESS    read-only
        STATUS    mandatory
        DESCRIPTION
            "See DESCRIPTION of g3atmportpg2TGNumber91."
        ::= { g3atmportpg2Entry 136 }

    g3atmportpg2TGNumber136	OBJECT-TYPE
        SYNTAX    INTEGER
        ACCESS    read-only
        STATUS    mandatory
        DESCRIPTION
            "See DESCRIPTION of g3atmportpg2TGNumber91."
        ::= { g3atmportpg2Entry 137 }

    g3atmportpg2TGNumber137	OBJECT-TYPE
        SYNTAX    INTEGER
        ACCESS    read-only
        STATUS    mandatory
        DESCRIPTION
            "See DESCRIPTION of g3atmportpg2TGNumber91."
        ::= { g3atmportpg2Entry 138 }

    g3atmportpg2TGNumber138	OBJECT-TYPE
        SYNTAX    INTEGER
        ACCESS    read-only
        STATUS    mandatory
        DESCRIPTION
            "See DESCRIPTION of g3atmportpg2TGNumber91."
        ::= { g3atmportpg2Entry 139 }

    g3atmportpg2TGNumber139	OBJECT-TYPE
        SYNTAX    INTEGER
        ACCESS    read-only
        STATUS    mandatory
        DESCRIPTION
            "See DESCRIPTION of g3atmportpg2TGNumber91."
        ::= { g3atmportpg2Entry 140 }

    g3atmportpg2TGNumber140	OBJECT-TYPE
        SYNTAX    INTEGER
        ACCESS    read-only
        STATUS    mandatory
        DESCRIPTION
            "See DESCRIPTION of g3atmportpg2TGNumber91."
        ::= { g3atmportpg2Entry 141 }

    g3atmportpg2TGNumber141	OBJECT-TYPE
        SYNTAX    INTEGER
        ACCESS    read-only
        STATUS    mandatory
        DESCRIPTION
            "See DESCRIPTION of g3atmportpg2TGNumber91."
        ::= { g3atmportpg2Entry 142 }

    g3atmportpg2TGNumber142	OBJECT-TYPE
        SYNTAX    INTEGER
        ACCESS    read-only
        STATUS    mandatory
        DESCRIPTION
            "See DESCRIPTION of g3atmportpg2TGNumber91."
        ::= { g3atmportpg2Entry 143 }

    g3atmportpg2TGNumber143	OBJECT-TYPE
        SYNTAX    INTEGER
        ACCESS    read-only
        STATUS    mandatory
        DESCRIPTION
            "See DESCRIPTION of g3atmportpg2TGNumber91."
        ::= { g3atmportpg2Entry 144 }

    g3atmportpg2TGNumber144	OBJECT-TYPE
        SYNTAX    INTEGER
        ACCESS    read-only
        STATUS    mandatory
        DESCRIPTION
            "See DESCRIPTION of g3atmportpg2TGNumber91."
        ::= { g3atmportpg2Entry 145 }

    g3atmportpg2TGNumber145	OBJECT-TYPE
        SYNTAX    INTEGER
        ACCESS    read-only
        STATUS    mandatory
        DESCRIPTION
            "See DESCRIPTION of g3atmportpg2TGNumber91."
        ::= { g3atmportpg2Entry 146 }

    g3atmportpg2TGNumber146	OBJECT-TYPE
        SYNTAX    INTEGER
        ACCESS    read-only
        STATUS    mandatory
        DESCRIPTION
            "See DESCRIPTION of g3atmportpg2TGNumber91."
        ::= { g3atmportpg2Entry 147 }

    g3atmportpg2TGNumber147	OBJECT-TYPE
        SYNTAX    INTEGER
        ACCESS    read-only
        STATUS    mandatory
        DESCRIPTION
            "See DESCRIPTION of g3atmportpg2TGNumber91."
        ::= { g3atmportpg2Entry 148 }

    g3atmportpg2TGNumber148	OBJECT-TYPE
        SYNTAX    INTEGER
        ACCESS    read-only
        STATUS    mandatory
        DESCRIPTION
            "See DESCRIPTION of g3atmportpg2TGNumber91."
        ::= { g3atmportpg2Entry 149 }

    g3atmportpg2TGNumber149	OBJECT-TYPE
        SYNTAX    INTEGER
        ACCESS    read-only
        STATUS    mandatory
        DESCRIPTION
            "See DESCRIPTION of g3atmportpg2TGNumber91."
        ::= { g3atmportpg2Entry 150 }

    g3atmportpg2TGNumber150	OBJECT-TYPE
        SYNTAX    INTEGER
        ACCESS    read-only
        STATUS    mandatory
        DESCRIPTION
            "See DESCRIPTION of g3atmportpg2TGNumber91."
        ::= { g3atmportpg2Entry 151 }

    g3atmportpg2TGNumber151	OBJECT-TYPE
        SYNTAX    INTEGER
        ACCESS    read-only
        STATUS    mandatory
        DESCRIPTION
            "See DESCRIPTION of g3atmportpg2TGNumber91."
        ::= { g3atmportpg2Entry 152 }

    g3atmportpg2TGNumber152	OBJECT-TYPE
        SYNTAX    INTEGER
        ACCESS    read-only
        STATUS    mandatory
        DESCRIPTION
            "See DESCRIPTION of g3atmportpg2TGNumber91."
        ::= { g3atmportpg2Entry 153 }

    g3atmportpg2TGNumber153	OBJECT-TYPE
        SYNTAX    INTEGER
        ACCESS    read-only
        STATUS    mandatory
        DESCRIPTION
            "See DESCRIPTION of g3atmportpg2TGNumber91."
        ::= { g3atmportpg2Entry 154 }

    g3atmportpg2TGNumber154	OBJECT-TYPE
        SYNTAX    INTEGER
        ACCESS    read-only
        STATUS    mandatory
        DESCRIPTION
            "See DESCRIPTION of g3atmportpg2TGNumber91."
        ::= { g3atmportpg2Entry 155 }

    g3atmportpg2TGNumber155	OBJECT-TYPE
        SYNTAX    INTEGER
        ACCESS    read-only
        STATUS    mandatory
        DESCRIPTION
            "See DESCRIPTION of g3atmportpg2TGNumber91."
        ::= { g3atmportpg2Entry 156 }

    g3atmportpg2TGNumber156	OBJECT-TYPE
        SYNTAX    INTEGER
        ACCESS    read-only
        STATUS    mandatory
        DESCRIPTION
            "See DESCRIPTION of g3atmportpg2TGNumber91."
        ::= { g3atmportpg2Entry 157 }

    g3atmportpg2TGNumber157	OBJECT-TYPE
        SYNTAX    INTEGER
        ACCESS    read-only
        STATUS    mandatory
        DESCRIPTION
            "See DESCRIPTION of g3atmportpg2TGNumber91."
        ::= { g3atmportpg2Entry 158 }

    g3atmportpg2TGNumber158	OBJECT-TYPE
        SYNTAX    INTEGER
        ACCESS    read-only
        STATUS    mandatory
        DESCRIPTION
            "See DESCRIPTION of g3atmportpg2TGNumber91."
        ::= { g3atmportpg2Entry 159 }

    g3atmportpg2TGNumber159	OBJECT-TYPE
        SYNTAX    INTEGER
        ACCESS    read-only
        STATUS    mandatory
        DESCRIPTION
            "See DESCRIPTION of g3atmportpg2TGNumber91."
        ::= { g3atmportpg2Entry 160 }

    g3atmportpg2TGNumber160	OBJECT-TYPE
        SYNTAX    INTEGER
        ACCESS    read-only
        STATUS    mandatory
        DESCRIPTION
            "See DESCRIPTION of g3atmportpg2TGNumber91."
        ::= { g3atmportpg2Entry 161 }

    g3atmportpg2TGNumber161	OBJECT-TYPE
        SYNTAX    INTEGER
        ACCESS    read-only
        STATUS    mandatory
        DESCRIPTION
            "See DESCRIPTION of g3atmportpg2TGNumber91."
        ::= { g3atmportpg2Entry 162 }

    g3atmportpg2TGNumber162	OBJECT-TYPE
        SYNTAX    INTEGER
        ACCESS    read-only
        STATUS    mandatory
        DESCRIPTION
            "See DESCRIPTION of g3atmportpg2TGNumber91."
        ::= { g3atmportpg2Entry 163 }

    g3atmportpg2TGNumber163	OBJECT-TYPE
        SYNTAX    INTEGER
        ACCESS    read-only
        STATUS    mandatory
        DESCRIPTION
            "See DESCRIPTION of g3atmportpg2TGNumber91."
        ::= { g3atmportpg2Entry 164 }

    g3atmportpg2TGNumber164	OBJECT-TYPE
        SYNTAX    INTEGER
        ACCESS    read-only
        STATUS    mandatory
        DESCRIPTION
            "See DESCRIPTION of g3atmportpg2TGNumber91."
        ::= { g3atmportpg2Entry 165 }

    g3atmportpg2TGNumber165	OBJECT-TYPE
        SYNTAX    INTEGER
        ACCESS    read-only
        STATUS    mandatory
        DESCRIPTION
            "See DESCRIPTION of g3atmportpg2TGNumber91."
        ::= { g3atmportpg2Entry 166 }

    g3atmportpg2TGNumber166	OBJECT-TYPE
        SYNTAX    INTEGER
        ACCESS    read-only
        STATUS    mandatory
        DESCRIPTION
            "See DESCRIPTION of g3atmportpg2TGNumber91."
        ::= { g3atmportpg2Entry 167 }

    g3atmportpg2TGNumber167	OBJECT-TYPE
        SYNTAX    INTEGER
        ACCESS    read-only
        STATUS    mandatory
        DESCRIPTION
            "See DESCRIPTION of g3atmportpg2TGNumber91."
        ::= { g3atmportpg2Entry 168 }

    g3atmportpg2TGNumber168	OBJECT-TYPE
        SYNTAX    INTEGER
        ACCESS    read-only
        STATUS    mandatory
        DESCRIPTION
            "See DESCRIPTION of g3atmportpg2TGNumber91."
        ::= { g3atmportpg2Entry 169 }

    g3atmportpg2TGNumber169	OBJECT-TYPE
        SYNTAX    INTEGER
        ACCESS    read-only
        STATUS    mandatory
        DESCRIPTION
            "See DESCRIPTION of g3atmportpg2TGNumber91."
        ::= { g3atmportpg2Entry 170 }

    g3atmportpg2TGNumber170	OBJECT-TYPE
        SYNTAX    INTEGER
        ACCESS    read-only
        STATUS    mandatory
        DESCRIPTION
            "See DESCRIPTION of g3atmportpg2TGNumber91."
        ::= { g3atmportpg2Entry 171 }

    g3atmportpg2TGNumber171	OBJECT-TYPE
        SYNTAX    INTEGER
        ACCESS    read-only
        STATUS    mandatory
        DESCRIPTION
            "See DESCRIPTION of g3atmportpg2TGNumber91."
        ::= { g3atmportpg2Entry 172 }

    g3atmportpg2TGNumber172	OBJECT-TYPE
        SYNTAX    INTEGER
        ACCESS    read-only
        STATUS    mandatory
        DESCRIPTION
            "See DESCRIPTION of g3atmportpg2TGNumber91."
        ::= { g3atmportpg2Entry 173 }

    g3atmportpg2TGNumber173	OBJECT-TYPE
        SYNTAX    INTEGER
        ACCESS    read-only
        STATUS    mandatory
        DESCRIPTION
            "See DESCRIPTION of g3atmportpg2TGNumber91."
        ::= { g3atmportpg2Entry 174 }

    g3atmportpg2TGNumber174	OBJECT-TYPE
        SYNTAX    INTEGER
        ACCESS    read-only
        STATUS    mandatory
        DESCRIPTION
            "See DESCRIPTION of g3atmportpg2TGNumber91."
        ::= { g3atmportpg2Entry 175 }

    g3atmportpg2TGNumber175	OBJECT-TYPE
        SYNTAX    INTEGER
        ACCESS    read-only
        STATUS    mandatory
        DESCRIPTION
            "See DESCRIPTION of g3atmportpg2TGNumber91."
        ::= { g3atmportpg2Entry 176 }

    g3atmportpg2TGNumber176	OBJECT-TYPE
        SYNTAX    INTEGER
        ACCESS    read-only
        STATUS    mandatory
        DESCRIPTION
            "See DESCRIPTION of g3atmportpg2TGNumber91."
        ::= { g3atmportpg2Entry 177 }

    g3atmportpg2TGNumber177	OBJECT-TYPE
        SYNTAX    INTEGER
        ACCESS    read-only
        STATUS    mandatory
        DESCRIPTION
            "See DESCRIPTION of g3atmportpg2TGNumber91."
        ::= { g3atmportpg2Entry 178 }

    g3atmportpg2TGNumber178	OBJECT-TYPE
        SYNTAX    INTEGER
        ACCESS    read-only
        STATUS    mandatory
        DESCRIPTION
            "See DESCRIPTION of g3atmportpg2TGNumber91."
        ::= { g3atmportpg2Entry 179 }

    g3atmportpg2TGNumber179	OBJECT-TYPE
        SYNTAX    INTEGER
        ACCESS    read-only
        STATUS    mandatory
        DESCRIPTION
            "See DESCRIPTION of g3atmportpg2TGNumber91."
        ::= { g3atmportpg2Entry 180 }

    g3atmportpg2TGNumber180	OBJECT-TYPE
        SYNTAX    INTEGER
        ACCESS    read-only
        STATUS    mandatory
        DESCRIPTION
            "See DESCRIPTION of g3atmportpg2TGNumber91."
        ::= { g3atmportpg2Entry 181 }


    -- the g3atmportpg3 group

    g3atmportpg3Tage	OBJECT-TYPE
        SYNTAX    INTEGER
        ACCESS    read-only
        STATUS    mandatory
        DESCRIPTION
            "The number of timeticks since the atm port data was
            extracted from the switch by the G3 Proxy Agent. This object
            along with the g3atmportpg3Tintvl object allows the Network Manager
            to determine the validity of the atm port data in the
            cache and to control when the proxy agent extracts the
            atm port data from the switch."
        ::= { g3atmportpg3 1 }

    g3atmportpg3Tintvl	OBJECT-TYPE
        SYNTAX    INTEGER
        ACCESS    read-write
        STATUS    mandatory
        DESCRIPTION
            "An object containing the interval for which the atm port data extracted 
            from	the switch is considered valid by the proxy agent.  When a GET or
            GET-NEXT request for atm port data objects is received by the agent it 
            uses	the g3atmportpg3Tage and g3atmportpg3Tintvl objects to determine
            whether it should refresh the cached atmportpg3Table.  If
            g3atmportpg3Tstmp + g3atmportpg3Tintvl is less than the current
            value of the sysUpTime object then the agent refreshes the
            atmportpg3Table cache.  In either case it responds to the 
            requests it receives with the data it currently has in the cache."
        ::= { g3atmportpg3 2 }

    g3atmportpg3Tdelay	OBJECT-TYPE
        SYNTAX    INTEGER
        ACCESS    read-only
        STATUS    mandatory
        DESCRIPTION
            "An object containing the delay encountered in updating
            the cached data"
        ::= { g3atmportpg3 3 }

    g3atmportpg3Tretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3atmportpg3 4 }

    g3atmportpg3Tcount	OBJECT-TYPE
        SYNTAX    Gauge
        ACCESS    read-only
        STATUS    mandatory
        DESCRIPTION
            "A Gauge object containing the number of data records in the cache."
        ::= { g3atmportpg3 5 }

    g3atmportpg3Table	OBJECT-TYPE
        SYNTAX    SEQUENCE OF G3atmportpg3Entry
        ACCESS    not-accessible
        STATUS    mandatory
        DESCRIPTION
            "A list of g3atmportpg3 entries."
        ::= { g3atmportpg3 6 }

    g3atmportpg3Entry	OBJECT-TYPE
        SYNTAX    G3atmportpg3Entry
        ACCESS    not-accessible
        STATUS    mandatory
        DESCRIPTION
            "A g3atmportpg3 entry containing objects of the
            g3atmportpg3 information sent by the switch."
        INDEX    { g3atmportpg3Location }
        ::= { g3atmportpg3Table 1 }

    G3atmportpg3Entry ::= SEQUENCE {
        g3atmportpg3Location
            DisplayString,
        g3atmportpg3SGNumber181
            INTEGER,
        g3atmportpg3SGNumber182
            INTEGER,
        g3atmportpg3SGNumber183
            INTEGER,
        g3atmportpg3SGNumber184
            INTEGER,
        g3atmportpg3SGNumber185
            INTEGER,
        g3atmportpg3SGNumber186
            INTEGER,
        g3atmportpg3SGNumber187
            INTEGER,
        g3atmportpg3SGNumber188
            INTEGER,
        g3atmportpg3SGNumber189
            INTEGER,
        g3atmportpg3SGNumber190
            INTEGER,
        g3atmportpg3SGNumber191
            INTEGER,
        g3atmportpg3SGNumber192
            INTEGER,
        g3atmportpg3SGNumber193
            INTEGER,
        g3atmportpg3SGNumber194
            INTEGER,
        g3atmportpg3SGNumber195
            INTEGER,
        g3atmportpg3SGNumber196
            INTEGER,
        g3atmportpg3SGNumber197
            INTEGER,
        g3atmportpg3SGNumber198
            INTEGER,
        g3atmportpg3SGNumber199
            INTEGER,
        g3atmportpg3SGNumber200
            INTEGER,
        g3atmportpg3SGNumber201
            INTEGER,
        g3atmportpg3SGNumber202
            INTEGER,
        g3atmportpg3SGNumber203
            INTEGER,
        g3atmportpg3SGNumber204
            INTEGER,
        g3atmportpg3SGNumber205
            INTEGER,
        g3atmportpg3SGNumber206
            INTEGER,
        g3atmportpg3SGNumber207
            INTEGER,
        g3atmportpg3SGNumber208
            INTEGER,
        g3atmportpg3SGNumber209
            INTEGER,
        g3atmportpg3SGNumber210
            INTEGER,
        g3atmportpg3SGNumber211
            INTEGER,
        g3atmportpg3SGNumber212
            INTEGER,
        g3atmportpg3SGNumber213
            INTEGER,
        g3atmportpg3SGNumber214
            INTEGER,
        g3atmportpg3SGNumber215
            INTEGER,
        g3atmportpg3SGNumber216
            INTEGER,
        g3atmportpg3SGNumber217
            INTEGER,
        g3atmportpg3SGNumber218
            INTEGER,
        g3atmportpg3SGNumber219
            INTEGER,
        g3atmportpg3SGNumber220
            INTEGER,
        g3atmportpg3SGNumber221
            INTEGER,
        g3atmportpg3SGNumber222
            INTEGER,
        g3atmportpg3SGNumber223
            INTEGER,
        g3atmportpg3SGNumber224
            INTEGER,
        g3atmportpg3SGNumber225
            INTEGER,
        g3atmportpg3SGNumber226
            INTEGER,
        g3atmportpg3SGNumber227
            INTEGER,
        g3atmportpg3SGNumber228
            INTEGER,
        g3atmportpg3SGNumber229
            INTEGER,
        g3atmportpg3SGNumber230
            INTEGER,
        g3atmportpg3SGNumber231
            INTEGER,
        g3atmportpg3SGNumber232
            INTEGER,
        g3atmportpg3SGNumber233
            INTEGER,
        g3atmportpg3SGNumber234
            INTEGER,
        g3atmportpg3SGNumber235
            INTEGER,
        g3atmportpg3SGNumber236
            INTEGER,
        g3atmportpg3SGNumber237
            INTEGER,
        g3atmportpg3SGNumber238
            INTEGER,
        g3atmportpg3SGNumber239
            INTEGER,
        g3atmportpg3SGNumber240
            INTEGER,
        g3atmportpg3SGNumber241
            INTEGER,
        g3atmportpg3SGNumber242
            INTEGER,
        g3atmportpg3SGNumber243
            INTEGER,
        g3atmportpg3SGNumber244
            INTEGER,
        g3atmportpg3SGNumber245
            INTEGER,
        g3atmportpg3SGNumber246
            INTEGER,
        g3atmportpg3SGNumber247
            INTEGER,
        g3atmportpg3SGNumber248
            INTEGER,
        g3atmportpg3SGNumber249
            INTEGER,
        g3atmportpg3SGNumber250
            INTEGER,
        g3atmportpg3SGNumber251
            INTEGER,
        g3atmportpg3SGNumber252
            INTEGER,
        g3atmportpg3SGNumber253
            INTEGER,
        g3atmportpg3SGNumber254
            INTEGER,
        g3atmportpg3SGNumber255
            INTEGER,
        g3atmportpg3SGNumber256
            INTEGER,
        g3atmportpg3TGNumber181
            INTEGER,
        g3atmportpg3TGNumber182
            INTEGER,
        g3atmportpg3TGNumber183
            INTEGER,
        g3atmportpg3TGNumber184
            INTEGER,
        g3atmportpg3TGNumber185
            INTEGER,
        g3atmportpg3TGNumber186
            INTEGER,
        g3atmportpg3TGNumber187
            INTEGER,
        g3atmportpg3TGNumber188
            INTEGER,
        g3atmportpg3TGNumber189
            INTEGER,
        g3atmportpg3TGNumber190
            INTEGER,
        g3atmportpg3TGNumber191
            INTEGER,
        g3atmportpg3TGNumber192
            INTEGER,
        g3atmportpg3TGNumber193
            INTEGER,
        g3atmportpg3TGNumber194
            INTEGER,
        g3atmportpg3TGNumber195
            INTEGER,
        g3atmportpg3TGNumber196
            INTEGER,
        g3atmportpg3TGNumber197
            INTEGER,
        g3atmportpg3TGNumber198
            INTEGER,
        g3atmportpg3TGNumber199
            INTEGER,
        g3atmportpg3TGNumber200
            INTEGER,
        g3atmportpg3TGNumber201
            INTEGER,
        g3atmportpg3TGNumber202
            INTEGER,
        g3atmportpg3TGNumber203
            INTEGER,
        g3atmportpg3TGNumber204
            INTEGER,
        g3atmportpg3TGNumber205
            INTEGER,
        g3atmportpg3TGNumber206
            INTEGER,
        g3atmportpg3TGNumber207
            INTEGER,
        g3atmportpg3TGNumber208
            INTEGER,
        g3atmportpg3TGNumber209
            INTEGER,
        g3atmportpg3TGNumber210
            INTEGER,
        g3atmportpg3TGNumber211
            INTEGER,
        g3atmportpg3TGNumber212
            INTEGER,
        g3atmportpg3TGNumber213
            INTEGER,
        g3atmportpg3TGNumber214
            INTEGER,
        g3atmportpg3TGNumber215
            INTEGER,
        g3atmportpg3TGNumber216
            INTEGER,
        g3atmportpg3TGNumber217
            INTEGER,
        g3atmportpg3TGNumber218
            INTEGER,
        g3atmportpg3TGNumber219
            INTEGER,
        g3atmportpg3TGNumber220
            INTEGER,
        g3atmportpg3TGNumber221
            INTEGER,
        g3atmportpg3TGNumber222
            INTEGER,
        g3atmportpg3TGNumber223
            INTEGER,
        g3atmportpg3TGNumber224
            INTEGER,
        g3atmportpg3TGNumber225
            INTEGER,
        g3atmportpg3TGNumber226
            INTEGER,
        g3atmportpg3TGNumber227
            INTEGER,
        g3atmportpg3TGNumber228
            INTEGER,
        g3atmportpg3TGNumber229
            INTEGER,
        g3atmportpg3TGNumber230
            INTEGER,
        g3atmportpg3TGNumber231
            INTEGER,
        g3atmportpg3TGNumber232
            INTEGER,
        g3atmportpg3TGNumber233
            INTEGER,
        g3atmportpg3TGNumber234
            INTEGER,
        g3atmportpg3TGNumber235
            INTEGER,
        g3atmportpg3TGNumber236
            INTEGER,
        g3atmportpg3TGNumber237
            INTEGER,
        g3atmportpg3TGNumber238
            INTEGER,
        g3atmportpg3TGNumber239
            INTEGER,
        g3atmportpg3TGNumber240
            INTEGER,
        g3atmportpg3TGNumber241
            INTEGER,
        g3atmportpg3TGNumber242
            INTEGER,
        g3atmportpg3TGNumber243
            INTEGER,
        g3atmportpg3TGNumber244
            INTEGER,
        g3atmportpg3TGNumber245
            INTEGER,
        g3atmportpg3TGNumber246
            INTEGER,
        g3atmportpg3TGNumber247
            INTEGER,
        g3atmportpg3TGNumber248
            INTEGER,
        g3atmportpg3TGNumber249
            INTEGER,
        g3atmportpg3TGNumber250
            INTEGER,
        g3atmportpg3TGNumber251
            INTEGER,
        g3atmportpg3TGNumber252
            INTEGER,
        g3atmportpg3TGNumber253
            INTEGER,
        g3atmportpg3TGNumber254
            INTEGER,
        g3atmportpg3TGNumber255
            INTEGER,
        g3atmportpg3TGNumber256
            INTEGER
        }

    g3atmportpg3Location	OBJECT-TYPE
        SYNTAX    DisplayString (SIZE (0..7))
        ACCESS    read-only
        STATUS    mandatory
        DESCRIPTION
            "A DisplayString Object that uniquely identifies the ATM trunk
            board based on its location in the system. The syntax for the
            Board Number is as follows: cabinet(01-44):carrier(A-E):slot(01-20)."
        ::= { g3atmportpg3Entry 1 }

    g3atmportpg3SGNumber181	OBJECT-TYPE
        SYNTAX    INTEGER
        ACCESS    read-only
        STATUS    mandatory
        DESCRIPTION
            "An INTEGER Object that uniquely identifies the signaling group
            associated with the ATM ports (181 to 244) on page 3 of the form."
        ::= { g3atmportpg3Entry 2 }

    g3atmportpg3SGNumber182	OBJECT-TYPE
        SYNTAX    INTEGER
        ACCESS    read-only
        STATUS    mandatory
        DESCRIPTION
            "See DESCRIPTION of g3atmportpg3SGNumber181."
        ::= { g3atmportpg3Entry 3 }

    g3atmportpg3SGNumber183	OBJECT-TYPE
        SYNTAX    INTEGER
        ACCESS    read-only
        STATUS    mandatory
        DESCRIPTION
            "See DESCRIPTION of g3atmportpg3SGNumber181."
        ::= { g3atmportpg3Entry 4 }

    g3atmportpg3SGNumber184	OBJECT-TYPE
        SYNTAX    INTEGER
        ACCESS    read-only
        STATUS    mandatory
        DESCRIPTION
            "See DESCRIPTION of g3atmportpg3SGNumber181."
        ::= { g3atmportpg3Entry 5 }

    g3atmportpg3SGNumber185	OBJECT-TYPE
        SYNTAX    INTEGER
        ACCESS    read-only
        STATUS    mandatory
        DESCRIPTION
            "See DESCRIPTION of g3atmportpg3SGNumber181."
        ::= { g3atmportpg3Entry 6 }

    g3atmportpg3SGNumber186	OBJECT-TYPE
        SYNTAX    INTEGER
        ACCESS    read-only
        STATUS    mandatory
        DESCRIPTION
            "See DESCRIPTION of g3atmportpg3SGNumber181."
        ::= { g3atmportpg3Entry 7 }

    g3atmportpg3SGNumber187	OBJECT-TYPE
        SYNTAX    INTEGER
        ACCESS    read-only
        STATUS    mandatory
        DESCRIPTION
            "See DESCRIPTION of g3atmportpg3SGNumber181."
        ::= { g3atmportpg3Entry 8 }

    g3atmportpg3SGNumber188	OBJECT-TYPE
        SYNTAX    INTEGER
        ACCESS    read-only
        STATUS    mandatory
        DESCRIPTION
            "See DESCRIPTION of g3atmportpg3SGNumber181."
        ::= { g3atmportpg3Entry 9 }

    g3atmportpg3SGNumber189	OBJECT-TYPE
        SYNTAX    INTEGER
        ACCESS    read-only
        STATUS    mandatory
        DESCRIPTION
            "See DESCRIPTION of g3atmportpg3SGNumber181."
        ::= { g3atmportpg3Entry 10 }

    g3atmportpg3SGNumber190	OBJECT-TYPE
        SYNTAX    INTEGER
        ACCESS    read-only
        STATUS    mandatory
        DESCRIPTION
            "See DESCRIPTION of g3atmportpg3SGNumber181."
        ::= { g3atmportpg3Entry 11 }

    g3atmportpg3SGNumber191	OBJECT-TYPE
        SYNTAX    INTEGER
        ACCESS    read-only
        STATUS    mandatory
        DESCRIPTION
            "See DESCRIPTION of g3atmportpg3SGNumber181."
        ::= { g3atmportpg3Entry 12 }

    g3atmportpg3SGNumber192	OBJECT-TYPE
        SYNTAX    INTEGER
        ACCESS    read-only
        STATUS    mandatory
        DESCRIPTION
            "See DESCRIPTION of g3atmportpg3SGNumber181."
        ::= { g3atmportpg3Entry 13 }

    g3atmportpg3SGNumber193	OBJECT-TYPE
        SYNTAX    INTEGER
        ACCESS    read-only
        STATUS    mandatory
        DESCRIPTION
            "See DESCRIPTION of g3atmportpg3SGNumber181."
        ::= { g3atmportpg3Entry 14 }

    g3atmportpg3SGNumber194	OBJECT-TYPE
        SYNTAX    INTEGER
        ACCESS    read-only
        STATUS    mandatory
        DESCRIPTION
            "See DESCRIPTION of g3atmportpg3SGNumber181."
        ::= { g3atmportpg3Entry 15 }

    g3atmportpg3SGNumber195	OBJECT-TYPE
        SYNTAX    INTEGER
        ACCESS    read-only
        STATUS    mandatory
        DESCRIPTION
            "See DESCRIPTION of g3atmportpg3SGNumber181."
        ::= { g3atmportpg3Entry 16 }

    g3atmportpg3SGNumber196	OBJECT-TYPE
        SYNTAX    INTEGER
        ACCESS    read-only
        STATUS    mandatory
        DESCRIPTION
            "See DESCRIPTION of g3atmportpg3SGNumber181."
        ::= { g3atmportpg3Entry 17 }

    g3atmportpg3SGNumber197	OBJECT-TYPE
        SYNTAX    INTEGER
        ACCESS    read-only
        STATUS    mandatory
        DESCRIPTION
            "See DESCRIPTION of g3atmportpg3SGNumber181."
        ::= { g3atmportpg3Entry 18 }

    g3atmportpg3SGNumber198	OBJECT-TYPE
        SYNTAX    INTEGER
        ACCESS    read-only
        STATUS    mandatory
        DESCRIPTION
            "See DESCRIPTION of g3atmportpg3SGNumber181."
        ::= { g3atmportpg3Entry 19 }

    g3atmportpg3SGNumber199	OBJECT-TYPE
        SYNTAX    INTEGER
        ACCESS    read-only
        STATUS    mandatory
        DESCRIPTION
            "See DESCRIPTION of g3atmportpg3SGNumber181."
        ::= { g3atmportpg3Entry 20 }

    g3atmportpg3SGNumber200	OBJECT-TYPE
        SYNTAX    INTEGER
        ACCESS    read-only
        STATUS    mandatory
        DESCRIPTION
            "See DESCRIPTION of g3atmportpg3SGNumber181."
        ::= { g3atmportpg3Entry 21 }

    g3atmportpg3SGNumber201	OBJECT-TYPE
        SYNTAX    INTEGER
        ACCESS    read-only
        STATUS    mandatory
        DESCRIPTION
            "See DESCRIPTION of g3atmportpg3SGNumber181."
        ::= { g3atmportpg3Entry 22 }

    g3atmportpg3SGNumber202	OBJECT-TYPE
        SYNTAX    INTEGER
        ACCESS    read-only
        STATUS    mandatory
        DESCRIPTION
            "See DESCRIPTION of g3atmportpg3SGNumber181."
        ::= { g3atmportpg3Entry 23 }

    g3atmportpg3SGNumber203	OBJECT-TYPE
        SYNTAX    INTEGER
        ACCESS    read-only
        STATUS    mandatory
        DESCRIPTION
            "See DESCRIPTION of g3atmportpg3SGNumber181."
        ::= { g3atmportpg3Entry 24 }

    g3atmportpg3SGNumber204	OBJECT-TYPE
        SYNTAX    INTEGER
        ACCESS    read-only
        STATUS    mandatory
        DESCRIPTION
            "See DESCRIPTION of g3atmportpg3SGNumber181."
        ::= { g3atmportpg3Entry 25 }

    g3atmportpg3SGNumber205	OBJECT-TYPE
        SYNTAX    INTEGER
        ACCESS    read-only
        STATUS    mandatory
        DESCRIPTION
            "See DESCRIPTION of g3atmportpg3SGNumber181."
        ::= { g3atmportpg3Entry 26 }

    g3atmportpg3SGNumber206	OBJECT-TYPE
        SYNTAX    INTEGER
        ACCESS    read-only
        STATUS    mandatory
        DESCRIPTION
            "See DESCRIPTION of g3atmportpg3SGNumber181."
        ::= { g3atmportpg3Entry 27 }

    g3atmportpg3SGNumber207	OBJECT-TYPE
        SYNTAX    INTEGER
        ACCESS    read-only
        STATUS    mandatory
        DESCRIPTION
            "See DESCRIPTION of g3atmportpg3SGNumber181."
        ::= { g3atmportpg3Entry 28 }

    g3atmportpg3SGNumber208	OBJECT-TYPE
        SYNTAX    INTEGER
        ACCESS    read-only
        STATUS    mandatory
        DESCRIPTION
            "See DESCRIPTION of g3atmportpg3SGNumber181."
        ::= { g3atmportpg3Entry 29 }

    g3atmportpg3SGNumber209	OBJECT-TYPE
        SYNTAX    INTEGER
        ACCESS    read-only
        STATUS    mandatory
        DESCRIPTION
            "See DESCRIPTION of g3atmportpg3SGNumber181."
        ::= { g3atmportpg3Entry 30 }

    g3atmportpg3SGNumber210	OBJECT-TYPE
        SYNTAX    INTEGER
        ACCESS    read-only
        STATUS    mandatory
        DESCRIPTION
            "See DESCRIPTION of g3atmportpg3SGNumber181."
        ::= { g3atmportpg3Entry 31 }

    g3atmportpg3SGNumber211	OBJECT-TYPE
        SYNTAX    INTEGER
        ACCESS    read-only
        STATUS    mandatory
        DESCRIPTION
            "See DESCRIPTION of g3atmportpg3SGNumber181."
        ::= { g3atmportpg3Entry 32 }

    g3atmportpg3SGNumber212	OBJECT-TYPE
        SYNTAX    INTEGER
        ACCESS    read-only
        STATUS    mandatory
        DESCRIPTION
            "See DESCRIPTION of g3atmportpg3SGNumber181."
        ::= { g3atmportpg3Entry 33 }

    g3atmportpg3SGNumber213	OBJECT-TYPE
        SYNTAX    INTEGER
        ACCESS    read-only
        STATUS    mandatory
        DESCRIPTION
            "See DESCRIPTION of g3atmportpg3SGNumber181."
        ::= { g3atmportpg3Entry 34 }

    g3atmportpg3SGNumber214	OBJECT-TYPE
        SYNTAX    INTEGER
        ACCESS    read-only
        STATUS    mandatory
        DESCRIPTION
            "See DESCRIPTION of g3atmportpg3SGNumber181."
        ::= { g3atmportpg3Entry 35 }

    g3atmportpg3SGNumber215	OBJECT-TYPE
        SYNTAX    INTEGER
        ACCESS    read-only
        STATUS    mandatory
        DESCRIPTION
            "See DESCRIPTION of g3atmportpg3SGNumber181."
        ::= { g3atmportpg3Entry 36 }

    g3atmportpg3SGNumber216	OBJECT-TYPE
        SYNTAX    INTEGER
        ACCESS    read-only
        STATUS    mandatory
        DESCRIPTION
            "See DESCRIPTION of g3atmportpg3SGNumber181."
        ::= { g3atmportpg3Entry 37 }

    g3atmportpg3SGNumber217	OBJECT-TYPE
        SYNTAX    INTEGER
        ACCESS    read-only
        STATUS    mandatory
        DESCRIPTION
            "See DESCRIPTION of g3atmportpg3SGNumber181."
        ::= { g3atmportpg3Entry 38 }

    g3atmportpg3SGNumber218	OBJECT-TYPE
        SYNTAX    INTEGER
        ACCESS    read-only
        STATUS    mandatory
        DESCRIPTION
            "See DESCRIPTION of g3atmportpg3SGNumber181."
        ::= { g3atmportpg3Entry 39 }

    g3atmportpg3SGNumber219	OBJECT-TYPE
        SYNTAX    INTEGER
        ACCESS    read-only
        STATUS    mandatory
        DESCRIPTION
            "See DESCRIPTION of g3atmportpg3SGNumber181."
        ::= { g3atmportpg3Entry 40 }

    g3atmportpg3SGNumber220	OBJECT-TYPE
        SYNTAX    INTEGER
        ACCESS    read-only
        STATUS    mandatory
        DESCRIPTION
            "See DESCRIPTION of g3atmportpg3SGNumber181."
        ::= { g3atmportpg3Entry 41 }

    g3atmportpg3SGNumber221	OBJECT-TYPE
        SYNTAX    INTEGER
        ACCESS    read-only
        STATUS    mandatory
        DESCRIPTION
            "See DESCRIPTION of g3atmportpg3SGNumber181."
        ::= { g3atmportpg3Entry 42 }

    g3atmportpg3SGNumber222	OBJECT-TYPE
        SYNTAX    INTEGER
        ACCESS    read-only
        STATUS    mandatory
        DESCRIPTION
            "See DESCRIPTION of g3atmportpg3SGNumber181."
        ::= { g3atmportpg3Entry 43 }

    g3atmportpg3SGNumber223	OBJECT-TYPE
        SYNTAX    INTEGER
        ACCESS    read-only
        STATUS    mandatory
        DESCRIPTION
            "See DESCRIPTION of g3atmportpg3SGNumber181."
        ::= { g3atmportpg3Entry 44 }

    g3atmportpg3SGNumber224	OBJECT-TYPE
        SYNTAX    INTEGER
        ACCESS    read-only
        STATUS    mandatory
        DESCRIPTION
            "See DESCRIPTION of g3atmportpg3SGNumber181."
        ::= { g3atmportpg3Entry 45 }

    g3atmportpg3SGNumber225	OBJECT-TYPE
        SYNTAX    INTEGER
        ACCESS    read-only
        STATUS    mandatory
        DESCRIPTION
            "See DESCRIPTION of g3atmportpg3SGNumber181."
        ::= { g3atmportpg3Entry 46 }

    g3atmportpg3SGNumber226	OBJECT-TYPE
        SYNTAX    INTEGER
        ACCESS    read-only
        STATUS    mandatory
        DESCRIPTION
            "See DESCRIPTION of g3atmportpg3SGNumber181."
        ::= { g3atmportpg3Entry 47 }

    g3atmportpg3SGNumber227	OBJECT-TYPE
        SYNTAX    INTEGER
        ACCESS    read-only
        STATUS    mandatory
        DESCRIPTION
            "See DESCRIPTION of g3atmportpg3SGNumber181."
        ::= { g3atmportpg3Entry 48 }

    g3atmportpg3SGNumber228	OBJECT-TYPE
        SYNTAX    INTEGER
        ACCESS    read-only
        STATUS    mandatory
        DESCRIPTION
            "See DESCRIPTION of g3atmportpg3SGNumber181."
        ::= { g3atmportpg3Entry 49 }

    g3atmportpg3SGNumber229	OBJECT-TYPE
        SYNTAX    INTEGER
        ACCESS    read-only
        STATUS    mandatory
        DESCRIPTION
            "See DESCRIPTION of g3atmportpg3SGNumber181."
        ::= { g3atmportpg3Entry 50 }

    g3atmportpg3SGNumber230	OBJECT-TYPE
        SYNTAX    INTEGER
        ACCESS    read-only
        STATUS    mandatory
        DESCRIPTION
            "See DESCRIPTION of g3atmportpg3SGNumber181."
        ::= { g3atmportpg3Entry 51 }

    g3atmportpg3SGNumber231	OBJECT-TYPE
        SYNTAX    INTEGER
        ACCESS    read-only
        STATUS    mandatory
        DESCRIPTION
            "See DESCRIPTION of g3atmportpg3SGNumber181."
        ::= { g3atmportpg3Entry 52 }

    g3atmportpg3SGNumber232	OBJECT-TYPE
        SYNTAX    INTEGER
        ACCESS    read-only
        STATUS    mandatory
        DESCRIPTION
            "See DESCRIPTION of g3atmportpg3SGNumber181."
        ::= { g3atmportpg3Entry 53 }

    g3atmportpg3SGNumber233	OBJECT-TYPE
        SYNTAX    INTEGER
        ACCESS    read-only
        STATUS    mandatory
        DESCRIPTION
            "See DESCRIPTION of g3atmportpg3SGNumber181."
        ::= { g3atmportpg3Entry 54 }

    g3atmportpg3SGNumber234	OBJECT-TYPE
        SYNTAX    INTEGER
        ACCESS    read-only
        STATUS    mandatory
        DESCRIPTION
            "See DESCRIPTION of g3atmportpg3SGNumber181."
        ::= { g3atmportpg3Entry 55 }

    g3atmportpg3SGNumber235	OBJECT-TYPE
        SYNTAX    INTEGER
        ACCESS    read-only
        STATUS    mandatory
        DESCRIPTION
            "See DESCRIPTION of g3atmportpg3SGNumber181."
        ::= { g3atmportpg3Entry 56 }

    g3atmportpg3SGNumber236	OBJECT-TYPE
        SYNTAX    INTEGER
        ACCESS    read-only
        STATUS    mandatory
        DESCRIPTION
            "See DESCRIPTION of g3atmportpg3SGNumber181."
        ::= { g3atmportpg3Entry 57 }

    g3atmportpg3SGNumber237	OBJECT-TYPE
        SYNTAX    INTEGER
        ACCESS    read-only
        STATUS    mandatory
        DESCRIPTION
            "See DESCRIPTION of g3atmportpg3SGNumber181."
        ::= { g3atmportpg3Entry 58 }

    g3atmportpg3SGNumber238	OBJECT-TYPE
        SYNTAX    INTEGER
        ACCESS    read-only
        STATUS    mandatory
        DESCRIPTION
            "See DESCRIPTION of g3atmportpg3SGNumber181."
        ::= { g3atmportpg3Entry 59 }

    g3atmportpg3SGNumber239	OBJECT-TYPE
        SYNTAX    INTEGER
        ACCESS    read-only
        STATUS    mandatory
        DESCRIPTION
            "See DESCRIPTION of g3atmportpg3SGNumber181."
        ::= { g3atmportpg3Entry 60 }

    g3atmportpg3SGNumber240	OBJECT-TYPE
        SYNTAX    INTEGER
        ACCESS    read-only
        STATUS    mandatory
        DESCRIPTION
            "See DESCRIPTION of g3atmportpg3SGNumber181."
        ::= { g3atmportpg3Entry 61 }

    g3atmportpg3SGNumber241	OBJECT-TYPE
        SYNTAX    INTEGER
        ACCESS    read-only
        STATUS    mandatory
        DESCRIPTION
            "See DESCRIPTION of g3atmportpg3SGNumber181."
        ::= { g3atmportpg3Entry 62 }

    g3atmportpg3SGNumber242	OBJECT-TYPE
        SYNTAX    INTEGER
        ACCESS    read-only
        STATUS    mandatory
        DESCRIPTION
            "See DESCRIPTION of g3atmportpg3SGNumber181."
        ::= { g3atmportpg3Entry 63 }

    g3atmportpg3SGNumber243	OBJECT-TYPE
        SYNTAX    INTEGER
        ACCESS    read-only
        STATUS    mandatory
        DESCRIPTION
            "See DESCRIPTION of g3atmportpg3SGNumber181."
        ::= { g3atmportpg3Entry 64 }

    g3atmportpg3SGNumber244	OBJECT-TYPE
        SYNTAX    INTEGER
        ACCESS    read-only
        STATUS    mandatory
        DESCRIPTION
            "See DESCRIPTION of g3atmportpg3SGNumber181."
        ::= { g3atmportpg3Entry 65 }

    g3atmportpg3SGNumber245	OBJECT-TYPE
        SYNTAX    INTEGER
        ACCESS    read-only
        STATUS    mandatory
        DESCRIPTION
            "See DESCRIPTION of g3atmportpg3SGNumber181."
        ::= { g3atmportpg3Entry 66 }

    g3atmportpg3SGNumber246	OBJECT-TYPE
        SYNTAX    INTEGER
        ACCESS    read-only
        STATUS    mandatory
        DESCRIPTION
            "An INTEGER Object that uniquely identifies the signaling group
            associated with ATM port 246 on page 3 of the form."
        ::= { g3atmportpg3Entry 67 }

    g3atmportpg3SGNumber247	OBJECT-TYPE
        SYNTAX    INTEGER
        ACCESS    read-only
        STATUS    mandatory
        DESCRIPTION
            "An INTEGER Object that uniquely identifies the signaling group
            associated with ATM port 247 on page 3 of the form."
        ::= { g3atmportpg3Entry 68 }

    g3atmportpg3SGNumber248	OBJECT-TYPE
        SYNTAX    INTEGER
        ACCESS    read-only
        STATUS    mandatory
        DESCRIPTION
            "An INTEGER Object that uniquely identifies the signaling group
            associated with ATM port 248 on page 3 of the form."
        ::= { g3atmportpg3Entry 69 }

    g3atmportpg3SGNumber249	OBJECT-TYPE
        SYNTAX    INTEGER
        ACCESS    read-only
        STATUS    mandatory
        DESCRIPTION
            "An INTEGER Object that uniquely identifies the signaling group
            associated with ATM port 249 on page 3 of the form."
        ::= { g3atmportpg3Entry 70 }

    g3atmportpg3SGNumber250	OBJECT-TYPE
        SYNTAX    INTEGER
        ACCESS    read-only
        STATUS    mandatory
        DESCRIPTION
            "An INTEGER Object that uniquely identifies the signaling group
            associated with ATM port 250 on page 3 of the form."
        ::= { g3atmportpg3Entry 71 }

    g3atmportpg3SGNumber251	OBJECT-TYPE
        SYNTAX    INTEGER
        ACCESS    read-only
        STATUS    mandatory
        DESCRIPTION
            "An INTEGER Object that uniquely identifies the signaling group
            associated with ATM port 251 on page 3 of the form."
        ::= { g3atmportpg3Entry 72 }

    g3atmportpg3SGNumber252	OBJECT-TYPE
        SYNTAX    INTEGER
        ACCESS    read-only
        STATUS    mandatory
        DESCRIPTION
            "An INTEGER Object that uniquely identifies the signaling group
            associated with ATM port 252 on page 3 of the form."
        ::= { g3atmportpg3Entry 73 }

    g3atmportpg3SGNumber253	OBJECT-TYPE
        SYNTAX    INTEGER
        ACCESS    read-only
        STATUS    mandatory
        DESCRIPTION
            "An INTEGER Object that uniquely identifies the signaling group
            associated with ATM port 253 on page 3 of the form."
        ::= { g3atmportpg3Entry 74 }

    g3atmportpg3SGNumber254	OBJECT-TYPE
        SYNTAX    INTEGER
        ACCESS    read-only
        STATUS    mandatory
        DESCRIPTION
            "An INTEGER Object that uniquely identifies the signaling group
            associated with ATM port 254 on page 3 of the form."
        ::= { g3atmportpg3Entry 75 }

    g3atmportpg3SGNumber255	OBJECT-TYPE
        SYNTAX    INTEGER
        ACCESS    read-only
        STATUS    mandatory
        DESCRIPTION
            "An INTEGER Object that uniquely identifies the signaling group
            associated with ATM port 255 on page 3 of the form."
        ::= { g3atmportpg3Entry 76 }

    g3atmportpg3SGNumber256	OBJECT-TYPE
        SYNTAX    INTEGER
        ACCESS    read-only
        STATUS    mandatory
        DESCRIPTION
            "An INTEGER Object that uniquely identifies the signaling group
            associated with ATM port 256 on page 3 of the form."
        ::= { g3atmportpg3Entry 77 }

    g3atmportpg3TGNumber181	OBJECT-TYPE
        SYNTAX    INTEGER
        ACCESS    read-only
        STATUS    mandatory
        DESCRIPTION
            "An INTEGER Object that uniquely identifies the trunk group
            associated with the ATM ports (181 to 244) on page 3 of the form."
        ::= { g3atmportpg3Entry 78 }

    g3atmportpg3TGNumber182	OBJECT-TYPE
        SYNTAX    INTEGER
        ACCESS    read-only
        STATUS    mandatory
        DESCRIPTION
            "See DESCRIPTION of g3atmportpg3TGNumber181."
        ::= { g3atmportpg3Entry 79 }

    g3atmportpg3TGNumber183	OBJECT-TYPE
        SYNTAX    INTEGER
        ACCESS    read-only
        STATUS    mandatory
        DESCRIPTION
            "See DESCRIPTION of g3atmportpg3TGNumber181."
        ::= { g3atmportpg3Entry 80 }

    g3atmportpg3TGNumber184	OBJECT-TYPE
        SYNTAX    INTEGER
        ACCESS    read-only
        STATUS    mandatory
        DESCRIPTION
            "See DESCRIPTION of g3atmportpg3TGNumber181."
        ::= { g3atmportpg3Entry 81 }

    g3atmportpg3TGNumber185	OBJECT-TYPE
        SYNTAX    INTEGER
        ACCESS    read-only
        STATUS    mandatory
        DESCRIPTION
            "See DESCRIPTION of g3atmportpg3TGNumber181."
        ::= { g3atmportpg3Entry 82 }

    g3atmportpg3TGNumber186	OBJECT-TYPE
        SYNTAX    INTEGER
        ACCESS    read-only
        STATUS    mandatory
        DESCRIPTION
            "See DESCRIPTION of g3atmportpg3TGNumber181."
        ::= { g3atmportpg3Entry 83 }

    g3atmportpg3TGNumber187	OBJECT-TYPE
        SYNTAX    INTEGER
        ACCESS    read-only
        STATUS    mandatory
        DESCRIPTION
            "See DESCRIPTION of g3atmportpg3TGNumber181."
        ::= { g3atmportpg3Entry 84 }

    g3atmportpg3TGNumber188	OBJECT-TYPE
        SYNTAX    INTEGER
        ACCESS    read-only
        STATUS    mandatory
        DESCRIPTION
            "See DESCRIPTION of g3atmportpg3TGNumber181."
        ::= { g3atmportpg3Entry 85 }

    g3atmportpg3TGNumber189	OBJECT-TYPE
        SYNTAX    INTEGER
        ACCESS    read-only
        STATUS    mandatory
        DESCRIPTION
            "See DESCRIPTION of g3atmportpg3TGNumber181."
        ::= { g3atmportpg3Entry 86 }

    g3atmportpg3TGNumber190	OBJECT-TYPE
        SYNTAX    INTEGER
        ACCESS    read-only
        STATUS    mandatory
        DESCRIPTION
            "See DESCRIPTION of g3atmportpg3TGNumber181."
        ::= { g3atmportpg3Entry 87 }

    g3atmportpg3TGNumber191	OBJECT-TYPE
        SYNTAX    INTEGER
        ACCESS    read-only
        STATUS    mandatory
        DESCRIPTION
            "See DESCRIPTION of g3atmportpg3TGNumber181."
        ::= { g3atmportpg3Entry 88 }

    g3atmportpg3TGNumber192	OBJECT-TYPE
        SYNTAX    INTEGER
        ACCESS    read-only
        STATUS    mandatory
        DESCRIPTION
            "See DESCRIPTION of g3atmportpg3TGNumber181."
        ::= { g3atmportpg3Entry 89 }

    g3atmportpg3TGNumber193	OBJECT-TYPE
        SYNTAX    INTEGER
        ACCESS    read-only
        STATUS    mandatory
        DESCRIPTION
            "See DESCRIPTION of g3atmportpg3TGNumber181."
        ::= { g3atmportpg3Entry 90 }

    g3atmportpg3TGNumber194	OBJECT-TYPE
        SYNTAX    INTEGER
        ACCESS    read-only
        STATUS    mandatory
        DESCRIPTION
            "See DESCRIPTION of g3atmportpg3TGNumber181."
        ::= { g3atmportpg3Entry 91 }

    g3atmportpg3TGNumber195	OBJECT-TYPE
        SYNTAX    INTEGER
        ACCESS    read-only
        STATUS    mandatory
        DESCRIPTION
            "See DESCRIPTION of g3atmportpg3TGNumber181."
        ::= { g3atmportpg3Entry 92 }

    g3atmportpg3TGNumber196	OBJECT-TYPE
        SYNTAX    INTEGER
        ACCESS    read-only
        STATUS    mandatory
        DESCRIPTION
            "See DESCRIPTION of g3atmportpg3TGNumber181."
        ::= { g3atmportpg3Entry 93 }

    g3atmportpg3TGNumber197	OBJECT-TYPE
        SYNTAX    INTEGER
        ACCESS    read-only
        STATUS    mandatory
        DESCRIPTION
            "See DESCRIPTION of g3atmportpg3TGNumber181."
        ::= { g3atmportpg3Entry 94 }

    g3atmportpg3TGNumber198	OBJECT-TYPE
        SYNTAX    INTEGER
        ACCESS    read-only
        STATUS    mandatory
        DESCRIPTION
            "See DESCRIPTION of g3atmportpg3TGNumber181."
        ::= { g3atmportpg3Entry 95 }

    g3atmportpg3TGNumber199	OBJECT-TYPE
        SYNTAX    INTEGER
        ACCESS    read-only
        STATUS    mandatory
        DESCRIPTION
            "See DESCRIPTION of g3atmportpg3TGNumber181."
        ::= { g3atmportpg3Entry 96 }

    g3atmportpg3TGNumber200	OBJECT-TYPE
        SYNTAX    INTEGER
        ACCESS    read-only
        STATUS    mandatory
        DESCRIPTION
            "See DESCRIPTION of g3atmportpg3TGNumber181."
        ::= { g3atmportpg3Entry 97 }

    g3atmportpg3TGNumber201	OBJECT-TYPE
        SYNTAX    INTEGER
        ACCESS    read-only
        STATUS    mandatory
        DESCRIPTION
            "See DESCRIPTION of g3atmportpg3TGNumber181."
        ::= { g3atmportpg3Entry 98 }

    g3atmportpg3TGNumber202	OBJECT-TYPE
        SYNTAX    INTEGER
        ACCESS    read-only
        STATUS    mandatory
        DESCRIPTION
            "See DESCRIPTION of g3atmportpg3TGNumber181."
        ::= { g3atmportpg3Entry 99 }

    g3atmportpg3TGNumber203	OBJECT-TYPE
        SYNTAX    INTEGER
        ACCESS    read-only
        STATUS    mandatory
        DESCRIPTION
            "See DESCRIPTION of g3atmportpg3TGNumber181."
        ::= { g3atmportpg3Entry 100 }

    g3atmportpg3TGNumber204	OBJECT-TYPE
        SYNTAX    INTEGER
        ACCESS    read-only
        STATUS    mandatory
        DESCRIPTION
            "See DESCRIPTION of g3atmportpg3TGNumber181."
        ::= { g3atmportpg3Entry 101 }

    g3atmportpg3TGNumber205	OBJECT-TYPE
        SYNTAX    INTEGER
        ACCESS    read-only
        STATUS    mandatory
        DESCRIPTION
            "See DESCRIPTION of g3atmportpg3TGNumber181."
        ::= { g3atmportpg3Entry 102 }

    g3atmportpg3TGNumber206	OBJECT-TYPE
        SYNTAX    INTEGER
        ACCESS    read-only
        STATUS    mandatory
        DESCRIPTION
            "See DESCRIPTION of g3atmportpg3TGNumber181."
        ::= { g3atmportpg3Entry 103 }

    g3atmportpg3TGNumber207	OBJECT-TYPE
        SYNTAX    INTEGER
        ACCESS    read-only
        STATUS    mandatory
        DESCRIPTION
            "See DESCRIPTION of g3atmportpg3TGNumber181."
        ::= { g3atmportpg3Entry 104 }

    g3atmportpg3TGNumber208	OBJECT-TYPE
        SYNTAX    INTEGER
        ACCESS    read-only
        STATUS    mandatory
        DESCRIPTION
            "See DESCRIPTION of g3atmportpg3TGNumber181."
        ::= { g3atmportpg3Entry 105 }

    g3atmportpg3TGNumber209	OBJECT-TYPE
        SYNTAX    INTEGER
        ACCESS    read-only
        STATUS    mandatory
        DESCRIPTION
            "See DESCRIPTION of g3atmportpg3TGNumber181."
        ::= { g3atmportpg3Entry 106 }

    g3atmportpg3TGNumber210	OBJECT-TYPE
        SYNTAX    INTEGER
        ACCESS    read-only
        STATUS    mandatory
        DESCRIPTION
            "See DESCRIPTION of g3atmportpg3TGNumber181."
        ::= { g3atmportpg3Entry 107 }

    g3atmportpg3TGNumber211	OBJECT-TYPE
        SYNTAX    INTEGER
        ACCESS    read-only
        STATUS    mandatory
        DESCRIPTION
            "See DESCRIPTION of g3atmportpg3TGNumber181."
        ::= { g3atmportpg3Entry 108 }

    g3atmportpg3TGNumber212	OBJECT-TYPE
        SYNTAX    INTEGER
        ACCESS    read-only
        STATUS    mandatory
        DESCRIPTION
            "See DESCRIPTION of g3atmportpg3TGNumber181."
        ::= { g3atmportpg3Entry 109 }

    g3atmportpg3TGNumber213	OBJECT-TYPE
        SYNTAX    INTEGER
        ACCESS    read-only
        STATUS    mandatory
        DESCRIPTION
            "See DESCRIPTION of g3atmportpg3TGNumber181."
        ::= { g3atmportpg3Entry 110 }

    g3atmportpg3TGNumber214	OBJECT-TYPE
        SYNTAX    INTEGER
        ACCESS    read-only
        STATUS    mandatory
        DESCRIPTION
            "See DESCRIPTION of g3atmportpg3TGNumber181."
        ::= { g3atmportpg3Entry 111 }

    g3atmportpg3TGNumber215	OBJECT-TYPE
        SYNTAX    INTEGER
        ACCESS    read-only
        STATUS    mandatory
        DESCRIPTION
            "See DESCRIPTION of g3atmportpg3TGNumber181."
        ::= { g3atmportpg3Entry 112 }

    g3atmportpg3TGNumber216	OBJECT-TYPE
        SYNTAX    INTEGER
        ACCESS    read-only
        STATUS    mandatory
        DESCRIPTION
            "See DESCRIPTION of g3atmportpg3TGNumber181."
        ::= { g3atmportpg3Entry 113 }

    g3atmportpg3TGNumber217	OBJECT-TYPE
        SYNTAX    INTEGER
        ACCESS    read-only
        STATUS    mandatory
        DESCRIPTION
            "See DESCRIPTION of g3atmportpg3TGNumber181."
        ::= { g3atmportpg3Entry 114 }

    g3atmportpg3TGNumber218	OBJECT-TYPE
        SYNTAX    INTEGER
        ACCESS    read-only
        STATUS    mandatory
        DESCRIPTION
            "See DESCRIPTION of g3atmportpg3TGNumber181."
        ::= { g3atmportpg3Entry 115 }

    g3atmportpg3TGNumber219	OBJECT-TYPE
        SYNTAX    INTEGER
        ACCESS    read-only
        STATUS    mandatory
        DESCRIPTION
            "See DESCRIPTION of g3atmportpg3TGNumber181."
        ::= { g3atmportpg3Entry 116 }

    g3atmportpg3TGNumber220	OBJECT-TYPE
        SYNTAX    INTEGER
        ACCESS    read-only
        STATUS    mandatory
        DESCRIPTION
            "See DESCRIPTION of g3atmportpg3TGNumber181."
        ::= { g3atmportpg3Entry 117 }

    g3atmportpg3TGNumber221	OBJECT-TYPE
        SYNTAX    INTEGER
        ACCESS    read-only
        STATUS    mandatory
        DESCRIPTION
            "See DESCRIPTION of g3atmportpg3TGNumber181."
        ::= { g3atmportpg3Entry 118 }

    g3atmportpg3TGNumber222	OBJECT-TYPE
        SYNTAX    INTEGER
        ACCESS    read-only
        STATUS    mandatory
        DESCRIPTION
            "See DESCRIPTION of g3atmportpg3TGNumber181."
        ::= { g3atmportpg3Entry 119 }

    g3atmportpg3TGNumber223	OBJECT-TYPE
        SYNTAX    INTEGER
        ACCESS    read-only
        STATUS    mandatory
        DESCRIPTION
            "See DESCRIPTION of g3atmportpg3TGNumber181."
        ::= { g3atmportpg3Entry 120 }

    g3atmportpg3TGNumber224	OBJECT-TYPE
        SYNTAX    INTEGER
        ACCESS    read-only
        STATUS    mandatory
        DESCRIPTION
            "See DESCRIPTION of g3atmportpg3TGNumber181."
        ::= { g3atmportpg3Entry 121 }

    g3atmportpg3TGNumber225	OBJECT-TYPE
        SYNTAX    INTEGER
        ACCESS    read-only
        STATUS    mandatory
        DESCRIPTION
            "See DESCRIPTION of g3atmportpg3TGNumber181."
        ::= { g3atmportpg3Entry 122 }

    g3atmportpg3TGNumber226	OBJECT-TYPE
        SYNTAX    INTEGER
        ACCESS    read-only
        STATUS    mandatory
        DESCRIPTION
            "See DESCRIPTION of g3atmportpg3TGNumber181."
        ::= { g3atmportpg3Entry 123 }

    g3atmportpg3TGNumber227	OBJECT-TYPE
        SYNTAX    INTEGER
        ACCESS    read-only
        STATUS    mandatory
        DESCRIPTION
            "See DESCRIPTION of g3atmportpg3TGNumber181."
        ::= { g3atmportpg3Entry 124 }

    g3atmportpg3TGNumber228	OBJECT-TYPE
        SYNTAX    INTEGER
        ACCESS    read-only
        STATUS    mandatory
        DESCRIPTION
            "See DESCRIPTION of g3atmportpg3TGNumber181."
        ::= { g3atmportpg3Entry 125 }

    g3atmportpg3TGNumber229	OBJECT-TYPE
        SYNTAX    INTEGER
        ACCESS    read-only
        STATUS    mandatory
        DESCRIPTION
            "See DESCRIPTION of g3atmportpg3TGNumber181."
        ::= { g3atmportpg3Entry 126 }

    g3atmportpg3TGNumber230	OBJECT-TYPE
        SYNTAX    INTEGER
        ACCESS    read-only
        STATUS    mandatory
        DESCRIPTION
            "See DESCRIPTION of g3atmportpg3TGNumber181."
        ::= { g3atmportpg3Entry 127 }

    g3atmportpg3TGNumber231	OBJECT-TYPE
        SYNTAX    INTEGER
        ACCESS    read-only
        STATUS    mandatory
        DESCRIPTION
            "See DESCRIPTION of g3atmportpg3TGNumber181."
        ::= { g3atmportpg3Entry 128 }

    g3atmportpg3TGNumber232	OBJECT-TYPE
        SYNTAX    INTEGER
        ACCESS    read-only
        STATUS    mandatory
        DESCRIPTION
            "See DESCRIPTION of g3atmportpg3TGNumber181."
        ::= { g3atmportpg3Entry 129 }

    g3atmportpg3TGNumber233	OBJECT-TYPE
        SYNTAX    INTEGER
        ACCESS    read-only
        STATUS    mandatory
        DESCRIPTION
            "See DESCRIPTION of g3atmportpg3TGNumber181."
        ::= { g3atmportpg3Entry 130 }

    g3atmportpg3TGNumber234	OBJECT-TYPE
        SYNTAX    INTEGER
        ACCESS    read-only
        STATUS    mandatory
        DESCRIPTION
            "See DESCRIPTION of g3atmportpg3TGNumber181."
        ::= { g3atmportpg3Entry 131 }

    g3atmportpg3TGNumber235	OBJECT-TYPE
        SYNTAX    INTEGER
        ACCESS    read-only
        STATUS    mandatory
        DESCRIPTION
            "See DESCRIPTION of g3atmportpg3TGNumber181."
        ::= { g3atmportpg3Entry 132 }

    g3atmportpg3TGNumber236	OBJECT-TYPE
        SYNTAX    INTEGER
        ACCESS    read-only
        STATUS    mandatory
        DESCRIPTION
            "See DESCRIPTION of g3atmportpg3TGNumber181."
        ::= { g3atmportpg3Entry 133 }

    g3atmportpg3TGNumber237	OBJECT-TYPE
        SYNTAX    INTEGER
        ACCESS    read-only
        STATUS    mandatory
        DESCRIPTION
            "See DESCRIPTION of g3atmportpg3TGNumber181."
        ::= { g3atmportpg3Entry 134 }

    g3atmportpg3TGNumber238	OBJECT-TYPE
        SYNTAX    INTEGER
        ACCESS    read-only
        STATUS    mandatory
        DESCRIPTION
            "See DESCRIPTION of g3atmportpg3TGNumber181."
        ::= { g3atmportpg3Entry 135 }

    g3atmportpg3TGNumber239	OBJECT-TYPE
        SYNTAX    INTEGER
        ACCESS    read-only
        STATUS    mandatory
        DESCRIPTION
            "See DESCRIPTION of g3atmportpg3TGNumber181."
        ::= { g3atmportpg3Entry 136 }

    g3atmportpg3TGNumber240	OBJECT-TYPE
        SYNTAX    INTEGER
        ACCESS    read-only
        STATUS    mandatory
        DESCRIPTION
            "See DESCRIPTION of g3atmportpg3TGNumber181."
        ::= { g3atmportpg3Entry 137 }

    g3atmportpg3TGNumber241	OBJECT-TYPE
        SYNTAX    INTEGER
        ACCESS    read-only
        STATUS    mandatory
        DESCRIPTION
            "See DESCRIPTION of g3atmportpg3TGNumber181."
        ::= { g3atmportpg3Entry 138 }

    g3atmportpg3TGNumber242	OBJECT-TYPE
        SYNTAX    INTEGER
        ACCESS    read-only
        STATUS    mandatory
        DESCRIPTION
            "See DESCRIPTION of g3atmportpg3TGNumber181."
        ::= { g3atmportpg3Entry 139 }

    g3atmportpg3TGNumber243	OBJECT-TYPE
        SYNTAX    INTEGER
        ACCESS    read-only
        STATUS    mandatory
        DESCRIPTION
            "See DESCRIPTION of g3atmportpg3TGNumber181."
        ::= { g3atmportpg3Entry 140 }

    g3atmportpg3TGNumber244	OBJECT-TYPE
        SYNTAX    INTEGER
        ACCESS    read-only
        STATUS    mandatory
        DESCRIPTION
            "See DESCRIPTION of g3atmportpg3TGNumber181."
        ::= { g3atmportpg3Entry 141 }

    g3atmportpg3TGNumber245	OBJECT-TYPE
        SYNTAX    INTEGER
        ACCESS    read-only
        STATUS    mandatory
        DESCRIPTION
            "See DESCRIPTION of g3atmportpg3TGNumber181."
        ::= { g3atmportpg3Entry 142 }

    g3atmportpg3TGNumber246	OBJECT-TYPE
        SYNTAX    INTEGER
        ACCESS    read-only
        STATUS    mandatory
        DESCRIPTION
            "An INTEGER Object that uniquely identifies the trunk group
            associated with the ATM port 246 on page 3 of the form."
        ::= { g3atmportpg3Entry 143 }

    g3atmportpg3TGNumber247	OBJECT-TYPE
        SYNTAX    INTEGER
        ACCESS    read-only
        STATUS    mandatory
        DESCRIPTION
            "An INTEGER Object that uniquely identifies the trunk group
            associated with the ATM port 247 on page 3 of the form."
        ::= { g3atmportpg3Entry 144 }

    g3atmportpg3TGNumber248	OBJECT-TYPE
        SYNTAX    INTEGER
        ACCESS    read-only
        STATUS    mandatory
        DESCRIPTION
            "An INTEGER Object that uniquely identifies the trunk group
            associated with the ATM port 248 on page 3 of the form."
        ::= { g3atmportpg3Entry 145 }

    g3atmportpg3TGNumber249	OBJECT-TYPE
        SYNTAX    INTEGER
        ACCESS    read-only
        STATUS    mandatory
        DESCRIPTION
            "An INTEGER Object that uniquely identifies the trunk group
            associated with the ATM port 249 on page 3 of the form."
        ::= { g3atmportpg3Entry 146 }

    g3atmportpg3TGNumber250	OBJECT-TYPE
        SYNTAX    INTEGER
        ACCESS    read-only
        STATUS    mandatory
        DESCRIPTION
            "An INTEGER Object that uniquely identifies the trunk group
            associated with the ATM port 250 on page 3 of the form."
        ::= { g3atmportpg3Entry 147 }

    g3atmportpg3TGNumber251	OBJECT-TYPE
        SYNTAX    INTEGER
        ACCESS    read-only
        STATUS    mandatory
        DESCRIPTION
            "An INTEGER Object that uniquely identifies the trunk group
            associated with the ATM port 251 on page 3 of the form."
        ::= { g3atmportpg3Entry 148 }

    g3atmportpg3TGNumber252	OBJECT-TYPE
        SYNTAX    INTEGER
        ACCESS    read-only
        STATUS    mandatory
        DESCRIPTION
            "An INTEGER Object that uniquely identifies the trunk group
            associated with the ATM port 252 on page 3 of the form."
        ::= { g3atmportpg3Entry 149 }

    g3atmportpg3TGNumber253	OBJECT-TYPE
        SYNTAX    INTEGER
        ACCESS    read-only
        STATUS    mandatory
        DESCRIPTION
            "An INTEGER Object that uniquely identifies the trunk group
            associated with the ATM port 253 on page 3 of the form."
        ::= { g3atmportpg3Entry 150 }

    g3atmportpg3TGNumber254	OBJECT-TYPE
        SYNTAX    INTEGER
        ACCESS    read-only
        STATUS    mandatory
        DESCRIPTION
            "An INTEGER Object that uniquely identifies the trunk group
            associated with the ATM port 254 on page 3 of the form."
        ::= { g3atmportpg3Entry 151 }

    g3atmportpg3TGNumber255	OBJECT-TYPE
        SYNTAX    INTEGER
        ACCESS    read-only
        STATUS    mandatory
        DESCRIPTION
            "An INTEGER Object that uniquely identifies the trunk group
            associated with the ATM port 255 on page 3 of the form."
        ::= { g3atmportpg3Entry 152 }

    g3atmportpg3TGNumber256	OBJECT-TYPE
        SYNTAX    INTEGER
        ACCESS    read-only
        STATUS    mandatory
        DESCRIPTION
            "An INTEGER Object that uniquely identifies the trunk group
            associated with the ATM port 256 on page 3 of the form."
        ::= { g3atmportpg3Entry 153 }


    -- the g3dmodule group

    g3dmoduleTage	OBJECT-TYPE
        SYNTAX    INTEGER
        ACCESS    read-only
        STATUS    mandatory
        DESCRIPTION
            "The number of timeticks since the data-module data was last
            extracted from the switch by the Proxy Agent.  This object
            along with the g3dmoduleintvl object allows the Network Manager
            to determine the validity of the data-module data in the cache and to 
            control when the Proxy Agent extracts the data from the switch."
        ::= { g3dmodule 1 }

    g3dmoduleTintvl	OBJECT-TYPE
        SYNTAX    INTEGER
        ACCESS    read-write
        STATUS    mandatory
        DESCRIPTION
            "An object containing the interval for which the data-module
            data extracted from the switch is considered valid by the
            Proxy Agent.  When a GET or GET-NEXT request for these data-module data
            objects is received by the agent it uses the g3dmoduleage
            and g3dmoduleintvl objects to determine whether it should refresh
            the cached dmoduleTable.  If g3dmodulestmp +
            g3dmoduleintvl is less than the current value of the sysUpTime
            object then the agent refreshes the dmoduleTable cache.  In
            either case it responds to the requests it receives with the data
            it currently has in the cache."
        ::= { g3dmodule 2 }

    g3dmoduleTdelay	OBJECT-TYPE
        SYNTAX    INTEGER
        ACCESS    read-only
        STATUS    mandatory
        DESCRIPTION
            "An object containing the delay encountered in updating
            the cached data."
        ::= { g3dmodule 3 }

    g3dmoduleTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3dmodule 4 }

    g3dmoduleTcount	OBJECT-TYPE
        SYNTAX    Gauge
        ACCESS    read-only
        STATUS    mandatory
        DESCRIPTION
            "A Gauge object containing the number of data records in the cache."
        ::= { g3dmodule 5 }

    g3dmoduleTable	OBJECT-TYPE
        SYNTAX    SEQUENCE OF G3dmoduleEntry
        ACCESS    not-accessible
        STATUS    mandatory
        DESCRIPTION
            "A list of g3dmodule entries."
        ::= { g3dmodule 6 }

    g3dmoduleEntry	OBJECT-TYPE
        SYNTAX    G3dmoduleEntry
        ACCESS    not-accessible
        STATUS    mandatory
        DESCRIPTION
            "A g3dmodule entry containing objects of the
            g3dmodule information sent by the switch."
        INDEX    { g3dmoduleExtension }
        ::= { g3dmoduleTable 1 }

    G3dmoduleEntry ::= SEQUENCE {
        g3dmoduleExtension
            DisplayString,
        g3dmoduleType
            DisplayString,
        g3dmoduleName
            DisplayString,
        g3dmodulePort
            DisplayString
        }

    g3dmoduleExtension	OBJECT-TYPE
        SYNTAX    DisplayString (SIZE (0..15))
        ACCESS    read-only
        STATUS    mandatory
        DESCRIPTION
            "A DisplayString Object that uniquely identifies an administered
            data module."
        ::= { g3dmoduleEntry 1 }

    g3dmoduleType	OBJECT-TYPE
        SYNTAX    DisplayString (SIZE (0..12))
        ACCESS    read-only
        STATUS    mandatory
        DESCRIPTION
            "A DisplayString Object containing the data module type."
        ::= { g3dmoduleEntry 2 }

    g3dmoduleName	OBJECT-TYPE
        SYNTAX    DisplayString (SIZE (0..15))
        ACCESS    read-only
        STATUS    mandatory
        DESCRIPTION
            "A DisplayString Object containing the name assigned to the data
            module."
        ::= { g3dmoduleEntry 3 }

    g3dmodulePort	OBJECT-TYPE
        SYNTAX    DisplayString (SIZE (0..9))
        ACCESS    read-only
        STATUS    mandatory
        DESCRIPTION
            "A DisplayString Object that uniquely identifies a data-module
            port based on its location in the system. The syntax for the
            Port location is as follows:
            cabinet(01-44):carrier(A-E):slot(01-20):port(01-32)."
        ::= { g3dmoduleEntry 4 }


    -- the g3occsum group

    g3occsumTage	OBJECT-TYPE
        SYNTAX    INTEGER
        ACCESS    read-only
        STATUS    mandatory
        DESCRIPTION
            "The number of timeticks since the occupancy summary data was last
            extracted from the switch by the Proxy Agent.  This object
            along with the g3occsumintvl object allows the Network Manager
            to determine the validity of the occupancy summary data in the cache and 
            to control	when the Proxy Agent extracts the data from the switch."
        ::= { g3occsum 1 }

    g3occsumTintvl	OBJECT-TYPE
        SYNTAX    INTEGER
        ACCESS    read-write
        STATUS    mandatory
        DESCRIPTION
            "An object containing the interval for which the occupancy summary data
            extracted from the switch is considered valid by the Proxy Agent.
            When a GET or GET-NEXT request for occupancy summary objects is
            received by the agent it uses the g3occsumage and g3occsumintvl
            objects to determine whether it should refresh the cached occsumTable.
            If g3occsumstmp + g3occsumintvl is less than the current value of
            the sysUpTime object then the agent refreshes the occsumTable
            cache.  In either case it responds to the requests it receives
            with the data it currently has in the cache."
        ::= { g3occsum 2 }

    g3occsumTdelay	OBJECT-TYPE
        SYNTAX    INTEGER
        ACCESS    read-only
        STATUS    mandatory
        DESCRIPTION
            "An object containing the delay encountered in updating
            the cached data."
        ::= { g3occsum 3 }

    g3occsumTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3occsum 4 }

    g3occsumTcount	OBJECT-TYPE
        SYNTAX    Gauge
        ACCESS    read-only
        STATUS    mandatory
        DESCRIPTION
            "A Gauge object containing the number of data records in the cache."
        ::= { g3occsum 5 }

    g3occsumTable	OBJECT-TYPE
        SYNTAX    SEQUENCE OF G3occsumEntry
        ACCESS    not-accessible
        STATUS    mandatory
        DESCRIPTION
            "A list of g3occsum entries."
        ::= { g3occsum 6 }

    g3occsumEntry	OBJECT-TYPE
        SYNTAX    G3occsumEntry
        ACCESS    not-accessible
        STATUS    mandatory
        DESCRIPTION
            "A g3occsum entry containing objects of the
            g3occsum information sent by the switch."
        INDEX    { g3occsumMeasHour }
        ::= { g3occsumTable 1 }

    G3occsumEntry ::= SEQUENCE {
        g3occsumMeasHour
            INTEGER,
        g3occsumRunYear
            INTEGER,
        g3occsumRunMonth
            INTEGER,
        g3occsumRunDay
            INTEGER,
        g3occsumRunHour
            INTEGER,
        g3occsumPeakHour
            INTEGER,
        g3occsumStatOcc
            INTEGER,
        g3occsumCPOcc
            INTEGER,
        g3occsumSMOcc
            INTEGER,
        g3occsumIdleOcc
            INTEGER,
        g3occsumTotCall
            INTEGER,
        g3occsumTandCall
            INTEGER,
        g3occsumTotAtt
            INTEGER,
        g3occsumIntcomAtt
            INTEGER,
        g3occsumIncAtt
            INTEGER,
        g3occsumOutAtt
            INTEGER,
        g3occsumPnetAtt
            INTEGER
        }

    g3occsumMeasHour	OBJECT-TYPE
        SYNTAX    INTEGER
        ACCESS    read-only
        STATUS    mandatory
        DESCRIPTION
            "An object containing the Peak Hour for occupancy."
        ::= { g3occsumEntry 1 }

    g3occsumRunYear	OBJECT-TYPE
        SYNTAX    INTEGER
        ACCESS    read-only
        STATUS    mandatory
        DESCRIPTION
            "An object containing the Year the command was executed."
        ::= { g3occsumEntry 2 }

    g3occsumRunMonth	OBJECT-TYPE
        SYNTAX    INTEGER
        ACCESS    read-only
        STATUS    mandatory
        DESCRIPTION
            "An object containing the Month the command was executed."
        ::= { g3occsumEntry 3 }

    g3occsumRunDay	OBJECT-TYPE
        SYNTAX    INTEGER
        ACCESS    read-only
        STATUS    mandatory
        DESCRIPTION
            "An object containing the Day the command was executed."
        ::= { g3occsumEntry 4 }

    g3occsumRunHour	OBJECT-TYPE
        SYNTAX    INTEGER
        ACCESS    read-only
        STATUS    mandatory
        DESCRIPTION
            "An object containing the Hour the measurement was taken."
        ::= { g3occsumEntry 5 }

    g3occsumPeakHour	OBJECT-TYPE
        SYNTAX    INTEGER
        ACCESS    read-only
        STATUS    mandatory
        DESCRIPTION
            "An object containing the Hour the command was executed."
        ::= { g3occsumEntry 6 }

    g3occsumStatOcc	OBJECT-TYPE
        SYNTAX    INTEGER
        ACCESS    read-only
        STATUS    mandatory
        DESCRIPTION
            "An object containing the processor utilized by static processes."
        ::= { g3occsumEntry 7 }

    g3occsumCPOcc	OBJECT-TYPE
        SYNTAX    INTEGER
        ACCESS    read-only
        STATUS    mandatory
        DESCRIPTION
            "An object containing the processor occupancy utilized by Call
            Processing processes."
        ::= { g3occsumEntry 8 }

    g3occsumSMOcc	OBJECT-TYPE
        SYNTAX    INTEGER
        ACCESS    read-only
        STATUS    mandatory
        DESCRIPTION
            "An object containing the processor occupancy utilized by System
            Management processes."
        ::= { g3occsumEntry 9 }

    g3occsumIdleOcc	OBJECT-TYPE
        SYNTAX    INTEGER
        ACCESS    read-only
        STATUS    mandatory
        DESCRIPTION
            "An object containing the processor occupancy that is unused."
        ::= { g3occsumEntry 10 }

    g3occsumTotCall	OBJECT-TYPE
        SYNTAX    INTEGER
        ACCESS    read-only
        STATUS    mandatory
        DESCRIPTION
            "An object containing total calls connected for the measurement hour."
        ::= { g3occsumEntry 11 }

    g3occsumTandCall	OBJECT-TYPE
        SYNTAX    INTEGER
        ACCESS    read-only
        STATUS    mandatory
        DESCRIPTION
            "An object containing trunk-to-trunk calls connected for the
            measurement hour."
        ::= { g3occsumEntry 12 }

    g3occsumTotAtt	OBJECT-TYPE
        SYNTAX    INTEGER
        ACCESS    read-only
        STATUS    mandatory
        DESCRIPTION
            "An object containing the total calls attempted for the measurement hour."
        ::= { g3occsumEntry 13 }

    g3occsumIntcomAtt	OBJECT-TYPE
        SYNTAX    INTEGER
        ACCESS    read-only
        STATUS    mandatory
        DESCRIPTION
            "An object containing the number of extension-to-extension calls
            on the same switch and partially completed calls for the measurement
            hour."
        ::= { g3occsumEntry 14 }

    g3occsumIncAtt	OBJECT-TYPE
        SYNTAX    INTEGER
        ACCESS    read-only
        STATUS    mandatory
        DESCRIPTION
            "An object containing the number of incoming trunk seizures from
            public network facilities."
        ::= { g3occsumEntry 15 }

    g3occsumOutAtt	OBJECT-TYPE
        SYNTAX    INTEGER
        ACCESS    read-only
        STATUS    mandatory
        DESCRIPTION
            "An object containing the number of outgoing trunk seizures that
            are made over public network facilities."
        ::= { g3occsumEntry 16 }

    g3occsumPnetAtt	OBJECT-TYPE
        SYNTAX    INTEGER
        ACCESS    read-only
        STATUS    mandatory
        DESCRIPTION
            "The number of incoming and outgoing seizures that are made over"
        ::= { g3occsumEntry 17 }


    -- the g3attdgrp group

    g3attdgrpTage	OBJECT-TYPE
        SYNTAX    INTEGER
        ACCESS    read-only
        STATUS    mandatory
        DESCRIPTION
            "The number of timeticks since the attendant group data was last
            extracted from the switch by the Proxy Agent.  This object
            along with the g3attdgrpintvl object allows the Network Manager
            to determine the validity of the attendant group data in the cache and to 
            control	when the Proxy Agent extracts the data from the switch."
        ::= { g3attdgrp 1 }

    g3attdgrpTintvl	OBJECT-TYPE
        SYNTAX    INTEGER
        ACCESS    read-write
        STATUS    mandatory
        DESCRIPTION
            "An object containing the interval for which the attendant group data
            extracted from the switch is considered valid by the Proxy Agent.
            When a GET or GET-NEXT request for attendant group objects is
            received by the agent it uses the g3attdgrpage and g3attdgrpintvl
            objects to determine whether it should refresh the cached attdgrpTable.
            If g3attdgrpstmp + g3attdgrpintvl is less than the current value of
            the sysUpTime object then the agent refreshes the attdgrpTable
            cache.  In either case it responds to the requests it receives
            with the data it currently has in the cache."
        ::= { g3attdgrp 2 }

    g3attdgrpTdelay	OBJECT-TYPE
        SYNTAX    INTEGER
        ACCESS    read-only
        STATUS    mandatory
        DESCRIPTION
            "An object containing the delay encountered in updating
            the cached data."
        ::= { g3attdgrp 3 }

    g3attdgrpTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3attdgrp 4 }

    g3attdgrpTcount	OBJECT-TYPE
        SYNTAX    Gauge
        ACCESS    read-only
        STATUS    mandatory
        DESCRIPTION
            "A Gauge object containing the number of data records in the cache."
        ::= { g3attdgrp 5 }

    g3attdgrpTable	OBJECT-TYPE
        SYNTAX    SEQUENCE OF G3attdgrpEntry
        ACCESS    not-accessible
        STATUS    mandatory
        DESCRIPTION
            "A list of g3attdgrp entries."
        ::= { g3attdgrp 6 }

    g3attdgrpEntry	OBJECT-TYPE
        SYNTAX    G3attdgrpEntry
        ACCESS    not-accessible
        STATUS    mandatory
        DESCRIPTION
            "A g3attdgrp entry containing objects of the
            g3attdgrp information sent by the switch."
        INDEX    { g3attdgrpMeasType }
        ::= { g3attdgrpTable 1 }

    G3attdgrpEntry ::= SEQUENCE {
        g3attdgrpMeasType
            DisplayString,
        g3attdgrpMeasHour
            INTEGER,
        g3attdgrpRunYear
            INTEGER,
        g3attdgrpRunMonth
            INTEGER,
        g3attdgrpRunDay
            INTEGER,
        g3attdgrpRunHour
            INTEGER,
        g3attdgrpGrpSiz
            INTEGER,
        g3attdgrpCallsAns
            INTEGER,
        g3attdgrpCallsAbnd
            INTEGER,
        g3attdgrpCallsQued
            INTEGER,
        g3attdgrpCallsHAbd
            INTEGER,
        g3attdgrpCallsHeld
            INTEGER,
        g3attdgrpTimeAvail
            INTEGER,
        g3attdgrpTimeTalk
            INTEGER,
        g3attdgrpTimeHeld
            INTEGER,
        g3attdgrpTimeAbnd
            INTEGER,
        g3attdgrpSpeedAns
            INTEGER
        }

    g3attdgrpMeasType	OBJECT-TYPE
        SYNTAX    DisplayString (SIZE (0..11))
        ACCESS    read-only
        STATUS    mandatory
        DESCRIPTION
            "A DisplayString object containing the measurement type (YEST PEAK,
            TODAY PEAK, LASTHOUR)."
        ::= { g3attdgrpEntry 1 }

    g3attdgrpMeasHour	OBJECT-TYPE
        SYNTAX    INTEGER
        ACCESS    read-only
        STATUS    mandatory
        DESCRIPTION
            "An object containing the Hour the measurement was taken."
        ::= { g3attdgrpEntry 2 }

    g3attdgrpRunYear	OBJECT-TYPE
        SYNTAX    INTEGER
        ACCESS    read-only
        STATUS    mandatory
        DESCRIPTION
            "An object containing the Year the command was executed."
        ::= { g3attdgrpEntry 3 }

    g3attdgrpRunMonth	OBJECT-TYPE
        SYNTAX    INTEGER
        ACCESS    read-only
        STATUS    mandatory
        DESCRIPTION
            "An object containing the Month the command was executed."
        ::= { g3attdgrpEntry 4 }

    g3attdgrpRunDay	OBJECT-TYPE
        SYNTAX    INTEGER
        ACCESS    read-only
        STATUS    mandatory
        DESCRIPTION
            "An object containing the Day the command was executed."
        ::= { g3attdgrpEntry 5 }

    g3attdgrpRunHour	OBJECT-TYPE
        SYNTAX    INTEGER
        ACCESS    read-only
        STATUS    mandatory
        DESCRIPTION
            "An object containing the Hour the command was executed."
        ::= { g3attdgrpEntry 6 }

    g3attdgrpGrpSiz	OBJECT-TYPE
        SYNTAX    INTEGER
        ACCESS    read-only
        STATUS    mandatory
        DESCRIPTION
            "An object containing the number of attendant positions that are
            administered for the groups."
        ::= { g3attdgrpEntry 7 }

    g3attdgrpCallsAns	OBJECT-TYPE
        SYNTAX    INTEGER
        ACCESS    read-only
        STATUS    mandatory
        DESCRIPTION
            "An object containing the number of calls answered by all active
            attendants during the measurement hour."
        ::= { g3attdgrpEntry 8 }

    g3attdgrpCallsAbnd	OBJECT-TYPE
        SYNTAX    INTEGER
        ACCESS    read-only
        STATUS    mandatory
        DESCRIPTION
            "An object containing the number of calls that ring an attendant
            group and drop (hang up) before an attendant answers."
        ::= { g3attdgrpEntry 9 }

    g3attdgrpCallsQued	OBJECT-TYPE
        SYNTAX    INTEGER
        ACCESS    read-only
        STATUS    mandatory
        DESCRIPTION
            "An object containing the total number of calls that were placed in
            the attendant queue (delayed) because no attendants were available."
        ::= { g3attdgrpEntry 10 }

    g3attdgrpCallsHAbd	OBJECT-TYPE
        SYNTAX    INTEGER
        ACCESS    read-only
        STATUS    mandatory
        DESCRIPTION
            "An object containing the number of calls that abandon while the
            caller is in hold mode."
        ::= { g3attdgrpEntry 11 }

    g3attdgrpCallsHeld	OBJECT-TYPE
        SYNTAX    INTEGER
        ACCESS    read-only
        STATUS    mandatory
        DESCRIPTION
            "An object containing the number of calls that are answered by the
            attendant group and then placed on hold."
        ::= { g3attdgrpEntry 12 }

    g3attdgrpTimeAvail	OBJECT-TYPE
        SYNTAX    INTEGER
        ACCESS    read-only
        STATUS    mandatory
        DESCRIPTION
            "An object containing the time during which the pos avail lamp is
            lit on all attendant consoles, and the attendants are not talking
            on calls but are available to handle new calls (in CCS)."
        ::= { g3attdgrpEntry 13 }

    g3attdgrpTimeTalk	OBJECT-TYPE
        SYNTAX    INTEGER
        ACCESS    read-only
        STATUS    mandatory
        DESCRIPTION
            "An object containing the time that attendants are active or talking
            on a loop (in CCS)."
        ::= { g3attdgrpEntry 14 }

    g3attdgrpTimeHeld	OBJECT-TYPE
        SYNTAX    INTEGER
        ACCESS    read-only
        STATUS    mandatory
        DESCRIPTION
            "An object containing the time that attendants have calls on hold
            (in seconds)."
        ::= { g3attdgrpEntry 15 }

    g3attdgrpTimeAbnd	OBJECT-TYPE
        SYNTAX    INTEGER
        ACCESS    read-only
        STATUS    mandatory
        DESCRIPTION
            "An object containing the average amount of time that calls spend
            in queue and/or ringing at the console before the caller hangs
            up (in seconds)."
        ::= { g3attdgrpEntry 16 }

    g3attdgrpSpeedAns	OBJECT-TYPE
        SYNTAX    INTEGER
        ACCESS    read-only
        STATUS    mandatory
        DESCRIPTION
            "An object containing the average elapsed time from when a call
            terminates at the attendant group to when the call is answered by
            an attendant (in seconds)."
        ::= { g3attdgrpEntry 17 }


    -- the g3attdpos group

    g3attdposTage	OBJECT-TYPE
        SYNTAX    INTEGER
        ACCESS    read-only
        STATUS    mandatory
        DESCRIPTION
            "The number of timeticks since the attendant position data was last
            extracted from the switch by the Proxy Agent.  This object
            along with the g3attdposintvl object allows the Network Manager
            to determine the validity of the data in the cache and to control
            when the Proxy Agent extracts the data from the switch."
        ::= { g3attdpos 1 }

    g3attdposTintvl	OBJECT-TYPE
        SYNTAX    INTEGER
        ACCESS    read-write
        STATUS    mandatory
        DESCRIPTION
            "An object containing the interval for which the attendant position
            data extracted from the switch is considered valid by the
            Proxy Agent.  When a GET or GET-NEXT request for attendant position
            objects is received by the agent it uses the g3attdposage
            and g3attdposintvl objects to determine whether it should refresh
            the cached attdposTable.  If g3attdposstmp + g3attdposintvl
            is less than the current value of the sysUpTime object then the agent
            refreshes the attdposTable cache.  In either case it responds to
            the requests it receives with the data it currently has in the cache."
        ::= { g3attdpos 2 }

    g3attdposTdelay	OBJECT-TYPE
        SYNTAX    INTEGER
        ACCESS    read-only
        STATUS    mandatory
        DESCRIPTION
            "An object containing the delay encountered in updating
            the cached data."
        ::= { g3attdpos 3 }

    g3attdposTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3attdpos 4 }

    g3attdposTcount	OBJECT-TYPE
        SYNTAX    Gauge
        ACCESS    read-only
        STATUS    mandatory
        DESCRIPTION
            "A Gauge object containing the number of data records in the cache."
        ::= { g3attdpos 5 }

    g3attdposTable	OBJECT-TYPE
        SYNTAX    SEQUENCE OF G3attdposEntry
        ACCESS    not-accessible
        STATUS    mandatory
        DESCRIPTION
            "A list of g3attdpos entries."
        ::= { g3attdpos 6 }

    g3attdposEntry	OBJECT-TYPE
        SYNTAX    G3attdposEntry
        ACCESS    not-accessible
        STATUS    mandatory
        DESCRIPTION
            "A g3attdpos entry containing objects of the
            g3attdpos information sent by the switch."
        INDEX    { g3attdposAttdID }
        ::= { g3attdposTable 1 }

    G3attdposEntry ::= SEQUENCE {
        g3attdposAttdID
            INTEGER,
        g3attdposYear
            INTEGER,
        g3attdposMonth
            INTEGER,
        g3attdposDay
            INTEGER,
        g3attdposHour
            INTEGER,
        g3attdposPeakHour
            INTEGER,
        g3attdposPkTimeAvail
            INTEGER,
        g3attdposPkTimeTalk
            INTEGER,
        g3attdposPkTimeHeld
            INTEGER,
        g3attdposPkCallsAns
            INTEGER,
        g3attdposLastHour
            INTEGER,
        g3attdposTimeAvail
            INTEGER,
        g3attdposTimeTalk
            INTEGER,
        g3attdposTimeHeld
            INTEGER,
        g3attdposCallsAns
            INTEGER
        }

    g3attdposAttdID	OBJECT-TYPE
        SYNTAX    INTEGER
        ACCESS    read-only
        STATUS    mandatory
        DESCRIPTION
            "An object containing an attendant number to identify which attendant
            data is being displayed."
        ::= { g3attdposEntry 1 }

    g3attdposYear	OBJECT-TYPE
        SYNTAX    INTEGER
        ACCESS    read-only
        STATUS    mandatory
        DESCRIPTION
            "An object containing the Year the command was executed."
        ::= { g3attdposEntry 2 }

    g3attdposMonth	OBJECT-TYPE
        SYNTAX    INTEGER
        ACCESS    read-only
        STATUS    mandatory
        DESCRIPTION
            "An object containing the Month the command was executed."
        ::= { g3attdposEntry 3 }

    g3attdposDay	OBJECT-TYPE
        SYNTAX    INTEGER
        ACCESS    read-only
        STATUS    mandatory
        DESCRIPTION
            "An object containing the Day the command was executed."
        ::= { g3attdposEntry 4 }

    g3attdposHour	OBJECT-TYPE
        SYNTAX    INTEGER
        ACCESS    read-only
        STATUS    mandatory
        DESCRIPTION
            "An object containing the Hour the command was executed."
        ::= { g3attdposEntry 5 }

    g3attdposPeakHour	OBJECT-TYPE
        SYNTAX    INTEGER
        ACCESS    read-only
        STATUS    mandatory
        DESCRIPTION
            "An object containing the peak measurement hour."
        ::= { g3attdposEntry 6 }

    g3attdposPkTimeAvail	OBJECT-TYPE
        SYNTAX    INTEGER
        ACCESS    read-only
        STATUS    mandatory
        DESCRIPTION
            "An object containing the total time the attendant is availiable
            to receive calls during the polling interval (in CCS)."
        ::= { g3attdposEntry 7 }

    g3attdposPkTimeTalk	OBJECT-TYPE
        SYNTAX    INTEGER
        ACCESS    read-only
        STATUS    mandatory
        DESCRIPTION
            "An object containing the total time the attendant is active on
            calls (in CCS)."
        ::= { g3attdposEntry 8 }

    g3attdposPkTimeHeld	OBJECT-TYPE
        SYNTAX    INTEGER
        ACCESS    read-only
        STATUS    mandatory
        DESCRIPTION
            "An object containing the total time the attendant has calls on hold
            (in seconds)."
        ::= { g3attdposEntry 9 }

    g3attdposPkCallsAns	OBJECT-TYPE
        SYNTAX    INTEGER
        ACCESS    read-only
        STATUS    mandatory
        DESCRIPTION
            "An object containing the total number of calls answered by the
            attendant (in CCS)."
        ::= { g3attdposEntry 10 }

    g3attdposLastHour	OBJECT-TYPE
        SYNTAX    INTEGER
        ACCESS    read-only
        STATUS    mandatory
        DESCRIPTION
            "An object containing the last measurement hour."
        ::= { g3attdposEntry 11 }

    g3attdposTimeAvail	OBJECT-TYPE
        SYNTAX    INTEGER
        ACCESS    read-only
        STATUS    mandatory
        DESCRIPTION
            "An object containing the total time the attendant is availiable
            to receive calls during the polling interval (in CCS)."
        ::= { g3attdposEntry 12 }

    g3attdposTimeTalk	OBJECT-TYPE
        SYNTAX    INTEGER
        ACCESS    read-only
        STATUS    mandatory
        DESCRIPTION
            "An object containing the total time the attendant is active on
            calls (in CCS)."
        ::= { g3attdposEntry 13 }

    g3attdposTimeHeld	OBJECT-TYPE
        SYNTAX    INTEGER
        ACCESS    read-only
        STATUS    mandatory
        DESCRIPTION
            "An object containing the total time the attendant has calls on hold
            (in seconds)."
        ::= { g3attdposEntry 14 }

    g3attdposCallsAns	OBJECT-TYPE
        SYNTAX    INTEGER
        ACCESS    read-only
        STATUS    mandatory
        DESCRIPTION
            "An object containing the total number of calls answered by the
            attendant (in CCS)."
        ::= { g3attdposEntry 15 }


    -- the g3trunksum group

    g3trunksumTage	OBJECT-TYPE
        SYNTAX    INTEGER
        ACCESS    read-only
        STATUS    mandatory
        DESCRIPTION
            "The number of timeticks since the trunk summary data was last
            extracted from the switch by the Proxy Agent.  This object
            along with the g3trunksumintvl object allows the Network Manager
            to determine the validity of the data in the cache and to control
            when the Proxy Agent extracts the data from the switch."
        ::= { g3trunksum 1 }

    g3trunksumTintvl	OBJECT-TYPE
        SYNTAX    INTEGER
        ACCESS    read-write
        STATUS    mandatory
        DESCRIPTION
            "An object containing the interval for which the trunk summary data
            extracted from the switch is considered valid by the Proxy Agent.
            When a GET or GET-NEXT request for trunk summary objects is
            received by the agent it uses the g3trunksumage and g3trunksumintvl
            objects to determine whether it should refresh the cached trunksumTable.
            If g3trunksumstmp + g3trunksumintvl is less than the current value of
            the sysUpTime object then the agent refreshes the trunksumTable
            cache.  In either case it responds to the requests it receives
            with the data it currently has in the cache."
        ::= { g3trunksum 2 }

    g3trunksumTdelay	OBJECT-TYPE
        SYNTAX    INTEGER
        ACCESS    read-only
        STATUS    mandatory
        DESCRIPTION
            "An object containing the delay encountered in updating
            the cached data."
        ::= { g3trunksum 3 }

    g3trunksumTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3trunksum 4 }

    g3trunksumTcount	OBJECT-TYPE
        SYNTAX    Gauge
        ACCESS    read-only
        STATUS    mandatory
        DESCRIPTION
            "A Gauge object containing the number of data records in the cache."
        ::= { g3trunksum 5 }

    g3trunksumTable	OBJECT-TYPE
        SYNTAX    SEQUENCE OF G3trunksumEntry
        ACCESS    not-accessible
        STATUS    mandatory
        DESCRIPTION
            "A list of g3trunksum entries."
        ::= { g3trunksum 6 }

    g3trunksumEntry	OBJECT-TYPE
        SYNTAX    G3trunksumEntry
        ACCESS    not-accessible
        STATUS    mandatory
        DESCRIPTION
            "A g3trunksum entry containing objects of the
            g3trunksum information sent by the switch."
        INDEX    { g3trunksumTrunkGroup }
        ::= { g3trunksumTable 1 }

    G3trunksumEntry ::= SEQUENCE {
        g3trunksumTrunkGroup
            INTEGER,
        g3trunksumMeasHour
            INTEGER,
        g3trunksumRunYear
            INTEGER,
        g3trunksumRunMonth
            INTEGER,
        g3trunksumRunDay
            INTEGER,
        g3trunksumRunHour
            INTEGER,
        g3trunksumGroupSize
            INTEGER,
        g3trunksumTotalUsage
            INTEGER,
        g3trunksumTotalSeize
            INTEGER,
        g3trunksumIncSeize
            INTEGER,
        g3trunksumGrpOvfl
            INTEGER,
        g3trunksumQueSiz
            INTEGER,
        g3trunksumCallQued
            INTEGER,
        g3trunksumQueOvf
            INTEGER,
        g3trunksumQueAbd
            INTEGER,
        g3trunksumOutSrv
            INTEGER,
        g3trunksumPercentAtb
            INTEGER,
        g3trunksumPercentOutBlk
            INTEGER
        }

    g3trunksumTrunkGroup	OBJECT-TYPE
        SYNTAX    INTEGER
        ACCESS    read-only
        STATUS    mandatory
        DESCRIPTION
            "An object containing the trunk group number for which data has
            been collected."
        ::= { g3trunksumEntry 1 }

    g3trunksumMeasHour	OBJECT-TYPE
        SYNTAX    INTEGER
        ACCESS    read-only
        STATUS    mandatory
        DESCRIPTION
            "An object containing the Hour the measurement was taken."
        ::= { g3trunksumEntry 2 }

    g3trunksumRunYear	OBJECT-TYPE
        SYNTAX    INTEGER
        ACCESS    read-only
        STATUS    mandatory
        DESCRIPTION
            "An object containing the Year the command was executed."
        ::= { g3trunksumEntry 3 }

    g3trunksumRunMonth	OBJECT-TYPE
        SYNTAX    INTEGER
        ACCESS    read-only
        STATUS    mandatory
        DESCRIPTION
            "An object containing the Month the command was executed."
        ::= { g3trunksumEntry 4 }

    g3trunksumRunDay	OBJECT-TYPE
        SYNTAX    INTEGER
        ACCESS    read-only
        STATUS    mandatory
        DESCRIPTION
            "An object containing the Day the command was executed."
        ::= { g3trunksumEntry 5 }

    g3trunksumRunHour	OBJECT-TYPE
        SYNTAX    INTEGER
        ACCESS    read-only
        STATUS    mandatory
        DESCRIPTION
            "An object containing the Hour the command was executed."
        ::= { g3trunksumEntry 6 }

    g3trunksumGroupSize	OBJECT-TYPE
        SYNTAX    INTEGER
        ACCESS    read-only
        STATUS    mandatory
        DESCRIPTION
            "An object containing the number of administered trunks in the trunk
            group."
        ::= { g3trunksumEntry 7 }

    g3trunksumTotalUsage	OBJECT-TYPE
        SYNTAX    INTEGER
        ACCESS    read-only
        STATUS    mandatory
        DESCRIPTION
            "An object containing the total time trunks are busy with calls
            during the measurement period (in CCS)."
        ::= { g3trunksumEntry 8 }

    g3trunksumTotalSeize	OBJECT-TYPE
        SYNTAX    INTEGER
        ACCESS    read-only
        STATUS    mandatory
        DESCRIPTION
            "An object containing the number of times a trunk was seized in the
            group including false starts, don't answer and busy."
        ::= { g3trunksumEntry 9 }

    g3trunksumIncSeize	OBJECT-TYPE
        SYNTAX    INTEGER
        ACCESS    read-only
        STATUS    mandatory
        DESCRIPTION
            "An object containing the number of incoming seizures carried on the
            trunk group."
        ::= { g3trunksumEntry 10 }

    g3trunksumGrpOvfl	OBJECT-TYPE
        SYNTAX    INTEGER
        ACCESS    read-only
        STATUS    mandatory
        DESCRIPTION
            "An object containing the number of calls offered to a trunk group
            that are not carried or queued."
        ::= { g3trunksumEntry 11 }

    g3trunksumQueSiz	OBJECT-TYPE
        SYNTAX    INTEGER
        ACCESS    read-only
        STATUS    mandatory
        DESCRIPTION
            "An object containing a number (0-100) that identifies the number of
            slots assigned to the trunk group queue."
        ::= { g3trunksumEntry 12 }

    g3trunksumCallQued	OBJECT-TYPE
        SYNTAX    INTEGER
        ACCESS    read-only
        STATUS    mandatory
        DESCRIPTION
            "An object containing the total number of calls that entered the
            trunk group queue after finding all trunks busy."
        ::= { g3trunksumEntry 13 }

    g3trunksumQueOvf	OBJECT-TYPE
        SYNTAX    INTEGER
        ACCESS    read-only
        STATUS    mandatory
        DESCRIPTION
            "An object containing the total number of calls that were not queued
            because the queue was full."
        ::= { g3trunksumEntry 14 }

    g3trunksumQueAbd	OBJECT-TYPE
        SYNTAX    INTEGER
        ACCESS    read-only
        STATUS    mandatory
        DESCRIPTION
            "An object containing the total number of calls that were removed
            from the queue (i.e., due to queue timeout or user cancel)"
        ::= { g3trunksumEntry 15 }

    g3trunksumOutSrv	OBJECT-TYPE
        SYNTAX    INTEGER
        ACCESS    read-only
        STATUS    mandatory
        DESCRIPTION
            "An object containing the number of trunks in the group that are
            out of service (maintenance busy)."
        ::= { g3trunksumEntry 16 }

    g3trunksumPercentAtb	OBJECT-TYPE
        SYNTAX    INTEGER
        ACCESS    read-only
        STATUS    mandatory
        DESCRIPTION
            "An object containing the percentage of time all trunks in the group
            were simultaneously in use."
        ::= { g3trunksumEntry 17 }

    g3trunksumPercentOutBlk	OBJECT-TYPE
        SYNTAX    INTEGER
        ACCESS    read-only
        STATUS    mandatory
        DESCRIPTION
            "An object containing the percentage of offered calls that are not
            carried on the group."
        ::= { g3trunksumEntry 18 }


    -- the g3pktrunksum group

    g3pktrunksumTage	OBJECT-TYPE
        SYNTAX    INTEGER
        ACCESS    read-only
        STATUS    mandatory
        DESCRIPTION
            "The number of timeticks since the trunk summary data was last
            extracted from the switch by the Proxy Agent.  This object
            along with the g3trunksumintvl object allows the Network Manager
            to determine the validity of the data in the cache and to control
            when the Proxy Agent extracts the data from the switch."
        ::= { g3pktrunksum 1 }

    g3pktrunksumTintvl	OBJECT-TYPE
        SYNTAX    INTEGER
        ACCESS    read-write
        STATUS    mandatory
        DESCRIPTION
            "An object containing the interval for which the trunk summary data
            extracted from the switch is considered valid by the Proxy Agent.
            When a GET or GET-NEXT request for trunk summary objects is
            received by the agent it uses the g3trunksumage and g3trunksumintvl
            objects to determine whether it should refresh the cached trunksumTable.
            If g3trunksumstmp + g3trunksumintvl is less than the current value of
            the sysUpTime object then the agent refreshes the trunksumTable
            cache.  In either case it responds to the requests it receives
            with the data it currently has in the cache."
        ::= { g3pktrunksum 2 }

    g3pktrunksumTdelay	OBJECT-TYPE
        SYNTAX    INTEGER
        ACCESS    read-only
        STATUS    mandatory
        DESCRIPTION
            "An object containing the delay encountered in updating
            the cached data."
        ::= { g3pktrunksum 3 }

    g3pktrunksumTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3pktrunksum 4 }

    g3pktrunksumTcount	OBJECT-TYPE
        SYNTAX    Gauge
        ACCESS    read-only
        STATUS    mandatory
        DESCRIPTION
            "A Gauge object containing the number of data records in the cache."
        ::= { g3pktrunksum 5 }

    g3pktrunksumTable	OBJECT-TYPE
        SYNTAX    SEQUENCE OF G3pktrunksumEntry
        ACCESS    not-accessible
        STATUS    mandatory
        DESCRIPTION
            "A list of g3pktrunksum entries."
        ::= { g3pktrunksum 6 }

    g3pktrunksumEntry	OBJECT-TYPE
        SYNTAX    G3pktrunksumEntry
        ACCESS    not-accessible
        STATUS    mandatory
        DESCRIPTION
            "A g3pktrunksum entry containing objects of the
            g3pktrunksum information sent by the switch."
        INDEX    { g3pktrunksumTrunkGroup }
        ::= { g3pktrunksumTable 1 }

    G3pktrunksumEntry ::= SEQUENCE {
        g3pktrunksumTrunkGroup
            INTEGER,
        g3pktrunksumMeasHour
            INTEGER,
        g3pktrunksumRunYear
            INTEGER,
        g3pktrunksumRunMonth
            INTEGER,
        g3pktrunksumRunDay
            INTEGER,
        g3pktrunksumRunHour
            INTEGER,
        g3pktrunksumGroupSize
            INTEGER,
        g3pktrunksumTotalUsage
            INTEGER,
        g3pktrunksumTotalSeize
            INTEGER,
        g3pktrunksumIncSeize
            INTEGER,
        g3pktrunksumGrpOvfl
            INTEGER,
        g3pktrunksumQueSiz
            INTEGER,
        g3pktrunksumCallQued
            INTEGER,
        g3pktrunksumQueOvf
            INTEGER,
        g3pktrunksumQueAbd
            INTEGER,
        g3pktrunksumOutSrv
            INTEGER,
        g3pktrunksumPercentAtb
            INTEGER,
        g3pktrunksumPercentOutBlk
            INTEGER
        }

    g3pktrunksumTrunkGroup	OBJECT-TYPE
        SYNTAX    INTEGER
        ACCESS    read-only
        STATUS    mandatory
        DESCRIPTION
            "An object containing the trunk group number for which data has
            been collected."
        ::= { g3pktrunksumEntry 1 }

    g3pktrunksumMeasHour	OBJECT-TYPE
        SYNTAX    INTEGER
        ACCESS    read-only
        STATUS    mandatory
        DESCRIPTION
            "An object containing the Hour the measurement was taken."
        ::= { g3pktrunksumEntry 2 }

    g3pktrunksumRunYear	OBJECT-TYPE
        SYNTAX    INTEGER
        ACCESS    read-only
        STATUS    mandatory
        DESCRIPTION
            "An object containing the Year the command was executed."
        ::= { g3pktrunksumEntry 3 }

    g3pktrunksumRunMonth	OBJECT-TYPE
        SYNTAX    INTEGER
        ACCESS    read-only
        STATUS    mandatory
        DESCRIPTION
            "An object containing the Month the command was executed."
        ::= { g3pktrunksumEntry 4 }

    g3pktrunksumRunDay	OBJECT-TYPE
        SYNTAX    INTEGER
        ACCESS    read-only
        STATUS    mandatory
        DESCRIPTION
            "An object containing the Day the command was executed."
        ::= { g3pktrunksumEntry 5 }

    g3pktrunksumRunHour	OBJECT-TYPE
        SYNTAX    INTEGER
        ACCESS    read-only
        STATUS    mandatory
        DESCRIPTION
            "An object containing the Hour the command was executed."
        ::= { g3pktrunksumEntry 6 }

    g3pktrunksumGroupSize	OBJECT-TYPE
        SYNTAX    INTEGER
        ACCESS    read-only
        STATUS    mandatory
        DESCRIPTION
            "An object containing the number of administered trunks in the trunk
            group."
        ::= { g3pktrunksumEntry 7 }

    g3pktrunksumTotalUsage	OBJECT-TYPE
        SYNTAX    INTEGER
        ACCESS    read-only
        STATUS    mandatory
        DESCRIPTION
            "An object containing the total time trunks are busy with calls
            during the measurement period (in CCS)."
        ::= { g3pktrunksumEntry 8 }

    g3pktrunksumTotalSeize	OBJECT-TYPE
        SYNTAX    INTEGER
        ACCESS    read-only
        STATUS    mandatory
        DESCRIPTION
            "An object containing the number of times a trunk was seized in the
            group including false starts, don't answer and busy."
        ::= { g3pktrunksumEntry 9 }

    g3pktrunksumIncSeize	OBJECT-TYPE
        SYNTAX    INTEGER
        ACCESS    read-only
        STATUS    mandatory
        DESCRIPTION
            "An object containing the number of incoming seizures carried on the
            trunk group."
        ::= { g3pktrunksumEntry 10 }

    g3pktrunksumGrpOvfl	OBJECT-TYPE
        SYNTAX    INTEGER
        ACCESS    read-only
        STATUS    mandatory
        DESCRIPTION
            "An object containing the number of calls offered to a trunk group
            that are not carried or queued."
        ::= { g3pktrunksumEntry 11 }

    g3pktrunksumQueSiz	OBJECT-TYPE
        SYNTAX    INTEGER
        ACCESS    read-only
        STATUS    mandatory
        DESCRIPTION
            "An object containing a number (0-100) that identifies the number of
            slots assigned to the trunk group queue."
        ::= { g3pktrunksumEntry 12 }

    g3pktrunksumCallQued	OBJECT-TYPE
        SYNTAX    INTEGER
        ACCESS    read-only
        STATUS    mandatory
        DESCRIPTION
            "An object containing the total number of calls that entered the
            trunk group queue after finding all trunks busy."
        ::= { g3pktrunksumEntry 13 }

    g3pktrunksumQueOvf	OBJECT-TYPE
        SYNTAX    INTEGER
        ACCESS    read-only
        STATUS    mandatory
        DESCRIPTION
            "An object containing the total number of calls that were not queued
            because the queue was full."
        ::= { g3pktrunksumEntry 14 }

    g3pktrunksumQueAbd	OBJECT-TYPE
        SYNTAX    INTEGER
        ACCESS    read-only
        STATUS    mandatory
        DESCRIPTION
            "An object containing the total number of calls that were removed
            from the queue (i.e., due to queue timeout or user cancel)"
        ::= { g3pktrunksumEntry 15 }

    g3pktrunksumOutSrv	OBJECT-TYPE
        SYNTAX    INTEGER
        ACCESS    read-only
        STATUS    mandatory
        DESCRIPTION
            "An object containing the number of trunks in the group that are
            out of service (maintenance busy)."
        ::= { g3pktrunksumEntry 16 }

    g3pktrunksumPercentAtb	OBJECT-TYPE
        SYNTAX    INTEGER
        ACCESS    read-only
        STATUS    mandatory
        DESCRIPTION
            "An object containing the percentage of time all trunks in the group
            were simultaneously in use."
        ::= { g3pktrunksumEntry 17 }

    g3pktrunksumPercentOutBlk	OBJECT-TYPE
        SYNTAX    INTEGER
        ACCESS    read-only
        STATUS    mandatory
        DESCRIPTION
            "An object containing the percentage of offered calls that are not
            carried on the group."
        ::= { g3pktrunksumEntry 18 }


    -- the g3trunkwbsum group

    g3trunkwbsumTage	OBJECT-TYPE
        SYNTAX    INTEGER
        ACCESS    read-only
        STATUS    mandatory
        DESCRIPTION
            "The number of timeticks since the wideband trunk summary data was last
            extracted from the switch by the Proxy Agent.  This object
            along with the g3trunkwbsumintvl object allows the Network Manager
            to determine the validity of the data in the cache and to control
            when the Proxy Agent extracts the data from the switch."
        ::= { g3trunkwbsum 1 }

    g3trunkwbsumTintvl	OBJECT-TYPE
        SYNTAX    INTEGER
        ACCESS    read-write
        STATUS    mandatory
        DESCRIPTION
            "An object containing the interval for which the wideband trunk
            summary data extracted from the switch is considered valid by the
            Proxy Agent.  When a GET or GET-NEXT request for wideband trunk
            summary objects is received by the agent it uses the g3trunkwbsumage
            and g3trunkwbsumintvl objects to determine whether it should refresh
            the cached trunkwbsumTable.  If g3trunkwbsumstmp + g3trunkwbsumintvl
            is less than the current value of the sysUpTime object then the agent
            refreshes the trunkwbsumTable cache.  In either case it responds to
            the requests it receives with the data it currently has in the cache."
        ::= { g3trunkwbsum 2 }

    g3trunkwbsumTdelay	OBJECT-TYPE
        SYNTAX    INTEGER
        ACCESS    read-only
        STATUS    mandatory
        DESCRIPTION
            "An object containing the delay encountered in updating
            the cached data."
        ::= { g3trunkwbsum 3 }

    g3trunkwbsumTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3trunkwbsum 4 }

    g3trunkwbsumTcount	OBJECT-TYPE
        SYNTAX    Gauge
        ACCESS    read-only
        STATUS    mandatory
        DESCRIPTION
            "A Gauge object containing the number of data records in the cache."
        ::= { g3trunkwbsum 5 }

    g3trunkwbsumTable	OBJECT-TYPE
        SYNTAX    SEQUENCE OF G3trunkwbsumEntry
        ACCESS    not-accessible
        STATUS    mandatory
        DESCRIPTION
            "A list of g3trunkwbsum entries."
        ::= { g3trunkwbsum 6 }

    g3trunkwbsumEntry	OBJECT-TYPE
        SYNTAX    G3trunkwbsumEntry
        ACCESS    not-accessible
        STATUS    mandatory
        DESCRIPTION
            "A g3trunkwbsum entry containing objects of the
            g3trunkwbsum information sent by the switch."
        INDEX    { g3trunkwbsumTrunkGroup }
        ::= { g3trunkwbsumTable 1 }

    G3trunkwbsumEntry ::= SEQUENCE {
        g3trunkwbsumTrunkGroup
            INTEGER,
        g3trunkwbsumMeasHour
            INTEGER,
        g3trunkwbsumYear
            INTEGER,
        g3trunkwbsumMonth
            INTEGER,
        g3trunkwbsumDay
            INTEGER,
        g3trunkwbsumHour
            INTEGER,
        g3trunkwbsumTotalUsage
            INTEGER,
        g3trunkwbsumTotalSeize
            INTEGER,
        g3trunkwbsumIncSeize
            INTEGER,
        g3trunkwbsumGrpOvfl
            INTEGER,
        g3trunkwbsumOutSrv
            INTEGER,
        g3trunkwbsumPercentAtb
            INTEGER,
        g3trunkwbsumPercentOutBlk
            INTEGER
        }

    g3trunkwbsumTrunkGroup	OBJECT-TYPE
        SYNTAX    INTEGER
        ACCESS    read-only
        STATUS    mandatory
        DESCRIPTION
            "An object containing the trunk group number for which data has
            been collected."
        ::= { g3trunkwbsumEntry 1 }

    g3trunkwbsumMeasHour	OBJECT-TYPE
        SYNTAX    INTEGER
        ACCESS    read-only
        STATUS    mandatory
        DESCRIPTION
            "An object containing the Hour the measurement was taken."
        ::= { g3trunkwbsumEntry 2 }

    g3trunkwbsumYear	OBJECT-TYPE
        SYNTAX    INTEGER
        ACCESS    read-only
        STATUS    mandatory
        DESCRIPTION
            "An object containing the Year the command was executed."
        ::= { g3trunkwbsumEntry 3 }

    g3trunkwbsumMonth	OBJECT-TYPE
        SYNTAX    INTEGER
        ACCESS    read-only
        STATUS    mandatory
        DESCRIPTION
            "An object containing the Month the command was executed."
        ::= { g3trunkwbsumEntry 4 }

    g3trunkwbsumDay	OBJECT-TYPE
        SYNTAX    INTEGER
        ACCESS    read-only
        STATUS    mandatory
        DESCRIPTION
            "An object containing the Day the command was executed."
        ::= { g3trunkwbsumEntry 5 }

    g3trunkwbsumHour	OBJECT-TYPE
        SYNTAX    INTEGER
        ACCESS    read-only
        STATUS    mandatory
        DESCRIPTION
            "An object containing the Hour the command was executed."
        ::= { g3trunkwbsumEntry 6 }

    g3trunkwbsumTotalUsage	OBJECT-TYPE
        SYNTAX    INTEGER
        ACCESS    read-only
        STATUS    mandatory
        DESCRIPTION
            "An object containing the total wideband call usage for
            all trunks in the trunk group (in CCS)."
        ::= { g3trunkwbsumEntry 7 }

    g3trunkwbsumTotalSeize	OBJECT-TYPE
        SYNTAX    INTEGER
        ACCESS    read-only
        STATUS    mandatory
        DESCRIPTION
            "An object containing the number of wideband call attempts."
        ::= { g3trunkwbsumEntry 8 }

    g3trunkwbsumIncSeize	OBJECT-TYPE
        SYNTAX    INTEGER
        ACCESS    read-only
        STATUS    mandatory
        DESCRIPTION
            "An object containing the number of wideband incoming call attempts."
        ::= { g3trunkwbsumEntry 9 }

    g3trunkwbsumGrpOvfl	OBJECT-TYPE
        SYNTAX    INTEGER
        ACCESS    read-only
        STATUS    mandatory
        DESCRIPTION
            "An object containing the number of wideband outgoing calls that
            were attempted when the remaining trunk group capacity was
            insufficient to accommodate the call or the trunk group's
            remaining bandwidth was in the wrong configuration."
        ::= { g3trunkwbsumEntry 10 }

    g3trunkwbsumOutSrv	OBJECT-TYPE
        SYNTAX    INTEGER
        ACCESS    read-only
        STATUS    mandatory
        DESCRIPTION
            "An object containing the number of wideband trunks in the group
            that are out of service (listed as maintenance busy)."
        ::= { g3trunkwbsumEntry 11 }

    g3trunkwbsumPercentAtb	OBJECT-TYPE
        SYNTAX    INTEGER
        ACCESS    read-only
        STATUS    mandatory
        DESCRIPTION
            "An object containing the percentage of time that all trunks in
            the trunk group were simultaneously in use during the
            measurement interval."
        ::= { g3trunkwbsumEntry 12 }

    g3trunkwbsumPercentOutBlk	OBJECT-TYPE
        SYNTAX    INTEGER
        ACCESS    read-only
        STATUS    mandatory
        DESCRIPTION
            "An object containing the percentage of offered wideband calls that
            are not carried on the trunk group."
        ::= { g3trunkwbsumEntry 13 }


    -- the g3pktrunkwbsum group

    g3pktrunkwbsumTage	OBJECT-TYPE
        SYNTAX    INTEGER
        ACCESS    read-only
        STATUS    mandatory
        DESCRIPTION
            "The number of timeticks since the wideband trunk summary data was last
            extracted from the switch by the Proxy Agent.  This object
            along with the g3trunkwbsumintvl object allows the Network Manager
            to determine the validity of the data in the cache and to control
            when the Proxy Agent extracts the data from the switch."
        ::= { g3pktrunkwbsum 1 }

    g3pktrunkwbsumTintvl	OBJECT-TYPE
        SYNTAX    INTEGER
        ACCESS    read-write
        STATUS    mandatory
        DESCRIPTION
            "An object containing the interval for which the wideband trunk
            summary data extracted from the switch is considered valid by the
            Proxy Agent.  When a GET or GET-NEXT request for wideband trunk
            summary objects is received by the agent it uses the g3trunkwbsumage
            and g3trunkwbsumintvl objects to determine whether it should refresh
            the cached trunkwbsumTable.  If g3trunkwbsumstmp + g3trunkwbsumintvl
            is less than the current value of the sysUpTime object then the agent
            refreshes the trunkwbsumTable cache.  In either case it responds to
            the requests it receives with the data it currently has in the cache."
        ::= { g3pktrunkwbsum 2 }

    g3pktrunkwbsumTdelay	OBJECT-TYPE
        SYNTAX    INTEGER
        ACCESS    read-only
        STATUS    mandatory
        DESCRIPTION
            "An object containing the delay encountered in updating
            the cached data."
        ::= { g3pktrunkwbsum 3 }

    g3pktrunkwbsumTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3pktrunkwbsum 4 }

    g3pktrunkwbsumTcount	OBJECT-TYPE
        SYNTAX    Gauge
        ACCESS    read-only
        STATUS    mandatory
        DESCRIPTION
            "A Gauge object containing the number of data records in the cache."
        ::= { g3pktrunkwbsum 5 }

    g3pktrunkwbsumTable	OBJECT-TYPE
        SYNTAX    SEQUENCE OF G3pktrunkwbsumEntry
        ACCESS    not-accessible
        STATUS    mandatory
        DESCRIPTION
            "A list of g3pktrunkwbsum entries."
        ::= { g3pktrunkwbsum 6 }

    g3pktrunkwbsumEntry	OBJECT-TYPE
        SYNTAX    G3pktrunkwbsumEntry
        ACCESS    not-accessible
        STATUS    mandatory
        DESCRIPTION
            "A g3pktrunkwbsum entry containing objects of the
            g3pktrunkwbsum information sent by the switch."
        INDEX    { g3pktrunkwbsumTrunkGroup }
        ::= { g3pktrunkwbsumTable 1 }

    G3pktrunkwbsumEntry ::= SEQUENCE {
        g3pktrunkwbsumTrunkGroup
            INTEGER,
        g3pktrunkwbsumMeasHour
            INTEGER,
        g3pktrunkwbsumYear
            INTEGER,
        g3pktrunkwbsumMonth
            INTEGER,
        g3pktrunkwbsumDay
            INTEGER,
        g3pktrunkwbsumHour
            INTEGER,
        g3pktrunkwbsumTotalUsage
            INTEGER,
        g3pktrunkwbsumTotalSeize
            INTEGER,
        g3pktrunkwbsumIncSeize
            INTEGER,
        g3pktrunkwbsumGrpOvfl
            INTEGER,
        g3pktrunkwbsumOutSrv
            INTEGER,
        g3pktrunkwbsumPercentAtb
            INTEGER,
        g3pktrunkwbsumPercentOutBlk
            INTEGER
        }

    g3pktrunkwbsumTrunkGroup	OBJECT-TYPE
        SYNTAX    INTEGER
        ACCESS    read-only
        STATUS    mandatory
        DESCRIPTION
            "An object containing the trunk group number for which data has
            been collected."
        ::= { g3pktrunkwbsumEntry 1 }

    g3pktrunkwbsumMeasHour	OBJECT-TYPE
        SYNTAX    INTEGER
        ACCESS    read-only
        STATUS    mandatory
        DESCRIPTION
            "An object containing the Hour the measurement was taken."
        ::= { g3pktrunkwbsumEntry 2 }

    g3pktrunkwbsumYear	OBJECT-TYPE
        SYNTAX    INTEGER
        ACCESS    read-only
        STATUS    mandatory
        DESCRIPTION
            "An object containing the Year the command was executed."
        ::= { g3pktrunkwbsumEntry 3 }

    g3pktrunkwbsumMonth	OBJECT-TYPE
        SYNTAX    INTEGER
        ACCESS    read-only
        STATUS    mandatory
        DESCRIPTION
            "An object containing the Month the command was executed."
        ::= { g3pktrunkwbsumEntry 4 }

    g3pktrunkwbsumDay	OBJECT-TYPE
        SYNTAX    INTEGER
        ACCESS    read-only
        STATUS    mandatory
        DESCRIPTION
            "An object containing the Day the command was executed."
        ::= { g3pktrunkwbsumEntry 5 }

    g3pktrunkwbsumHour	OBJECT-TYPE
        SYNTAX    INTEGER
        ACCESS    read-only
        STATUS    mandatory
        DESCRIPTION
            "An object containing the Hour the command was executed."
        ::= { g3pktrunkwbsumEntry 6 }

    g3pktrunkwbsumTotalUsage	OBJECT-TYPE
        SYNTAX    INTEGER
        ACCESS    read-only
        STATUS    mandatory
        DESCRIPTION
            "An object containing the total wideband call usage for
            all trunks in the trunk group (in CCS)."
        ::= { g3pktrunkwbsumEntry 7 }

    g3pktrunkwbsumTotalSeize	OBJECT-TYPE
        SYNTAX    INTEGER
        ACCESS    read-only
        STATUS    mandatory
        DESCRIPTION
            "An object containing the number of wideband call attempts."
        ::= { g3pktrunkwbsumEntry 8 }

    g3pktrunkwbsumIncSeize	OBJECT-TYPE
        SYNTAX    INTEGER
        ACCESS    read-only
        STATUS    mandatory
        DESCRIPTION
            "An object containing the number of wideband incoming call attempts."
        ::= { g3pktrunkwbsumEntry 9 }

    g3pktrunkwbsumGrpOvfl	OBJECT-TYPE
        SYNTAX    INTEGER
        ACCESS    read-only
        STATUS    mandatory
        DESCRIPTION
            "An object containing the number of wideband outgoing calls that
            were attempted when the remaining trunk group capacity was
            insufficient to accommodate the call or the trunk group's
            remaining bandwidth was in the wrong configuration."
        ::= { g3pktrunkwbsumEntry 10 }

    g3pktrunkwbsumOutSrv	OBJECT-TYPE
        SYNTAX    INTEGER
        ACCESS    read-only
        STATUS    mandatory
        DESCRIPTION
            "An object containing the number of wideband trunks in the group
            that are out of service (listed as maintenance busy)."
        ::= { g3pktrunkwbsumEntry 11 }

    g3pktrunkwbsumPercentAtb	OBJECT-TYPE
        SYNTAX    INTEGER
        ACCESS    read-only
        STATUS    mandatory
        DESCRIPTION
            "An object containing the percentage of time that all trunks in
            the trunk group were simultaneously in use during the
            measurement interval."
        ::= { g3pktrunkwbsumEntry 12 }

    g3pktrunkwbsumPercentOutBlk	OBJECT-TYPE
        SYNTAX    INTEGER
        ACCESS    read-only
        STATUS    mandatory
        DESCRIPTION
            "An object containing the percentage of offered wideband calls that
            are not carried on the trunk group."
        ::= { g3pktrunkwbsumEntry 13 }


    -- the g3pktrunkout group

    g3pktrunkoutTage	OBJECT-TYPE
        SYNTAX    INTEGER
        ACCESS    read-only
        STATUS    mandatory
        DESCRIPTION
            "The number of timeticks since the outage trunk data was last
            extracted from the switch by the Proxy Agent.  This object
            along with the g3pktrunkoutintvl object allows the Network Manager
            to determine the validity of the data in the cache and to control
            when the Proxy Agent extracts the data from the switch."
        ::= { g3pktrunkout 1 }

    g3pktrunkoutTintvl	OBJECT-TYPE
        SYNTAX    INTEGER
        ACCESS    read-write
        STATUS    mandatory
        DESCRIPTION
            "An object containing the interval for which the trunk outage
            data extracted from the switch is considered valid by the
            Proxy Agent.  When a GET or GET-NEXT request for trunk outage
            objects is received by the agent it uses the g3pktrunkoutage
            and g3pktrunkoutintvl objects to determine whether it should refresh
            the cached pktrunkoutTable.  If g3pktrunkoutstmp + g3pktrunkoutintvl
            is less than the current value of the sysUpTime object then the agent
            refreshes the pktrunkoutTable cache.  In either case it responds to
            the requests it receives with the data it currently has in the cache."
        ::= { g3pktrunkout 2 }

    g3pktrunkoutTdelay	OBJECT-TYPE
        SYNTAX    INTEGER
        ACCESS    read-only
        STATUS    mandatory
        DESCRIPTION
            "An object containing the delay encountered in updating
            the cached data."
        ::= { g3pktrunkout 3 }

    g3pktrunkoutTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3pktrunkout 4 }

    g3pktrunkoutTcount	OBJECT-TYPE
        SYNTAX    Gauge
        ACCESS    read-only
        STATUS    mandatory
        DESCRIPTION
            "A Gauge object containing the number of data records in the cache."
        ::= { g3pktrunkout 5 }

    g3pktrunkoutTable	OBJECT-TYPE
        SYNTAX    SEQUENCE OF G3pktrunkoutEntry
        ACCESS    not-accessible
        STATUS    mandatory
        DESCRIPTION
            "A list of g3pktrunkout entries."
        ::= { g3pktrunkout 6 }

    g3pktrunkoutEntry	OBJECT-TYPE
        SYNTAX    G3pktrunkoutEntry
        ACCESS    not-accessible
        STATUS    mandatory
        DESCRIPTION
            "A g3pktrunkout entry containing objects of the
            g3pktrunkout information sent by the switch."
        INDEX    { g3pktrunkoutTrunkGroup, g3pktrunkoutMember }
        ::= { g3pktrunkoutTable 1 }

    G3pktrunkoutEntry ::= SEQUENCE {
        g3pktrunkoutTrunkGroup
            INTEGER,
        g3pktrunkoutMember
            INTEGER,
        g3pktrunkoutYear
            INTEGER,
        g3pktrunkoutMonth
            INTEGER,
        g3pktrunkoutDay
            INTEGER,
        g3pktrunkoutHour
            INTEGER,
        g3pktrunkoutOutages
            INTEGER
        }

    g3pktrunkoutTrunkGroup	OBJECT-TYPE
        SYNTAX    INTEGER
        ACCESS    read-only
        STATUS    mandatory
        DESCRIPTION
            "An object containing the trunk group number."
        ::= { g3pktrunkoutEntry 1 }

    g3pktrunkoutMember	OBJECT-TYPE
        SYNTAX    INTEGER
        ACCESS    read-only
        STATUS    mandatory
        DESCRIPTION
            "An object containing the group member number."
        ::= { g3pktrunkoutEntry 2 }

    g3pktrunkoutYear	OBJECT-TYPE
        SYNTAX    INTEGER
        ACCESS    read-only
        STATUS    mandatory
        DESCRIPTION
            "An object containing the Year the command was executed."
        ::= { g3pktrunkoutEntry 3 }

    g3pktrunkoutMonth	OBJECT-TYPE
        SYNTAX    INTEGER
        ACCESS    read-only
        STATUS    mandatory
        DESCRIPTION
            "An object containing the Month the command was executed."
        ::= { g3pktrunkoutEntry 4 }

    g3pktrunkoutDay	OBJECT-TYPE
        SYNTAX    INTEGER
        ACCESS    read-only
        STATUS    mandatory
        DESCRIPTION
            "An object containing the Day the command was executed."
        ::= { g3pktrunkoutEntry 5 }

    g3pktrunkoutHour	OBJECT-TYPE
        SYNTAX    INTEGER
        ACCESS    read-only
        STATUS    mandatory
        DESCRIPTION
            "An object containing the Hour the command was executed."
        ::= { g3pktrunkoutEntry 6 }

    g3pktrunkoutOutages	OBJECT-TYPE
        SYNTAX    INTEGER
        ACCESS    read-only
        STATUS    mandatory
        DESCRIPTION
            "An object containing the number of times the group member is
            sampled as out of service over the measurement period."
        ::= { g3pktrunkoutEntry 7 }


    -- the g3pktrunklight group

    g3pktrunklightTage	OBJECT-TYPE
        SYNTAX    INTEGER
        ACCESS    read-only
        STATUS    mandatory
        DESCRIPTION
            "The number of timeticks since the lightly used trunk data was last
            extracted from the switch by the Proxy Agent.  This object
            along with the g3pktrunklightintvl object allows the Network Manager
            to determine the validity of the data in the cache and to control
            when the Proxy Agent extracts the data from the switch."
        ::= { g3pktrunklight 1 }

    g3pktrunklightTintvl	OBJECT-TYPE
        SYNTAX    INTEGER
        ACCESS    read-write
        STATUS    mandatory
        DESCRIPTION
            "An object containing the interval for which the lightly used trunk
            data extracted from the switch is considered valid by the
            Proxy Agent.  When a GET or GET-NEXT request for lightly used trunk
            objects is received by the agent it uses the g3pktrunklightage
            and g3pktrunklightintvl objects to determine whether it should refresh
            the cached pktrunklightTable. If g3pktrunklightstmp+g3pktrunklightintvl
            is less than the current value of the sysUpTime object then the agent
            refreshes the pktrunklightTable cache.  In either case it responds to
            the requests it receives with the data it currently has in the cache."
        ::= { g3pktrunklight 2 }

    g3pktrunklightTdelay	OBJECT-TYPE
        SYNTAX    INTEGER
        ACCESS    read-only
        STATUS    mandatory
        DESCRIPTION
            "An object containing the delay encountered in updating
            the cached data."
        ::= { g3pktrunklight 3 }

    g3pktrunklightTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3pktrunklight 4 }

    g3pktrunklightTcount	OBJECT-TYPE
        SYNTAX    Gauge
        ACCESS    read-only
        STATUS    mandatory
        DESCRIPTION
            "A Gauge object containing the number of data records in the cache."
        ::= { g3pktrunklight 5 }

    g3pktrunklightTable	OBJECT-TYPE
        SYNTAX    SEQUENCE OF G3pktrunklightEntry
        ACCESS    not-accessible
        STATUS    mandatory
        DESCRIPTION
            "A list of g3pktrunklight entries."
        ::= { g3pktrunklight 6 }

    g3pktrunklightEntry	OBJECT-TYPE
        SYNTAX    G3pktrunklightEntry
        ACCESS    not-accessible
        STATUS    mandatory
        DESCRIPTION
            "A g3pktrunklight entry containing objects of the
            g3pktrunklight information sent by the switch."
        INDEX    { g3pktrunklightTrunkGroup, g3pktrunklightMember }
        ::= { g3pktrunklightTable 1 }

    G3pktrunklightEntry ::= SEQUENCE {
        g3pktrunklightTrunkGroup
            INTEGER,
        g3pktrunklightMember
            INTEGER,
        g3pktrunklightYear
            INTEGER,
        g3pktrunklightMonth
            INTEGER,
        g3pktrunklightDay
            INTEGER,
        g3pktrunklightHour
            INTEGER,
        g3pktrunklightCarried
            INTEGER
        }

    g3pktrunklightTrunkGroup	OBJECT-TYPE
        SYNTAX    INTEGER
        ACCESS    read-only
        STATUS    mandatory
        DESCRIPTION
            "An object containing the trunk group number."
        ::= { g3pktrunklightEntry 1 }

    g3pktrunklightMember	OBJECT-TYPE
        SYNTAX    INTEGER
        ACCESS    read-only
        STATUS    mandatory
        DESCRIPTION
            "An object containing the group member number."
        ::= { g3pktrunklightEntry 2 }

    g3pktrunklightYear	OBJECT-TYPE
        SYNTAX    INTEGER
        ACCESS    read-only
        STATUS    mandatory
        DESCRIPTION
            "An object containing the Year the command was executed."
        ::= { g3pktrunklightEntry 3 }

    g3pktrunklightMonth	OBJECT-TYPE
        SYNTAX    INTEGER
        ACCESS    read-only
        STATUS    mandatory
        DESCRIPTION
            "An object containing the Month the command was executed."
        ::= { g3pktrunklightEntry 4 }

    g3pktrunklightDay	OBJECT-TYPE
        SYNTAX    INTEGER
        ACCESS    read-only
        STATUS    mandatory
        DESCRIPTION
            "An object containing the Day the command was executed."
        ::= { g3pktrunklightEntry 5 }

    g3pktrunklightHour	OBJECT-TYPE
        SYNTAX    INTEGER
        ACCESS    read-only
        STATUS    mandatory
        DESCRIPTION
            "An object containing the Hour the command was executed."
        ::= { g3pktrunklightEntry 6 }

    g3pktrunklightCarried	OBJECT-TYPE
        SYNTAX    INTEGER
        ACCESS    read-only
        STATUS    mandatory
        DESCRIPTION
            "An object containing the number of calls carried on the trunk
            member over the measurement interval."
        ::= { g3pktrunklightEntry 7 }


    -- the g3pnblock group

    g3pnblockTage	OBJECT-TYPE
        SYNTAX    INTEGER
        ACCESS    read-only
        STATUS    mandatory
        DESCRIPTION
            "The number of timeticks since the port network blockage data was
            last extracted from the switch by the Proxy Agent.  This object
            along with the g3pnblockintvl object allows the Network Manager
            to determine the validity of the data in the cache and to control
            when the Proxy Agent extracts the data from the switch."
        ::= { g3pnblock 1 }

    g3pnblockTintvl	OBJECT-TYPE
        SYNTAX    INTEGER
        ACCESS    read-write
        STATUS    mandatory
        DESCRIPTION
            "An object containing the interval for which the port network blockage
            data extracted from the switch is considered valid by the Proxy Agent.
            When a GET or GET-NEXT request for port network blockage objects is
            received by the agent it uses the g3pnblockage and g3pnblockintvl
            objects to determine whether it should refresh the cached pnblockTable.
            If g3pnblockstmp + g3pnblockintvl is less than the current value of
            the sysUpTime object then the agent refreshes the pnblockTable
            cache.  In either case it responds to the requests it receives
            with the data it currently has in the cache."
        ::= { g3pnblock 2 }

    g3pnblockTdelay	OBJECT-TYPE
        SYNTAX    INTEGER
        ACCESS    read-only
        STATUS    mandatory
        DESCRIPTION
            "An object containing the delay encountered in updating
            the cached data."
        ::= { g3pnblock 3 }

    g3pnblockTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3pnblock 4 }

    g3pnblockTcount	OBJECT-TYPE
        SYNTAX    Gauge
        ACCESS    read-only
        STATUS    mandatory
        DESCRIPTION
            "A Gauge object containing the number of data records in the cache."
        ::= { g3pnblock 5 }

    g3pnblockTable	OBJECT-TYPE
        SYNTAX    SEQUENCE OF G3pnblockEntry
        ACCESS    not-accessible
        STATUS    mandatory
        DESCRIPTION
            "A list of g3pnblock entries."
        ::= { g3pnblock 6 }

    g3pnblockEntry	OBJECT-TYPE
        SYNTAX    G3pnblockEntry
        ACCESS    not-accessible
        STATUS    mandatory
        DESCRIPTION
            "A g3pnblock entry containing objects of the
            g3pnblock information sent by the switch."
        INDEX    { g3pnblockPNNumber }
        ::= { g3pnblockTable 1 }

    G3pnblockEntry ::= SEQUENCE {
        g3pnblockPNNumber
            INTEGER,
        g3pnblockMeasHour
            INTEGER,
        g3pnblockYear
            INTEGER,
        g3pnblockMonth
            INTEGER,
        g3pnblockDay
            INTEGER,
        g3pnblockHour
            INTEGER,
        g3pnblockTdmUsage
            INTEGER,
        g3pnblockTdmPeg
            INTEGER,
        g3pnblockTdmPeak
            INTEGER,
        g3pnblockTdmBlockage
            INTEGER,
        g3pnblockTimeSlots
            INTEGER,
        g3pnblockPNlinkUsage
            INTEGER,
        g3pnblockPNlinkPeg
            INTEGER,
        g3pnblockPNlinkPeak
            INTEGER,
        g3pnblockPNlinkBlockage
            INTEGER
        }

    g3pnblockPNNumber	OBJECT-TYPE
        SYNTAX    INTEGER
        ACCESS    read-only
        STATUS    mandatory
        DESCRIPTION
            "An object containing the Port Network number."
        ::= { g3pnblockEntry 1 }

    g3pnblockMeasHour	OBJECT-TYPE
        SYNTAX    INTEGER
        ACCESS    read-only
        STATUS    mandatory
        DESCRIPTION
            "An object containing the Hour the measurement was taken."
        ::= { g3pnblockEntry 2 }

    g3pnblockYear	OBJECT-TYPE
        SYNTAX    INTEGER
        ACCESS    read-only
        STATUS    mandatory
        DESCRIPTION
            "An object containing the Year the command was executed."
        ::= { g3pnblockEntry 3 }

    g3pnblockMonth	OBJECT-TYPE
        SYNTAX    INTEGER
        ACCESS    read-only
        STATUS    mandatory
        DESCRIPTION
            "An object containing the Month the command was executed."
        ::= { g3pnblockEntry 4 }

    g3pnblockDay	OBJECT-TYPE
        SYNTAX    INTEGER
        ACCESS    read-only
        STATUS    mandatory
        DESCRIPTION
            "An object containing the Day the command was executed."
        ::= { g3pnblockEntry 5 }

    g3pnblockHour	OBJECT-TYPE
        SYNTAX    INTEGER
        ACCESS    read-only
        STATUS    mandatory
        DESCRIPTION
            "An object containing the Hour the command was executed."
        ::= { g3pnblockEntry 6 }

    g3pnblockTdmUsage	OBJECT-TYPE
        SYNTAX    INTEGER
        ACCESS    read-only
        STATUS    mandatory
        DESCRIPTION
            "An object containing the total TDM time-slot usage."
        ::= { g3pnblockEntry 7 }

    g3pnblockTdmPeg	OBJECT-TYPE
        SYNTAX    INTEGER
        ACCESS    read-only
        STATUS    mandatory
        DESCRIPTION
            "An object containing the total count of circuit switch TDM time-slot
            seizure attempts for the PN."
        ::= { g3pnblockEntry 8 }

    g3pnblockTdmPeak	OBJECT-TYPE
        SYNTAX    INTEGER
        ACCESS    read-only
        STATUS    mandatory
        DESCRIPTION
            "An object containing the maximum number of time-slots allocated
            at any one time."
        ::= { g3pnblockEntry 9 }

    g3pnblockTdmBlockage	OBJECT-TYPE
        SYNTAX    INTEGER
        ACCESS    read-only
        STATUS    mandatory
        DESCRIPTION
            "An object containing the total count of TDM blockages, that is, the
            total number of times a TDM time-slot request is denied for the PN."
        ::= { g3pnblockEntry 10 }

    g3pnblockTimeSlots	OBJECT-TYPE
        SYNTAX    INTEGER
        ACCESS    read-only
        STATUS    mandatory
        DESCRIPTION
            "An object containing the number of PN link time-slots available
            between port networks or between Port Networks and Switch Nodes."
        ::= { g3pnblockEntry 11 }

    g3pnblockPNlinkUsage	OBJECT-TYPE
        SYNTAX    INTEGER
        ACCESS    read-only
        STATUS    mandatory
        DESCRIPTION
            "An object containing the total circuit switch usage of the
            available PN link(s) connecting the PN to the SN or to other PNs."
        ::= { g3pnblockEntry 12 }

    g3pnblockPNlinkPeg	OBJECT-TYPE
        SYNTAX    INTEGER
        ACCESS    read-only
        STATUS    mandatory
        DESCRIPTION
            "An object containing the total count of circuit switched time-slot
            seizure attempts for the link(s)."
        ::= { g3pnblockEntry 13 }

    g3pnblockPNlinkPeak	OBJECT-TYPE
        SYNTAX    INTEGER
        ACCESS    read-only
        STATUS    mandatory
        DESCRIPTION
            "An object containing the maximum number of time slots allocated
            at any one time on the PN links."
        ::= { g3pnblockEntry 14 }

    g3pnblockPNlinkBlockage	OBJECT-TYPE
        SYNTAX    INTEGER
        ACCESS    read-only
        STATUS    mandatory
        DESCRIPTION
            "An object containing the total count of circuit switched PN blockages,
            that is, the number of times a PN link time-slot is denied."
        ::= { g3pnblockEntry 15 }


    -- the g3pkpnblock group

    g3pkpnblockTage	OBJECT-TYPE
        SYNTAX    INTEGER
        ACCESS    read-only
        STATUS    mandatory
        DESCRIPTION
            "The number of timeticks since the port network blockage data was
            last extracted from the switch by the Proxy Agent.  This object
            along with the g3pnblockintvl object allows the Network Manager
            to determine the validity of the data in the cache and to control
            when the Proxy Agent extracts the data from the switch."
        ::= { g3pkpnblock 1 }

    g3pkpnblockTintvl	OBJECT-TYPE
        SYNTAX    INTEGER
        ACCESS    read-write
        STATUS    mandatory
        DESCRIPTION
            "An object containing the interval for which the port network blockage
            data extracted from the switch is considered valid by the Proxy Agent.
            When a GET or GET-NEXT request for port network blockage objects is
            received by the agent it uses the g3pnblockage and g3pnblockintvl
            objects to determine whether it should refresh the cached pnblockTable.
            If g3pnblockstmp + g3pnblockintvl is less than the current value of
            the sysUpTime object then the agent refreshes the pnblockTable
            cache.  In either case it responds to the requests it receives
            with the data it currently has in the cache."
        ::= { g3pkpnblock 2 }

    g3pkpnblockTdelay	OBJECT-TYPE
        SYNTAX    INTEGER
        ACCESS    read-only
        STATUS    mandatory
        DESCRIPTION
            "An object containing the delay encountered in updating
            the cached data."
        ::= { g3pkpnblock 3 }

    g3pkpnblockTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3pkpnblock 4 }

    g3pkpnblockTcount	OBJECT-TYPE
        SYNTAX    Gauge
        ACCESS    read-only
        STATUS    mandatory
        DESCRIPTION
            "A Gauge object containing the number of data records in the cache."
        ::= { g3pkpnblock 5 }

    g3pkpnblockTable	OBJECT-TYPE
        SYNTAX    SEQUENCE OF G3pkpnblockEntry
        ACCESS    not-accessible
        STATUS    mandatory
        DESCRIPTION
            "A list of g3pkpnblock entries."
        ::= { g3pkpnblock 6 }

    g3pkpnblockEntry	OBJECT-TYPE
        SYNTAX    G3pkpnblockEntry
        ACCESS    not-accessible
        STATUS    mandatory
        DESCRIPTION
            "A g3pkpnblock entry containing objects of the
            g3pkpnblock information sent by the switch."
        INDEX    { g3pkpnblockPNNumber }
        ::= { g3pkpnblockTable 1 }

    G3pkpnblockEntry ::= SEQUENCE {
        g3pkpnblockPNNumber
            INTEGER,
        g3pkpnblockMeasHour
            INTEGER,
        g3pkpnblockYear
            INTEGER,
        g3pkpnblockMonth
            INTEGER,
        g3pkpnblockDay
            INTEGER,
        g3pkpnblockHour
            INTEGER,
        g3pkpnblockTdmUsage
            INTEGER,
        g3pkpnblockTdmPeg
            INTEGER,
        g3pkpnblockTdmPeak
            INTEGER,
        g3pkpnblockTdmBlockage
            INTEGER,
        g3pkpnblockTimeSlots
            INTEGER,
        g3pkpnblockPNlinkUsage
            INTEGER,
        g3pkpnblockPNlinkPeg
            INTEGER,
        g3pkpnblockPNlinkPeak
            INTEGER,
        g3pkpnblockPNlinkBlockage
            INTEGER
        }

    g3pkpnblockPNNumber	OBJECT-TYPE
        SYNTAX    INTEGER
        ACCESS    read-only
        STATUS    mandatory
        DESCRIPTION
            "An object containing the Port Network number."
        ::= { g3pkpnblockEntry 1 }

    g3pkpnblockMeasHour	OBJECT-TYPE
        SYNTAX    INTEGER
        ACCESS    read-only
        STATUS    mandatory
        DESCRIPTION
            "An object containing the Hour the measurement was taken."
        ::= { g3pkpnblockEntry 2 }

    g3pkpnblockYear	OBJECT-TYPE
        SYNTAX    INTEGER
        ACCESS    read-only
        STATUS    mandatory
        DESCRIPTION
            "An object containing the Year the command was executed."
        ::= { g3pkpnblockEntry 3 }

    g3pkpnblockMonth	OBJECT-TYPE
        SYNTAX    INTEGER
        ACCESS    read-only
        STATUS    mandatory
        DESCRIPTION
            "An object containing the Month the command was executed."
        ::= { g3pkpnblockEntry 4 }

    g3pkpnblockDay	OBJECT-TYPE
        SYNTAX    INTEGER
        ACCESS    read-only
        STATUS    mandatory
        DESCRIPTION
            "An object containing the Day the command was executed."
        ::= { g3pkpnblockEntry 5 }

    g3pkpnblockHour	OBJECT-TYPE
        SYNTAX    INTEGER
        ACCESS    read-only
        STATUS    mandatory
        DESCRIPTION
            "An object containing the Hour the command was executed."
        ::= { g3pkpnblockEntry 6 }

    g3pkpnblockTdmUsage	OBJECT-TYPE
        SYNTAX    INTEGER
        ACCESS    read-only
        STATUS    mandatory
        DESCRIPTION
            "An object containing the total TDM time-slot usage."
        ::= { g3pkpnblockEntry 7 }

    g3pkpnblockTdmPeg	OBJECT-TYPE
        SYNTAX    INTEGER
        ACCESS    read-only
        STATUS    mandatory
        DESCRIPTION
            "An object containing the total count of circuit switch TDM time-slot
            seizure attempts for the PN."
        ::= { g3pkpnblockEntry 8 }

    g3pkpnblockTdmPeak	OBJECT-TYPE
        SYNTAX    INTEGER
        ACCESS    read-only
        STATUS    mandatory
        DESCRIPTION
            "An object containing the maximum number of time-slots allocated
            at any one time."
        ::= { g3pkpnblockEntry 9 }

    g3pkpnblockTdmBlockage	OBJECT-TYPE
        SYNTAX    INTEGER
        ACCESS    read-only
        STATUS    mandatory
        DESCRIPTION
            "An object containing the total count of TDM blockages, that is, the
            total number of times a TDM time-slot request is denied for the PN."
        ::= { g3pkpnblockEntry 10 }

    g3pkpnblockTimeSlots	OBJECT-TYPE
        SYNTAX    INTEGER
        ACCESS    read-only
        STATUS    mandatory
        DESCRIPTION
            "An object containing the number of PN link time-slots available
            between port networks or between Port Networks and Switch Nodes."
        ::= { g3pkpnblockEntry 11 }

    g3pkpnblockPNlinkUsage	OBJECT-TYPE
        SYNTAX    INTEGER
        ACCESS    read-only
        STATUS    mandatory
        DESCRIPTION
            "An object containing the total circuit switch usage of the
            available PN link(s) connecting the PN to the SN or to other PNs."
        ::= { g3pkpnblockEntry 12 }

    g3pkpnblockPNlinkPeg	OBJECT-TYPE
        SYNTAX    INTEGER
        ACCESS    read-only
        STATUS    mandatory
        DESCRIPTION
            "An object containing the total count of circuit switched time-slot
            seizure attempts for the link(s)."
        ::= { g3pkpnblockEntry 13 }

    g3pkpnblockPNlinkPeak	OBJECT-TYPE
        SYNTAX    INTEGER
        ACCESS    read-only
        STATUS    mandatory
        DESCRIPTION
            "An object containing the maximum number of time slots allocated
            at any one time on the PN links."
        ::= { g3pkpnblockEntry 14 }

    g3pkpnblockPNlinkBlockage	OBJECT-TYPE
        SYNTAX    INTEGER
        ACCESS    read-only
        STATUS    mandatory
        DESCRIPTION
            "An object containing the total count of circuit switched PN blockages,
            that is, the number of times a PN link time-slot is denied."
        ::= { g3pkpnblockEntry 15 }


    -- the g3snblock group

    g3snblockTage	OBJECT-TYPE
        SYNTAX    INTEGER
        ACCESS    read-only
        STATUS    mandatory
        DESCRIPTION
            "The number of timeticks since the switch node blockage data was
            last extracted from the switch by the Proxy Agent.  This object
            along with the g3snblockintvl object allows the Network Manager
            to determine the validity of the data in the cache and to control
            when the Proxy Agent extracts the data from the switch."
        ::= { g3snblock 1 }

    g3snblockTintvl	OBJECT-TYPE
        SYNTAX    INTEGER
        ACCESS    read-write
        STATUS    mandatory
        DESCRIPTION
            "An object containing the interval for which the switch node blockage
            data extracted from the switch is considered valid by the Proxy Agent.
            When a GET or GET-NEXT request for switch node blockage objects is
            received by the agent it uses the g3snblockage and g3snblockintvl
            objects to determine whether it should refresh the cached snblockTable.
            If g3snblockstmp + g3snblockintvl is less than the current value of
            the sysUpTime object then the agent refreshes the snblockTable
            cache.  In either case it responds to the requests it receives
            with the data it currently has in the cache."
        ::= { g3snblock 2 }

    g3snblockTdelay	OBJECT-TYPE
        SYNTAX    INTEGER
        ACCESS    read-only
        STATUS    mandatory
        DESCRIPTION
            "An object containing the delay encountered in updating
            the cached data."
        ::= { g3snblock 3 }

    g3snblockTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3snblock 4 }

    g3snblockTcount	OBJECT-TYPE
        SYNTAX    Gauge
        ACCESS    read-only
        STATUS    mandatory
        DESCRIPTION
            "A Gauge object containing the number of data records in the cache."
        ::= { g3snblock 5 }

    g3snblockTable	OBJECT-TYPE
        SYNTAX    SEQUENCE OF G3snblockEntry
        ACCESS    not-accessible
        STATUS    mandatory
        DESCRIPTION
            "A list of g3snblock entries."
        ::= { g3snblock 6 }

    g3snblockEntry	OBJECT-TYPE
        SYNTAX    G3snblockEntry
        ACCESS    not-accessible
        STATUS    mandatory
        DESCRIPTION
            "A g3snblock entry containing objects of the
            g3snblock information sent by the switch."
        INDEX    { g3snblockSnPair }
        ::= { g3snblockTable 1 }

    G3snblockEntry ::= SEQUENCE {
        g3snblockSnPair
            DisplayString,
        g3snblockMeasHour
            INTEGER,
        g3snblockYear
            INTEGER,
        g3snblockMonth
            INTEGER,
        g3snblockDay
            INTEGER,
        g3snblockHour
            INTEGER,
        g3snblockTimeSlots
            INTEGER,
        g3snblockUsage
            INTEGER,
        g3snblockSnPeg
            INTEGER,
        g3snblockLinkBlockage
            INTEGER,
        g3snblockOverflow
            INTEGER
        }

    g3snblockSnPair	OBJECT-TYPE
        SYNTAX    DisplayString (SIZE (0..6))
        ACCESS    read-only
        STATUS    mandatory
        DESCRIPTION
            "An object containing the identifiers for the two SNs connected
            by the SN link being measured."
        ::= { g3snblockEntry 1 }

    g3snblockMeasHour	OBJECT-TYPE
        SYNTAX    INTEGER
        ACCESS    read-only
        STATUS    mandatory
        DESCRIPTION
            "An object containing the Hour the measurement was taken."
        ::= { g3snblockEntry 2 }

    g3snblockYear	OBJECT-TYPE
        SYNTAX    INTEGER
        ACCESS    read-only
        STATUS    mandatory
        DESCRIPTION
            "An object containing the Year the command was executed."
        ::= { g3snblockEntry 3 }

    g3snblockMonth	OBJECT-TYPE
        SYNTAX    INTEGER
        ACCESS    read-only
        STATUS    mandatory
        DESCRIPTION
            "An object containing the Month the command was executed."
        ::= { g3snblockEntry 4 }

    g3snblockDay	OBJECT-TYPE
        SYNTAX    INTEGER
        ACCESS    read-only
        STATUS    mandatory
        DESCRIPTION
            "An object containing the Day the command was executed."
        ::= { g3snblockEntry 5 }

    g3snblockHour	OBJECT-TYPE
        SYNTAX    INTEGER
        ACCESS    read-only
        STATUS    mandatory
        DESCRIPTION
            "An object containing the Hour the command was executed."
        ::= { g3snblockEntry 6 }

    g3snblockTimeSlots	OBJECT-TYPE
        SYNTAX    INTEGER
        ACCESS    read-only
        STATUS    mandatory
        DESCRIPTION
            "An object containing the number of SN link time-slots available
            between SNs."
        ::= { g3snblockEntry 7 }

    g3snblockUsage	OBJECT-TYPE
        SYNTAX    INTEGER
        ACCESS    read-only
        STATUS    mandatory
        DESCRIPTION
            "An object containing the total circuit switch usage of the SN link
            connecting the two SNs."
        ::= { g3snblockEntry 8 }

    g3snblockSnPeg	OBJECT-TYPE
        SYNTAX    INTEGER
        ACCESS    read-only
        STATUS    mandatory
        DESCRIPTION
            "An object containing the total count of circuit switched SN link
            time-slot seizure attempts between the two measured SNs."
        ::= { g3snblockEntry 9 }

    g3snblockLinkBlockage	OBJECT-TYPE
        SYNTAX    INTEGER
        ACCESS    read-only
        STATUS    mandatory
        DESCRIPTION
            "An object containing the total count of circuit switched SN link
            blockages, that is, the total number of times a call is blocked
            because no time-slots are available either in the most direct
            route or through any alternate route."
        ::= { g3snblockEntry 10 }

    g3snblockOverflow	OBJECT-TYPE
        SYNTAX    INTEGER
        ACCESS    read-only
        STATUS    mandatory
        DESCRIPTION
            "An object containing the total number of times a call had to be
            routed over an alternate route."
        ::= { g3snblockEntry 11 }


    -- the g3pksnblock group

    g3pksnblockTage	OBJECT-TYPE
        SYNTAX    INTEGER
        ACCESS    read-only
        STATUS    mandatory
        DESCRIPTION
            "The number of timeticks since the switch node blockage data was
            last extracted from the switch by the Proxy Agent.  This object
            along with the g3snblockintvl object allows the Network Manager
            to determine the validity of the data in the cache and to control
            when the Proxy Agent extracts the data from the switch."
        ::= { g3pksnblock 1 }

    g3pksnblockTintvl	OBJECT-TYPE
        SYNTAX    INTEGER
        ACCESS    read-write
        STATUS    mandatory
        DESCRIPTION
            "An object containing the interval for which the switch node blockage
            data extracted from the switch is considered valid by the Proxy Agent.
            When a GET or GET-NEXT request for switch node blockage objects is
            received by the agent it uses the g3snblockage and g3snblockintvl
            objects to determine whether it should refresh the cached snblockTable.
            If g3snblockstmp + g3snblockintvl is less than the current value of
            the sysUpTime object then the agent refreshes the snblockTable
            cache.  In either case it responds to the requests it receives
            with the data it currently has in the cache."
        ::= { g3pksnblock 2 }

    g3pksnblockTdelay	OBJECT-TYPE
        SYNTAX    INTEGER
        ACCESS    read-only
        STATUS    mandatory
        DESCRIPTION
            "An object containing the delay encountered in updating
            the cached data."
        ::= { g3pksnblock 3 }

    g3pksnblockTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3pksnblock 4 }

    g3pksnblockTcount	OBJECT-TYPE
        SYNTAX    Gauge
        ACCESS    read-only
        STATUS    mandatory
        DESCRIPTION
            "A Gauge object containing the number of data records in the cache."
        ::= { g3pksnblock 5 }

    g3pksnblockTable	OBJECT-TYPE
        SYNTAX    SEQUENCE OF G3pksnblockEntry
        ACCESS    not-accessible
        STATUS    mandatory
        DESCRIPTION
            "A list of g3pksnblock entries."
        ::= { g3pksnblock 6 }

    g3pksnblockEntry	OBJECT-TYPE
        SYNTAX    G3pksnblockEntry
        ACCESS    not-accessible
        STATUS    mandatory
        DESCRIPTION
            "A g3pksnblock entry containing objects of the
            g3pksnblock information sent by the switch."
        INDEX    { g3pksnblockSnPair }
        ::= { g3pksnblockTable 1 }

    G3pksnblockEntry ::= SEQUENCE {
        g3pksnblockSnPair
            DisplayString,
        g3pksnblockMeasHour
            INTEGER,
        g3pksnblockYear
            INTEGER,
        g3pksnblockMonth
            INTEGER,
        g3pksnblockDay
            INTEGER,
        g3pksnblockHour
            INTEGER,
        g3pksnblockTimeSlots
            INTEGER,
        g3pksnblockUsage
            INTEGER,
        g3pksnblockSnPeg
            INTEGER,
        g3pksnblockLinkBlockage
            INTEGER,
        g3pksnblockOverflow
            INTEGER
        }

    g3pksnblockSnPair	OBJECT-TYPE
        SYNTAX    DisplayString (SIZE (0..6))
        ACCESS    read-only
        STATUS    mandatory
        DESCRIPTION
            "An object containing the identifiers for the two SNs connected
            by the SN link being measured."
        ::= { g3pksnblockEntry 1 }

    g3pksnblockMeasHour	OBJECT-TYPE
        SYNTAX    INTEGER
        ACCESS    read-only
        STATUS    mandatory
        DESCRIPTION
            "An object containing the Hour the measurement was taken."
        ::= { g3pksnblockEntry 2 }

    g3pksnblockYear	OBJECT-TYPE
        SYNTAX    INTEGER
        ACCESS    read-only
        STATUS    mandatory
        DESCRIPTION
            "An object containing the Year the command was executed."
        ::= { g3pksnblockEntry 3 }

    g3pksnblockMonth	OBJECT-TYPE
        SYNTAX    INTEGER
        ACCESS    read-only
        STATUS    mandatory
        DESCRIPTION
            "An object containing the Month the command was executed."
        ::= { g3pksnblockEntry 4 }

    g3pksnblockDay	OBJECT-TYPE
        SYNTAX    INTEGER
        ACCESS    read-only
        STATUS    mandatory
        DESCRIPTION
            "An object containing the Day the command was executed."
        ::= { g3pksnblockEntry 5 }

    g3pksnblockHour	OBJECT-TYPE
        SYNTAX    INTEGER
        ACCESS    read-only
        STATUS    mandatory
        DESCRIPTION
            "An object containing the Hour the command was executed."
        ::= { g3pksnblockEntry 6 }

    g3pksnblockTimeSlots	OBJECT-TYPE
        SYNTAX    INTEGER
        ACCESS    read-only
        STATUS    mandatory
        DESCRIPTION
            "An object containing the number of SN link time-slots available
            between SNs."
        ::= { g3pksnblockEntry 7 }

    g3pksnblockUsage	OBJECT-TYPE
        SYNTAX    INTEGER
        ACCESS    read-only
        STATUS    mandatory
        DESCRIPTION
            "An object containing the total circuit switch usage of the SN link
            connecting the two SNs."
        ::= { g3pksnblockEntry 8 }

    g3pksnblockSnPeg	OBJECT-TYPE
        SYNTAX    INTEGER
        ACCESS    read-only
        STATUS    mandatory
        DESCRIPTION
            "An object containing the total count of circuit switched SN link
            time-slot seizure attempts between the two measured SNs."
        ::= { g3pksnblockEntry 9 }

    g3pksnblockLinkBlockage	OBJECT-TYPE
        SYNTAX    INTEGER
        ACCESS    read-only
        STATUS    mandatory
        DESCRIPTION
            "An object containing the total count of circuit switched SN link
            blockages, that is, the total number of times a call is blocked
            because no time-slots are available either in the most direct
            route or through any alternate route."
        ::= { g3pksnblockEntry 10 }

    g3pksnblockOverflow	OBJECT-TYPE
        SYNTAX    INTEGER
        ACCESS    read-only
        STATUS    mandatory
        DESCRIPTION
            "An object containing the total number of times a call had to be
            routed over an alternate route."
        ::= { g3pksnblockEntry 11 }


    -- the g3hunt group

    g3huntTage	OBJECT-TYPE
        SYNTAX    INTEGER
        ACCESS    read-only
        STATUS    mandatory
        DESCRIPTION
            "The number of timeticks since the hunt group data was last
            extracted from the switch by the Proxy Agent.  This object
            along with the g3huntintvl object allows the Network Manager
            to determine the validity of the data in the cache and to control
            when the Proxy Agent extracts the data from the switch."
        ::= { g3hunt 1 }

    g3huntTintvl	OBJECT-TYPE
        SYNTAX    INTEGER
        ACCESS    read-write
        STATUS    mandatory
        DESCRIPTION
            "An object containing the interval for which the hunt group
            data extracted from the switch is considered valid by the
            Proxy Agent.  When a GET or GET-NEXT request for hunt group
            objects is received by the agent it uses the g3huntage
            and g3huntintvl objects to determine whether it should refresh
            the cached huntTable.  If g3huntstmp + g3huntintvl
            is less than the current value of the sysUpTime object then the agent
            refreshes the huntTable cache.  In either case it responds to
            the requests it receives with the data it currently has in the cache."
        ::= { g3hunt 2 }

    g3huntTdelay	OBJECT-TYPE
        SYNTAX    INTEGER
        ACCESS    read-only
        STATUS    mandatory
        DESCRIPTION
            "An object containing the delay encountered in updating
            the cached data."
        ::= { g3hunt 3 }

    g3huntTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3hunt 4 }

    g3huntTcount	OBJECT-TYPE
        SYNTAX    Gauge
        ACCESS    read-only
        STATUS    mandatory
        DESCRIPTION
            "A Gauge object containing the number of data records in the cache."
        ::= { g3hunt 5 }

    g3huntTable	OBJECT-TYPE
        SYNTAX    SEQUENCE OF G3huntEntry
        ACCESS    not-accessible
        STATUS    mandatory
        DESCRIPTION
            "A list of g3hunt entries."
        ::= { g3hunt 6 }

    g3huntEntry	OBJECT-TYPE
        SYNTAX    G3huntEntry
        ACCESS    not-accessible
        STATUS    mandatory
        DESCRIPTION
            "A g3hunt entry containing objects of the
            g3hunt information sent by the switch."
        INDEX    { g3huntHuntGroup }
        ::= { g3huntTable 1 }

    G3huntEntry ::= SEQUENCE {
        g3huntHuntGroup
            INTEGER,
        g3huntMeasHour
            INTEGER,
        g3huntYear
            INTEGER,
        g3huntMonth
            INTEGER,
        g3huntDay
            INTEGER,
        g3huntHour
            INTEGER,
        g3huntGroupSize
            INTEGER,
        g3huntTotalUsage
            INTEGER,
        g3huntCallsAns
            INTEGER,
        g3huntCallsAban
            INTEGER,
        g3huntQueSiz
            INTEGER,
        g3huntCallsQue
            INTEGER,
        g3huntQueOvfl
            INTEGER,
        g3huntTimeAvail
            INTEGER,
        g3huntSpeedAns
            INTEGER
        }

    g3huntHuntGroup	OBJECT-TYPE
        SYNTAX    INTEGER
        ACCESS    read-only
        STATUS    mandatory
        DESCRIPTION
            "An object containing the hunt group number."
        ::= { g3huntEntry 1 }

    g3huntMeasHour	OBJECT-TYPE
        SYNTAX    INTEGER
        ACCESS    read-only
        STATUS    mandatory
        DESCRIPTION
            "An object containing the Hour the measurement was taken."
        ::= { g3huntEntry 2 }

    g3huntYear	OBJECT-TYPE
        SYNTAX    INTEGER
        ACCESS    read-only
        STATUS    mandatory
        DESCRIPTION
            "An object containing the Year the command was executed."
        ::= { g3huntEntry 3 }

    g3huntMonth	OBJECT-TYPE
        SYNTAX    INTEGER
        ACCESS    read-only
        STATUS    mandatory
        DESCRIPTION
            "An object containing the Month the command was executed."
        ::= { g3huntEntry 4 }

    g3huntDay	OBJECT-TYPE
        SYNTAX    INTEGER
        ACCESS    read-only
        STATUS    mandatory
        DESCRIPTION
            "An object containing the Day the command was executed."
        ::= { g3huntEntry 5 }

    g3huntHour	OBJECT-TYPE
        SYNTAX    INTEGER
        ACCESS    read-only
        STATUS    mandatory
        DESCRIPTION
            "An object containing the Hour the command was executed."
        ::= { g3huntEntry 6 }

    g3huntGroupSize	OBJECT-TYPE
        SYNTAX    INTEGER
        ACCESS    read-only
        STATUS    mandatory
        DESCRIPTION
            "An object containing the total number of members in the trunk group."
        ::= { g3huntEntry 7 }

    g3huntTotalUsage	OBJECT-TYPE
        SYNTAX    INTEGER
        ACCESS    read-only
        STATUS    mandatory
        DESCRIPTION
            "An object containing the sum of all times that the members of the
            hunt group are busy on hunt group calls (in CCS)."
        ::= { g3huntEntry 8 }

    g3huntCallsAns	OBJECT-TYPE
        SYNTAX    INTEGER
        ACCESS    read-only
        STATUS    mandatory
        DESCRIPTION
            "An object containing the total number of calls that are answered
            by the hunt group."
        ::= { g3huntEntry 9 }

    g3huntCallsAban	OBJECT-TYPE
        SYNTAX    INTEGER
        ACCESS    read-only
        STATUS    mandatory
        DESCRIPTION
            "An object containing the total number of calls that attempt to reach
            the hunt group but abandon the attempt before being answered."
        ::= { g3huntEntry 10 }

    g3huntQueSiz	OBJECT-TYPE
        SYNTAX    INTEGER
        ACCESS    read-only
        STATUS    mandatory
        DESCRIPTION
            "An object containing the length of the queue assigned to the hunt
            group during administration."
        ::= { g3huntEntry 11 }

    g3huntCallsQue	OBJECT-TYPE
        SYNTAX    INTEGER
        ACCESS    read-only
        STATUS    mandatory
        DESCRIPTION
            "An object containing the total number of calls that arrive to find
            all members of the hunt group busy and are placed in the queue."
        ::= { g3huntEntry 12 }

    g3huntQueOvfl	OBJECT-TYPE
        SYNTAX    INTEGER
        ACCESS    read-only
        STATUS    mandatory
        DESCRIPTION
            "An object containing the number of calls that arrive when all
            slots in the hunt group queue are occupied."
        ::= { g3huntEntry 13 }

    g3huntTimeAvail	OBJECT-TYPE
        SYNTAX    INTEGER
        ACCESS    read-only
        STATUS    mandatory
        DESCRIPTION
            "An object containing the total time that the hunt group extensions are
            not in use but are available to receive hunt group calls (in CCS)."
        ::= { g3huntEntry 14 }

    g3huntSpeedAns	OBJECT-TYPE
        SYNTAX    INTEGER
        ACCESS    read-only
        STATUS    mandatory
        DESCRIPTION
            "An object containing the average time interval from when the call 
            first enters the hunt group or hunt group queue until the call is
            answered by a hunt group member (in seconds)."
        ::= { g3huntEntry 15 }


    -- the g3pkhunt group

    g3pkhuntTage	OBJECT-TYPE
        SYNTAX    INTEGER
        ACCESS    read-only
        STATUS    mandatory
        DESCRIPTION
            "The number of timeticks since the peak hunt group data was last
            extracted from the switch by the Proxy Agent.  This object
            along with the g3pkhuntintvl object allows the Network Manager
            to determine the validity of the data in the cache and to control
            when the Proxy Agent extracts the data from the switch."
        ::= { g3pkhunt 1 }

    g3pkhuntTintvl	OBJECT-TYPE
        SYNTAX    INTEGER
        ACCESS    read-write
        STATUS    mandatory
        DESCRIPTION
            "An object containing the interval for which the peak hunt group
            data extracted from the switch is considered valid by the
            Proxy Agent.  When a GET or GET-NEXT request for peak hunt group
            objects is received by the agent it uses the g3pkhuntage
            and g3pkhuntintvl objects to determine whether it should refresh
            the cached pkhuntTable.  If g3pkhuntstmp + g3pkhuntintvl
            is less than the current value of the sysUpTime object then the agent
            refreshes the pkhuntTable cache.  In either case it responds to
            the requests it receives with the data it currently has in the cache."
        ::= { g3pkhunt 2 }

    g3pkhuntTdelay	OBJECT-TYPE
        SYNTAX    INTEGER
        ACCESS    read-only
        STATUS    mandatory
        DESCRIPTION
            "An object containing the delay encountered in updating
            the cached data."
        ::= { g3pkhunt 3 }

    g3pkhuntTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3pkhunt 4 }

    g3pkhuntTcount	OBJECT-TYPE
        SYNTAX    Gauge
        ACCESS    read-only
        STATUS    mandatory
        DESCRIPTION
            "A Gauge object containing the number of data records in the cache."
        ::= { g3pkhunt 5 }

    g3pkhuntTable	OBJECT-TYPE
        SYNTAX    SEQUENCE OF G3pkhuntEntry
        ACCESS    not-accessible
        STATUS    mandatory
        DESCRIPTION
            "A list of g3pkhunt entries."
        ::= { g3pkhunt 6 }

    g3pkhuntEntry	OBJECT-TYPE
        SYNTAX    G3pkhuntEntry
        ACCESS    not-accessible
        STATUS    mandatory
        DESCRIPTION
            "A g3pkhunt entry containing objects of the
            g3pkhunt information sent by the switch."
        INDEX    { g3pkhuntHuntGroup }
        ::= { g3pkhuntTable 1 }

    G3pkhuntEntry ::= SEQUENCE {
        g3pkhuntHuntGroup
            INTEGER,
        g3pkhuntMeasHour
            INTEGER,
        g3pkhuntYear
            INTEGER,
        g3pkhuntMonth
            INTEGER,
        g3pkhuntDay
            INTEGER,
        g3pkhuntHour
            INTEGER,
        g3pkhuntGroupSize
            INTEGER,
        g3pkhuntTotalUsage
            INTEGER,
        g3pkhuntCallsAns
            INTEGER,
        g3pkhuntCallsAban
            INTEGER,
        g3pkhuntQueSiz
            INTEGER,
        g3pkhuntCallsQue
            INTEGER,
        g3pkhuntQueOvfl
            INTEGER,
        g3pkhuntTimeAvail
            INTEGER,
        g3pkhuntSpeedAns
            INTEGER
        }

    g3pkhuntHuntGroup	OBJECT-TYPE
        SYNTAX    INTEGER
        ACCESS    read-only
        STATUS    mandatory
        DESCRIPTION
            "An object containing the hunt group number."
        ::= { g3pkhuntEntry 1 }

    g3pkhuntMeasHour	OBJECT-TYPE
        SYNTAX    INTEGER
        ACCESS    read-only
        STATUS    mandatory
        DESCRIPTION
            "An object containing the Hour the measurement was taken."
        ::= { g3pkhuntEntry 2 }

    g3pkhuntYear	OBJECT-TYPE
        SYNTAX    INTEGER
        ACCESS    read-only
        STATUS    mandatory
        DESCRIPTION
            "An object containing the Year the command was executed."
        ::= { g3pkhuntEntry 3 }

    g3pkhuntMonth	OBJECT-TYPE
        SYNTAX    INTEGER
        ACCESS    read-only
        STATUS    mandatory
        DESCRIPTION
            "An object containing the Month the command was executed."
        ::= { g3pkhuntEntry 4 }

    g3pkhuntDay	OBJECT-TYPE
        SYNTAX    INTEGER
        ACCESS    read-only
        STATUS    mandatory
        DESCRIPTION
            "An object containing the Day the command was executed."
        ::= { g3pkhuntEntry 5 }

    g3pkhuntHour	OBJECT-TYPE
        SYNTAX    INTEGER
        ACCESS    read-only
        STATUS    mandatory
        DESCRIPTION
            "An object containing the Hour the command was executed."
        ::= { g3pkhuntEntry 6 }

    g3pkhuntGroupSize	OBJECT-TYPE
        SYNTAX    INTEGER
        ACCESS    read-only
        STATUS    mandatory
        DESCRIPTION
            "An object containing the total number of members in the trunk group."
        ::= { g3pkhuntEntry 7 }

    g3pkhuntTotalUsage	OBJECT-TYPE
        SYNTAX    INTEGER
        ACCESS    read-only
        STATUS    mandatory
        DESCRIPTION
            "An object containing the sum of all times that the members of the
            hunt group are busy on hunt group calls (in CCS)."
        ::= { g3pkhuntEntry 8 }

    g3pkhuntCallsAns	OBJECT-TYPE
        SYNTAX    INTEGER
        ACCESS    read-only
        STATUS    mandatory
        DESCRIPTION
            "An object containing the total number of calls that are answered
            by the hunt group."
        ::= { g3pkhuntEntry 9 }

    g3pkhuntCallsAban	OBJECT-TYPE
        SYNTAX    INTEGER
        ACCESS    read-only
        STATUS    mandatory
        DESCRIPTION
            "An object containing the total number of calls that attempt to reach
            the hunt group but abandon the attempt before being answered."
        ::= { g3pkhuntEntry 10 }

    g3pkhuntQueSiz	OBJECT-TYPE
        SYNTAX    INTEGER
        ACCESS    read-only
        STATUS    mandatory
        DESCRIPTION
            "An object containing the length of the queue assigned to the hunt
            group during administration."
        ::= { g3pkhuntEntry 11 }

    g3pkhuntCallsQue	OBJECT-TYPE
        SYNTAX    INTEGER
        ACCESS    read-only
        STATUS    mandatory
        DESCRIPTION
            "An object containing the total number of calls that arrive to find
            all members of the hunt group busy and are placed in the queue."
        ::= { g3pkhuntEntry 12 }

    g3pkhuntQueOvfl	OBJECT-TYPE
        SYNTAX    INTEGER
        ACCESS    read-only
        STATUS    mandatory
        DESCRIPTION
            "An object containing the number of calls that arrive when all
            slots in the hunt group queue are occupied."
        ::= { g3pkhuntEntry 13 }

    g3pkhuntTimeAvail	OBJECT-TYPE
        SYNTAX    INTEGER
        ACCESS    read-only
        STATUS    mandatory
        DESCRIPTION
            "An object containing the total time that the hunt group extensions are
            not in use but are available to receive hunt group calls (in CCS)."
        ::= { g3pkhuntEntry 14 }

    g3pkhuntSpeedAns	OBJECT-TYPE
        SYNTAX    INTEGER
        ACCESS    read-only
        STATUS    mandatory
        DESCRIPTION
            "An object containing the average time interval from when the call 
            first enters the hunt group or hunt group queue until the call is
            answered by a hunt group member (in seconds)."
        ::= { g3pkhuntEntry 15 }


    -- the g3huntlist group

    g3huntlistTage	OBJECT-TYPE
        SYNTAX    INTEGER
        ACCESS    read-only
        STATUS    mandatory
        DESCRIPTION
            "The number of timeticks since the hunt group list data was last
            extracted from the switch by the Proxy Agent.  This object
            along with the g3huntlistintvl object allows the Network Manager
            to determine the validity of the data in the cache and to control
            when the Proxy Agent extracts the data from the switch."
        ::= { g3huntlist 1 }

    g3huntlistTintvl	OBJECT-TYPE
        SYNTAX    INTEGER
        ACCESS    read-write
        STATUS    mandatory
        DESCRIPTION
            "An object containing the interval for which the hunt group list
            data extracted from the switch is considered valid by the
            Proxy Agent.  When a GET or GET-NEXT request for hunt group list
            objects is received by the agent it uses the g3huntlistage
            and g3huntlistintvl objects to determine whether it should refresh
            the cached huntlistTable.  If g3huntliststmp + g3huntlistintvl
            is less than the current value of the sysUpTime object then the agent
            refreshes the huntlistTable cache.  In either case it responds to
            the requests it receives with the data it currently has in the cache."
        ::= { g3huntlist 2 }

    g3huntlistTdelay	OBJECT-TYPE
        SYNTAX    INTEGER
        ACCESS    read-only
        STATUS    mandatory
        DESCRIPTION
            "An object containing the delay encountered in updating
            the cached data."
        ::= { g3huntlist 3 }

    g3huntlistTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3huntlist 4 }

    g3huntlistTcount	OBJECT-TYPE
        SYNTAX    Gauge
        ACCESS    read-only
        STATUS    mandatory
        DESCRIPTION
            "A Gauge object containing the number of data records in the cache."
        ::= { g3huntlist 5 }

    g3huntlistTable	OBJECT-TYPE
        SYNTAX    SEQUENCE OF G3huntlistEntry
        ACCESS    not-accessible
        STATUS    mandatory
        DESCRIPTION
            "A list of g3huntlist entries."
        ::= { g3huntlist 6 }

    g3huntlistEntry	OBJECT-TYPE
        SYNTAX    G3huntlistEntry
        ACCESS    not-accessible
        STATUS    mandatory
        DESCRIPTION
            "A g3huntlist entry containing objects of the
            g3huntlist information sent by the switch."
        INDEX    { g3huntlistHGNumber }
        ::= { g3huntlistTable 1 }

    G3huntlistEntry ::= SEQUENCE {
        g3huntlistHGNumber
            INTEGER,
        g3huntlistName
            DisplayString,
        g3huntlistExtension
            DisplayString,
        g3huntlistType
            DisplayString
        }

    g3huntlistHGNumber	OBJECT-TYPE
        SYNTAX    INTEGER
        ACCESS    read-only
        STATUS    mandatory
        DESCRIPTION
            "An object containing the number of the hunt group."
        ::= { g3huntlistEntry 1 }

    g3huntlistName	OBJECT-TYPE
        SYNTAX    DisplayString (SIZE (0..27))
        ACCESS    read-only
        STATUS    mandatory
        DESCRIPTION
            "A DisplayString Object containing the name of the hunt group."
        ::= { g3huntlistEntry 2 }

    g3huntlistExtension	OBJECT-TYPE
        SYNTAX    DisplayString (SIZE (0..15))
        ACCESS    read-only
        STATUS    mandatory
        DESCRIPTION
            "An object containing the extension of the hunt group."
        ::= { g3huntlistEntry 3 }

    g3huntlistType	OBJECT-TYPE
        SYNTAX    DisplayString (SIZE (0..7))
        ACCESS    read-only
        STATUS    mandatory
        DESCRIPTION
            "A DisplayString Object containing the type of hunt group."
        ::= { g3huntlistEntry 4 }


    -- the g3tonerec group

    g3tonerecTage	OBJECT-TYPE
        SYNTAX    INTEGER
        ACCESS    read-only
        STATUS    mandatory
        DESCRIPTION
            "The number of timeticks since the tone receiver data was last
            extracted from the switch by the Proxy Agent.  This object
            along with the g3tonerecintvl object allows the Network Manager
            to determine the validity of the data in the cache and to control
            when the Proxy Agent extracts the data from the switch."
        ::= { g3tonerec 1 }

    g3tonerecTintvl	OBJECT-TYPE
        SYNTAX    INTEGER
        ACCESS    read-write
        STATUS    mandatory
        DESCRIPTION
            "An object containing the interval for which the tone receiver
            data extracted from the switch is considered valid by the
            Proxy Agent.  When a GET or GET-NEXT request for tone receiver
            objects is received by the agent it uses the g3tonerecage
            and g3tonerecintvl objects to determine whether it should refresh
            the cached tonerecTable.  If g3tonerecstmp + g3tonerecintvl
            is less than the current value of the sysUpTime object then the agent
            refreshes the tonerecTable cache.  In either case it responds to
            the requests it receives with the data it currently has in the cache."
        ::= { g3tonerec 2 }

    g3tonerecTdelay	OBJECT-TYPE
        SYNTAX    INTEGER
        ACCESS    read-only
        STATUS    mandatory
        DESCRIPTION
            "An object containing the delay encountered in updating
            the cached data."
        ::= { g3tonerec 3 }

    g3tonerecTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3tonerec 4 }

    g3tonerecTcount	OBJECT-TYPE
        SYNTAX    Gauge
        ACCESS    read-only
        STATUS    mandatory
        DESCRIPTION
            "A Gauge object containing the number of data records in the cache."
        ::= { g3tonerec 5 }

    g3tonerecTable	OBJECT-TYPE
        SYNTAX    SEQUENCE OF G3tonerecEntry
        ACCESS    not-accessible
        STATUS    mandatory
        DESCRIPTION
            "A list of g3tonerec entries."
        ::= { g3tonerec 6 }

    g3tonerecEntry	OBJECT-TYPE
        SYNTAX    G3tonerecEntry
        ACCESS    not-accessible
        STATUS    mandatory
        DESCRIPTION
            "A g3tonerec entry containing objects of the
            g3tonerec information sent by the switch."
        INDEX    { g3tonerecPNNumber }
        ::= { g3tonerecTable 1 }

    G3tonerecEntry ::= SEQUENCE {
        g3tonerecPNNumber
            INTEGER,
        g3tonerecMeasHour
            INTEGER,
        g3tonerecYear
            INTEGER,
        g3tonerecMonth
            INTEGER,
        g3tonerecDay
            INTEGER,
        g3tonerecHour
            INTEGER,
        g3tonerecDTMFPnReq
            INTEGER,
        g3tonerecDTMFPnAlloc
            INTEGER,
        g3tonerecDTMFPkAlloc
            INTEGER,
        g3tonerecDTMFTotOffPN
            INTEGER,
        g3tonerecDTMFPkOffPN
            INTEGER,
        g3tonerecGPTDPnReq
            INTEGER,
        g3tonerecGPTDPnAlloc
            INTEGER,
        g3tonerecGPTDPkAlloc
            INTEGER,
        g3tonerecGPTDTotOffPN
            INTEGER,
        g3tonerecGPTDPkOffPN
            INTEGER,
        g3tonerecCCTTRPnReq
            INTEGER,
        g3tonerecCCTTRPnAlloc
            INTEGER,
        g3tonerecCCTTRPkAlloc
            INTEGER,
        g3tonerecCCTTRTotOffPN
            INTEGER,
        g3tonerecCCTTRPkOffPN
            INTEGER,
        g3tonerecCCCPTRPnReq
            INTEGER,
        g3tonerecCCCPTRPnAlloc
            INTEGER,
        g3tonerecCCCPTRPkAlloc
            INTEGER,
        g3tonerecCCCPTRTotOffPN
            INTEGER,
        g3tonerecCCCPTRPkOffPN
            INTEGER,
        g3tonerecCCMFCRPnReq
            INTEGER,
        g3tonerecCCMFCRPnAlloc
            INTEGER,
        g3tonerecCCMFCRPkAlloc
            INTEGER,
        g3tonerecCCMFCRTotOffPN
            INTEGER,
        g3tonerecCCMFCRPkOffPN
            INTEGER
        }

    g3tonerecPNNumber	OBJECT-TYPE
        SYNTAX    INTEGER
        ACCESS    read-only
        STATUS    mandatory
        DESCRIPTION
            "An object containing the Port Network number in which the
            tone receiver is located."
        ::= { g3tonerecEntry 1 }

    g3tonerecMeasHour	OBJECT-TYPE
        SYNTAX    INTEGER
        ACCESS    read-only
        STATUS    mandatory
        DESCRIPTION
            "An object containing the Hour the measurement was taken."
        ::= { g3tonerecEntry 2 }

    g3tonerecYear	OBJECT-TYPE
        SYNTAX    INTEGER
        ACCESS    read-only
        STATUS    mandatory
        DESCRIPTION
            "An object containing the Year the command was executed."
        ::= { g3tonerecEntry 3 }

    g3tonerecMonth	OBJECT-TYPE
        SYNTAX    INTEGER
        ACCESS    read-only
        STATUS    mandatory
        DESCRIPTION
            "An object containing the Month the command was executed."
        ::= { g3tonerecEntry 4 }

    g3tonerecDay	OBJECT-TYPE
        SYNTAX    INTEGER
        ACCESS    read-only
        STATUS    mandatory
        DESCRIPTION
            "An object containing the Day the command was executed."
        ::= { g3tonerecEntry 5 }

    g3tonerecHour	OBJECT-TYPE
        SYNTAX    INTEGER
        ACCESS    read-only
        STATUS    mandatory
        DESCRIPTION
            "An object containing the Hour the command was executed."
        ::= { g3tonerecEntry 6 }

    g3tonerecDTMFPnReq	OBJECT-TYPE
        SYNTAX    INTEGER
        ACCESS    read-only
        STATUS    mandatory
        DESCRIPTION
            "An object containing the number of DTMF requests within the PN."
        ::= { g3tonerecEntry 7 }

    g3tonerecDTMFPnAlloc	OBJECT-TYPE
        SYNTAX    INTEGER
        ACCESS    read-only
        STATUS    mandatory
        DESCRIPTION
            "An object containing the total number of DTMF receivers located
            in the listed PN that were allocated during the last hour."
        ::= { g3tonerecEntry 8 }

    g3tonerecDTMFPkAlloc	OBJECT-TYPE
        SYNTAX    INTEGER
        ACCESS    read-only
        STATUS    mandatory
        DESCRIPTION
            "An object containing the peak number of DTMF receivers located
            in the listed PN that were in use simulatneously."
        ::= { g3tonerecEntry 9 }

    g3tonerecDTMFTotOffPN	OBJECT-TYPE
        SYNTAX    INTEGER
        ACCESS    read-only
        STATUS    mandatory
        DESCRIPTION
            "An object containing the total number of DTMF receivers allocated
            of a different PN for requests originated on this PN."
        ::= { g3tonerecEntry 10 }

    g3tonerecDTMFPkOffPN	OBJECT-TYPE
        SYNTAX    INTEGER
        ACCESS    read-only
        STATUS    mandatory
        DESCRIPTION
            "An object containing the peak number of DTMF receivers simultaneously
            allocated on a different PN for requests originated on this PN."
        ::= { g3tonerecEntry 11 }

    g3tonerecGPTDPnReq	OBJECT-TYPE
        SYNTAX    INTEGER
        ACCESS    read-only
        STATUS    mandatory
        DESCRIPTION
            "An object containing the number of GPTD requests within the PN."
        ::= { g3tonerecEntry 12 }

    g3tonerecGPTDPnAlloc	OBJECT-TYPE
        SYNTAX    INTEGER
        ACCESS    read-only
        STATUS    mandatory
        DESCRIPTION
            "An object containing the total number of GPTD receivers located
            in the listed PN that were allocated during the last hour."
        ::= { g3tonerecEntry 13 }

    g3tonerecGPTDPkAlloc	OBJECT-TYPE
        SYNTAX    INTEGER
        ACCESS    read-only
        STATUS    mandatory
        DESCRIPTION
            "An object containing the peak number of GPTD receivers located
            in the listed PN that were in use simulatneously."
        ::= { g3tonerecEntry 14 }

    g3tonerecGPTDTotOffPN	OBJECT-TYPE
        SYNTAX    INTEGER
        ACCESS    read-only
        STATUS    mandatory
        DESCRIPTION
            "An object containing the total number of GPTD receivers allocated
            of a different PN for requests originated on this PN."
        ::= { g3tonerecEntry 15 }

    g3tonerecGPTDPkOffPN	OBJECT-TYPE
        SYNTAX    INTEGER
        ACCESS    read-only
        STATUS    mandatory
        DESCRIPTION
            "An object containing the peak number of GPTD receivers simultaneously
            allocated on a different PN for requests originated on this PN."
        ::= { g3tonerecEntry 16 }

    g3tonerecCCTTRPnReq	OBJECT-TYPE
        SYNTAX    INTEGER
        ACCESS    read-only
        STATUS    mandatory
        DESCRIPTION
            "An object containing the number of CC-TTR requests within the PN."
        ::= { g3tonerecEntry 17 }

    g3tonerecCCTTRPnAlloc	OBJECT-TYPE
        SYNTAX    INTEGER
        ACCESS    read-only
        STATUS    mandatory
        DESCRIPTION
            "An object containing the total number of CC-TTR receivers located
            in the listed PN that were allocated during the last hour."
        ::= { g3tonerecEntry 18 }

    g3tonerecCCTTRPkAlloc	OBJECT-TYPE
        SYNTAX    INTEGER
        ACCESS    read-only
        STATUS    mandatory
        DESCRIPTION
            "An object containing the peak number of CC-TTR receivers located
            in the listed PN that were in use simulatneously."
        ::= { g3tonerecEntry 19 }

    g3tonerecCCTTRTotOffPN	OBJECT-TYPE
        SYNTAX    INTEGER
        ACCESS    read-only
        STATUS    mandatory
        DESCRIPTION
            "An object containing the total number of CC-TTR receivers allocated
            of a different PN for requests originated on this PN."
        ::= { g3tonerecEntry 20 }

    g3tonerecCCTTRPkOffPN	OBJECT-TYPE
        SYNTAX    INTEGER
        ACCESS    read-only
        STATUS    mandatory
        DESCRIPTION
            "An object containing the peak number of CC-TTR receivers simultaneously
            allocated on a different PN for requests originated on this PN."
        ::= { g3tonerecEntry 21 }

    g3tonerecCCCPTRPnReq	OBJECT-TYPE
        SYNTAX    INTEGER
        ACCESS    read-only
        STATUS    mandatory
        DESCRIPTION
            "An object containing the number of CC-CPTR requests within the PN."
        ::= { g3tonerecEntry 22 }

    g3tonerecCCCPTRPnAlloc	OBJECT-TYPE
        SYNTAX    INTEGER
        ACCESS    read-only
        STATUS    mandatory
        DESCRIPTION
            "An object containing the total number of CC-CPTR receivers located
            in the listed PN that were allocated during the last hour."
        ::= { g3tonerecEntry 23 }

    g3tonerecCCCPTRPkAlloc	OBJECT-TYPE
        SYNTAX    INTEGER
        ACCESS    read-only
        STATUS    mandatory
        DESCRIPTION
            "An object containing the peak number of CC-CPTR receivers located
            in the listed PN that were in use simulatneously."
        ::= { g3tonerecEntry 24 }

    g3tonerecCCCPTRTotOffPN	OBJECT-TYPE
        SYNTAX    INTEGER
        ACCESS    read-only
        STATUS    mandatory
        DESCRIPTION
            "An object containing the total number of CC-CPTR receivers allocated
            of a different PN for requests originated on this PN."
        ::= { g3tonerecEntry 25 }

    g3tonerecCCCPTRPkOffPN	OBJECT-TYPE
        SYNTAX    INTEGER
        ACCESS    read-only
        STATUS    mandatory
        DESCRIPTION
            "An object containing the peak number of CC-CPTR receivers simultaneously
            allocated on a different PN for requests originated on this PN."
        ::= { g3tonerecEntry 26 }

    g3tonerecCCMFCRPnReq	OBJECT-TYPE
        SYNTAX    INTEGER
        ACCESS    read-only
        STATUS    mandatory
        DESCRIPTION
            "An object containing the number of CC-MFCR requests within the PN."
        ::= { g3tonerecEntry 27 }

    g3tonerecCCMFCRPnAlloc	OBJECT-TYPE
        SYNTAX    INTEGER
        ACCESS    read-only
        STATUS    mandatory
        DESCRIPTION
            "An object containing the total number of CC-MFCR receivers located
            in the listed PN that were allocated during the last hour."
        ::= { g3tonerecEntry 28 }

    g3tonerecCCMFCRPkAlloc	OBJECT-TYPE
        SYNTAX    INTEGER
        ACCESS    read-only
        STATUS    mandatory
        DESCRIPTION
            "An object containing the peak number of CC-MFCR receivers located
            in the listed PN that were in use simulatneously."
        ::= { g3tonerecEntry 29 }

    g3tonerecCCMFCRTotOffPN	OBJECT-TYPE
        SYNTAX    INTEGER
        ACCESS    read-only
        STATUS    mandatory
        DESCRIPTION
            "An object containing the total number of CC-MFCR receivers allocated
            of a different PN for requests originated on this PN."
        ::= { g3tonerecEntry 30 }

    g3tonerecCCMFCRPkOffPN	OBJECT-TYPE
        SYNTAX    INTEGER
        ACCESS    read-only
        STATUS    mandatory
        DESCRIPTION
            "An object containing the peak number of CC-MFCR receivers simultaneously
            allocated on a different PN for requests originated on this PN."
        ::= { g3tonerecEntry 31 }


    -- the g3pktonerec group

    g3pktonerecTage	OBJECT-TYPE
        SYNTAX    INTEGER
        ACCESS    read-only
        STATUS    mandatory
        DESCRIPTION
            "The number of timeticks since the tone receiver data was last
            extracted from the switch by the Proxy Agent.  This object
            along with the g3tonerecintvl object allows the Network Manager
            to determine the validity of the data in the cache and to control
            when the Proxy Agent extracts the data from the switch."
        ::= { g3pktonerec 1 }

    g3pktonerecTintvl	OBJECT-TYPE
        SYNTAX    INTEGER
        ACCESS    read-write
        STATUS    mandatory
        DESCRIPTION
            "An object containing the interval for which the tone receiver
            data extracted from the switch is considered valid by the
            Proxy Agent.  When a GET or GET-NEXT request for tone receiver
            objects is received by the agent it uses the g3tonerecage
            and g3tonerecintvl objects to determine whether it should refresh
            the cached tonerecTable.  If g3tonerecstmp + g3tonerecintvl
            is less than the current value of the sysUpTime object then the agent
            refreshes the tonerecTable cache.  In either case it responds to
            the requests it receives with the data it currently has in the cache."
        ::= { g3pktonerec 2 }

    g3pktonerecTdelay	OBJECT-TYPE
        SYNTAX    INTEGER
        ACCESS    read-only
        STATUS    mandatory
        DESCRIPTION
            "An object containing the delay encountered in updating
            the cached data."
        ::= { g3pktonerec 3 }

    g3pktonerecTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3pktonerec 4 }

    g3pktonerecTcount	OBJECT-TYPE
        SYNTAX    Gauge
        ACCESS    read-only
        STATUS    mandatory
        DESCRIPTION
            "A Gauge object containing the number of data records in the cache."
        ::= { g3pktonerec 5 }

    g3pktonerecTable	OBJECT-TYPE
        SYNTAX    SEQUENCE OF G3pktonerecEntry
        ACCESS    not-accessible
        STATUS    mandatory
        DESCRIPTION
            "A list of g3pktonerec entries."
        ::= { g3pktonerec 6 }

    g3pktonerecEntry	OBJECT-TYPE
        SYNTAX    G3pktonerecEntry
        ACCESS    not-accessible
        STATUS    mandatory
        DESCRIPTION
            "A g3pktonerec entry containing objects of the
            g3pktonerec information sent by the switch."
        INDEX    { g3pktonerecPNNumber }
        ::= { g3pktonerecTable 1 }

    G3pktonerecEntry ::= SEQUENCE {
        g3pktonerecPNNumber
            INTEGER,
        g3pktonerecMeasHour
            INTEGER,
        g3pktonerecYear
            INTEGER,
        g3pktonerecMonth
            INTEGER,
        g3pktonerecDay
            INTEGER,
        g3pktonerecHour
            INTEGER,
        g3pktonerecDTMFPnReq
            INTEGER,
        g3pktonerecDTMFPnAlloc
            INTEGER,
        g3pktonerecDTMFPkAlloc
            INTEGER,
        g3pktonerecDTMFTotOffPN
            INTEGER,
        g3pktonerecDTMFPkOffPN
            INTEGER,
        g3pktonerecGPTDPnReq
            INTEGER,
        g3pktonerecGPTDPnAlloc
            INTEGER,
        g3pktonerecGPTDPkAlloc
            INTEGER,
        g3pktonerecGPTDTotOffPN
            INTEGER,
        g3pktonerecGPTDPkOffPN
            INTEGER,
        g3pktonerecCCTTRPnReq
            INTEGER,
        g3pktonerecCCTTRPnAlloc
            INTEGER,
        g3pktonerecCCTTRPkAlloc
            INTEGER,
        g3pktonerecCCTTRTotOffPN
            INTEGER,
        g3pktonerecCCTTRPkOffPN
            INTEGER,
        g3pktonerecCCCPTRPnReq
            INTEGER,
        g3pktonerecCCCPTRPnAlloc
            INTEGER,
        g3pktonerecCCCPTRPkAlloc
            INTEGER,
        g3pktonerecCCCPTRTotOffPN
            INTEGER,
        g3pktonerecCCCPTRPkOffPN
            INTEGER,
        g3pktonerecCCMFCRPnReq
            INTEGER,
        g3pktonerecCCMFCRPnAlloc
            INTEGER,
        g3pktonerecCCMFCRPkAlloc
            INTEGER,
        g3pktonerecCCMFCRTotOffPN
            INTEGER,
        g3pktonerecCCMFCRPkOffPN
            INTEGER
        }

    g3pktonerecPNNumber	OBJECT-TYPE
        SYNTAX    INTEGER
        ACCESS    read-only
        STATUS    mandatory
        DESCRIPTION
            "An object containing the Port Network number in which the
            tone receiver is located."
        ::= { g3pktonerecEntry 1 }

    g3pktonerecMeasHour	OBJECT-TYPE
        SYNTAX    INTEGER
        ACCESS    read-only
        STATUS    mandatory
        DESCRIPTION
            "An object containing the Hour the measurement was taken."
        ::= { g3pktonerecEntry 2 }

    g3pktonerecYear	OBJECT-TYPE
        SYNTAX    INTEGER
        ACCESS    read-only
        STATUS    mandatory
        DESCRIPTION
            "An object containing the Year the command was executed."
        ::= { g3pktonerecEntry 3 }

    g3pktonerecMonth	OBJECT-TYPE
        SYNTAX    INTEGER
        ACCESS    read-only
        STATUS    mandatory
        DESCRIPTION
            "An object containing the Month the command was executed."
        ::= { g3pktonerecEntry 4 }

    g3pktonerecDay	OBJECT-TYPE
        SYNTAX    INTEGER
        ACCESS    read-only
        STATUS    mandatory
        DESCRIPTION
            "An object containing the Day the command was executed."
        ::= { g3pktonerecEntry 5 }

    g3pktonerecHour	OBJECT-TYPE
        SYNTAX    INTEGER
        ACCESS    read-only
        STATUS    mandatory
        DESCRIPTION
            "An object containing the Hour the command was executed."
        ::= { g3pktonerecEntry 6 }

    g3pktonerecDTMFPnReq	OBJECT-TYPE
        SYNTAX    INTEGER
        ACCESS    read-only
        STATUS    mandatory
        DESCRIPTION
            "An object containing the number of DTMF requests within the PN."
        ::= { g3pktonerecEntry 7 }

    g3pktonerecDTMFPnAlloc	OBJECT-TYPE
        SYNTAX    INTEGER
        ACCESS    read-only
        STATUS    mandatory
        DESCRIPTION
            "An object containing the total number of DTMF receivers located
            in the listed PN that were allocated during the last hour."
        ::= { g3pktonerecEntry 8 }

    g3pktonerecDTMFPkAlloc	OBJECT-TYPE
        SYNTAX    INTEGER
        ACCESS    read-only
        STATUS    mandatory
        DESCRIPTION
            "An object containing the peak number of DTMF receivers located
            in the listed PN that were in use simulatneously."
        ::= { g3pktonerecEntry 9 }

    g3pktonerecDTMFTotOffPN	OBJECT-TYPE
        SYNTAX    INTEGER
        ACCESS    read-only
        STATUS    mandatory
        DESCRIPTION
            "An object containing the total number of DTMF receivers allocated
            of a different PN for requests originated on this PN."
        ::= { g3pktonerecEntry 10 }

    g3pktonerecDTMFPkOffPN	OBJECT-TYPE
        SYNTAX    INTEGER
        ACCESS    read-only
        STATUS    mandatory
        DESCRIPTION
            "An object containing the peak number of DTMF receivers simultaneously
            allocated on a different PN for requests originated on this PN."
        ::= { g3pktonerecEntry 11 }

    g3pktonerecGPTDPnReq	OBJECT-TYPE
        SYNTAX    INTEGER
        ACCESS    read-only
        STATUS    mandatory
        DESCRIPTION
            "An object containing the number of GPTD requests within the PN."
        ::= { g3pktonerecEntry 12 }

    g3pktonerecGPTDPnAlloc	OBJECT-TYPE
        SYNTAX    INTEGER
        ACCESS    read-only
        STATUS    mandatory
        DESCRIPTION
            "An object containing the total number of GPTD receivers located
            in the listed PN that were allocated during the last hour."
        ::= { g3pktonerecEntry 13 }

    g3pktonerecGPTDPkAlloc	OBJECT-TYPE
        SYNTAX    INTEGER
        ACCESS    read-only
        STATUS    mandatory
        DESCRIPTION
            "An object containing the peak number of GPTD receivers located
            in the listed PN that were in use simulatneously."
        ::= { g3pktonerecEntry 14 }

    g3pktonerecGPTDTotOffPN	OBJECT-TYPE
        SYNTAX    INTEGER
        ACCESS    read-only
        STATUS    mandatory
        DESCRIPTION
            "An object containing the total number of GPTD receivers allocated
            of a different PN for requests originated on this PN."
        ::= { g3pktonerecEntry 15 }

    g3pktonerecGPTDPkOffPN	OBJECT-TYPE
        SYNTAX    INTEGER
        ACCESS    read-only
        STATUS    mandatory
        DESCRIPTION
            "An object containing the peak number of GPTD receivers simultaneously
            allocated on a different PN for requests originated on this PN."
        ::= { g3pktonerecEntry 16 }

    g3pktonerecCCTTRPnReq	OBJECT-TYPE
        SYNTAX    INTEGER
        ACCESS    read-only
        STATUS    mandatory
        DESCRIPTION
            "An object containing the number of CC-TTR requests within the PN."
        ::= { g3pktonerecEntry 17 }

    g3pktonerecCCTTRPnAlloc	OBJECT-TYPE
        SYNTAX    INTEGER
        ACCESS    read-only
        STATUS    mandatory
        DESCRIPTION
            "An object containing the total number of CC-TTR receivers located
            in the listed PN that were allocated during the last hour."
        ::= { g3pktonerecEntry 18 }

    g3pktonerecCCTTRPkAlloc	OBJECT-TYPE
        SYNTAX    INTEGER
        ACCESS    read-only
        STATUS    mandatory
        DESCRIPTION
            "An object containing the peak number of CC-TTR receivers located
            in the listed PN that were in use simulatneously."
        ::= { g3pktonerecEntry 19 }

    g3pktonerecCCTTRTotOffPN	OBJECT-TYPE
        SYNTAX    INTEGER
        ACCESS    read-only
        STATUS    mandatory
        DESCRIPTION
            "An object containing the total number of CC-TTR receivers allocated
            of a different PN for requests originated on this PN."
        ::= { g3pktonerecEntry 20 }

    g3pktonerecCCTTRPkOffPN	OBJECT-TYPE
        SYNTAX    INTEGER
        ACCESS    read-only
        STATUS    mandatory
        DESCRIPTION
            "An object containing the peak number of CC-TTR receivers simultaneously
            allocated on a different PN for requests originated on this PN."
        ::= { g3pktonerecEntry 21 }

    g3pktonerecCCCPTRPnReq	OBJECT-TYPE
        SYNTAX    INTEGER
        ACCESS    read-only
        STATUS    mandatory
        DESCRIPTION
            "An object containing the number of CC-CPTR requests within the PN."
        ::= { g3pktonerecEntry 22 }

    g3pktonerecCCCPTRPnAlloc	OBJECT-TYPE
        SYNTAX    INTEGER
        ACCESS    read-only
        STATUS    mandatory
        DESCRIPTION
            "An object containing the total number of CC-CPTR receivers located
            in the listed PN that were allocated during the last hour."
        ::= { g3pktonerecEntry 23 }

    g3pktonerecCCCPTRPkAlloc	OBJECT-TYPE
        SYNTAX    INTEGER
        ACCESS    read-only
        STATUS    mandatory
        DESCRIPTION
            "An object containing the peak number of CC-CPTR receivers located
            in the listed PN that were in use simulatneously."
        ::= { g3pktonerecEntry 24 }

    g3pktonerecCCCPTRTotOffPN	OBJECT-TYPE
        SYNTAX    INTEGER
        ACCESS    read-only
        STATUS    mandatory
        DESCRIPTION
            "An object containing the total number of CC-CPTR receivers allocated
            of a different PN for requests originated on this PN."
        ::= { g3pktonerecEntry 25 }

    g3pktonerecCCCPTRPkOffPN	OBJECT-TYPE
        SYNTAX    INTEGER
        ACCESS    read-only
        STATUS    mandatory
        DESCRIPTION
            "An object containing the peak number of CC-CPTR receivers simultaneously
            allocated on a different PN for requests originated on this PN."
        ::= { g3pktonerecEntry 26 }

    g3pktonerecCCMFCRPnReq	OBJECT-TYPE
        SYNTAX    INTEGER
        ACCESS    read-only
        STATUS    mandatory
        DESCRIPTION
            "An object containing the number of CC-MFCR requests within the PN."
        ::= { g3pktonerecEntry 27 }

    g3pktonerecCCMFCRPnAlloc	OBJECT-TYPE
        SYNTAX    INTEGER
        ACCESS    read-only
        STATUS    mandatory
        DESCRIPTION
            "An object containing the total number of CC-MFCR receivers located
            in the listed PN that were allocated during the last hour."
        ::= { g3pktonerecEntry 28 }

    g3pktonerecCCMFCRPkAlloc	OBJECT-TYPE
        SYNTAX    INTEGER
        ACCESS    read-only
        STATUS    mandatory
        DESCRIPTION
            "An object containing the peak number of CC-MFCR receivers located
            in the listed PN that were in use simulatneously."
        ::= { g3pktonerecEntry 29 }

    g3pktonerecCCMFCRTotOffPN	OBJECT-TYPE
        SYNTAX    INTEGER
        ACCESS    read-only
        STATUS    mandatory
        DESCRIPTION
            "An object containing the total number of CC-MFCR receivers allocated
            of a different PN for requests originated on this PN."
        ::= { g3pktonerecEntry 30 }

    g3pktonerecCCMFCRPkOffPN	OBJECT-TYPE
        SYNTAX    INTEGER
        ACCESS    read-only
        STATUS    mandatory
        DESCRIPTION
            "An object containing the peak number of CC-MFCR receivers simultaneously
            allocated on a different PN for requests originated on this PN."
        ::= { g3pktonerecEntry 31 }


    -- the g3tonerecsum group

    g3tonerecsumTage	OBJECT-TYPE
        SYNTAX    INTEGER
        ACCESS    read-only
        STATUS    mandatory
        DESCRIPTION
            "The number of timeticks since the tone receiver summary data was last
            extracted from the switch by the Proxy Agent.  This object
            along with the g3tonerecsumintvl object allows the Network Manager
            to determine the validity of the data in the cache and to control
            when the Proxy Agent extracts the data from the switch."
        ::= { g3tonerecsum 1 }

    g3tonerecsumTintvl	OBJECT-TYPE
        SYNTAX    INTEGER
        ACCESS    read-write
        STATUS    mandatory
        DESCRIPTION
            "An object containing the interval for which the tone receiver summary
            data extracted from the switch is considered valid by the Proxy
            Agent.  When a GET or GET-NEXT request for tone receiver summary
            objects is received by the agent it uses the g3tonerecsumage
            and g3tonerecsumintvl objects to determine whether it should refresh
            the cached tonerecsumTable.  If g3tonerecsumstmp + g3tonerecsumintvl
            is less than the current value of the sysUpTime object then the agent
            refreshes the tonerecsumTable cache.  In either case it responds to
            the requests it receives with the data it currently has in the cache."
        ::= { g3tonerecsum 2 }

    g3tonerecsumTdelay	OBJECT-TYPE
        SYNTAX    INTEGER
        ACCESS    read-only
        STATUS    mandatory
        DESCRIPTION
            "An object containing the delay encountered in updating
            the cached data."
        ::= { g3tonerecsum 3 }

    g3tonerecsumTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3tonerecsum 4 }

    g3tonerecsumRunYear	OBJECT-TYPE
        SYNTAX    INTEGER
        ACCESS    read-only
        STATUS    mandatory
        DESCRIPTION
            "An object containing the Year the command was executed."
        ::= { g3tonerecsum 5 }

    g3tonerecsumRunMonth	OBJECT-TYPE
        SYNTAX    INTEGER
        ACCESS    read-only
        STATUS    mandatory
        DESCRIPTION
            "An object containing the Month the command was executed."
        ::= { g3tonerecsum 6 }

    g3tonerecsumRunDay	OBJECT-TYPE
        SYNTAX    INTEGER
        ACCESS    read-only
        STATUS    mandatory
        DESCRIPTION
            "An object containing the Day the command was executed."
        ::= { g3tonerecsum 7 }

    g3tonerecsumRunHour	OBJECT-TYPE
        SYNTAX    INTEGER
        ACCESS    read-only
        STATUS    mandatory
        DESCRIPTION
            "An object containing the Hour the measurement was taken."
        ::= { g3tonerecsum 8 }

    g3tonerecsumDTMFHour	OBJECT-TYPE
        SYNTAX    INTEGER
        ACCESS    read-only
        STATUS    mandatory
        DESCRIPTION
            "An object containing the Hour the measurement was taken."
        ::= { g3tonerecsum 9 }

    g3tonerecsumDTMFTReq	OBJECT-TYPE
        SYNTAX    INTEGER
        ACCESS    read-only
        STATUS    mandatory
        DESCRIPTION
            "An object containing the system-wide total number of requests for
            tone receivers of this type for the measurement interval."
        ::= { g3tonerecsum 10 }

    g3tonerecsumDTMFPReq	OBJECT-TYPE
        SYNTAX    INTEGER
        ACCESS    read-only
        STATUS    mandatory
        DESCRIPTION
            "An object containing the system-wide peak number of simultaneous
            requests for tone receivers of this type that occurred at any one
            time over the measurement interval."
        ::= { g3tonerecsum 11 }

    g3tonerecsumDTMFTQueue	OBJECT-TYPE
        SYNTAX    INTEGER
        ACCESS    read-only
        STATUS    mandatory
        DESCRIPTION
            "An object containing the system-wide total number of requests queued
            for tone receivers of this type during the measurement interval."
        ::= { g3tonerecsum 12 }

    g3tonerecsumDTMFPQueue	OBJECT-TYPE
        SYNTAX    INTEGER
        ACCESS    read-only
        STATUS    mandatory
        DESCRIPTION
            "An object containing the system-wide peak number of requests queued
            at any one time during the measurement hour for tone receivers of
            this type."
        ::= { g3tonerecsum 13 }

    g3tonerecsumDTMFTDeny	OBJECT-TYPE
        SYNTAX    INTEGER
        ACCESS    read-only
        STATUS    mandatory
        DESCRIPTION
            "An object containing the system-wide total number of requests that
            were denied because no receivers of this type were available during
            the measurement hour."
        ::= { g3tonerecsum 14 }

    g3tonerecsumDTMFPDeny	OBJECT-TYPE
        SYNTAX    INTEGER
        ACCESS    read-only
        STATUS    mandatory
        DESCRIPTION
            "An object containing the system-wide peak number of requests that
            were denied at any one time because no receivers of this type were
            available during the measurement hour."
        ::= { g3tonerecsum 15 }

    g3tonerecsumGPTDHour	OBJECT-TYPE
        SYNTAX    INTEGER
        ACCESS    read-only
        STATUS    mandatory
        DESCRIPTION
            "An object containing the Hour the measurement was taken."
        ::= { g3tonerecsum 16 }

    g3tonerecsumGPTDTReq	OBJECT-TYPE
        SYNTAX    INTEGER
        ACCESS    read-only
        STATUS    mandatory
        DESCRIPTION
            "An object containing the system-wide total number of requests for
            tone receivers of this type for the measurement interval."
        ::= { g3tonerecsum 17 }

    g3tonerecsumGPTDPReq	OBJECT-TYPE
        SYNTAX    INTEGER
        ACCESS    read-only
        STATUS    mandatory
        DESCRIPTION
            "An object containing the system-wide peak number of simultaneous
            requests for tone receivers of this type that occurred at any one
            time over the measurement interval."
        ::= { g3tonerecsum 18 }

    g3tonerecsumGPTDTDeny	OBJECT-TYPE
        SYNTAX    INTEGER
        ACCESS    read-only
        STATUS    mandatory
        DESCRIPTION
            "An object containing the system-wide total number of requests that
            were denied because no receivers of this type were available during
            the measurement hour."
        ::= { g3tonerecsum 19 }

    g3tonerecsumGPTDPDeny	OBJECT-TYPE
        SYNTAX    INTEGER
        ACCESS    read-only
        STATUS    mandatory
        DESCRIPTION
            "An object containing the system-wide peak number of requests that
            were denied at any one time because no receivers of this type were
            available during the measurement hour."
        ::= { g3tonerecsum 20 }

    g3tonerecsumCCTTRHour	OBJECT-TYPE
        SYNTAX    INTEGER
        ACCESS    read-only
        STATUS    mandatory
        DESCRIPTION
            "An object containing the Hour the measurement was taken."
        ::= { g3tonerecsum 21 }

    g3tonerecsumCCTTRTReq	OBJECT-TYPE
        SYNTAX    INTEGER
        ACCESS    read-only
        STATUS    mandatory
        DESCRIPTION
            "An object containing the system-wide total number of requests for
            tone receivers of this type for the measurement interval."
        ::= { g3tonerecsum 22 }

    g3tonerecsumCCTTRPReq	OBJECT-TYPE
        SYNTAX    INTEGER
        ACCESS    read-only
        STATUS    mandatory
        DESCRIPTION
            "An object containing the system-wide peak number of simultaneous
            requests for tone receivers of this type that occurred at any one
            time over the measurement interval."
        ::= { g3tonerecsum 23 }

    g3tonerecsumCCTTRTQueue	OBJECT-TYPE
        SYNTAX    INTEGER
        ACCESS    read-only
        STATUS    mandatory
        DESCRIPTION
            "An object containing the system-wide total number of requests queued
            for tone receivers of this type during the measurement interval."
        ::= { g3tonerecsum 24 }

    g3tonerecsumCCTTRPQueue	OBJECT-TYPE
        SYNTAX    INTEGER
        ACCESS    read-only
        STATUS    mandatory
        DESCRIPTION
            "An object containing the system-wide peak number of requests queued
            at any one time during the measurement hour for tone receivers of
            this type."
        ::= { g3tonerecsum 25 }

    g3tonerecsumCCTTRTDeny	OBJECT-TYPE
        SYNTAX    INTEGER
        ACCESS    read-only
        STATUS    mandatory
        DESCRIPTION
            "An object containing the system-wide total number of requests that
            were denied because no receivers of this type were available during
            the measurement hour."
        ::= { g3tonerecsum 26 }

    g3tonerecsumCCTTRPDeny	OBJECT-TYPE
        SYNTAX    INTEGER
        ACCESS    read-only
        STATUS    mandatory
        DESCRIPTION
            "An object containing the system-wide peak number of requests that
            were denied at any one time because no receivers of this type were
            available during the measurement hour."
        ::= { g3tonerecsum 27 }

    g3tonerecsumCCCPTRHour	OBJECT-TYPE
        SYNTAX    INTEGER
        ACCESS    read-only
        STATUS    mandatory
        DESCRIPTION
            "An object containing the Hour the measurement was taken."
        ::= { g3tonerecsum 28 }

    g3tonerecsumCCCPTRTReq	OBJECT-TYPE
        SYNTAX    INTEGER
        ACCESS    read-only
        STATUS    mandatory
        DESCRIPTION
            "An object containing the system-wide total number of requests for
            tone receivers of this type for the measurement interval."
        ::= { g3tonerecsum 29 }

    g3tonerecsumCCCPTRPReq	OBJECT-TYPE
        SYNTAX    INTEGER
        ACCESS    read-only
        STATUS    mandatory
        DESCRIPTION
            "An object containing the system-wide peak number of simultaneous
            requests for tone receivers of this type that occurred at any one
            time over the measurement interval."
        ::= { g3tonerecsum 30 }

    g3tonerecsumCCCPTRTDeny	OBJECT-TYPE
        SYNTAX    INTEGER
        ACCESS    read-only
        STATUS    mandatory
        DESCRIPTION
            "An object containing the system-wide total number of requests that
            were denied because no receivers of this type were available during
            the measurement hour."
        ::= { g3tonerecsum 31 }

    g3tonerecsumCCCPTRPDeny	OBJECT-TYPE
        SYNTAX    INTEGER
        ACCESS    read-only
        STATUS    mandatory
        DESCRIPTION
            "An object containing the system-wide peak number of requests that
            were denied at any one time because no receivers of this type were
            available during the measurement hour."
        ::= { g3tonerecsum 32 }

    g3tonerecsumCCMFCRHour	OBJECT-TYPE
        SYNTAX    INTEGER
        ACCESS    read-only
        STATUS    mandatory
        DESCRIPTION
            "An object containing the Hour the measurement was taken."
        ::= { g3tonerecsum 33 }

    g3tonerecsumCCMFCRTReq	OBJECT-TYPE
        SYNTAX    INTEGER
        ACCESS    read-only
        STATUS    mandatory
        DESCRIPTION
            "An object containing the system-wide total number of requests for
            tone receivers of this type for the measurement interval."
        ::= { g3tonerecsum 34 }

    g3tonerecsumCCMFCRPReq	OBJECT-TYPE
        SYNTAX    INTEGER
        ACCESS    read-only
        STATUS    mandatory
        DESCRIPTION
            "An object containing the system-wide peak number of simultaneous
            requests for tone receivers of this type that occurred at any one
            time over the measurement interval."
        ::= { g3tonerecsum 35 }

    g3tonerecsumCCMFCRTDeny	OBJECT-TYPE
        SYNTAX    INTEGER
        ACCESS    read-only
        STATUS    mandatory
        DESCRIPTION
            "An object containing the system-wide total number of requests that
            were denied because no receivers of this type were available during
            the measurement hour."
        ::= { g3tonerecsum 36 }

    g3tonerecsumCCMFCRPDeny	OBJECT-TYPE
        SYNTAX    INTEGER
        ACCESS    read-only
        STATUS    mandatory
        DESCRIPTION
            "An object containing the system-wide peak number of requests that
            were denied at any one time because no receivers of this type were
            available during the measurement hour."
        ::= { g3tonerecsum 37 }

    g3tonerecsumDTMRTAvail	OBJECT-TYPE
        SYNTAX    INTEGER
        ACCESS    read-only
        STATUS    mandatory
        DESCRIPTION
            "An object containing the number of ports available for the type
            of tone receiver."
        ::= { g3tonerecsum 38 }

    g3tonerecsumGPRDTAvail	OBJECT-TYPE
        SYNTAX    INTEGER
        ACCESS    read-only
        STATUS    mandatory
        DESCRIPTION
            "An object containing the number of ports available for the type
            of tone receiver."
        ::= { g3tonerecsum 39 }

    g3tonerecsumCLASTAvail	OBJECT-TYPE
        SYNTAX    INTEGER
        ACCESS    read-only
        STATUS    mandatory
        DESCRIPTION
            "An object containing the number of ports available for the type
            of tone receiver."
        ::= { g3tonerecsum 40 }

    g3tonerecsumETRTAvail	OBJECT-TYPE
        SYNTAX    INTEGER
        ACCESS    read-only
        STATUS    mandatory
        DESCRIPTION
            "An object containing the number of ports available for the type
            of tone receiver."
        ::= { g3tonerecsum 41 }


    -- the g3pktonerecsum group

    g3pktonerecsumTage	OBJECT-TYPE
        SYNTAX    INTEGER
        ACCESS    read-only
        STATUS    mandatory
        DESCRIPTION
            "The number of timeticks since the tone receiver summary data was last
            extracted from the switch by the Proxy Agent.  This object
            along with the g3pktonerecsumintvl object allows the Network Manager
            to determine the validity of the data in the cache and to control
            when the Proxy Agent extracts the data from the switch."
        ::= { g3pktonerecsum 1 }

    g3pktonerecsumTintvl	OBJECT-TYPE
        SYNTAX    INTEGER
        ACCESS    read-write
        STATUS    mandatory
        DESCRIPTION
            "An object containing the interval for which the tone receiver summary
            data extracted from the switch is considered valid by the Proxy
            Agent.  When a GET or GET-NEXT request for tone receiver summary
            objects is received by the agent it uses the g3pktonerecsumage
            and g3pktonerecsumintvl objects to determine whether it should refresh
            the cached pktonerecsumTable. If pkg3tonerecsumstmp+pkg3tonerecsumintvl
            is less than the current value of the sysUpTime object then the agent
            refreshes the pktonerecsumTable cache.  In either case it responds to
            the requests it receives with the data it currently has in the cache."
        ::= { g3pktonerecsum 2 }

    g3pktonerecsumTdelay	OBJECT-TYPE
        SYNTAX    INTEGER
        ACCESS    read-only
        STATUS    mandatory
        DESCRIPTION
            "An object containing the delay encountered in updating
            the cached data."
        ::= { g3pktonerecsum 3 }

    g3pktonerecsumTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3pktonerecsum 4 }

    g3pktonerecsumRunYear	OBJECT-TYPE
        SYNTAX    INTEGER
        ACCESS    read-only
        STATUS    mandatory
        DESCRIPTION
            "An object containing the Year the command was executed."
        ::= { g3pktonerecsum 5 }

    g3pktonerecsumRunMonth	OBJECT-TYPE
        SYNTAX    INTEGER
        ACCESS    read-only
        STATUS    mandatory
        DESCRIPTION
            "An object containing the Month the command was executed."
        ::= { g3pktonerecsum 6 }

    g3pktonerecsumRunDay	OBJECT-TYPE
        SYNTAX    INTEGER
        ACCESS    read-only
        STATUS    mandatory
        DESCRIPTION
            "An object containing the Day the command was executed."
        ::= { g3pktonerecsum 7 }

    g3pktonerecsumRunHour	OBJECT-TYPE
        SYNTAX    INTEGER
        ACCESS    read-only
        STATUS    mandatory
        DESCRIPTION
            "An object containing the Hour the measurement was taken."
        ::= { g3pktonerecsum 8 }

    g3pktonerecsumDTMFHour	OBJECT-TYPE
        SYNTAX    INTEGER
        ACCESS    read-only
        STATUS    mandatory
        DESCRIPTION
            "An object containing the Hour the measurement was taken."
        ::= { g3pktonerecsum 9 }

    g3pktonerecsumDTMFTReq	OBJECT-TYPE
        SYNTAX    INTEGER
        ACCESS    read-only
        STATUS    mandatory
        DESCRIPTION
            "An object containing the system-wide total number of requests for
            tone receivers of this type for the measurement interval."
        ::= { g3pktonerecsum 10 }

    g3pktonerecsumDTMFPReq	OBJECT-TYPE
        SYNTAX    INTEGER
        ACCESS    read-only
        STATUS    mandatory
        DESCRIPTION
            "An object containing the system-wide peak number of simultaneous
            requests for tone receivers of this type that occurred at any one
            time over the measurement interval."
        ::= { g3pktonerecsum 11 }

    g3pktonerecsumDTMFTQueue	OBJECT-TYPE
        SYNTAX    INTEGER
        ACCESS    read-only
        STATUS    mandatory
        DESCRIPTION
            "An object containing the system-wide total number of requests queued
            for tone receivers of this type during the measurement interval."
        ::= { g3pktonerecsum 12 }

    g3pktonerecsumDTMFPQueue	OBJECT-TYPE
        SYNTAX    INTEGER
        ACCESS    read-only
        STATUS    mandatory
        DESCRIPTION
            "An object containing the system-wide peak number of requests queued
            at any one time during the measurement hour for tone receivers of
            this type."
        ::= { g3pktonerecsum 13 }

    g3pktonerecsumDTMFTDeny	OBJECT-TYPE
        SYNTAX    INTEGER
        ACCESS    read-only
        STATUS    mandatory
        DESCRIPTION
            "An object containing the system-wide total number of requests that
            were denied because no receivers of this type were available during
            the measurement hour."
        ::= { g3pktonerecsum 14 }

    g3pktonerecsumDTMFPDeny	OBJECT-TYPE
        SYNTAX    INTEGER
        ACCESS    read-only
        STATUS    mandatory
        DESCRIPTION
            "An object containing the system-wide peak number of requests that
            were denied at any one time because no receivers of this type were"
        ::= { g3pktonerecsum 15 }

    g3pktonerecsumGPTDHour	OBJECT-TYPE
        SYNTAX    INTEGER
        ACCESS    read-only
        STATUS    mandatory
        DESCRIPTION
            "An object containing the Hour the measurement was taken."
        ::= { g3pktonerecsum 16 }

    g3pktonerecsumGPTDTReq	OBJECT-TYPE
        SYNTAX    INTEGER
        ACCESS    read-only
        STATUS    mandatory
        DESCRIPTION
            "An object containing the system-wide total number of requests for
            tone receivers of this type for the measurement interval."
        ::= { g3pktonerecsum 17 }

    g3pktonerecsumGPTDPReq	OBJECT-TYPE
        SYNTAX    INTEGER
        ACCESS    read-only
        STATUS    mandatory
        DESCRIPTION
            "An object containing the system-wide peak number of simultaneous
            requests for tone receivers of this type that occurred at any one
            time over the measurement interval."
        ::= { g3pktonerecsum 18 }

    g3pktonerecsumGPTDTDeny	OBJECT-TYPE
        SYNTAX    INTEGER
        ACCESS    read-only
        STATUS    mandatory
        DESCRIPTION
            "An object containing the system-wide total number of requests that
            were denied because no receivers of this type were available during
            the measurement hour."
        ::= { g3pktonerecsum 19 }

    g3pktonerecsumGPTDPDeny	OBJECT-TYPE
        SYNTAX    INTEGER
        ACCESS    read-only
        STATUS    mandatory
        DESCRIPTION
            "An object containing the system-wide peak number of requests that
            were denied at any one time because no receivers of this type were
            available during the measurement hour."
        ::= { g3pktonerecsum 20 }

    g3pktonerecsumCCTTRHour	OBJECT-TYPE
        SYNTAX    INTEGER
        ACCESS    read-only
        STATUS    mandatory
        DESCRIPTION
            "An object containing the Hour the measurement was taken."
        ::= { g3pktonerecsum 21 }

    g3pktonerecsumCCTTRTReq	OBJECT-TYPE
        SYNTAX    INTEGER
        ACCESS    read-only
        STATUS    mandatory
        DESCRIPTION
            "An object containing the system-wide total number of requests for
            tone receivers of this type for the measurement interval."
        ::= { g3pktonerecsum 22 }

    g3pktonerecsumCCTTRPReq	OBJECT-TYPE
        SYNTAX    INTEGER
        ACCESS    read-only
        STATUS    mandatory
        DESCRIPTION
            "An object containing the system-wide peak number of simultaneous
            requests for tone receivers of this type that occurred at any one
            time over the measurement interval."
        ::= { g3pktonerecsum 23 }

    g3pktonerecsumCCTTRTQueue	OBJECT-TYPE
        SYNTAX    INTEGER
        ACCESS    read-only
        STATUS    mandatory
        DESCRIPTION
            "An object containing the system-wide total number of requests queued
            for tone receivers of this type during the measurement interval."
        ::= { g3pktonerecsum 24 }

    g3pktonerecsumCCTTRPQueue	OBJECT-TYPE
        SYNTAX    INTEGER
        ACCESS    read-only
        STATUS    mandatory
        DESCRIPTION
            "An object containing the system-wide peak number of requests queued
            at any one time during the measurement hour for tone receivers of
            this type."
        ::= { g3pktonerecsum 25 }

    g3pktonerecsumCCTTRTDeny	OBJECT-TYPE
        SYNTAX    INTEGER
        ACCESS    read-only
        STATUS    mandatory
        DESCRIPTION
            "An object containing the system-wide total number of requests that
            were denied because no receivers of this type were available during
            the measurement hour."
        ::= { g3pktonerecsum 26 }

    g3pktonerecsumCCTTRPDeny	OBJECT-TYPE
        SYNTAX    INTEGER
        ACCESS    read-only
        STATUS    mandatory
        DESCRIPTION
            "An object containing the system-wide peak number of requests that
            were denied at any one time because no receivers of this type were
            available during the measurement hour."
        ::= { g3pktonerecsum 27 }

    g3pktonerecsumCCCPTRHour	OBJECT-TYPE
        SYNTAX    INTEGER
        ACCESS    read-only
        STATUS    mandatory
        DESCRIPTION
            "An object containing the Hour the measurement was taken."
        ::= { g3pktonerecsum 28 }

    g3pktonerecsumCCCPTRTReq	OBJECT-TYPE
        SYNTAX    INTEGER
        ACCESS    read-only
        STATUS    mandatory
        DESCRIPTION
            "An object containing the system-wide total number of requests for
            tone receivers of this type for the measurement interval."
        ::= { g3pktonerecsum 29 }

    g3pktonerecsumCCCPTRPReq	OBJECT-TYPE
        SYNTAX    INTEGER
        ACCESS    read-only
        STATUS    mandatory
        DESCRIPTION
            "An object containing the system-wide peak number of simultaneous
            requests for tone receivers of this type that occurred at any one
            time over the measurement interval."
        ::= { g3pktonerecsum 30 }

    g3pktonerecsumCCCPTRTDeny	OBJECT-TYPE
        SYNTAX    INTEGER
        ACCESS    read-only
        STATUS    mandatory
        DESCRIPTION
            "An object containing the system-wide total number of requests that
            were denied because no receivers of this type were available during
            the measurement hour."
        ::= { g3pktonerecsum 31 }

    g3pktonerecsumCCCPTRPDeny	OBJECT-TYPE
        SYNTAX    INTEGER
        ACCESS    read-only
        STATUS    mandatory
        DESCRIPTION
            "An object containing the system-wide peak number of requests that
            were denied at any one time because no receivers of this type were
            available during the measurement hour."
        ::= { g3pktonerecsum 32 }

    g3pktonerecsumCCMFCRHour	OBJECT-TYPE
        SYNTAX    INTEGER
        ACCESS    read-only
        STATUS    mandatory
        DESCRIPTION
            "An object containing the Hour the measurement was taken."
        ::= { g3pktonerecsum 33 }

    g3pktonerecsumCCMFCRTReq	OBJECT-TYPE
        SYNTAX    INTEGER
        ACCESS    read-only
        STATUS    mandatory
        DESCRIPTION
            "An object containing the system-wide total number of requests for
            tone receivers of this type for the measurement interval."
        ::= { g3pktonerecsum 34 }

    g3pktonerecsumCCMFCRPReq	OBJECT-TYPE
        SYNTAX    INTEGER
        ACCESS    read-only
        STATUS    mandatory
        DESCRIPTION
            "An object containing the system-wide peak number of simultaneous
            requests for tone receivers of this type that occurred at any one
            time over the measurement interval."
        ::= { g3pktonerecsum 35 }

    g3pktonerecsumCCMFCRTDeny	OBJECT-TYPE
        SYNTAX    INTEGER
        ACCESS    read-only
        STATUS    mandatory
        DESCRIPTION
            "An object containing the system-wide total number of requests that
            were denied because no receivers of this type were available during
            the measurement hour."
        ::= { g3pktonerecsum 36 }

    g3pktonerecsumCCMFCRPDeny	OBJECT-TYPE
        SYNTAX    INTEGER
        ACCESS    read-only
        STATUS    mandatory
        DESCRIPTION
            "An object containing the system-wide peak number of requests that
            were denied at any one time because no receivers of this type were
            available during the measurement hour."
        ::= { g3pktonerecsum 37 }

    g3pktonerecsumDTMRTAvail	OBJECT-TYPE
        SYNTAX    INTEGER
        ACCESS    read-only
        STATUS    mandatory
        DESCRIPTION
            "An object containing the number of ports available for the type
            of tone receiver."
        ::= { g3pktonerecsum 38 }

    g3pktonerecsumGPRDTAvail	OBJECT-TYPE
        SYNTAX    INTEGER
        ACCESS    read-only
        STATUS    mandatory
        DESCRIPTION
            "An object containing the number of ports available for the type
            of tone receiver."
        ::= { g3pktonerecsum 39 }

    g3pktonerecsumCLASTAvail	OBJECT-TYPE
        SYNTAX    INTEGER
        ACCESS    read-only
        STATUS    mandatory
        DESCRIPTION
            "An object containing the number of ports available for the type
            of tone receiver."
        ::= { g3pktonerecsum 40 }

    g3pktonerecsumETRTAvail	OBJECT-TYPE
        SYNTAX    INTEGER
        ACCESS    read-only
        STATUS    mandatory
        DESCRIPTION
            "An object containing the number of ports available for the type
            of tone receiver."
        ::= { g3pktonerecsum 41 }


    -- the g3rpatcfg group

    g3rpatcfgTage	OBJECT-TYPE
        SYNTAX    INTEGER
        ACCESS    read-only
        STATUS    mandatory
        DESCRIPTION
            "The number of timeticks since the route pattern data was last
            extracted from the switch by the Proxy Agent.  This object
            along with the g3rpatcfgintvl object allows the Network Manager
            to determine the validity of the data in the cache and to control
            when the Proxy Agent extracts the data from the switch."
        ::= { g3rpatcfg 1 }

    g3rpatcfgTintvl	OBJECT-TYPE
        SYNTAX    INTEGER
        ACCESS    read-write
        STATUS    mandatory
        DESCRIPTION
            "An object containing the interval for which the route pattern
            data extracted from the switch is considered valid by the
            Proxy Agent.  When a GET or GET-NEXT request for route pattern
            objects is received by the agent it uses the g3rpatcfgage
            and g3rpatcfgintvl objects to determine whether it should refresh
            the cached rpatcfgTable.  If g3rpatcfgstmp + g3rpatcfgintvl
            is less than the current value of the sysUpTime object then the agent
            refreshes the rpatcfgTable cache.  In either case it responds to
            the requests it receives with the data it currently has in the cache."
        ::= { g3rpatcfg 2 }

    g3rpatcfgTdelay	OBJECT-TYPE
        SYNTAX    INTEGER
        ACCESS    read-only
        STATUS    mandatory
        DESCRIPTION
            "An object containing the delay encountered in updating
            the cached data."
        ::= { g3rpatcfg 3 }

    g3rpatcfgTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3rpatcfg 4 }

    g3rpatcfgTcount	OBJECT-TYPE
        SYNTAX    Gauge
        ACCESS    read-only
        STATUS    mandatory
        DESCRIPTION
            "A Gauge object containing the number of data records in the cache."
        ::= { g3rpatcfg 5 }

    g3rpatcfgPattern1	OBJECT-TYPE
        SYNTAX    INTEGER
        ACCESS    read-only
        STATUS    mandatory
        DESCRIPTION
            "An object containing the measurement 1 route pattern"
        ::= { g3rpatcfg 6 }

    g3rpatcfgPattern2	OBJECT-TYPE
        SYNTAX    INTEGER
        ACCESS    read-only
        STATUS    mandatory
        DESCRIPTION
            "An object containing the measurement 2 route pattern"
        ::= { g3rpatcfg 7 }

    g3rpatcfgPattern3	OBJECT-TYPE
        SYNTAX    INTEGER
        ACCESS    read-only
        STATUS    mandatory
        DESCRIPTION
            "An object containing the measurement 3 route pattern"
        ::= { g3rpatcfg 8 }

    g3rpatcfgPattern4	OBJECT-TYPE
        SYNTAX    INTEGER
        ACCESS    read-only
        STATUS    mandatory
        DESCRIPTION
            "An object containing the measurement 4 route pattern"
        ::= { g3rpatcfg 9 }

    g3rpatcfgPattern5	OBJECT-TYPE
        SYNTAX    INTEGER
        ACCESS    read-only
        STATUS    mandatory
        DESCRIPTION
            "An object containing the measurement 5 route pattern"
        ::= { g3rpatcfg 10 }

    g3rpatcfgPattern6	OBJECT-TYPE
        SYNTAX    INTEGER
        ACCESS    read-only
        STATUS    mandatory
        DESCRIPTION
            "An object containing the measurement 6 route pattern"
        ::= { g3rpatcfg 11 }

    g3rpatcfgPattern7	OBJECT-TYPE
        SYNTAX    INTEGER
        ACCESS    read-only
        STATUS    mandatory
        DESCRIPTION
            "An object containing the measurement 7 route pattern"
        ::= { g3rpatcfg 12 }

    g3rpatcfgPattern8	OBJECT-TYPE
        SYNTAX    INTEGER
        ACCESS    read-only
        STATUS    mandatory
        DESCRIPTION
            "An object containing the measurement 8 route pattern"
        ::= { g3rpatcfg 13 }

    g3rpatcfgPattern9	OBJECT-TYPE
        SYNTAX    INTEGER
        ACCESS    read-only
        STATUS    mandatory
        DESCRIPTION
            "An object containing the measurement 9 route pattern"
        ::= { g3rpatcfg 14 }

    g3rpatcfgPattern10	OBJECT-TYPE
        SYNTAX    INTEGER
        ACCESS    read-only
        STATUS    mandatory
        DESCRIPTION
            "An object containing the measurement 10 route pattern"
        ::= { g3rpatcfg 15 }

    g3rpatcfgPattern11	OBJECT-TYPE
        SYNTAX    INTEGER
        ACCESS    read-only
        STATUS    mandatory
        DESCRIPTION
            "An object containing the measurement 11 route pattern"
        ::= { g3rpatcfg 16 }

    g3rpatcfgPattern12	OBJECT-TYPE
        SYNTAX    INTEGER
        ACCESS    read-only
        STATUS    mandatory
        DESCRIPTION
            "An object containing the measurement 12 route pattern"
        ::= { g3rpatcfg 17 }

    g3rpatcfgPattern13	OBJECT-TYPE
        SYNTAX    INTEGER
        ACCESS    read-only
        STATUS    mandatory
        DESCRIPTION
            "An object containing the measurement 13 route pattern"
        ::= { g3rpatcfg 18 }

    g3rpatcfgPattern14	OBJECT-TYPE
        SYNTAX    INTEGER
        ACCESS    read-only
        STATUS    mandatory
        DESCRIPTION
            "An object containing the measurement 14 route pattern"
        ::= { g3rpatcfg 19 }

    g3rpatcfgPattern15	OBJECT-TYPE
        SYNTAX    INTEGER
        ACCESS    read-only
        STATUS    mandatory
        DESCRIPTION
            "An object containing the measurement 15 route pattern"
        ::= { g3rpatcfg 20 }

    g3rpatcfgPattern16	OBJECT-TYPE
        SYNTAX    INTEGER
        ACCESS    read-only
        STATUS    mandatory
        DESCRIPTION
            "An object containing the measurement 16 route pattern"
        ::= { g3rpatcfg 21 }

    g3rpatcfgPattern17	OBJECT-TYPE
        SYNTAX    INTEGER
        ACCESS    read-only
        STATUS    mandatory
        DESCRIPTION
            "An object containing the measurement 17 route pattern"
        ::= { g3rpatcfg 22 }

    g3rpatcfgPattern18	OBJECT-TYPE
        SYNTAX    INTEGER
        ACCESS    read-only
        STATUS    mandatory
        DESCRIPTION
            "An object containing the measurement 18 route pattern"
        ::= { g3rpatcfg 23 }

    g3rpatcfgPattern19	OBJECT-TYPE
        SYNTAX    INTEGER
        ACCESS    read-only
        STATUS    mandatory
        DESCRIPTION
            "An object containing the measurement 19 route pattern"
        ::= { g3rpatcfg 24 }

    g3rpatcfgPattern20	OBJECT-TYPE
        SYNTAX    INTEGER
        ACCESS    read-only
        STATUS    mandatory
        DESCRIPTION
            "An object containing the measurement 20 route pattern"
        ::= { g3rpatcfg 25 }

    g3rpatcfgPattern21	OBJECT-TYPE
        SYNTAX    INTEGER
        ACCESS    read-only
        STATUS    mandatory
        DESCRIPTION
            "An object containing the measurement 21 route pattern"
        ::= { g3rpatcfg 26 }

    g3rpatcfgPattern22	OBJECT-TYPE
        SYNTAX    INTEGER
        ACCESS    read-only
        STATUS    mandatory
        DESCRIPTION
            "An object containing the measurement 22 route pattern"
        ::= { g3rpatcfg 27 }

    g3rpatcfgPattern23	OBJECT-TYPE
        SYNTAX    INTEGER
        ACCESS    read-only
        STATUS    mandatory
        DESCRIPTION
            "An object containing the measurement 23 route pattern"
        ::= { g3rpatcfg 28 }

    g3rpatcfgPattern24	OBJECT-TYPE
        SYNTAX    INTEGER
        ACCESS    read-only
        STATUS    mandatory
        DESCRIPTION
            "An object containing the measurement 24 route pattern"
        ::= { g3rpatcfg 29 }

    g3rpatcfgPattern25	OBJECT-TYPE
        SYNTAX    INTEGER
        ACCESS    read-only
        STATUS    mandatory
        DESCRIPTION
            "An object containing the measurement 25 route pattern"
        ::= { g3rpatcfg 30 }


    -- the g3rpat group

    g3rpatTage	OBJECT-TYPE
        SYNTAX    INTEGER
        ACCESS    read-only
        STATUS    mandatory
        DESCRIPTION
            "The number of timeticks since the route pattern data was last
            extracted from the switch by the Proxy Agent.  This object
            along with the g3rpatintvl object allows the Network Manager
            to determine the validity of the data in the cache and to control
            when the Proxy Agent extracts the data from the switch."
        ::= { g3rpat 1 }

    g3rpatTintvl	OBJECT-TYPE
        SYNTAX    INTEGER
        ACCESS    read-write
        STATUS    mandatory
        DESCRIPTION
            "An object containing the interval for which the route pattern
            data extracted from the switch is considered valid by the
            Proxy Agent.  When a GET or GET-NEXT request for route pattern
            objects is received by the agent it uses the g3rpatage
            and g3rpatintvl objects to determine whether it should refresh
            the cached rpatTable.  If g3rpatstmp + g3rpatintvl
            is less than the current value of the sysUpTime object then the agent
            refreshes the rpatTable cache.  In either case it responds to
            the requests it receives with the data it currently has in the cache."
        ::= { g3rpat 2 }

    g3rpatTdelay	OBJECT-TYPE
        SYNTAX    INTEGER
        ACCESS    read-only
        STATUS    mandatory
        DESCRIPTION
            "An object containing the delay encountered in updating
            the cached data."
        ::= { g3rpat 3 }

    g3rpatTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3rpat 4 }

    g3rpatTcount	OBJECT-TYPE
        SYNTAX    Gauge
        ACCESS    read-only
        STATUS    mandatory
        DESCRIPTION
            "A Gauge object containing the number of data records in the cache."
        ::= { g3rpat 5 }

    g3rpatTable	OBJECT-TYPE
        SYNTAX    SEQUENCE OF G3rpatEntry
        ACCESS    not-accessible
        STATUS    mandatory
        DESCRIPTION
            "A list of g3rpat entries."
        ::= { g3rpat 6 }

    g3rpatEntry	OBJECT-TYPE
        SYNTAX    G3rpatEntry
        ACCESS    not-accessible
        STATUS    mandatory
        DESCRIPTION
            "A g3rpat entry containing objects of the
            g3rpat information sent by the switch."
        INDEX    { g3rpatPattern, g3rpatIndex }
        ::= { g3rpatTable 1 }

    G3rpatEntry ::= SEQUENCE {
        g3rpatPattern
            INTEGER,
        g3rpatTrunkGroup
            INTEGER,
        g3rpatYear
            INTEGER,
        g3rpatMonth
            INTEGER,
        g3rpatDay
            INTEGER,
        g3rpatHour
            INTEGER,
        g3rpatQueueSize
            INTEGER,
        g3rpatCallsOffered
            INTEGER,
        g3rpatCallsCarried
            INTEGER,
        g3rpatCallsBlocked
            INTEGER,
        g3rpatCallsQueued
            INTEGER,
        g3rpatQueueOvflo
            INTEGER,
        g3rpatCallsCarrd
            INTEGER,
        g3rpatTotalCalls
            INTEGER,
        g3rpatIndex
            INTEGER
        }

    g3rpatPattern	OBJECT-TYPE
        SYNTAX    INTEGER
        ACCESS    read-only
        STATUS    mandatory
        DESCRIPTION
            "An object containing the number of route pattern being measured."
        ::= { g3rpatEntry 1 }

    g3rpatTrunkGroup	OBJECT-TYPE
        SYNTAX    INTEGER
        ACCESS    read-only
        STATUS    mandatory
        DESCRIPTION
            "An object containing the first trunk group number."
        ::= { g3rpatEntry 2 }

    g3rpatYear	OBJECT-TYPE
        SYNTAX    INTEGER
        ACCESS    read-only
        STATUS    mandatory
        DESCRIPTION
            "An object containing the Year the command was executed."
        ::= { g3rpatEntry 3 }

    g3rpatMonth	OBJECT-TYPE
        SYNTAX    INTEGER
        ACCESS    read-only
        STATUS    mandatory
        DESCRIPTION
            "An object containing the Month the command was executed."
        ::= { g3rpatEntry 4 }

    g3rpatDay	OBJECT-TYPE
        SYNTAX    INTEGER
        ACCESS    read-only
        STATUS    mandatory
        DESCRIPTION
            "An object containing the Day the command was executed."
        ::= { g3rpatEntry 5 }

    g3rpatHour	OBJECT-TYPE
        SYNTAX    INTEGER
        ACCESS    read-only
        STATUS    mandatory
        DESCRIPTION
            "An object containing the Hour the command was executed."
        ::= { g3rpatEntry 6 }

    g3rpatQueueSize	OBJECT-TYPE
        SYNTAX    INTEGER
        ACCESS    read-only
        STATUS    mandatory
        DESCRIPTION
            "An object containing the length of the queue for the first trunk
            group in the route pattern."
        ::= { g3rpatEntry 7 }

    g3rpatCallsOffered	OBJECT-TYPE
        SYNTAX    INTEGER
        ACCESS    read-only
        STATUS    mandatory
        DESCRIPTION
            "An object containing the total number of calls offered to the
            route pattern."
        ::= { g3rpatEntry 8 }

    g3rpatCallsCarried	OBJECT-TYPE
        SYNTAX    INTEGER
        ACCESS    read-only
        STATUS    mandatory
        DESCRIPTION
            "An object containing the total number of seizures for all trunk
            groups in the routing pattern."
        ::= { g3rpatEntry 9 }

    g3rpatCallsBlocked	OBJECT-TYPE
        SYNTAX    INTEGER
        ACCESS    read-only
        STATUS    mandatory
        DESCRIPTION
            "An object containing the number of outgoing calls that found all
            trunk groups in the pattern busy."
        ::= { g3rpatEntry 10 }

    g3rpatCallsQueued	OBJECT-TYPE
        SYNTAX    INTEGER
        ACCESS    read-only
        STATUS    mandatory
        DESCRIPTION
            "An object containing the number of offered calls that found all
            trunk groups in the pattern busy and were placed in queue for
            the first trunk group in the pattern."
        ::= { g3rpatEntry 11 }

    g3rpatQueueOvflo	OBJECT-TYPE
        SYNTAX    INTEGER
        ACCESS    read-only
        STATUS    mandatory
        DESCRIPTION
            "An object containing the number of calls that find the queue on
            the first trunk group full."
        ::= { g3rpatEntry 12 }

    g3rpatCallsCarrd	OBJECT-TYPE
        SYNTAX    INTEGER
        ACCESS    read-only
        STATUS    mandatory
        DESCRIPTION
            "An object containing the percentage of total calls carried over
            the route pattern by the trunk group."
        ::= { g3rpatEntry 13 }

    g3rpatTotalCalls	OBJECT-TYPE
        SYNTAX    INTEGER
        ACCESS    read-only
        STATUS    mandatory
        DESCRIPTION
            "An object containing the total number of calls carried by the route
            pattern over the trunk group."
        ::= { g3rpatEntry 14 }

    g3rpatIndex	OBJECT-TYPE
        SYNTAX    INTEGER
        ACCESS    read-only
        STATUS    mandatory
        DESCRIPTION
            "An object containing an index for a route pattern/trunk group
            number combination to make a record unique."
        ::= { g3rpatEntry 15 }


    -- the g3pkrpat group

    g3pkrpatTage	OBJECT-TYPE
        SYNTAX    INTEGER
        ACCESS    read-only
        STATUS    mandatory
        DESCRIPTION
            "The number of timeticks since the route pattern data was last
            extracted from the switch by the Proxy Agent.  This object
            along with the g3rpatintvl object allows the Network Manager
            to determine the validity of the data in the cache and to control
            when the Proxy Agent extracts the data from the switch."
        ::= { g3pkrpat 1 }

    g3pkrpatTintvl	OBJECT-TYPE
        SYNTAX    INTEGER
        ACCESS    read-write
        STATUS    mandatory
        DESCRIPTION
            "An object containing the interval for which the route pattern
            data extracted from the switch is considered valid by the
            Proxy Agent.  When a GET or GET-NEXT request for route pattern
            objects is received by the agent it uses the g3rpatage
            and g3rpatintvl objects to determine whether it should refresh
            the cached rpatTable.  If g3rpatstmp + g3rpatintvl
            is less than the current value of the sysUpTime object then the agent
            refreshes the rpatTable cache.  In either case it responds to
            the requests it receives with the data it currently has in the cache."
        ::= { g3pkrpat 2 }

    g3pkrpatTdelay	OBJECT-TYPE
        SYNTAX    INTEGER
        ACCESS    read-only
        STATUS    mandatory
        DESCRIPTION
            "An object containing the delay encountered in updating
            the cached data."
        ::= { g3pkrpat 3 }

    g3pkrpatTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3pkrpat 4 }

    g3pkrpatTcount	OBJECT-TYPE
        SYNTAX    Gauge
        ACCESS    read-only
        STATUS    mandatory
        DESCRIPTION
            "A Gauge object containing the number of data records in the cache."
        ::= { g3pkrpat 5 }

    g3pkrpatTable	OBJECT-TYPE
        SYNTAX    SEQUENCE OF G3pkrpatEntry
        ACCESS    not-accessible
        STATUS    mandatory
        DESCRIPTION
            "A list of g3pkrpat entries."
        ::= { g3pkrpat 6 }

    g3pkrpatEntry	OBJECT-TYPE
        SYNTAX    G3pkrpatEntry
        ACCESS    not-accessible
        STATUS    mandatory
        DESCRIPTION
            "A g3pkrpat entry containing objects of the
            g3pkrpat information sent by the switch."
        INDEX    { g3pkrpatPattern, g3pkrpatIndex }
        ::= { g3pkrpatTable 1 }

    G3pkrpatEntry ::= SEQUENCE {
        g3pkrpatPattern
            INTEGER,
        g3pkrpatTrunkGroup
            INTEGER,
        g3pkrpatYear
            INTEGER,
        g3pkrpatMonth
            INTEGER,
        g3pkrpatDay
            INTEGER,
        g3pkrpatHour
            INTEGER,
        g3pkrpatQueueSize
            INTEGER,
        g3pkrpatCallsOffered
            INTEGER,
        g3pkrpatCallsCarried
            INTEGER,
        g3pkrpatCallsBlocked
            INTEGER,
        g3pkrpatCallsQueued
            INTEGER,
        g3pkrpatQueueOvflo
            INTEGER,
        g3pkrpatCallsCarrd
            INTEGER,
        g3pkrpatTotalCalls
            INTEGER,
        g3pkrpatIndex
            INTEGER
        }

    g3pkrpatPattern	OBJECT-TYPE
        SYNTAX    INTEGER
        ACCESS    read-only
        STATUS    mandatory
        DESCRIPTION
            "An object containing the number of route pattern being measured."
        ::= { g3pkrpatEntry 1 }

    g3pkrpatTrunkGroup	OBJECT-TYPE
        SYNTAX    INTEGER
        ACCESS    read-only
        STATUS    mandatory
        DESCRIPTION
            "An object containing the first trunk group number."
        ::= { g3pkrpatEntry 2 }

    g3pkrpatYear	OBJECT-TYPE
        SYNTAX    INTEGER
        ACCESS    read-only
        STATUS    mandatory
        DESCRIPTION
            "An object containing the Year the command was executed."
        ::= { g3pkrpatEntry 3 }

    g3pkrpatMonth	OBJECT-TYPE
        SYNTAX    INTEGER
        ACCESS    read-only
        STATUS    mandatory
        DESCRIPTION
            "An object containing the Month the command was executed."
        ::= { g3pkrpatEntry 4 }

    g3pkrpatDay	OBJECT-TYPE
        SYNTAX    INTEGER
        ACCESS    read-only
        STATUS    mandatory
        DESCRIPTION
            "An object containing the Day the command was executed."
        ::= { g3pkrpatEntry 5 }

    g3pkrpatHour	OBJECT-TYPE
        SYNTAX    INTEGER
        ACCESS    read-only
        STATUS    mandatory
        DESCRIPTION
            "An object containing the Hour the command was executed."
        ::= { g3pkrpatEntry 6 }

    g3pkrpatQueueSize	OBJECT-TYPE
        SYNTAX    INTEGER
        ACCESS    read-only
        STATUS    mandatory
        DESCRIPTION
            "An object containing the length of the queue for the first trunk
            group in the route pattern."
        ::= { g3pkrpatEntry 7 }

    g3pkrpatCallsOffered	OBJECT-TYPE
        SYNTAX    INTEGER
        ACCESS    read-only
        STATUS    mandatory
        DESCRIPTION
            "An object containing the total number of calls offered to the
            route pattern."
        ::= { g3pkrpatEntry 8 }

    g3pkrpatCallsCarried	OBJECT-TYPE
        SYNTAX    INTEGER
        ACCESS    read-only
        STATUS    mandatory
        DESCRIPTION
            "An object containing the total number of seizures for all trunk
            groups in the routing pattern."
        ::= { g3pkrpatEntry 9 }

    g3pkrpatCallsBlocked	OBJECT-TYPE
        SYNTAX    INTEGER
        ACCESS    read-only
        STATUS    mandatory
        DESCRIPTION
            "An object containing the number of outgoing calls that found all
            trunk groups in the pattern busy."
        ::= { g3pkrpatEntry 10 }

    g3pkrpatCallsQueued	OBJECT-TYPE
        SYNTAX    INTEGER
        ACCESS    read-only
        STATUS    mandatory
        DESCRIPTION
            "An object containing the number of offered calls that found all
            trunk groups in the pattern busy and were placed in queue for
            the first trunk group in the pattern."
        ::= { g3pkrpatEntry 11 }

    g3pkrpatQueueOvflo	OBJECT-TYPE
        SYNTAX    INTEGER
        ACCESS    read-only
        STATUS    mandatory
        DESCRIPTION
            "An object containing the number of calls that find the queue on
            the first trunk group full."
        ::= { g3pkrpatEntry 12 }

    g3pkrpatCallsCarrd	OBJECT-TYPE
        SYNTAX    INTEGER
        ACCESS    read-only
        STATUS    mandatory
        DESCRIPTION
            "An object containing the percentage of total calls carried over
            the route pattern by the trunk group."
        ::= { g3pkrpatEntry 13 }

    g3pkrpatTotalCalls	OBJECT-TYPE
        SYNTAX    INTEGER
        ACCESS    read-only
        STATUS    mandatory
        DESCRIPTION
            "An object containing the total number of calls carried by the route"
        ::= { g3pkrpatEntry 14 }

    g3pkrpatIndex	OBJECT-TYPE
        SYNTAX    INTEGER
        ACCESS    read-only
        STATUS    mandatory
        DESCRIPTION
            "An object containing an index for a route pattern/trunk group
            number combination to make a record unique."
        ::= { g3pkrpatEntry 15 }


    -- the g3secviolate group

    g3secviolateTage	OBJECT-TYPE
        SYNTAX    INTEGER
        ACCESS    read-only
        STATUS    mandatory
        DESCRIPTION
            "The number of timeticks since the security violations data was last
            extracted from the switch by the Proxy Agent.  This object
            along with the g3secviolateintvl object allows the Network Manager
            to determine the validity of the data in the cache and to control
            when the Proxy Agent extracts the data from the switch."
        ::= { g3secviolate 1 }

    g3secviolateTintvl	OBJECT-TYPE
        SYNTAX    INTEGER
        ACCESS    read-write
        STATUS    mandatory
        DESCRIPTION
            "An object containing the interval for which the security violations
            data extracted from the switch is considered valid by the
            Proxy Agent.  When a GET or GET-NEXT request for security violations
            objects is received by the agent it uses the g3secviolateage
            and g3secviolateintvl objects to determine whether it should refresh
            the cached secviolateTable.  If g3secviolatestmp + g3secviolateintvl
            is less than the current value of the sysUpTime object then the agent
            refreshes the secviolateTable cache.  In either case it responds to
            the requests it receives with the data it currently has in the cache."
        ::= { g3secviolate 2 }

    g3secviolateTdelay	OBJECT-TYPE
        SYNTAX    INTEGER
        ACCESS    read-only
        STATUS    mandatory
        DESCRIPTION
            "An object containing the delay encountered in updating
            the cached data."
        ::= { g3secviolate 3 }

    g3secviolateTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3secviolate 4 }

    g3secviolateTcount	OBJECT-TYPE
        SYNTAX    Gauge
        ACCESS    read-only
        STATUS    mandatory
        DESCRIPTION
            "A Gauge object containing the number of data records in the cache."
        ::= { g3secviolate 5 }

    g3secviolateTable	OBJECT-TYPE
        SYNTAX    SEQUENCE OF G3secviolateEntry
        ACCESS    not-accessible
        STATUS    mandatory
        DESCRIPTION
            "A list of g3secviolate entries."
        ::= { g3secviolate 6 }

    g3secviolateEntry	OBJECT-TYPE
        SYNTAX    G3secviolateEntry
        ACCESS    not-accessible
        STATUS    mandatory
        DESCRIPTION
            "A g3secviolate entry containing objects of the
            g3secviolate information sent by the switch."
        INDEX    { g3secviolatePortType }
        ::= { g3secviolateTable 1 }

    G3secviolateEntry ::= SEQUENCE {
        g3secviolatePortType
            DisplayString,
        g3secviolateYear
            INTEGER,
        g3secviolateMonth
            INTEGER,
        g3secviolateDay
            INTEGER,
        g3secviolateHour
            INTEGER,
        g3secviolateCountSince
            DisplayString,
        g3secviolateValidBC
            INTEGER,
        g3secviolateInvalidBC
            INTEGER,
        g3secviolateViolateBC
            INTEGER,
        g3secviolateStnValidSSC
            INTEGER,
        g3secviolateStnInvalidSSC
            INTEGER,
        g3secviolateTrkValidSSC
            INTEGER,
        g3secviolateTrkInvalidSSC
            INTEGER,
        g3secviolateTtlValidSSC
            INTEGER,
        g3secviolateTtlInvalidSSC
            INTEGER,
        g3secviolateTtlViolateSSC
            INTEGER,
        g3secviolateStnValidAC
            INTEGER,
        g3secviolateStnInvalidAC
            INTEGER,
        g3secviolateStnViolateAC
            INTEGER,
        g3secviolateTrkValidAC
            INTEGER,
        g3secviolateTrkInvalidAC
            INTEGER,
        g3secviolateTrkViolateAC
            INTEGER,
        g3secviolateRAValidAC
            INTEGER,
        g3secviolateRAInvalidAC
            INTEGER,
        g3secviolateRAViolateAC
            INTEGER,
        g3secviolateAtdValidAC
            INTEGER,
        g3secviolateAtdInvalidAC
            INTEGER,
        g3secviolateAtdViolateAC
            INTEGER,
        g3secviolateTtlValidAC
            INTEGER,
        g3secviolateTtlInvalidAC
            INTEGER,
        g3secviolateTtlViolateAC
            INTEGER,
        g3secviolateLoginSuccess
            INTEGER,
        g3secviolateInvalidAttempt
            INTEGER,
        g3secviolateInvalidID
            INTEGER,
        g3secviolateForceDsc
            INTEGER,
        g3secviolateSecViolate
            INTEGER,
        g3secviolateTrivialAttempt
            INTEGER
        }

    g3secviolatePortType	OBJECT-TYPE
        SYNTAX    DisplayString (SIZE (0..9))
        ACCESS    read-only
        STATUS    mandatory
        DESCRIPTION
            "An object containing the type of port to which the login was attempted."
        ::= { g3secviolateEntry 1 }

    g3secviolateYear	OBJECT-TYPE
        SYNTAX    INTEGER
        ACCESS    read-only
        STATUS    mandatory
        DESCRIPTION
            "An object containing the Year the command was executed."
        ::= { g3secviolateEntry 2 }

    g3secviolateMonth	OBJECT-TYPE
        SYNTAX    INTEGER
        ACCESS    read-only
        STATUS    mandatory
        DESCRIPTION
            "An object containing the Month the command was executed."
        ::= { g3secviolateEntry 3 }

    g3secviolateDay	OBJECT-TYPE
        SYNTAX    INTEGER
        ACCESS    read-only
        STATUS    mandatory
        DESCRIPTION
            "An object containing the Day the command was executed."
        ::= { g3secviolateEntry 4 }

    g3secviolateHour	OBJECT-TYPE
        SYNTAX    INTEGER
        ACCESS    read-only
        STATUS    mandatory
        DESCRIPTION
            "An object containing the Hour the command was executed."
        ::= { g3secviolateEntry 5 }

    g3secviolateCountSince	OBJECT-TYPE
        SYNTAX    DisplayString (SIZE (0..27))
        ACCESS    read-only
        STATUS    mandatory
        DESCRIPTION
            "An object containing the Year the command was executed."
        ::= { g3secviolateEntry 6 }

    g3secviolateValidBC	OBJECT-TYPE
        SYNTAX    INTEGER
        ACCESS    read-only
        STATUS    mandatory
        DESCRIPTION
            "An object containing the total number of times a user entered a
            valid barrier code."
        ::= { g3secviolateEntry 7 }

    g3secviolateInvalidBC	OBJECT-TYPE
        SYNTAX    INTEGER
        ACCESS    read-only
        STATUS    mandatory
        DESCRIPTION
            "An object containing the total number of times a user entered a
            invalid barrier code."
        ::= { g3secviolateEntry 8 }

    g3secviolateViolateBC	OBJECT-TYPE
        SYNTAX    INTEGER
        ACCESS    read-only
        STATUS    mandatory
        DESCRIPTION
            "An object containing the total number of security violations for
            barrier codes."
        ::= { g3secviolateEntry 9 }

    g3secviolateStnValidSSC	OBJECT-TYPE
        SYNTAX    INTEGER
        ACCESS    read-only
        STATUS    mandatory
        DESCRIPTION
            "An object containing the number of calls originating from stations
            that generated valid station security codes."
        ::= { g3secviolateEntry 10 }

    g3secviolateStnInvalidSSC	OBJECT-TYPE
        SYNTAX    INTEGER
        ACCESS    read-only
        STATUS    mandatory
        DESCRIPTION
            "An object containing the number of calls originating from stations
            that generated invalid station security codes."
        ::= { g3secviolateEntry 11 }

    g3secviolateTrkValidSSC	OBJECT-TYPE
        SYNTAX    INTEGER
        ACCESS    read-only
        STATUS    mandatory
        DESCRIPTION
            "An object containing the number of calls originating from trunks
            that generated valid station security codes."
        ::= { g3secviolateEntry 12 }

    g3secviolateTrkInvalidSSC	OBJECT-TYPE
        SYNTAX    INTEGER
        ACCESS    read-only
        STATUS    mandatory
        DESCRIPTION
            "An object containing the number of calls originating from trunks
            that generated invalid station security codes."
        ::= { g3secviolateEntry 13 }

    g3secviolateTtlValidSSC	OBJECT-TYPE
        SYNTAX    INTEGER
        ACCESS    read-only
        STATUS    mandatory
        DESCRIPTION
            "An object containing the number of total calls that generated
            valid station security codes."
        ::= { g3secviolateEntry 14 }

    g3secviolateTtlInvalidSSC	OBJECT-TYPE
        SYNTAX    INTEGER
        ACCESS    read-only
        STATUS    mandatory
        DESCRIPTION
            "An object containing the number of total calls that generated invalid
            station security codes."
        ::= { g3secviolateEntry 15 }

    g3secviolateTtlViolateSSC	OBJECT-TYPE
        SYNTAX    INTEGER
        ACCESS    read-only
        STATUS    mandatory
        DESCRIPTION
            "An object containing the number of total calls that generated
            station security violations."
        ::= { g3secviolateEntry 16 }

    g3secviolateStnValidAC	OBJECT-TYPE
        SYNTAX    INTEGER
        ACCESS    read-only
        STATUS    mandatory
        DESCRIPTION
            "An object containing the number of calls originating from stations
            that generated valid authorization codes."
        ::= { g3secviolateEntry 17 }

    g3secviolateStnInvalidAC	OBJECT-TYPE
        SYNTAX    INTEGER
        ACCESS    read-only
        STATUS    mandatory
        DESCRIPTION
            "An object containing the number of calls originating from stations
            that generated invalid authorization codes."
        ::= { g3secviolateEntry 18 }

    g3secviolateStnViolateAC	OBJECT-TYPE
        SYNTAX    INTEGER
        ACCESS    read-only
        STATUS    mandatory
        DESCRIPTION
            "An object containing the number of calls originating from stations
            that generated security violations for authorization codes."
        ::= { g3secviolateEntry 19 }

    g3secviolateTrkValidAC	OBJECT-TYPE
        SYNTAX    INTEGER
        ACCESS    read-only
        STATUS    mandatory
        DESCRIPTION
            "An object containing the number of calls originating from trunks
            that generated valid authorization codes."
        ::= { g3secviolateEntry 20 }

    g3secviolateTrkInvalidAC	OBJECT-TYPE
        SYNTAX    INTEGER
        ACCESS    read-only
        STATUS    mandatory
        DESCRIPTION
            "An object containing the number of calls originating from trunks
            that generated invalid authorization codes."
        ::= { g3secviolateEntry 21 }

    g3secviolateTrkViolateAC	OBJECT-TYPE
        SYNTAX    INTEGER
        ACCESS    read-only
        STATUS    mandatory
        DESCRIPTION
            "An object containing the number of calls originating from trunks
            that generated security violations for authorization codes."
        ::= { g3secviolateEntry 22 }

    g3secviolateRAValidAC	OBJECT-TYPE
        SYNTAX    INTEGER
        ACCESS    read-only
        STATUS    mandatory
        DESCRIPTION
            "An object containing the number of calls originating from remote
            access that generated valid authorization codes."
        ::= { g3secviolateEntry 23 }

    g3secviolateRAInvalidAC	OBJECT-TYPE
        SYNTAX    INTEGER
        ACCESS    read-only
        STATUS    mandatory
        DESCRIPTION
            "An object containing the number of calls originating from remote
            access that generated invalid authorization codes."
        ::= { g3secviolateEntry 24 }

    g3secviolateRAViolateAC	OBJECT-TYPE
        SYNTAX    INTEGER
        ACCESS    read-only
        STATUS    mandatory
        DESCRIPTION
            "An object containing the number of calls originating from remote
            access that generated security violations for authorization codes."
        ::= { g3secviolateEntry 25 }

    g3secviolateAtdValidAC	OBJECT-TYPE
        SYNTAX    INTEGER
        ACCESS    read-only
        STATUS    mandatory
        DESCRIPTION
            "An object containing the number of calls originating from attendants
            that generated valid authorization codes."
        ::= { g3secviolateEntry 26 }

    g3secviolateAtdInvalidAC	OBJECT-TYPE
        SYNTAX    INTEGER
        ACCESS    read-only
        STATUS    mandatory
        DESCRIPTION
            "An object containing the number of calls originating from attendants
            that generated invalid authorization codes."
        ::= { g3secviolateEntry 27 }

    g3secviolateAtdViolateAC	OBJECT-TYPE
        SYNTAX    INTEGER
        ACCESS    read-only
        STATUS    mandatory
        DESCRIPTION
            "An object containing the number of calls originating from attendants
            that generated security violations for authorization codes."
        ::= { g3secviolateEntry 28 }

    g3secviolateTtlValidAC	OBJECT-TYPE
        SYNTAX    INTEGER
        ACCESS    read-only
        STATUS    mandatory
        DESCRIPTION
            "An object containing the number of total calls that generated
            valid authorization codes."
        ::= { g3secviolateEntry 29 }

    g3secviolateTtlInvalidAC	OBJECT-TYPE
        SYNTAX    INTEGER
        ACCESS    read-only
        STATUS    mandatory
        DESCRIPTION
            "An object containing the number of total calls that generated invalid
            authorization codes."
        ::= { g3secviolateEntry 30 }

    g3secviolateTtlViolateAC	OBJECT-TYPE
        SYNTAX    INTEGER
        ACCESS    read-only
        STATUS    mandatory
        DESCRIPTION
            "An object containing the number of total calls that generated
            security violations for authorization codes."
        ::= { g3secviolateEntry 31 }

    g3secviolateLoginSuccess	OBJECT-TYPE
        SYNTAX    INTEGER
        ACCESS    read-only
        STATUS    mandatory
        DESCRIPTION
            "An object containing the total number of successful logins into
            the given port type."
        ::= { g3secviolateEntry 32 }

    g3secviolateInvalidAttempt	OBJECT-TYPE
        SYNTAX    INTEGER
        ACCESS    read-only
        STATUS    mandatory
        DESCRIPTION
            "An object containing the total number of login attempts where the
            login ID or password were invalid."
        ::= { g3secviolateEntry 33 }

    g3secviolateInvalidID	OBJECT-TYPE
        SYNTAX    INTEGER
        ACCESS    read-only
        STATUS    mandatory
        DESCRIPTION
            "An object containing the total number of login attempts where the
            login ID was invalid."
        ::= { g3secviolateEntry 34 }

    g3secviolateForceDsc	OBJECT-TYPE
        SYNTAX    INTEGER
        ACCESS    read-only
        STATUS    mandatory
        DESCRIPTION
            "An object containing the total number of login processes that
            were disconnected automatically by the switch because the threshold
            for consecutive invalid login attempts was exceeded."
        ::= { g3secviolateEntry 35 }

    g3secviolateSecViolate	OBJECT-TYPE
        SYNTAX    INTEGER
        ACCESS    read-only
        STATUS    mandatory
        DESCRIPTION
            "An object containing the total number of login security violations."
        ::= { g3secviolateEntry 36 }

    g3secviolateTrivialAttempt	OBJECT-TYPE
        SYNTAX    INTEGER
        ACCESS    read-only
        STATUS    mandatory
        DESCRIPTION
            "An object containing the total number of times a user connected
            to the system and gave no input to the login sequence."
        ::= { g3secviolateEntry 37 }


    -- the g3cbctrunk group

    g3cbctrunkTage	OBJECT-TYPE
        SYNTAX    INTEGER
        ACCESS    read-only
        STATUS    mandatory
        DESCRIPTION
            "The number of timeticks since the cbc trunk group data was last
            extracted from the switch by the Proxy Agent.  This object
            along with the g3cbctrunkintvl object allows the Network Manager
            to determine the validity of the data in the cache and to control
            when the Proxy Agent extracts the data from the switch."
        ::= { g3cbctrunk 1 }

    g3cbctrunkTintvl	OBJECT-TYPE
        SYNTAX    INTEGER
        ACCESS    read-write
        STATUS    mandatory
        DESCRIPTION
            "An object containing the interval for which the cbc trunk group
            data extracted from the switch is considered valid by the
            Proxy Agent.  When a GET or GET-NEXT request for cbc trunk group
            objects is received by the agent it uses the g3cbctrunkage
            and g3cbctrunkintvl objects to determine whether it should refresh
            the cached cbctrunkTable.  If g3cbctrunkstmp + g3cbctrunkintvl
            is less than the current value of the sysUpTime object then the agent
            refreshes the cbctrunkTable cache.  In either case it responds to
            the requests it receives with the data it currently has in the cache."
        ::= { g3cbctrunk 2 }

    g3cbctrunkTdelay	OBJECT-TYPE
        SYNTAX    INTEGER
        ACCESS    read-only
        STATUS    mandatory
        DESCRIPTION
            "An object containing the delay encountered in updating
            the cached data."
        ::= { g3cbctrunk 3 }

    g3cbctrunkTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3cbctrunk 4 }

    g3cbctrunkTcount	OBJECT-TYPE
        SYNTAX    Gauge
        ACCESS    read-only
        STATUS    mandatory
        DESCRIPTION
            "A Gauge object containing the number of data records in the cache."
        ::= { g3cbctrunk 5 }

    g3cbctrunkTable	OBJECT-TYPE
        SYNTAX    SEQUENCE OF G3cbctrunkEntry
        ACCESS    not-accessible
        STATUS    mandatory
        DESCRIPTION
            "A list of g3cbctrunk entries."
        ::= { g3cbctrunk 6 }

    g3cbctrunkEntry	OBJECT-TYPE
        SYNTAX    G3cbctrunkEntry
        ACCESS    not-accessible
        STATUS    mandatory
        DESCRIPTION
            "A g3cbctrunk entry containing objects of the
            g3cbctrunk information sent by the switch."
        INDEX    { g3cbctrunkTGNumber, g3cbctrunkServiceName }
        ::= { g3cbctrunkTable 1 }

    G3cbctrunkEntry ::= SEQUENCE {
        g3cbctrunkTGNumber
            INTEGER,
        g3cbctrunkServiceName
            DisplayString,
        g3cbctrunkYear
            INTEGER,
        g3cbctrunkMonth
            INTEGER,
        g3cbctrunkDay
            INTEGER,
        g3cbctrunkHour
            INTEGER,
        g3cbctrunkQueueSize
            INTEGER,
        g3cbctrunkCallsQueued
            INTEGER,
        g3cbctrunkQueueOvflw
            INTEGER,
        g3cbctrunkQueueAband
            INTEGER,
        g3cbctrunkTrunksOOS
            INTEGER,
        g3cbctrunkPlan1
            INTEGER,
        g3cbctrunkPlan2
            INTEGER,
        g3cbctrunkPlan3
            INTEGER,
        g3cbctrunkPlan4
            INTEGER,
        g3cbctrunkPlan5
            INTEGER,
        g3cbctrunkPlan6
            INTEGER,
        g3cbctrunkDur1
            INTEGER,
        g3cbctrunkDur2
            INTEGER,
        g3cbctrunkDur3
            INTEGER,
        g3cbctrunkDur4
            INTEGER,
        g3cbctrunkDur5
            INTEGER,
        g3cbctrunkDur6
            INTEGER,
        g3cbctrunkMinChan
            INTEGER,
        g3cbctrunkMaxChan
            INTEGER,
        g3cbctrunkMeasHour
            INTEGER,
        g3cbctrunkTotUsage
            INTEGER,
        g3cbctrunkTotSeize
            INTEGER,
        g3cbctrunkIncSeize
            INTEGER,
        g3cbctrunkTanSeize
            INTEGER,
        g3cbctrunkOvfTG
            INTEGER,
        g3cbctrunkOvfSF
            INTEGER,
        g3cbctrunkOvfMAX
            INTEGER,
        g3cbctrunkTBM
            INTEGER,
        g3cbctrunkATB
            INTEGER,
        g3cbctrunkOutBlk
            INTEGER
        }

    g3cbctrunkTGNumber	OBJECT-TYPE
        SYNTAX    INTEGER
        ACCESS    read-only
        STATUS    mandatory
        DESCRIPTION
            "An object containing the trunk group number."
        ::= { g3cbctrunkEntry 1 }

    g3cbctrunkServiceName	OBJECT-TYPE
        SYNTAX    DisplayString (SIZE (0..12))
        ACCESS    read-only
        STATUS    mandatory
        DESCRIPTION
            "An object containing the name of the services or features for
            which the associated measurements are being reported."
        ::= { g3cbctrunkEntry 2 }

    g3cbctrunkYear	OBJECT-TYPE
        SYNTAX    INTEGER
        ACCESS    read-only
        STATUS    mandatory
        DESCRIPTION
            "An object containing the Year the command was executed."
        ::= { g3cbctrunkEntry 3 }

    g3cbctrunkMonth	OBJECT-TYPE
        SYNTAX    INTEGER
        ACCESS    read-only
        STATUS    mandatory
        DESCRIPTION
            "An object containing the Month the command was executed."
        ::= { g3cbctrunkEntry 4 }

    g3cbctrunkDay	OBJECT-TYPE
        SYNTAX    INTEGER
        ACCESS    read-only
        STATUS    mandatory
        DESCRIPTION
            "An object containing the Day the command was executed."
        ::= { g3cbctrunkEntry 5 }

    g3cbctrunkHour	OBJECT-TYPE
        SYNTAX    INTEGER
        ACCESS    read-only
        STATUS    mandatory
        DESCRIPTION
            "An object containing the Hour the command was executed."
        ::= { g3cbctrunkEntry 6 }

    g3cbctrunkQueueSize	OBJECT-TYPE
        SYNTAX    INTEGER
        ACCESS    read-only
        STATUS    mandatory
        DESCRIPTION
            "An object containing the size of the trunk group queue."
        ::= { g3cbctrunkEntry 7 }

    g3cbctrunkCallsQueued	OBJECT-TYPE
        SYNTAX    INTEGER
        ACCESS    read-only
        STATUS    mandatory
        DESCRIPTION
            "An object containing the total number of calls that entered the
            queue."
        ::= { g3cbctrunkEntry 8 }

    g3cbctrunkQueueOvflw	OBJECT-TYPE
        SYNTAX    INTEGER
        ACCESS    read-only
        STATUS    mandatory
        DESCRIPTION
            "An object containing the total number of calls that were denied
            access to the trunk, found the queue full, and received reorder
            tone."
        ::= { g3cbctrunkEntry 9 }

    g3cbctrunkQueueAband	OBJECT-TYPE
        SYNTAX    INTEGER
        ACCESS    read-only
        STATUS    mandatory
        DESCRIPTION
            "An object containing the total number of calls that were removed
            from the queue by the system or the user."
        ::= { g3cbctrunkEntry 10 }

    g3cbctrunkTrunksOOS	OBJECT-TYPE
        SYNTAX    INTEGER
        ACCESS    read-only
        STATUS    mandatory
        DESCRIPTION
            "An object containing the total number of trunks in the group
            that were out-of-service when measurements were collected."
        ::= { g3cbctrunkEntry 11 }

    g3cbctrunkPlan1	OBJECT-TYPE
        SYNTAX    INTEGER
        ACCESS    read-only
        STATUS    mandatory
        DESCRIPTION
            "An object containing the first usage allocation plan number
            (if any)."
        ::= { g3cbctrunkEntry 12 }

    g3cbctrunkPlan2	OBJECT-TYPE
        SYNTAX    INTEGER
        ACCESS    read-only
        STATUS    mandatory
        DESCRIPTION
            "An object containing the second usage allocation plan number
            (if any)."
        ::= { g3cbctrunkEntry 13 }

    g3cbctrunkPlan3	OBJECT-TYPE
        SYNTAX    INTEGER
        ACCESS    read-only
        STATUS    mandatory
        DESCRIPTION
            "An object containing the third usage allocation plan number
            (if any)."
        ::= { g3cbctrunkEntry 14 }

    g3cbctrunkPlan4	OBJECT-TYPE
        SYNTAX    INTEGER
        ACCESS    read-only
        STATUS    mandatory
        DESCRIPTION
            "An object containing the fourth usage allocation plan number
            (if any)."
        ::= { g3cbctrunkEntry 15 }

    g3cbctrunkPlan5	OBJECT-TYPE
        SYNTAX    INTEGER
        ACCESS    read-only
        STATUS    mandatory
        DESCRIPTION
            "An object containing the fifth usage allocation plan number
            (if any)."
        ::= { g3cbctrunkEntry 16 }

    g3cbctrunkPlan6	OBJECT-TYPE
        SYNTAX    INTEGER
        ACCESS    read-only
        STATUS    mandatory
        DESCRIPTION
            "An object containing the sixth usage allocation plan number
            (if any)."
        ::= { g3cbctrunkEntry 17 }

    g3cbctrunkDur1	OBJECT-TYPE
        SYNTAX    INTEGER
        ACCESS    read-only
        STATUS    mandatory
        DESCRIPTION
            "An object containing the first usage allocation plan duration
            (in minutes) that the first plan was in effect  (if any)."
        ::= { g3cbctrunkEntry 18 }

    g3cbctrunkDur2	OBJECT-TYPE
        SYNTAX    INTEGER
        ACCESS    read-only
        STATUS    mandatory
        DESCRIPTION
            "An object containing the second usage allocation plan duration
            (in minutes) that the second plan was in effect  (if any)."
        ::= { g3cbctrunkEntry 19 }

    g3cbctrunkDur3	OBJECT-TYPE
        SYNTAX    INTEGER
        ACCESS    read-only
        STATUS    mandatory
        DESCRIPTION
            "An object containing the third usage allocation plan duration
            (in minutes) that the third plan was in effect  (if any)."
        ::= { g3cbctrunkEntry 20 }

    g3cbctrunkDur4	OBJECT-TYPE
        SYNTAX    INTEGER
        ACCESS    read-only
        STATUS    mandatory
        DESCRIPTION
            "An object containing the fourth usage allocation plan duration
            (in minutes) that the fourth plan was in effect  (if any)."
        ::= { g3cbctrunkEntry 21 }

    g3cbctrunkDur5	OBJECT-TYPE
        SYNTAX    INTEGER
        ACCESS    read-only
        STATUS    mandatory
        DESCRIPTION
            "An object containing the fifth usage allocation plan duration
            (in minutes) that the fifth plan was in effect  (if any)."
        ::= { g3cbctrunkEntry 22 }

    g3cbctrunkDur6	OBJECT-TYPE
        SYNTAX    INTEGER
        ACCESS    read-only
        STATUS    mandatory
        DESCRIPTION
            "An object containing the sixth usage allocation plan duration
            (in minutes) that the sixth plan was in effect  (if any)."
        ::= { g3cbctrunkEntry 23 }

    g3cbctrunkMinChan	OBJECT-TYPE
        SYNTAX    INTEGER
        ACCESS    read-only
        STATUS    mandatory
        DESCRIPTION
            "An object containing the minimum number of channels in the ISDN-PRI
            CBC trunk group allocated to the specified service/feature."
        ::= { g3cbctrunkEntry 24 }

    g3cbctrunkMaxChan	OBJECT-TYPE
        SYNTAX    INTEGER
        ACCESS    read-only
        STATUS    mandatory
        DESCRIPTION
            "An object containing the maximum number of channels in the ISDN-PRI
            CBC trunk group allocated to the specified service/feature."
        ::= { g3cbctrunkEntry 25 }

    g3cbctrunkMeasHour	OBJECT-TYPE
        SYNTAX    INTEGER
        ACCESS    read-only
        STATUS    mandatory
        DESCRIPTION
            "An object containing the Hour the measurement was taken."
        ::= { g3cbctrunkEntry 26 }

    g3cbctrunkTotUsage	OBJECT-TYPE
        SYNTAX    INTEGER
        ACCESS    read-only
        STATUS    mandatory
        DESCRIPTION
            "An object containing the sum of time (CCS) for all channels used
            by the specified service/feature."
        ::= { g3cbctrunkEntry 27 }

    g3cbctrunkTotSeize	OBJECT-TYPE
        SYNTAX    INTEGER
        ACCESS    read-only
        STATUS    mandatory
        DESCRIPTION
            "An object containing the total number of incoming and outgoing
            calls that requested the specified service/feature."
        ::= { g3cbctrunkEntry 28 }

    g3cbctrunkIncSeize	OBJECT-TYPE
        SYNTAX    INTEGER
        ACCESS    read-only
        STATUS    mandatory
        DESCRIPTION
            "An object containing the total number of incoming calls that
            requested the specified service/feature."
        ::= { g3cbctrunkEntry 29 }

    g3cbctrunkTanSeize	OBJECT-TYPE
        SYNTAX    INTEGER
        ACCESS    read-only
        STATUS    mandatory
        DESCRIPTION
            "An object containing the total number of trunk-to-trunk call
            seizures using the specified service/feature."
        ::= { g3cbctrunkEntry 30 }

    g3cbctrunkOvfTG	OBJECT-TYPE
        SYNTAX    INTEGER
        ACCESS    read-only
        STATUS    mandatory
        DESCRIPTION
            "An object containing the number of outgoing calls that requested
            the specified service/feature, but were not carried because the
            calls arrived to find no idle trunk members."
        ::= { g3cbctrunkEntry 31 }

    g3cbctrunkOvfSF	OBJECT-TYPE
        SYNTAX    INTEGER
        ACCESS    read-only
        STATUS    mandatory
        DESCRIPTION
            "An object containing the number of calls that requested the
            specified service/feature but were denied."
        ::= { g3cbctrunkEntry 32 }

    g3cbctrunkOvfMAX	OBJECT-TYPE
        SYNTAX    INTEGER
        ACCESS    read-only
        STATUS    mandatory
        DESCRIPTION
            "An object containing the number of calls that were not carried
            because they originated at a time when the specified service/feature
            had already used up its allotted maximum number of channels."
        ::= { g3cbctrunkEntry 33 }

    g3cbctrunkTBM	OBJECT-TYPE
        SYNTAX    INTEGER
        ACCESS    read-only
        STATUS    mandatory
        DESCRIPTION
            "An object containing the percentage of time during the polling
            interval that the number of channels in use by the specified
            service/feature is below the specified minimum."
        ::= { g3cbctrunkEntry 34 }

    g3cbctrunkATB	OBJECT-TYPE
        SYNTAX    INTEGER
        ACCESS    read-only
        STATUS    mandatory
        DESCRIPTION
            "An object containing the percentage of time during the measurement
            interval that the specified service/feature could not get a channel."
        ::= { g3cbctrunkEntry 35 }

    g3cbctrunkOutBlk	OBJECT-TYPE
        SYNTAX    INTEGER
        ACCESS    read-only
        STATUS    mandatory
        DESCRIPTION
            "An object containing the ratio of outgoing calls not carried
            for a specified service/feature to the outgoing calls offered
            by the service/feature."
        ::= { g3cbctrunkEntry 36 }


    -- the g3deftime group

    g3deftimeTage	OBJECT-TYPE
        SYNTAX    INTEGER
        ACCESS    read-only
        STATUS    mandatory
        DESCRIPTION
            "The number of timeticks since the definity time data was last
            extracted from the switch by the Proxy Agent.  This object
            along with the g3deftimeintvl object allows the Network Manager
            to determine the validity of the definity time data in the cache and to 
            control when the Proxy Agent extracts the data from the switch."
        ::= { g3deftime 1 }

    g3deftimeTintvl	OBJECT-TYPE
        SYNTAX    INTEGER
        ACCESS    read-write
        STATUS    mandatory
        DESCRIPTION
            "An object containing the interval for which the definity time data 
            extracted from the switch is considered valid by the Proxy Agent.  When
            a GET or GET-NEXT request for definity time objects is
            received by the agent it uses the g3deftimeage
            and g3deftimeintvl objects to determine whether it should refresh
            the cached deftimeTable.  If g3deftimestmp + g3deftimeintvl
            is less than the current value of the sysUpTime object then the agent
            refreshes the deftimeTable cache.  In either case it responds to
            the requests it receives with the data it currently has in the cache."
        ::= { g3deftime 2 }

    g3deftimeTdelay	OBJECT-TYPE
        SYNTAX    INTEGER
        ACCESS    read-only
        STATUS    mandatory
        DESCRIPTION
            "An object containing the delay encountered in updating
            the cached data."
        ::= { g3deftime 3 }

    g3deftimeTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3deftime 4 }

    g3deftimeDayOfMonth	OBJECT-TYPE
        SYNTAX    INTEGER
        ACCESS    read-only
        STATUS    mandatory
        DESCRIPTION
            "An INTEGER object containing the current system time Day of the
            Month (1-31)."
        ::= { g3deftime 5 }

    g3deftimeMonth	OBJECT-TYPE
        SYNTAX    DisplayString (SIZE (0..9))
        ACCESS    read-only
        STATUS    mandatory
        DESCRIPTION
            "A DisplayString Object that contains the name of the Month ('January',
            'February', 'March', 'April', 'May', 'June', 'July', 'August',
            'September', 'October', 'November', or 'December')."
        ::= { g3deftime 6 }

    g3deftimeYear	OBJECT-TYPE
        SYNTAX    INTEGER
        ACCESS    read-only
        STATUS    mandatory
        DESCRIPTION
            "An INTEGER object containing the current system time Year (0000-9999)."
        ::= { g3deftime 7 }

    g3deftimeDayOfWeek	OBJECT-TYPE
        SYNTAX    DisplayString (SIZE (0..9))
        ACCESS    read-only
        STATUS    mandatory
        DESCRIPTION
            "A DisplayString Object that contains the day of the week ('Monday',
            'Tuesday', 'Wednesday', 'Thursday', 'Friday', 'Saturday', or
            'Sunday')."
        ::= { g3deftime 8 }

    g3deftimeHour	OBJECT-TYPE
        SYNTAX    INTEGER
        ACCESS    read-only
        STATUS    mandatory
        DESCRIPTION
            "An INTEGER object containing the current system time Hour (0-23)."
        ::= { g3deftime 9 }

    g3deftimeMinute	OBJECT-TYPE
        SYNTAX    INTEGER
        ACCESS    read-only
        STATUS    mandatory
        DESCRIPTION
            "An INTEGER object containing the current system time Minute (0-59)."
        ::= { g3deftime 10 }

    g3deftimeSecond	OBJECT-TYPE
        SYNTAX    INTEGER
        ACCESS    read-only
        STATUS    mandatory
        DESCRIPTION
            "An INTEGER object containing the current system time Second (0-59)."
        ::= { g3deftime 11 }


    -- the g3trunkout group

    g3trunkoutTage	OBJECT-TYPE
        SYNTAX    INTEGER
        ACCESS    read-only
        STATUS    mandatory
        DESCRIPTION
            "The number of timeticks since the trunk outage data was last
            extracted from the switch by the Proxy Agent.  This object
            along with the g3trunkoutintvl object allows the Network Manager
            to determine the validity of the trunk outage data in the cache and to 
            control when the Proxy Agent extracts the data from the switch."
        ::= { g3trunkout 1 }

    g3trunkoutTintvl	OBJECT-TYPE
        SYNTAX    INTEGER
        ACCESS    read-write
        STATUS    mandatory
        DESCRIPTION
            "An object containing the interval for which the trunk outage
            data extracted from the switch is considered valid by the
            Proxy Agent.  When a GET or GET-NEXT request for trunk outage
            objects is received by the agent it uses the g3trunkoutage
            and g3trunkoutintvl objects to determine whether it should refresh
            the cached trunkoutTable.  If g3trunkoutstmp + g3trunkoutintvl
            is less than the current value of the sysUpTime object then the agent
            refreshes the trunkoutTable cache.  In either case it responds to
            the requests it receives with the data it currently has in the cache."
        ::= { g3trunkout 2 }

    g3trunkoutTdelay	OBJECT-TYPE
        SYNTAX    INTEGER
        ACCESS    read-only
        STATUS    mandatory
        DESCRIPTION
            "An object containing the delay encountered in updating
            the cached data."
        ::= { g3trunkout 3 }

    g3trunkoutTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3trunkout 4 }

    g3trunkoutTcount	OBJECT-TYPE
        SYNTAX    Gauge
        ACCESS    read-only
        STATUS    mandatory
        DESCRIPTION
            "A Gauge object containing the number of data records in the cache."
        ::= { g3trunkout 5 }

    g3trunkoutTable	OBJECT-TYPE
        SYNTAX    SEQUENCE OF G3trunkoutEntry
        ACCESS    not-accessible
        STATUS    mandatory
        DESCRIPTION
            "A list of g3trunkout entries."
        ::= { g3trunkout 6 }

    g3trunkoutEntry	OBJECT-TYPE
        SYNTAX    G3trunkoutEntry
        ACCESS    not-accessible
        STATUS    mandatory
        DESCRIPTION
            "A g3trunkout entry containing objects of the
            g3trunkout information sent by the switch."
        INDEX    { g3trunkoutTrunkGroup, g3trunkoutMember }
        ::= { g3trunkoutTable 1 }

    G3trunkoutEntry ::= SEQUENCE {
        g3trunkoutTrunkGroup
            INTEGER,
        g3trunkoutMember
            INTEGER,
        g3trunkoutYear
            INTEGER,
        g3trunkoutMonth
            INTEGER,
        g3trunkoutDay
            INTEGER,
        g3trunkoutHour
            INTEGER,
        g3trunkoutOutages
            INTEGER
        }

    g3trunkoutTrunkGroup	OBJECT-TYPE
        SYNTAX    INTEGER
        ACCESS    read-only
        STATUS    mandatory
        DESCRIPTION
            "An object containing the trunk group number."
        ::= { g3trunkoutEntry 1 }

    g3trunkoutMember	OBJECT-TYPE
        SYNTAX    INTEGER
        ACCESS    read-only
        STATUS    mandatory
        DESCRIPTION
            "An object containing the group member number."
        ::= { g3trunkoutEntry 2 }

    g3trunkoutYear	OBJECT-TYPE
        SYNTAX    INTEGER
        ACCESS    read-only
        STATUS    mandatory
        DESCRIPTION
            "An object containing the Year the command was executed."
        ::= { g3trunkoutEntry 3 }

    g3trunkoutMonth	OBJECT-TYPE
        SYNTAX    INTEGER
        ACCESS    read-only
        STATUS    mandatory
        DESCRIPTION
            "An object containing the Month the command was executed."
        ::= { g3trunkoutEntry 4 }

    g3trunkoutDay	OBJECT-TYPE
        SYNTAX    INTEGER
        ACCESS    read-only
        STATUS    mandatory
        DESCRIPTION
            "An object containing the Day the command was executed."
        ::= { g3trunkoutEntry 5 }

    g3trunkoutHour	OBJECT-TYPE
        SYNTAX    INTEGER
        ACCESS    read-only
        STATUS    mandatory
        DESCRIPTION
            "An object containing the Hour the command was executed."
        ::= { g3trunkoutEntry 6 }

    g3trunkoutOutages	OBJECT-TYPE
        SYNTAX    INTEGER
        ACCESS    read-only
        STATUS    mandatory
        DESCRIPTION
            "An object containing the number of times the group member is
            sampled as out of service over the measurement period."
        ::= { g3trunkoutEntry 7 }


    -- the g3trunklight group

    g3trunklightTage	OBJECT-TYPE
        SYNTAX    INTEGER
        ACCESS    read-only
        STATUS    mandatory
        DESCRIPTION
            "The number of timeticks since the lightly used trunk data was last
            extracted from the switch by the Proxy Agent.  This object
            along with the g3trunklightintvl object allows the Network Manager
            to determine the validity of the lightly used trunk data in the cache and 
            to control	when the Proxy Agent extracts the data from the switch."
        ::= { g3trunklight 1 }

    g3trunklightTintvl	OBJECT-TYPE
        SYNTAX    INTEGER
        ACCESS    read-write
        STATUS    mandatory
        DESCRIPTION
            "An object containing the interval for which the lightly used trunk
            data extracted from the switch is considered valid by the
            Proxy Agent.  When a GET or GET-NEXT request for lightly used trunk
            objects is received by the agent it uses the g3trunklightage
            and g3trunklightintvl objects to determine whether it should refresh
            the cached trunklightTable. If g3trunklightstmp+g3trunklightintvl
            is less than the current value of the sysUpTime object then the agent
            refreshes the trunklightTable cache.  In either case it responds to
            the requests it receives with the data it currently has in the cache."
        ::= { g3trunklight 2 }

    g3trunklightTdelay	OBJECT-TYPE
        SYNTAX    INTEGER
        ACCESS    read-only
        STATUS    mandatory
        DESCRIPTION
            "An object containing the delay encountered in updating
            the cached data."
        ::= { g3trunklight 3 }

    g3trunklightTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3trunklight 4 }

    g3trunklightTcount	OBJECT-TYPE
        SYNTAX    Gauge
        ACCESS    read-only
        STATUS    mandatory
        DESCRIPTION
            "A Gauge object containing the number of data records in the cache."
        ::= { g3trunklight 5 }

    g3trunklightTable	OBJECT-TYPE
        SYNTAX    SEQUENCE OF G3trunklightEntry
        ACCESS    not-accessible
        STATUS    mandatory
        DESCRIPTION
            "A list of g3trunklight entries."
        ::= { g3trunklight 6 }

    g3trunklightEntry	OBJECT-TYPE
        SYNTAX    G3trunklightEntry
        ACCESS    not-accessible
        STATUS    mandatory
        DESCRIPTION
            "A g3trunklight entry containing objects of the
            g3trunklight information sent by the switch."
        INDEX    { g3trunklightTrunkGroup, g3trunklightMember }
        ::= { g3trunklightTable 1 }

    G3trunklightEntry ::= SEQUENCE {
        g3trunklightTrunkGroup
            INTEGER,
        g3trunklightMember
            INTEGER,
        g3trunklightYear
            INTEGER,
        g3trunklightMonth
            INTEGER,
        g3trunklightDay
            INTEGER,
        g3trunklightHour
            INTEGER,
        g3trunklightCarried
            INTEGER
        }

    g3trunklightTrunkGroup	OBJECT-TYPE
        SYNTAX    INTEGER
        ACCESS    read-only
        STATUS    mandatory
        DESCRIPTION
            "An object containing the trunk group number."
        ::= { g3trunklightEntry 1 }

    g3trunklightMember	OBJECT-TYPE
        SYNTAX    INTEGER
        ACCESS    read-only
        STATUS    mandatory
        DESCRIPTION
            "An object containing the group member number."
        ::= { g3trunklightEntry 2 }

    g3trunklightYear	OBJECT-TYPE
        SYNTAX    INTEGER
        ACCESS    read-only
        STATUS    mandatory
        DESCRIPTION
            "An object containing the Year the command was executed."
        ::= { g3trunklightEntry 3 }

    g3trunklightMonth	OBJECT-TYPE
        SYNTAX    INTEGER
        ACCESS    read-only
        STATUS    mandatory
        DESCRIPTION
            "An object containing the Month the command was executed."
        ::= { g3trunklightEntry 4 }

    g3trunklightDay	OBJECT-TYPE
        SYNTAX    INTEGER
        ACCESS    read-only
        STATUS    mandatory
        DESCRIPTION
            "An object containing the Day the command was executed."
        ::= { g3trunklightEntry 5 }

    g3trunklightHour	OBJECT-TYPE
        SYNTAX    INTEGER
        ACCESS    read-only
        STATUS    mandatory
        DESCRIPTION
            "An object containing the Hour the command was executed."
        ::= { g3trunklightEntry 6 }

    g3trunklightCarried	OBJECT-TYPE
        SYNTAX    INTEGER
        ACCESS    read-only
        STATUS    mandatory
        DESCRIPTION
            "An object containing the number of calls carried on the trunk
            member over the measurement interval."
        ::= { g3trunklightEntry 7 }


    -- the g3loadtotal group

    g3loadtotalTage	OBJECT-TYPE
        SYNTAX    INTEGER
        ACCESS    read-only
        STATUS    mandatory
        DESCRIPTION
            "The number of timeticks since the data was
            last extracted from the switch by the Proxy Agent.  This object
            along with the g3loadtotalintvl object allows the Network Manager
            to determine the validity of the data in the cache and to control
            when the Proxy Agent extracts the data from the switch."
        ::= { g3loadtotal 1 }

    g3loadtotalTintvl	OBJECT-TYPE
        SYNTAX    INTEGER
        ACCESS    read-write
        STATUS    mandatory
        DESCRIPTION
            "An object containing the interval for which the
            data extracted from the switch is considered valid by the Proxy Agent.
            When a GET or GET-NEXT request for these objects is received by the
            agent it uses the g3loadtotalage and g3loadtotalintvl objects to
            determine whether it should refresh the cached loadtotalTable.  If
            g3loadtotalstmp + g3loadtotalintvl is less than the current value of
            the sysUpTime object then the agent refreshes the loadtotalTable
            cache.  In either case it responds to the requests it receives
            with the data it currently has in the cache."
        ::= { g3loadtotal 2 }

    g3loadtotalTdelay	OBJECT-TYPE
        SYNTAX    INTEGER
        ACCESS    read-only
        STATUS    mandatory
        DESCRIPTION
            "An object containing the delay encountered in updating
            the cached data."
        ::= { g3loadtotal 3 }

    g3loadtotalTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3loadtotal 4 }

    g3loadtotalTcount	OBJECT-TYPE
        SYNTAX    Gauge
        ACCESS    read-only
        STATUS    mandatory
        DESCRIPTION
            "A Gauge object containing the number of data records in the cache."
        ::= { g3loadtotal 5 }

    g3loadtotalTable	OBJECT-TYPE
        SYNTAX    SEQUENCE OF G3loadtotalEntry
        ACCESS    not-accessible
        STATUS    mandatory
        DESCRIPTION
            "A list of g3loadtotal entries."
        ::= { g3loadtotal 6 }

    g3loadtotalEntry	OBJECT-TYPE
        SYNTAX    G3loadtotalEntry
        ACCESS    not-accessible
        STATUS    mandatory
        DESCRIPTION
            "A g3loadtotal entry containing objects of the
            g3loadtotal information sent by the switch."
        INDEX    { g3loadtotalPNNumber }
        ::= { g3loadtotalTable 1 }

    G3loadtotalEntry ::= SEQUENCE {
        g3loadtotalPNNumber
            INTEGER,
        g3loadtotalYear
            INTEGER,
        g3loadtotalMonth
            INTEGER,
        g3loadtotalDay
            INTEGER,
        g3loadtotalHour
            INTEGER,
        g3loadtotalPNOccupancy
            INTEGER,
        g3loadtotalPNUtil
            INTEGER,
        g3loadtotalTDMOccupancy
            INTEGER,
        g3loadtotalMeasHour
            INTEGER
        }

    g3loadtotalPNNumber	OBJECT-TYPE
        SYNTAX    INTEGER
        ACCESS    read-only
        STATUS    mandatory
        DESCRIPTION
            "An object containing the Port Network number."
        ::= { g3loadtotalEntry 1 }

    g3loadtotalYear	OBJECT-TYPE
        SYNTAX    INTEGER
        ACCESS    read-only
        STATUS    mandatory
        DESCRIPTION
            "An object containing the Year the command was executed."
        ::= { g3loadtotalEntry 2 }

    g3loadtotalMonth	OBJECT-TYPE
        SYNTAX    INTEGER
        ACCESS    read-only
        STATUS    mandatory
        DESCRIPTION
            "An object containing the Month the command was executed."
        ::= { g3loadtotalEntry 3 }

    g3loadtotalDay	OBJECT-TYPE
        SYNTAX    INTEGER
        ACCESS    read-only
        STATUS    mandatory
        DESCRIPTION
            "An object containing the Day the command was executed."
        ::= { g3loadtotalEntry 4 }

    g3loadtotalHour	OBJECT-TYPE
        SYNTAX    INTEGER
        ACCESS    read-only
        STATUS    mandatory
        DESCRIPTION
            "An object containing the Hour the command was executed."
        ::= { g3loadtotalEntry 5 }

    g3loadtotalPNOccupancy	OBJECT-TYPE
        SYNTAX    INTEGER
        ACCESS    read-only
        STATUS    mandatory
        DESCRIPTION
            "An object containing the percentage of port network link
            occupancy."
        ::= { g3loadtotalEntry 6 }

    g3loadtotalPNUtil	OBJECT-TYPE
        SYNTAX    INTEGER
        ACCESS    read-only
        STATUS    mandatory
        DESCRIPTION
            "An object containing the percentage of the total capacity of the
            processor on the measured EI board."
        ::= { g3loadtotalEntry 7 }

    g3loadtotalTDMOccupancy	OBJECT-TYPE
        SYNTAX    INTEGER
        ACCESS    read-only
        STATUS    mandatory
        DESCRIPTION
            "An object containing the percentage of time division muliplexed
            occupancy."
        ::= { g3loadtotalEntry 8 }

    g3loadtotalMeasHour	OBJECT-TYPE
        SYNTAX    INTEGER
        ACCESS    read-only
        STATUS    mandatory
        DESCRIPTION
            "An object containing the hour the measurement was taken."
        ::= { g3loadtotalEntry 9 }


    -- the g3loadint group

    g3loadintTage	OBJECT-TYPE
        SYNTAX    INTEGER
        ACCESS    read-only
        STATUS    mandatory
        DESCRIPTION
            "The number of timeticks since the data was
            last extracted from the switch by the Proxy Agent.  This object
            along with the g3loadintintvl object allows the Network Manager
            to determine the validity of the data in the cache and to control
            when the Proxy Agent extracts the data from the switch."
        ::= { g3loadint 1 }

    g3loadintTintvl	OBJECT-TYPE
        SYNTAX    INTEGER
        ACCESS    read-write
        STATUS    mandatory
        DESCRIPTION
            "An object containing the interval for which the
            data extracted from the switch is considered valid by the Proxy Agent.
            When a GET or GET-NEXT request for these objects is received by the
            agent it uses the g3loadintage and g3loadintintvl objects to
            determine whether it should refresh the cached loadintTable.  If
            g3loadintstmp + g3loadintintvl is less than the current value of
            the sysUpTime object then the agent refreshes the loadintTable
            cache.  In either case it responds to the requests it receives
            with the data it currently has in the cache."
        ::= { g3loadint 2 }

    g3loadintTdelay	OBJECT-TYPE
        SYNTAX    INTEGER
        ACCESS    read-only
        STATUS    mandatory
        DESCRIPTION
            "An object containing the delay encountered in updating
            the cached data."
        ::= { g3loadint 3 }

    g3loadintTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3loadint 4 }

    g3loadintTcount	OBJECT-TYPE
        SYNTAX    Gauge
        ACCESS    read-only
        STATUS    mandatory
        DESCRIPTION
            "A Gauge object containing the number of data records in the cache."
        ::= { g3loadint 5 }

    g3loadintTable	OBJECT-TYPE
        SYNTAX    SEQUENCE OF G3loadintEntry
        ACCESS    not-accessible
        STATUS    mandatory
        DESCRIPTION
            "A list of g3loadint entries."
        ::= { g3loadint 6 }

    g3loadintEntry	OBJECT-TYPE
        SYNTAX    G3loadintEntry
        ACCESS    not-accessible
        STATUS    mandatory
        DESCRIPTION
            "A g3loadint entry containing objects of the
            g3loadint information sent by the switch."
        INDEX    { g3loadintPNNumber }
        ::= { g3loadintTable 1 }

    G3loadintEntry ::= SEQUENCE {
        g3loadintPNNumber
            INTEGER,
        g3loadintYear
            INTEGER,
        g3loadintMonth
            INTEGER,
        g3loadintDay
            INTEGER,
        g3loadintHour
            INTEGER,
        g3loadintIntIntraPNUse
            INTEGER,
        g3loadintIntIntraPNPeg
            INTEGER,
        g3loadintIntInterPNUse
            INTEGER,
        g3loadintIntInterPNPeg
            INTEGER,
        g3loadintMeasHour
            INTEGER
        }

    g3loadintPNNumber	OBJECT-TYPE
        SYNTAX    INTEGER
        ACCESS    read-only
        STATUS    mandatory
        DESCRIPTION
            "An object containing the Port Network number."
        ::= { g3loadintEntry 1 }

    g3loadintYear	OBJECT-TYPE
        SYNTAX    INTEGER
        ACCESS    read-only
        STATUS    mandatory
        DESCRIPTION
            "An object containing the Year the command was executed."
        ::= { g3loadintEntry 2 }

    g3loadintMonth	OBJECT-TYPE
        SYNTAX    INTEGER
        ACCESS    read-only
        STATUS    mandatory
        DESCRIPTION
            "An object containing the Month the command was executed."
        ::= { g3loadintEntry 3 }

    g3loadintDay	OBJECT-TYPE
        SYNTAX    INTEGER
        ACCESS    read-only
        STATUS    mandatory
        DESCRIPTION
            "An object containing the Day the command was executed."
        ::= { g3loadintEntry 4 }

    g3loadintHour	OBJECT-TYPE
        SYNTAX    INTEGER
        ACCESS    read-only
        STATUS    mandatory
        DESCRIPTION
            "An object containing the Hour the command was executed."
        ::= { g3loadintEntry 5 }

    g3loadintIntIntraPNUse	OBJECT-TYPE
        SYNTAX    INTEGER
        ACCESS    read-only
        STATUS    mandatory
        DESCRIPTION
            "An object containing the TDM time-slot usage caused by
            station-to-station calls between terminals on the same port
            network (displayed in CCS)."
        ::= { g3loadintEntry 6 }

    g3loadintIntIntraPNPeg	OBJECT-TYPE
        SYNTAX    INTEGER
        ACCESS    read-only
        STATUS    mandatory
        DESCRIPTION
            "An object containing the count of TDM time-slot seizures caused
            by station-to-station calls between terminals on the same PN."
        ::= { g3loadintEntry 7 }

    g3loadintIntInterPNUse	OBJECT-TYPE
        SYNTAX    INTEGER
        ACCESS    read-only
        STATUS    mandatory
        DESCRIPTION
            "An object containing the TDM time-slot usage caused by
            station-to-station calls between terminals on different port
            networks (in CCS)."
        ::= { g3loadintEntry 8 }

    g3loadintIntInterPNPeg	OBJECT-TYPE
        SYNTAX    INTEGER
        ACCESS    read-only
        STATUS    mandatory
        DESCRIPTION
            "An object containing the TDM time slot seizures caused by
            station-to-station calls between terminals on different PNs."
        ::= { g3loadintEntry 9 }

    g3loadintMeasHour	OBJECT-TYPE
        SYNTAX    INTEGER
        ACCESS    read-only
        STATUS    mandatory
        DESCRIPTION
            "An object containing the hour the measurement was taken."
        ::= { g3loadintEntry 10 }


    -- the g3loadinc group

    g3loadincTage	OBJECT-TYPE
        SYNTAX    INTEGER
        ACCESS    read-only
        STATUS    mandatory
        DESCRIPTION
            "The number of timeticks since the data was
            last extracted from the switch by the Proxy Agent.  This object
            along with the g3loadincintvl object allows the Network Manager
            to determine the validity of the data in the cache and to control
            when the Proxy Agent extracts the data from the switch."
        ::= { g3loadinc 1 }

    g3loadincTintvl	OBJECT-TYPE
        SYNTAX    INTEGER
        ACCESS    read-write
        STATUS    mandatory
        DESCRIPTION
            "An object containing the interval for which the
            data extracted from the switch is considered valid by the Proxy Agent.
            When a GET or GET-NEXT request for these objects is received by the
            agent it uses the g3loadincage and g3loadincintvl objects to
            determine whether it should refresh the cached loadincTable.  If
            g3loadincstmp + g3loadincintvl is less than the current value of
            the sysUpTime object then the agent refreshes the loadincTable
            cache.  In either case it responds to the requests it receives
            with the data it currently has in the cache."
        ::= { g3loadinc 2 }

    g3loadincTdelay	OBJECT-TYPE
        SYNTAX    INTEGER
        ACCESS    read-only
        STATUS    mandatory
        DESCRIPTION
            "An object containing the delay encountered in updating
            the cached data."
        ::= { g3loadinc 3 }

    g3loadincTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3loadinc 4 }

    g3loadincTcount	OBJECT-TYPE
        SYNTAX    Gauge
        ACCESS    read-only
        STATUS    mandatory
        DESCRIPTION
            "A Gauge object containing the number of data records in the cache."
        ::= { g3loadinc 5 }

    g3loadincTable	OBJECT-TYPE
        SYNTAX    SEQUENCE OF G3loadincEntry
        ACCESS    not-accessible
        STATUS    mandatory
        DESCRIPTION
            "A list of g3loadinc entries."
        ::= { g3loadinc 6 }

    g3loadincEntry	OBJECT-TYPE
        SYNTAX    G3loadincEntry
        ACCESS    not-accessible
        STATUS    mandatory
        DESCRIPTION
            "A g3loadinc entry containing objects of the
            g3loadinc information sent by the switch."
        INDEX    { g3loadincPNNumber }
        ::= { g3loadincTable 1 }

    G3loadincEntry ::= SEQUENCE {
        g3loadincPNNumber
            INTEGER,
        g3loadincYear
            INTEGER,
        g3loadincMonth
            INTEGER,
        g3loadincDay
            INTEGER,
        g3loadincHour
            INTEGER,
        g3loadincIncIntraPNUse
            INTEGER,
        g3loadincIncIntraPNPeg
            INTEGER,
        g3loadincIncIncomingUse
            INTEGER,
        g3loadincIncIncomingPeg
            INTEGER,
        g3loadincIncOutgoingUse
            INTEGER,
        g3loadincIncOutgoingPeg
            INTEGER,
        g3loadincMeasHour
            INTEGER
        }

    g3loadincPNNumber	OBJECT-TYPE
        SYNTAX    INTEGER
        ACCESS    read-only
        STATUS    mandatory
        DESCRIPTION
            "An object containing the Port Network number."
        ::= { g3loadincEntry 1 }

    g3loadincYear	OBJECT-TYPE
        SYNTAX    INTEGER
        ACCESS    read-only
        STATUS    mandatory
        DESCRIPTION
            "An object containing the Year the command was executed."
        ::= { g3loadincEntry 2 }

    g3loadincMonth	OBJECT-TYPE
        SYNTAX    INTEGER
        ACCESS    read-only
        STATUS    mandatory
        DESCRIPTION
            "An object containing the Month the command was executed."
        ::= { g3loadincEntry 3 }

    g3loadincDay	OBJECT-TYPE
        SYNTAX    INTEGER
        ACCESS    read-only
        STATUS    mandatory
        DESCRIPTION
            "An object containing the Day the command was executed."
        ::= { g3loadincEntry 4 }

    g3loadincHour	OBJECT-TYPE
        SYNTAX    INTEGER
        ACCESS    read-only
        STATUS    mandatory
        DESCRIPTION
            "An object containing the Hour the command was executed."
        ::= { g3loadincEntry 5 }

    g3loadincIncIntraPNUse	OBJECT-TYPE
        SYNTAX    INTEGER
        ACCESS    read-only
        STATUS    mandatory
        DESCRIPTION
            "An object containing the TDM time-slot usage caused by incoming
            trunk calls to a station on the same port network (in CCS)."
        ::= { g3loadincEntry 6 }

    g3loadincIncIntraPNPeg	OBJECT-TYPE
        SYNTAX    INTEGER
        ACCESS    read-only
        STATUS    mandatory
        DESCRIPTION
            "An object containing the count of TDM time-slot seizures caused
            by incoming trunk calls to a station on the same port network."
        ::= { g3loadincEntry 7 }

    g3loadincIncIncomingUse	OBJECT-TYPE
        SYNTAX    INTEGER
        ACCESS    read-only
        STATUS    mandatory
        DESCRIPTION
            "An object containing the TDM time-slot usage caused by calls to
            a station on the port network from an incoming trunk on another
            port network (in CCS)."
        ::= { g3loadincEntry 8 }

    g3loadincIncIncomingPeg	OBJECT-TYPE
        SYNTAX    INTEGER
        ACCESS    read-only
        STATUS    mandatory
        DESCRIPTION
            "An object containing the count of TDM time-slot seizures caused
            by calls to a station on the port network from an incoming trunk
            on another port network."
        ::= { g3loadincEntry 9 }

    g3loadincIncOutgoingUse	OBJECT-TYPE
        SYNTAX    INTEGER
        ACCESS    read-only
        STATUS    mandatory
        DESCRIPTION
            "An object containing the TDM time-slot usage caused by calls to
            a station on another port network from an incoming trunk on the
            measured port network (in CCS)."
        ::= { g3loadincEntry 10 }

    g3loadincIncOutgoingPeg	OBJECT-TYPE
        SYNTAX    INTEGER
        ACCESS    read-only
        STATUS    mandatory
        DESCRIPTION
            "An object containing the count of TDM time-slot seizures caused by
            calls to a station on another port network from an incoming trunk
            on the measured port network."
        ::= { g3loadincEntry 11 }

    g3loadincMeasHour	OBJECT-TYPE
        SYNTAX    INTEGER
        ACCESS    read-only
        STATUS    mandatory
        DESCRIPTION
            "An object containing the hour the measurement was taken."
        ::= { g3loadincEntry 12 }


    -- the g3loadout group

    g3loadoutTage	OBJECT-TYPE
        SYNTAX    INTEGER
        ACCESS    read-only
        STATUS    mandatory
        DESCRIPTION
            "The number of timeticks since the data was
            last extracted from the switch by the Proxy Agent.  This object
            along with the g3loadoutintvl object allows the Network Manager
            to determine the validity of the data in the cache and to control
            when the Proxy Agent extracts the data from the switch."
        ::= { g3loadout 1 }

    g3loadoutTintvl	OBJECT-TYPE
        SYNTAX    INTEGER
        ACCESS    read-write
        STATUS    mandatory
        DESCRIPTION
            "An object containing the interval for which the
            data extracted from the switch is considered valid by the Proxy Agent.
            When a GET or GET-NEXT request for these objects is received by the
            agent it uses the g3loadoutage and g3loadoutintvl objects to
            determine whether it should refresh the cached loadoutTable.  If
            g3loadoutstmp + g3loadoutintvl is less than the current value of
            the sysUpTime object then the agent refreshes the loadoutTable
            cache.  In either case it responds to the requests it receives
            with the data it currently has in the cache."
        ::= { g3loadout 2 }

    g3loadoutTdelay	OBJECT-TYPE
        SYNTAX    INTEGER
        ACCESS    read-only
        STATUS    mandatory
        DESCRIPTION
            "An object containing the delay encountered in updating
            the cached data."
        ::= { g3loadout 3 }

    g3loadoutTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3loadout 4 }

    g3loadoutTcount	OBJECT-TYPE
        SYNTAX    Gauge
        ACCESS    read-only
        STATUS    mandatory
        DESCRIPTION
            "A Gauge object containing the number of data records in the cache."
        ::= { g3loadout 5 }

    g3loadoutTable	OBJECT-TYPE
        SYNTAX    SEQUENCE OF G3loadoutEntry
        ACCESS    not-accessible
        STATUS    mandatory
        DESCRIPTION
            "A list of g3loadout entries."
        ::= { g3loadout 6 }

    g3loadoutEntry	OBJECT-TYPE
        SYNTAX    G3loadoutEntry
        ACCESS    not-accessible
        STATUS    mandatory
        DESCRIPTION
            "A g3loadout entry containing objects of the
            g3loadout information sent by the switch."
        INDEX    { g3loadoutPNNumber }
        ::= { g3loadoutTable 1 }

    G3loadoutEntry ::= SEQUENCE {
        g3loadoutPNNumber
            INTEGER,
        g3loadoutYear
            INTEGER,
        g3loadoutMonth
            INTEGER,
        g3loadoutDay
            INTEGER,
        g3loadoutHour
            INTEGER,
        g3loadoutOutIntraPNUse
            INTEGER,
        g3loadoutOutIntraPNPeg
            INTEGER,
        g3loadoutOutIncomingUse
            INTEGER,
        g3loadoutOutIncomingPeg
            INTEGER,
        g3loadoutOutOutgoingUse
            INTEGER,
        g3loadoutOutOutgoingPeg
            INTEGER,
        g3loadoutMeasHour
            INTEGER
        }

    g3loadoutPNNumber	OBJECT-TYPE
        SYNTAX    INTEGER
        ACCESS    read-only
        STATUS    mandatory
        DESCRIPTION
            "An object containing the Port Network number."
        ::= { g3loadoutEntry 1 }

    g3loadoutYear	OBJECT-TYPE
        SYNTAX    INTEGER
        ACCESS    read-only
        STATUS    mandatory
        DESCRIPTION
            "An object containing the Year the command was executed."
        ::= { g3loadoutEntry 2 }

    g3loadoutMonth	OBJECT-TYPE
        SYNTAX    INTEGER
        ACCESS    read-only
        STATUS    mandatory
        DESCRIPTION
            "An object containing the Month the command was executed."
        ::= { g3loadoutEntry 3 }

    g3loadoutDay	OBJECT-TYPE
        SYNTAX    INTEGER
        ACCESS    read-only
        STATUS    mandatory
        DESCRIPTION
            "An object containing the Day the command was executed."
        ::= { g3loadoutEntry 4 }

    g3loadoutHour	OBJECT-TYPE
        SYNTAX    INTEGER
        ACCESS    read-only
        STATUS    mandatory
        DESCRIPTION
            "An object containing the Hour the command was executed."
        ::= { g3loadoutEntry 5 }

    g3loadoutOutIntraPNUse	OBJECT-TYPE
        SYNTAX    INTEGER
        ACCESS    read-only
        STATUS    mandatory
        DESCRIPTION
            "An object containing the TDM time-slot usage caused by outgoing
            calls made by stations on the measured port network and serviced by
            outgoing trunks on the same port network (in CCS)."
        ::= { g3loadoutEntry 6 }

    g3loadoutOutIntraPNPeg	OBJECT-TYPE
        SYNTAX    INTEGER
        ACCESS    read-only
        STATUS    mandatory
        DESCRIPTION
            "An object containing the count of TDM time-slot seizures caused
            by outgoing calls made by stations on the measured port network
            and serviced by outgoing trunks on the same port network."
        ::= { g3loadoutEntry 7 }

    g3loadoutOutIncomingUse	OBJECT-TYPE
        SYNTAX    INTEGER
        ACCESS    read-only
        STATUS    mandatory
        DESCRIPTION
            "An object containing the TDM time-slot usage resulting from
            outgoing calls originated at stations on another port network
            but serviced by trunks on the port network being measured (in CCS)."
        ::= { g3loadoutEntry 8 }

    g3loadoutOutIncomingPeg	OBJECT-TYPE
        SYNTAX    INTEGER
        ACCESS    read-only
        STATUS    mandatory
        DESCRIPTION
            "An object containing the count of TDM time-slot seizures resulting
            from outgoing calls originated at stations on another port
            network, but serviced by trunks on the port network being measured."
        ::= { g3loadoutEntry 9 }

    g3loadoutOutOutgoingUse	OBJECT-TYPE
        SYNTAX    INTEGER
        ACCESS    read-only
        STATUS    mandatory
        DESCRIPTION
            "An object containing the TDM time-slot usage resulting from
            outgoing calls originated at stations on the port network being
            measured, but serviced by trunks on another port network (in CCS)."
        ::= { g3loadoutEntry 10 }

    g3loadoutOutOutgoingPeg	OBJECT-TYPE
        SYNTAX    INTEGER
        ACCESS    read-only
        STATUS    mandatory
        DESCRIPTION
            "An object containing the count of TDM time-slot seizures resulting
            from outgoing calls originated at stations on the port network
            being measured, but serviced by trunks on another port network."
        ::= { g3loadoutEntry 11 }

    g3loadoutMeasHour	OBJECT-TYPE
        SYNTAX    INTEGER
        ACCESS    read-only
        STATUS    mandatory
        DESCRIPTION
            "An object containing the hour the measurement was taken."
        ::= { g3loadoutEntry 12 }


    -- the g3loadtan group

    g3loadtanTage	OBJECT-TYPE
        SYNTAX    INTEGER
        ACCESS    read-only
        STATUS    mandatory
        DESCRIPTION
            "The number of timeticks since the tandem load data was
            last extracted from the switch by the Proxy Agent.  This object
            along with the g3loadtanintvl object allows the Network Manager
            to determine the validity of the tandem load data in the cache and to 
            control when the Proxy Agent extracts the data from the switch."
        ::= { g3loadtan 1 }

    g3loadtanTintvl	OBJECT-TYPE
        SYNTAX    INTEGER
        ACCESS    read-write
        STATUS    mandatory
        DESCRIPTION
            "An object containing the interval for which the tandem load
            data extracted from the switch is considered valid by the Proxy Agent.
            When a GET or GET-NEXT request for the tandem load objects is received by 
            the	agent it uses the g3loadtanage and g3loadtanintvl objects to
            determine whether it should refresh the cached loadtanTable.  If
            g3loadtanstmp + g3loadtanintvl is less than the current value of
            the sysUpTime object then the agent refreshes the loadtanTable
            cache.  In either case it responds to the requests it receives
            with the data it currently has in the cache."
        ::= { g3loadtan 2 }

    g3loadtanTdelay	OBJECT-TYPE
        SYNTAX    INTEGER
        ACCESS    read-only
        STATUS    mandatory
        DESCRIPTION
            "An object containing the delay encountered in updating
            the cached data."
        ::= { g3loadtan 3 }

    g3loadtanTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3loadtan 4 }

    g3loadtanTcount	OBJECT-TYPE
        SYNTAX    Gauge
        ACCESS    read-only
        STATUS    mandatory
        DESCRIPTION
            "A Gauge object containing the number of data records in the cache."
        ::= { g3loadtan 5 }

    g3loadtanTable	OBJECT-TYPE
        SYNTAX    SEQUENCE OF G3loadtanEntry
        ACCESS    not-accessible
        STATUS    mandatory
        DESCRIPTION
            "A list of g3loadtan entries."
        ::= { g3loadtan 6 }

    g3loadtanEntry	OBJECT-TYPE
        SYNTAX    G3loadtanEntry
        ACCESS    not-accessible
        STATUS    mandatory
        DESCRIPTION
            "A g3loadtan entry containing objects of the
            g3loadtan information sent by the switch."
        INDEX    { g3loadtanPNNumber }
        ::= { g3loadtanTable 1 }

    G3loadtanEntry ::= SEQUENCE {
        g3loadtanPNNumber
            INTEGER,
        g3loadtanYear
            INTEGER,
        g3loadtanMonth
            INTEGER,
        g3loadtanDay
            INTEGER,
        g3loadtanHour
            INTEGER,
        g3loadtanTanIntraPNUse
            INTEGER,
        g3loadtanTanIntraPNPeg
            INTEGER,
        g3loadtanTanIncomingUse
            INTEGER,
        g3loadtanTanIncomingPeg
            INTEGER,
        g3loadtanTanOutgoingUse
            INTEGER,
        g3loadtanTanOutgoingPeg
            INTEGER,
        g3loadtanMeasHour
            INTEGER
        }

    g3loadtanPNNumber	OBJECT-TYPE
        SYNTAX    INTEGER
        ACCESS    read-only
        STATUS    mandatory
        DESCRIPTION
            "An object containing the Port Network number."
        ::= { g3loadtanEntry 1 }

    g3loadtanYear	OBJECT-TYPE
        SYNTAX    INTEGER
        ACCESS    read-only
        STATUS    mandatory
        DESCRIPTION
            "An object containing the Year the command was executed."
        ::= { g3loadtanEntry 2 }

    g3loadtanMonth	OBJECT-TYPE
        SYNTAX    INTEGER
        ACCESS    read-only
        STATUS    mandatory
        DESCRIPTION
            "An object containing the Month the command was executed."
        ::= { g3loadtanEntry 3 }

    g3loadtanDay	OBJECT-TYPE
        SYNTAX    INTEGER
        ACCESS    read-only
        STATUS    mandatory
        DESCRIPTION
            "An object containing the Day the command was executed."
        ::= { g3loadtanEntry 4 }

    g3loadtanHour	OBJECT-TYPE
        SYNTAX    INTEGER
        ACCESS    read-only
        STATUS    mandatory
        DESCRIPTION
            "An object containing the Hour the command was executed."
        ::= { g3loadtanEntry 5 }

    g3loadtanTanIntraPNUse	OBJECT-TYPE
        SYNTAX    INTEGER
        ACCESS    read-only
        STATUS    mandatory
        DESCRIPTION
            "An object containing the TDM usage caused by tandem trunk calls
            originating and terminating on the port network being measured
            (in CCS)."
        ::= { g3loadtanEntry 6 }

    g3loadtanTanIntraPNPeg	OBJECT-TYPE
        SYNTAX    INTEGER
        ACCESS    read-only
        STATUS    mandatory
        DESCRIPTION
            "An object containing the count of TDM time-slot seizures caused
            by tandem trunk calls originating and terminating on the port
            network being measured."
        ::= { g3loadtanEntry 7 }

    g3loadtanTanIncomingUse	OBJECT-TYPE
        SYNTAX    INTEGER
        ACCESS    read-only
        STATUS    mandatory
        DESCRIPTION
            "An object containing the TDM usage resulting from tandem trunk
            calls originating on another port network, but terminating on the
            port network being measured (in CCS)."
        ::= { g3loadtanEntry 8 }

    g3loadtanTanIncomingPeg	OBJECT-TYPE
        SYNTAX    INTEGER
        ACCESS    read-only
        STATUS    mandatory
        DESCRIPTION
            "An object containing the count of TDM time-slot seizures resulting
            from tandem trunk calls originating on another port network, but
            terminating on the port network being measured.
            that is, the number of times a PN link time-slot is denied."
        ::= { g3loadtanEntry 9 }

    g3loadtanTanOutgoingUse	OBJECT-TYPE
        SYNTAX    INTEGER
        ACCESS    read-only
        STATUS    mandatory
        DESCRIPTION
            "An object containing the TDM usage resulting from tandem trunk
            calls originating on the port network being measured, but
            terminating on another port network (in CCS)."
        ::= { g3loadtanEntry 10 }

    g3loadtanTanOutgoingPeg	OBJECT-TYPE
        SYNTAX    INTEGER
        ACCESS    read-only
        STATUS    mandatory
        DESCRIPTION
            "An object containing the count of TDM time-slot seizures resulting
            from tandem trunk calls originating on the port network being
            measured, but terminating on another port network."
        ::= { g3loadtanEntry 11 }

    g3loadtanMeasHour	OBJECT-TYPE
        SYNTAX    INTEGER
        ACCESS    read-only
        STATUS    mandatory
        DESCRIPTION
            "An object containing the hour the measurement was taken."
        ::= { g3loadtanEntry 12 }


    -- the g3pkloadtotal group

    g3pkloadtotalTage	OBJECT-TYPE
        SYNTAX    INTEGER
        ACCESS    read-only
        STATUS    mandatory
        DESCRIPTION
            "The number of timeticks since the data was
            last extracted from the switch by the Proxy Agent.  This object
            along with the g3pkloadtotalintvl object allows the Network Manager
            to determine the validity of the data in the cache and to control
            when the Proxy Agent extracts the data from the switch."
        ::= { g3pkloadtotal 1 }

    g3pkloadtotalTintvl	OBJECT-TYPE
        SYNTAX    INTEGER
        ACCESS    read-write
        STATUS    mandatory
        DESCRIPTION
            "An object containing the interval for which the
            data extracted from the switch is considered valid by the Proxy Agent.
            When a GET or GET-NEXT request for these objects is received by the
            agent it uses the g3pkloadtotalage and g3pkloadtotalintvl objects to
            determine whether it should refresh the cached pkloadtotalTable.  If
            g3pkloadtotalstmp + g3pkloadtotalintvl is less than the current value of
            the sysUpTime object then the agent refreshes the pkloadtotalTable
            cache.  In either case it responds to the requests it receives
            with the data it currently has in the cache."
        ::= { g3pkloadtotal 2 }

    g3pkloadtotalTdelay	OBJECT-TYPE
        SYNTAX    INTEGER
        ACCESS    read-only
        STATUS    mandatory
        DESCRIPTION
            "An object containing the delay encountered in updating
            the cached data."
        ::= { g3pkloadtotal 3 }

    g3pkloadtotalTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3pkloadtotal 4 }

    g3pkloadtotalTcount	OBJECT-TYPE
        SYNTAX    Gauge
        ACCESS    read-only
        STATUS    mandatory
        DESCRIPTION
            "A Gauge object containing the number of data records in the cache."
        ::= { g3pkloadtotal 5 }

    g3pkloadtotalTable	OBJECT-TYPE
        SYNTAX    SEQUENCE OF G3pkloadtotalEntry
        ACCESS    not-accessible
        STATUS    mandatory
        DESCRIPTION
            "A list of g3pkloadtotal entries."
        ::= { g3pkloadtotal 6 }

    g3pkloadtotalEntry	OBJECT-TYPE
        SYNTAX    G3pkloadtotalEntry
        ACCESS    not-accessible
        STATUS    mandatory
        DESCRIPTION
            "A g3pkloadtotal entry containing objects of the
            g3pkloadtotal information sent by the switch."
        INDEX    { g3pkloadtotalPNNumber }
        ::= { g3pkloadtotalTable 1 }

    G3pkloadtotalEntry ::= SEQUENCE {
        g3pkloadtotalPNNumber
            INTEGER,
        g3pkloadtotalYear
            INTEGER,
        g3pkloadtotalMonth
            INTEGER,
        g3pkloadtotalDay
            INTEGER,
        g3pkloadtotalHour
            INTEGER,
        g3pkloadtotalPNOccupancy
            INTEGER,
        g3pkloadtotalPNUtil
            INTEGER,
        g3pkloadtotalTDMOccupancy
            INTEGER,
        g3pkloadtotalMeasHour
            INTEGER
        }

    g3pkloadtotalPNNumber	OBJECT-TYPE
        SYNTAX    INTEGER
        ACCESS    read-only
        STATUS    mandatory
        DESCRIPTION
            "An object containing the Port Network number."
        ::= { g3pkloadtotalEntry 1 }

    g3pkloadtotalYear	OBJECT-TYPE
        SYNTAX    INTEGER
        ACCESS    read-only
        STATUS    mandatory
        DESCRIPTION
            "An object containing the Year the command was executed."
        ::= { g3pkloadtotalEntry 2 }

    g3pkloadtotalMonth	OBJECT-TYPE
        SYNTAX    INTEGER
        ACCESS    read-only
        STATUS    mandatory
        DESCRIPTION
            "An object containing the Month the command was executed."
        ::= { g3pkloadtotalEntry 3 }

    g3pkloadtotalDay	OBJECT-TYPE
        SYNTAX    INTEGER
        ACCESS    read-only
        STATUS    mandatory
        DESCRIPTION
            "An object containing the Day the command was executed."
        ::= { g3pkloadtotalEntry 4 }

    g3pkloadtotalHour	OBJECT-TYPE
        SYNTAX    INTEGER
        ACCESS    read-only
        STATUS    mandatory
        DESCRIPTION
            "An object containing the Hour the command was executed."
        ::= { g3pkloadtotalEntry 5 }

    g3pkloadtotalPNOccupancy	OBJECT-TYPE
        SYNTAX    INTEGER
        ACCESS    read-only
        STATUS    mandatory
        DESCRIPTION
            "An object containing the percentage of port network link
            occupancy."
        ::= { g3pkloadtotalEntry 6 }

    g3pkloadtotalPNUtil	OBJECT-TYPE
        SYNTAX    INTEGER
        ACCESS    read-only
        STATUS    mandatory
        DESCRIPTION
            "An object containing the percentage of the total capacity of the
            processor on the measured EI board (this field no longer is no
            longer populated)."
        ::= { g3pkloadtotalEntry 7 }

    g3pkloadtotalTDMOccupancy	OBJECT-TYPE
        SYNTAX    INTEGER
        ACCESS    read-only
        STATUS    mandatory
        DESCRIPTION
            "An object containing the percentage of time division muliplexed
            occupancy."
        ::= { g3pkloadtotalEntry 8 }

    g3pkloadtotalMeasHour	OBJECT-TYPE
        SYNTAX    INTEGER
        ACCESS    read-only
        STATUS    mandatory
        DESCRIPTION
            "An object containing the hour the measurement was taken."
        ::= { g3pkloadtotalEntry 9 }


    -- the g3pkloadint group

    g3pkloadintTage	OBJECT-TYPE
        SYNTAX    INTEGER
        ACCESS    read-only
        STATUS    mandatory
        DESCRIPTION
            "The number of timeticks since the data was
            last extracted from the switch by the Proxy Agent.  This object
            along with the g3pkloadintintvl object allows the Network Manager
            to determine the validity of the data in the cache and to control
            when the Proxy Agent extracts the data from the switch."
        ::= { g3pkloadint 1 }

    g3pkloadintTintvl	OBJECT-TYPE
        SYNTAX    INTEGER
        ACCESS    read-write
        STATUS    mandatory
        DESCRIPTION
            "An object containing the interval for which the
            data extracted from the switch is considered valid by the Proxy Agent.
            When a GET or GET-NEXT request for these objects is received by the
            agent it uses the g3pkloadintage and g3pkloadintintvl objects to
            determine whether it should refresh the cached pkloadintTable.  If
            g3pkloadintstmp + g3pkloadintintvl is less than the current value of
            the sysUpTime object then the agent refreshes the pkloadintTable
            cache.  In either case it responds to the requests it receives
            with the data it currently has in the cache."
        ::= { g3pkloadint 2 }

    g3pkloadintTdelay	OBJECT-TYPE
        SYNTAX    INTEGER
        ACCESS    read-only
        STATUS    mandatory
        DESCRIPTION
            "An object containing the delay encountered in updating
            the cached data."
        ::= { g3pkloadint 3 }

    g3pkloadintTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3pkloadint 4 }

    g3pkloadintTcount	OBJECT-TYPE
        SYNTAX    Gauge
        ACCESS    read-only
        STATUS    mandatory
        DESCRIPTION
            "A Gauge object containing the number of data records in the cache."
        ::= { g3pkloadint 5 }

    g3pkloadintTable	OBJECT-TYPE
        SYNTAX    SEQUENCE OF G3pkloadintEntry
        ACCESS    not-accessible
        STATUS    mandatory
        DESCRIPTION
            "A list of g3pkloadint entries."
        ::= { g3pkloadint 6 }

    g3pkloadintEntry	OBJECT-TYPE
        SYNTAX    G3pkloadintEntry
        ACCESS    not-accessible
        STATUS    mandatory
        DESCRIPTION
            "A g3pkloadint entry containing objects of the
            g3pkloadint information sent by the switch."
        INDEX    { g3pkloadintPNNumber }
        ::= { g3pkloadintTable 1 }

    G3pkloadintEntry ::= SEQUENCE {
        g3pkloadintPNNumber
            INTEGER,
        g3pkloadintYear
            INTEGER,
        g3pkloadintMonth
            INTEGER,
        g3pkloadintDay
            INTEGER,
        g3pkloadintHour
            INTEGER,
        g3pkloadintIntIntraPNUse
            INTEGER,
        g3pkloadintIntIntraPNPeg
            INTEGER,
        g3pkloadintIntInterPNUse
            INTEGER,
        g3pkloadintIntInterPNPeg
            INTEGER,
        g3pkloadintMeasHour
            INTEGER
        }

    g3pkloadintPNNumber	OBJECT-TYPE
        SYNTAX    INTEGER
        ACCESS    read-only
        STATUS    mandatory
        DESCRIPTION
            "An object containing the Port Network number."
        ::= { g3pkloadintEntry 1 }

    g3pkloadintYear	OBJECT-TYPE
        SYNTAX    INTEGER
        ACCESS    read-only
        STATUS    mandatory
        DESCRIPTION
            "An object containing the Year the command was executed."
        ::= { g3pkloadintEntry 2 }

    g3pkloadintMonth	OBJECT-TYPE
        SYNTAX    INTEGER
        ACCESS    read-only
        STATUS    mandatory
        DESCRIPTION
            "An object containing the Month the command was executed."
        ::= { g3pkloadintEntry 3 }

    g3pkloadintDay	OBJECT-TYPE
        SYNTAX    INTEGER
        ACCESS    read-only
        STATUS    mandatory
        DESCRIPTION
            "An object containing the Day the command was executed."
        ::= { g3pkloadintEntry 4 }

    g3pkloadintHour	OBJECT-TYPE
        SYNTAX    INTEGER
        ACCESS    read-only
        STATUS    mandatory
        DESCRIPTION
            "An object containing the Hour the command was executed."
        ::= { g3pkloadintEntry 5 }

    g3pkloadintIntIntraPNUse	OBJECT-TYPE
        SYNTAX    INTEGER
        ACCESS    read-only
        STATUS    mandatory
        DESCRIPTION
            "An object containing the TDM time-slot usage caused by
            station-to-station calls between terminals on the same port
            network (displayed in CCS)."
        ::= { g3pkloadintEntry 6 }

    g3pkloadintIntIntraPNPeg	OBJECT-TYPE
        SYNTAX    INTEGER
        ACCESS    read-only
        STATUS    mandatory
        DESCRIPTION
            "An object containing the count of TDM time-slot seizures caused
            by station-to-station calls between terminals on the same PN."
        ::= { g3pkloadintEntry 7 }

    g3pkloadintIntInterPNUse	OBJECT-TYPE
        SYNTAX    INTEGER
        ACCESS    read-only
        STATUS    mandatory
        DESCRIPTION
            "An object containing the TDM time-slot usage caused by
            station-to-station calls between terminals on different port
            networks (in CCS)."
        ::= { g3pkloadintEntry 8 }

    g3pkloadintIntInterPNPeg	OBJECT-TYPE
        SYNTAX    INTEGER
        ACCESS    read-only
        STATUS    mandatory
        DESCRIPTION
            "An object containing the TDM time slot seizures caused by
            station-to-station calls between terminals on different PNs."
        ::= { g3pkloadintEntry 9 }

    g3pkloadintMeasHour	OBJECT-TYPE
        SYNTAX    INTEGER
        ACCESS    read-only
        STATUS    mandatory
        DESCRIPTION
            "An object containing the hour the measurement was taken."
        ::= { g3pkloadintEntry 10 }


    -- the g3pkloadinc group

    g3pkloadincTage	OBJECT-TYPE
        SYNTAX    INTEGER
        ACCESS    read-only
        STATUS    mandatory
        DESCRIPTION
            "The number of timeticks since the data was
            last extracted from the switch by the Proxy Agent.  This object
            along with the g3pkloadincintvl object allows the Network Manager
            to determine the validity of the data in the cache and to control
            when the Proxy Agent extracts the data from the switch."
        ::= { g3pkloadinc 1 }

    g3pkloadincTintvl	OBJECT-TYPE
        SYNTAX    INTEGER
        ACCESS    read-write
        STATUS    mandatory
        DESCRIPTION
            "An object containing the interval for which the
            data extracted from the switch is considered valid by the Proxy Agent.
            When a GET or GET-NEXT request for these objects is received by the
            agent it uses the g3pkloadincage and g3pkloadincintvl objects to
            determine whether it should refresh the cached pkloadincTable.  If
            g3pkloadincstmp + g3pkloadincintvl is less than the current value of
            the sysUpTime object then the agent refreshes the pkloadincTable
            cache.  In either case it responds to the requests it receives
            with the data it currently has in the cache."
        ::= { g3pkloadinc 2 }

    g3pkloadincTdelay	OBJECT-TYPE
        SYNTAX    INTEGER
        ACCESS    read-only
        STATUS    mandatory
        DESCRIPTION
            "An object containing the delay encountered in updating
            the cached data."
        ::= { g3pkloadinc 3 }

    g3pkloadincTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3pkloadinc 4 }

    g3pkloadincTcount	OBJECT-TYPE
        SYNTAX    Gauge
        ACCESS    read-only
        STATUS    mandatory
        DESCRIPTION
            "A Gauge object containing the number of data records in the cache."
        ::= { g3pkloadinc 5 }

    g3pkloadincTable	OBJECT-TYPE
        SYNTAX    SEQUENCE OF G3pkloadincEntry
        ACCESS    not-accessible
        STATUS    mandatory
        DESCRIPTION
            "A list of g3pkloadinc entries."
        ::= { g3pkloadinc 6 }

    g3pkloadincEntry	OBJECT-TYPE
        SYNTAX    G3pkloadincEntry
        ACCESS    not-accessible
        STATUS    mandatory
        DESCRIPTION
            "A g3pkloadinc entry containing objects of the
            g3pkloadinc information sent by the switch."
        INDEX    { g3pkloadincPNNumber }
        ::= { g3pkloadincTable 1 }

    G3pkloadincEntry ::= SEQUENCE {
        g3pkloadincPNNumber
            INTEGER,
        g3pkloadincYear
            INTEGER,
        g3pkloadincMonth
            INTEGER,
        g3pkloadincDay
            INTEGER,
        g3pkloadincHour
            INTEGER,
        g3pkloadincIncIntraPNUse
            INTEGER,
        g3pkloadincIncIntraPNPeg
            INTEGER,
        g3pkloadincIncIncomingUse
            INTEGER,
        g3pkloadincIncIncomingPeg
            INTEGER,
        g3pkloadincIncOutgoingUse
            INTEGER,
        g3pkloadincIncOutgoingPeg
            INTEGER,
        g3pkloadincMeasHour
            INTEGER
        }

    g3pkloadincPNNumber	OBJECT-TYPE
        SYNTAX    INTEGER
        ACCESS    read-only
        STATUS    mandatory
        DESCRIPTION
            "An object containing the Port Network number."
        ::= { g3pkloadincEntry 1 }

    g3pkloadincYear	OBJECT-TYPE
        SYNTAX    INTEGER
        ACCESS    read-only
        STATUS    mandatory
        DESCRIPTION
            "An object containing the Year the command was executed."
        ::= { g3pkloadincEntry 2 }

    g3pkloadincMonth	OBJECT-TYPE
        SYNTAX    INTEGER
        ACCESS    read-only
        STATUS    mandatory
        DESCRIPTION
            "An object containing the Month the command was executed."
        ::= { g3pkloadincEntry 3 }

    g3pkloadincDay	OBJECT-TYPE
        SYNTAX    INTEGER
        ACCESS    read-only
        STATUS    mandatory
        DESCRIPTION
            "An object containing the Day the command was executed."
        ::= { g3pkloadincEntry 4 }

    g3pkloadincHour	OBJECT-TYPE
        SYNTAX    INTEGER
        ACCESS    read-only
        STATUS    mandatory
        DESCRIPTION
            "An object containing the Hour the command was executed."
        ::= { g3pkloadincEntry 5 }

    g3pkloadincIncIntraPNUse	OBJECT-TYPE
        SYNTAX    INTEGER
        ACCESS    read-only
        STATUS    mandatory
        DESCRIPTION
            "An object containing the TDM time-slot usage caused by incoming
            trunk calls to a station on the same port network (in CCS)."
        ::= { g3pkloadincEntry 6 }

    g3pkloadincIncIntraPNPeg	OBJECT-TYPE
        SYNTAX    INTEGER
        ACCESS    read-only
        STATUS    mandatory
        DESCRIPTION
            "An object containing the count of TDM time-slot seizures caused
            by incoming trunk calls to a station on the same port network."
        ::= { g3pkloadincEntry 7 }

    g3pkloadincIncIncomingUse	OBJECT-TYPE
        SYNTAX    INTEGER
        ACCESS    read-only
        STATUS    mandatory
        DESCRIPTION
            "An object containing the TDM time-slot usage caused by calls to
            a station on the port network from an incoming trunk on another
            port network (in CCS)."
        ::= { g3pkloadincEntry 8 }

    g3pkloadincIncIncomingPeg	OBJECT-TYPE
        SYNTAX    INTEGER
        ACCESS    read-only
        STATUS    mandatory
        DESCRIPTION
            "An object containing the count of TDM time-slot seizures caused
            by calls to a station on the port network from an incoming trunk
            on another port network."
        ::= { g3pkloadincEntry 9 }

    g3pkloadincIncOutgoingUse	OBJECT-TYPE
        SYNTAX    INTEGER
        ACCESS    read-only
        STATUS    mandatory
        DESCRIPTION
            "An object containing the TDM time-slot usage caused by calls to
            a station on another port network from an incoming trunk on the
            measured port network (in CCS)."
        ::= { g3pkloadincEntry 10 }

    g3pkloadincIncOutgoingPeg	OBJECT-TYPE
        SYNTAX    INTEGER
        ACCESS    read-only
        STATUS    mandatory
        DESCRIPTION
            "An object containing the count of TDM time-slot seizures caused by
            calls to a station on another port network from an incoming trunk
            on the measured port network."
        ::= { g3pkloadincEntry 11 }

    g3pkloadincMeasHour	OBJECT-TYPE
        SYNTAX    INTEGER
        ACCESS    read-only
        STATUS    mandatory
        DESCRIPTION
            "An object containing the hour the measurement was taken."
        ::= { g3pkloadincEntry 12 }


    -- the g3pkloadout group

    g3pkloadoutTage	OBJECT-TYPE
        SYNTAX    INTEGER
        ACCESS    read-only
        STATUS    mandatory
        DESCRIPTION
            "The number of timeticks since the data was
            last extracted from the switch by the Proxy Agent.  This object
            along with the g3pkloadoutintvl object allows the Network Manager
            to determine the validity of the data in the cache and to control
            when the Proxy Agent extracts the data from the switch."
        ::= { g3pkloadout 1 }

    g3pkloadoutTintvl	OBJECT-TYPE
        SYNTAX    INTEGER
        ACCESS    read-write
        STATUS    mandatory
        DESCRIPTION
            "An object containing the interval for which the
            data extracted from the switch is considered valid by the Proxy Agent.
            When a GET or GET-NEXT request for these objects is received by the
            agent it uses the g3pkloadoutage and g3pkloadoutintvl objects to
            determine whether it should refresh the cached pkloadoutTable.  If
            g3pkloadoutstmp + g3pkloadoutintvl is less than the current value of
            the sysUpTime object then the agent refreshes the pkloadoutTable
            cache.  In either case it responds to the requests it receives
            with the data it currently has in the cache."
        ::= { g3pkloadout 2 }

    g3pkloadoutTdelay	OBJECT-TYPE
        SYNTAX    INTEGER
        ACCESS    read-only
        STATUS    mandatory
        DESCRIPTION
            "An object containing the delay encountered in updating
            the cached data."
        ::= { g3pkloadout 3 }

    g3pkloadoutTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3pkloadout 4 }

    g3pkloadoutTcount	OBJECT-TYPE
        SYNTAX    Gauge
        ACCESS    read-only
        STATUS    mandatory
        DESCRIPTION
            "A Gauge object containing the number of data records in the cache."
        ::= { g3pkloadout 5 }

    g3pkloadoutTable	OBJECT-TYPE
        SYNTAX    SEQUENCE OF G3pkloadoutEntry
        ACCESS    not-accessible
        STATUS    mandatory
        DESCRIPTION
            "A list of g3pkloadout entries."
        ::= { g3pkloadout 6 }

    g3pkloadoutEntry	OBJECT-TYPE
        SYNTAX    G3pkloadoutEntry
        ACCESS    not-accessible
        STATUS    mandatory
        DESCRIPTION
            "A g3pkloadout entry containing objects of the
            g3pkloadout information sent by the switch."
        INDEX    { g3pkloadoutPNNumber }
        ::= { g3pkloadoutTable 1 }

    G3pkloadoutEntry ::= SEQUENCE {
        g3pkloadoutPNNumber
            INTEGER,
        g3pkloadoutYear
            INTEGER,
        g3pkloadoutMonth
            INTEGER,
        g3pkloadoutDay
            INTEGER,
        g3pkloadoutHour
            INTEGER,
        g3pkloadoutOutIntraPNUse
            INTEGER,
        g3pkloadoutOutIntraPNPeg
            INTEGER,
        g3pkloadoutOutIncomingUse
            INTEGER,
        g3pkloadoutOutIncomingPeg
            INTEGER,
        g3pkloadoutOutOutgoingUse
            INTEGER,
        g3pkloadoutOutOutgoingPeg
            INTEGER,
        g3pkloadoutMeasHour
            INTEGER
        }

    g3pkloadoutPNNumber	OBJECT-TYPE
        SYNTAX    INTEGER
        ACCESS    read-only
        STATUS    mandatory
        DESCRIPTION
            "An object containing the Port Network number."
        ::= { g3pkloadoutEntry 1 }

    g3pkloadoutYear	OBJECT-TYPE
        SYNTAX    INTEGER
        ACCESS    read-only
        STATUS    mandatory
        DESCRIPTION
            "An object containing the Year the command was executed."
        ::= { g3pkloadoutEntry 2 }

    g3pkloadoutMonth	OBJECT-TYPE
        SYNTAX    INTEGER
        ACCESS    read-only
        STATUS    mandatory
        DESCRIPTION
            "An object containing the Month the command was executed."
        ::= { g3pkloadoutEntry 3 }

    g3pkloadoutDay	OBJECT-TYPE
        SYNTAX    INTEGER
        ACCESS    read-only
        STATUS    mandatory
        DESCRIPTION
            "An object containing the Day the command was executed."
        ::= { g3pkloadoutEntry 4 }

    g3pkloadoutHour	OBJECT-TYPE
        SYNTAX    INTEGER
        ACCESS    read-only
        STATUS    mandatory
        DESCRIPTION
            "An object containing the Hour the command was executed."
        ::= { g3pkloadoutEntry 5 }

    g3pkloadoutOutIntraPNUse	OBJECT-TYPE
        SYNTAX    INTEGER
        ACCESS    read-only
        STATUS    mandatory
        DESCRIPTION
            "An object containing the TDM time-slot usage caused by outgoing
            calls made by stations on the measured port network and serviced by
            outgoing trunks on the same port network (in CCS)."
        ::= { g3pkloadoutEntry 6 }

    g3pkloadoutOutIntraPNPeg	OBJECT-TYPE
        SYNTAX    INTEGER
        ACCESS    read-only
        STATUS    mandatory
        DESCRIPTION
            "An object containing the count of TDM time-slot seizures caused
            by outgoing calls made by stations on the measured port network
            and serviced by outgoing trunks on the same port network."
        ::= { g3pkloadoutEntry 7 }

    g3pkloadoutOutIncomingUse	OBJECT-TYPE
        SYNTAX    INTEGER
        ACCESS    read-only
        STATUS    mandatory
        DESCRIPTION
            "An object containing the TDM time-slot usage resulting from
            outgoing calls originated at stations on another port network
            but serviced by trunks on the port network being measured (in CCS)."
        ::= { g3pkloadoutEntry 8 }

    g3pkloadoutOutIncomingPeg	OBJECT-TYPE
        SYNTAX    INTEGER
        ACCESS    read-only
        STATUS    mandatory
        DESCRIPTION
            "An object containing the count of TDM time-slot seizures resulting
            from outgoing calls originated at stations on another port
            network, but serviced by trunks on the port network being measured."
        ::= { g3pkloadoutEntry 9 }

    g3pkloadoutOutOutgoingUse	OBJECT-TYPE
        SYNTAX    INTEGER
        ACCESS    read-only
        STATUS    mandatory
        DESCRIPTION
            "An object containing the TDM time-slot usage resulting from
            outgoing calls originated at stations on the port network being
            measured, but serviced by trunks on another port network (in CCS)."
        ::= { g3pkloadoutEntry 10 }

    g3pkloadoutOutOutgoingPeg	OBJECT-TYPE
        SYNTAX    INTEGER
        ACCESS    read-only
        STATUS    mandatory
        DESCRIPTION
            "An object containing the count of TDM time-slot seizures resulting
            from outgoing calls originated at stations on the port network
            being measured, but serviced by trunks on another port network."
        ::= { g3pkloadoutEntry 11 }

    g3pkloadoutMeasHour	OBJECT-TYPE
        SYNTAX    INTEGER
        ACCESS    read-only
        STATUS    mandatory
        DESCRIPTION
            "An object containing the hour the measurement was taken."
        ::= { g3pkloadoutEntry 12 }


    -- the g3pkloadtan group

    g3pkloadtanTage	OBJECT-TYPE
        SYNTAX    INTEGER
        ACCESS    read-only
        STATUS    mandatory
        DESCRIPTION
            "The number of timeticks since the peak tandem load data was
            last extracted from the switch by the Proxy Agent.  This object
            along with the g3pkloadtanintvl object allows the Network Manager
            to determine the validity of the peak tandem load data in the cache and to 
            control when the Proxy Agent extracts the data from the switch."
        ::= { g3pkloadtan 1 }

    g3pkloadtanTintvl	OBJECT-TYPE
        SYNTAX    INTEGER
        ACCESS    read-write
        STATUS    mandatory
        DESCRIPTION
            "An object containing the interval for which the
            data extracted from the switch is considered valid by the Proxy Agent.
            When a GET or GET-NEXT request for the peak tandem load objects is  
            received by the	agent it uses the g3pkloadtanage and g3pkloadtanintvl 
            objects to	determine whether it should refresh the cached pkloadtanTable.  
            If g3pkloadtanstmp + g3pkloadtanintvl is less than the current value of
            the sysUpTime object then the agent refreshes the pkloadtanTable
            cache.  In either case it responds to the requests it receives
            with the data it currently has in the cache."
        ::= { g3pkloadtan 2 }

    g3pkloadtanTdelay	OBJECT-TYPE
        SYNTAX    INTEGER
        ACCESS    read-only
        STATUS    mandatory
        DESCRIPTION
            "An object containing the delay encountered in updating
            the cached data."
        ::= { g3pkloadtan 3 }

    g3pkloadtanTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3pkloadtan 4 }

    g3pkloadtanTcount	OBJECT-TYPE
        SYNTAX    Gauge
        ACCESS    read-only
        STATUS    mandatory
        DESCRIPTION
            "A Gauge object containing the number of data records in the cache."
        ::= { g3pkloadtan 5 }

    g3pkloadtanTable	OBJECT-TYPE
        SYNTAX    SEQUENCE OF G3pkloadtanEntry
        ACCESS    not-accessible
        STATUS    mandatory
        DESCRIPTION
            "A list of g3pkloadtan entries."
        ::= { g3pkloadtan 6 }

    g3pkloadtanEntry	OBJECT-TYPE
        SYNTAX    G3pkloadtanEntry
        ACCESS    not-accessible
        STATUS    mandatory
        DESCRIPTION
            "A g3pkloadtan entry containing objects of the
            g3pkloadtan information sent by the switch."
        INDEX    { g3pkloadtanPNNumber }
        ::= { g3pkloadtanTable 1 }

    G3pkloadtanEntry ::= SEQUENCE {
        g3pkloadtanPNNumber
            INTEGER,
        g3pkloadtanYear
            INTEGER,
        g3pkloadtanMonth
            INTEGER,
        g3pkloadtanDay
            INTEGER,
        g3pkloadtanHour
            INTEGER,
        g3pkloadtanTanIntraPNUse
            INTEGER,
        g3pkloadtanTanIntraPNPeg
            INTEGER,
        g3pkloadtanTanIncomingUse
            INTEGER,
        g3pkloadtanTanIncomingPeg
            INTEGER,
        g3pkloadtanTanOutgoingUse
            INTEGER,
        g3pkloadtanTanOutgoingPeg
            INTEGER,
        g3pkloadtanMeasHour
            INTEGER
        }

    g3pkloadtanPNNumber	OBJECT-TYPE
        SYNTAX    INTEGER
        ACCESS    read-only
        STATUS    mandatory
        DESCRIPTION
            "An object containing the Port Network number."
        ::= { g3pkloadtanEntry 1 }

    g3pkloadtanYear	OBJECT-TYPE
        SYNTAX    INTEGER
        ACCESS    read-only
        STATUS    mandatory
        DESCRIPTION
            "An object containing the Year the command was executed."
        ::= { g3pkloadtanEntry 2 }

    g3pkloadtanMonth	OBJECT-TYPE
        SYNTAX    INTEGER
        ACCESS    read-only
        STATUS    mandatory
        DESCRIPTION
            "An object containing the Month the command was executed."
        ::= { g3pkloadtanEntry 3 }

    g3pkloadtanDay	OBJECT-TYPE
        SYNTAX    INTEGER
        ACCESS    read-only
        STATUS    mandatory
        DESCRIPTION
            "An object containing the Day the command was executed."
        ::= { g3pkloadtanEntry 4 }

    g3pkloadtanHour	OBJECT-TYPE
        SYNTAX    INTEGER
        ACCESS    read-only
        STATUS    mandatory
        DESCRIPTION
            "An object containing the Hour the command was executed."
        ::= { g3pkloadtanEntry 5 }

    g3pkloadtanTanIntraPNUse	OBJECT-TYPE
        SYNTAX    INTEGER
        ACCESS    read-only
        STATUS    mandatory
        DESCRIPTION
            "An object containing the TDM usage caused by tandem trunk calls
            originating and terminating on the port network being measured
            (in CCS)."
        ::= { g3pkloadtanEntry 6 }

    g3pkloadtanTanIntraPNPeg	OBJECT-TYPE
        SYNTAX    INTEGER
        ACCESS    read-only
        STATUS    mandatory
        DESCRIPTION
            "An object containing the count of TDM time-slot seizures caused
            by tandem trunk calls originating and terminating on the port
            network being measured."
        ::= { g3pkloadtanEntry 7 }

    g3pkloadtanTanIncomingUse	OBJECT-TYPE
        SYNTAX    INTEGER
        ACCESS    read-only
        STATUS    mandatory
        DESCRIPTION
            "An object containing the TDM usage resulting from tandem trunk
            calls originating on another port network, but terminating on the
            port network being measured (in CCS)."
        ::= { g3pkloadtanEntry 8 }

    g3pkloadtanTanIncomingPeg	OBJECT-TYPE
        SYNTAX    INTEGER
        ACCESS    read-only
        STATUS    mandatory
        DESCRIPTION
            "An object containing the count of TDM time-slot seizures resulting
            from tandem trunk calls originating on another port network, but
            terminating on the port network being measured."
        ::= { g3pkloadtanEntry 9 }

    g3pkloadtanTanOutgoingUse	OBJECT-TYPE
        SYNTAX    INTEGER
        ACCESS    read-only
        STATUS    mandatory
        DESCRIPTION
            "An object containing the TDM usage resulting from tandem trunk
            calls originating on the port network being measured, but
            terminating on another port network (in CCS)."
        ::= { g3pkloadtanEntry 10 }

    g3pkloadtanTanOutgoingPeg	OBJECT-TYPE
        SYNTAX    INTEGER
        ACCESS    read-only
        STATUS    mandatory
        DESCRIPTION
            "An object containing the count of TDM time-slot seizures resulting
            from tandem trunk calls originating on the port network being
            measured, but terminating on another port network."
        ::= { g3pkloadtanEntry 11 }

    g3pkloadtanMeasHour	OBJECT-TYPE
        SYNTAX    INTEGER
        ACCESS    read-only
        STATUS    mandatory
        DESCRIPTION
            "An object containing the hour the measurement was taken."
        ::= { g3pkloadtanEntry 12 }


    -- the g3atmlatency group

    g3atmlatencyTage	OBJECT-TYPE
        SYNTAX    INTEGER
        ACCESS    read-only
        STATUS    mandatory
        DESCRIPTION
            "The number of timeticks since the atm pnc latency data was last
            extracted from the switch by the Proxy Agent.  This object
            along with the g3atmlatencyintvl object allows the Network Manager
            to determine the validity of the atm pnc latency data in the cache and to 
            control when the Proxy Agent extracts the data from the switch."
        ::= { g3atmlatency 1 }

    g3atmlatencyTintvl	OBJECT-TYPE
        SYNTAX    INTEGER
        ACCESS    read-write
        STATUS    mandatory
        DESCRIPTION
            "An object containing the interval for which the
            data extracted from the switch is considered valid by the
            Proxy Agent.  When a GET or GET-NEXT request for the atm pnc latency 
            objects is received by the agent it uses the g3atmlatencyage
            and g3atmlatencyintvl objects to determine whether it should refresh
            the cached atmlatencyTable.  If g3atmlatencystmp + g3atmlatencyintvl
            is less than the current value of the sysUpTime object then the agent
            refreshes the atmlatencyTable cache.  In either case it responds to
            the requests it receives with the data it currently has in the cache."
        ::= { g3atmlatency 2 }

    g3atmlatencyTdelay	OBJECT-TYPE
        SYNTAX    INTEGER
        ACCESS    read-only
        STATUS    mandatory
        DESCRIPTION
            "An object containing the delay encountered in updating
            the cached data."
        ::= { g3atmlatency 3 }

    g3atmlatencyTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3atmlatency 4 }

    g3atmlatencyTcount	OBJECT-TYPE
        SYNTAX    Gauge
        ACCESS    read-only
        STATUS    mandatory
        DESCRIPTION
            "A Gauge object containing the number of data records in the cache."
        ::= { g3atmlatency 5 }

    g3atmlatencyTable	OBJECT-TYPE
        SYNTAX    SEQUENCE OF G3atmlatencyEntry
        ACCESS    not-accessible
        STATUS    mandatory
        DESCRIPTION
            "A list of g3atmlatency entries."
        ::= { g3atmlatency 6 }

    g3atmlatencyEntry	OBJECT-TYPE
        SYNTAX    G3atmlatencyEntry
        ACCESS    not-accessible
        STATUS    mandatory
        DESCRIPTION
            "A g3atmlatency entry containing objects of the
            g3atmlatency information sent by the switch."
        INDEX    { g3atmlatencyPNPair }
        ::= { g3atmlatencyTable 1 }

    G3atmlatencyEntry ::= SEQUENCE {
        g3atmlatencyPNPair
            INTEGER,
        g3atmlatencyYear
            INTEGER,
        g3atmlatencyMonth
            INTEGER,
        g3atmlatencyDay
            INTEGER,
        g3atmlatencyHour
            INTEGER,
        g3atmlatencyPNOrig1
            INTEGER,
        g3atmlatencyPNDest1
            INTEGER,
        g3atmlatencyCount1A
            INTEGER,
        g3atmlatencySetup1A
            INTEGER,
        g3atmlatencyATMCount1A
            INTEGER,
        g3atmlatencyATMSetup1A
            INTEGER,
        g3atmlatencyMeasHour1A
            INTEGER,
        g3atmlatencyCount1B
            INTEGER,
        g3atmlatencySetup1B
            INTEGER,
        g3atmlatencyATMCount1B
            INTEGER,
        g3atmlatencyATMSetup1B
            INTEGER,
        g3atmlatencyMeasHour1B
            INTEGER
        }

    g3atmlatencyPNPair	OBJECT-TYPE
        SYNTAX    INTEGER
        ACCESS    read-only
        STATUS    mandatory
        DESCRIPTION
            "An INTEGER object containing an index numbering the PN Pair."
        ::= { g3atmlatencyEntry 1 }

    g3atmlatencyYear	OBJECT-TYPE
        SYNTAX    INTEGER
        ACCESS    read-only
        STATUS    mandatory
        DESCRIPTION
            "An object containing the Year the command was executed."
        ::= { g3atmlatencyEntry 2 }

    g3atmlatencyMonth	OBJECT-TYPE
        SYNTAX    INTEGER
        ACCESS    read-only
        STATUS    mandatory
        DESCRIPTION
            "An object containing the Month the command was executed."
        ::= { g3atmlatencyEntry 3 }

    g3atmlatencyDay	OBJECT-TYPE
        SYNTAX    INTEGER
        ACCESS    read-only
        STATUS    mandatory
        DESCRIPTION
            "An object containing the Day the command was executed."
        ::= { g3atmlatencyEntry 4 }

    g3atmlatencyHour	OBJECT-TYPE
        SYNTAX    INTEGER
        ACCESS    read-only
        STATUS    mandatory
        DESCRIPTION
            "An object containing the Hour the command was executed."
        ::= { g3atmlatencyEntry 5 }

    g3atmlatencyPNOrig1	OBJECT-TYPE
        SYNTAX    INTEGER
        ACCESS    read-only
        STATUS    mandatory
        DESCRIPTION
            "Originating Port Network for the PN Pair."
        ::= { g3atmlatencyEntry 6 }

    g3atmlatencyPNDest1	OBJECT-TYPE
        SYNTAX    INTEGER
        ACCESS    read-only
        STATUS    mandatory
        DESCRIPTION
            "Originating Port Network for the PN Pair."
        ::= { g3atmlatencyEntry 7 }

    g3atmlatencyCount1A	OBJECT-TYPE
        SYNTAX    INTEGER
        ACCESS    read-only
        STATUS    mandatory
        DESCRIPTION
            "An object containing the number (count) of connections
            for the PN Pair on A-PNC."
        ::= { g3atmlatencyEntry 8 }

    g3atmlatencySetup1A	OBJECT-TYPE
        SYNTAX    INTEGER
        ACCESS    read-only
        STATUS    mandatory
        DESCRIPTION
            "An object containing the average PN connection setup time
            (latency) in milliseconds for the PN Pair on A-PNC."
        ::= { g3atmlatencyEntry 9 }

    g3atmlatencyATMCount1A	OBJECT-TYPE
        SYNTAX    INTEGER
        ACCESS    read-only
        STATUS    mandatory
        DESCRIPTION
            "An object containing the number (count) of ATM network
            connections for the PN Pair on A-PNC."
        ::= { g3atmlatencyEntry 10 }

    g3atmlatencyATMSetup1A	OBJECT-TYPE
        SYNTAX    INTEGER
        ACCESS    read-only
        STATUS    mandatory
        DESCRIPTION
            "An object containing the average ATM network connection setup
            time (latency) in milliseconds for the PN Pair on A-PNC."
        ::= { g3atmlatencyEntry 11 }

    g3atmlatencyMeasHour1A	OBJECT-TYPE
        SYNTAX    INTEGER
        ACCESS    read-only
        STATUS    mandatory
        DESCRIPTION
            "An object containing the Hour the PN Pair A-PNC
            measurement was taken."
        ::= { g3atmlatencyEntry 12 }

    g3atmlatencyCount1B	OBJECT-TYPE
        SYNTAX    INTEGER
        ACCESS    read-only
        STATUS    mandatory
        DESCRIPTION
            "An object containing the number (count) of connections
            for the PN Pair on B-PNC."
        ::= { g3atmlatencyEntry 13 }

    g3atmlatencySetup1B	OBJECT-TYPE
        SYNTAX    INTEGER
        ACCESS    read-only
        STATUS    mandatory
        DESCRIPTION
            "An object containing the average PN connection setup time
            (latency) in milliseconds for the PN Pair on B-PNC."
        ::= { g3atmlatencyEntry 14 }

    g3atmlatencyATMCount1B	OBJECT-TYPE
        SYNTAX    INTEGER
        ACCESS    read-only
        STATUS    mandatory
        DESCRIPTION
            "An object containing the number (count) of ATM network
            connections for the PN Pair on B-PNC."
        ::= { g3atmlatencyEntry 15 }

    g3atmlatencyATMSetup1B	OBJECT-TYPE
        SYNTAX    INTEGER
        ACCESS    read-only
        STATUS    mandatory
        DESCRIPTION
            "An object containing the average ATM network connection setup
            time (latency) in milliseconds for the PN Pair on B-PNC."
        ::= { g3atmlatencyEntry 16 }

    g3atmlatencyMeasHour1B	OBJECT-TYPE
        SYNTAX    INTEGER
        ACCESS    read-only
        STATUS    mandatory
        DESCRIPTION
            "An object containing the Hour the PN Pair B-PNC
            measurement was taken."
        ::= { g3atmlatencyEntry 17 }


    -- the g3pkatmlatency group

    g3pkatmlatencyTage	OBJECT-TYPE
        SYNTAX    INTEGER
        ACCESS    read-only
        STATUS    mandatory
        DESCRIPTION
            "The number of timeticks since the peak atm latency data was last
            extracted from the switch by the Proxy Agent.  This object
            along with the g3pkatmlatencyintvl object allows the Network Manager
            to determine the validity of the peak atm latency data in the cache and to 
            control when the Proxy Agent extracts the data from the switch."
        ::= { g3pkatmlatency 1 }

    g3pkatmlatencyTintvl	OBJECT-TYPE
        SYNTAX    INTEGER
        ACCESS    read-write
        STATUS    mandatory
        DESCRIPTION
            "An object containing the interval for which the peak atm latency
            data extracted from the switch is considered valid by the
            Proxy Agent.  When a GET or GET-NEXT request for the peak atm latency 
            objects is received by the agent it uses the g3pkatmlatencyage
            and g3pkatmlatencyintvl objects to determine whether it should refresh
            the cached pkatmlatencyTable.  If g3pkatmlatencystmp +
            g3pkatmlatencyintvl is less than the current value of the sysUpTime
            object then the agent refreshes the pkatmlatencyTable cache.  In
            either case it responds to the requests it receives with the data
            it currently has in the cache."
        ::= { g3pkatmlatency 2 }

    g3pkatmlatencyTdelay	OBJECT-TYPE
        SYNTAX    INTEGER
        ACCESS    read-only
        STATUS    mandatory
        DESCRIPTION
            "An object containing the delay encountered in updating
            the cached data."
        ::= { g3pkatmlatency 3 }

    g3pkatmlatencyTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3pkatmlatency 4 }

    g3pkatmlatencyTcount	OBJECT-TYPE
        SYNTAX    Gauge
        ACCESS    read-only
        STATUS    mandatory
        DESCRIPTION
            "A Gauge object containing the number of data records in the cache."
        ::= { g3pkatmlatency 5 }

    g3pkatmlatencyTable	OBJECT-TYPE
        SYNTAX    SEQUENCE OF G3pkatmlatencyEntry
        ACCESS    not-accessible
        STATUS    mandatory
        DESCRIPTION
            "A list of g3pkatmlatency entries."
        ::= { g3pkatmlatency 6 }

    g3pkatmlatencyEntry	OBJECT-TYPE
        SYNTAX    G3pkatmlatencyEntry
        ACCESS    not-accessible
        STATUS    mandatory
        DESCRIPTION
            "A g3pkatmlatency entry containing objects of the
            g3pkatmlatency information sent by the switch."
        INDEX    { g3pkatmlatencyPNPair }
        ::= { g3pkatmlatencyTable 1 }

    G3pkatmlatencyEntry ::= SEQUENCE {
        g3pkatmlatencyPNPair
            INTEGER,
        g3pkatmlatencyYear
            INTEGER,
        g3pkatmlatencyMonth
            INTEGER,
        g3pkatmlatencyDay
            INTEGER,
        g3pkatmlatencyHour
            INTEGER,
        g3pkatmlatencyPNOrig1
            INTEGER,
        g3pkatmlatencyPNDest1
            INTEGER,
        g3pkatmlatencyCount1A
            INTEGER,
        g3pkatmlatencySetup1A
            INTEGER,
        g3pkatmlatencyATMCount1A
            INTEGER,
        g3pkatmlatencyATMSetup1A
            INTEGER,
        g3pkatmlatencyMeasHour1A
            INTEGER,
        g3pkatmlatencyCount1B
            INTEGER,
        g3pkatmlatencySetup1B
            INTEGER,
        g3pkatmlatencyATMCount1B
            INTEGER,
        g3pkatmlatencyATMSetup1B
            INTEGER,
        g3pkatmlatencyMeasHour1B
            INTEGER
        }

    g3pkatmlatencyPNPair	OBJECT-TYPE
        SYNTAX    INTEGER
        ACCESS    read-only
        STATUS    mandatory
        DESCRIPTION
            "An INTEGER object containing an index numbering the PN Pair."
        ::= { g3pkatmlatencyEntry 1 }

    g3pkatmlatencyYear	OBJECT-TYPE
        SYNTAX    INTEGER
        ACCESS    read-only
        STATUS    mandatory
        DESCRIPTION
            "An object containing the Year the command was executed."
        ::= { g3pkatmlatencyEntry 2 }

    g3pkatmlatencyMonth	OBJECT-TYPE
        SYNTAX    INTEGER
        ACCESS    read-only
        STATUS    mandatory
        DESCRIPTION
            "An object containing the Month the command was executed."
        ::= { g3pkatmlatencyEntry 3 }

    g3pkatmlatencyDay	OBJECT-TYPE
        SYNTAX    INTEGER
        ACCESS    read-only
        STATUS    mandatory
        DESCRIPTION
            "An object containing the Day the command was executed."
        ::= { g3pkatmlatencyEntry 4 }

    g3pkatmlatencyHour	OBJECT-TYPE
        SYNTAX    INTEGER
        ACCESS    read-only
        STATUS    mandatory
        DESCRIPTION
            "An object containing the Hour the command was executed."
        ::= { g3pkatmlatencyEntry 5 }

    g3pkatmlatencyPNOrig1	OBJECT-TYPE
        SYNTAX    INTEGER
        ACCESS    read-only
        STATUS    mandatory
        DESCRIPTION
            "Originating Port Network for the PN Pair."
        ::= { g3pkatmlatencyEntry 6 }

    g3pkatmlatencyPNDest1	OBJECT-TYPE
        SYNTAX    INTEGER
        ACCESS    read-only
        STATUS    mandatory
        DESCRIPTION
            "Originating Port Network for the PN Pair."
        ::= { g3pkatmlatencyEntry 7 }

    g3pkatmlatencyCount1A	OBJECT-TYPE
        SYNTAX    INTEGER
        ACCESS    read-only
        STATUS    mandatory
        DESCRIPTION
            "An object containing the number (count) of connections
            for the PN Pair on A-PNC."
        ::= { g3pkatmlatencyEntry 8 }

    g3pkatmlatencySetup1A	OBJECT-TYPE
        SYNTAX    INTEGER
        ACCESS    read-only
        STATUS    mandatory
        DESCRIPTION
            "An object containing the average PN connection setup time
            (latency) in milliseconds for the PN Pair on A-PNC."
        ::= { g3pkatmlatencyEntry 9 }

    g3pkatmlatencyATMCount1A	OBJECT-TYPE
        SYNTAX    INTEGER
        ACCESS    read-only
        STATUS    mandatory
        DESCRIPTION
            "An object containing the number (count) of ATM network
            connections for the PN Pair on A-PNC."
        ::= { g3pkatmlatencyEntry 10 }

    g3pkatmlatencyATMSetup1A	OBJECT-TYPE
        SYNTAX    INTEGER
        ACCESS    read-only
        STATUS    mandatory
        DESCRIPTION
            "An object containing the average ATM network connection setup
            time (latency) in milliseconds for the PN Pair on A-PNC."
        ::= { g3pkatmlatencyEntry 11 }

    g3pkatmlatencyMeasHour1A	OBJECT-TYPE
        SYNTAX    INTEGER
        ACCESS    read-only
        STATUS    mandatory
        DESCRIPTION
            "An object containing the Hour the PN Pair A-PNC
            measurement was taken."
        ::= { g3pkatmlatencyEntry 12 }

    g3pkatmlatencyCount1B	OBJECT-TYPE
        SYNTAX    INTEGER
        ACCESS    read-only
        STATUS    mandatory
        DESCRIPTION
            "An object containing the number (count) of connections
            for the PN Pair on B-PNC."
        ::= { g3pkatmlatencyEntry 13 }

    g3pkatmlatencySetup1B	OBJECT-TYPE
        SYNTAX    INTEGER
        ACCESS    read-only
        STATUS    mandatory
        DESCRIPTION
            "An object containing the average PN connection setup time
            (latency) in milliseconds for the PN Pair on B-PNC."
        ::= { g3pkatmlatencyEntry 14 }

    g3pkatmlatencyATMCount1B	OBJECT-TYPE
        SYNTAX    INTEGER
        ACCESS    read-only
        STATUS    mandatory
        DESCRIPTION
            "An object containing the number (count) of ATM network
            connections for the PN Pair on B-PNC."
        ::= { g3pkatmlatencyEntry 15 }

    g3pkatmlatencyATMSetup1B	OBJECT-TYPE
        SYNTAX    INTEGER
        ACCESS    read-only
        STATUS    mandatory
        DESCRIPTION
            "An object containing the average ATM network connection setup
            time (latency) in milliseconds for the PN Pair on B-PNC."
        ::= { g3pkatmlatencyEntry 16 }

    g3pkatmlatencyMeasHour1B	OBJECT-TYPE
        SYNTAX    INTEGER
        ACCESS    read-only
        STATUS    mandatory
        DESCRIPTION
            "An object containing the Hour the PN Pair B-PNC
            measurement was taken."
        ::= { g3pkatmlatencyEntry 17 }


    -- the g3ipcodecsum group

    g3ipcodecsumTage	OBJECT-TYPE
        SYNTAX    INTEGER
        ACCESS    read-only
        STATUS    mandatory
        DESCRIPTION
            "The number of timeticks since the ip codec summary data was last
            extracted from the switch by the Proxy Agent.  This object
            along with the g3ipcodecsumintvl object allows the Network Manager
            to determine the validity of the ip codec summary data in the cache and to 
            control when the Proxy Agent extracts the data from the switch."
        ::= { g3ipcodecsum 1 }

    g3ipcodecsumTintvl	OBJECT-TYPE
        SYNTAX    INTEGER
        ACCESS    read-write
        STATUS    mandatory
        DESCRIPTION
            "An object containing the interval for which the
            data extracted from the switch is considered valid by the
            Proxy Agent.  When a GET or GET-NEXT request for the ip codec summary 
            objects is received by the agent it uses the g3ipcodecsumage
            and g3ipcodecsumintvl objects to determine whether it should refresh
            the cached ipcodecsumTable.  If g3ipcodecsumstmp +
            g3ipcodecsumintvl is less than the current value of the sysUpTime
            object then the agent refreshes the ipcodecsumTable cache.  In
            either case it responds to the requests it receives with the data
            it currently has in the cache."
        ::= { g3ipcodecsum 2 }

    g3ipcodecsumTdelay	OBJECT-TYPE
        SYNTAX    INTEGER
        ACCESS    read-only
        STATUS    mandatory
        DESCRIPTION
            "An object containing the delay encountered in updating
            the cached data."
        ::= { g3ipcodecsum 3 }

    g3ipcodecsumTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3ipcodecsum 4 }

    g3ipcodecsumTcount	OBJECT-TYPE
        SYNTAX    Gauge
        ACCESS    read-only
        STATUS    mandatory
        DESCRIPTION
            "A Gauge object containing the number of data records in the cache."
        ::= { g3ipcodecsum 5 }

    g3ipcodecsumTable	OBJECT-TYPE
        SYNTAX    SEQUENCE OF G3ipcodecsumEntry
        ACCESS    not-accessible
        STATUS    mandatory
        DESCRIPTION
            "A list of g3ipcodecsum entries."
        ::= { g3ipcodecsum 6 }

    g3ipcodecsumEntry	OBJECT-TYPE
        SYNTAX    G3ipcodecsumEntry
        ACCESS    not-accessible
        STATUS    mandatory
        DESCRIPTION
            "A g3ipcodecsum entry containing objects of the
            g3ipcodecsum information sent by the switch."
        INDEX    { g3ipcodecsumRegion }
        ::= { g3ipcodecsumTable 1 }

    G3ipcodecsumEntry ::= SEQUENCE {
        g3ipcodecsumRegion
            INTEGER,
        g3ipcodecsumMeasHour
            INTEGER,
        g3ipcodecsumYear
            INTEGER,
        g3ipcodecsumMonth
            INTEGER,
        g3ipcodecsumDay
            INTEGER,
        g3ipcodecsumHour
            INTEGER,
        g3ipcodecsumDSPRecs
            INTEGER,
        g3ipcodecsumG711Usage
            DisplayString,
        g3ipcodecsumG711InRegion
            INTEGER,
        g3ipcodecsumG711OutRegion
            INTEGER,
        g3ipcodecsumG723Usage
            DisplayString,
        g3ipcodecsumG723InRegion
            INTEGER,
        g3ipcodecsumG723OutRegion
            INTEGER
        }

    g3ipcodecsumRegion	OBJECT-TYPE
        SYNTAX    INTEGER
        ACCESS    read-only
        STATUS    mandatory
        DESCRIPTION
            "An object containing The network region that the IP Media Processors and 
            Medpros for this measurement are in. Range: 1-44."
        ::= { g3ipcodecsumEntry 1 }

    g3ipcodecsumMeasHour	OBJECT-TYPE
        SYNTAX    INTEGER
        ACCESS    read-only
        STATUS    mandatory
        DESCRIPTION
            "An object containing the Hour the measurement was taken"
        ::= { g3ipcodecsumEntry 2 }

    g3ipcodecsumYear	OBJECT-TYPE
        SYNTAX    INTEGER
        ACCESS    read-only
        STATUS    mandatory
        DESCRIPTION
            "An object containing the Year the command was executed"
        ::= { g3ipcodecsumEntry 3 }

    g3ipcodecsumMonth	OBJECT-TYPE
        SYNTAX    INTEGER
        ACCESS    read-only
        STATUS    mandatory
        DESCRIPTION
            "An object containing the Month the command was executed"
        ::= { g3ipcodecsumEntry 4 }

    g3ipcodecsumDay	OBJECT-TYPE
        SYNTAX    INTEGER
        ACCESS    read-only
        STATUS    mandatory
        DESCRIPTION
            "An object containing the Day the command was executed"
        ::= { g3ipcodecsumEntry 5 }

    g3ipcodecsumHour	OBJECT-TYPE
        SYNTAX    INTEGER
        ACCESS    read-only
        STATUS    mandatory
        DESCRIPTION
            "An object containing the Hour the command was executed"
        ::= { g3ipcodecsumEntry 6 }

    g3ipcodecsumDSPRecs	OBJECT-TYPE
        SYNTAX    INTEGER
        ACCESS    read-only
        STATUS    mandatory
        DESCRIPTION
            "An object containing the total IP codec resources (voice channels) in the region."
        ::= { g3ipcodecsumEntry 7 }

    g3ipcodecsumG711Usage	OBJECT-TYPE
        SYNTAX    DisplayString (SIZE (0..6))
        ACCESS    read-only
        STATUS    mandatory
        DESCRIPTION
            "An object containing the usage in Erlangs of G.711 codecs during the 
            measurement interval. Includes time that the voice channels are on a call. 
            Usage shall be  measured from the time the voice channel is allocated 
            until it is released."
        ::= { g3ipcodecsumEntry 8 }

    g3ipcodecsumG711InRegion	OBJECT-TYPE
        SYNTAX    INTEGER
        ACCESS    read-only
        STATUS    mandatory
        DESCRIPTION
            "An object containing the total number of times an IP media processor port  
            in the region was allocated to a G.711 call. Range: 0-65535."
        ::= { g3ipcodecsumEntry 9 }

    g3ipcodecsumG711OutRegion	OBJECT-TYPE
        SYNTAX    INTEGER
        ACCESS    read-only
        STATUS    mandatory
        DESCRIPTION
            "An object containing the total number of times an IP media processor port 
            was needed in the region for a G.711 call, but was successfully allocated 
            to a resource in another region. Out of Region does not include denials."
        ::= { g3ipcodecsumEntry 10 }

    g3ipcodecsumG723Usage	OBJECT-TYPE
        SYNTAX    DisplayString (SIZE (0..6))
        ACCESS    read-only
        STATUS    mandatory
        DESCRIPTION
            "An object containing the usage in Erlangs of G.723 or G.729 codecs during 
            the measurement interval. Includes time that the voice channels are on a 
            call. Usage is measured from the time the voice channel is allocated until   
            it is released."
        ::= { g3ipcodecsumEntry 11 }

    g3ipcodecsumG723InRegion	OBJECT-TYPE
        SYNTAX    INTEGER
        ACCESS    read-only
        STATUS    mandatory
        DESCRIPTION
            "An object containing the total number of times an IP media processor port 
            in the region was allocated to a G.723 or G.729 call. Range: 0-65535."
        ::= { g3ipcodecsumEntry 12 }

    g3ipcodecsumG723OutRegion	OBJECT-TYPE
        SYNTAX    INTEGER
        ACCESS    read-only
        STATUS    mandatory
        DESCRIPTION
            "An object containing the total number of times an IP media processor port 
            was needed in the region for a G.723 or G.729 call, but was successfully  
            allocated to a resource in another region. Out of Region does not include 
            denials."
        ::= { g3ipcodecsumEntry 13 }


    -- the g3pkipcodecsum group

    g3pkipcodecsumTage	OBJECT-TYPE
        SYNTAX    INTEGER
        ACCESS    read-only
        STATUS    mandatory
        DESCRIPTION
            "The number of timeticks since the peak ip codec summary data was last
            extracted from the switch by the Proxy Agent.  This object
            along with the g3pkipcodecsumintvl object allows the Network Manager
            to determine the validity of the peak ip codec summary data in 
            the cache and to control when the Proxy Agent extracts the data 
            from the switch."
        ::= { g3pkipcodecsum 1 }

    g3pkipcodecsumTintvl	OBJECT-TYPE
        SYNTAX    INTEGER
        ACCESS    read-write
        STATUS    mandatory
        DESCRIPTION
            "An object containing the interval for which the peak ip codec summary
            data extracted from the switch is considered valid by the
            Proxy Agent.  When a GET or GET-NEXT request for the peak ip codec summary 
            data 	objects is received by the agent it uses the g3pkipcodecsumage
            and g3pkipcodecsumintvl objects to determine whether it should refresh
            the cached pkipcodecsumTable.  
            If g3pkipcodecsumstmp + g3pkipcodecsumintvl is less than the 
            current value of the sysUpTime
            object then the agent refreshes the pkipcodecsumTable cache.  In
            either case it responds to the requests it receives with the data
            it currently has in the cache."
        ::= { g3pkipcodecsum 2 }

    g3pkipcodecsumTdelay	OBJECT-TYPE
        SYNTAX    INTEGER
        ACCESS    read-only
        STATUS    mandatory
        DESCRIPTION
            "An object containing the delay encountered in updating
            the cached data."
        ::= { g3pkipcodecsum 3 }

    g3pkipcodecsumTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3pkipcodecsum 4 }

    g3pkipcodecsumTcount	OBJECT-TYPE
        SYNTAX    Gauge
        ACCESS    read-only
        STATUS    mandatory
        DESCRIPTION
            "A Gauge object containing the number of data records in the cache."
        ::= { g3pkipcodecsum 5 }

    g3pkipcodecsumTable	OBJECT-TYPE
        SYNTAX    SEQUENCE OF G3pkipcodecsumEntry
        ACCESS    not-accessible
        STATUS    mandatory
        DESCRIPTION
            "A list of g3pkipcodecsum entries."
        ::= { g3pkipcodecsum 6 }

    g3pkipcodecsumEntry	OBJECT-TYPE
        SYNTAX    G3pkipcodecsumEntry
        ACCESS    not-accessible
        STATUS    mandatory
        DESCRIPTION
            "A g3pkipcodecsum entry containing objects of the
            g3pkipcodecsum information sent by the switch."
        INDEX    { g3pkipcodecsumRegion }
        ::= { g3pkipcodecsumTable 1 }

    G3pkipcodecsumEntry ::= SEQUENCE {
        g3pkipcodecsumRegion
            INTEGER,
        g3pkipcodecsumMeasHour
            INTEGER,
        g3pkipcodecsumYear
            INTEGER,
        g3pkipcodecsumMonth
            INTEGER,
        g3pkipcodecsumDay
            INTEGER,
        g3pkipcodecsumHour
            INTEGER,
        g3pkipcodecsumDSPRecs
            INTEGER,
        g3pkipcodecsumG711Usage
            DisplayString,
        g3pkipcodecsumG711InRegion
            INTEGER,
        g3pkipcodecsumG711OutRegion
            INTEGER,
        g3pkipcodecsumG723Usage
            DisplayString,
        g3pkipcodecsumG723InRegion
            INTEGER,
        g3pkipcodecsumG723OutRegion
            INTEGER
        }

    g3pkipcodecsumRegion	OBJECT-TYPE
        SYNTAX    INTEGER
        ACCESS    read-only
        STATUS    mandatory
        DESCRIPTION
            "An object containing"
        ::= { g3pkipcodecsumEntry 1 }

    g3pkipcodecsumMeasHour	OBJECT-TYPE
        SYNTAX    INTEGER
        ACCESS    read-only
        STATUS    mandatory
        DESCRIPTION
            "An object containing the Hour the measurement was taken"
        ::= { g3pkipcodecsumEntry 2 }

    g3pkipcodecsumYear	OBJECT-TYPE
        SYNTAX    INTEGER
        ACCESS    read-only
        STATUS    mandatory
        DESCRIPTION
            "An object containing the Year the command was executed"
        ::= { g3pkipcodecsumEntry 3 }

    g3pkipcodecsumMonth	OBJECT-TYPE
        SYNTAX    INTEGER
        ACCESS    read-only
        STATUS    mandatory
        DESCRIPTION
            "An object containing the Month the command was executed"
        ::= { g3pkipcodecsumEntry 4 }

    g3pkipcodecsumDay	OBJECT-TYPE
        SYNTAX    INTEGER
        ACCESS    read-only
        STATUS    mandatory
        DESCRIPTION
            "An object containing the Day the command was executed"
        ::= { g3pkipcodecsumEntry 5 }

    g3pkipcodecsumHour	OBJECT-TYPE
        SYNTAX    INTEGER
        ACCESS    read-only
        STATUS    mandatory
        DESCRIPTION
            "An object containing the Hour the command was executed"
        ::= { g3pkipcodecsumEntry 6 }

    g3pkipcodecsumDSPRecs	OBJECT-TYPE
        SYNTAX    INTEGER
        ACCESS    read-only
        STATUS    mandatory
        DESCRIPTION
            "An object containing the total IP codec resources (voice channels) in the  
            region"
        ::= { g3pkipcodecsumEntry 7 }

    g3pkipcodecsumG711Usage	OBJECT-TYPE
        SYNTAX    DisplayString (SIZE (0..6))
        ACCESS    read-only
        STATUS    mandatory
        DESCRIPTION
            "An object containing the usage in Erlangs of G.711 codecs during the 
            measurement interval. Includes time that the voice channels are on a call. 
            Usage shall be  measured from the time the voice channel is allocated 
            until it is released"
        ::= { g3pkipcodecsumEntry 8 }

    g3pkipcodecsumG711InRegion	OBJECT-TYPE
        SYNTAX    INTEGER
        ACCESS    read-only
        STATUS    mandatory
        DESCRIPTION
            "An object containing the total number of times an IP media processor
            port in the region was  allocated to a G.711 call. Range: 0-65535."
        ::= { g3pkipcodecsumEntry 9 }

    g3pkipcodecsumG711OutRegion	OBJECT-TYPE
        SYNTAX    INTEGER
        ACCESS    read-only
        STATUS    mandatory
        DESCRIPTION
            "An object containing the total number of times an IP media processor port 
            was needed in the region for a G.711 call, but was successfully allocated  
            to a resource in another region. Out of Region does not include denials."
        ::= { g3pkipcodecsumEntry 10 }

    g3pkipcodecsumG723Usage	OBJECT-TYPE
        SYNTAX    DisplayString (SIZE (0..6))
        ACCESS    read-only
        STATUS    mandatory
        DESCRIPTION
            "An object containing the usage in Erlangs of G.723 or G.729 codecs during 
            the measurement interval. Includes time that the voice channels are on a 
            call. Usage shall be measured from the time the voice channel is allocated  
            until it is released."
        ::= { g3pkipcodecsumEntry 11 }

    g3pkipcodecsumG723InRegion	OBJECT-TYPE
        SYNTAX    INTEGER
        ACCESS    read-only
        STATUS    mandatory
        DESCRIPTION
            "An object containing the total number of times an IP media processor port 
            in the region was allocated to a G.723 or G.729 call. Range: 0-65535."
        ::= { g3pkipcodecsumEntry 12 }

    g3pkipcodecsumG723OutRegion	OBJECT-TYPE
        SYNTAX    INTEGER
        ACCESS    read-only
        STATUS    mandatory
        DESCRIPTION
            "An object containing the total number of times an IP media processor port 
            was needed in the region for a G.723 or G.729 call, but was successfully   
            allocated to a resource in another region. Out of Region does not include  
            denials."
        ::= { g3pkipcodecsumEntry 13 }


    -- the g3ipregion group

    g3ipregionTage	OBJECT-TYPE
        SYNTAX    INTEGER
        ACCESS    read-only
        STATUS    mandatory
        DESCRIPTION
            "The number of timeticks since the ip network region data was last
            extracted from the switch by the Proxy Agent.  This object
            along with the g3ipregionintvl object allows the Network Manager
            to determine the validity of the ip network region data in the cache and 
            to control	when the Proxy Agent extracts the data from the switch."
        ::= { g3ipregion 1 }

    g3ipregionTintvl	OBJECT-TYPE
        SYNTAX    INTEGER
        ACCESS    read-write
        STATUS    mandatory
        DESCRIPTION
            "An object containing the interval for which the ip network region
            data extracted from the switch is considered valid by the
            Proxy Agent.  When a GET or GET-NEXT request for the ip network region 
            objects is received by the agent it uses the g3ipregionage
            and g3ipregionintvl objects to determine whether it should refresh
            the cached ipregionTable.  If g3ipregionstmp +
            g3ipregionintvl is less than the current value of the sysUpTime
            object then the agent refreshes the ipregionTable cache.  In
            either case it responds to the requests it receives with the data
            it currently has in the cache."
        ::= { g3ipregion 2 }

    g3ipregionTdelay	OBJECT-TYPE
        SYNTAX    INTEGER
        ACCESS    read-only
        STATUS    mandatory
        DESCRIPTION
            "An object containing the delay encountered in updating
            the cached data."
        ::= { g3ipregion 3 }

    g3ipregionTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3ipregion 4 }

    g3ipregionTcount	OBJECT-TYPE
        SYNTAX    Gauge
        ACCESS    read-only
        STATUS    mandatory
        DESCRIPTION
            "A Gauge object containing the number of data records in the cache."
        ::= { g3ipregion 5 }

    g3ipregionTable	OBJECT-TYPE
        SYNTAX    SEQUENCE OF G3ipregionEntry
        ACCESS    not-accessible
        STATUS    mandatory
        DESCRIPTION
            "A list of g3ipregion entries."
        ::= { g3ipregion 6 }

    g3ipregionEntry	OBJECT-TYPE
        SYNTAX    G3ipregionEntry
        ACCESS    not-accessible
        STATUS    mandatory
        DESCRIPTION
            "A g3ipregion entry containing objects of the
            g3ipregion information sent by the switch."
        INDEX    { g3ipregionRegion }
        ::= { g3ipregionTable 1 }

    G3ipregionEntry ::= SEQUENCE {
        g3ipregionRegion
            INTEGER,
        g3ipregionName
            DisplayString
        }

    g3ipregionRegion	OBJECT-TYPE
        SYNTAX    INTEGER
        ACCESS    read-only
        STATUS    mandatory
        DESCRIPTION
            "An object containing the network region of the IP media processors being 
            region number is assigned on the Ip-interfaces screen during switch    
            administration. Range:1-2000"
        ::= { g3ipregionEntry 1 }

    g3ipregionName	OBJECT-TYPE
        SYNTAX    DisplayString (SIZE (0..20))
        ACCESS    read-only
        STATUS    mandatory
        DESCRIPTION
            "An object containing the name of the ip-network region"
        ::= { g3ipregionEntry 2 }


    -- the g3ipdspsum group

    g3ipdspsumTage	OBJECT-TYPE
        SYNTAX    INTEGER
        ACCESS    read-only
        STATUS    mandatory
        DESCRIPTION
            "The number of timeticks since the ip dsp resource data was last
            extracted from the switch by the Proxy Agent.  This object
            along with the g3ipdspsumintvl object allows the Network Manager
            to determine the validity of the ip dsp resource data in the cache and to 
            control when the Proxy Agent extracts the data from the switch."
        ::= { g3ipdspsum 1 }

    g3ipdspsumTintvl	OBJECT-TYPE
        SYNTAX    INTEGER
        ACCESS    read-write
        STATUS    mandatory
        DESCRIPTION
            "An object containing the interval for which the ip dsp resource
            data extracted from the switch is considered valid by the
            Proxy Agent.  When a GET or GET-NEXT request for the ip dsp resource 
            objects is received by the agent it uses the g3ipdspsumage
            and g3ipdspsumintvl objects to determine whether it should refresh
            the cached ipdspsumTable.  If g3ipdspsumstmp +
            g3ipdspsumintvl is less than the current value of the sysUpTime
            object then the agent refreshes the ipdspsumTable cache.  In
            either case it responds to the requests it receives with the data
            it currently has in the cache."
        ::= { g3ipdspsum 2 }

    g3ipdspsumTdelay	OBJECT-TYPE
        SYNTAX    INTEGER
        ACCESS    read-only
        STATUS    mandatory
        DESCRIPTION
            "An object containing the delay encountered in updating
            the cached data."
        ::= { g3ipdspsum 3 }

    g3ipdspsumTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3ipdspsum 4 }

    g3ipdspsumTcount	OBJECT-TYPE
        SYNTAX    Gauge
        ACCESS    read-only
        STATUS    mandatory
        DESCRIPTION
            "A Gauge object containing the number of data records in the cache."
        ::= { g3ipdspsum 5 }

    g3ipdspsumTable	OBJECT-TYPE
        SYNTAX    SEQUENCE OF G3ipdspsumEntry
        ACCESS    not-accessible
        STATUS    mandatory
        DESCRIPTION
            "A list of g3ipdspsum entries."
        ::= { g3ipdspsum 6 }

    g3ipdspsumEntry	OBJECT-TYPE
        SYNTAX    G3ipdspsumEntry
        ACCESS    not-accessible
        STATUS    mandatory
        DESCRIPTION
            "A g3ipdspsum entry containing objects of the
            g3ipdspsum information sent by the switch."
        INDEX    { g3ipdspsumRegion }
        ::= { g3ipdspsumTable 1 }

    G3ipdspsumEntry ::= SEQUENCE {
        g3ipdspsumRegion
            INTEGER,
        g3ipdspsumMeasHour
            INTEGER,
        g3ipdspsumYear
            INTEGER,
        g3ipdspsumMonth
            INTEGER,
        g3ipdspsumDay
            INTEGER,
        g3ipdspsumHour
            INTEGER,
        g3ipdspsumDSPRecs
            INTEGER,
        g3ipdspsumDSPUsage
            DisplayString,
        g3ipdspsumInRegion
            INTEGER,
        g3ipdspsumOutRegion
            INTEGER,
        g3ipdspsumDenied
            INTEGER,
        g3ipdspsumPctBlk
            DisplayString,
        g3ipdspsumPctOutSrv
            DisplayString
        }

    g3ipdspsumRegion	OBJECT-TYPE
        SYNTAX    INTEGER
        ACCESS    read-only
        STATUS    mandatory
        DESCRIPTION
            "An object containing the network region of the IP media processors being  
            measured. The region number is assigned on the Ip-interfaces screen during 
            switch administration.Range:1-44"
        ::= { g3ipdspsumEntry 1 }

    g3ipdspsumMeasHour	OBJECT-TYPE
        SYNTAX    INTEGER
        ACCESS    read-only
        STATUS    mandatory
        DESCRIPTION
            "An object containing the hour the measurement was taken"
        ::= { g3ipdspsumEntry 2 }

    g3ipdspsumYear	OBJECT-TYPE
        SYNTAX    INTEGER
        ACCESS    read-only
        STATUS    mandatory
        DESCRIPTION
            "An object containing the Year the command was executed"
        ::= { g3ipdspsumEntry 3 }

    g3ipdspsumMonth	OBJECT-TYPE
        SYNTAX    INTEGER
        ACCESS    read-only
        STATUS    mandatory
        DESCRIPTION
            "An object containing the Month the command was executed"
        ::= { g3ipdspsumEntry 4 }

    g3ipdspsumDay	OBJECT-TYPE
        SYNTAX    INTEGER
        ACCESS    read-only
        STATUS    mandatory
        DESCRIPTION
            "An object containing the Day the command was executed"
        ::= { g3ipdspsumEntry 5 }

    g3ipdspsumHour	OBJECT-TYPE
        SYNTAX    INTEGER
        ACCESS    read-only
        STATUS    mandatory
        DESCRIPTION
            "An object containing the Hour the command was executed"
        ::= { g3ipdspsumEntry 6 }

    g3ipdspsumDSPRecs	OBJECT-TYPE
        SYNTAX    INTEGER
        ACCESS    read-only
        STATUS    mandatory
        DESCRIPTION
            "An object containing the total number of IP codec resources, or voice
            channels, in the region. Range:0-9999"
        ::= { g3ipdspsumEntry 7 }

    g3ipdspsumDSPUsage	OBJECT-TYPE
        SYNTAX    DisplayString (SIZE (0..6))
        ACCESS    read-only
        STATUS    mandatory
        DESCRIPTION
            "An object containing the amount of time (in erlangs) that all codecs were    
            in use  during the measurement period. The time is measured from the time  
            the voice channel is allocated until it is released,including the time   
            that the voice channel is on a call. Range:0-9999"
        ::= { g3ipdspsumEntry 8 }

    g3ipdspsumInRegion	OBJECT-TYPE
        SYNTAX    INTEGER
        ACCESS    read-only
        STATUS    mandatory
        DESCRIPTION
            "An object containing the total number of times an IP media processor port 
            in the region was allocated to a call. Range:0-65535"
        ::= { g3ipdspsumEntry 9 }

    g3ipdspsumOutRegion	OBJECT-TYPE
        SYNTAX    INTEGER
        ACCESS    read-only
        STATUS    mandatory
        DESCRIPTION
            "An object containing the total number of times an IP media processor port  
            was needed in the region for a call, but was successfully allocated to a   
            resource in another region. Range:0-65535"
        ::= { g3ipdspsumEntry 10 }

    g3ipdspsumDenied	OBJECT-TYPE
        SYNTAX    INTEGER
        ACCESS    read-only
        STATUS    mandatory
        DESCRIPTION
            "An object containing the total number of times an IP media processor port  
            was needed in the region for a call, but all media ports in all regions 
            were busy and the call did not go through. Range:0-65535"
        ::= { g3ipdspsumEntry 11 }

    g3ipdspsumPctBlk	OBJECT-TYPE
        SYNTAX    DisplayString (SIZE (0..5))
        ACCESS    read-only
        STATUS    mandatory
        DESCRIPTION
            "An object containing"
        ::= { g3ipdspsumEntry 12 }

    g3ipdspsumPctOutSrv	OBJECT-TYPE
        SYNTAX    DisplayString (SIZE (0..5))
        ACCESS    read-only
        STATUS    mandatory
        DESCRIPTION
            "An object containing"
        ::= { g3ipdspsumEntry 13 }


    -- the g3pkipdspsum group

    g3pkipdspsumTage	OBJECT-TYPE
        SYNTAX    INTEGER
        ACCESS    read-only
        STATUS    mandatory
        DESCRIPTION
            "The number of timeticks since the peak ip dsp resource data was last
            extracted from the switch by the Proxy Agent.  This object
            along with the g3pkipdspsumintvl object allows the Network Manager
            to determine the validity of the peak ip dsp resource data in the cache 
            and to control	when the Proxy Agent extracts the data from the switch."
        ::= { g3pkipdspsum 1 }

    g3pkipdspsumTintvl	OBJECT-TYPE
        SYNTAX    INTEGER
        ACCESS    read-write
        STATUS    mandatory
        DESCRIPTION
            "An object containing the interval for which the peak ip dsp resource
            data extracted from the switch is considered valid by the
            Proxy Agent.  When a GET or GET-NEXT request for the peak ip dsp resource 
            objects is received by the agent it uses the g3pkipdspsumage
            and g3pkipdspsumintvl objects to determine whether it should refresh
            the cached pkipdspsumTable.  If g3pkipdspsumstmp +
            g3pkipdspsumintvl is less than the current value of the sysUpTime
            object then the agent refreshes the pkipdspsumTable cache.  In
            either case it responds to the requests it receives with the data
            it currently has in the cache."
        ::= { g3pkipdspsum 2 }

    g3pkipdspsumTdelay	OBJECT-TYPE
        SYNTAX    INTEGER
        ACCESS    read-only
        STATUS    mandatory
        DESCRIPTION
            "An object containing the delay encountered in updating
            the cached data."
        ::= { g3pkipdspsum 3 }

    g3pkipdspsumTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3pkipdspsum 4 }

    g3pkipdspsumTcount	OBJECT-TYPE
        SYNTAX    Gauge
        ACCESS    read-only
        STATUS    mandatory
        DESCRIPTION
            "A Gauge object containing the number of data records in the cache."
        ::= { g3pkipdspsum 5 }

    g3pkipdspsumTable	OBJECT-TYPE
        SYNTAX    SEQUENCE OF G3pkipdspsumEntry
        ACCESS    not-accessible
        STATUS    mandatory
        DESCRIPTION
            "A list of g3pkipdspsum entries."
        ::= { g3pkipdspsum 6 }

    g3pkipdspsumEntry	OBJECT-TYPE
        SYNTAX    G3pkipdspsumEntry
        ACCESS    not-accessible
        STATUS    mandatory
        DESCRIPTION
            "A g3pkipdspsum entry containing objects of the
            g3pkipdspsum information sent by the switch."
        INDEX    { g3pkipdspsumRegion }
        ::= { g3pkipdspsumTable 1 }

    G3pkipdspsumEntry ::= SEQUENCE {
        g3pkipdspsumRegion
            INTEGER,
        g3pkipdspsumMeasHour
            INTEGER,
        g3pkipdspsumYear
            INTEGER,
        g3pkipdspsumMonth
            INTEGER,
        g3pkipdspsumDay
            INTEGER,
        g3pkipdspsumHour
            INTEGER,
        g3pkipdspsumDSPRecs
            INTEGER,
        g3pkipdspsumDSPUsage
            DisplayString,
        g3pkipdspsumInRegion
            INTEGER,
        g3pkipdspsumOutRegion
            INTEGER,
        g3pkipdspsumDenied
            INTEGER,
        g3pkipdspsumPctBlk
            DisplayString,
        g3pkipdspsumPctOutSrv
            DisplayString
        }

    g3pkipdspsumRegion	OBJECT-TYPE
        SYNTAX    INTEGER
        ACCESS    read-only
        STATUS    mandatory
        DESCRIPTION
            "An object containing"
        ::= { g3pkipdspsumEntry 1 }

    g3pkipdspsumMeasHour	OBJECT-TYPE
        SYNTAX    INTEGER
        ACCESS    read-only
        STATUS    mandatory
        DESCRIPTION
            "An object containing the Hour the measurement was taken"
        ::= { g3pkipdspsumEntry 2 }

    g3pkipdspsumYear	OBJECT-TYPE
        SYNTAX    INTEGER
        ACCESS    read-only
        STATUS    mandatory
        DESCRIPTION
            "An object containing the Year the command was executed"
        ::= { g3pkipdspsumEntry 3 }

    g3pkipdspsumMonth	OBJECT-TYPE
        SYNTAX    INTEGER
        ACCESS    read-only
        STATUS    mandatory
        DESCRIPTION
            "An object containing the Month the command was executed"
        ::= { g3pkipdspsumEntry 4 }

    g3pkipdspsumDay	OBJECT-TYPE
        SYNTAX    INTEGER
        ACCESS    read-only
        STATUS    mandatory
        DESCRIPTION
            "An object containing the Day the command was executed"
        ::= { g3pkipdspsumEntry 5 }

    g3pkipdspsumHour	OBJECT-TYPE
        SYNTAX    INTEGER
        ACCESS    read-only
        STATUS    mandatory
        DESCRIPTION
            "An object containing the Hour the command was executed"
        ::= { g3pkipdspsumEntry 6 }

    g3pkipdspsumDSPRecs	OBJECT-TYPE
        SYNTAX    INTEGER
        ACCESS    read-only
        STATUS    mandatory
        DESCRIPTION
            "An object containing total number of IP codec resources, or voice 
            channels, in  the region. Range:0-9999"
        ::= { g3pkipdspsumEntry 7 }

    g3pkipdspsumDSPUsage	OBJECT-TYPE
        SYNTAX    DisplayString (SIZE (0..6))
        ACCESS    read-only
        STATUS    mandatory
        DESCRIPTION
            "An object containing amount of time (in erlangs) that all codecs were in  
            use during the measurement period. The time is measured from the time the   
            voice channel is allocated until it is released,including the time that  
            the voice channel is on a call. Range:0-9999"
        ::= { g3pkipdspsumEntry 8 }

    g3pkipdspsumInRegion	OBJECT-TYPE
        SYNTAX    INTEGER
        ACCESS    read-only
        STATUS    mandatory
        DESCRIPTION
            "An object containing the total number of times an IP media processor port  
            in the region was allocated to a call.Range:0-65535"
        ::= { g3pkipdspsumEntry 9 }

    g3pkipdspsumOutRegion	OBJECT-TYPE
        SYNTAX    INTEGER
        ACCESS    read-only
        STATUS    mandatory
        DESCRIPTION
            "An object containing the total number of times an IP media processor port  
            was needed in the region for a call, but was successfully allocated to a  
            resource in another region. Range: 0-65535"
        ::= { g3pkipdspsumEntry 10 }

    g3pkipdspsumDenied	OBJECT-TYPE
        SYNTAX    INTEGER
        ACCESS    read-only
        STATUS    mandatory
        DESCRIPTION
            "An object containing The total number of times an IP media processor port   
            was needed in the region for a call, but all media ports in all
            regions were busy and the call did not go through. Range:0-65535"
        ::= { g3pkipdspsumEntry 11 }

    g3pkipdspsumPctBlk	OBJECT-TYPE
        SYNTAX    DisplayString (SIZE (0..5))
        ACCESS    read-only
        STATUS    mandatory
        DESCRIPTION
            "An object containing the percent of attempted use of IP media processor   
            ports in the region that were not successful (blocked). This percent  
            includes calls that were denied after they were successfully allocated out   
            of the region. "
        ::= { g3pkipdspsumEntry 12 }

    g3pkipdspsumPctOutSrv	OBJECT-TYPE
        SYNTAX    DisplayString (SIZE (0..5))
        ACCESS    read-only
        STATUS    mandatory
        DESCRIPTION
            "An object containing the percent of CCS time that any IP media processor   
            ports were out of service during the measurement period. This
            percent includes ports that were manually busied out or maintenance busy    
            during the measured interval."
        ::= { g3pkipdspsumEntry 13 }


    -- the g3ipsignal group

    g3ipsignalTage	OBJECT-TYPE
        SYNTAX    INTEGER
        ACCESS    read-only
        STATUS    mandatory
        DESCRIPTION
            "The number of timeticks since the ip signaling group data was last
            extracted from the switch by the Proxy Agent.  This object
            along with the g3ipsignalintvl object allows the Network Manager
            to determine the validity of the ip signaling group data in the cache and 
            to control	when the Proxy Agent extracts the data from the switch."
        ::= { g3ipsignal 1 }

    g3ipsignalTintvl	OBJECT-TYPE
        SYNTAX    INTEGER
        ACCESS    read-write
        STATUS    mandatory
        DESCRIPTION
            "An object containing the interval for which the ip signaling group
            data extracted from the switch is considered valid by the
            Proxy Agent.  When a GET or GET-NEXT request for the ip signaling group 
            objects is received by the agent it uses the g3ipsignalage
            and g3ipsignalintvl objects to determine whether it should refresh
            the cached ipsignalTable.  If g3ipsignalstmp +
            g3ipsignalintvl is less than the current value of the sysUpTime
            object then the agent refreshes the ipsignalTable cache.  In
            either case it responds to the requests it receives with the data
            it currently has in the cache."
        ::= { g3ipsignal 2 }

    g3ipsignalTdelay	OBJECT-TYPE
        SYNTAX    INTEGER
        ACCESS    read-only
        STATUS    mandatory
        DESCRIPTION
            "An object containing the delay encountered in updating
            the cached data."
        ::= { g3ipsignal 3 }

    g3ipsignalTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3ipsignal 4 }

    g3ipsignalTcount	OBJECT-TYPE
        SYNTAX    Gauge
        ACCESS    read-only
        STATUS    mandatory
        DESCRIPTION
            "A Gauge object containing the number of data records in the cache."
        ::= { g3ipsignal 5 }

    g3ipsignalTable	OBJECT-TYPE
        SYNTAX    SEQUENCE OF G3ipsignalEntry
        ACCESS    not-accessible
        STATUS    mandatory
        DESCRIPTION
            "A list of g3ipsignal entries."
        ::= { g3ipsignal 6 }

    g3ipsignalEntry	OBJECT-TYPE
        SYNTAX    G3ipsignalEntry
        ACCESS    not-accessible
        STATUS    mandatory
        DESCRIPTION
            "A g3ipsignal entry containing objects of the
            g3ipsignal information sent by the switch."
        INDEX    { g3ipsignalSigGroup }
        ::= { g3ipsignalTable 1 }

    G3ipsignalEntry ::= SEQUENCE {
        g3ipsignalSigGroup
            INTEGER,
        g3ipsignalRegion
            INTEGER,
        g3ipsignalYear
            INTEGER,
        g3ipsignalMonth
            INTEGER,
        g3ipsignalDay
            INTEGER,
        g3ipsignalHour
            INTEGER,
        g3ipsignalHourAvgLatency
            INTEGER,
        g3ipsignalHourPacketsSent
            INTEGER,
        g3ipsignalHourPktsLostPct
            INTEGER,
        g3ipsignalMeasHour
            INTEGER,
        g3ipsignalWorstInterval
            INTEGER,
        g3ipsignalIntvlAvgLatency
            INTEGER,
        g3ipsignalIntvlPacketsSent
            INTEGER,
        g3ipsignalIntvlPktsLostPct
            INTEGER
        }

    g3ipsignalSigGroup	OBJECT-TYPE
        SYNTAX    INTEGER
        ACCESS    read-only
        STATUS    mandatory
        DESCRIPTION
            "An object containing the ip signaling group number"
        ::= { g3ipsignalEntry 1 }

    g3ipsignalRegion	OBJECT-TYPE
        SYNTAX    INTEGER
        ACCESS    read-only
        STATUS    mandatory
        DESCRIPTION
            "An object containing the network region of the ip signaling group"
        ::= { g3ipsignalEntry 2 }

    g3ipsignalYear	OBJECT-TYPE
        SYNTAX    INTEGER
        ACCESS    read-only
        STATUS    mandatory
        DESCRIPTION
            "An object containing the Year the command was executed"
        ::= { g3ipsignalEntry 3 }

    g3ipsignalMonth	OBJECT-TYPE
        SYNTAX    INTEGER
        ACCESS    read-only
        STATUS    mandatory
        DESCRIPTION
            "An object containing the Month the command was executed"
        ::= { g3ipsignalEntry 4 }

    g3ipsignalDay	OBJECT-TYPE
        SYNTAX    INTEGER
        ACCESS    read-only
        STATUS    mandatory
        DESCRIPTION
            "An object containing the Day the command was executed"
        ::= { g3ipsignalEntry 5 }

    g3ipsignalHour	OBJECT-TYPE
        SYNTAX    INTEGER
        ACCESS    read-only
        STATUS    mandatory
        DESCRIPTION
            "An object containing the Hour the command was executed"
        ::= { g3ipsignalEntry 6 }

    g3ipsignalHourAvgLatency	OBJECT-TYPE
        SYNTAX    INTEGER
        ACCESS    read-only
        STATUS    mandatory
        DESCRIPTION
            "An object containing the average latency for the whole hour"
        ::= { g3ipsignalEntry 7 }

    g3ipsignalHourPacketsSent	OBJECT-TYPE
        SYNTAX    INTEGER
        ACCESS    read-only
        STATUS    mandatory
        DESCRIPTION
            "An object containing the number of packets sent during the whole hour"
        ::= { g3ipsignalEntry 8 }

    g3ipsignalHourPktsLostPct	OBJECT-TYPE
        SYNTAX    INTEGER
        ACCESS    read-only
        STATUS    mandatory
        DESCRIPTION
            "An object containing the percent lost packets for the whole hour"
        ::= { g3ipsignalEntry 9 }

    g3ipsignalMeasHour	OBJECT-TYPE
        SYNTAX    INTEGER
        ACCESS    read-only
        STATUS    mandatory
        DESCRIPTION
            "An object containing the Hour the measurement was taken"
        ::= { g3ipsignalEntry 10 }

    g3ipsignalWorstInterval	OBJECT-TYPE
        SYNTAX    INTEGER
        ACCESS    read-only
        STATUS    mandatory
        DESCRIPTION
            "An object containing the hour and worst 3 minute interval within the hour."
        ::= { g3ipsignalEntry 11 }

    g3ipsignalIntvlAvgLatency	OBJECT-TYPE
        SYNTAX    INTEGER
        ACCESS    read-only
        STATUS    mandatory
        DESCRIPTION
            "An object containing the average latency for the interval."
        ::= { g3ipsignalEntry 12 }

    g3ipsignalIntvlPacketsSent	OBJECT-TYPE
        SYNTAX    INTEGER
        ACCESS    read-only
        STATUS    mandatory
        DESCRIPTION
            "An object containing the number of packets sent during the interval."
        ::= { g3ipsignalEntry 13 }

    g3ipsignalIntvlPktsLostPct	OBJECT-TYPE
        SYNTAX    INTEGER
        ACCESS    read-only
        STATUS    mandatory
        DESCRIPTION
            "An object containing the percent of packets lost  for the interval"
        ::= { g3ipsignalEntry 14 }


    -- the g3pkipsignal group

    g3pkipsignalTage	OBJECT-TYPE
        SYNTAX    INTEGER
        ACCESS    read-only
        STATUS    mandatory
        DESCRIPTION
            "The number of timeticks since the peak ip signaling group data was last
            extracted from the switch by the Proxy Agent.  This object
            along with the g3pkipsignalintvl object allows the Network Manager
            to determine the validity of the peak ip signaling group data in the cache 
            and to control when the Proxy Agent extracts the data from the switch."
        ::= { g3pkipsignal 1 }

    g3pkipsignalTintvl	OBJECT-TYPE
        SYNTAX    INTEGER
        ACCESS    read-write
        STATUS    mandatory
        DESCRIPTION
            "An object containing the interval for which the peak ip signaling
            group	data extracted from the switch is considered valid by the
            Proxy Agent.  When a GET or GET-NEXT request for the peak ip signaling  
            group objects is received by the agent it uses the g3pkipsignalage
            and g3pkipsignalintvl objects to determine whether it should refresh
            the cached pkipsignalTable.  If g3pkipsignalstmp +
            g3pkipsignalintvl is less than the current value of the sysUpTime
            object then the agent refreshes the pkipsignalTable cache.  In
            either case it responds to the requests it receives with the data
            it currently has in the cache."
        ::= { g3pkipsignal 2 }

    g3pkipsignalTdelay	OBJECT-TYPE
        SYNTAX    INTEGER
        ACCESS    read-only
        STATUS    mandatory
        DESCRIPTION
            "An object containing the delay encountered in updating
            the cached data."
        ::= { g3pkipsignal 3 }

    g3pkipsignalTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3pkipsignal 4 }

    g3pkipsignalTcount	OBJECT-TYPE
        SYNTAX    Gauge
        ACCESS    read-only
        STATUS    mandatory
        DESCRIPTION
            "A Gauge object containing the number of data records in the cache."
        ::= { g3pkipsignal 5 }

    g3pkipsignalTable	OBJECT-TYPE
        SYNTAX    SEQUENCE OF G3pkipsignalEntry
        ACCESS    not-accessible
        STATUS    mandatory
        DESCRIPTION
            "A list of g3pkipsignal entries."
        ::= { g3pkipsignal 6 }

    g3pkipsignalEntry	OBJECT-TYPE
        SYNTAX    G3pkipsignalEntry
        ACCESS    not-accessible
        STATUS    mandatory
        DESCRIPTION
            "A g3pkipsignal entry containing objects of the
            g3pkipsignal information sent by the switch."
        INDEX    { g3pkipsignalSigGroup, g3pkipsignalMeasHour }
        ::= { g3pkipsignalTable 1 }

    G3pkipsignalEntry ::= SEQUENCE {
        g3pkipsignalSigGroup
            INTEGER,
        g3pkipsignalRegion
            INTEGER,
        g3pkipsignalYear
            INTEGER,
        g3pkipsignalMonth
            INTEGER,
        g3pkipsignalDay
            INTEGER,
        g3pkipsignalHour
            INTEGER,
        g3pkipsignalHourAvgLatency
            INTEGER,
        g3pkipsignalHourPacketsSent
            INTEGER,
        g3pkipsignalHourPktsLostPct
            INTEGER,
        g3pkipsignalMeasHour
            INTEGER,
        g3pkipsignalWorstInterval
            INTEGER,
        g3pkipsignalIntvlAvgLatency
            INTEGER,
        g3pkipsignalIntvlPacketsSent
            INTEGER,
        g3pkipsignalIntvlPktsLostPct
            INTEGER
        }

    g3pkipsignalSigGroup	OBJECT-TYPE
        SYNTAX    INTEGER
        ACCESS    read-only
        STATUS    mandatory
        DESCRIPTION
            "An object containing the ip signaling group number"
        ::= { g3pkipsignalEntry 1 }

    g3pkipsignalRegion	OBJECT-TYPE
        SYNTAX    INTEGER
        ACCESS    read-only
        STATUS    mandatory
        DESCRIPTION
            "An object containing the network region of the ip signaling group"
        ::= { g3pkipsignalEntry 2 }

    g3pkipsignalYear	OBJECT-TYPE
        SYNTAX    INTEGER
        ACCESS    read-only
        STATUS    mandatory
        DESCRIPTION
            "An object containing the Year the command was executed"
        ::= { g3pkipsignalEntry 3 }

    g3pkipsignalMonth	OBJECT-TYPE
        SYNTAX    INTEGER
        ACCESS    read-only
        STATUS    mandatory
        DESCRIPTION
            "An object containing the Month the command was executed"
        ::= { g3pkipsignalEntry 4 }

    g3pkipsignalDay	OBJECT-TYPE
        SYNTAX    INTEGER
        ACCESS    read-only
        STATUS    mandatory
        DESCRIPTION
            "An object containing the Day the command was executed"
        ::= { g3pkipsignalEntry 5 }

    g3pkipsignalHour	OBJECT-TYPE
        SYNTAX    INTEGER
        ACCESS    read-only
        STATUS    mandatory
        DESCRIPTION
            "An object containing the Hour the command was executed"
        ::= { g3pkipsignalEntry 6 }

    g3pkipsignalHourAvgLatency	OBJECT-TYPE
        SYNTAX    INTEGER
        ACCESS    read-only
        STATUS    mandatory
        DESCRIPTION
            "An object containing the average latency for the whole hour"
        ::= { g3pkipsignalEntry 7 }

    g3pkipsignalHourPacketsSent	OBJECT-TYPE
        SYNTAX    INTEGER
        ACCESS    read-only
        STATUS    mandatory
        DESCRIPTION
            "An object containing the number of packets sent during the whole hour"
        ::= { g3pkipsignalEntry 8 }

    g3pkipsignalHourPktsLostPct	OBJECT-TYPE
        SYNTAX    INTEGER
        ACCESS    read-only
        STATUS    mandatory
        DESCRIPTION
            "An object containing the percent of packets  lost for the whole hour"
        ::= { g3pkipsignalEntry 9 }

    g3pkipsignalMeasHour	OBJECT-TYPE
        SYNTAX    INTEGER
        ACCESS    read-only
        STATUS    mandatory
        DESCRIPTION
            "An object containing the Hour the measurement was taken"
        ::= { g3pkipsignalEntry 10 }

    g3pkipsignalWorstInterval	OBJECT-TYPE
        SYNTAX    INTEGER
        ACCESS    read-only
        STATUS    mandatory
        DESCRIPTION
            "An object containing the hour and worst 3 minute interval within the hour"
        ::= { g3pkipsignalEntry 11 }

    g3pkipsignalIntvlAvgLatency	OBJECT-TYPE
        SYNTAX    INTEGER
        ACCESS    read-only
        STATUS    mandatory
        DESCRIPTION
            "An object containing the average latency for the interval"
        ::= { g3pkipsignalEntry 12 }

    g3pkipsignalIntvlPacketsSent	OBJECT-TYPE
        SYNTAX    INTEGER
        ACCESS    read-only
        STATUS    mandatory
        DESCRIPTION
            "An object containing the number of packets sent during the interval"
        ::= { g3pkipsignalEntry 13 }

    g3pkipsignalIntvlPktsLostPct	OBJECT-TYPE
        SYNTAX    INTEGER
        ACCESS    read-only
        STATUS    mandatory
        DESCRIPTION
            "An object containing the percent of packets lost for the interval"
        ::= { g3pkipsignalEntry 14 }


    -- the g3annall group

    g3annallTage	OBJECT-TYPE
        SYNTAX    INTEGER
        ACCESS    read-only
        STATUS    mandatory
        DESCRIPTION
            "The number of timeticks since the announcement data was last
            extracted from the switch by the Proxy Agent.  This object
            along with the g3annallintvl object allows the Network Manager
            to determine the validity of the announcement data in the cache and to 
            control	when the Proxy Agent extracts the data from the switch."
        ::= { g3annall 1 }

    g3annallTintvl	OBJECT-TYPE
        SYNTAX    INTEGER
        ACCESS    read-write
        STATUS    mandatory
        DESCRIPTION
            "An object containing the interval for which the announcement
            data extracted from the switch is considered valid by the
            Proxy Agent.  When a GET or GET-NEXT request for the announcement 
            objects is received by the agent it uses the g3annallage
            and g3annallintvl objects to determine whether it should refresh
            the cached annallTable.  If g3annallstmp +
            g3annallintvl is less than the current value of the sysUpTime
            object then the agent refreshes the annallTable cache.  In
            either case it responds to the requests it receives with the data
            it currently has in the cache."
        ::= { g3annall 2 }

    g3annallTdelay	OBJECT-TYPE
        SYNTAX    INTEGER
        ACCESS    read-only
        STATUS    mandatory
        DESCRIPTION
            "An object containing the delay encountered in updating
            the cached data."
        ::= { g3annall 3 }

    g3annallTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3annall 4 }

    g3annallTcount	OBJECT-TYPE
        SYNTAX    Gauge
        ACCESS    read-only
        STATUS    mandatory
        DESCRIPTION
            "A Gauge object containing the number of data records in the cache."
        ::= { g3annall 5 }

    g3annallTable	OBJECT-TYPE
        SYNTAX    SEQUENCE OF G3annallEntry
        ACCESS    not-accessible
        STATUS    mandatory
        DESCRIPTION
            "A list of g3annall entries."
        ::= { g3annall 6 }

    g3annallEntry	OBJECT-TYPE
        SYNTAX    G3annallEntry
        ACCESS    not-accessible
        STATUS    mandatory
        DESCRIPTION
            "A g3annall entry containing objects of the
            g3annall information sent by the switch."
        INDEX    { g3annallExtension }
        ::= { g3annallTable 1 }

    G3annallEntry ::= SEQUENCE {
        g3annallAnnNbr
            INTEGER,
        g3annallYear
            INTEGER,
        g3annallMonth
            INTEGER,
        g3annallDay
            INTEGER,
        g3annallHour
            INTEGER,
        g3annallExtension
            DisplayString,
        g3annallName
            DisplayString,
        g3annallMeasHour
            INTEGER,
        g3annallPlayRequests
            INTEGER,
        g3annallCallsQueued
            INTEGER,
        g3annallASP
            INTEGER,
        g3annallQueueDrops
            INTEGER,
        g3annallMPortPlay
            INTEGER,
        g3annallMaxPorts
            INTEGER,
        g3annallMaxCallers
            INTEGER
        }

    g3annallAnnNbr	OBJECT-TYPE
        SYNTAX    INTEGER
        ACCESS    read-only
        STATUS    mandatory
        DESCRIPTION
            "An object containing the announcement number. This field is
            no longer applicable and the table is sorted by the
            g3annallExtension field instead since the announcement number
            not longer applies in CM starting with CM 4.0."
        ::= { g3annallEntry 1 }

    g3annallYear	OBJECT-TYPE
        SYNTAX    INTEGER
        ACCESS    read-only
        STATUS    mandatory
        DESCRIPTION
            "An object containing the Year the command was executed"
        ::= { g3annallEntry 2 }

    g3annallMonth	OBJECT-TYPE
        SYNTAX    INTEGER
        ACCESS    read-only
        STATUS    mandatory
        DESCRIPTION
            "An object containing the Month the command was executed"
        ::= { g3annallEntry 3 }

    g3annallDay	OBJECT-TYPE
        SYNTAX    INTEGER
        ACCESS    read-only
        STATUS    mandatory
        DESCRIPTION
            "An object containing the Day the command was executed"
        ::= { g3annallEntry 4 }

    g3annallHour	OBJECT-TYPE
        SYNTAX    INTEGER
        ACCESS    read-only
        STATUS    mandatory
        DESCRIPTION
            "An object containing the Hour the command was executed"
        ::= { g3annallEntry 5 }

    g3annallExtension	OBJECT-TYPE
        SYNTAX    DisplayString (SIZE (0..15))
        ACCESS    read-only
        STATUS    mandatory
        DESCRIPTION
            "An object containing the extension number for the announcement"
        ::= { g3annallEntry 6 }

    g3annallName	OBJECT-TYPE
        SYNTAX    DisplayString (SIZE (0..24))
        ACCESS    read-only
        STATUS    mandatory
        DESCRIPTION
            "An object containing the first 24 characters of the announcement"
        ::= { g3annallEntry 7 }

    g3annallMeasHour	OBJECT-TYPE
        SYNTAX    INTEGER
        ACCESS    read-only
        STATUS    mandatory
        DESCRIPTION
            "An object containing the Hour the measurement was taken"
        ::= { g3annallEntry 8 }

    g3annallPlayRequests	OBJECT-TYPE
        SYNTAX    INTEGER
        ACCESS    read-only
        STATUS    mandatory
        DESCRIPTION
            "An object containing total number of calls that requested a play of
            this announcement during the period"
        ::= { g3annallEntry 9 }

    g3annallCallsQueued	OBJECT-TYPE
        SYNTAX    INTEGER
        ACCESS    read-only
        STATUS    mandatory
        DESCRIPTION
            "An object containing the number of calls for an announcement that had
            to queue waiting for a port during the period"
        ::= { g3annallEntry 10 }

    g3annallASP	OBJECT-TYPE
        SYNTAX    INTEGER
        ACCESS    read-only
        STATUS    mandatory
        DESCRIPTION
            "An object containing from time waiting for announcement to play to
            when it starts playing in seconds averaged over the period.  Calls
            abandoned while in the waiting for announcement port queue are not to
            be included"
        ::= { g3annallEntry 11 }

    g3annallQueueDrops	OBJECT-TYPE
        SYNTAX    INTEGER
        ACCESS    read-only
        STATUS    mandatory
        DESCRIPTION
            "An object containing - count of the individual calls that had to queue
            but dropped while waiting during the period - this includes calls
            abandoned by the caller and VOA (VDN of origin Announcements) aborts
            but should exclude calls that were waiting but answered by an agent"
        ::= { g3annallEntry 12 }

    g3annallMPortPlay	OBJECT-TYPE
        SYNTAX    INTEGER
        ACCESS    read-only
        STATUS    mandatory
        DESCRIPTION
            "An object containing - count of how many times the announcement is
            being played out of more than one port at the same time during the
            period"
        ::= { g3annallEntry 13 }

    g3annallMaxPorts	OBJECT-TYPE
        SYNTAX    INTEGER
        ACCESS    read-only
        STATUS    mandatory
        DESCRIPTION
            "An object containing the peak number of ports used for the
            announcement during the period"
        ::= { g3annallEntry 14 }

    g3annallMaxCallers	OBJECT-TYPE
        SYNTAX    INTEGER
        ACCESS    read-only
        STATUS    mandatory
        DESCRIPTION
            "An object containing the peak number callers connected to a port at
            the same time for this announcement during the period"
        ::= { g3annallEntry 15 }


    -- the g3pkannall group

    g3pkannallTage	OBJECT-TYPE
        SYNTAX    INTEGER
        ACCESS    read-only
        STATUS    mandatory
        DESCRIPTION
            "The number of timeticks since the announcement data was last
            extracted from the switch by the Proxy Agent.  This object
            along with the g3pkannallintvl object allows the Network Manager
            to determine the validity of the announcement data in the cache and to 
            control when the Proxy Agent extracts the data from the switch."
        ::= { g3pkannall 1 }

    g3pkannallTintvl	OBJECT-TYPE
        SYNTAX    INTEGER
        ACCESS    read-write
        STATUS    mandatory
        DESCRIPTION
            "An object containing the interval for which the Announcement data 
            extracted from the switch is considered valid by the
            Proxy Agent.  When a GET or GET-NEXT request for the announcement 
            objects is received by the agent it uses the g3pkannallage
            and g3pkannallintvl objects to determine whether it should refresh
            the cached pkannallTable.  If g3pkannallstmp +
            g3pkannallintvl is less than the current value of the sysUpTime
            object then the agent refreshes the pkannallTable cache.  In
            either case it responds to the requests it receives with the data
            it currently has in the cache."
        ::= { g3pkannall 2 }

    g3pkannallTdelay	OBJECT-TYPE
        SYNTAX    INTEGER
        ACCESS    read-only
        STATUS    mandatory
        DESCRIPTION
            "An object containing the delay encountered in updating
            the cached data."
        ::= { g3pkannall 3 }

    g3pkannallTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3pkannall 4 }

    g3pkannallTcount	OBJECT-TYPE
        SYNTAX    Gauge
        ACCESS    read-only
        STATUS    mandatory
        DESCRIPTION
            "A Gauge object containing the number of data records in the cache."
        ::= { g3pkannall 5 }

    g3pkannallTable	OBJECT-TYPE
        SYNTAX    SEQUENCE OF G3pkannallEntry
        ACCESS    not-accessible
        STATUS    mandatory
        DESCRIPTION
            "A list of g3pkannall entries."
        ::= { g3pkannall 6 }

    g3pkannallEntry	OBJECT-TYPE
        SYNTAX    G3pkannallEntry
        ACCESS    not-accessible
        STATUS    mandatory
        DESCRIPTION
            "A g3pkannall entry containing objects of the
            g3pkannall information sent by the switch."
        INDEX    { g3pkannallExtension }
        ::= { g3pkannallTable 1 }

    G3pkannallEntry ::= SEQUENCE {
        g3pkannallAnnNbr
            INTEGER,
        g3pkannallYear
            INTEGER,
        g3pkannallMonth
            INTEGER,
        g3pkannallDay
            INTEGER,
        g3pkannallHour
            INTEGER,
        g3pkannallExtension
            DisplayString,
        g3pkannallName
            DisplayString,
        g3pkannallMeasHour
            INTEGER,
        g3pkannallPlayRequests
            INTEGER,
        g3pkannallCallsQueued
            INTEGER,
        g3pkannallASP
            INTEGER,
        g3pkannallQueueDrops
            INTEGER,
        g3pkannallMPortPlay
            INTEGER,
        g3pkannallMaxPorts
            INTEGER,
        g3pkannallMaxCall
            INTEGER
        }

    g3pkannallAnnNbr	OBJECT-TYPE
        SYNTAX    INTEGER
        ACCESS    read-only
        STATUS    mandatory
        DESCRIPTION
            "An object containing the announcement number. This field is
            no longer applicable and the table is sorted by the
            g3pkannallExtension field instead since the announcement number
            not longer applies in CM starting with CM 4.0."
        ::= { g3pkannallEntry 1 }

    g3pkannallYear	OBJECT-TYPE
        SYNTAX    INTEGER
        ACCESS    read-only
        STATUS    mandatory
        DESCRIPTION
            "An object containing the Year the command was executed"
        ::= { g3pkannallEntry 2 }

    g3pkannallMonth	OBJECT-TYPE
        SYNTAX    INTEGER
        ACCESS    read-only
        STATUS    mandatory
        DESCRIPTION
            "An object containing the Month the command was executed"
        ::= { g3pkannallEntry 3 }

    g3pkannallDay	OBJECT-TYPE
        SYNTAX    INTEGER
        ACCESS    read-only
        STATUS    mandatory
        DESCRIPTION
            "An object containing the Day the command was executed"
        ::= { g3pkannallEntry 4 }

    g3pkannallHour	OBJECT-TYPE
        SYNTAX    INTEGER
        ACCESS    read-only
        STATUS    mandatory
        DESCRIPTION
            "An object containing the Hour the command was executed"
        ::= { g3pkannallEntry 5 }

    g3pkannallExtension	OBJECT-TYPE
        SYNTAX    DisplayString (SIZE (0..15))
        ACCESS    read-only
        STATUS    mandatory
        DESCRIPTION
            "An object containing the extension number for the announcement"
        ::= { g3pkannallEntry 6 }

    g3pkannallName	OBJECT-TYPE
        SYNTAX    DisplayString (SIZE (0..24))
        ACCESS    read-only
        STATUS    mandatory
        DESCRIPTION
            "An object containing the first 24 characters of the announcement"
        ::= { g3pkannallEntry 7 }

    g3pkannallMeasHour	OBJECT-TYPE
        SYNTAX    INTEGER
        ACCESS    read-only
        STATUS    mandatory
        DESCRIPTION
            "An object containing the Hour the measurement was taken"
        ::= { g3pkannallEntry 8 }

    g3pkannallPlayRequests	OBJECT-TYPE
        SYNTAX    INTEGER
        ACCESS    read-only
        STATUS    mandatory
        DESCRIPTION
            "An object containing total number of calls that requested a play of
            this announcement during the period"
        ::= { g3pkannallEntry 9 }

    g3pkannallCallsQueued	OBJECT-TYPE
        SYNTAX    INTEGER
        ACCESS    read-only
        STATUS    mandatory
        DESCRIPTION
            "An object containing number of calls for an announcement that had to
            queue waiting for a port during the period"
        ::= { g3pkannallEntry 10 }

    g3pkannallASP	OBJECT-TYPE
        SYNTAX    INTEGER
        ACCESS    read-only
        STATUS    mandatory
        DESCRIPTION
            "An object containing from time waiting for announcement to play to
            when it starts playing in seconds averaged over the period.  Calls
            abandoned while in the waiting for announcement port queue are not to
            be included"
        ::= { g3pkannallEntry 11 }

    g3pkannallQueueDrops	OBJECT-TYPE
        SYNTAX    INTEGER
        ACCESS    read-only
        STATUS    mandatory
        DESCRIPTION
            "An object containing count of the individual calls that had to queue
            but dropped while waiting during the period - this includes calls
            abandoned by the caller and VOA (VDN of origin Announcements) aborts
            but should exclude calls that were waiting but answered by an agent)"
        ::= { g3pkannallEntry 12 }

    g3pkannallMPortPlay	OBJECT-TYPE
        SYNTAX    INTEGER
        ACCESS    read-only
        STATUS    mandatory
        DESCRIPTION
            "An object containing count of how many times the announcement is being
            played out of more than one port at the same time during the period"
        ::= { g3pkannallEntry 13 }

    g3pkannallMaxPorts	OBJECT-TYPE
        SYNTAX    INTEGER
        ACCESS    read-only
        STATUS    mandatory
        DESCRIPTION
            "An object containing the peak number of ports used for the
            announcement during the period"
        ::= { g3pkannallEntry 14 }

    g3pkannallMaxCall	OBJECT-TYPE
        SYNTAX    INTEGER
        ACCESS    read-only
        STATUS    mandatory
        DESCRIPTION
            "An object containing the peak number callers connected to a port at
            the same time for this announcement during the period"
        ::= { g3pkannallEntry 15 }


    -- the g3anninteg group

    g3annintegTage	OBJECT-TYPE
        SYNTAX    INTEGER
        ACCESS    read-only
        STATUS    mandatory
        DESCRIPTION
            "The number of timeticks since the data was last
            extracted from the switch by the Proxy Agent.  This object
            along with the g3annintegintvl object allows the Network Manager
            to determine the validity of the data in the cache and to control
            when the Proxy Agent extracts the data from the switch."
        ::= { g3anninteg 1 }

    g3annintegTintvl	OBJECT-TYPE
        SYNTAX    INTEGER
        ACCESS    read-write
        STATUS    mandatory
        DESCRIPTION
            "An object containing the interval for which the
            data extracted from the switch is considered valid by the
            Proxy Agent.  When a GET or GET-NEXT request for these data
            objects is received by the agent it uses the g3annintegage
            and g3annintegintvl objects to determine whether it should refresh
            the cached annintegTable.  If g3annintegstmp +
            g3annintegintvl is less than the current value of the sysUpTime
            object then the agent refreshes the annintegTable cache.  In
            either case it responds to the requests it receives with the data
            it currently has in the cache."
        ::= { g3anninteg 2 }

    g3annintegTdelay	OBJECT-TYPE
        SYNTAX    INTEGER
        ACCESS    read-only
        STATUS    mandatory
        DESCRIPTION
            "An object containing the delay encountered in updating
            the cached data."
        ::= { g3anninteg 3 }

    g3annintegTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3anninteg 4 }

    g3annintegTcount	OBJECT-TYPE
        SYNTAX    Gauge
        ACCESS    read-only
        STATUS    mandatory
        DESCRIPTION
            "A Gauge object containing the number of data records in the cache."
        ::= { g3anninteg 5 }

    g3annintegTable	OBJECT-TYPE
        SYNTAX    SEQUENCE OF G3annintegEntry
        ACCESS    not-accessible
        STATUS    mandatory
        DESCRIPTION
            "A list of g3anninteg entries."
        ::= { g3anninteg 6 }

    g3annintegEntry	OBJECT-TYPE
        SYNTAX    G3annintegEntry
        ACCESS    not-accessible
        STATUS    mandatory
        DESCRIPTION
            "A g3anninteg entry containing objects of the
            g3anninteg information sent by the switch."
        INDEX    { g3annintegExtension }
        ::= { g3annintegTable 1 }

    G3annintegEntry ::= SEQUENCE {
        g3annintegBoard
            DisplayString,
        g3annintegYear
            INTEGER,
        g3annintegMonth
            INTEGER,
        g3annintegDay
            INTEGER,
        g3annintegHour
            INTEGER,
        g3annintegPlayPorts
            INTEGER,
        g3annintegMaxCallPeriod
            INTEGER,
        g3annintegAllPortsBusy
            INTEGER,
        g3annintegAnnNbr
            INTEGER,
        g3annintegExtension
            DisplayString,
        g3annintegName
            DisplayString,
        g3annintegMeasHour
            INTEGER,
        g3annintegPlayReqts
            INTEGER,
        g3annintegCallsQueued
            INTEGER,
        g3annintegASP
            INTEGER,
        g3annintegQueueDrops
            INTEGER,
        g3annintegMPortPlay
            INTEGER,
        g3annintegMaxPorts
            INTEGER,
        g3annintegMaxCall
            INTEGER
        }

    g3annintegBoard	OBJECT-TYPE
        SYNTAX    DisplayString (SIZE (0..5))
        ACCESS    read-only
        STATUS    mandatory
        DESCRIPTION
            "An object containing the board number for the integrated announcement board"
        ::= { g3annintegEntry 1 }

    g3annintegYear	OBJECT-TYPE
        SYNTAX    INTEGER
        ACCESS    read-only
        STATUS    mandatory
        DESCRIPTION
            "An object containing the Year the command was executed"
        ::= { g3annintegEntry 2 }

    g3annintegMonth	OBJECT-TYPE
        SYNTAX    INTEGER
        ACCESS    read-only
        STATUS    mandatory
        DESCRIPTION
            "An object containing the Month the command was executed"
        ::= { g3annintegEntry 3 }

    g3annintegDay	OBJECT-TYPE
        SYNTAX    INTEGER
        ACCESS    read-only
        STATUS    mandatory
        DESCRIPTION
            "An object containing the Day the command was executed"
        ::= { g3annintegEntry 4 }

    g3annintegHour	OBJECT-TYPE
        SYNTAX    INTEGER
        ACCESS    read-only
        STATUS    mandatory
        DESCRIPTION
            "An object containing the Hour the command was executed"
        ::= { g3annintegEntry 5 }

    g3annintegPlayPorts	OBJECT-TYPE
        SYNTAX    INTEGER
        ACCESS    read-only
        STATUS    mandatory
        DESCRIPTION
            "An object containing "
        ::= { g3annintegEntry 6 }

    g3annintegMaxCallPeriod	OBJECT-TYPE
        SYNTAX    INTEGER
        ACCESS    read-only
        STATUS    mandatory
        DESCRIPTION
            "An object containing"
        ::= { g3annintegEntry 7 }

    g3annintegAllPortsBusy	OBJECT-TYPE
        SYNTAX    INTEGER
        ACCESS    read-only
        STATUS    mandatory
        DESCRIPTION
            "An object containing an indication of how frequently the
            all-ports-busy condition occurs within the period of time"
        ::= { g3annintegEntry 8 }

    g3annintegAnnNbr	OBJECT-TYPE
        SYNTAX    INTEGER
        ACCESS    read-only
        STATUS    mandatory
        DESCRIPTION
            "An object containing the announcement number. This field is
            no longer applicable and the table is sorted by the
            g3annintegExtension field instead since the announcement number
            not longer applies in CM starting with CM 4.0."
        ::= { g3annintegEntry 9 }

    g3annintegExtension	OBJECT-TYPE
        SYNTAX    DisplayString (SIZE (0..15))
        ACCESS    read-only
        STATUS    mandatory
        DESCRIPTION
            "An object containing the extension number for the announcement"
        ::= { g3annintegEntry 10 }

    g3annintegName	OBJECT-TYPE
        SYNTAX    DisplayString (SIZE (0..24))
        ACCESS    read-only
        STATUS    mandatory
        DESCRIPTION
            "An object containing the first 24 characters of the announcement"
        ::= { g3annintegEntry 11 }

    g3annintegMeasHour	OBJECT-TYPE
        SYNTAX    INTEGER
        ACCESS    read-only
        STATUS    mandatory
        DESCRIPTION
            "An object containing the Hour the measurement was taken"
        ::= { g3annintegEntry 12 }

    g3annintegPlayReqts	OBJECT-TYPE
        SYNTAX    INTEGER
        ACCESS    read-only
        STATUS    mandatory
        DESCRIPTION
            "An object containing total number of calls that requested a play of
            this announcement during the period"
        ::= { g3annintegEntry 13 }

    g3annintegCallsQueued	OBJECT-TYPE
        SYNTAX    INTEGER
        ACCESS    read-only
        STATUS    mandatory
        DESCRIPTION
            "An object containing number of calls for an announcement that had to
            queue waiting for a port during the period"
        ::= { g3annintegEntry 14 }

    g3annintegASP	OBJECT-TYPE
        SYNTAX    INTEGER
        ACCESS    read-only
        STATUS    mandatory
        DESCRIPTION
            "An object containing from time waiting for announcement to play to
            when it starts playing in seconds averaged over the period.  Calls
            abandoned while in the waiting for announcement port queue are not to
            be included"
        ::= { g3annintegEntry 15 }

    g3annintegQueueDrops	OBJECT-TYPE
        SYNTAX    INTEGER
        ACCESS    read-only
        STATUS    mandatory
        DESCRIPTION
            "An object containing count of the individual calls that had to queue
            but dropped while waiting during the period - this includes calls
            abandoned by the caller and VOA (VDN of origin Announcements) aborts
            but should exclude calls that were waiting but answered by an agent"
        ::= { g3annintegEntry 16 }

    g3annintegMPortPlay	OBJECT-TYPE
        SYNTAX    INTEGER
        ACCESS    read-only
        STATUS    mandatory
        DESCRIPTION
            "An object containing count of how many times the announcement is being
            played out of more than one port at the same time during the period"
        ::= { g3annintegEntry 17 }

    g3annintegMaxPorts	OBJECT-TYPE
        SYNTAX    INTEGER
        ACCESS    read-only
        STATUS    mandatory
        DESCRIPTION
            "An object containing the peak number of ports used for the
            announcement during the period"
        ::= { g3annintegEntry 18 }

    g3annintegMaxCall	OBJECT-TYPE
        SYNTAX    INTEGER
        ACCESS    read-only
        STATUS    mandatory
        DESCRIPTION
            "An object containing the peak number callers connected to a board (sum
            of the ports) at the same time"
        ::= { g3annintegEntry 19 }


    -- the g3pkanninteg group

    g3pkannintegTage	OBJECT-TYPE
        SYNTAX    INTEGER
        ACCESS    read-only
        STATUS    mandatory
        DESCRIPTION
            "The number of timeticks since the data was last
            extracted from the switch by the Proxy Agent.  This object
            along with the g3pkannintegintvl object allows the Network Manager
            to determine the validity of the data in the cache and to control
            when the Proxy Agent extracts the data from the switch."
        ::= { g3pkanninteg 1 }

    g3pkannintegTintvl	OBJECT-TYPE
        SYNTAX    INTEGER
        ACCESS    read-write
        STATUS    mandatory
        DESCRIPTION
            "An object containing the interval for which the
            data extracted from the switch is considered valid by the
            Proxy Agent.  When a GET or GET-NEXT request for these data
            objects is received by the agent it uses the g3pkannintegage
            and g3pkannintegintvl objects to determine whether it should refresh
            the cached pkannintegTable.  If g3pkannintegstmp +
            g3pkannintegintvl is less than the current value of the sysUpTime
            object then the agent refreshes the pkannintegTable cache.  In
            either case it responds to the requests it receives with the data
            it currently has in the cache."
        ::= { g3pkanninteg 2 }

    g3pkannintegTdelay	OBJECT-TYPE
        SYNTAX    INTEGER
        ACCESS    read-only
        STATUS    mandatory
        DESCRIPTION
            "An object containing the delay encountered in updating
            the cached data."
        ::= { g3pkanninteg 3 }

    g3pkannintegTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3pkanninteg 4 }

    g3pkannintegTcount	OBJECT-TYPE
        SYNTAX    Gauge
        ACCESS    read-only
        STATUS    mandatory
        DESCRIPTION
            "A Gauge object containing the number of data records in the cache."
        ::= { g3pkanninteg 5 }

    g3pkannintegTable	OBJECT-TYPE
        SYNTAX    SEQUENCE OF G3pkannintegEntry
        ACCESS    not-accessible
        STATUS    mandatory
        DESCRIPTION
            "A list of g3pkanninteg entries."
        ::= { g3pkanninteg 6 }

    g3pkannintegEntry	OBJECT-TYPE
        SYNTAX    G3pkannintegEntry
        ACCESS    not-accessible
        STATUS    mandatory
        DESCRIPTION
            "A g3pkanninteg entry containing objects of the
            g3pkanninteg information sent by the switch."
        INDEX    { g3pkannintegExtension }
        ::= { g3pkannintegTable 1 }

    G3pkannintegEntry ::= SEQUENCE {
        g3pkannintegBoard
            DisplayString,
        g3pkannintegYear
            INTEGER,
        g3pkannintegMonth
            INTEGER,
        g3pkannintegDay
            INTEGER,
        g3pkannintegHour
            INTEGER,
        g3pkannintegPlayPorts
            INTEGER,
        g3pkannintegMaxCallPeriod
            INTEGER,
        g3pkannintegAllPortsBusy
            INTEGER,
        g3pkannintegAnnNbr
            INTEGER,
        g3pkannintegExtension
            DisplayString,
        g3pkannintegName
            DisplayString,
        g3pkannintegMeasHour
            INTEGER,
        g3pkannintegPlayReqts
            INTEGER,
        g3pkannintegCallsQueued
            INTEGER,
        g3pkannintegASP
            INTEGER,
        g3pkannintegQueueDrops
            INTEGER,
        g3pkannintegMPortPlay
            INTEGER,
        g3pkannintegMaxPorts
            INTEGER,
        g3pkannintegMaxCall
            INTEGER
        }

    g3pkannintegBoard	OBJECT-TYPE
        SYNTAX    DisplayString (SIZE (0..5))
        ACCESS    read-only
        STATUS    mandatory
        DESCRIPTION
            "An object containing the number of the integrated announcement board"
        ::= { g3pkannintegEntry 1 }

    g3pkannintegYear	OBJECT-TYPE
        SYNTAX    INTEGER
        ACCESS    read-only
        STATUS    mandatory
        DESCRIPTION
            "An object containing the Year the command was executed"
        ::= { g3pkannintegEntry 2 }

    g3pkannintegMonth	OBJECT-TYPE
        SYNTAX    INTEGER
        ACCESS    read-only
        STATUS    mandatory
        DESCRIPTION
            "An object containing the Month the command was executed"
        ::= { g3pkannintegEntry 3 }

    g3pkannintegDay	OBJECT-TYPE
        SYNTAX    INTEGER
        ACCESS    read-only
        STATUS    mandatory
        DESCRIPTION
            "An object containing the Day the command was executed"
        ::= { g3pkannintegEntry 4 }

    g3pkannintegHour	OBJECT-TYPE
        SYNTAX    INTEGER
        ACCESS    read-only
        STATUS    mandatory
        DESCRIPTION
            "An object containing the Hour the command was executed"
        ::= { g3pkannintegEntry 5 }

    g3pkannintegPlayPorts	OBJECT-TYPE
        SYNTAX    INTEGER
        ACCESS    read-only
        STATUS    mandatory
        DESCRIPTION
            "An object containing the number of ports on the board which 
            can play the announcements. "
        ::= { g3pkannintegEntry 6 }

    g3pkannintegMaxCallPeriod	OBJECT-TYPE
        SYNTAX    INTEGER
        ACCESS    read-only
        STATUS    mandatory
        DESCRIPTION
            "An object containing the Maximum number of  Callers on Board in the Period"
        ::= { g3pkannintegEntry 7 }

    g3pkannintegAllPortsBusy	OBJECT-TYPE
        SYNTAX    INTEGER
        ACCESS    read-only
        STATUS    mandatory
        DESCRIPTION
            "An object containing an indication of how frequently the
            all-ports-busy condition occurs within the period of time"
        ::= { g3pkannintegEntry 8 }

    g3pkannintegAnnNbr	OBJECT-TYPE
        SYNTAX    INTEGER
        ACCESS    read-only
        STATUS    mandatory
        DESCRIPTION
            "An object containing the announcement number. This field is
            no longer applicable and the table is sorted by the
            g3pkannintegExtension field instead since the announcement number
            not longer applies in CM starting with CM 4.0."
        ::= { g3pkannintegEntry 9 }

    g3pkannintegExtension	OBJECT-TYPE
        SYNTAX    DisplayString (SIZE (0..15))
        ACCESS    read-only
        STATUS    mandatory
        DESCRIPTION
            "An object containing the extension number for the announcement"
        ::= { g3pkannintegEntry 10 }

    g3pkannintegName	OBJECT-TYPE
        SYNTAX    DisplayString (SIZE (0..24))
        ACCESS    read-only
        STATUS    mandatory
        DESCRIPTION
            "An object containing the first 24 characters of the announcement"
        ::= { g3pkannintegEntry 11 }

    g3pkannintegMeasHour	OBJECT-TYPE
        SYNTAX    INTEGER
        ACCESS    read-only
        STATUS    mandatory
        DESCRIPTION
            "An object containing the Hour the measurement was taken"
        ::= { g3pkannintegEntry 12 }

    g3pkannintegPlayReqts	OBJECT-TYPE
        SYNTAX    INTEGER
        ACCESS    read-only
        STATUS    mandatory
        DESCRIPTION
            "An object containing total number of calls that requested a play of
            this announcement during the period"
        ::= { g3pkannintegEntry 13 }

    g3pkannintegCallsQueued	OBJECT-TYPE
        SYNTAX    INTEGER
        ACCESS    read-only
        STATUS    mandatory
        DESCRIPTION
            "An object containing number of calls for an announcement that had to
            queue waiting for a port during the period"
        ::= { g3pkannintegEntry 14 }

    g3pkannintegASP	OBJECT-TYPE
        SYNTAX    INTEGER
        ACCESS    read-only
        STATUS    mandatory
        DESCRIPTION
            "An object containing from time waiting for announcement to play to
            when it starts playing in seconds averaged over the period.  Calls
            abandoned while in the waiting for announcement port queue are not to
            be included"
        ::= { g3pkannintegEntry 15 }

    g3pkannintegQueueDrops	OBJECT-TYPE
        SYNTAX    INTEGER
        ACCESS    read-only
        STATUS    mandatory
        DESCRIPTION
            "An object containing count of the individual calls that had to queue
            but dropped while waiting during the period - this includes calls
            abandoned by the caller and VOA (VDN of origin Announcements) aborts
            but should exclude calls that were waiting but answered by an agent"
        ::= { g3pkannintegEntry 16 }

    g3pkannintegMPortPlay	OBJECT-TYPE
        SYNTAX    INTEGER
        ACCESS    read-only
        STATUS    mandatory
        DESCRIPTION
            "An object containing count of how many times the announcement is being
            played out of more than one port at the same time during the period"
        ::= { g3pkannintegEntry 17 }

    g3pkannintegMaxPorts	OBJECT-TYPE
        SYNTAX    INTEGER
        ACCESS    read-only
        STATUS    mandatory
        DESCRIPTION
            "An object containing the peak number of ports used for the
            announcement during the period"
        ::= { g3pkannintegEntry 18 }

    g3pkannintegMaxCall	OBJECT-TYPE
        SYNTAX    INTEGER
        ACCESS    read-only
        STATUS    mandatory
        DESCRIPTION
            "An object containing the peak number callers connected to a board (sum
            of the ports) at the same time"
        ::= { g3pkannintegEntry 19 }


    -- the g3nodename group

    g3nodenameTage	OBJECT-TYPE
        SYNTAX    INTEGER
        ACCESS    read-only
        STATUS    mandatory
        DESCRIPTION
            "The number of timeticks since the node name data was last
            extracted from the switch by the Proxy Agent.  This object
            along with the g3nodenameintvl object allows the Network Manager
            to determine the validity of the node name data in the cache and to 
            control	when the Proxy Agent extracts the data from the switch."
        ::= { g3nodename 1 }

    g3nodenameTintvl	OBJECT-TYPE
        SYNTAX    INTEGER
        ACCESS    read-write
        STATUS    mandatory
        DESCRIPTION
            "An object containing the interval for which the node name
            data extracted from the switch is considered valid by the
            Proxy Agent.  When a GET or GET-NEXT request for these node name 
            objects is received by the agent it uses the g3nodenameage
            and g3nodenameintvl objects to determine whether it should refresh
            the cached nodenameTable.  If g3nodenamestmp +
            g3nodenameintvl is less than the current value of the sysUpTime
            object then the agent refreshes the nodenameTable cache.  In
            either case it responds to the requests it receives with the data
            it currently has in the cache."
        ::= { g3nodename 2 }

    g3nodenameTdelay	OBJECT-TYPE
        SYNTAX    INTEGER
        ACCESS    read-only
        STATUS    mandatory
        DESCRIPTION
            "An object containing the delay encountered in updating
            the cached data."
        ::= { g3nodename 3 }

    g3nodenameTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3nodename 4 }

    g3nodenameTcount	OBJECT-TYPE
        SYNTAX    Gauge
        ACCESS    read-only
        STATUS    mandatory
        DESCRIPTION
            "A Gauge object containing the number of data records in the cache."
        ::= { g3nodename 5 }

    g3nodenameTable	OBJECT-TYPE
        SYNTAX    SEQUENCE OF G3nodenameEntry
        ACCESS    not-accessible
        STATUS    mandatory
        DESCRIPTION
            "A list of g3nodename entries."
        ::= { g3nodename 6 }

    g3nodenameEntry	OBJECT-TYPE
        SYNTAX    G3nodenameEntry
        ACCESS    not-accessible
        STATUS    mandatory
        DESCRIPTION
            "A g3nodename entry containing objects of the
            g3nodename information sent by the switch."
        INDEX    { g3nodenameName }
        ::= { g3nodenameTable 1 }

    G3nodenameEntry ::= SEQUENCE {
        g3nodenameName
            DisplayString,
        g3nodenameType
            DisplayString,
        g3nodenameIP1
            DisplayString,
        g3nodenameIP2
            DisplayString,
        g3nodenameIP3
            DisplayString,
        g3nodenameIP4
            DisplayString
        }

    g3nodenameName	OBJECT-TYPE
        SYNTAX    DisplayString (SIZE (0..15))
        ACCESS    read-only
        STATUS    mandatory
        DESCRIPTION
            "This MIB Group displays the names of all the nodes that are
            administered on the system."
        ::= { g3nodenameEntry 1 }

    g3nodenameType	OBJECT-TYPE
        SYNTAX    DisplayString (SIZE (0..5))
        ACCESS    read-only
        STATUS    mandatory
        DESCRIPTION
            "An object containing the type of the node"
        ::= { g3nodenameEntry 2 }

    g3nodenameIP1	OBJECT-TYPE
        SYNTAX    DisplayString (SIZE (0..40))
        ACCESS    read-only
        STATUS    mandatory
        DESCRIPTION
            "An object containing the first octet of the IP address"
        ::= { g3nodenameEntry 3 }

    g3nodenameIP2	OBJECT-TYPE
        SYNTAX    DisplayString (SIZE (0..3))
        ACCESS    read-only
        STATUS    mandatory
        DESCRIPTION
            "An object containing the second octet of the IP address"
        ::= { g3nodenameEntry 4 }

    g3nodenameIP3	OBJECT-TYPE
        SYNTAX    DisplayString (SIZE (0..3))
        ACCESS    read-only
        STATUS    mandatory
        DESCRIPTION
            "An object containing the third octet of the IP address"
        ::= { g3nodenameEntry 5 }

    g3nodenameIP4	OBJECT-TYPE
        SYNTAX    DisplayString (SIZE (0..3))
        ACCESS    read-only
        STATUS    mandatory
        DESCRIPTION
            "An object containing the fourth octet of the IP address"
        ::= { g3nodenameEntry 6 }


    -- the g3trkgrpmem group

    g3trkgrpmemTage	OBJECT-TYPE
        SYNTAX    INTEGER
        ACCESS    read-only
        STATUS    mandatory
        DESCRIPTION
            "The number of timeticks since the trunk group member data was last
            extracted from the switch by the Proxy Agent.  This object
            along with the g3trkgrpmemintvl object allows the Network Manager
            to determine the validity of the trunk group member data in the cache and 
            to control	when the Proxy Agent extracts the data from the switch."
        ::= { g3trkgrpmem 1 }

    g3trkgrpmemTintvl	OBJECT-TYPE
        SYNTAX    INTEGER
        ACCESS    read-write
        STATUS    mandatory
        DESCRIPTION
            "An object containing the interval for which the trunk group member
            data extracted from the switch is considered valid by the Proxy Agent.
            When a GET or GET-NEXT request for these trunk group member objects is
            received by the agent it uses the g3trkgrpmemage
            and g3trkgrpmemintvl objects to determine whether it should refresh
            the cached trkgrpmemTable.  If g3trkgrpmemstmp +
            g3trkgrpmemintvl is less than the current value of the sysUpTime
            object then the agent refreshes the trkgrpmemTable cache.  In
            either case it responds to the requests it receives with the data
            it currently has in the cache."
        ::= { g3trkgrpmem 2 }

    g3trkgrpmemTdelay	OBJECT-TYPE
        SYNTAX    INTEGER
        ACCESS    read-only
        STATUS    mandatory
        DESCRIPTION
            "An object containing the delay encountered in updating
            the cached data."
        ::= { g3trkgrpmem 3 }

    g3trkgrpmemTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3trkgrpmem 4 }

    g3trkgrpmemTcount	OBJECT-TYPE
        SYNTAX    Gauge
        ACCESS    read-only
        STATUS    mandatory
        DESCRIPTION
            "A Gauge object containing the number of data records in the cache."
        ::= { g3trkgrpmem 5 }

    g3trkgrpmemTable	OBJECT-TYPE
        SYNTAX    SEQUENCE OF G3trkgrpmemEntry
        ACCESS    not-accessible
        STATUS    mandatory
        DESCRIPTION
            "A list of g3trkgrpmem entries."
        ::= { g3trkgrpmem 6 }

    g3trkgrpmemEntry	OBJECT-TYPE
        SYNTAX    G3trkgrpmemEntry
        ACCESS    not-accessible
        STATUS    mandatory
        DESCRIPTION
            "A g3trkgrpmem entry containing objects of the
            g3trkgrpmem information sent by the switch."
        INDEX    { g3trkgrpmemGroup, g3trkgrpmemMember }
        ::= { g3trkgrpmemTable 1 }

    G3trkgrpmemEntry ::= SEQUENCE {
        g3trkgrpmemGroup
            INTEGER,
        g3trkgrpmemMember
            INTEGER,
        g3trkgrpmemName
            DisplayString,
        g3trkgrpmemType
            DisplayString,
        g3trkgrpmemSigGroup
            DisplayString,
        g3trkgrpmemPort
            DisplayString
        }

    g3trkgrpmemGroup	OBJECT-TYPE
        SYNTAX    INTEGER
        ACCESS    read-only
        STATUS    mandatory
        DESCRIPTION
            "An INTEGER Object that uniquely identifies an administered
            trunk group."
        ::= { g3trkgrpmemEntry 1 }

    g3trkgrpmemMember	OBJECT-TYPE
        SYNTAX    INTEGER
        ACCESS    read-only
        STATUS    mandatory
        DESCRIPTION
            "An INTEGER Object that uniquely identifies a trunk group member.
            Trunk group members range from 1 to 666 and exist whether or
            not they are assigned a port."
        ::= { g3trkgrpmemEntry 2 }

    g3trkgrpmemName	OBJECT-TYPE
        SYNTAX    DisplayString (SIZE (0..12))
        ACCESS    read-only
        STATUS    mandatory
        DESCRIPTION
            "A DisplayString Object containing the name assigned to the trunk
            group member."
        ::= { g3trkgrpmemEntry 3 }

    g3trkgrpmemType	OBJECT-TYPE
        SYNTAX    DisplayString (SIZE (0..7))
        ACCESS    read-only
        STATUS    mandatory
        DESCRIPTION
            "A DisplayString Object containing the Type of the trunk group member."
        ::= { g3trkgrpmemEntry 4 }

    g3trkgrpmemSigGroup	OBJECT-TYPE
        SYNTAX    DisplayString (SIZE (0..3))
        ACCESS    read-only
        STATUS    mandatory
        DESCRIPTION
            "A DisplayString Object containing the Signaling Group assigned
            to the trunk group member."
        ::= { g3trkgrpmemEntry 5 }

    g3trkgrpmemPort	OBJECT-TYPE
        SYNTAX    DisplayString (SIZE (0..7))
        ACCESS    read-only
        STATUS    mandatory
        DESCRIPTION
            "A DisplayString Object that uniquely identifies the trunk port
            based on its location in the system. The syntax for the Port Number
            is as follows: cabinet(1-22):carrier(A-E):slot(01-20)."
        ::= { g3trkgrpmemEntry 6 }


    -- the g3ipinterface group

    g3ipinterfaceTage	OBJECT-TYPE
        SYNTAX    INTEGER
        ACCESS    read-only
        STATUS    mandatory
        DESCRIPTION
            "The number of timeticks since the ip interface data was last
            extracted from the switch by the G3 Proxy Agent. This object
            along with the g3ipinterfaceintvl object allows the Network Manager
            to determine the validity of the ip interface data in the
            cache and to control when the proxy agent extracts the
            ip interface data from the switch."
        ::= { g3ipinterface 1 }

    g3ipinterfaceTintvl	OBJECT-TYPE
        SYNTAX    INTEGER
        ACCESS    read-write
        STATUS    mandatory
        DESCRIPTION
            "An object containing the interval for which the ip interface data
            extracted from the switch is considered valid by the proxy agent.
            When a GET or GET-NEXT request for ip interface objects is
            received by the agent it uses the g3ipinterfaceage and 
            g3ipinterfaceintvl objects to determine whether it should refresh 
            the cached ipinterfaceTable.  If g3ipinterfacestmp + 
            g3ipinterfaceintvl is less than the current value of the sysUpTime 
            object then the agent refreshes the ipinterfaceTable cache.  In 
            either case it responds to the requests it receives with the data 
            it currently has in the cache."
        ::= { g3ipinterface 2 }

    g3ipinterfaceTdelay	OBJECT-TYPE
        SYNTAX    INTEGER
        ACCESS    read-only
        STATUS    mandatory
        DESCRIPTION
            "An object containing the delay encountered in updating the cached data"
        ::= { g3ipinterface 3 }

    g3ipinterfaceTretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3ipinterface 4 }

    g3ipinterfaceNodeName1	OBJECT-TYPE
        SYNTAX    DisplayString (SIZE (0..15))
        ACCESS    read-only
        STATUS    mandatory
        DESCRIPTION
            "An object containing the the node-name for the ip interface"
        ::= { g3ipinterface 5 }

    g3ipinterfaceNodeName2	OBJECT-TYPE
        SYNTAX    DisplayString (SIZE (0..15))
        ACCESS    read-only
        STATUS    mandatory
        DESCRIPTION
            "See DESCRIPTION of g3ipinterfaceNodeName1."
        ::= { g3ipinterface 6 }

    g3ipinterfaceNodeName3	OBJECT-TYPE
        SYNTAX    DisplayString (SIZE (0..15))
        ACCESS    read-only
        STATUS    mandatory
        DESCRIPTION
            "See DESCRIPTION of g3ipinterfaceNodeName1."
        ::= { g3ipinterface 7 }

    g3ipinterfaceNodeName4	OBJECT-TYPE
        SYNTAX    DisplayString (SIZE (0..15))
        ACCESS    read-only
        STATUS    mandatory
        DESCRIPTION
            "See DESCRIPTION of g3ipinterfaceNodeName1."
        ::= { g3ipinterface 8 }

    g3ipinterfaceNodeName5	OBJECT-TYPE
        SYNTAX    DisplayString (SIZE (0..15))
        ACCESS    read-only
        STATUS    mandatory
        DESCRIPTION
            "See DESCRIPTION of g3ipinterfaceNodeName1."
        ::= { g3ipinterface 9 }

    g3ipinterfaceNodeName6	OBJECT-TYPE
        SYNTAX    DisplayString (SIZE (0..15))
        ACCESS    read-only
        STATUS    mandatory
        DESCRIPTION
            "See DESCRIPTION of g3ipinterfaceNodeName1."
        ::= { g3ipinterface 10 }

    g3ipinterfaceNodeName7	OBJECT-TYPE
        SYNTAX    DisplayString (SIZE (0..15))
        ACCESS    read-only
        STATUS    mandatory
        DESCRIPTION
            "See DESCRIPTION of g3ipinterfaceNodeName1."
        ::= { g3ipinterface 11 }

    g3ipinterfaceNodeName8	OBJECT-TYPE
        SYNTAX    DisplayString (SIZE (0..15))
        ACCESS    read-only
        STATUS    mandatory
        DESCRIPTION
            "See DESCRIPTION of g3ipinterfaceNodeName1."
        ::= { g3ipinterface 12 }

    g3ipinterfaceNodeName9	OBJECT-TYPE
        SYNTAX    DisplayString (SIZE (0..15))
        ACCESS    read-only
        STATUS    mandatory
        DESCRIPTION
            "See DESCRIPTION of g3ipinterfaceNodeName1."
        ::= { g3ipinterface 13 }

    g3ipinterfaceNodeName10	OBJECT-TYPE
        SYNTAX    DisplayString (SIZE (0..15))
        ACCESS    read-only
        STATUS    mandatory
        DESCRIPTION
            "See DESCRIPTION of g3ipinterfaceNodeName1."
        ::= { g3ipinterface 14 }

    g3ipinterfaceNodeName11	OBJECT-TYPE
        SYNTAX    DisplayString (SIZE (0..15))
        ACCESS    read-only
        STATUS    mandatory
        DESCRIPTION
            "See DESCRIPTION of g3ipinterfaceNodeName1."
        ::= { g3ipinterface 15 }

    g3ipinterfaceNodeName12	OBJECT-TYPE
        SYNTAX    DisplayString (SIZE (0..15))
        ACCESS    read-only
        STATUS    mandatory
        DESCRIPTION
            "See DESCRIPTION of g3ipinterfaceNodeName1."
        ::= { g3ipinterface 16 }

    g3ipinterfaceNodeName13	OBJECT-TYPE
        SYNTAX    DisplayString (SIZE (0..15))
        ACCESS    read-only
        STATUS    mandatory
        DESCRIPTION
            "See DESCRIPTION of g3ipinterfaceNodeName1."
        ::= { g3ipinterface 17 }

    g3ipinterfaceNodeName14	OBJECT-TYPE
        SYNTAX    DisplayString (SIZE (0..15))
        ACCESS    read-only
        STATUS    mandatory
        DESCRIPTION
            "See DESCRIPTION of g3ipinterfaceNodeName1."
        ::= { g3ipinterface 18 }

    g3ipinterfaceNodeName15	OBJECT-TYPE
        SYNTAX    DisplayString (SIZE (0..15))
        ACCESS    read-only
        STATUS    mandatory
        DESCRIPTION
            "See DESCRIPTION of g3ipinterfaceNodeName1."
        ::= { g3ipinterface 19 }

    g3ipinterfaceNodeName16	OBJECT-TYPE
        SYNTAX    DisplayString (SIZE (0..15))
        ACCESS    read-only
        STATUS    mandatory
        DESCRIPTION
            "See DESCRIPTION of g3ipinterfaceNodeName1."
        ::= { g3ipinterface 20 }

    g3ipinterfaceNodeName17	OBJECT-TYPE
        SYNTAX    DisplayString (SIZE (0..15))
        ACCESS    read-only
        STATUS    mandatory
        DESCRIPTION
            "See DESCRIPTION of g3ipinterfaceNodeName1."
        ::= { g3ipinterface 21 }

    g3ipinterfaceNodeName18	OBJECT-TYPE
        SYNTAX    DisplayString (SIZE (0..15))
        ACCESS    read-only
        STATUS    mandatory
        DESCRIPTION
            "See DESCRIPTION of g3ipinterfaceNodeName1."
        ::= { g3ipinterface 22 }

    g3ipinterfaceNodeName19	OBJECT-TYPE
        SYNTAX    DisplayString (SIZE (0..15))
        ACCESS    read-only
        STATUS    mandatory
        DESCRIPTION
            "See DESCRIPTION of g3ipinterfaceNodeName1."
        ::= { g3ipinterface 23 }

    g3ipinterfaceNodeName20	OBJECT-TYPE
        SYNTAX    DisplayString (SIZE (0..15))
        ACCESS    read-only
        STATUS    mandatory
        DESCRIPTION
            "See DESCRIPTION of g3ipinterfaceNodeName1."
        ::= { g3ipinterface 24 }

    g3ipinterfaceNodeName21	OBJECT-TYPE
        SYNTAX    DisplayString (SIZE (0..15))
        ACCESS    read-only
        STATUS    mandatory
        DESCRIPTION
            "See DESCRIPTION of g3ipinterfaceNodeName1."
        ::= { g3ipinterface 25 }

    g3ipinterfaceNodeName22	OBJECT-TYPE
        SYNTAX    DisplayString (SIZE (0..15))
        ACCESS    read-only
        STATUS    mandatory
        DESCRIPTION
            "See DESCRIPTION of g3ipinterfaceNodeName1."
        ::= { g3ipinterface 26 }

    g3ipinterfaceNodeName23	OBJECT-TYPE
        SYNTAX    DisplayString (SIZE (0..15))
        ACCESS    read-only
        STATUS    mandatory
        DESCRIPTION
            "See DESCRIPTION of g3ipinterfaceNodeName1."
        ::= { g3ipinterface 27 }

    g3ipinterfaceNodeName24	OBJECT-TYPE
        SYNTAX    DisplayString (SIZE (0..15))
        ACCESS    read-only
        STATUS    mandatory
        DESCRIPTION
            "See DESCRIPTION of g3ipinterfaceNodeName1."
        ::= { g3ipinterface 28 }

    g3ipinterfaceNodeName25	OBJECT-TYPE
        SYNTAX    DisplayString (SIZE (0..15))
        ACCESS    read-only
        STATUS    mandatory
        DESCRIPTION
            "See DESCRIPTION of g3ipinterfaceNodeName1."
        ::= { g3ipinterface 29 }

    g3ipinterfaceNodeName26	OBJECT-TYPE
        SYNTAX    DisplayString (SIZE (0..15))
        ACCESS    read-only
        STATUS    mandatory
        DESCRIPTION
            "See DESCRIPTION of g3ipinterfaceNodeName1."
        ::= { g3ipinterface 30 }

    g3ipinterfaceNodeName27	OBJECT-TYPE
        SYNTAX    DisplayString (SIZE (0..15))
        ACCESS    read-only
        STATUS    mandatory
        DESCRIPTION
            "See DESCRIPTION of g3ipinterfaceNodeName1."
        ::= { g3ipinterface 31 }

    g3ipinterfaceNodeName28	OBJECT-TYPE
        SYNTAX    DisplayString (SIZE (0..15))
        ACCESS    read-only
        STATUS    mandatory
        DESCRIPTION
            "See DESCRIPTION of g3ipinterfaceNodeName1."
        ::= { g3ipinterface 32 }

    g3ipinterfaceNodeName29	OBJECT-TYPE
        SYNTAX    DisplayString (SIZE (0..15))
        ACCESS    read-only
        STATUS    mandatory
        DESCRIPTION
            "See DESCRIPTION of g3ipinterfaceNodeName1."
        ::= { g3ipinterface 33 }

    g3ipinterfaceNodeName30	OBJECT-TYPE
        SYNTAX    DisplayString (SIZE (0..15))
        ACCESS    read-only
        STATUS    mandatory
        DESCRIPTION
            "See DESCRIPTION of g3ipinterfaceNodeName1."
        ::= { g3ipinterface 34 }

    g3ipinterfaceNodeName31	OBJECT-TYPE
        SYNTAX    DisplayString (SIZE (0..15))
        ACCESS    read-only
        STATUS    mandatory
        DESCRIPTION
            "See DESCRIPTION of g3ipinterfaceNodeName1."
        ::= { g3ipinterface 35 }

    g3ipinterfaceNodeName32	OBJECT-TYPE
        SYNTAX    DisplayString (SIZE (0..15))
        ACCESS    read-only
        STATUS    mandatory
        DESCRIPTION
            "See DESCRIPTION of g3ipinterfaceNodeName1."
        ::= { g3ipinterface 36 }

    g3ipinterfaceNodeName33	OBJECT-TYPE
        SYNTAX    DisplayString (SIZE (0..15))
        ACCESS    read-only
        STATUS    mandatory
        DESCRIPTION
            "See DESCRIPTION of g3ipinterfaceNodeName1."
        ::= { g3ipinterface 37 }

    g3ipinterfaceNodeName34	OBJECT-TYPE
        SYNTAX    DisplayString (SIZE (0..15))
        ACCESS    read-only
        STATUS    mandatory
        DESCRIPTION
            "See DESCRIPTION of g3ipinterfaceNodeName1."
        ::= { g3ipinterface 38 }

    g3ipinterfaceNodeName35	OBJECT-TYPE
        SYNTAX    DisplayString (SIZE (0..15))
        ACCESS    read-only
        STATUS    mandatory
        DESCRIPTION
            "See DESCRIPTION of g3ipinterfaceNodeName1."
        ::= { g3ipinterface 39 }

    g3ipinterfaceNodeName36	OBJECT-TYPE
        SYNTAX    DisplayString (SIZE (0..15))
        ACCESS    read-only
        STATUS    mandatory
        DESCRIPTION
            "See DESCRIPTION of g3ipinterfaceNodeName1."
        ::= { g3ipinterface 40 }

    g3ipinterfaceNodeName37	OBJECT-TYPE
        SYNTAX    DisplayString (SIZE (0..15))
        ACCESS    read-only
        STATUS    mandatory
        DESCRIPTION
            "See DESCRIPTION of g3ipinterfaceNodeName1."
        ::= { g3ipinterface 41 }

    g3ipinterfaceNodeName38	OBJECT-TYPE
        SYNTAX    DisplayString (SIZE (0..15))
        ACCESS    read-only
        STATUS    mandatory
        DESCRIPTION
            "See DESCRIPTION of g3ipinterfaceNodeName1."
        ::= { g3ipinterface 42 }

    g3ipinterfaceNodeName39	OBJECT-TYPE
        SYNTAX    DisplayString (SIZE (0..15))
        ACCESS    read-only
        STATUS    mandatory
        DESCRIPTION
            "See DESCRIPTION of g3ipinterfaceNodeName1."
        ::= { g3ipinterface 43 }

    g3ipinterfaceNodeName40	OBJECT-TYPE
        SYNTAX    DisplayString (SIZE (0..15))
        ACCESS    read-only
        STATUS    mandatory
        DESCRIPTION
            "See DESCRIPTION of g3ipinterfaceNodeName1."
        ::= { g3ipinterface 44 }

    g3ipinterfaceNodeName41	OBJECT-TYPE
        SYNTAX    DisplayString (SIZE (0..15))
        ACCESS    read-only
        STATUS    mandatory
        DESCRIPTION
            "See DESCRIPTION of g3ipinterfaceNodeName1."
        ::= { g3ipinterface 45 }

    g3ipinterfaceNodeName42	OBJECT-TYPE
        SYNTAX    DisplayString (SIZE (0..15))
        ACCESS    read-only
        STATUS    mandatory
        DESCRIPTION
            "See DESCRIPTION of g3ipinterfaceNodeName1."
        ::= { g3ipinterface 46 }

    g3ipinterfaceNodeName43	OBJECT-TYPE
        SYNTAX    DisplayString (SIZE (0..15))
        ACCESS    read-only
        STATUS    mandatory
        DESCRIPTION
            "See DESCRIPTION of g3ipinterfaceNodeName1."
        ::= { g3ipinterface 47 }

    g3ipinterfaceNodeName44	OBJECT-TYPE
        SYNTAX    DisplayString (SIZE (0..15))
        ACCESS    read-only
        STATUS    mandatory
        DESCRIPTION
            "See DESCRIPTION of g3ipinterfaceNodeName1."
        ::= { g3ipinterface 48 }

    g3ipinterfaceNodeName45	OBJECT-TYPE
        SYNTAX    DisplayString (SIZE (0..15))
        ACCESS    read-only
        STATUS    mandatory
        DESCRIPTION
            "See DESCRIPTION of g3ipinterfaceNodeName1."
        ::= { g3ipinterface 49 }

    g3ipinterfaceNodeName46	OBJECT-TYPE
        SYNTAX    DisplayString (SIZE (0..15))
        ACCESS    read-only
        STATUS    mandatory
        DESCRIPTION
            "See DESCRIPTION of g3ipinterfaceNodeName1."
        ::= { g3ipinterface 50 }

    g3ipinterfaceNodeName47	OBJECT-TYPE
        SYNTAX    DisplayString (SIZE (0..15))
        ACCESS    read-only
        STATUS    mandatory
        DESCRIPTION
            "See DESCRIPTION of g3ipinterfaceNodeName1."
        ::= { g3ipinterface 51 }

    g3ipinterfaceNodeName48	OBJECT-TYPE
        SYNTAX    DisplayString (SIZE (0..15))
        ACCESS    read-only
        STATUS    mandatory
        DESCRIPTION
            "See DESCRIPTION of g3ipinterfaceNodeName1."
        ::= { g3ipinterface 52 }

    g3ipinterfaceNodeName49	OBJECT-TYPE
        SYNTAX    DisplayString (SIZE (0..15))
        ACCESS    read-only
        STATUS    mandatory
        DESCRIPTION
            "See DESCRIPTION of g3ipinterfaceNodeName1."
        ::= { g3ipinterface 53 }

    g3ipinterfaceNodeName50	OBJECT-TYPE
        SYNTAX    DisplayString (SIZE (0..15))
        ACCESS    read-only
        STATUS    mandatory
        DESCRIPTION
            "See DESCRIPTION of g3ipinterfaceNodeName1."
        ::= { g3ipinterface 54 }

    g3ipinterfaceNodeName51	OBJECT-TYPE
        SYNTAX    DisplayString (SIZE (0..15))
        ACCESS    read-only
        STATUS    mandatory
        DESCRIPTION
            "See DESCRIPTION of g3ipinterfaceNodeName1."
        ::= { g3ipinterface 55 }

    g3ipinterfaceNodeName52	OBJECT-TYPE
        SYNTAX    DisplayString (SIZE (0..15))
        ACCESS    read-only
        STATUS    mandatory
        DESCRIPTION
            "See DESCRIPTION of g3ipinterfaceNodeName1."
        ::= { g3ipinterface 56 }

    g3ipinterfaceNodeName53	OBJECT-TYPE
        SYNTAX    DisplayString (SIZE (0..15))
        ACCESS    read-only
        STATUS    mandatory
        DESCRIPTION
            "See DESCRIPTION of g3ipinterfaceNodeName1."
        ::= { g3ipinterface 57 }

    g3ipinterfaceNodeName54	OBJECT-TYPE
        SYNTAX    DisplayString (SIZE (0..15))
        ACCESS    read-only
        STATUS    mandatory
        DESCRIPTION
            "See DESCRIPTION of g3ipinterfaceNodeName1."
        ::= { g3ipinterface 58 }

    g3ipinterfaceNodeName55	OBJECT-TYPE
        SYNTAX    DisplayString (SIZE (0..15))
        ACCESS    read-only
        STATUS    mandatory
        DESCRIPTION
            "See DESCRIPTION of g3ipinterfaceNodeName1."
        ::= { g3ipinterface 59 }

    g3ipinterfaceNodeName56	OBJECT-TYPE
        SYNTAX    DisplayString (SIZE (0..15))
        ACCESS    read-only
        STATUS    mandatory
        DESCRIPTION
            "See DESCRIPTION of g3ipinterfaceNodeName1."
        ::= { g3ipinterface 60 }

    g3ipinterfaceNodeName57	OBJECT-TYPE
        SYNTAX    DisplayString (SIZE (0..15))
        ACCESS    read-only
        STATUS    mandatory
        DESCRIPTION
            "See DESCRIPTION of g3ipinterfaceNodeName1."
        ::= { g3ipinterface 61 }

    g3ipinterfaceNodeName58	OBJECT-TYPE
        SYNTAX    DisplayString (SIZE (0..15))
        ACCESS    read-only
        STATUS    mandatory
        DESCRIPTION
            "See DESCRIPTION of g3ipinterfaceNodeName1."
        ::= { g3ipinterface 62 }

    g3ipinterfaceNodeName59	OBJECT-TYPE
        SYNTAX    DisplayString (SIZE (0..15))
        ACCESS    read-only
        STATUS    mandatory
        DESCRIPTION
            "See DESCRIPTION of g3ipinterfaceNodeName1."
        ::= { g3ipinterface 63 }

    g3ipinterfaceNodeName60	OBJECT-TYPE
        SYNTAX    DisplayString (SIZE (0..15))
        ACCESS    read-only
        STATUS    mandatory
        DESCRIPTION
            "See DESCRIPTION of g3ipinterfaceNodeName1."
        ::= { g3ipinterface 64 }

    g3ipinterfaceNodeName61	OBJECT-TYPE
        SYNTAX    DisplayString (SIZE (0..15))
        ACCESS    read-only
        STATUS    mandatory
        DESCRIPTION
            "See DESCRIPTION of g3ipinterfaceNodeName1."
        ::= { g3ipinterface 65 }

    g3ipinterfaceNodeName62	OBJECT-TYPE
        SYNTAX    DisplayString (SIZE (0..15))
        ACCESS    read-only
        STATUS    mandatory
        DESCRIPTION
            "See DESCRIPTION of g3ipinterfaceNodeName1."
        ::= { g3ipinterface 66 }

    g3ipinterfaceNodeName63	OBJECT-TYPE
        SYNTAX    DisplayString (SIZE (0..15))
        ACCESS    read-only
        STATUS    mandatory
        DESCRIPTION
            "See DESCRIPTION of g3ipinterfaceNodeName1."
        ::= { g3ipinterface 67 }

    g3ipinterfaceNodeName64	OBJECT-TYPE
        SYNTAX    DisplayString (SIZE (0..15))
        ACCESS    read-only
        STATUS    mandatory
        DESCRIPTION
            "See DESCRIPTION of g3ipinterfaceNodeName1."
        ::= { g3ipinterface 68 }

    g3ipinterfaceNodeName65	OBJECT-TYPE
        SYNTAX    DisplayString (SIZE (0..15))
        ACCESS    read-only
        STATUS    mandatory
        DESCRIPTION
            "See DESCRIPTION of g3ipinterfaceNodeName1."
        ::= { g3ipinterface 69 }

    g3ipinterfaceNodeName66	OBJECT-TYPE
        SYNTAX    DisplayString (SIZE (0..15))
        ACCESS    read-only
        STATUS    mandatory
        DESCRIPTION
            "See DESCRIPTION of g3ipinterfaceNodeName1."
        ::= { g3ipinterface 70 }

    g3ipinterfaceNodeName67	OBJECT-TYPE
        SYNTAX    DisplayString (SIZE (0..15))
        ACCESS    read-only
        STATUS    mandatory
        DESCRIPTION
            "See DESCRIPTION of g3ipinterfaceNodeName1."
        ::= { g3ipinterface 71 }

    g3ipinterfaceNodeName68	OBJECT-TYPE
        SYNTAX    DisplayString (SIZE (0..15))
        ACCESS    read-only
        STATUS    mandatory
        DESCRIPTION
            "See DESCRIPTION of g3ipinterfaceNodeName1."
        ::= { g3ipinterface 72 }

    g3ipinterfaceNodeName69	OBJECT-TYPE
        SYNTAX    DisplayString (SIZE (0..15))
        ACCESS    read-only
        STATUS    mandatory
        DESCRIPTION
            "See DESCRIPTION of g3ipinterfaceNodeName1."
        ::= { g3ipinterface 73 }

    g3ipinterfaceNodeName70	OBJECT-TYPE
        SYNTAX    DisplayString (SIZE (0..15))
        ACCESS    read-only
        STATUS    mandatory
        DESCRIPTION
            "See DESCRIPTION of g3ipinterfaceNodeName1."
        ::= { g3ipinterface 74 }

    g3ipinterfaceNodeName71	OBJECT-TYPE
        SYNTAX    DisplayString (SIZE (0..15))
        ACCESS    read-only
        STATUS    mandatory
        DESCRIPTION
            "See DESCRIPTION of g3ipinterfaceNodeName1."
        ::= { g3ipinterface 75 }

    g3ipinterfaceNodeName72	OBJECT-TYPE
        SYNTAX    DisplayString (SIZE (0..15))
        ACCESS    read-only
        STATUS    mandatory
        DESCRIPTION
            "See DESCRIPTION of g3ipinterfaceNodeName1."
        ::= { g3ipinterface 76 }

    g3ipinterfaceNodeName73	OBJECT-TYPE
        SYNTAX    DisplayString (SIZE (0..15))
        ACCESS    read-only
        STATUS    mandatory
        DESCRIPTION
            "See DESCRIPTION of g3ipinterfaceNodeName1."
        ::= { g3ipinterface 77 }

    g3ipinterfaceNodeName74	OBJECT-TYPE
        SYNTAX    DisplayString (SIZE (0..15))
        ACCESS    read-only
        STATUS    mandatory
        DESCRIPTION
            "See DESCRIPTION of g3ipinterfaceNodeName1."
        ::= { g3ipinterface 78 }

    g3ipinterfaceNodeName75	OBJECT-TYPE
        SYNTAX    DisplayString (SIZE (0..15))
        ACCESS    read-only
        STATUS    mandatory
        DESCRIPTION
            "See DESCRIPTION of g3ipinterfaceNodeName1."
        ::= { g3ipinterface 79 }

    g3ipinterfaceNodeName76	OBJECT-TYPE
        SYNTAX    DisplayString (SIZE (0..15))
        ACCESS    read-only
        STATUS    mandatory
        DESCRIPTION
            "See DESCRIPTION of g3ipinterfaceNodeName1."
        ::= { g3ipinterface 80 }

    g3ipinterfaceNodeName77	OBJECT-TYPE
        SYNTAX    DisplayString (SIZE (0..15))
        ACCESS    read-only
        STATUS    mandatory
        DESCRIPTION
            "See DESCRIPTION of g3ipinterfaceNodeName1."
        ::= { g3ipinterface 81 }

    g3ipinterfaceNodeName78	OBJECT-TYPE
        SYNTAX    DisplayString (SIZE (0..15))
        ACCESS    read-only
        STATUS    mandatory
        DESCRIPTION
            "See DESCRIPTION of g3ipinterfaceNodeName1."
        ::= { g3ipinterface 82 }

    g3ipinterfaceNodeName79	OBJECT-TYPE
        SYNTAX    DisplayString (SIZE (0..15))
        ACCESS    read-only
        STATUS    mandatory
        DESCRIPTION
            "See DESCRIPTION of g3ipinterfaceNodeName1."
        ::= { g3ipinterface 83 }

    g3ipinterfaceNodeName80	OBJECT-TYPE
        SYNTAX    DisplayString (SIZE (0..15))
        ACCESS    read-only
        STATUS    mandatory
        DESCRIPTION
            "See DESCRIPTION of g3ipinterfaceNodeName1."
        ::= { g3ipinterface 84 }

    g3ipinterfaceNodeName81	OBJECT-TYPE
        SYNTAX    DisplayString (SIZE (0..15))
        ACCESS    read-only
        STATUS    mandatory
        DESCRIPTION
            "See DESCRIPTION of g3ipinterfaceNodeName1."
        ::= { g3ipinterface 85 }

    g3ipinterfaceNodeName82	OBJECT-TYPE
        SYNTAX    DisplayString (SIZE (0..15))
        ACCESS    read-only
        STATUS    mandatory
        DESCRIPTION
            "See DESCRIPTION of g3ipinterfaceNodeName1."
        ::= { g3ipinterface 86 }

    g3ipinterfaceNodeName83	OBJECT-TYPE
        SYNTAX    DisplayString (SIZE (0..15))
        ACCESS    read-only
        STATUS    mandatory
        DESCRIPTION
            "See DESCRIPTION of g3ipinterfaceNodeName1."
        ::= { g3ipinterface 87 }

    g3ipinterfaceNodeName84	OBJECT-TYPE
        SYNTAX    DisplayString (SIZE (0..15))
        ACCESS    read-only
        STATUS    mandatory
        DESCRIPTION
            "See DESCRIPTION of g3ipinterfaceNodeName1."
        ::= { g3ipinterface 88 }

    g3ipinterfaceNodeName85	OBJECT-TYPE
        SYNTAX    DisplayString (SIZE (0..15))
        ACCESS    read-only
        STATUS    mandatory
        DESCRIPTION
            "See DESCRIPTION of g3ipinterfaceNodeName1."
        ::= { g3ipinterface 89 }

    g3ipinterfaceSlot1	OBJECT-TYPE
        SYNTAX    DisplayString (SIZE (0..5))
        ACCESS    read-only
        STATUS    mandatory
        DESCRIPTION
            "An object containing the the VAL, CLAN or MEDPRO board slot number "
        ::= { g3ipinterface 90 }

    g3ipinterfaceSlot2	OBJECT-TYPE
        SYNTAX    DisplayString (SIZE (0..5))
        ACCESS    read-only
        STATUS    mandatory
        DESCRIPTION
            "See DESCRIPTION of g3ipinterfaceSlot1."
        ::= { g3ipinterface 91 }

    g3ipinterfaceSlot3	OBJECT-TYPE
        SYNTAX    DisplayString (SIZE (0..5))
        ACCESS    read-only
        STATUS    mandatory
        DESCRIPTION
            "See DESCRIPTION of g3ipinterfaceSlot1."
        ::= { g3ipinterface 92 }

    g3ipinterfaceSlot4	OBJECT-TYPE
        SYNTAX    DisplayString (SIZE (0..5))
        ACCESS    read-only
        STATUS    mandatory
        DESCRIPTION
            "See DESCRIPTION of g3ipinterfaceSlot1."
        ::= { g3ipinterface 93 }

    g3ipinterfaceSlot5	OBJECT-TYPE
        SYNTAX    DisplayString (SIZE (0..5))
        ACCESS    read-only
        STATUS    mandatory
        DESCRIPTION
            "See DESCRIPTION of g3ipinterfaceSlot1."
        ::= { g3ipinterface 94 }

    g3ipinterfaceSlot6	OBJECT-TYPE
        SYNTAX    DisplayString (SIZE (0..5))
        ACCESS    read-only
        STATUS    mandatory
        DESCRIPTION
            "See DESCRIPTION of g3ipinterfaceSlot1."
        ::= { g3ipinterface 95 }

    g3ipinterfaceSlot7	OBJECT-TYPE
        SYNTAX    DisplayString (SIZE (0..5))
        ACCESS    read-only
        STATUS    mandatory
        DESCRIPTION
            "See DESCRIPTION of g3ipinterfaceSlot1."
        ::= { g3ipinterface 96 }

    g3ipinterfaceSlot8	OBJECT-TYPE
        SYNTAX    DisplayString (SIZE (0..5))
        ACCESS    read-only
        STATUS    mandatory
        DESCRIPTION
            "See DESCRIPTION of g3ipinterfaceSlot1."
        ::= { g3ipinterface 97 }

    g3ipinterfaceSlot9	OBJECT-TYPE
        SYNTAX    DisplayString (SIZE (0..5))
        ACCESS    read-only
        STATUS    mandatory
        DESCRIPTION
            "See DESCRIPTION of g3ipinterfaceSlot1."
        ::= { g3ipinterface 98 }

    g3ipinterfaceSlot10	OBJECT-TYPE
        SYNTAX    DisplayString (SIZE (0..5))
        ACCESS    read-only
        STATUS    mandatory
        DESCRIPTION
            "See DESCRIPTION of g3ipinterfaceSlot1."
        ::= { g3ipinterface 99 }

    g3ipinterfaceSlot11	OBJECT-TYPE
        SYNTAX    DisplayString (SIZE (0..5))
        ACCESS    read-only
        STATUS    mandatory
        DESCRIPTION
            "See DESCRIPTION of g3ipinterfaceSlot1."
        ::= { g3ipinterface 100 }

    g3ipinterfaceSlot12	OBJECT-TYPE
        SYNTAX    DisplayString (SIZE (0..5))
        ACCESS    read-only
        STATUS    mandatory
        DESCRIPTION
            "See DESCRIPTION of g3ipinterfaceSlot1."
        ::= { g3ipinterface 101 }

    g3ipinterfaceSlot13	OBJECT-TYPE
        SYNTAX    DisplayString (SIZE (0..5))
        ACCESS    read-only
        STATUS    mandatory
        DESCRIPTION
            "See DESCRIPTION of g3ipinterfaceSlot1."
        ::= { g3ipinterface 102 }

    g3ipinterfaceSlot14	OBJECT-TYPE
        SYNTAX    DisplayString (SIZE (0..5))
        ACCESS    read-only
        STATUS    mandatory
        DESCRIPTION
            "See DESCRIPTION of g3ipinterfaceSlot1."
        ::= { g3ipinterface 103 }

    g3ipinterfaceSlot15	OBJECT-TYPE
        SYNTAX    DisplayString (SIZE (0..5))
        ACCESS    read-only
        STATUS    mandatory
        DESCRIPTION
            "See DESCRIPTION of g3ipinterfaceSlot1."
        ::= { g3ipinterface 104 }

    g3ipinterfaceSlot16	OBJECT-TYPE
        SYNTAX    DisplayString (SIZE (0..5))
        ACCESS    read-only
        STATUS    mandatory
        DESCRIPTION
            "See DESCRIPTION of g3ipinterfaceSlot1."
        ::= { g3ipinterface 105 }

    g3ipinterfaceSlot17	OBJECT-TYPE
        SYNTAX    DisplayString (SIZE (0..5))
        ACCESS    read-only
        STATUS    mandatory
        DESCRIPTION
            "See DESCRIPTION of g3ipinterfaceSlot1."
        ::= { g3ipinterface 106 }

    g3ipinterfaceSlot18	OBJECT-TYPE
        SYNTAX    DisplayString (SIZE (0..5))
        ACCESS    read-only
        STATUS    mandatory
        DESCRIPTION
            "See DESCRIPTION of g3ipinterfaceSlot1."
        ::= { g3ipinterface 107 }

    g3ipinterfaceSlot19	OBJECT-TYPE
        SYNTAX    DisplayString (SIZE (0..5))
        ACCESS    read-only
        STATUS    mandatory
        DESCRIPTION
            "See DESCRIPTION of g3ipinterfaceSlot1."
        ::= { g3ipinterface 108 }

    g3ipinterfaceSlot20	OBJECT-TYPE
        SYNTAX    DisplayString (SIZE (0..5))
        ACCESS    read-only
        STATUS    mandatory
        DESCRIPTION
            "See DESCRIPTION of g3ipinterfaceSlot1."
        ::= { g3ipinterface 109 }

    g3ipinterfaceSlot21	OBJECT-TYPE
        SYNTAX    DisplayString (SIZE (0..5))
        ACCESS    read-only
        STATUS    mandatory
        DESCRIPTION
            "See DESCRIPTION of g3ipinterfaceSlot1."
        ::= { g3ipinterface 110 }

    g3ipinterfaceSlot22	OBJECT-TYPE
        SYNTAX    DisplayString (SIZE (0..5))
        ACCESS    read-only
        STATUS    mandatory
        DESCRIPTION
            "See DESCRIPTION of g3ipinterfaceSlot1."
        ::= { g3ipinterface 111 }

    g3ipinterfaceSlot23	OBJECT-TYPE
        SYNTAX    DisplayString (SIZE (0..5))
        ACCESS    read-only
        STATUS    mandatory
        DESCRIPTION
            "See DESCRIPTION of g3ipinterfaceSlot1."
        ::= { g3ipinterface 112 }

    g3ipinterfaceSlot24	OBJECT-TYPE
        SYNTAX    DisplayString (SIZE (0..5))
        ACCESS    read-only
        STATUS    mandatory
        DESCRIPTION
            "See DESCRIPTION of g3ipinterfaceSlot1."
        ::= { g3ipinterface 113 }

    g3ipinterfaceSlot25	OBJECT-TYPE
        SYNTAX    DisplayString (SIZE (0..5))
        ACCESS    read-only
        STATUS    mandatory
        DESCRIPTION
            "See DESCRIPTION of g3ipinterfaceSlot1."
        ::= { g3ipinterface 114 }

    g3ipinterfaceSlot26	OBJECT-TYPE
        SYNTAX    DisplayString (SIZE (0..5))
        ACCESS    read-only
        STATUS    mandatory
        DESCRIPTION
            "See DESCRIPTION of g3ipinterfaceSlot1."
        ::= { g3ipinterface 115 }

    g3ipinterfaceSlot27	OBJECT-TYPE
        SYNTAX    DisplayString (SIZE (0..5))
        ACCESS    read-only
        STATUS    mandatory
        DESCRIPTION
            "See DESCRIPTION of g3ipinterfaceSlot1."
        ::= { g3ipinterface 116 }

    g3ipinterfaceSlot28	OBJECT-TYPE
        SYNTAX    DisplayString (SIZE (0..5))
        ACCESS    read-only
        STATUS    mandatory
        DESCRIPTION
            "See DESCRIPTION of g3ipinterfaceSlot1."
        ::= { g3ipinterface 117 }

    g3ipinterfaceSlot29	OBJECT-TYPE
        SYNTAX    DisplayString (SIZE (0..5))
        ACCESS    read-only
        STATUS    mandatory
        DESCRIPTION
            "See DESCRIPTION of g3ipinterfaceSlot1."
        ::= { g3ipinterface 118 }

    g3ipinterfaceSlot30	OBJECT-TYPE
        SYNTAX    DisplayString (SIZE (0..5))
        ACCESS    read-only
        STATUS    mandatory
        DESCRIPTION
            "See DESCRIPTION of g3ipinterfaceSlot1."
        ::= { g3ipinterface 119 }

    g3ipinterfaceSlot31	OBJECT-TYPE
        SYNTAX    DisplayString (SIZE (0..5))
        ACCESS    read-only
        STATUS    mandatory
        DESCRIPTION
            "See DESCRIPTION of g3ipinterfaceSlot1."
        ::= { g3ipinterface 120 }

    g3ipinterfaceSlot32	OBJECT-TYPE
        SYNTAX    DisplayString (SIZE (0..5))
        ACCESS    read-only
        STATUS    mandatory
        DESCRIPTION
            "See DESCRIPTION of g3ipinterfaceSlot1."
        ::= { g3ipinterface 121 }

    g3ipinterfaceSlot33	OBJECT-TYPE
        SYNTAX    DisplayString (SIZE (0..5))
        ACCESS    read-only
        STATUS    mandatory
        DESCRIPTION
            "See DESCRIPTION of g3ipinterfaceSlot1."
        ::= { g3ipinterface 122 }

    g3ipinterfaceSlot34	OBJECT-TYPE
        SYNTAX    DisplayString (SIZE (0..5))
        ACCESS    read-only
        STATUS    mandatory
        DESCRIPTION
            "See DESCRIPTION of g3ipinterfaceSlot1."
        ::= { g3ipinterface 123 }

    g3ipinterfaceSlot35	OBJECT-TYPE
        SYNTAX    DisplayString (SIZE (0..5))
        ACCESS    read-only
        STATUS    mandatory
        DESCRIPTION
            "See DESCRIPTION of g3ipinterfaceSlot1."
        ::= { g3ipinterface 124 }

    g3ipinterfaceSlot36	OBJECT-TYPE
        SYNTAX    DisplayString (SIZE (0..5))
        ACCESS    read-only
        STATUS    mandatory
        DESCRIPTION
            "See DESCRIPTION of g3ipinterfaceSlot1."
        ::= { g3ipinterface 125 }

    g3ipinterfaceSlot37	OBJECT-TYPE
        SYNTAX    DisplayString (SIZE (0..5))
        ACCESS    read-only
        STATUS    mandatory
        DESCRIPTION
            "See DESCRIPTION of g3ipinterfaceSlot1."
        ::= { g3ipinterface 126 }

    g3ipinterfaceSlot38	OBJECT-TYPE
        SYNTAX    DisplayString (SIZE (0..5))
        ACCESS    read-only
        STATUS    mandatory
        DESCRIPTION
            "See DESCRIPTION of g3ipinterfaceSlot1."
        ::= { g3ipinterface 127 }

    g3ipinterfaceSlot39	OBJECT-TYPE
        SYNTAX    DisplayString (SIZE (0..5))
        ACCESS    read-only
        STATUS    mandatory
        DESCRIPTION
            "See DESCRIPTION of g3ipinterfaceSlot1."
        ::= { g3ipinterface 128 }

    g3ipinterfaceSlot40	OBJECT-TYPE
        SYNTAX    DisplayString (SIZE (0..5))
        ACCESS    read-only
        STATUS    mandatory
        DESCRIPTION
            "See DESCRIPTION of g3ipinterfaceSlot1."
        ::= { g3ipinterface 129 }

    g3ipinterfaceSlot41	OBJECT-TYPE
        SYNTAX    DisplayString (SIZE (0..5))
        ACCESS    read-only
        STATUS    mandatory
        DESCRIPTION
            "See DESCRIPTION of g3ipinterfaceSlot1."
        ::= { g3ipinterface 130 }

    g3ipinterfaceSlot42	OBJECT-TYPE
        SYNTAX    DisplayString (SIZE (0..5))
        ACCESS    read-only
        STATUS    mandatory
        DESCRIPTION
            "See DESCRIPTION of g3ipinterfaceSlot1."
        ::= { g3ipinterface 131 }

    g3ipinterfaceSlot43	OBJECT-TYPE
        SYNTAX    DisplayString (SIZE (0..5))
        ACCESS    read-only
        STATUS    mandatory
        DESCRIPTION
            "See DESCRIPTION of g3ipinterfaceSlot1."
        ::= { g3ipinterface 132 }

    g3ipinterfaceSlot44	OBJECT-TYPE
        SYNTAX    DisplayString (SIZE (0..5))
        ACCESS    read-only
        STATUS    mandatory
        DESCRIPTION
            "See DESCRIPTION of g3ipinterfaceSlot1."
        ::= { g3ipinterface 133 }

    g3ipinterfaceSlot45	OBJECT-TYPE
        SYNTAX    DisplayString (SIZE (0..5))
        ACCESS    read-only
        STATUS    mandatory
        DESCRIPTION
            "See DESCRIPTION of g3ipinterfaceSlot1."
        ::= { g3ipinterface 134 }

    g3ipinterfaceSlot46	OBJECT-TYPE
        SYNTAX    DisplayString (SIZE (0..5))
        ACCESS    read-only
        STATUS    mandatory
        DESCRIPTION
            "See DESCRIPTION of g3ipinterfaceSlot1."
        ::= { g3ipinterface 135 }

    g3ipinterfaceSlot47	OBJECT-TYPE
        SYNTAX    DisplayString (SIZE (0..5))
        ACCESS    read-only
        STATUS    mandatory
        DESCRIPTION
            "See DESCRIPTION of g3ipinterfaceSlot1."
        ::= { g3ipinterface 136 }

    g3ipinterfaceSlot48	OBJECT-TYPE
        SYNTAX    DisplayString (SIZE (0..5))
        ACCESS    read-only
        STATUS    mandatory
        DESCRIPTION
            "See DESCRIPTION of g3ipinterfaceSlot1."
        ::= { g3ipinterface 137 }

    g3ipinterfaceSlot49	OBJECT-TYPE
        SYNTAX    DisplayString (SIZE (0..5))
        ACCESS    read-only
        STATUS    mandatory
        DESCRIPTION
            "See DESCRIPTION of g3ipinterfaceSlot1."
        ::= { g3ipinterface 138 }

    g3ipinterfaceSlot50	OBJECT-TYPE
        SYNTAX    DisplayString (SIZE (0..5))
        ACCESS    read-only
        STATUS    mandatory
        DESCRIPTION
            "See DESCRIPTION of g3ipinterfaceSlot1."
        ::= { g3ipinterface 139 }

    g3ipinterfaceSlot51	OBJECT-TYPE
        SYNTAX    DisplayString (SIZE (0..5))
        ACCESS    read-only
        STATUS    mandatory
        DESCRIPTION
            "See DESCRIPTION of g3ipinterfaceSlot1."
        ::= { g3ipinterface 140 }

    g3ipinterfaceSlot52	OBJECT-TYPE
        SYNTAX    DisplayString (SIZE (0..5))
        ACCESS    read-only
        STATUS    mandatory
        DESCRIPTION
            "See DESCRIPTION of g3ipinterfaceSlot1."
        ::= { g3ipinterface 141 }

    g3ipinterfaceSlot53	OBJECT-TYPE
        SYNTAX    DisplayString (SIZE (0..5))
        ACCESS    read-only
        STATUS    mandatory
        DESCRIPTION
            "See DESCRIPTION of g3ipinterfaceSlot1."
        ::= { g3ipinterface 142 }

    g3ipinterfaceSlot54	OBJECT-TYPE
        SYNTAX    DisplayString (SIZE (0..5))
        ACCESS    read-only
        STATUS    mandatory
        DESCRIPTION
            "See DESCRIPTION of g3ipinterfaceSlot1."
        ::= { g3ipinterface 143 }

    g3ipinterfaceSlot55	OBJECT-TYPE
        SYNTAX    DisplayString (SIZE (0..5))
        ACCESS    read-only
        STATUS    mandatory
        DESCRIPTION
            "See DESCRIPTION of g3ipinterfaceSlot1."
        ::= { g3ipinterface 144 }

    g3ipinterfaceSlot56	OBJECT-TYPE
        SYNTAX    DisplayString (SIZE (0..5))
        ACCESS    read-only
        STATUS    mandatory
        DESCRIPTION
            "See DESCRIPTION of g3ipinterfaceSlot1."
        ::= { g3ipinterface 145 }

    g3ipinterfaceSlot57	OBJECT-TYPE
        SYNTAX    DisplayString (SIZE (0..5))
        ACCESS    read-only
        STATUS    mandatory
        DESCRIPTION
            "See DESCRIPTION of g3ipinterfaceSlot1."
        ::= { g3ipinterface 146 }

    g3ipinterfaceSlot58	OBJECT-TYPE
        SYNTAX    DisplayString (SIZE (0..5))
        ACCESS    read-only
        STATUS    mandatory
        DESCRIPTION
            "See DESCRIPTION of g3ipinterfaceSlot1."
        ::= { g3ipinterface 147 }

    g3ipinterfaceSlot59	OBJECT-TYPE
        SYNTAX    DisplayString (SIZE (0..5))
        ACCESS    read-only
        STATUS    mandatory
        DESCRIPTION
            "See DESCRIPTION of g3ipinterfaceSlot1."
        ::= { g3ipinterface 148 }

    g3ipinterfaceSlot60	OBJECT-TYPE
        SYNTAX    DisplayString (SIZE (0..5))
        ACCESS    read-only
        STATUS    mandatory
        DESCRIPTION
            "See DESCRIPTION of g3ipinterfaceSlot1."
        ::= { g3ipinterface 149 }

    g3ipinterfaceSlot61	OBJECT-TYPE
        SYNTAX    DisplayString (SIZE (0..5))
        ACCESS    read-only
        STATUS    mandatory
        DESCRIPTION
            "See DESCRIPTION of g3ipinterfaceSlot1."
        ::= { g3ipinterface 150 }

    g3ipinterfaceSlot62	OBJECT-TYPE
        SYNTAX    DisplayString (SIZE (0..5))
        ACCESS    read-only
        STATUS    mandatory
        DESCRIPTION
            "See DESCRIPTION of g3ipinterfaceSlot1."
        ::= { g3ipinterface 151 }

    g3ipinterfaceSlot63	OBJECT-TYPE
        SYNTAX    DisplayString (SIZE (0..5))
        ACCESS    read-only
        STATUS    mandatory
        DESCRIPTION
            "See DESCRIPTION of g3ipinterfaceSlot1."
        ::= { g3ipinterface 152 }

    g3ipinterfaceSlot64	OBJECT-TYPE
        SYNTAX    DisplayString (SIZE (0..5))
        ACCESS    read-only
        STATUS    mandatory
        DESCRIPTION
            "See DESCRIPTION of g3ipinterfaceSlot1."
        ::= { g3ipinterface 153 }

    g3ipinterfaceSlot65	OBJECT-TYPE
        SYNTAX    DisplayString (SIZE (0..5))
        ACCESS    read-only
        STATUS    mandatory
        DESCRIPTION
            "See DESCRIPTION of g3ipinterfaceSlot1."
        ::= { g3ipinterface 154 }

    g3ipinterfaceSlot66	OBJECT-TYPE
        SYNTAX    DisplayString (SIZE (0..5))
        ACCESS    read-only
        STATUS    mandatory
        DESCRIPTION
            "See DESCRIPTION of g3ipinterfaceSlot1."
        ::= { g3ipinterface 155 }

    g3ipinterfaceSlot67	OBJECT-TYPE
        SYNTAX    DisplayString (SIZE (0..5))
        ACCESS    read-only
        STATUS    mandatory
        DESCRIPTION
            "See DESCRIPTION of g3ipinterfaceSlot1."
        ::= { g3ipinterface 156 }

    g3ipinterfaceSlot68	OBJECT-TYPE
        SYNTAX    DisplayString (SIZE (0..5))
        ACCESS    read-only
        STATUS    mandatory
        DESCRIPTION
            "See DESCRIPTION of g3ipinterfaceSlot1."
        ::= { g3ipinterface 157 }

    g3ipinterfaceSlot69	OBJECT-TYPE
        SYNTAX    DisplayString (SIZE (0..5))
        ACCESS    read-only
        STATUS    mandatory
        DESCRIPTION
            "See DESCRIPTION of g3ipinterfaceSlot1."
        ::= { g3ipinterface 158 }

    g3ipinterfaceSlot70	OBJECT-TYPE
        SYNTAX    DisplayString (SIZE (0..5))
        ACCESS    read-only
        STATUS    mandatory
        DESCRIPTION
            "See DESCRIPTION of g3ipinterfaceSlot1."
        ::= { g3ipinterface 159 }

    g3ipinterfaceSlot71	OBJECT-TYPE
        SYNTAX    DisplayString (SIZE (0..5))
        ACCESS    read-only
        STATUS    mandatory
        DESCRIPTION
            "See DESCRIPTION of g3ipinterfaceSlot1."
        ::= { g3ipinterface 160 }

    g3ipinterfaceSlot72	OBJECT-TYPE
        SYNTAX    DisplayString (SIZE (0..5))
        ACCESS    read-only
        STATUS    mandatory
        DESCRIPTION
            "See DESCRIPTION of g3ipinterfaceSlot1."
        ::= { g3ipinterface 161 }

    g3ipinterfaceSlot73	OBJECT-TYPE
        SYNTAX    DisplayString (SIZE (0..5))
        ACCESS    read-only
        STATUS    mandatory
        DESCRIPTION
            "See DESCRIPTION of g3ipinterfaceSlot1."
        ::= { g3ipinterface 162 }

    g3ipinterfaceSlot74	OBJECT-TYPE
        SYNTAX    DisplayString (SIZE (0..5))
        ACCESS    read-only
        STATUS    mandatory
        DESCRIPTION
            "See DESCRIPTION of g3ipinterfaceSlot1."
        ::= { g3ipinterface 163 }

    g3ipinterfaceSlot75	OBJECT-TYPE
        SYNTAX    DisplayString (SIZE (0..5))
        ACCESS    read-only
        STATUS    mandatory
        DESCRIPTION
            "See DESCRIPTION of g3ipinterfaceSlot1."
        ::= { g3ipinterface 164 }

    g3ipinterfaceSlot76	OBJECT-TYPE
        SYNTAX    DisplayString (SIZE (0..5))
        ACCESS    read-only
        STATUS    mandatory
        DESCRIPTION
            "See DESCRIPTION of g3ipinterfaceSlot1."
        ::= { g3ipinterface 165 }

    g3ipinterfaceSlot77	OBJECT-TYPE
        SYNTAX    DisplayString (SIZE (0..5))
        ACCESS    read-only
        STATUS    mandatory
        DESCRIPTION
            "See DESCRIPTION of g3ipinterfaceSlot1."
        ::= { g3ipinterface 166 }

    g3ipinterfaceSlot78	OBJECT-TYPE
        SYNTAX    DisplayString (SIZE (0..5))
        ACCESS    read-only
        STATUS    mandatory
        DESCRIPTION
            "See DESCRIPTION of g3ipinterfaceSlot1."
        ::= { g3ipinterface 167 }

    g3ipinterfaceSlot79	OBJECT-TYPE
        SYNTAX    DisplayString (SIZE (0..5))
        ACCESS    read-only
        STATUS    mandatory
        DESCRIPTION
            "See DESCRIPTION of g3ipinterfaceSlot1."
        ::= { g3ipinterface 168 }

    g3ipinterfaceSlot80	OBJECT-TYPE
        SYNTAX    DisplayString (SIZE (0..5))
        ACCESS    read-only
        STATUS    mandatory
        DESCRIPTION
            "See DESCRIPTION of g3ipinterfaceSlot1."
        ::= { g3ipinterface 169 }

    g3ipinterfaceSlot81	OBJECT-TYPE
        SYNTAX    DisplayString (SIZE (0..5))
        ACCESS    read-only
        STATUS    mandatory
        DESCRIPTION
            "See DESCRIPTION of g3ipinterfaceSlot1."
        ::= { g3ipinterface 170 }

    g3ipinterfaceSlot82	OBJECT-TYPE
        SYNTAX    DisplayString (SIZE (0..5))
        ACCESS    read-only
        STATUS    mandatory
        DESCRIPTION
            "See DESCRIPTION of g3ipinterfaceSlot1."
        ::= { g3ipinterface 171 }

    g3ipinterfaceSlot83	OBJECT-TYPE
        SYNTAX    DisplayString (SIZE (0..5))
        ACCESS    read-only
        STATUS    mandatory
        DESCRIPTION
            "See DESCRIPTION of g3ipinterfaceSlot1."
        ::= { g3ipinterface 172 }

    g3ipinterfaceSlot84	OBJECT-TYPE
        SYNTAX    DisplayString (SIZE (0..5))
        ACCESS    read-only
        STATUS    mandatory
        DESCRIPTION
            "See DESCRIPTION of g3ipinterfaceSlot1."
        ::= { g3ipinterface 173 }

    g3ipinterfaceSlot85	OBJECT-TYPE
        SYNTAX    DisplayString (SIZE (0..5))
        ACCESS    read-only
        STATUS    mandatory
        DESCRIPTION
            "See DESCRIPTION of g3ipinterfaceSlot1."
        ::= { g3ipinterface 174 }


    -- the g3gateway group

    g3gatewayTage	OBJECT-TYPE
        SYNTAX    INTEGER
        ACCESS    read-only
        STATUS    mandatory
        DESCRIPTION
            "The number of timeticks since the gateway data was last
            extracted from the switch by the Proxy Agent.  This object
            along with the g3gatewayintvl object allows the Network Manager
            to determine the validity of the gateway data in the cache and to control
            when the Proxy Agent extracts the data from the switch."
        ::= { g3gateway 1 }

    g3gatewayTintvl	OBJECT-TYPE
        SYNTAX    INTEGER
        ACCESS    read-write
        STATUS    mandatory
        DESCRIPTION
            "An object containing the interval for which the gateway data extracted 
            from the switch is considered valid by the
            Proxy Agent.  When a GET or GET-NEXT request for these gateway 
            objects is received by the agent it uses the g3gatewayage
            and g3gatewayintvl objects to determine whether it should refresh
            the cached gatewayTable.  If g3gatewaystmp +
            g3gatewayintvl is less than the current value of the sysUpTime
            object then the agent refreshes the gatewayTable cache.  In
            either case it responds to the requests it receives with the data
            it currently has in the cache."
        ::= { g3gateway 2 }

    g3gatewayTdelay	OBJECT-TYPE
        SYNTAX    INTEGER
        ACCESS    read-only
        STATUS    mandatory
        DESCRIPTION
            "An object containing the delay encountered in updating
            the cached data."
        ::= { g3gateway 3 }

    g3gatewayTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3gateway 4 }

    g3gatewayTcount	OBJECT-TYPE
        SYNTAX    Gauge
        ACCESS    read-only
        STATUS    mandatory
        DESCRIPTION
            "A Gauge object containing the number of data records in the cache."
        ::= { g3gateway 5 }

    g3gatewayTable	OBJECT-TYPE
        SYNTAX    SEQUENCE OF G3gatewayEntry
        ACCESS    not-accessible
        STATUS    mandatory
        DESCRIPTION
            "A list of g3gateway entries."
        ::= { g3gateway 6 }

    g3gatewayEntry	OBJECT-TYPE
        SYNTAX    G3gatewayEntry
        ACCESS    not-accessible
        STATUS    mandatory
        DESCRIPTION
            "A g3gateway entry containing objects of the
            g3gateway information sent by the switch."
        INDEX    { g3gatewayNumber }
        ::= { g3gatewayTable 1 }

    G3gatewayEntry ::= SEQUENCE {
        g3gatewayNumber
            INTEGER,
        g3gatewayName
            DisplayString,
        g3gatewayIdentifier
            DisplayString,
        g3gatewayIPAddress
            DisplayString,
        g3gatewayMACAddress
            DisplayString,
        g3gatewayRegion
            INTEGER,
        g3gatewayLocation
            DisplayString,
        g3gatewaySiteData1
            DisplayString,
        g3gatewaySiteData2
            DisplayString,
        g3gatewayG700ModTypeV1
            DisplayString,
        g3gatewayG700ModTypeV2
            DisplayString,
        g3gatewayG700ModTypeV3
            DisplayString,
        g3gatewayG700ModTypeV4
            DisplayString,
        g3gatewayG700ModTypeV8
            DisplayString,
        g3gatewayG700ModTypeV9
            DisplayString,
        g3gatewayRegistered
            DisplayString,
        g3gatewayType
            DisplayString,
        g3gatewayFWVintage
            DisplayString,
        g3gatewayHWVintage
            DisplayString,
        g3gatewayNearEndIP
            DisplayString,
        g3gatewayEncrypt
            DisplayString,
        g3gatewayG350ModTypeV1
            DisplayString,
        g3gatewayG350ModTypeV2
            DisplayString,
        g3gatewayG350ModTypeV3
            DisplayString,
        g3gatewayG350ModTypeV4
            DisplayString,
        g3gatewayG350ModTypeV5
            DisplayString,
        g3gatewayG350ModTypeV6
            DisplayString,
        g3gatewayG350ModTypeV7
            DisplayString,
        g3gatewayG350ModTypeV9
            DisplayString,
        g3gatewayRecoveryRule
            DisplayString,
        g3gatewayG350ModTypeV8
            DisplayString,
        g3gatewayG450ModTypeV1
            DisplayString,
        g3gatewayG450ModTypeV2
            DisplayString,
        g3gatewayG450ModTypeV3
            DisplayString,
        g3gatewayG450ModTypeV4
            DisplayString,
        g3gatewayG450ModTypeV5
            DisplayString,
        g3gatewayG450ModTypeV6
            DisplayString,
        g3gatewayG450ModTypeV7
            DisplayString,
        g3gatewayG450ModTypeV8
            DisplayString,
        g3gatewayG450ModTypeV9
            DisplayString,
        g3gatewayG250ModTypeV1
            DisplayString,
        g3gatewayG250ModTypeV2
            DisplayString,
        g3gatewayG250ModTypeV3
            DisplayString,
        g3gatewayG250ModTypeV4
            DisplayString,
        g3gatewayG250ModTypeV9
            DisplayString,
        g3gatewayJ6350J4350ModTypeV1
            DisplayString,
        g3gatewayJ6350J4350ModTypeV2
            DisplayString,
        g3gatewayJ6350J4350ModTypeV3
            DisplayString,
        g3gatewayJ6350J4350ModTypeV4
            DisplayString,
        g3gatewayJ6350J4350ModTypeV5
            DisplayString,
        g3gatewayJ6350J4350ModTypeV6
            DisplayString,
        g3gatewayJ6350J4350ModTypeV9
            DisplayString,
        g3gatewayJ2320ModTypeV1
            DisplayString,
        g3gatewayJ2320ModTypeV2
            DisplayString,
        g3gatewayJ2320ModTypeV3
            DisplayString,
        g3gatewayJ2320ModTypeV9
            DisplayString,
        g3gatewayJ2350ModTypeV1
            DisplayString,
        g3gatewayJ2350ModTypeV2
            DisplayString,
        g3gatewayJ2350ModTypeV3
            DisplayString,
        g3gatewayJ2350ModTypeV4
            DisplayString,
        g3gatewayJ2350ModTypeV5
            DisplayString,
        g3gatewayJ2350ModTypeV9
            DisplayString
        }

    g3gatewayNumber	OBJECT-TYPE
        SYNTAX    INTEGER
        ACCESS    read-only
        STATUS    mandatory
        DESCRIPTION
            "An object containing the Media Gateway number"
        ::= { g3gatewayEntry 1 }

    g3gatewayName	OBJECT-TYPE
        SYNTAX    DisplayString (SIZE (0..20))
        ACCESS    read-only
        STATUS    mandatory
        DESCRIPTION
            "An object containing the Media Gateway name"
        ::= { g3gatewayEntry 2 }

    g3gatewayIdentifier	OBJECT-TYPE
        SYNTAX    DisplayString (SIZE (0..20))
        ACCESS    read-only
        STATUS    mandatory
        DESCRIPTION
            "An object containing the Media Gateway identifier (either the serial    
            number or other alpha-numeric characters for identification)"
        ::= { g3gatewayEntry 3 }

    g3gatewayIPAddress	OBJECT-TYPE
        SYNTAX    DisplayString (SIZE (0..40))
        ACCESS    read-only
        STATUS    mandatory
        DESCRIPTION
            "An object containing the IP adrress of the Media Gateway"
        ::= { g3gatewayEntry 4 }

    g3gatewayMACAddress	OBJECT-TYPE
        SYNTAX    DisplayString (SIZE (0..17))
        ACCESS    read-only
        STATUS    mandatory
        DESCRIPTION
            "An object containing the MAC address of the Media Gateway"
        ::= { g3gatewayEntry 5 }

    g3gatewayRegion	OBJECT-TYPE
        SYNTAX    INTEGER
        ACCESS    read-only
        STATUS    mandatory
        DESCRIPTION
            "An object containing the network region for the Media Gateway"
        ::= { g3gatewayEntry 6 }

    g3gatewayLocation	OBJECT-TYPE
        SYNTAX    DisplayString (SIZE (0..2))
        ACCESS    read-only
        STATUS    mandatory
        DESCRIPTION
            "An object containing information about time-zone offset, daylight
            savings rule and number plan area code."
        ::= { g3gatewayEntry 7 }

    g3gatewaySiteData1	OBJECT-TYPE
        SYNTAX    DisplayString (SIZE (0..20))
        ACCESS    read-only
        STATUS    mandatory
        DESCRIPTION
            "An object containing general site information"
        ::= { g3gatewayEntry 8 }

    g3gatewaySiteData2	OBJECT-TYPE
        SYNTAX    DisplayString (SIZE (0..20))
        ACCESS    read-only
        STATUS    mandatory
        DESCRIPTION
            "An object containing general site information"
        ::= { g3gatewayEntry 9 }

    g3gatewayG700ModTypeV1	OBJECT-TYPE
        SYNTAX    DisplayString (SIZE (0..21))
        ACCESS    read-only
        STATUS    mandatory
        DESCRIPTION
            "An object containing the hardware contained in the G700 media module
            slot V1 (if any)."
        ::= { g3gatewayEntry 10 }

    g3gatewayG700ModTypeV2	OBJECT-TYPE
        SYNTAX    DisplayString (SIZE (0..21))
        ACCESS    read-only
        STATUS    mandatory
        DESCRIPTION
            "An object containing the hardware contained in the G700 media module
            slot V2 (if any)."
        ::= { g3gatewayEntry 11 }

    g3gatewayG700ModTypeV3	OBJECT-TYPE
        SYNTAX    DisplayString (SIZE (0..21))
        ACCESS    read-only
        STATUS    mandatory
        DESCRIPTION
            "An object containing the hardware contained in the G700 media module
            slot V3 (if any)."
        ::= { g3gatewayEntry 12 }

    g3gatewayG700ModTypeV4	OBJECT-TYPE
        SYNTAX    DisplayString (SIZE (0..21))
        ACCESS    read-only
        STATUS    mandatory
        DESCRIPTION
            "An object containing the hardware contained in the G700 media module
            slot V4 (if any)."
        ::= { g3gatewayEntry 13 }

    g3gatewayG700ModTypeV8	OBJECT-TYPE
        SYNTAX    DisplayString (SIZE (0..21))
        ACCESS    read-only
        STATUS    mandatory
        DESCRIPTION
            "An object containing the hardware contained in the G700 media module
            slot V8 (if any)."
        ::= { g3gatewayEntry 14 }

    g3gatewayG700ModTypeV9	OBJECT-TYPE
        SYNTAX    DisplayString (SIZE (0..21))
        ACCESS    read-only
        STATUS    mandatory
        DESCRIPTION
            "An object containing the hardware contained in the G700 media module
            slot V9 (if any)."
        ::= { g3gatewayEntry 15 }

    g3gatewayRegistered	OBJECT-TYPE
        SYNTAX    DisplayString (SIZE (0..1))
        ACCESS    read-only
        STATUS    mandatory
        DESCRIPTION
            "An object containing information about whether a Media Gateway is
            registered with a communications controller."
        ::= { g3gatewayEntry 16 }

    g3gatewayType	OBJECT-TYPE
        SYNTAX    DisplayString (SIZE (0..4))
        ACCESS    read-only
        STATUS    mandatory
        DESCRIPTION
            "An object containing the type of media gateway (G700 or G350)."
        ::= { g3gatewayEntry 17 }

    g3gatewayFWVintage	OBJECT-TYPE
        SYNTAX    DisplayString (SIZE (0..12))
        ACCESS    read-only
        STATUS    mandatory
        DESCRIPTION
            "An object containing the firmware version of the media gateway
            processor (for G700) or the single firmware image on the 
            motherboard (for G350). This value may not be available on
            a G700 with older firmware and is only available if the media
            gateway is registered. The object contains a set of three
            numbers in the format xxx.xxx.xxx."
        ::= { g3gatewayEntry 18 }

    g3gatewayHWVintage	OBJECT-TYPE
        SYNTAX    DisplayString (SIZE (0..3))
        ACCESS    read-only
        STATUS    mandatory
        DESCRIPTION
            "An object containing the hardware version of the media gateway.
            This value may not be available for a G700 with older firmware
            and is only available if th media gateway is registered."
        ::= { g3gatewayEntry 19 }

    g3gatewayNearEndIP	OBJECT-TYPE
        SYNTAX    DisplayString (SIZE (0..15))
        ACCESS    read-only
        STATUS    mandatory
        DESCRIPTION
            "An object containing the IP address of the CLAN or S8300 to
            which the media gateway is registered."
        ::= { g3gatewayEntry 20 }

    g3gatewayEncrypt	OBJECT-TYPE
        SYNTAX    DisplayString (SIZE (0..1))
        ACCESS    read-only
        STATUS    mandatory
        DESCRIPTION
            "An object indicating whether or not the media gateway is using
            encryption (y or n)."
        ::= { g3gatewayEntry 21 }

    g3gatewayG350ModTypeV1	OBJECT-TYPE
        SYNTAX    DisplayString (SIZE (0..21))
        ACCESS    read-only
        STATUS    mandatory
        DESCRIPTION
            "An object containing the hardware contained in the G350 media module
            slot V1 (if any)."
        ::= { g3gatewayEntry 22 }

    g3gatewayG350ModTypeV2	OBJECT-TYPE
        SYNTAX    DisplayString (SIZE (0..21))
        ACCESS    read-only
        STATUS    mandatory
        DESCRIPTION
            "An object containing the hardware contained in the G350 media module
            slot V2 (if any)."
        ::= { g3gatewayEntry 23 }

    g3gatewayG350ModTypeV3	OBJECT-TYPE
        SYNTAX    DisplayString (SIZE (0..21))
        ACCESS    read-only
        STATUS    mandatory
        DESCRIPTION
            "An object containing the hardware contained in the G350 media module
            slot V3 (if any)."
        ::= { g3gatewayEntry 24 }

    g3gatewayG350ModTypeV4	OBJECT-TYPE
        SYNTAX    DisplayString (SIZE (0..21))
        ACCESS    read-only
        STATUS    mandatory
        DESCRIPTION
            "An object containing the hardware contained in the G350 media module
            slot V4 (if any)."
        ::= { g3gatewayEntry 25 }

    g3gatewayG350ModTypeV5	OBJECT-TYPE
        SYNTAX    DisplayString (SIZE (0..21))
        ACCESS    read-only
        STATUS    mandatory
        DESCRIPTION
            "An object containing the hardware contained in the G350 media module
            slot V5 (if any)."
        ::= { g3gatewayEntry 26 }

    g3gatewayG350ModTypeV6	OBJECT-TYPE
        SYNTAX    DisplayString (SIZE (0..21))
        ACCESS    read-only
        STATUS    mandatory
        DESCRIPTION
            "An object containing the hardware contained in the G350 media module
            slot V6 (if any)."
        ::= { g3gatewayEntry 27 }

    g3gatewayG350ModTypeV7	OBJECT-TYPE
        SYNTAX    DisplayString (SIZE (0..21))
        ACCESS    read-only
        STATUS    mandatory
        DESCRIPTION
            "An object containing the hardware contained in the G350 media module
            slot V7 (if any)."
        ::= { g3gatewayEntry 28 }

    g3gatewayG350ModTypeV9	OBJECT-TYPE
        SYNTAX    DisplayString (SIZE (0..21))
        ACCESS    read-only
        STATUS    mandatory
        DESCRIPTION
            "An object containing the hardware contained in the G350 media module
            slot V9 (if any)."
        ::= { g3gatewayEntry 29 }

    g3gatewayRecoveryRule	OBJECT-TYPE
        SYNTAX    DisplayString (SIZE (0..4))
        ACCESS    read-only
        STATUS    mandatory
        DESCRIPTION
            "An object containing the recovery rule that is to be used by this
            media gateway for auto fail back to primary; acceptable values are
            1-250 or none; the default is none."
        ::= { g3gatewayEntry 30 }

    g3gatewayG350ModTypeV8	OBJECT-TYPE
        SYNTAX    DisplayString (SIZE (0..21))
        ACCESS    read-only
        STATUS    mandatory
        DESCRIPTION
            "An object containing the hardware contained in the G350 media module
            slot V8 (if any)."
        ::= { g3gatewayEntry 31 }

    g3gatewayG450ModTypeV1	OBJECT-TYPE
        SYNTAX    DisplayString (SIZE (0..21))
        ACCESS    read-only
        STATUS    mandatory
        DESCRIPTION
            "An object containing the hardware contained in the G450 media module
            slot V1 (if any)."
        ::= { g3gatewayEntry 32 }

    g3gatewayG450ModTypeV2	OBJECT-TYPE
        SYNTAX    DisplayString (SIZE (0..21))
        ACCESS    read-only
        STATUS    mandatory
        DESCRIPTION
            "An object containing the hardware contained in the G450 media module
            slot V2 (if any)."
        ::= { g3gatewayEntry 33 }

    g3gatewayG450ModTypeV3	OBJECT-TYPE
        SYNTAX    DisplayString (SIZE (0..21))
        ACCESS    read-only
        STATUS    mandatory
        DESCRIPTION
            "An object containing the hardware contained in the G450 media module
            slot V3 (if any)."
        ::= { g3gatewayEntry 34 }

    g3gatewayG450ModTypeV4	OBJECT-TYPE
        SYNTAX    DisplayString (SIZE (0..21))
        ACCESS    read-only
        STATUS    mandatory
        DESCRIPTION
            "An object containing the hardware contained in the G450 media module
            slot V4 (if any)."
        ::= { g3gatewayEntry 35 }

    g3gatewayG450ModTypeV5	OBJECT-TYPE
        SYNTAX    DisplayString (SIZE (0..21))
        ACCESS    read-only
        STATUS    mandatory
        DESCRIPTION
            "An object containing the hardware contained in the G450 media module
            slot V5 (if any)."
        ::= { g3gatewayEntry 36 }

    g3gatewayG450ModTypeV6	OBJECT-TYPE
        SYNTAX    DisplayString (SIZE (0..21))
        ACCESS    read-only
        STATUS    mandatory
        DESCRIPTION
            "An object containing the hardware contained in the G450 media module
            slot V6 (if any)."
        ::= { g3gatewayEntry 37 }

    g3gatewayG450ModTypeV7	OBJECT-TYPE
        SYNTAX    DisplayString (SIZE (0..21))
        ACCESS    read-only
        STATUS    mandatory
        DESCRIPTION
            "An object containing the hardware contained in the G450 media module
            slot V7 (if any)."
        ::= { g3gatewayEntry 38 }

    g3gatewayG450ModTypeV8	OBJECT-TYPE
        SYNTAX    DisplayString (SIZE (0..21))
        ACCESS    read-only
        STATUS    mandatory
        DESCRIPTION
            "An object containing the hardware contained in the G450 media module
            slot V8 (if any)."
        ::= { g3gatewayEntry 39 }

    g3gatewayG450ModTypeV9	OBJECT-TYPE
        SYNTAX    DisplayString (SIZE (0..21))
        ACCESS    read-only
        STATUS    mandatory
        DESCRIPTION
            "An object containing the hardware contained in the G450 media module
            slot V9 (if any)."
        ::= { g3gatewayEntry 40 }

    g3gatewayG250ModTypeV1	OBJECT-TYPE
        SYNTAX    DisplayString (SIZE (0..21))
        ACCESS    read-only
        STATUS    mandatory
        DESCRIPTION
            "An object containing the hardware contained in the G250 media module
            slot V1 (if any)."
        ::= { g3gatewayEntry 41 }

    g3gatewayG250ModTypeV2	OBJECT-TYPE
        SYNTAX    DisplayString (SIZE (0..21))
        ACCESS    read-only
        STATUS    mandatory
        DESCRIPTION
            "An object containing the hardware contained in the G250 media module
            slot V2 (if any)."
        ::= { g3gatewayEntry 42 }

    g3gatewayG250ModTypeV3	OBJECT-TYPE
        SYNTAX    DisplayString (SIZE (0..21))
        ACCESS    read-only
        STATUS    mandatory
        DESCRIPTION
            "An object containing the hardware contained in the G250 media module
            slot V3 (if any)."
        ::= { g3gatewayEntry 43 }

    g3gatewayG250ModTypeV4	OBJECT-TYPE
        SYNTAX    DisplayString (SIZE (0..21))
        ACCESS    read-only
        STATUS    mandatory
        DESCRIPTION
            "An object containing the hardware contained in the G250 media module
            slot V4 (if any)."
        ::= { g3gatewayEntry 44 }

    g3gatewayG250ModTypeV9	OBJECT-TYPE
        SYNTAX    DisplayString (SIZE (0..21))
        ACCESS    read-only
        STATUS    mandatory
        DESCRIPTION
            "An object containing the hardware contained in the G250 media module
            slot V9 (if any)."
        ::= { g3gatewayEntry 45 }

    g3gatewayJ6350J4350ModTypeV1	OBJECT-TYPE
        SYNTAX    DisplayString (SIZE (0..21))
        ACCESS    read-only
        STATUS    mandatory
        DESCRIPTION
            "An object containing the hardware contained in the J6350 or J4350
            media module slot V1 (if any)."
        ::= { g3gatewayEntry 46 }

    g3gatewayJ6350J4350ModTypeV2	OBJECT-TYPE
        SYNTAX    DisplayString (SIZE (0..21))
        ACCESS    read-only
        STATUS    mandatory
        DESCRIPTION
            "An object containing the hardware contained in the J6350 or J4350
            media module slot V2 (if any)."
        ::= { g3gatewayEntry 47 }

    g3gatewayJ6350J4350ModTypeV3	OBJECT-TYPE
        SYNTAX    DisplayString (SIZE (0..21))
        ACCESS    read-only
        STATUS    mandatory
        DESCRIPTION
            "An object containing the hardware contained in the J6350 or J4350
            media module slot V3 (if any)."
        ::= { g3gatewayEntry 48 }

    g3gatewayJ6350J4350ModTypeV4	OBJECT-TYPE
        SYNTAX    DisplayString (SIZE (0..21))
        ACCESS    read-only
        STATUS    mandatory
        DESCRIPTION
            "An object containing the hardware contained in the J6350 or J4350
            media module slot V4 (if any)."
        ::= { g3gatewayEntry 49 }

    g3gatewayJ6350J4350ModTypeV5	OBJECT-TYPE
        SYNTAX    DisplayString (SIZE (0..21))
        ACCESS    read-only
        STATUS    mandatory
        DESCRIPTION
            "An object containing the hardware contained in the J6350 or J4350
            media module slot V5 (if any)."
        ::= { g3gatewayEntry 50 }

    g3gatewayJ6350J4350ModTypeV6	OBJECT-TYPE
        SYNTAX    DisplayString (SIZE (0..21))
        ACCESS    read-only
        STATUS    mandatory
        DESCRIPTION
            "An object containing the hardware contained in the J6350 or J4350
            media module slot V6 (if any)."
        ::= { g3gatewayEntry 51 }

    g3gatewayJ6350J4350ModTypeV9	OBJECT-TYPE
        SYNTAX    DisplayString (SIZE (0..21))
        ACCESS    read-only
        STATUS    mandatory
        DESCRIPTION
            "An object containing the hardware contained in the J6350 or J4350
            media module slot V9 (if any)."
        ::= { g3gatewayEntry 52 }

    g3gatewayJ2320ModTypeV1	OBJECT-TYPE
        SYNTAX    DisplayString (SIZE (0..21))
        ACCESS    read-only
        STATUS    mandatory
        DESCRIPTION
            "An object containing the hardware contained in the J2320 media module
            slot V1 (if any)."
        ::= { g3gatewayEntry 53 }

    g3gatewayJ2320ModTypeV2	OBJECT-TYPE
        SYNTAX    DisplayString (SIZE (0..21))
        ACCESS    read-only
        STATUS    mandatory
        DESCRIPTION
            "An object containing the hardware contained in the J2320 media module
            slot V2 (if any)."
        ::= { g3gatewayEntry 54 }

    g3gatewayJ2320ModTypeV3	OBJECT-TYPE
        SYNTAX    DisplayString (SIZE (0..21))
        ACCESS    read-only
        STATUS    mandatory
        DESCRIPTION
            "An object containing the hardware contained in the J2320 media module
            slot V3 (if any)."
        ::= { g3gatewayEntry 55 }

    g3gatewayJ2320ModTypeV9	OBJECT-TYPE
        SYNTAX    DisplayString (SIZE (0..21))
        ACCESS    read-only
        STATUS    mandatory
        DESCRIPTION
            "An object containing the hardware contained in the J2320 media module
            slot V9 (if any)."
        ::= { g3gatewayEntry 56 }

    g3gatewayJ2350ModTypeV1	OBJECT-TYPE
        SYNTAX    DisplayString (SIZE (0..21))
        ACCESS    read-only
        STATUS    mandatory
        DESCRIPTION
            "An object containing the hardware contained in the J2350 media module
            slot V1 (if any)."
        ::= { g3gatewayEntry 57 }

    g3gatewayJ2350ModTypeV2	OBJECT-TYPE
        SYNTAX    DisplayString (SIZE (0..21))
        ACCESS    read-only
        STATUS    mandatory
        DESCRIPTION
            "An object containing the hardware contained in the J2350 media module
            slot V2 (if any)."
        ::= { g3gatewayEntry 58 }

    g3gatewayJ2350ModTypeV3	OBJECT-TYPE
        SYNTAX    DisplayString (SIZE (0..21))
        ACCESS    read-only
        STATUS    mandatory
        DESCRIPTION
            "An object containing the hardware contained in the J2350 media module
            slot V3 (if any)."
        ::= { g3gatewayEntry 59 }

    g3gatewayJ2350ModTypeV4	OBJECT-TYPE
        SYNTAX    DisplayString (SIZE (0..21))
        ACCESS    read-only
        STATUS    mandatory
        DESCRIPTION
            "An object containing the hardware contained in the J2350 media module
            slot V4(if any)."
        ::= { g3gatewayEntry 60 }

    g3gatewayJ2350ModTypeV5	OBJECT-TYPE
        SYNTAX    DisplayString (SIZE (0..21))
        ACCESS    read-only
        STATUS    mandatory
        DESCRIPTION
            "An object containing the hardware contained in the J2350 media module
            slot V5(if any)."
        ::= { g3gatewayEntry 61 }

    g3gatewayJ2350ModTypeV9	OBJECT-TYPE
        SYNTAX    DisplayString (SIZE (0..21))
        ACCESS    read-only
        STATUS    mandatory
        DESCRIPTION
            "An object containing the hardware contained in the J2350 media module
            slot V9 (if any)."
        ::= { g3gatewayEntry 62 }


    -- the g3mediacfg group

    g3mediacfgTage	OBJECT-TYPE
        SYNTAX    INTEGER
        ACCESS    read-only
        STATUS    mandatory
        DESCRIPTION
            "The number of timeticks since the media config data was
            extracted from the switch by the G3 Proxy Agent. This object
            along with the g3mediacfgTintvl object allows the Network Manager
            to determine the validity of the media config data in the
            cache and to control when the proxy agent extracts the
            media config data from the switch."
        ::= { g3mediacfg 1 }

    g3mediacfgTintvl	OBJECT-TYPE
        SYNTAX    INTEGER
        ACCESS    read-write
        STATUS    mandatory
        DESCRIPTION
            "An object containing the interval for which the media config data 
            extracted from	the switch is considered valid by the proxy agent.  When 
            a GET or	GET-NEXT request for media config objects is received by 
            the agent it uses	the g3mediacfgTage and g3mediacfgTintvl objects to 
            determine	whether it should refresh the cached mediacfgTable.  If
            g3mediacfgTstmp + g3mediacfgTintvl is less than the current
            value of the sysUpTime object then the agent refreshes the
            mediacfgTable cache.  In either case it responds to the 
            requests it receives with the data it currently has in the cache."
        ::= { g3mediacfg 2 }

    g3mediacfgTdelay	OBJECT-TYPE
        SYNTAX    INTEGER
        ACCESS    read-only
        STATUS    mandatory
        DESCRIPTION
            "An object containing the delay encountered in updating
            the cached data"
        ::= { g3mediacfg 3 }

    g3mediacfgTretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3mediacfg 4 }

    g3mediacfgTcount	OBJECT-TYPE
        SYNTAX    Gauge
        ACCESS    read-only
        STATUS    mandatory
        DESCRIPTION
            "A Gauge object containing the number of data records in the cache."
        ::= { g3mediacfg 5 }

    g3mediacfgTable	OBJECT-TYPE
        SYNTAX    SEQUENCE OF G3mediacfgEntry
        ACCESS    not-accessible
        STATUS    mandatory
        DESCRIPTION
            "A list of g3mediacfg entries."
        ::= { g3mediacfg 6 }

    g3mediacfgEntry	OBJECT-TYPE
        SYNTAX    G3mediacfgEntry
        ACCESS    not-accessible
        STATUS    mandatory
        DESCRIPTION
            "A g3mediacfg entry containing objects of the
            g3mediacfg information sent by the switch."
        INDEX    { g3mediacfgBoardNum }
        ::= { g3mediacfgTable 1 }

    G3mediacfgEntry ::= SEQUENCE {
        g3mediacfgBoardNum
            DisplayString,
        g3mediacfgBoardType
            DisplayString,
        g3mediacfgCode
            DisplayString,
        g3mediacfgVintage
            DisplayString,
        g3mediacfgSuffix
            DisplayString
        }

    g3mediacfgBoardNum	OBJECT-TYPE
        SYNTAX    DisplayString (SIZE (0..7))
        ACCESS    read-only
        STATUS    mandatory
        DESCRIPTION
            "A DisplayString Object that uniquely identifies a station board based
            on its location in the system. The syntax for the Board Number is as
            follows: cabinet(01-44):carrier(A-E):slot(01-20)."
        ::= { g3mediacfgEntry 1 }

    g3mediacfgBoardType	OBJECT-TYPE
        SYNTAX    DisplayString (SIZE (0..19))
        ACCESS    read-only
        STATUS    mandatory
        DESCRIPTION
            "A DisplayString Object that contains a text description of the
            type of media gateway board."
        ::= { g3mediacfgEntry 2 }

    g3mediacfgCode	OBJECT-TYPE
        SYNTAX    DisplayString (SIZE (0..8))
        ACCESS    read-only
        STATUS    mandatory
        DESCRIPTION
            "A DisplayString Object that contains the code that defines the
            type of media gateway board."
        ::= { g3mediacfgEntry 3 }

    g3mediacfgVintage	OBJECT-TYPE
        SYNTAX    DisplayString (SIZE (0..10))
        ACCESS    read-only
        STATUS    mandatory
        DESCRIPTION
            "A DisplayString Object that contains the vintage of the media 
            gateway board."
        ::= { g3mediacfgEntry 4 }

    g3mediacfgSuffix	OBJECT-TYPE
        SYNTAX    DisplayString (SIZE (0..2))
        ACCESS    read-only
        STATUS    mandatory
        DESCRIPTION
            "A DisplayString Object that contains the suffix to the code"
        ::= { g3mediacfgEntry 5 }


    -- the g3stamedia group

    g3stamediaTage	OBJECT-TYPE
        SYNTAX    INTEGER
        ACCESS    read-only
        STATUS    mandatory
        DESCRIPTION
            "The number of timeticks since the media gateway status data was last
            extracted from the switch by the G3 Proxy Agent. This object
            along with the g3stamediaintvl object allows the Network Manager
            to determine the validity of the media gateway status data in the
            cache and to control when the proxy agent extracts the
            media gateway status data from the switch."
        ::= { g3stamedia 1 }

    g3stamediaTintvl	OBJECT-TYPE
        SYNTAX    INTEGER
        ACCESS    read-write
        STATUS    mandatory
        DESCRIPTION
            "An object containing the interval for which the media gateway data
            extracted from the switch is considered valid by the proxy agent.
            When a GET or GET-NEXT request for media gateway objects is
            received by the agent it uses the g3stamediaage and g3stamediaintvl
            objects to determine whether it should refresh the cached
            stamediaTable.  If g3stamediastmp + g3stamediaintvl is less than the
            current value of the sysUpTime object then the agent refreshes
            the stamediaTable cache.  In either case it responds to the requests
            it receives with the data it currently has in the cache."
        ::= { g3stamedia 2 }

    g3stamediaTdelay	OBJECT-TYPE
        SYNTAX    INTEGER
        ACCESS    read-only
        STATUS    mandatory
        DESCRIPTION
            "An object containing the delay encountered in updating
            the cached data"
        ::= { g3stamedia 3 }

    g3stamediaTretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3stamedia 4 }

    g3stamediaAlarmMajor	OBJECT-TYPE
        SYNTAX    INTEGER
        ACCESS    read-only
        STATUS    mandatory
        DESCRIPTION
            "An object containing the total number of major alarms existing on the
            media gateways administered in the system."
        ::= { g3stamedia 5 }

    g3stamediaAlarmMinor	OBJECT-TYPE
        SYNTAX    INTEGER
        ACCESS    read-only
        STATUS    mandatory
        DESCRIPTION
            "An object containing the total number of minor alarms existing on the
            media gateways administered in the system."
        ::= { g3stamedia 6 }

    g3stamediaAlarmWarning	OBJECT-TYPE
        SYNTAX    INTEGER
        ACCESS    read-only
        STATUS    mandatory
        DESCRIPTION
            "An object containing the total number of warnings existing on the
            media gateways administered in a system."
        ::= { g3stamedia 7 }

    g3stamediaBusyOutTrunks	OBJECT-TYPE
        SYNTAX    INTEGER
        ACCESS    read-only
        STATUS    mandatory
        DESCRIPTION
            "An object containing the total number of busied out trunks existing on
            the media gateways administered in the system."
        ::= { g3stamedia 8 }

    g3stamediaBusyOutStations	OBJECT-TYPE
        SYNTAX    INTEGER
        ACCESS    read-only
        STATUS    mandatory
        DESCRIPTION
            "An object containing the total number of busied out stations existing
            on the media gateways administered in the system."
        ::= { g3stamedia 9 }

    g3stamediaH248LinksDown	OBJECT-TYPE
        SYNTAX    INTEGER
        ACCESS    read-only
        STATUS    mandatory
        DESCRIPTION
            "An object containing the total number of media gateways administered
            in a system that do not have a H.248 link established to the media
            gateway controller."
        ::= { g3stamedia 10 }

    g3stamediaH248LinksUp	OBJECT-TYPE
        SYNTAX    INTEGER
        ACCESS    read-only
        STATUS    mandatory
        DESCRIPTION
            "An object containing the total number of media gateways administered
            in a system that do have a H.248 link established to the media gateway
            controller."
        ::= { g3stamedia 11 }

    g3stamediaNbrLogins	OBJECT-TYPE
        SYNTAX    INTEGER
        ACCESS    read-only
        STATUS    mandatory
        DESCRIPTION
            "An object containing the total number of logins into the system."
        ::= { g3stamedia 12 }

    g3stamediaGatewayStatus1	OBJECT-TYPE
        SYNTAX    DisplayString (SIZE (0..14))
        ACCESS    read-only
        STATUS    mandatory
        DESCRIPTION
            "An object containing the status of the first set of eight media
            gateways, including the number of major alarms, minor alarms,
            warnings, and the H.248 link status for each specific media gateway
            number."
        ::= { g3stamedia 13 }

    g3stamediaGatewayStatus2	OBJECT-TYPE
        SYNTAX    DisplayString (SIZE (0..14))
        ACCESS    read-only
        STATUS    mandatory
        DESCRIPTION
            "See DESCRIPTION of g3stamediaGatewayStatus1."
        ::= { g3stamedia 14 }

    g3stamediaGatewayStatus3	OBJECT-TYPE
        SYNTAX    DisplayString (SIZE (0..14))
        ACCESS    read-only
        STATUS    mandatory
        DESCRIPTION
            "See DESCRIPTION of g3stamediaGatewayStatus1."
        ::= { g3stamedia 15 }

    g3stamediaGatewayStatus4	OBJECT-TYPE
        SYNTAX    DisplayString (SIZE (0..14))
        ACCESS    read-only
        STATUS    mandatory
        DESCRIPTION
            "See DESCRIPTION of g3stamediaGatewayStatus1."
        ::= { g3stamedia 16 }

    g3stamediaGatewayStatus5	OBJECT-TYPE
        SYNTAX    DisplayString (SIZE (0..14))
        ACCESS    read-only
        STATUS    mandatory
        DESCRIPTION
            "See DESCRIPTION of g3stamediaGatewayStatus1."
        ::= { g3stamedia 17 }

    g3stamediaGatewayStatus6	OBJECT-TYPE
        SYNTAX    DisplayString (SIZE (0..14))
        ACCESS    read-only
        STATUS    mandatory
        DESCRIPTION
            "See DESCRIPTION of g3stamediaGatewayStatus1."
        ::= { g3stamedia 18 }

    g3stamediaGatewayStatus7	OBJECT-TYPE
        SYNTAX    DisplayString (SIZE (0..14))
        ACCESS    read-only
        STATUS    mandatory
        DESCRIPTION
            "See DESCRIPTION of g3stamediaGatewayStatus1."
        ::= { g3stamedia 19 }

    g3stamediaGatewayStatus8	OBJECT-TYPE
        SYNTAX    DisplayString (SIZE (0..14))
        ACCESS    read-only
        STATUS    mandatory
        DESCRIPTION
            "See DESCRIPTION of g3stamediaGatewayStatus1."
        ::= { g3stamedia 20 }

    g3stamediaGatewayStatus9	OBJECT-TYPE
        SYNTAX    DisplayString (SIZE (0..14))
        ACCESS    read-only
        STATUS    mandatory
        DESCRIPTION
            "An object containing the status of the second set of eight media
            gateways, including the number of major alarms, minor alarms,
            warnings, and the H.248 link status for each specific media gateway
            number."
        ::= { g3stamedia 21 }

    g3stamediaGatewayStatus10	OBJECT-TYPE
        SYNTAX    DisplayString (SIZE (0..14))
        ACCESS    read-only
        STATUS    mandatory
        DESCRIPTION
            "See DESCRIPTION of g3stamediaGatewayStatus9."
        ::= { g3stamedia 22 }

    g3stamediaGatewayStatus11	OBJECT-TYPE
        SYNTAX    DisplayString (SIZE (0..14))
        ACCESS    read-only
        STATUS    mandatory
        DESCRIPTION
            "See DESCRIPTION of g3stamediaGatewayStatus9."
        ::= { g3stamedia 23 }

    g3stamediaGatewayStatus12	OBJECT-TYPE
        SYNTAX    DisplayString (SIZE (0..14))
        ACCESS    read-only
        STATUS    mandatory
        DESCRIPTION
            "See DESCRIPTION of g3stamediaGatewayStatus9."
        ::= { g3stamedia 24 }

    g3stamediaGatewayStatus13	OBJECT-TYPE
        SYNTAX    DisplayString (SIZE (0..14))
        ACCESS    read-only
        STATUS    mandatory
        DESCRIPTION
            "See DESCRIPTION of g3stamediaGatewayStatus9."
        ::= { g3stamedia 25 }

    g3stamediaGatewayStatus14	OBJECT-TYPE
        SYNTAX    DisplayString (SIZE (0..14))
        ACCESS    read-only
        STATUS    mandatory
        DESCRIPTION
            "See DESCRIPTION of g3stamediaGatewayStatus9."
        ::= { g3stamedia 26 }

    g3stamediaGatewayStatus15	OBJECT-TYPE
        SYNTAX    DisplayString (SIZE (0..14))
        ACCESS    read-only
        STATUS    mandatory
        DESCRIPTION
            "See DESCRIPTION of g3stamediaGatewayStatus9."
        ::= { g3stamedia 27 }

    g3stamediaGatewayStatus16	OBJECT-TYPE
        SYNTAX    DisplayString (SIZE (0..14))
        ACCESS    read-only
        STATUS    mandatory
        DESCRIPTION
            "See DESCRIPTION of g3stamediaGatewayStatus9."
        ::= { g3stamedia 28 }

    g3stamediaGatewayStatus17	OBJECT-TYPE
        SYNTAX    DisplayString (SIZE (0..14))
        ACCESS    read-only
        STATUS    mandatory
        DESCRIPTION
            "An object containing the status of the third set of eight media
            gateways, including the number of major alarms, minor alarms,
            warnings, and the H.248 link status for each specific media gateway
            number."
        ::= { g3stamedia 29 }

    g3stamediaGatewayStatus18	OBJECT-TYPE
        SYNTAX    DisplayString (SIZE (0..14))
        ACCESS    read-only
        STATUS    mandatory
        DESCRIPTION
            "See DESCRIPTION of g3stamediaGatewayStatus17."
        ::= { g3stamedia 30 }

    g3stamediaGatewayStatus19	OBJECT-TYPE
        SYNTAX    DisplayString (SIZE (0..14))
        ACCESS    read-only
        STATUS    mandatory
        DESCRIPTION
            "See DESCRIPTION of g3stamediaGatewayStatus17."
        ::= { g3stamedia 31 }

    g3stamediaGatewayStatus20	OBJECT-TYPE
        SYNTAX    DisplayString (SIZE (0..14))
        ACCESS    read-only
        STATUS    mandatory
        DESCRIPTION
            "See DESCRIPTION of g3stamediaGatewayStatus17."
        ::= { g3stamedia 32 }

    g3stamediaGatewayStatus21	OBJECT-TYPE
        SYNTAX    DisplayString (SIZE (0..14))
        ACCESS    read-only
        STATUS    mandatory
        DESCRIPTION
            "See DESCRIPTION of g3stamediaGatewayStatus17."
        ::= { g3stamedia 33 }

    g3stamediaGatewayStatus22	OBJECT-TYPE
        SYNTAX    DisplayString (SIZE (0..14))
        ACCESS    read-only
        STATUS    mandatory
        DESCRIPTION
            "See DESCRIPTION of g3stamediaGatewayStatus17."
        ::= { g3stamedia 34 }

    g3stamediaGatewayStatus23	OBJECT-TYPE
        SYNTAX    DisplayString (SIZE (0..14))
        ACCESS    read-only
        STATUS    mandatory
        DESCRIPTION
            "See DESCRIPTION of g3stamediaGatewayStatus17."
        ::= { g3stamedia 35 }

    g3stamediaGatewayStatus24	OBJECT-TYPE
        SYNTAX    DisplayString (SIZE (0..14))
        ACCESS    read-only
        STATUS    mandatory
        DESCRIPTION
            "See DESCRIPTION of g3stamediaGatewayStatus17."
        ::= { g3stamedia 36 }

    g3stamediaGatewayStatus25	OBJECT-TYPE
        SYNTAX    DisplayString (SIZE (0..14))
        ACCESS    read-only
        STATUS    mandatory
        DESCRIPTION
            "An object containing the status of the fourth set of eight media
            gateways, including the number of major alarms, minor alarms,
            warnings, and the H.248 link status for each specific media gateway
            number."
        ::= { g3stamedia 37 }

    g3stamediaGatewayStatus26	OBJECT-TYPE
        SYNTAX    DisplayString (SIZE (0..14))
        ACCESS    read-only
        STATUS    mandatory
        DESCRIPTION
            "See DESCRIPTION of g3stamediaGatewayStatus25."
        ::= { g3stamedia 38 }

    g3stamediaGatewayStatus27	OBJECT-TYPE
        SYNTAX    DisplayString (SIZE (0..14))
        ACCESS    read-only
        STATUS    mandatory
        DESCRIPTION
            "See DESCRIPTION of g3stamediaGatewayStatus25."
        ::= { g3stamedia 39 }

    g3stamediaGatewayStatus28	OBJECT-TYPE
        SYNTAX    DisplayString (SIZE (0..14))
        ACCESS    read-only
        STATUS    mandatory
        DESCRIPTION
            "See DESCRIPTION of g3stamediaGatewayStatus25."
        ::= { g3stamedia 40 }

    g3stamediaGatewayStatus29	OBJECT-TYPE
        SYNTAX    DisplayString (SIZE (0..14))
        ACCESS    read-only
        STATUS    mandatory
        DESCRIPTION
            "See DESCRIPTION of g3stamediaGatewayStatus25."
        ::= { g3stamedia 41 }

    g3stamediaGatewayStatus30	OBJECT-TYPE
        SYNTAX    DisplayString (SIZE (0..14))
        ACCESS    read-only
        STATUS    mandatory
        DESCRIPTION
            "See DESCRIPTION of g3stamediaGatewayStatus25."
        ::= { g3stamedia 42 }

    g3stamediaGatewayStatus31	OBJECT-TYPE
        SYNTAX    DisplayString (SIZE (0..14))
        ACCESS    read-only
        STATUS    mandatory
        DESCRIPTION
            "See DESCRIPTION of g3stamediaGatewayStatus25."
        ::= { g3stamedia 43 }

    g3stamediaGatewayStatus32	OBJECT-TYPE
        SYNTAX    DisplayString (SIZE (0..14))
        ACCESS    read-only
        STATUS    mandatory
        DESCRIPTION
            "See DESCRIPTION of g3stamediaGatewayStatus25."
        ::= { g3stamedia 44 }

    g3stamediaGatewayStatus33	OBJECT-TYPE
        SYNTAX    DisplayString (SIZE (0..14))
        ACCESS    read-only
        STATUS    mandatory
        DESCRIPTION
            "An object containing the status of the fifth set of eight media
            gateways, including the number of major alarms, minor alarms,
            warnings, and the H.248 link status for each specific media gateway
            number."
        ::= { g3stamedia 45 }

    g3stamediaGatewayStatus34	OBJECT-TYPE
        SYNTAX    DisplayString (SIZE (0..14))
        ACCESS    read-only
        STATUS    mandatory
        DESCRIPTION
            "See DESCRIPTION of g3stamediaGatewayStatus33."
        ::= { g3stamedia 46 }

    g3stamediaGatewayStatus35	OBJECT-TYPE
        SYNTAX    DisplayString (SIZE (0..14))
        ACCESS    read-only
        STATUS    mandatory
        DESCRIPTION
            "See DESCRIPTION of g3stamediaGatewayStatus33."
        ::= { g3stamedia 47 }

    g3stamediaGatewayStatus36	OBJECT-TYPE
        SYNTAX    DisplayString (SIZE (0..14))
        ACCESS    read-only
        STATUS    mandatory
        DESCRIPTION
            "See DESCRIPTION of g3stamediaGatewayStatus33."
        ::= { g3stamedia 48 }

    g3stamediaGatewayStatus37	OBJECT-TYPE
        SYNTAX    DisplayString (SIZE (0..14))
        ACCESS    read-only
        STATUS    mandatory
        DESCRIPTION
            "See DESCRIPTION of g3stamediaGatewayStatus33."
        ::= { g3stamedia 49 }

    g3stamediaGatewayStatus38	OBJECT-TYPE
        SYNTAX    DisplayString (SIZE (0..14))
        ACCESS    read-only
        STATUS    mandatory
        DESCRIPTION
            "See DESCRIPTION of g3stamediaGatewayStatus33."
        ::= { g3stamedia 50 }

    g3stamediaGatewayStatus39	OBJECT-TYPE
        SYNTAX    DisplayString (SIZE (0..14))
        ACCESS    read-only
        STATUS    mandatory
        DESCRIPTION
            "See DESCRIPTION of g3stamediaGatewayStatus33."
        ::= { g3stamedia 51 }

    g3stamediaGatewayStatus40	OBJECT-TYPE
        SYNTAX    DisplayString (SIZE (0..14))
        ACCESS    read-only
        STATUS    mandatory
        DESCRIPTION
            "See DESCRIPTION of g3stamediaGatewayStatus33."
        ::= { g3stamedia 52 }

    g3stamediaGatewayStatus41	OBJECT-TYPE
        SYNTAX    DisplayString (SIZE (0..14))
        ACCESS    read-only
        STATUS    mandatory
        DESCRIPTION
            "An object containing the status of the sixth set of eight media
            gateways, including the number of major alarms, minor alarms,
            warnings, and the H.248 link status for each specific media gateway
            number."
        ::= { g3stamedia 53 }

    g3stamediaGatewayStatus42	OBJECT-TYPE
        SYNTAX    DisplayString (SIZE (0..14))
        ACCESS    read-only
        STATUS    mandatory
        DESCRIPTION
            "See DESCRIPTION of g3stamediaGatewayStatus41."
        ::= { g3stamedia 54 }

    g3stamediaGatewayStatus43	OBJECT-TYPE
        SYNTAX    DisplayString (SIZE (0..14))
        ACCESS    read-only
        STATUS    mandatory
        DESCRIPTION
            "See DESCRIPTION of g3stamediaGatewayStatus41."
        ::= { g3stamedia 55 }

    g3stamediaGatewayStatus44	OBJECT-TYPE
        SYNTAX    DisplayString (SIZE (0..14))
        ACCESS    read-only
        STATUS    mandatory
        DESCRIPTION
            "See DESCRIPTION of g3stamediaGatewayStatus41."
        ::= { g3stamedia 56 }

    g3stamediaGatewayStatus45	OBJECT-TYPE
        SYNTAX    DisplayString (SIZE (0..14))
        ACCESS    read-only
        STATUS    mandatory
        DESCRIPTION
            "See DESCRIPTION of g3stamediaGatewayStatus41."
        ::= { g3stamedia 57 }

    g3stamediaGatewayStatus46	OBJECT-TYPE
        SYNTAX    DisplayString (SIZE (0..14))
        ACCESS    read-only
        STATUS    mandatory
        DESCRIPTION
            "See DESCRIPTION of g3stamediaGatewayStatus41."
        ::= { g3stamedia 58 }

    g3stamediaGatewayStatus47	OBJECT-TYPE
        SYNTAX    DisplayString (SIZE (0..14))
        ACCESS    read-only
        STATUS    mandatory
        DESCRIPTION
            "See DESCRIPTION of g3stamediaGatewayStatus41."
        ::= { g3stamedia 59 }

    g3stamediaGatewayStatus48	OBJECT-TYPE
        SYNTAX    DisplayString (SIZE (0..14))
        ACCESS    read-only
        STATUS    mandatory
        DESCRIPTION
            "See DESCRIPTION of g3stamediaGatewayStatus41."
        ::= { g3stamedia 60 }

    g3stamediaGatewayStatus49	OBJECT-TYPE
        SYNTAX    DisplayString (SIZE (0..14))
        ACCESS    read-only
        STATUS    mandatory
        DESCRIPTION
            "An object containing the status of the seventh set of eight media
            gateways, including the number of major alarms, minor alarms,
            warnings, and the H.248 link status for each specific media gateway
            number."
        ::= { g3stamedia 61 }

    g3stamediaGatewayStatus50	OBJECT-TYPE
        SYNTAX    DisplayString (SIZE (0..14))
        ACCESS    read-only
        STATUS    mandatory
        DESCRIPTION
            "See DESCRIPTION of g3stamediaGatewayStatus49."
        ::= { g3stamedia 62 }

    g3stamediaGatewayStatus51	OBJECT-TYPE
        SYNTAX    DisplayString (SIZE (0..14))
        ACCESS    read-only
        STATUS    mandatory
        DESCRIPTION
            "See DESCRIPTION of g3stamediaGatewayStatus49."
        ::= { g3stamedia 63 }

    g3stamediaGatewayStatus52	OBJECT-TYPE
        SYNTAX    DisplayString (SIZE (0..14))
        ACCESS    read-only
        STATUS    mandatory
        DESCRIPTION
            "See DESCRIPTION of g3stamediaGatewayStatus49."
        ::= { g3stamedia 64 }

    g3stamediaGatewayStatus53	OBJECT-TYPE
        SYNTAX    DisplayString (SIZE (0..14))
        ACCESS    read-only
        STATUS    mandatory
        DESCRIPTION
            "See DESCRIPTION of g3stamediaGatewayStatus49."
        ::= { g3stamedia 65 }

    g3stamediaGatewayStatus54	OBJECT-TYPE
        SYNTAX    DisplayString (SIZE (0..14))
        ACCESS    read-only
        STATUS    mandatory
        DESCRIPTION
            "See DESCRIPTION of g3stamediaGatewayStatus49."
        ::= { g3stamedia 66 }

    g3stamediaGatewayStatus55	OBJECT-TYPE
        SYNTAX    DisplayString (SIZE (0..14))
        ACCESS    read-only
        STATUS    mandatory
        DESCRIPTION
            "See DESCRIPTION of g3stamediaGatewayStatus49."
        ::= { g3stamedia 67 }

    g3stamediaGatewayStatus56	OBJECT-TYPE
        SYNTAX    DisplayString (SIZE (0..14))
        ACCESS    read-only
        STATUS    mandatory
        DESCRIPTION
            "See DESCRIPTION of g3stamediaGatewayStatus49."
        ::= { g3stamedia 68 }

    g3stamediaGatewayStatus57	OBJECT-TYPE
        SYNTAX    DisplayString (SIZE (0..14))
        ACCESS    read-only
        STATUS    mandatory
        DESCRIPTION
            "An object containing the status of the eighth set of eight media
            gateways, including the number of major alarms, minor alarms,
            warnings, and the H.248 link status for each specific media gateway
            number."
        ::= { g3stamedia 69 }

    g3stamediaGatewayStatus58	OBJECT-TYPE
        SYNTAX    DisplayString (SIZE (0..14))
        ACCESS    read-only
        STATUS    mandatory
        DESCRIPTION
            "See DESCRIPTION of g3stamediaGatewayStatus57."
        ::= { g3stamedia 70 }

    g3stamediaGatewayStatus59	OBJECT-TYPE
        SYNTAX    DisplayString (SIZE (0..14))
        ACCESS    read-only
        STATUS    mandatory
        DESCRIPTION
            "See DESCRIPTION of g3stamediaGatewayStatus57."
        ::= { g3stamedia 71 }

    g3stamediaGatewayStatus60	OBJECT-TYPE
        SYNTAX    DisplayString (SIZE (0..14))
        ACCESS    read-only
        STATUS    mandatory
        DESCRIPTION
            "See DESCRIPTION of g3stamediaGatewayStatus57."
        ::= { g3stamedia 72 }

    g3stamediaGatewayStatus61	OBJECT-TYPE
        SYNTAX    DisplayString (SIZE (0..14))
        ACCESS    read-only
        STATUS    mandatory
        DESCRIPTION
            "See DESCRIPTION of g3stamediaGatewayStatus57."
        ::= { g3stamedia 73 }

    g3stamediaGatewayStatus62	OBJECT-TYPE
        SYNTAX    DisplayString (SIZE (0..14))
        ACCESS    read-only
        STATUS    mandatory
        DESCRIPTION
            "See DESCRIPTION of g3stamediaGatewayStatus57."
        ::= { g3stamedia 74 }

    g3stamediaGatewayStatus63	OBJECT-TYPE
        SYNTAX    DisplayString (SIZE (0..14))
        ACCESS    read-only
        STATUS    mandatory
        DESCRIPTION
            "See DESCRIPTION of g3stamediaGatewayStatus57."
        ::= { g3stamedia 75 }

    g3stamediaGatewayStatus64	OBJECT-TYPE
        SYNTAX    DisplayString (SIZE (0..14))
        ACCESS    read-only
        STATUS    mandatory
        DESCRIPTION
            "See DESCRIPTION of g3stamediaGatewayStatus57."
        ::= { g3stamedia 76 }

    g3stamediaGatewayStatus65	OBJECT-TYPE
        SYNTAX    DisplayString (SIZE (0..14))
        ACCESS    read-only
        STATUS    mandatory
        DESCRIPTION
            "An object containing the status of the ninth set of eight media
            gateways, including the number of major alarms, minor alarms,
            warnings, and the H.248 link status for each specific media gateway
            number."
        ::= { g3stamedia 77 }

    g3stamediaGatewayStatus66	OBJECT-TYPE
        SYNTAX    DisplayString (SIZE (0..14))
        ACCESS    read-only
        STATUS    mandatory
        DESCRIPTION
            "See DESCRIPTION of g3stamediaGatewayStatus65."
        ::= { g3stamedia 78 }

    g3stamediaGatewayStatus67	OBJECT-TYPE
        SYNTAX    DisplayString (SIZE (0..14))
        ACCESS    read-only
        STATUS    mandatory
        DESCRIPTION
            "See DESCRIPTION of g3stamediaGatewayStatus65."
        ::= { g3stamedia 79 }

    g3stamediaGatewayStatus68	OBJECT-TYPE
        SYNTAX    DisplayString (SIZE (0..14))
        ACCESS    read-only
        STATUS    mandatory
        DESCRIPTION
            "See DESCRIPTION of g3stamediaGatewayStatus65."
        ::= { g3stamedia 80 }

    g3stamediaGatewayStatus69	OBJECT-TYPE
        SYNTAX    DisplayString (SIZE (0..14))
        ACCESS    read-only
        STATUS    mandatory
        DESCRIPTION
            "See DESCRIPTION of g3stamediaGatewayStatus65."
        ::= { g3stamedia 81 }

    g3stamediaGatewayStatus70	OBJECT-TYPE
        SYNTAX    DisplayString (SIZE (0..14))
        ACCESS    read-only
        STATUS    mandatory
        DESCRIPTION
            "See DESCRIPTION of g3stamediaGatewayStatus65."
        ::= { g3stamedia 82 }

    g3stamediaGatewayStatus71	OBJECT-TYPE
        SYNTAX    DisplayString (SIZE (0..14))
        ACCESS    read-only
        STATUS    mandatory
        DESCRIPTION
            "See DESCRIPTION of g3stamediaGatewayStatus65."
        ::= { g3stamedia 83 }

    g3stamediaGatewayStatus72	OBJECT-TYPE
        SYNTAX    DisplayString (SIZE (0..14))
        ACCESS    read-only
        STATUS    mandatory
        DESCRIPTION
            "See DESCRIPTION of g3stamediaGatewayStatus65."
        ::= { g3stamedia 84 }

    g3stamediaGatewayStatus73	OBJECT-TYPE
        SYNTAX    DisplayString (SIZE (0..14))
        ACCESS    read-only
        STATUS    mandatory
        DESCRIPTION
            "An object containing the status of the tenth set of eight media
            gateways, including the number of major alarms, minor alarms,
            warnings, and the H.248 link status for each specific media gateway
            number."
        ::= { g3stamedia 85 }

    g3stamediaGatewayStatus74	OBJECT-TYPE
        SYNTAX    DisplayString (SIZE (0..14))
        ACCESS    read-only
        STATUS    mandatory
        DESCRIPTION
            "See DESCRIPTION of g3stamediaGatewayStatus73."
        ::= { g3stamedia 86 }

    g3stamediaGatewayStatus75	OBJECT-TYPE
        SYNTAX    DisplayString (SIZE (0..14))
        ACCESS    read-only
        STATUS    mandatory
        DESCRIPTION
            "See DESCRIPTION of g3stamediaGatewayStatus73."
        ::= { g3stamedia 87 }

    g3stamediaGatewayStatus76	OBJECT-TYPE
        SYNTAX    DisplayString (SIZE (0..14))
        ACCESS    read-only
        STATUS    mandatory
        DESCRIPTION
            "See DESCRIPTION of g3stamediaGatewayStatus73."
        ::= { g3stamedia 88 }

    g3stamediaGatewayStatus77	OBJECT-TYPE
        SYNTAX    DisplayString (SIZE (0..14))
        ACCESS    read-only
        STATUS    mandatory
        DESCRIPTION
            "See DESCRIPTION of g3stamediaGatewayStatus73."
        ::= { g3stamedia 89 }

    g3stamediaGatewayStatus78	OBJECT-TYPE
        SYNTAX    DisplayString (SIZE (0..14))
        ACCESS    read-only
        STATUS    mandatory
        DESCRIPTION
            "See DESCRIPTION of g3stamediaGatewayStatus73."
        ::= { g3stamedia 90 }

    g3stamediaGatewayStatus79	OBJECT-TYPE
        SYNTAX    DisplayString (SIZE (0..14))
        ACCESS    read-only
        STATUS    mandatory
        DESCRIPTION
            "See DESCRIPTION of g3stamediaGatewayStatus73."
        ::= { g3stamedia 91 }

    g3stamediaGatewayStatus80	OBJECT-TYPE
        SYNTAX    DisplayString (SIZE (0..14))
        ACCESS    read-only
        STATUS    mandatory
        DESCRIPTION
            "See DESCRIPTION of g3stamediaGatewayStatus73."
        ::= { g3stamedia 92 }


    -- the g3stamgann group

    g3stamgannTage	OBJECT-TYPE
        SYNTAX    INTEGER
        ACCESS    read-only
        STATUS    mandatory
        DESCRIPTION
            "The number of timeticks since the mg-announcment data was last
            extracted from the switch by the G3 Proxy Agent. This object
            along with the g3stamgannintvl object allows the Network Manager
            to determine the validity of the mg-announcement data in the
            cache and to control when the proxy agent extracts the
            mg-announcement data from the switch."
        ::= { g3stamgann 1 }

    g3stamgannTintvl	OBJECT-TYPE
        SYNTAX    INTEGER
        ACCESS    read-write
        STATUS    mandatory
        DESCRIPTION
            "An object containing the interval for which the mg-announcement data
            extracted from the switch is considered valid by the proxy agent.
            When a GET or GET-NEXT request for mg-announcement objects is
            received by the agent it uses the g3stamgannage and g3stamgannintvl
            objects to determine whether it should refresh the cached
            stamgannTable.  If g3stamgannstmp + g3stamgannintvl is less than the
            current value of the sysUpTime object then the agent refreshes
            the stamgannTable cache.  In either case it responds to the requests
            it receives with the data it currently has in the cache."
        ::= { g3stamgann 2 }

    g3stamgannTdelay	OBJECT-TYPE
        SYNTAX    INTEGER
        ACCESS    read-only
        STATUS    mandatory
        DESCRIPTION
            "An object containing the delay encountered in updating
            the cached data"
        ::= { g3stamgann 3 }

    g3stamgannTretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3stamgann 4 }

    g3stamgannTcount	OBJECT-TYPE
        SYNTAX    Gauge
        ACCESS    read-only
        STATUS    mandatory
        DESCRIPTION
            "A Gauge object containing the number of data records in the cache."
        ::= { g3stamgann 5 }

    g3stamgannTable	OBJECT-TYPE
        SYNTAX    SEQUENCE OF G3stamgannEntry
        ACCESS    not-accessible
        STATUS    mandatory
        DESCRIPTION
            "A list of g3stamgann entries."
        ::= { g3stamgann 6 }

    g3stamgannEntry	OBJECT-TYPE
        SYNTAX    G3stamgannEntry
        ACCESS    not-accessible
        STATUS    mandatory
        DESCRIPTION
            "A g3stamgann entry containing objects of the
            g3stamgann information sent by the switch."
        INDEX    { g3stamgannGatewayNbr }
        ::= { g3stamgannTable 1 }

    G3stamgannEntry ::= SEQUENCE {
        g3stamgannGatewayNbr
            INTEGER,
        g3stamgannAnnActive
            DisplayString
        }

    g3stamgannGatewayNbr	OBJECT-TYPE
        SYNTAX    INTEGER
        ACCESS    read-only
        STATUS    mandatory
        DESCRIPTION
            "An object containing the media gateway number of a G700 media gateway
            that has the virtual VAL board administered in the V9 slot."
        ::= { g3stamgannEntry 1 }

    g3stamgannAnnActive	OBJECT-TYPE
        SYNTAX    DisplayString (SIZE (0..1))
        ACCESS    read-only
        STATUS    mandatory
        DESCRIPTION
            "An object containing the status of the administered virtual VAL board
            functionality in the Auser maintenance table. The status is active,
            either yes or no."
        ::= { g3stamgannEntry 2 }


    -- the g3ipserver group

    g3ipserverTage	OBJECT-TYPE
        SYNTAX    INTEGER
        ACCESS    read-only
        STATUS    mandatory
        DESCRIPTION
            "The number of timeticks since the data was last
            extracted from the switch by the Proxy Agent.  This object
            along with the g3gatewayTintvl object allows the Network Manager
            to determine the validity of the data in the cache and to control
            when the Proxy Agent extracts the data from the switch."
        ::= { g3ipserver 1 }

    g3ipserverTintvl	OBJECT-TYPE
        SYNTAX    INTEGER
        ACCESS    read-write
        STATUS    mandatory
        DESCRIPTION
            "An object containing the interval for which the
            data extracted from the switch is considered valid by the
            Proxy Agent.  When a GET or GET-NEXT request for these data
            objects is received by the agent it uses the g3gatewayTage
            and g3gatewayTintvl objects to determine whether it should refresh
            the cached gatewayTable.  If g3gatewayTstmp +
            g3gatewayTintvl is less than the current value of the sysUpTime
            object then the agent refreshes the gatewayTable cache.  In
            either case it responds to the requests it receives with the data
            it currently has in the cache."
        ::= { g3ipserver 2 }

    g3ipserverTdelay	OBJECT-TYPE
        SYNTAX    INTEGER
        ACCESS    read-only
        STATUS    mandatory
        DESCRIPTION
            "An object containing the delay encountered in updating
            the cached data."
        ::= { g3ipserver 3 }

    g3ipserverTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3ipserver 4 }

    g3ipserverTcount	OBJECT-TYPE
        SYNTAX    Gauge
        ACCESS    read-only
        STATUS    mandatory
        DESCRIPTION
            "A Gauge object containing the number of data records in the cache."
        ::= { g3ipserver 5 }

    g3ipserverTable	OBJECT-TYPE
        SYNTAX    SEQUENCE OF G3ipserverEntry
        ACCESS    not-accessible
        STATUS    mandatory
        DESCRIPTION
            "A list of g3ipserver entries."
        ::= { g3ipserver 6 }

    g3ipserverEntry	OBJECT-TYPE
        SYNTAX    G3ipserverEntry
        ACCESS    not-accessible
        STATUS    mandatory
        DESCRIPTION
            "A g3ipserver entry containing objects of the
            g3ipserver information sent by the switch."
        INDEX    { g3ipserverPortNetwork }
        ::= { g3ipserverTable 1 }

    G3ipserverEntry ::= SEQUENCE {
        g3ipserverPortNetwork
            INTEGER,
        g3ipserverSocketEncr
            DisplayString,
        g3ipserverSecServer
            DisplayString,
        g3ipserverPrimLocation
            DisplayString,
        g3ipserverPrimHost
            DisplayString,
        g3ipserverPrimDHCPID
            DisplayString,
        g3ipserverPrimIP1
            DisplayString,
        g3ipserverPrimIP2
            DisplayString,
        g3ipserverPrimIP3
            DisplayString,
        g3ipserverPrimIP4
            DisplayString,
        g3ipserverPrimIPPort
            DisplayString,
        g3ipserverPrimServState
            DisplayString,
        g3ipserverPrimCntlState
            DisplayString,
        g3ipserverPrimStHealth
            DisplayString,
        g3ipserverSecLocation
            DisplayString,
        g3ipserverSecHost
            DisplayString,
        g3ipserverSecDHCPID
            DisplayString,
        g3ipserverSecIP1
            DisplayString,
        g3ipserverSecIP2
            DisplayString,
        g3ipserverSecIP3
            DisplayString,
        g3ipserverSecIP4
            DisplayString,
        g3ipserverSecIPPort
            DisplayString,
        g3ipserverSecServState
            DisplayString,
        g3ipserverSecCntlState
            DisplayString,
        g3ipserverSecStHealth
            DisplayString,
        g3ipserverCallCntl802
            DisplayString,
        g3ipserverCallCntlDiff
            DisplayString
        }

    g3ipserverPortNetwork	OBJECT-TYPE
        SYNTAX    INTEGER
        ACCESS    read-only
        STATUS    mandatory
        DESCRIPTION
            "An object containing the port network number where the ipserver
            interfaces are inserted"
        ::= { g3ipserverEntry 1 }

    g3ipserverSocketEncr	OBJECT-TYPE
        SYNTAX    DisplayString (SIZE (0..1))
        ACCESS    read-only
        STATUS    mandatory
        DESCRIPTION
            "An object containing the state of socket encryption for the Server
            Interface Module (SIM) interface between the server and the IPSI
            board. Values are y(es) and n(o) for enabling/disabling socket
            encryption. This is now an obsolete field."
        ::= { g3ipserverEntry 2 }

    g3ipserverSecServer	OBJECT-TYPE
        SYNTAX    DisplayString (SIZE (0..1))
        ACCESS    read-only
        STATUS    mandatory
        DESCRIPTION
            "An object containing an indicator as to whether or not a duplicated
            (secondary) ipserver interface (IPSI) board is administered within a
            port network. This is now an obsolete field."
        ::= { g3ipserverEntry 3 }

    g3ipserverPrimLocation	OBJECT-TYPE
        SYNTAX    DisplayString (SIZE (0..6))
        ACCESS    read-only
        STATUS    mandatory
        DESCRIPTION
            "An object containing the IPSI A Board Location."
        ::= { g3ipserverEntry 4 }

    g3ipserverPrimHost	OBJECT-TYPE
        SYNTAX    DisplayString (SIZE (0..16))
        ACCESS    read-only
        STATUS    mandatory
        DESCRIPTION
            "An object containing the IPSI A host name. This field is now
            obsolete."
        ::= { g3ipserverEntry 5 }

    g3ipserverPrimDHCPID	OBJECT-TYPE
        SYNTAX    DisplayString (SIZE (0..9))
        ACCESS    read-only
        STATUS    mandatory
        DESCRIPTION
            "An object containing the IPSI A DHCP ID."
        ::= { g3ipserverEntry 6 }

    g3ipserverPrimIP1	OBJECT-TYPE
        SYNTAX    DisplayString (SIZE (0..40))
        ACCESS    read-only
        STATUS    mandatory
        DESCRIPTION
            "An object containing the IPSI A IP address - segment 1."
        ::= { g3ipserverEntry 7 }

    g3ipserverPrimIP2	OBJECT-TYPE
        SYNTAX    DisplayString (SIZE (0..3))
        ACCESS    read-only
        STATUS    mandatory
        DESCRIPTION
            "An object containing the IPSI A IP address - segment 2."
        ::= { g3ipserverEntry 8 }

    g3ipserverPrimIP3	OBJECT-TYPE
        SYNTAX    DisplayString (SIZE (0..3))
        ACCESS    read-only
        STATUS    mandatory
        DESCRIPTION
            "An object containing the IPSI A IP address - segment 3."
        ::= { g3ipserverEntry 9 }

    g3ipserverPrimIP4	OBJECT-TYPE
        SYNTAX    DisplayString (SIZE (0..3))
        ACCESS    read-only
        STATUS    mandatory
        DESCRIPTION
            "An object containing the IPSI A IP address - segment 4."
        ::= { g3ipserverEntry 10 }

    g3ipserverPrimIPPort	OBJECT-TYPE
        SYNTAX    DisplayString (SIZE (0..5))
        ACCESS    read-only
        STATUS    mandatory
        DESCRIPTION
            "An object containing the IPSI A IP port number. This is now an
            obsolete field."
        ::= { g3ipserverEntry 11 }

    g3ipserverPrimServState	OBJECT-TYPE
        SYNTAX    DisplayString (SIZE (0..3))
        ACCESS    read-only
        STATUS    mandatory
        DESCRIPTION
            "An object containing the IPSI A Service State."
        ::= { g3ipserverEntry 12 }

    g3ipserverPrimCntlState	OBJECT-TYPE
        SYNTAX    DisplayString (SIZE (0..7))
        ACCESS    read-only
        STATUS    mandatory
        DESCRIPTION
            "An object containing the IPSI A Control State."
        ::= { g3ipserverEntry 13 }

    g3ipserverPrimStHealth	OBJECT-TYPE
        SYNTAX    DisplayString (SIZE (0..7))
        ACCESS    read-only
        STATUS    mandatory
        DESCRIPTION
            "An object containing the IPSI A State Of Health."
        ::= { g3ipserverEntry 14 }

    g3ipserverSecLocation	OBJECT-TYPE
        SYNTAX    DisplayString (SIZE (0..6))
        ACCESS    read-only
        STATUS    mandatory
        DESCRIPTION
            "An object containing the IPSI B Board Location."
        ::= { g3ipserverEntry 15 }

    g3ipserverSecHost	OBJECT-TYPE
        SYNTAX    DisplayString (SIZE (0..16))
        ACCESS    read-only
        STATUS    mandatory
        DESCRIPTION
            "An object containing the IPSI B Host Name."
        ::= { g3ipserverEntry 16 }

    g3ipserverSecDHCPID	OBJECT-TYPE
        SYNTAX    DisplayString (SIZE (0..9))
        ACCESS    read-only
        STATUS    mandatory
        DESCRIPTION
            "An object containing the IPSI B DCHP ID."
        ::= { g3ipserverEntry 17 }

    g3ipserverSecIP1	OBJECT-TYPE
        SYNTAX    DisplayString (SIZE (0..40))
        ACCESS    read-only
        STATUS    mandatory
        DESCRIPTION
            "An object containing the IPSI B IP Address - segment 1."
        ::= { g3ipserverEntry 18 }

    g3ipserverSecIP2	OBJECT-TYPE
        SYNTAX    DisplayString (SIZE (0..3))
        ACCESS    read-only
        STATUS    mandatory
        DESCRIPTION
            "An object containing the IPSI B IP Address - segment 2."
        ::= { g3ipserverEntry 19 }

    g3ipserverSecIP3	OBJECT-TYPE
        SYNTAX    DisplayString (SIZE (0..3))
        ACCESS    read-only
        STATUS    mandatory
        DESCRIPTION
            "An object containing the IPSI B IP Address - segment 3."
        ::= { g3ipserverEntry 20 }

    g3ipserverSecIP4	OBJECT-TYPE
        SYNTAX    DisplayString (SIZE (0..3))
        ACCESS    read-only
        STATUS    mandatory
        DESCRIPTION
            "An object containing the IPSI B IP Address - segment 4 ."
        ::= { g3ipserverEntry 21 }

    g3ipserverSecIPPort	OBJECT-TYPE
        SYNTAX    DisplayString (SIZE (0..5))
        ACCESS    read-only
        STATUS    mandatory
        DESCRIPTION
            "An object containing the IPSI B IP port number. This field is
            now obsolete."
        ::= { g3ipserverEntry 22 }

    g3ipserverSecServState	OBJECT-TYPE
        SYNTAX    DisplayString (SIZE (0..3))
        ACCESS    read-only
        STATUS    mandatory
        DESCRIPTION
            "An object containing the IPSI B Service State"
        ::= { g3ipserverEntry 23 }

    g3ipserverSecCntlState	OBJECT-TYPE
        SYNTAX    DisplayString (SIZE (0..7))
        ACCESS    read-only
        STATUS    mandatory
        DESCRIPTION
            "An object containing the IPSI B Control State."
        ::= { g3ipserverEntry 24 }

    g3ipserverSecStHealth	OBJECT-TYPE
        SYNTAX    DisplayString (SIZE (0..7))
        ACCESS    read-only
        STATUS    mandatory
        DESCRIPTION
            "An object containing the IPSI B State Of Health."
        ::= { g3ipserverEntry 25 }

    g3ipserverCallCntl802	OBJECT-TYPE
        SYNTAX    DisplayString (SIZE (0..1))
        ACCESS    read-only
        STATUS    mandatory
        DESCRIPTION
            "An object containing the call control (signaling) 802.1p value for the
            IPSI board. Default is 6, with a range of 0 to 7. This field is now
            obsolete."
        ::= { g3ipserverEntry 26 }

    g3ipserverCallCntlDiff	OBJECT-TYPE
        SYNTAX    DisplayString (SIZE (0..2))
        ACCESS    read-only
        STATUS    mandatory
        DESCRIPTION
            "An object containing the call control (signaling) DiffServ value for
            the IPSI board. Default is 40, with a range of 0 to 63. This field
            is now obsolete."
        ::= { g3ipserverEntry 27 }


    -- the g3regipstat group

    g3regipstatTage	OBJECT-TYPE
        SYNTAX    INTEGER
        ACCESS    read-only
        STATUS    mandatory
        DESCRIPTION
            "The number of timeticks since the registered ip stations data was last
            extracted from the switch by the Proxy Agent.  This object
            along with the g3regipstatintvl object allows the Network Manager
            to determine the validity of the registered ip stations data in the cache 
            and to control	when the Proxy Agent extracts the data from the switch."
        ::= { g3regipstat 1 }

    g3regipstatTintvl	OBJECT-TYPE
        SYNTAX    INTEGER
        ACCESS    read-write
        STATUS    mandatory
        DESCRIPTION
            "An object containing the interval for which the
            data extracted from the switch is considered valid by the
            Proxy Agent.  When a GET or GET-NEXT request for these registered ip 
            stations data	objects is received by the agent it uses the 
            g3regipstatage	and g3regipstatintvl objects to determine whether it 
            should refresh	the cached regipstatTable.  If g3regipstatstmp +
            g3regipstatintvl is less than the current value of the sysUpTime
            object then the agent refreshes the regipstatTable cache.  In
            either case it responds to the requests it receives with the data
            it currently has in the cache."
        ::= { g3regipstat 2 }

    g3regipstatTdelay	OBJECT-TYPE
        SYNTAX    INTEGER
        ACCESS    read-only
        STATUS    mandatory
        DESCRIPTION
            "An object containing the delay encountered in updating
            the cached data."
        ::= { g3regipstat 3 }

    g3regipstatTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3regipstat 4 }

    g3regipstatTcount	OBJECT-TYPE
        SYNTAX    Gauge
        ACCESS    read-only
        STATUS    mandatory
        DESCRIPTION
            "A Gauge object containing the number of data records in the cache."
        ::= { g3regipstat 5 }

    g3regipstatTable	OBJECT-TYPE
        SYNTAX    SEQUENCE OF G3regipstatEntry
        ACCESS    not-accessible
        STATUS    mandatory
        DESCRIPTION
            "A list of g3regipstat entries."
        ::= { g3regipstat 6 }

    g3regipstatEntry	OBJECT-TYPE
        SYNTAX    G3regipstatEntry
        ACCESS    not-accessible
        STATUS    mandatory
        DESCRIPTION
            "A g3regipstat entry containing objects of the
            g3regipstat information sent by the switch."
        INDEX    { g3regipstatExtension }
        ::= { g3regipstatTable 1 }

    G3regipstatEntry ::= SEQUENCE {
        g3regipstatExtension
            DisplayString
        }

    g3regipstatExtension	OBJECT-TYPE
        SYNTAX    DisplayString (SIZE (0..15))
        ACCESS    read-only
        STATUS    mandatory
        DESCRIPTION
            "An object containing the registered IP station extension. This
            MIB group is currently disabled in providing this data due to
            performance problems in running the associated CM SAT command."
        ::= { g3regipstatEntry 1 }


    -- the g3callratedata group

    g3callratedataTage	OBJECT-TYPE
        SYNTAX    INTEGER
        ACCESS    read-only
        STATUS    mandatory
        DESCRIPTION
            "The number of timeticks since the call rate data was last extracted 
            from the switch by the Proxy Agent.  This object along with the 
            g3callratedataTintvl object allows the Network Manager to determine 
            the validity of the call rate data in the cache and to control when 
            the Proxy Agent extracts the data from the switch."
        ::= { g3callratedata 1 }

    g3callratedataTintvl	OBJECT-TYPE
        SYNTAX    INTEGER
        ACCESS    read-write
        STATUS    mandatory
        DESCRIPTION
            "An object containing the interval for which the data extracted from the
            switch is considered valid by the Proxy Agent.  When a GET or GET-NEXT
            request for these call rate data objects is received by the agent it uses
            the g3callratedataTage	and g3callratedataTintvl objects to determine whether
            it should refresh the cached callratedataTable.  If g3callratedataTstmp +
            g3callratedataTintvl is less than the current value of the sysUpTime
            object then the agent refreshes the callratedataTable cache.In either case it 
            responds to the requests it receives with the data it currently has in the cache."
        ::= { g3callratedata 2 }

    g3callratedataTdelay	OBJECT-TYPE
        SYNTAX    INTEGER
        ACCESS    read-only
        STATUS    mandatory
        DESCRIPTION
            "An object containing the delay encountered in updating
            the cached data."
        ::= { g3callratedata 3 }

    g3callratedataTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3callratedata 4 }

    g3callratedataRunYear	OBJECT-TYPE
        SYNTAX    INTEGER
        ACCESS    read-only
        STATUS    mandatory
        DESCRIPTION
            "An object containing the Year the command was executed"
        ::= { g3callratedata 5 }

    g3callratedataRunMonth	OBJECT-TYPE
        SYNTAX    INTEGER
        ACCESS    read-only
        STATUS    mandatory
        DESCRIPTION
            "An object containing the Month the command was executed"
        ::= { g3callratedata 6 }

    g3callratedataRunDay	OBJECT-TYPE
        SYNTAX    INTEGER
        ACCESS    read-only
        STATUS    mandatory
        DESCRIPTION
            "An object containing the Day the command was executed"
        ::= { g3callratedata 7 }

    g3callratedataRunHour	OBJECT-TYPE
        SYNTAX    INTEGER
        ACCESS    read-only
        STATUS    mandatory
        DESCRIPTION
            "An object containing the Hour the command was executed"
        ::= { g3callratedata 8 }

    g3callratedataMeasHour	OBJECT-TYPE
        SYNTAX    DisplayString (SIZE (0..4))
        ACCESS    read-only
        STATUS    mandatory
        DESCRIPTION
            "An object containing the starting time (using 24-hour clock)
            of the hour during which the data was recorded"
        ::= { g3callratedata 9 }

    g3callratedataNumCalls	OBJECT-TYPE
        SYNTAX    DisplayString (SIZE (0..6))
        ACCESS    read-only
        STATUS    mandatory
        DESCRIPTION
            "The number of calls completed,or answered (including incoming,
            outgoing, and intercom),during the listed hour. "
        ::= { g3callratedata 10 }

    g3callratedataBsyIntHr	OBJECT-TYPE
        SYNTAX    DisplayString (SIZE (0..2))
        ACCESS    read-only
        STATUS    mandatory
        DESCRIPTION
            "An object containing"
        ::= { g3callratedata 11 }

    g3callratedataBsyIntMn	OBJECT-TYPE
        SYNTAX    DisplayString (SIZE (0..2))
        ACCESS    read-only
        STATUS    mandatory
        DESCRIPTION
            "An object containing"
        ::= { g3callratedata 12 }

    g3callratedataBsyIntSc	OBJECT-TYPE
        SYNTAX    DisplayString (SIZE (0..2))
        ACCESS    read-only
        STATUS    mandatory
        DESCRIPTION
            "An object containing"
        ::= { g3callratedata 13 }

    g3callratedataBsyCalCmpl	OBJECT-TYPE
        SYNTAX    DisplayString (SIZE (0..4))
        ACCESS    read-only
        STATUS    mandatory
        DESCRIPTION
            "An object containing the total number of calls completed in the listed busy interval."
        ::= { g3callratedata 14 }

    g3callratedataMeasHour2	OBJECT-TYPE
        SYNTAX    DisplayString (SIZE (0..4))
        ACCESS    read-only
        STATUS    mandatory
        DESCRIPTION
            "An object containing the starting time (using 24-hour clock) of the hour during 
            which the data was recorded."
        ::= { g3callratedata 15 }

    g3callratedataNumCallsToday	OBJECT-TYPE
        SYNTAX    DisplayString (SIZE (0..6))
        ACCESS    read-only
        STATUS    mandatory
        DESCRIPTION
            "The number of calls completed,or answered (including incoming,
            outgoing, and intercom),during the listed hour"
        ::= { g3callratedata 16 }

    g3callratedataBsyIntHrToday	OBJECT-TYPE
        SYNTAX    DisplayString (SIZE (0..2))
        ACCESS    read-only
        STATUS    mandatory
        DESCRIPTION
            "An object containing  today's busiest hour.This is the hour with the
            largest number of completed calls"
        ::= { g3callratedata 17 }

    g3callratedataBsyIntMnToday	OBJECT-TYPE
        SYNTAX    DisplayString (SIZE (0..2))
        ACCESS    read-only
        STATUS    mandatory
        DESCRIPTION
            "An object containing the minute field of today's busiest hour"
        ::= { g3callratedata 18 }

    g3callratedataBsyIntScToday	OBJECT-TYPE
        SYNTAX    DisplayString (SIZE (0..2))
        ACCESS    read-only
        STATUS    mandatory
        DESCRIPTION
            "An object containing the second field of today's busiest hour"
        ::= { g3callratedata 19 }

    g3callratedataBsyCalCmplToday	OBJECT-TYPE
        SYNTAX    DisplayString (SIZE (0..4))
        ACCESS    read-only
        STATUS    mandatory
        DESCRIPTION
            "An object containing the total number of calls completed in the listed busy interval"
        ::= { g3callratedata 20 }

    g3callratedataMeasHour3	OBJECT-TYPE
        SYNTAX    DisplayString (SIZE (0..4))
        ACCESS    read-only
        STATUS    mandatory
        DESCRIPTION
            "An object containing the starting time (using 24-hour clock) of the hour during
            which the data was recorded"
        ::= { g3callratedata 21 }

    g3callratedataNumCallsToday1	OBJECT-TYPE
        SYNTAX    DisplayString (SIZE (0..6))
        ACCESS    read-only
        STATUS    mandatory
        DESCRIPTION
            "The number of calls completed,or answered (including incoming,
            outgoing, and intercom),during the listed hour"
        ::= { g3callratedata 22 }

    g3callratedataBsyIntTodayHr	OBJECT-TYPE
        SYNTAX    DisplayString (SIZE (0..2))
        ACCESS    read-only
        STATUS    mandatory
        DESCRIPTION
            "An object containing the hour field of the hour with the busiest 36-second interval for today"
        ::= { g3callratedata 23 }

    g3callratedataBsyIntTodayMn	OBJECT-TYPE
        SYNTAX    DisplayString (SIZE (0..2))
        ACCESS    read-only
        STATUS    mandatory
        DESCRIPTION
            "An object containing the minute field of the hour with the busiest 36-second interval for today"
        ::= { g3callratedata 24 }

    g3callratedataBsyIntTodaySc	OBJECT-TYPE
        SYNTAX    DisplayString (SIZE (0..2))
        ACCESS    read-only
        STATUS    mandatory
        DESCRIPTION
            "An object containing the second field of the hour with the busiest 36-second interval for today"
        ::= { g3callratedata 25 }

    g3callratedataBsyCalCmplToday2	OBJECT-TYPE
        SYNTAX    DisplayString (SIZE (0..4))
        ACCESS    read-only
        STATUS    mandatory
        DESCRIPTION
            "An object containing the total number of calls completed in the listed busy interval"
        ::= { g3callratedata 26 }

    g3callratedataMeasHour4	OBJECT-TYPE
        SYNTAX    DisplayString (SIZE (0..4))
        ACCESS    read-only
        STATUS    mandatory
        DESCRIPTION
            "An object containing the starting time (using 24-hour clock)of the hour during 
            which the data was recorded"
        ::= { g3callratedata 27 }

    g3callratedataNumCallsToday3	OBJECT-TYPE
        SYNTAX    DisplayString (SIZE (0..6))
        ACCESS    read-only
        STATUS    mandatory
        DESCRIPTION
            "The number of calls completed,or answered (including incoming,
            outgoing, and intercom),during the listed hour"
        ::= { g3callratedata 28 }

    g3callratedataBsyIntHrYesterday	OBJECT-TYPE
        SYNTAX    DisplayString (SIZE (0..2))
        ACCESS    read-only
        STATUS    mandatory
        DESCRIPTION
            "An object containing  yesterday's busiest hour.This is the hour with the
            largest number of completed calls"
        ::= { g3callratedata 29 }

    g3callratedataBsyIntMnYesterday	OBJECT-TYPE
        SYNTAX    DisplayString (SIZE (0..2))
        ACCESS    read-only
        STATUS    mandatory
        DESCRIPTION
            "An object containing the minute field of yesterday's busiest hour"
        ::= { g3callratedata 30 }

    g3callratedataBsyIntScYesterday	OBJECT-TYPE
        SYNTAX    DisplayString (SIZE (0..2))
        ACCESS    read-only
        STATUS    mandatory
        DESCRIPTION
            "An object containing the second field of yesterday's busiest hour"
        ::= { g3callratedata 31 }

    g3callratedataBsyCalCmplYesterday	OBJECT-TYPE
        SYNTAX    DisplayString (SIZE (0..4))
        ACCESS    read-only
        STATUS    mandatory
        DESCRIPTION
            "An object containing the total number of calls completed in the listed busy interval"
        ::= { g3callratedata 32 }

    g3callratedataMeasHour5	OBJECT-TYPE
        SYNTAX    DisplayString (SIZE (0..4))
        ACCESS    read-only
        STATUS    mandatory
        DESCRIPTION
            "An object containing the starting time (using 24-hour clock)of the hour during 
            which the data was recorded"
        ::= { g3callratedata 33 }

    g3callratedataNumCallsYesterday	OBJECT-TYPE
        SYNTAX    DisplayString (SIZE (0..6))
        ACCESS    read-only
        STATUS    mandatory
        DESCRIPTION
            "The number of calls completed,or answered (including incoming,
            outgoing, and intercom),during the listed hour"
        ::= { g3callratedata 34 }

    g3callratedataBsyIntHrYesterday2	OBJECT-TYPE
        SYNTAX    DisplayString (SIZE (0..2))
        ACCESS    read-only
        STATUS    mandatory
        DESCRIPTION
            "An object containing the hour field of the hour with the busiest 36-second interval for yesterday"
        ::= { g3callratedata 35 }

    g3callratedataBsyIntMnYesterday2	OBJECT-TYPE
        SYNTAX    DisplayString (SIZE (0..2))
        ACCESS    read-only
        STATUS    mandatory
        DESCRIPTION
            "An object containing the minute field of the hour with the busiest 36-second interval for yesterday"
        ::= { g3callratedata 36 }

    g3callratedataBsyIntScYesteday2	OBJECT-TYPE
        SYNTAX    DisplayString (SIZE (0..2))
        ACCESS    read-only
        STATUS    mandatory
        DESCRIPTION
            "An object containing the second field of the hour with the busiest 36-second interval for yesterday"
        ::= { g3callratedata 37 }

    g3callratedataBsyCalCmplYesterday2	OBJECT-TYPE
        SYNTAX    DisplayString (SIZE (0..4))
        ACCESS    read-only
        STATUS    mandatory
        DESCRIPTION
            "An object containing the total number of calls completed in the listed busy interval"
        ::= { g3callratedata 38 }


    -- the g3callratevoice group

    g3callratevoiceTage	OBJECT-TYPE
        SYNTAX    INTEGER
        ACCESS    read-only
        STATUS    mandatory
        DESCRIPTION
            "The number of timeticks since the call rate data was last
            extracted from the switch by the Proxy Agent.  This object
            along with the g3callratevoiceTintvl object allows the Network Manager
            to determine the validity of the call rate data in the cache 
            and to control when the Proxy Agent extracts the data from the switch."
        ::= { g3callratevoice 1 }

    g3callratevoiceTintvl	OBJECT-TYPE
        SYNTAX    INTEGER
        ACCESS    read-write
        STATUS    mandatory
        DESCRIPTION
            "An object containing the interval for which the data extracted from the
            switch is considered valid by the Proxy Agent.When a GET or GET-NEXT
            request for these call rate data objects is received by the agent it uses
            the g3callratevoiceTage	and g3callratevoiceTintvl objects to determine whether
            it should refresh the cached callratevoiceTable.  If g3callratevoiceTstmp + 
            g3callratevoiceTintvl is less than the current value of the sysUpTime object then
            the agent refreshes the callrayevoiceTable cache.In either case it responds to the
            requests it receives with the data it currently has in the cache."
        ::= { g3callratevoice 2 }

    g3callratevoiceTdelay	OBJECT-TYPE
        SYNTAX    INTEGER
        ACCESS    read-only
        STATUS    mandatory
        DESCRIPTION
            "An object containing the delay encountered in updating
            the cached data."
        ::= { g3callratevoice 3 }

    g3callratevoiceTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3callratevoice 4 }

    g3callratevoiceRunYear	OBJECT-TYPE
        SYNTAX    INTEGER
        ACCESS    read-only
        STATUS    mandatory
        DESCRIPTION
            "An object containing the Year the command was executed"
        ::= { g3callratevoice 5 }

    g3callratevoiceRunMonth	OBJECT-TYPE
        SYNTAX    INTEGER
        ACCESS    read-only
        STATUS    mandatory
        DESCRIPTION
            "An object containing the Month the command was executed"
        ::= { g3callratevoice 6 }

    g3callratevoiceRunDay	OBJECT-TYPE
        SYNTAX    INTEGER
        ACCESS    read-only
        STATUS    mandatory
        DESCRIPTION
            "An object containing the Day the command was executed"
        ::= { g3callratevoice 7 }

    g3callratevoiceRunHour	OBJECT-TYPE
        SYNTAX    INTEGER
        ACCESS    read-only
        STATUS    mandatory
        DESCRIPTION
            "An object containing the Hour the command was executed"
        ::= { g3callratevoice 8 }

    g3callratevoiceMeasHour	OBJECT-TYPE
        SYNTAX    DisplayString (SIZE (0..4))
        ACCESS    read-only
        STATUS    mandatory
        DESCRIPTION
            "An object containing the starting time (using 24-hour clock)
            of the hour during which the data was recorded"
        ::= { g3callratevoice 9 }

    g3callratevoiceNumCalls	OBJECT-TYPE
        SYNTAX    DisplayString (SIZE (0..6))
        ACCESS    read-only
        STATUS    mandatory
        DESCRIPTION
            "The number of calls completed,or answered (including incoming,
            outgoing, and intercom),during the listed hour. "
        ::= { g3callratevoice 10 }

    g3callratevoiceBsyIntHr	OBJECT-TYPE
        SYNTAX    DisplayString (SIZE (0..2))
        ACCESS    read-only
        STATUS    mandatory
        DESCRIPTION
            "An object containing"
        ::= { g3callratevoice 11 }

    g3callratevoiceBsyIntMn	OBJECT-TYPE
        SYNTAX    DisplayString (SIZE (0..2))
        ACCESS    read-only
        STATUS    mandatory
        DESCRIPTION
            "An object containing"
        ::= { g3callratevoice 12 }

    g3callratevoiceBsyIntSc	OBJECT-TYPE
        SYNTAX    DisplayString (SIZE (0..2))
        ACCESS    read-only
        STATUS    mandatory
        DESCRIPTION
            "An object containing"
        ::= { g3callratevoice 13 }

    g3callratevoiceBsyCalCmpl	OBJECT-TYPE
        SYNTAX    DisplayString (SIZE (0..4))
        ACCESS    read-only
        STATUS    mandatory
        DESCRIPTION
            "An object containing the total number of calls completed in the listed busy interval."
        ::= { g3callratevoice 14 }

    g3callratevoiceMeasHour2	OBJECT-TYPE
        SYNTAX    DisplayString (SIZE (0..4))
        ACCESS    read-only
        STATUS    mandatory
        DESCRIPTION
            "An object containing the starting time (using 24-hour clock)
            of the hour during which the data was recorded."
        ::= { g3callratevoice 15 }

    g3callratevoiceNumCallsToday	OBJECT-TYPE
        SYNTAX    DisplayString (SIZE (0..6))
        ACCESS    read-only
        STATUS    mandatory
        DESCRIPTION
            "The number of calls completed,or answered (including incoming,
            outgoing, and intercom),during the listed hour"
        ::= { g3callratevoice 16 }

    g3callratevoiceBsyIntHrToday	OBJECT-TYPE
        SYNTAX    DisplayString (SIZE (0..2))
        ACCESS    read-only
        STATUS    mandatory
        DESCRIPTION
            "An object containing  today's busiest hour.This is the hour with the
            largest number of completed calls"
        ::= { g3callratevoice 17 }

    g3callratevoiceBsyIntMnToday	OBJECT-TYPE
        SYNTAX    DisplayString (SIZE (0..2))
        ACCESS    read-only
        STATUS    mandatory
        DESCRIPTION
            "An object containing the minute field of today's busiest hour"
        ::= { g3callratevoice 18 }

    g3callratevoiceBsyIntScToday	OBJECT-TYPE
        SYNTAX    DisplayString (SIZE (0..2))
        ACCESS    read-only
        STATUS    mandatory
        DESCRIPTION
            "An object containing the second field of today's busiest hour"
        ::= { g3callratevoice 19 }

    g3callratevoiceBsyCalCmplToday	OBJECT-TYPE
        SYNTAX    DisplayString (SIZE (0..4))
        ACCESS    read-only
        STATUS    mandatory
        DESCRIPTION
            "An object containing the total number of calls completed in the listed busy interval"
        ::= { g3callratevoice 20 }

    g3callratevoiceMeasHour3	OBJECT-TYPE
        SYNTAX    DisplayString (SIZE (0..4))
        ACCESS    read-only
        STATUS    mandatory
        DESCRIPTION
            "An object containing the starting time (using 24-hour clock)
            of the hour during which the data was recorded"
        ::= { g3callratevoice 21 }

    g3callratevoiceNumCallsToday2	OBJECT-TYPE
        SYNTAX    DisplayString (SIZE (0..6))
        ACCESS    read-only
        STATUS    mandatory
        DESCRIPTION
            "The number of calls completed,or answered (including incoming,
            outgoing, and intercom),during the listed hour"
        ::= { g3callratevoice 22 }

    g3callratevoiceBsyIntHrToday2	OBJECT-TYPE
        SYNTAX    DisplayString (SIZE (0..2))
        ACCESS    read-only
        STATUS    mandatory
        DESCRIPTION
            "An object containing the hour field of the hour with the busiest 36-second interval for today"
        ::= { g3callratevoice 23 }

    g3callratevoiceBsyIntMnToday2	OBJECT-TYPE
        SYNTAX    DisplayString (SIZE (0..2))
        ACCESS    read-only
        STATUS    mandatory
        DESCRIPTION
            "An object containing the minute field of the hour with the busiest 36-second interval for today"
        ::= { g3callratevoice 24 }

    g3callratevoiceBsyIntScToday2	OBJECT-TYPE
        SYNTAX    DisplayString (SIZE (0..2))
        ACCESS    read-only
        STATUS    mandatory
        DESCRIPTION
            "An object containing the second field of the hour with the busiest 36-second interval for today"
        ::= { g3callratevoice 25 }

    g3callratevoiceBsyCalCmplToday2	OBJECT-TYPE
        SYNTAX    DisplayString (SIZE (0..4))
        ACCESS    read-only
        STATUS    mandatory
        DESCRIPTION
            "An object containing the total number of calls completed in the listed busy interval"
        ::= { g3callratevoice 26 }

    g3callratevoiceMeasHour4	OBJECT-TYPE
        SYNTAX    DisplayString (SIZE (0..4))
        ACCESS    read-only
        STATUS    mandatory
        DESCRIPTION
            "An object containing the starting time (using 24-hour clock)
            of the hour during which the data was recorded"
        ::= { g3callratevoice 27 }

    g3callratevoiceNumCallsYesterday	OBJECT-TYPE
        SYNTAX    DisplayString (SIZE (0..6))
        ACCESS    read-only
        STATUS    mandatory
        DESCRIPTION
            "The number of calls completed,or answered (including incoming,
            outgoing, and intercom),during the listed hour"
        ::= { g3callratevoice 28 }

    g3callratevoiceBsyIntHrYesterday	OBJECT-TYPE
        SYNTAX    DisplayString (SIZE (0..2))
        ACCESS    read-only
        STATUS    mandatory
        DESCRIPTION
            "An object containing  yesterday's busiest hour.This is the hour with the
            largest number of completed calls."
        ::= { g3callratevoice 29 }

    g3callratevoiceBsyIntMnYesterday	OBJECT-TYPE
        SYNTAX    DisplayString (SIZE (0..2))
        ACCESS    read-only
        STATUS    mandatory
        DESCRIPTION
            "An object containing the minute field of yesterday's busiest hour"
        ::= { g3callratevoice 30 }

    g3callratevoiceBsyIntScYesterday	OBJECT-TYPE
        SYNTAX    DisplayString (SIZE (0..2))
        ACCESS    read-only
        STATUS    mandatory
        DESCRIPTION
            "An object containing the second field of yesterday's busiest hour"
        ::= { g3callratevoice 31 }

    g3callratevoiceBsyCalCmplYesterday	OBJECT-TYPE
        SYNTAX    DisplayString (SIZE (0..4))
        ACCESS    read-only
        STATUS    mandatory
        DESCRIPTION
            "An object containing the total number of calls completed in the listed busy interval"
        ::= { g3callratevoice 32 }

    g3callratevoiceMeasHour5	OBJECT-TYPE
        SYNTAX    DisplayString (SIZE (0..4))
        ACCESS    read-only
        STATUS    mandatory
        DESCRIPTION
            "An object containing the starting time (using 24-hour clock)
            of the hour during which the data was recorded"
        ::= { g3callratevoice 33 }

    g3callratevoiceNumCallsYesterday2	OBJECT-TYPE
        SYNTAX    DisplayString (SIZE (0..6))
        ACCESS    read-only
        STATUS    mandatory
        DESCRIPTION
            "The number of calls completed,or answered (including incoming,
            outgoing, and intercom),during the listed hour"
        ::= { g3callratevoice 34 }

    g3callratevoiceBsyIntHrYesterday2	OBJECT-TYPE
        SYNTAX    DisplayString (SIZE (0..2))
        ACCESS    read-only
        STATUS    mandatory
        DESCRIPTION
            "An object containing the hour field of the hour with the busiest 36-second interval for yesterday"
        ::= { g3callratevoice 35 }

    g3callratevoiceBsyIntMnYesterday2	OBJECT-TYPE
        SYNTAX    DisplayString (SIZE (0..2))
        ACCESS    read-only
        STATUS    mandatory
        DESCRIPTION
            "An object containing the minute field of the hour with the busiest 36-second interval for yesterday."
        ::= { g3callratevoice 36 }

    g3callratevoiceBsyIntScYesterday2	OBJECT-TYPE
        SYNTAX    DisplayString (SIZE (0..2))
        ACCESS    read-only
        STATUS    mandatory
        DESCRIPTION
            "An object containing the second field of the hour with the busiest 36-second interval for yesterday."
        ::= { g3callratevoice 37 }

    g3callratevoiceBsyCalCmplYesterday2	OBJECT-TYPE
        SYNTAX    DisplayString (SIZE (0..4))
        ACCESS    read-only
        STATUS    mandatory
        DESCRIPTION
            "An object containing the total number of calls completed in the listed busy interval"
        ::= { g3callratevoice 38 }


    -- the g3callratesrv group

    g3callratesrvTage	OBJECT-TYPE
        SYNTAX    INTEGER
        ACCESS    read-only
        STATUS    mandatory
        DESCRIPTION
            "The number of timeticks since the call rate data was last
            extracted from the switch by the Proxy Agent.  This object
            along with the g3callratesrvTintvl object allows the Network Manager
            to determine the validity of the call rate data in the cache 
            and to control when the Proxy Agent extracts the data from the switch."
        ::= { g3callratesrv 1 }

    g3callratesrvTintvl	OBJECT-TYPE
        SYNTAX    INTEGER
        ACCESS    read-write
        STATUS    mandatory
        DESCRIPTION
            "An object containing the interval for which the data extracted from the
            switch is considered valid by the Proxy Agent.When a GET or GET-NEXT
            request for these call rate data objects is received by the agent it uses
            the g3callratesrvTage and g3callratesrvTintvl objects to determine whether
            it should refresh the cached callratesrvTable.If g3callratesrvTstmp +
            g3callratesrvTintvl is less than the current value of the sysUpTime
            object then the agent refreshes the callratesrvTable cache.  In
            either case it responds to the requests it receives with the data
            it currently has in the cache."
        ::= { g3callratesrv 2 }

    g3callratesrvTdelay	OBJECT-TYPE
        SYNTAX    INTEGER
        ACCESS    read-only
        STATUS    mandatory
        DESCRIPTION
            "An object containing the delay encountered in updating
            the cached data."
        ::= { g3callratesrv 3 }

    g3callratesrvTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3callratesrv 4 }

    g3callratesrvRunYear	OBJECT-TYPE
        SYNTAX    INTEGER
        ACCESS    read-only
        STATUS    mandatory
        DESCRIPTION
            "An object containing the Year the command was executed"
        ::= { g3callratesrv 5 }

    g3callratesrvRunMonth	OBJECT-TYPE
        SYNTAX    INTEGER
        ACCESS    read-only
        STATUS    mandatory
        DESCRIPTION
            "An object containing the Month the command was executed"
        ::= { g3callratesrv 6 }

    g3callratesrvRunDay	OBJECT-TYPE
        SYNTAX    INTEGER
        ACCESS    read-only
        STATUS    mandatory
        DESCRIPTION
            "An object containing the Day the command was executed"
        ::= { g3callratesrv 7 }

    g3callratesrvRunHour	OBJECT-TYPE
        SYNTAX    INTEGER
        ACCESS    read-only
        STATUS    mandatory
        DESCRIPTION
            "An object containing the Hour the command was executed"
        ::= { g3callratesrv 8 }

    g3callratesrvMeasHour	OBJECT-TYPE
        SYNTAX    DisplayString (SIZE (0..4))
        ACCESS    read-only
        STATUS    mandatory
        DESCRIPTION
            "An object containing the starting time (using 24-hour clock)
            of the hour during which the data was recorded"
        ::= { g3callratesrv 9 }

    g3callratesrvNumCalls	OBJECT-TYPE
        SYNTAX    DisplayString (SIZE (0..6))
        ACCESS    read-only
        STATUS    mandatory
        DESCRIPTION
            "The number of calls completed,or answered (including incoming,
            outgoing, and intercom),during the listed hour. "
        ::= { g3callratesrv 10 }

    g3callratesrvBsyIntHr	OBJECT-TYPE
        SYNTAX    DisplayString (SIZE (0..2))
        ACCESS    read-only
        STATUS    mandatory
        DESCRIPTION
            "An object containing"
        ::= { g3callratesrv 11 }

    g3callratesrvBsyIntMn	OBJECT-TYPE
        SYNTAX    DisplayString (SIZE (0..2))
        ACCESS    read-only
        STATUS    mandatory
        DESCRIPTION
            "An object containing"
        ::= { g3callratesrv 12 }

    g3callratesrvBsyIntSc	OBJECT-TYPE
        SYNTAX    DisplayString (SIZE (0..2))
        ACCESS    read-only
        STATUS    mandatory
        DESCRIPTION
            "An object containing"
        ::= { g3callratesrv 13 }

    g3callratesrvBsyCalCmpl	OBJECT-TYPE
        SYNTAX    DisplayString (SIZE (0..4))
        ACCESS    read-only
        STATUS    mandatory
        DESCRIPTION
            "An object containing the total number of calls completed in the listed busy interval."
        ::= { g3callratesrv 14 }

    g3callratesrvMeasHour2	OBJECT-TYPE
        SYNTAX    DisplayString (SIZE (0..4))
        ACCESS    read-only
        STATUS    mandatory
        DESCRIPTION
            "An object containing the starting time (using 24-hour clock)
            of the hour during which the data was recorded."
        ::= { g3callratesrv 15 }

    g3callratesrvNumCallsToday	OBJECT-TYPE
        SYNTAX    DisplayString (SIZE (0..6))
        ACCESS    read-only
        STATUS    mandatory
        DESCRIPTION
            "The number of calls completed,or answered (including incoming,
            outgoing, and intercom),during the listed hour"
        ::= { g3callratesrv 16 }

    g3callratesrvBsyIntHrToday	OBJECT-TYPE
        SYNTAX    DisplayString (SIZE (0..2))
        ACCESS    read-only
        STATUS    mandatory
        DESCRIPTION
            "An object containing  today's busiest hour.This is the hour with the
            largest number of completed calls."
        ::= { g3callratesrv 17 }

    g3callratesrvBsyIntMnToday	OBJECT-TYPE
        SYNTAX    DisplayString (SIZE (0..2))
        ACCESS    read-only
        STATUS    mandatory
        DESCRIPTION
            "An object containing the minute field of today's busiest hour"
        ::= { g3callratesrv 18 }

    g3callratesrvBsyIntScToday	OBJECT-TYPE
        SYNTAX    DisplayString (SIZE (0..2))
        ACCESS    read-only
        STATUS    mandatory
        DESCRIPTION
            "An object containing the second field of today's busiest hour"
        ::= { g3callratesrv 19 }

    g3callratesrvBsyCalCmplToday	OBJECT-TYPE
        SYNTAX    DisplayString (SIZE (0..4))
        ACCESS    read-only
        STATUS    mandatory
        DESCRIPTION
            "An object containing the total number of calls completed in the listed busy interval"
        ::= { g3callratesrv 20 }

    g3callratesrvMeasHour3	OBJECT-TYPE
        SYNTAX    DisplayString (SIZE (0..4))
        ACCESS    read-only
        STATUS    mandatory
        DESCRIPTION
            "An object containing the starting time (using 24-hour clock)
            of the hour during which the data was recorded"
        ::= { g3callratesrv 21 }

    g3callratesrvNumCallsToday2	OBJECT-TYPE
        SYNTAX    DisplayString (SIZE (0..6))
        ACCESS    read-only
        STATUS    mandatory
        DESCRIPTION
            "The number of calls completed,or answered (including incoming,
            outgoing, and intercom),during the listed hour"
        ::= { g3callratesrv 22 }

    g3callratesrvBsyIntHrToday2	OBJECT-TYPE
        SYNTAX    DisplayString (SIZE (0..2))
        ACCESS    read-only
        STATUS    mandatory
        DESCRIPTION
            "An object containing the hour field of the hour with the busiest 36-second interval for today"
        ::= { g3callratesrv 23 }

    g3callratesrvBsyIntMnToday2	OBJECT-TYPE
        SYNTAX    DisplayString (SIZE (0..2))
        ACCESS    read-only
        STATUS    mandatory
        DESCRIPTION
            "An object containing the minute field of the hour with the busiest 36-second interval for today"
        ::= { g3callratesrv 24 }

    g3callratesrvBsyIntScToday2	OBJECT-TYPE
        SYNTAX    DisplayString (SIZE (0..2))
        ACCESS    read-only
        STATUS    mandatory
        DESCRIPTION
            "An object containing the second field of the hour with the busiest 36-second interval for today"
        ::= { g3callratesrv 25 }

    g3callratesrvBsyCalCmplToday2	OBJECT-TYPE
        SYNTAX    DisplayString (SIZE (0..4))
        ACCESS    read-only
        STATUS    mandatory
        DESCRIPTION
            "An object containing the total number of calls completed in the listed busy interval"
        ::= { g3callratesrv 26 }

    g3callratesrvMeasHour4	OBJECT-TYPE
        SYNTAX    DisplayString (SIZE (0..4))
        ACCESS    read-only
        STATUS    mandatory
        DESCRIPTION
            "An object containing the starting time (using 24-hour clock) of the hour during which the data 
            was recorded"
        ::= { g3callratesrv 27 }

    g3callratesrvNumCallsYesterday	OBJECT-TYPE
        SYNTAX    DisplayString (SIZE (0..6))
        ACCESS    read-only
        STATUS    mandatory
        DESCRIPTION
            "The number of calls completed,or answered (including incoming,
            outgoing, and intercom),during the listed hour"
        ::= { g3callratesrv 28 }

    g3callratesrvBsyIntHrYesterday	OBJECT-TYPE
        SYNTAX    DisplayString (SIZE (0..2))
        ACCESS    read-only
        STATUS    mandatory
        DESCRIPTION
            "An object containing  yesterday's busiest hour.This is the hour with the
            largest number of completed calls."
        ::= { g3callratesrv 29 }

    g3callratesrvBsyIntMnYesterday	OBJECT-TYPE
        SYNTAX    DisplayString (SIZE (0..2))
        ACCESS    read-only
        STATUS    mandatory
        DESCRIPTION
            "An object containing the minute field of yesterday's busiest hour"
        ::= { g3callratesrv 30 }

    g3callratesrvBsyIntScYesterday	OBJECT-TYPE
        SYNTAX    DisplayString (SIZE (0..2))
        ACCESS    read-only
        STATUS    mandatory
        DESCRIPTION
            "An object containing the second field of yesterday's busiest hour"
        ::= { g3callratesrv 31 }

    g3callratesrvBsyCalCmplYesterday	OBJECT-TYPE
        SYNTAX    DisplayString (SIZE (0..4))
        ACCESS    read-only
        STATUS    mandatory
        DESCRIPTION
            "An object containing the total number of calls completed in the listed busy interval"
        ::= { g3callratesrv 32 }

    g3callratesrvMeasHour5	OBJECT-TYPE
        SYNTAX    DisplayString (SIZE (0..4))
        ACCESS    read-only
        STATUS    mandatory
        DESCRIPTION
            "An object containing the starting time (using 24-hour clock)
            of the hour during which the data was recorded"
        ::= { g3callratesrv 33 }

    g3callratesrvNumCallsYesterday2	OBJECT-TYPE
        SYNTAX    DisplayString (SIZE (0..6))
        ACCESS    read-only
        STATUS    mandatory
        DESCRIPTION
            "The number of calls completed,or answered (including incoming,
            outgoing, and intercom),during the listed hour"
        ::= { g3callratesrv 34 }

    g3callratesrvBsyIntHrYesterday2	OBJECT-TYPE
        SYNTAX    DisplayString (SIZE (0..2))
        ACCESS    read-only
        STATUS    mandatory
        DESCRIPTION
            "An object containing the hour field of the hour with the busiest 36-second interval for yesterday."
        ::= { g3callratesrv 35 }

    g3callratesrvBsyIntMnYesterday2	OBJECT-TYPE
        SYNTAX    DisplayString (SIZE (0..2))
        ACCESS    read-only
        STATUS    mandatory
        DESCRIPTION
            "An object containing the minute field of the hour with the busiest 36-second interval for yesterday."
        ::= { g3callratesrv 36 }

    g3callratesrvBsyIntScYesterday2	OBJECT-TYPE
        SYNTAX    DisplayString (SIZE (0..2))
        ACCESS    read-only
        STATUS    mandatory
        DESCRIPTION
            "An object containing the second field of the hour with the busiest 36-second interval for yesterday."
        ::= { g3callratesrv 37 }

    g3callratesrvBsyCalCmplYesterday2	OBJECT-TYPE
        SYNTAX    DisplayString (SIZE (0..4))
        ACCESS    read-only
        STATUS    mandatory
        DESCRIPTION
            "An object containing the total number of calls completed in the listed busy interval"
        ::= { g3callratesrv 38 }


    -- the g3callratemedia group

    g3callratemediaTage	OBJECT-TYPE
        SYNTAX    INTEGER
        ACCESS    read-only
        STATUS    mandatory
        DESCRIPTION
            "The number of timeticks since the call rate data was last extracted from the 
            switch by the Proxy Agent.This object along with the g3callratemediaTintvl object
            allows the Network Manager to determine the validity of the call rate data in the cache 
            and to control when the Proxy Agent extracts the data from the switch."
        ::= { g3callratemedia 1 }

    g3callratemediaTintvl	OBJECT-TYPE
        SYNTAX    INTEGER
        ACCESS    read-write
        STATUS    mandatory
        DESCRIPTION
            "An object containing the interval for which the data extracted from the
            switch is considered valid by the Proxy Agent.  When a GET or GET-NEXT
            request for these call rate data objects is received by the agent it uses the
            g3callratemediaTage and g3callratemediaTintvl objects to determine whether it "
        ::= { g3callratemedia 2 }

    g3callratemediaTdelay	OBJECT-TYPE
        SYNTAX    INTEGER
        ACCESS    read-only
        STATUS    mandatory
        DESCRIPTION
            "An object containing the delay encountered in updating
            the cached data."
        ::= { g3callratemedia 3 }

    g3callratemediaTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3callratemedia 4 }

    g3callratemediaRunYear	OBJECT-TYPE
        SYNTAX    INTEGER
        ACCESS    read-only
        STATUS    mandatory
        DESCRIPTION
            "An object containing the Year the command was executed"
        ::= { g3callratemedia 5 }

    g3callratemediaRunMonth	OBJECT-TYPE
        SYNTAX    INTEGER
        ACCESS    read-only
        STATUS    mandatory
        DESCRIPTION
            "An object containing the Month the command was executed"
        ::= { g3callratemedia 6 }

    g3callratemediaRunDay	OBJECT-TYPE
        SYNTAX    INTEGER
        ACCESS    read-only
        STATUS    mandatory
        DESCRIPTION
            "An object containing the Day the command was executed"
        ::= { g3callratemedia 7 }

    g3callratemediaRunHour	OBJECT-TYPE
        SYNTAX    INTEGER
        ACCESS    read-only
        STATUS    mandatory
        DESCRIPTION
            "An object containing the Hour the command was executed"
        ::= { g3callratemedia 8 }

    g3callratemediaMeasHour	OBJECT-TYPE
        SYNTAX    DisplayString (SIZE (0..4))
        ACCESS    read-only
        STATUS    mandatory
        DESCRIPTION
            "An object containing the starting time (using 24-hour clock)
            of the hour during which the data was recorded"
        ::= { g3callratemedia 9 }

    g3callratemediaNumCalls	OBJECT-TYPE
        SYNTAX    DisplayString (SIZE (0..6))
        ACCESS    read-only
        STATUS    mandatory
        DESCRIPTION
            "The number of calls completed,or answered (including incoming,
            outgoing, and intercom),during the listed hour. "
        ::= { g3callratemedia 10 }

    g3callratemediaBsyIntHr	OBJECT-TYPE
        SYNTAX    DisplayString (SIZE (0..2))
        ACCESS    read-only
        STATUS    mandatory
        DESCRIPTION
            "An object containing"
        ::= { g3callratemedia 11 }

    g3callratemediaBsyIntMn	OBJECT-TYPE
        SYNTAX    DisplayString (SIZE (0..2))
        ACCESS    read-only
        STATUS    mandatory
        DESCRIPTION
            "An object containing"
        ::= { g3callratemedia 12 }

    g3callratemediaBsyIntSc	OBJECT-TYPE
        SYNTAX    DisplayString (SIZE (0..2))
        ACCESS    read-only
        STATUS    mandatory
        DESCRIPTION
            "An object containing"
        ::= { g3callratemedia 13 }

    g3callratemediaBsyCalCmpl	OBJECT-TYPE
        SYNTAX    DisplayString (SIZE (0..4))
        ACCESS    read-only
        STATUS    mandatory
        DESCRIPTION
            "An object containing the total number of calls completed in the listed busy interval."
        ::= { g3callratemedia 14 }

    g3callratemediaMeasHour2	OBJECT-TYPE
        SYNTAX    DisplayString (SIZE (0..4))
        ACCESS    read-only
        STATUS    mandatory
        DESCRIPTION
            "An object containing the starting time (using 24-hour clock)
            of the hour during which the data was recorded."
        ::= { g3callratemedia 15 }

    g3callratemediaNumCallsToday	OBJECT-TYPE
        SYNTAX    DisplayString (SIZE (0..6))
        ACCESS    read-only
        STATUS    mandatory
        DESCRIPTION
            "The number of calls completed,or answered (including incoming,
            outgoing, and intercom),during the listed hour"
        ::= { g3callratemedia 16 }

    g3callratemediaBsyIntHrToday	OBJECT-TYPE
        SYNTAX    DisplayString (SIZE (0..2))
        ACCESS    read-only
        STATUS    mandatory
        DESCRIPTION
            "An object containing  today's busiest hour.This is the hour with the
            largest number of completed calls."
        ::= { g3callratemedia 17 }

    g3callratemediaBsyIntMnToday	OBJECT-TYPE
        SYNTAX    DisplayString (SIZE (0..2))
        ACCESS    read-only
        STATUS    mandatory
        DESCRIPTION
            "An object containing the minute field of today's busiest hour"
        ::= { g3callratemedia 18 }

    g3callratemediaBsyIntScToday	OBJECT-TYPE
        SYNTAX    DisplayString (SIZE (0..2))
        ACCESS    read-only
        STATUS    mandatory
        DESCRIPTION
            "An object containing the minute field of today's busiest hour"
        ::= { g3callratemedia 19 }

    g3callratemediaBsyCalCmplToday	OBJECT-TYPE
        SYNTAX    DisplayString (SIZE (0..4))
        ACCESS    read-only
        STATUS    mandatory
        DESCRIPTION
            "An object containing the total number of calls completed in the listed busy interval"
        ::= { g3callratemedia 20 }

    g3callratemediaMeasHour3	OBJECT-TYPE
        SYNTAX    DisplayString (SIZE (0..4))
        ACCESS    read-only
        STATUS    mandatory
        DESCRIPTION
            "An object containing the starting time (using 24-hour clock)
            of the hour during which the data was recorded"
        ::= { g3callratemedia 21 }

    g3callratemediaNumCallsToday2	OBJECT-TYPE
        SYNTAX    DisplayString (SIZE (0..6))
        ACCESS    read-only
        STATUS    mandatory
        DESCRIPTION
            "The number of calls completed,or answered (including incoming,
            outgoing, and intercom),during the listed hour"
        ::= { g3callratemedia 22 }

    g3callratemediaBsyIntHrToday2	OBJECT-TYPE
        SYNTAX    DisplayString (SIZE (0..2))
        ACCESS    read-only
        STATUS    mandatory
        DESCRIPTION
            "An object containing the hour field of the hour with the busiest 36-second interval for today"
        ::= { g3callratemedia 23 }

    g3callratemediaBsyIntMnToday2	OBJECT-TYPE
        SYNTAX    DisplayString (SIZE (0..2))
        ACCESS    read-only
        STATUS    mandatory
        DESCRIPTION
            "An object containing the minute field of the hour with the busiest 36-second interval for today"
        ::= { g3callratemedia 24 }

    g3callratemediaBsyIntScToday2	OBJECT-TYPE
        SYNTAX    DisplayString (SIZE (0..2))
        ACCESS    read-only
        STATUS    mandatory
        DESCRIPTION
            "An object containing the second field of the hour with the busiest 36-second interval for today"
        ::= { g3callratemedia 25 }

    g3callratemediaBsyCalCmplToday2	OBJECT-TYPE
        SYNTAX    DisplayString (SIZE (0..4))
        ACCESS    read-only
        STATUS    mandatory
        DESCRIPTION
            "An object containing the total number of calls completed in the listed busy interval"
        ::= { g3callratemedia 26 }

    g3callratemediaMeasHour4	OBJECT-TYPE
        SYNTAX    DisplayString (SIZE (0..4))
        ACCESS    read-only
        STATUS    mandatory
        DESCRIPTION
            "An object containing the starting time (using 24-hour clock)
            of the hour during which the data was recorded"
        ::= { g3callratemedia 27 }

    g3callratemediaNumCallsYesterday	OBJECT-TYPE
        SYNTAX    DisplayString (SIZE (0..6))
        ACCESS    read-only
        STATUS    mandatory
        DESCRIPTION
            "The number of calls completed,or answered (including incoming,
            outgoing, and intercom),during the listed hour"
        ::= { g3callratemedia 28 }

    g3callratemediaBsyIntHrYesterday	OBJECT-TYPE
        SYNTAX    DisplayString (SIZE (0..2))
        ACCESS    read-only
        STATUS    mandatory
        DESCRIPTION
            "An object containing  yesterday's busiest hour.This is the hour with the
            largest number of completed calls."
        ::= { g3callratemedia 29 }

    g3callratemediaBsyIntMnYesterday	OBJECT-TYPE
        SYNTAX    DisplayString (SIZE (0..2))
        ACCESS    read-only
        STATUS    mandatory
        DESCRIPTION
            "An object containing the minute field of yesterday's busiest hour"
        ::= { g3callratemedia 30 }

    g3callratemediaBsyIntScYesterday	OBJECT-TYPE
        SYNTAX    DisplayString (SIZE (0..2))
        ACCESS    read-only
        STATUS    mandatory
        DESCRIPTION
            "An object containing the second field of yesterday's busiest hour"
        ::= { g3callratemedia 31 }

    g3callratemediaBsyCalCmplYesterday	OBJECT-TYPE
        SYNTAX    DisplayString (SIZE (0..4))
        ACCESS    read-only
        STATUS    mandatory
        DESCRIPTION
            "An object containing the total number of calls completed in the listed busy interval"
        ::= { g3callratemedia 32 }

    g3callratemediaMeasHour5	OBJECT-TYPE
        SYNTAX    DisplayString (SIZE (0..4))
        ACCESS    read-only
        STATUS    mandatory
        DESCRIPTION
            "An object containing the starting time (using 24-hour clock)
            of the hour during which the data was recorded"
        ::= { g3callratemedia 33 }

    g3callratemediaNumCallsYesterday2	OBJECT-TYPE
        SYNTAX    DisplayString (SIZE (0..6))
        ACCESS    read-only
        STATUS    mandatory
        DESCRIPTION
            "The number of calls completed,or answered (including incoming,
            outgoing, and intercom),during the listed hour"
        ::= { g3callratemedia 34 }

    g3callratemediaBsyIntHrYesterday2	OBJECT-TYPE
        SYNTAX    DisplayString (SIZE (0..2))
        ACCESS    read-only
        STATUS    mandatory
        DESCRIPTION
            "An object containing the hour field of the hour with the busiest 36-second interval for yesterday"
        ::= { g3callratemedia 35 }

    g3callratemediaBsyIntMnYesterday2	OBJECT-TYPE
        SYNTAX    DisplayString (SIZE (0..2))
        ACCESS    read-only
        STATUS    mandatory
        DESCRIPTION
            "An object containing the minute field of the hour with the busiest 36-second interval for yesterday"
        ::= { g3callratemedia 36 }

    g3callratemediaBsyIntScYesterday2	OBJECT-TYPE
        SYNTAX    DisplayString (SIZE (0..2))
        ACCESS    read-only
        STATUS    mandatory
        DESCRIPTION
            "An object containing the second field of the hour with the busiest 36-second interval for yesterday"
        ::= { g3callratemedia 37 }

    g3callratemediaBsyCalCmplYesterday2	OBJECT-TYPE
        SYNTAX    DisplayString (SIZE (0..4))
        ACCESS    read-only
        STATUS    mandatory
        DESCRIPTION
            "An object containing the total number of calls completed in the listed busy interval"
        ::= { g3callratemedia 38 }


    -- the g3callratetotal group

    g3callratetotalTage	OBJECT-TYPE
        SYNTAX    INTEGER
        ACCESS    read-only
        STATUS    mandatory
        DESCRIPTION
            "The number of timeticks since the call rate data was last extracted from the switch
            by the Proxy Agent.This object along with the g3callratedataTintvl object allows the
            Network Manager to determine the validity of the call rate data in the cache and to 
            control when the Proxy Agent extracts the data from the switch."
        ::= { g3callratetotal 1 }

    g3callratetotalTintvl	OBJECT-TYPE
        SYNTAX    INTEGER
        ACCESS    read-write
        STATUS    mandatory
        DESCRIPTION
            "An object containing the interval for which the data extracted from the
            switch is considered valid by the Proxy Agent.  When a GET or GET-NEXT
            request for these call rate data objects is received by the agent it uses
            the g3callratetotalTage and g3callratetotalTintvl objects to determine 
            whether it should refresh the cached callratetotalTable.  If g3callratetotalTstmp +
            g3callratetotalTintvl is less than the current value of the sysUpTime object then
            the agent refreshes the callratetotalTable cache.In either case it responds to the
            requests it receives with the data	it currently has in the cache."
        ::= { g3callratetotal 2 }

    g3callratetotalTdelay	OBJECT-TYPE
        SYNTAX    INTEGER
        ACCESS    read-only
        STATUS    mandatory
        DESCRIPTION
            "An object containing the delay encountered in updating
            the cached data."
        ::= { g3callratetotal 3 }

    g3callratetotalTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3callratetotal 4 }

    g3callratetotalRunYear	OBJECT-TYPE
        SYNTAX    INTEGER
        ACCESS    read-only
        STATUS    mandatory
        DESCRIPTION
            "An object containing the Year the command was executed"
        ::= { g3callratetotal 5 }

    g3callratetotalRunMonth	OBJECT-TYPE
        SYNTAX    INTEGER
        ACCESS    read-only
        STATUS    mandatory
        DESCRIPTION
            "An object containing the Month the command was executed"
        ::= { g3callratetotal 6 }

    g3callratetotalRunDay	OBJECT-TYPE
        SYNTAX    INTEGER
        ACCESS    read-only
        STATUS    mandatory
        DESCRIPTION
            "An object containing the Day the command was executed"
        ::= { g3callratetotal 7 }

    g3callratetotalRunHour	OBJECT-TYPE
        SYNTAX    INTEGER
        ACCESS    read-only
        STATUS    mandatory
        DESCRIPTION
            "An object containing the Hour the command was executed"
        ::= { g3callratetotal 8 }

    g3callratetotalMeasHour	OBJECT-TYPE
        SYNTAX    DisplayString (SIZE (0..4))
        ACCESS    read-only
        STATUS    mandatory
        DESCRIPTION
            "An object containing the starting time (using 24-hour clock)
            of the hour during which the data was recorded"
        ::= { g3callratetotal 9 }

    g3callratetotalNumCalls	OBJECT-TYPE
        SYNTAX    DisplayString (SIZE (0..6))
        ACCESS    read-only
        STATUS    mandatory
        DESCRIPTION
            "The number of calls completed or answered (including incoming,
            outgoing, and intercom),during the listed hour. "
        ::= { g3callratetotal 10 }

    g3callratetotalBsyIntHr	OBJECT-TYPE
        SYNTAX    DisplayString (SIZE (0..2))
        ACCESS    read-only
        STATUS    mandatory
        DESCRIPTION
            "An object containing"
        ::= { g3callratetotal 11 }

    g3callratetotalBsyIntMn	OBJECT-TYPE
        SYNTAX    DisplayString (SIZE (0..2))
        ACCESS    read-only
        STATUS    mandatory
        DESCRIPTION
            "An object containing"
        ::= { g3callratetotal 12 }

    g3callratetotalBsyIntSc	OBJECT-TYPE
        SYNTAX    DisplayString (SIZE (0..2))
        ACCESS    read-only
        STATUS    mandatory
        DESCRIPTION
            "An object containing"
        ::= { g3callratetotal 13 }

    g3callratetotalBsyCalCmpl	OBJECT-TYPE
        SYNTAX    DisplayString (SIZE (0..4))
        ACCESS    read-only
        STATUS    mandatory
        DESCRIPTION
            "An object containing the total number of calls completed in the listed busy interval."
        ::= { g3callratetotal 14 }

    g3callratetotalMeasHour2	OBJECT-TYPE
        SYNTAX    DisplayString (SIZE (0..4))
        ACCESS    read-only
        STATUS    mandatory
        DESCRIPTION
            "An object containing the starting time (using 24-hour clock)
            of the hour during which the data was recorded."
        ::= { g3callratetotal 15 }

    g3callratetotalNumCallsToday	OBJECT-TYPE
        SYNTAX    DisplayString (SIZE (0..6))
        ACCESS    read-only
        STATUS    mandatory
        DESCRIPTION
            "The number of calls completed,or answered (including incoming,
            outgoing, and intercom),during the listed hour"
        ::= { g3callratetotal 16 }

    g3callratetotalBsyIntHrToday	OBJECT-TYPE
        SYNTAX    DisplayString (SIZE (0..2))
        ACCESS    read-only
        STATUS    mandatory
        DESCRIPTION
            "An object containing  today's busiest hour.This is the hour with the
            largest number of completed calls."
        ::= { g3callratetotal 17 }

    g3callratetotalBsyIntMnToday	OBJECT-TYPE
        SYNTAX    DisplayString (SIZE (0..2))
        ACCESS    read-only
        STATUS    mandatory
        DESCRIPTION
            "An object containing the minute field of today's busiest hour"
        ::= { g3callratetotal 18 }

    g3callratetotalBsyIntScToday	OBJECT-TYPE
        SYNTAX    DisplayString (SIZE (0..2))
        ACCESS    read-only
        STATUS    mandatory
        DESCRIPTION
            "An object containing the second field of today's busiest hour"
        ::= { g3callratetotal 19 }

    g3callratetotalBsyCalCmplToday	OBJECT-TYPE
        SYNTAX    DisplayString (SIZE (0..4))
        ACCESS    read-only
        STATUS    mandatory
        DESCRIPTION
            "An object containing the total number of calls completed in the listed busy interval"
        ::= { g3callratetotal 20 }

    g3callratetotalMeasHour3	OBJECT-TYPE
        SYNTAX    DisplayString (SIZE (0..4))
        ACCESS    read-only
        STATUS    mandatory
        DESCRIPTION
            "An object containing the starting time (using 24-hour clock)
            of the hour during which the data was recorded"
        ::= { g3callratetotal 21 }

    g3callratetotalNumCallsToday2	OBJECT-TYPE
        SYNTAX    DisplayString (SIZE (0..6))
        ACCESS    read-only
        STATUS    mandatory
        DESCRIPTION
            "The number of calls completed,or answered (including incoming,
            outgoing, and intercom),during the listed hour"
        ::= { g3callratetotal 22 }

    g3callratetotalBsyIntHrToday2	OBJECT-TYPE
        SYNTAX    DisplayString (SIZE (0..2))
        ACCESS    read-only
        STATUS    mandatory
        DESCRIPTION
            "An object containing the hour field of the hour with the busiest 36-second interval for today."
        ::= { g3callratetotal 23 }

    g3callratetotalBsyIntMnToday2	OBJECT-TYPE
        SYNTAX    DisplayString (SIZE (0..2))
        ACCESS    read-only
        STATUS    mandatory
        DESCRIPTION
            "An object containing the minute field of the hour with the busiest 36-second interval for today."
        ::= { g3callratetotal 24 }

    g3callratetotalBsyIntScToday2	OBJECT-TYPE
        SYNTAX    DisplayString (SIZE (0..2))
        ACCESS    read-only
        STATUS    mandatory
        DESCRIPTION
            "An object containing the second field of the hour with the busiest 36-second interval for today."
        ::= { g3callratetotal 25 }

    g3callratetotalBsyCalCmplToday2	OBJECT-TYPE
        SYNTAX    DisplayString (SIZE (0..4))
        ACCESS    read-only
        STATUS    mandatory
        DESCRIPTION
            "An object containing the total number of calls completed in the listed busy interval"
        ::= { g3callratetotal 26 }

    g3callratetotalMeasHour4	OBJECT-TYPE
        SYNTAX    DisplayString (SIZE (0..4))
        ACCESS    read-only
        STATUS    mandatory
        DESCRIPTION
            "An object containing the starting time (using 24-hour clock)
            of the hour during which the data was recorded"
        ::= { g3callratetotal 27 }

    g3callratetotalNumCallsYesterday	OBJECT-TYPE
        SYNTAX    DisplayString (SIZE (0..6))
        ACCESS    read-only
        STATUS    mandatory
        DESCRIPTION
            "The number of calls completed,or answered (including incoming,
            outgoing, and intercom),during the listed hour"
        ::= { g3callratetotal 28 }

    g3callratetotalBsyIntHrYesterday	OBJECT-TYPE
        SYNTAX    DisplayString (SIZE (0..2))
        ACCESS    read-only
        STATUS    mandatory
        DESCRIPTION
            "An object containing  yesterday's busiest hour.This is the hour with the
            largest number of completed calls."
        ::= { g3callratetotal 29 }

    g3callratetotalBsyIntMnYesterday	OBJECT-TYPE
        SYNTAX    DisplayString (SIZE (0..2))
        ACCESS    read-only
        STATUS    mandatory
        DESCRIPTION
            "An object containing the minute field of yesterday's busiest hour"
        ::= { g3callratetotal 30 }

    g3callratetotalBsyIntScYesterday	OBJECT-TYPE
        SYNTAX    DisplayString (SIZE (0..2))
        ACCESS    read-only
        STATUS    mandatory
        DESCRIPTION
            "An object containing the second field of yesterday's busiest hour"
        ::= { g3callratetotal 31 }

    g3callratetotalBsyCalCmplYesterday	OBJECT-TYPE
        SYNTAX    DisplayString (SIZE (0..4))
        ACCESS    read-only
        STATUS    mandatory
        DESCRIPTION
            "An object containing the total number of calls completed in the listed busy interval"
        ::= { g3callratetotal 32 }

    g3callratetotalMeasHour5	OBJECT-TYPE
        SYNTAX    DisplayString (SIZE (0..4))
        ACCESS    read-only
        STATUS    mandatory
        DESCRIPTION
            "An object containing the starting time (using 24-hour clock)
            of the hour during which the data was recorded"
        ::= { g3callratetotal 33 }

    g3callratetotalNumCallsYesterday2	OBJECT-TYPE
        SYNTAX    DisplayString (SIZE (0..6))
        ACCESS    read-only
        STATUS    mandatory
        DESCRIPTION
            "The number of calls completed,or answered (including incoming,
            outgoing, and intercom),during the listed hour"
        ::= { g3callratetotal 34 }

    g3callratetotalBsyIntHrYesterday2	OBJECT-TYPE
        SYNTAX    DisplayString (SIZE (0..2))
        ACCESS    read-only
        STATUS    mandatory
        DESCRIPTION
            "An object containing the hour with the busiest 36-second interval for yesterday."
        ::= { g3callratetotal 35 }

    g3callratetotalBsyIntMnYesterday2	OBJECT-TYPE
        SYNTAX    DisplayString (SIZE (0..2))
        ACCESS    read-only
        STATUS    mandatory
        DESCRIPTION
            "An object containing the minute field of the hour with the busiest 36-second interval for yesterday."
        ::= { g3callratetotal 36 }

    g3callratetotalBsyIntScYesterday2	OBJECT-TYPE
        SYNTAX    DisplayString (SIZE (0..2))
        ACCESS    read-only
        STATUS    mandatory
        DESCRIPTION
            "An object containing the second field of the hour with the busiest 36-second interval for yesterday."
        ::= { g3callratetotal 37 }

    g3callratetotalBsyCalCmplYesterday2	OBJECT-TYPE
        SYNTAX    DisplayString (SIZE (0..4))
        ACCESS    read-only
        STATUS    mandatory
        DESCRIPTION
            "An object containing the total number of calls completed in the listed busy interval"
        ::= { g3callratetotal 38 }


    -- the g3clansocsum group

    g3clansocsumTage	OBJECT-TYPE
        SYNTAX    INTEGER
        ACCESS    read-only
        STATUS    mandatory
        DESCRIPTION
            "The number of timeticks since the clan sockets summary data was last extracted
            from the switch by the Proxy Agent.This object along with the g3clansocsumTintvl
            object allows the Network Manager to determine the validity of the clan socket data
            in the cache and to control when the Proxy Agent extracts the data from the switch."
        ::= { g3clansocsum 1 }

    g3clansocsumTintvl	OBJECT-TYPE
        SYNTAX    INTEGER
        ACCESS    read-write
        STATUS    mandatory
        DESCRIPTION
            "An object containing the interval for which the data extracted from the switch
            is considered valid by the Proxy Agent.
            When a GET or GET-NEXT request for these clan sockets data objects is received
            by the agent it uses the g3clansocsumTage and g3clansocsumTintvl objects to determine
            whether it should refresh the cached clansocsumTable.
            If g3clansocsumTstmp + g3clansocsumTintvl is less than the current value of the sysUpTime
            object then the	agent refreshes the clansocsumTable cache.
            In either case it responds to the requests it receives with the	data it	currently has
            in the cache."
        ::= { g3clansocsum 2 }

    g3clansocsumTdelay	OBJECT-TYPE
        SYNTAX    INTEGER
        ACCESS    read-only
        STATUS    mandatory
        DESCRIPTION
            "An object containing the delay encountered in updating 	the cached data."
        ::= { g3clansocsum 3 }

    g3clansocsumTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data	is being retrieved and 
            otherwise 'current'.This object may be set to 'update' to force a refresh of the cache."
        ::= { g3clansocsum 4 }

    g3clansocsumTcount	OBJECT-TYPE
        SYNTAX    Gauge
        ACCESS    read-only
        STATUS    mandatory
        DESCRIPTION
            "A Gauge object containing the number of data records in the cache."
        ::= { g3clansocsum 5 }

    g3clansocsumTable	OBJECT-TYPE
        SYNTAX    SEQUENCE OF G3clansocsumEntry
        ACCESS    not-accessible
        STATUS    mandatory
        DESCRIPTION
            "A list of g3clansocsum entries."
        ::= { g3clansocsum 6 }

    g3clansocsumEntry	OBJECT-TYPE
        SYNTAX    G3clansocsumEntry
        ACCESS    not-accessible
        STATUS    mandatory
        DESCRIPTION
            "A g3clansocsum entry containing objects of the
            g3clansocsum information sent by the switch."
        INDEX    { g3clansocsumBoard }
        ::= { g3clansocsumTable 1 }

    G3clansocsumEntry ::= SEQUENCE {
        g3clansocsumBoard
            DisplayString,
        g3clansocsumMeasHour
            DisplayString,
        g3clansocsumYear
            INTEGER,
        g3clansocsumMonth
            INTEGER,
        g3clansocsumDay
            INTEGER,
        g3clansocsumHour
            INTEGER,
        g3clansocsumRegion
            DisplayString,
        g3clansocsumSockusage
            DisplayString,
        g3clansocsumSockPeg
            DisplayString,
        g3clansocsumDenialPeg
            DisplayString,
        g3clansocsumPctDenial
            DisplayString,
        g3clansocsumPcttmASB
            DisplayString
        }

    g3clansocsumBoard	OBJECT-TYPE
        SYNTAX    DisplayString (SIZE (0..7))
        ACCESS    read-only
        STATUS    mandatory
        DESCRIPTION
            "An object containing the cabinet, carrier, and slot for the specified board"
        ::= { g3clansocsumEntry 1 }

    g3clansocsumMeasHour	OBJECT-TYPE
        SYNTAX    DisplayString (SIZE (0..4))
        ACCESS    read-only
        STATUS    mandatory
        DESCRIPTION
            "An object containing the hour the measurement was taken"
        ::= { g3clansocsumEntry 2 }

    g3clansocsumYear	OBJECT-TYPE
        SYNTAX    INTEGER
        ACCESS    read-only
        STATUS    mandatory
        DESCRIPTION
            "An object containing the Year the command was executed"
        ::= { g3clansocsumEntry 3 }

    g3clansocsumMonth	OBJECT-TYPE
        SYNTAX    INTEGER
        ACCESS    read-only
        STATUS    mandatory
        DESCRIPTION
            "An object containing the Month the command was executed"
        ::= { g3clansocsumEntry 4 }

    g3clansocsumDay	OBJECT-TYPE
        SYNTAX    INTEGER
        ACCESS    read-only
        STATUS    mandatory
        DESCRIPTION
            "An object containing the Day the command was executed"
        ::= { g3clansocsumEntry 5 }

    g3clansocsumHour	OBJECT-TYPE
        SYNTAX    INTEGER
        ACCESS    read-only
        STATUS    mandatory
        DESCRIPTION
            "An object containing the Hour the command was executed"
        ::= { g3clansocsumEntry 6 }

    g3clansocsumRegion	OBJECT-TYPE
        SYNTAX    DisplayString (SIZE (0..3))
        ACCESS    read-only
        STATUS    mandatory
        DESCRIPTION
            "An object containing the network region that the CLAN for this measurement is in.
            Range: 1-44"
        ::= { g3clansocsumEntry 7 }

    g3clansocsumSockusage	OBJECT-TYPE
        SYNTAX    DisplayString (SIZE (0..6))
        ACCESS    read-only
        STATUS    mandatory
        DESCRIPTION
            "An object containing the total time, in Erlangs, that is available from sockets on this
            C-lan board. Calculated by: (Total Socket Seconds of usage) / 3600. 
            Range:	0-9999.9."
        ::= { g3clansocsumEntry 8 }

    g3clansocsumSockPeg	OBJECT-TYPE
        SYNTAX    DisplayString (SIZE (0..5))
        ACCESS    read-only
        STATUS    mandatory
        DESCRIPTION
            "An object containing the total number of times a C-lan socket on the board
            was allocated to a call or link. Range: 0-65535"
        ::= { g3clansocsumEntry 9 }

    g3clansocsumDenialPeg	OBJECT-TYPE
        SYNTAX    DisplayString (SIZE (0..5))
        ACCESS    read-only
        STATUS    mandatory
        DESCRIPTION
            "An object containing the total number of times a C-lan socket on the board was
            needed for a call or link, but was not available. Range: 0-65535"
        ::= { g3clansocsumEntry 10 }

    g3clansocsumPctDenial	OBJECT-TYPE
        SYNTAX    DisplayString (SIZE (0..5))
        ACCESS    read-only
        STATUS    mandatory
        DESCRIPTION
            "An object containing (Socket Denial peg)/(Socket Denial peg + Socket peg). Range: 0-99"
        ::= { g3clansocsumEntry 11 }

    g3clansocsumPcttmASB	OBJECT-TYPE
        SYNTAX    DisplayString (SIZE (0..5))
        ACCESS    read-only
        STATUS    mandatory
        DESCRIPTION
            "An object containing the percentage of time during the measured interval that all C-lan 
            sockets on the board were unavailable for use. Range: 0-99"
        ::= { g3clansocsumEntry 12 }


    -- the g3pkclansocsum group

    g3pkclansocsumTage	OBJECT-TYPE
        SYNTAX    INTEGER
        ACCESS    read-only
        STATUS    mandatory
        DESCRIPTION
            "The number of timeticks since the clan sockets summary data was last extracted from
            the switch by the Proxy Agent.  This object along with the g3clansumintvl object 
            allows the Network Manager to determine the validity of the clan socket summary data
            in the cache and to control when the Proxy Agent extracts the data from the switch."
        ::= { g3pkclansocsum 1 }

    g3pkclansocsumTintvl	OBJECT-TYPE
        SYNTAX    INTEGER
        ACCESS    read-write
        STATUS    mandatory
        DESCRIPTION
            "An object containing the interval for which the data extracted from the switch is 
            considered valid by the Proxy Agent.  
            When a GET or GET-NEXT request for these clan socket sumary data objects is received
            by the agent it uses the g3clansocsumTage and g3clansocsumTintvl objects to determine
            whether it should refresh the cached clansocsumTable.
            If g3clasocsumTstmp + g3clansocsumTintvl is less than the current value of the sysUpTime
            object then the agent refreshes the clansocsumTable cache.
            In either case it responds to the requests it receives with the data it currently
            has in the cache."
        ::= { g3pkclansocsum 2 }

    g3pkclansocsumTdelay	OBJECT-TYPE
        SYNTAX    INTEGER
        ACCESS    read-only
        STATUS    mandatory
        DESCRIPTION
            "An object containing the delay encountered in updating the cached data."
        ::= { g3pkclansocsum 3 }

    g3pkclansocsumTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3pkclansocsum 4 }

    g3pkclansocsumTcount	OBJECT-TYPE
        SYNTAX    Gauge
        ACCESS    read-only
        STATUS    mandatory
        DESCRIPTION
            "A Gauge object containing the number of data records in the cache."
        ::= { g3pkclansocsum 5 }

    g3pkclansocsumTable	OBJECT-TYPE
        SYNTAX    SEQUENCE OF G3pkclansocsumEntry
        ACCESS    not-accessible
        STATUS    mandatory
        DESCRIPTION
            "A list of g3pkclansocsum entries."
        ::= { g3pkclansocsum 6 }

    g3pkclansocsumEntry	OBJECT-TYPE
        SYNTAX    G3pkclansocsumEntry
        ACCESS    not-accessible
        STATUS    mandatory
        DESCRIPTION
            "A g3pkclansocsum entry containing objects of the
            g3pkclansocsum information sent by the switch."
        INDEX    { g3pkclansocsumBoard }
        ::= { g3pkclansocsumTable 1 }

    G3pkclansocsumEntry ::= SEQUENCE {
        g3pkclansocsumBoard
            DisplayString,
        g3pkclansocsumMeasHour
            DisplayString,
        g3pkclansocsumYear
            INTEGER,
        g3pkclansocsumMonth
            INTEGER,
        g3pkclansocsumDay
            INTEGER,
        g3pkclansocsumHour
            INTEGER,
        g3pkclansocsumRegion
            DisplayString,
        g3pkclansocsumSockusage
            DisplayString,
        g3pkclansocsumSockPeg
            DisplayString,
        g3pkclansocsumDenialPeg
            DisplayString,
        g3pkclansocsumPctDenial
            DisplayString,
        g3pkclansocsumPcttmASB
            DisplayString
        }

    g3pkclansocsumBoard	OBJECT-TYPE
        SYNTAX    DisplayString (SIZE (0..7))
        ACCESS    read-only
        STATUS    mandatory
        DESCRIPTION
            "An object containing the cabinet, carrier, and slot for the specified board"
        ::= { g3pkclansocsumEntry 1 }

    g3pkclansocsumMeasHour	OBJECT-TYPE
        SYNTAX    DisplayString (SIZE (0..4))
        ACCESS    read-only
        STATUS    mandatory
        DESCRIPTION
            "An object containing the hour the measurement was taken"
        ::= { g3pkclansocsumEntry 2 }

    g3pkclansocsumYear	OBJECT-TYPE
        SYNTAX    INTEGER
        ACCESS    read-only
        STATUS    mandatory
        DESCRIPTION
            "An object containing the Year the command was executed"
        ::= { g3pkclansocsumEntry 3 }

    g3pkclansocsumMonth	OBJECT-TYPE
        SYNTAX    INTEGER
        ACCESS    read-only
        STATUS    mandatory
        DESCRIPTION
            "An object containing the Month the command was executed"
        ::= { g3pkclansocsumEntry 4 }

    g3pkclansocsumDay	OBJECT-TYPE
        SYNTAX    INTEGER
        ACCESS    read-only
        STATUS    mandatory
        DESCRIPTION
            "An object containing the Day the command was executed"
        ::= { g3pkclansocsumEntry 5 }

    g3pkclansocsumHour	OBJECT-TYPE
        SYNTAX    INTEGER
        ACCESS    read-only
        STATUS    mandatory
        DESCRIPTION
            "An object containing the Hour the command was executed"
        ::= { g3pkclansocsumEntry 6 }

    g3pkclansocsumRegion	OBJECT-TYPE
        SYNTAX    DisplayString (SIZE (0..3))
        ACCESS    read-only
        STATUS    mandatory
        DESCRIPTION
            "An object containing the network region that the CLAN for this measurement is in.
            Range: 1-44"
        ::= { g3pkclansocsumEntry 7 }

    g3pkclansocsumSockusage	OBJECT-TYPE
        SYNTAX    DisplayString (SIZE (0..6))
        ACCESS    read-only
        STATUS    mandatory
        DESCRIPTION
            "An object containing the total time, in Erlangs, that is available from sockets on
            this C-lan board. Calculated by: (Total Socket Seconds of usage) / 3600. 
            Range:	0-9999.9."
        ::= { g3pkclansocsumEntry 8 }

    g3pkclansocsumSockPeg	OBJECT-TYPE
        SYNTAX    DisplayString (SIZE (0..5))
        ACCESS    read-only
        STATUS    mandatory
        DESCRIPTION
            "An object containing the total number of times a C-lan socket on the board 
            was allocated to a call or link. Range: 0-65535"
        ::= { g3pkclansocsumEntry 9 }

    g3pkclansocsumDenialPeg	OBJECT-TYPE
        SYNTAX    DisplayString (SIZE (0..5))
        ACCESS    read-only
        STATUS    mandatory
        DESCRIPTION
            "An object containing the total number of times a C-lan socket on the board was 
            needed for a call or link, but was not available. Range: 0-65535"
        ::= { g3pkclansocsumEntry 10 }

    g3pkclansocsumPctDenial	OBJECT-TYPE
        SYNTAX    DisplayString (SIZE (0..5))
        ACCESS    read-only
        STATUS    mandatory
        DESCRIPTION
            "An object containing (Socket Denial peg)/(Socket Denial peg + Socket peg).
            Range: 0-99"
        ::= { g3pkclansocsumEntry 11 }

    g3pkclansocsumPcttmASB	OBJECT-TYPE
        SYNTAX    DisplayString (SIZE (0..5))
        ACCESS    read-only
        STATUS    mandatory
        DESCRIPTION
            "An object containing the percentage of time during the measured interval that 
            all C-lan sockets on the board were unavailable for use. Range: 0-99"
        ::= { g3pkclansocsumEntry 12 }


    -- the g3clanether group

    g3clanetherTage	OBJECT-TYPE
        SYNTAX    INTEGER
        ACCESS    read-only
        STATUS    mandatory
        DESCRIPTION
            "The number of timeticks since the clan ethernet data was last extracted from
            the switch by the Proxy Agent.This object along with the g3clanetherTintvl 
            object allows the Network Manager to determine the validity of the clan ethernet
            data in the cache and to control when the Proxy Agent extracts the data
            from the switch."
        ::= { g3clanether 1 }

    g3clanetherTintvl	OBJECT-TYPE
        SYNTAX    INTEGER
        ACCESS    read-write
        STATUS    mandatory
        DESCRIPTION
            "An object containing the interval for which the data extracted from the switch is 
            considered valid by the Proxy Agent.  
            When a GET or GET-NEXT request for these clan ethernet data objects is received
            by the agent it uses the g3clanetherTage and g3clanetherTintvl objects to determine
            whether it should refresh the cached clanetherTable.
            If g3clanetherTstmp + g3clanetherTintvl is less than the current value of the sysUpTime
            object then the agent refreshes the clanetherTable cache.In either case it responds
            to the requests it receives with the data it currently has in the cache."
        ::= { g3clanether 2 }

    g3clanetherTdelay	OBJECT-TYPE
        SYNTAX    INTEGER
        ACCESS    read-only
        STATUS    mandatory
        DESCRIPTION
            "An object containing the delay encountered in updating the cached data."
        ::= { g3clanether 3 }

    g3clanetherTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3clanether 4 }

    g3clanetherTcount	OBJECT-TYPE
        SYNTAX    Gauge
        ACCESS    read-only
        STATUS    mandatory
        DESCRIPTION
            "A Gauge object containing the number of data records in the cache."
        ::= { g3clanether 5 }

    g3clanetherTable	OBJECT-TYPE
        SYNTAX    SEQUENCE OF G3clanetherEntry
        ACCESS    not-accessible
        STATUS    mandatory
        DESCRIPTION
            "A list of g3clanether entries."
        ::= { g3clanether 6 }

    g3clanetherEntry	OBJECT-TYPE
        SYNTAX    G3clanetherEntry
        ACCESS    not-accessible
        STATUS    mandatory
        DESCRIPTION
            "A g3clanether entry containing objects of the
            g3clanether information sent by the switch."
        INDEX    { g3clanetherKey, g3clanetherDate, g3clanetherTime }
        ::= { g3clanetherTable 1 }

    G3clanetherEntry ::= SEQUENCE {
        g3clanetherKey
            DisplayString,
        g3clanetherYear
            INTEGER,
        g3clanetherMonth
            INTEGER,
        g3clanetherDay
            INTEGER,
        g3clanetherHour
            INTEGER,
        g3clanetherDate
            DisplayString,
        g3clanetherTime
            INTEGER,
        g3clanetherCrcChkTot
            DisplayString,
        g3clanetherCrcChkDelta
            DisplayString,
        g3clanetherCollCntTot
            DisplayString,
        g3clanetherCollCntDelta
            DisplayString
        }

    g3clanetherKey	OBJECT-TYPE
        SYNTAX    DisplayString (SIZE (0..8))
        ACCESS    read-only
        STATUS    mandatory
        DESCRIPTION
            "An object containing the index key"
        ::= { g3clanetherEntry 1 }

    g3clanetherYear	OBJECT-TYPE
        SYNTAX    INTEGER
        ACCESS    read-only
        STATUS    mandatory
        DESCRIPTION
            "An object containing the Year the command was executed"
        ::= { g3clanetherEntry 2 }

    g3clanetherMonth	OBJECT-TYPE
        SYNTAX    INTEGER
        ACCESS    read-only
        STATUS    mandatory
        DESCRIPTION
            "An object containing the Month the command was executed"
        ::= { g3clanetherEntry 3 }

    g3clanetherDay	OBJECT-TYPE
        SYNTAX    INTEGER
        ACCESS    read-only
        STATUS    mandatory
        DESCRIPTION
            "An object containing the Day the command was executed"
        ::= { g3clanetherEntry 4 }

    g3clanetherHour	OBJECT-TYPE
        SYNTAX    INTEGER
        ACCESS    read-only
        STATUS    mandatory
        DESCRIPTION
            "An object containing the Hour the command was executed"
        ::= { g3clanetherEntry 5 }

    g3clanetherDate	OBJECT-TYPE
        SYNTAX    DisplayString (SIZE (0..5))
        ACCESS    read-only
        STATUS    mandatory
        DESCRIPTION
            "An object containing the date that the data was collected"
        ::= { g3clanetherEntry 6 }

    g3clanetherTime	OBJECT-TYPE
        SYNTAX    INTEGER
        ACCESS    read-only
        STATUS    mandatory
        DESCRIPTION
            "An object containing the current 15-minute interval in which the action was performed"
        ::= { g3clanetherEntry 7 }

    g3clanetherCrcChkTot	OBJECT-TYPE
        SYNTAX    DisplayString (SIZE (0..10))
        ACCESS    read-only
        STATUS    mandatory
        DESCRIPTION
            "An object containing the total error count for CRC errors"
        ::= { g3clanetherEntry 8 }

    g3clanetherCrcChkDelta	OBJECT-TYPE
        SYNTAX    DisplayString (SIZE (0..10))
        ACCESS    read-only
        STATUS    mandatory
        DESCRIPTION
            "An object containing the difference between the current and the previous sample for CRC errors"
        ::= { g3clanetherEntry 9 }

    g3clanetherCollCntTot	OBJECT-TYPE
        SYNTAX    DisplayString (SIZE (0..10))
        ACCESS    read-only
        STATUS    mandatory
        DESCRIPTION
            "An object containing the error count for collisions on the ethernet"
        ::= { g3clanetherEntry 10 }

    g3clanetherCollCntDelta	OBJECT-TYPE
        SYNTAX    DisplayString (SIZE (0..10))
        ACCESS    read-only
        STATUS    mandatory
        DESCRIPTION
            "An object containing the difference between the current and previous samples for the error count
            for collisions on the ethernet"
        ::= { g3clanetherEntry 11 }


    -- the g3clanppp group

    g3clanpppTage	OBJECT-TYPE
        SYNTAX    INTEGER
        ACCESS    read-only
        STATUS    mandatory
        DESCRIPTION
            "The number of timeticks since the clan ppp data was last extracted from
            the switch by the Proxy Agent.
            This object along with the g3clanpppTintvl object allows the Network Manager to
            determine the validity of the clan ppp data in the cache and to control
            when the Proxy Agent extracts the data from the switch."
        ::= { g3clanppp 1 }

    g3clanpppTintvl	OBJECT-TYPE
        SYNTAX    INTEGER
        ACCESS    read-write
        STATUS    mandatory
        DESCRIPTION
            "An object containing the interval for which the	data extracted from the switch is
            considered valid by the Proxy Agent.  
            When a GET or GET-NEXT request for these clan ppp data objects is received by 
            the agent it uses the g3clanpppTage and g3clanpppTintvl objects to determine whether 
            it should refresh the cached clanpppTable.
            If g3clanpppTstmp + g3clanpppTintvl is less than the current value of the sysUpTime
            object then the agent refreshes the clanpppTable cache.In either case it responds
            to the requests it receives with the data it currently has in the cache."
        ::= { g3clanppp 2 }

    g3clanpppTdelay	OBJECT-TYPE
        SYNTAX    INTEGER
        ACCESS    read-only
        STATUS    mandatory
        DESCRIPTION
            "An object containing the delay encountered in updating the cached data."
        ::= { g3clanppp 3 }

    g3clanpppTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3clanppp 4 }

    g3clanpppTcount	OBJECT-TYPE
        SYNTAX    Gauge
        ACCESS    read-only
        STATUS    mandatory
        DESCRIPTION
            "A Gauge object containing the number of data records in the cache."
        ::= { g3clanppp 5 }

    g3clanpppTable	OBJECT-TYPE
        SYNTAX    SEQUENCE OF G3clanpppEntry
        ACCESS    not-accessible
        STATUS    mandatory
        DESCRIPTION
            "A list of g3clanppp entries."
        ::= { g3clanppp 6 }

    g3clanpppEntry	OBJECT-TYPE
        SYNTAX    G3clanpppEntry
        ACCESS    not-accessible
        STATUS    mandatory
        DESCRIPTION
            "A g3clanppp entry containing objects of the
            g3clanppp information sent by the switch."
        INDEX    { g3clanpppKey, g3clanpppDate, g3clanpppTime }
        ::= { g3clanpppTable 1 }

    G3clanpppEntry ::= SEQUENCE {
        g3clanpppKey
            DisplayString,
        g3clanpppYear
            INTEGER,
        g3clanpppMonth
            INTEGER,
        g3clanpppDay
            INTEGER,
        g3clanpppHour
            INTEGER,
        g3clanpppDate
            DisplayString,
        g3clanpppTime
            INTEGER,
        g3clanpppCrcChkTot
            DisplayString,
        g3clanpppCrcChkDelta
            DisplayString,
        g3clanpppInvFrameTot
            DisplayString,
        g3clanpppInvFrameDelta
            DisplayString,
        g3clanpppChapFailTot
            DisplayString,
        g3clanpppChapFailDelta
            DisplayString
        }

    g3clanpppKey	OBJECT-TYPE
        SYNTAX    DisplayString (SIZE (0..8))
        ACCESS    read-only
        STATUS    mandatory
        DESCRIPTION
            "An object containing the index key"
        ::= { g3clanpppEntry 1 }

    g3clanpppYear	OBJECT-TYPE
        SYNTAX    INTEGER
        ACCESS    read-only
        STATUS    mandatory
        DESCRIPTION
            "An object containing the Year the command was executed"
        ::= { g3clanpppEntry 2 }

    g3clanpppMonth	OBJECT-TYPE
        SYNTAX    INTEGER
        ACCESS    read-only
        STATUS    mandatory
        DESCRIPTION
            "An object containing the Month the command was executed"
        ::= { g3clanpppEntry 3 }

    g3clanpppDay	OBJECT-TYPE
        SYNTAX    INTEGER
        ACCESS    read-only
        STATUS    mandatory
        DESCRIPTION
            "An object containing the Day the command was executed"
        ::= { g3clanpppEntry 4 }

    g3clanpppHour	OBJECT-TYPE
        SYNTAX    INTEGER
        ACCESS    read-only
        STATUS    mandatory
        DESCRIPTION
            "An object containing the Hour the command was executed"
        ::= { g3clanpppEntry 5 }

    g3clanpppDate	OBJECT-TYPE
        SYNTAX    DisplayString (SIZE (0..5))
        ACCESS    read-only
        STATUS    mandatory
        DESCRIPTION
            "An object containing the date that the data was collected"
        ::= { g3clanpppEntry 6 }

    g3clanpppTime	OBJECT-TYPE
        SYNTAX    INTEGER
        ACCESS    read-only
        STATUS    mandatory
        DESCRIPTION
            "An object containing the current 15-minute interval in which the action was performed"
        ::= { g3clanpppEntry 7 }

    g3clanpppCrcChkTot	OBJECT-TYPE
        SYNTAX    DisplayString (SIZE (0..6))
        ACCESS    read-only
        STATUS    mandatory
        DESCRIPTION
            "An object containing the total error count for CRC errors"
        ::= { g3clanpppEntry 8 }

    g3clanpppCrcChkDelta	OBJECT-TYPE
        SYNTAX    DisplayString (SIZE (0..6))
        ACCESS    read-only
        STATUS    mandatory
        DESCRIPTION
            "An object containing the difference between the current and the previous sample for CRC errors"
        ::= { g3clanpppEntry 9 }

    g3clanpppInvFrameTot	OBJECT-TYPE
        SYNTAX    DisplayString (SIZE (0..6))
        ACCESS    read-only
        STATUS    mandatory
        DESCRIPTION
            "An object containing the total number of invalid frames detected. Invalid frames are the
            frames that are misaligned."
        ::= { g3clanpppEntry 10 }

    g3clanpppInvFrameDelta	OBJECT-TYPE
        SYNTAX    DisplayString (SIZE (0..6))
        ACCESS    read-only
        STATUS    mandatory
        DESCRIPTION
            "An object containing the difference between the Invalid frames count between the current and 
            previous samples for Invalid frames count"
        ::= { g3clanpppEntry 11 }

    g3clanpppChapFailTot	OBJECT-TYPE
        SYNTAX    DisplayString (SIZE (0..6))
        ACCESS    read-only
        STATUS    mandatory
        DESCRIPTION
            "An object containing the total number of failed attempts for ppp authentication"
        ::= { g3clanpppEntry 12 }

    g3clanpppChapFailDelta	OBJECT-TYPE
        SYNTAX    DisplayString (SIZE (0..6))
        ACCESS    read-only
        STATUS    mandatory
        DESCRIPTION
            "An object containing the difference betwen the current and previous sample for number of failed"
        ::= { g3clanpppEntry 13 }


    -- the g3mmisum group

    g3mmisumTage	OBJECT-TYPE
        SYNTAX    INTEGER
        ACCESS    read-only
        STATUS    mandatory
        DESCRIPTION
            "The number of timeticks since the hourly multimedia interface 
            traffic (MMI) summary data was last extracted from the switch by 
            the Proxy Agent.  This object along with the g3mmisumTintvl object 
            allows the Network Manager to determine the validity of the 
            hourly MMI summary data in the cache and to control when the 
            Proxy Agent extracts the data from the switch."
        ::= { g3mmisum 1 }

    g3mmisumTintvl	OBJECT-TYPE
        SYNTAX    INTEGER
        ACCESS    read-write
        STATUS    mandatory
        DESCRIPTION
            "An object containing the interval for which the data extracted 
            from the switch is considered valid by the Proxy Agent.
            When a GET or GET-NEXT request for these hourly MMI summary 
            objects is received by the agent it uses the g3mmisumTage and 
            g3mmisumTintvl objects to determine whether it should refresh 
            the cached hourly MMI summary data."
        ::= { g3mmisum 2 }

    g3mmisumTdelay	OBJECT-TYPE
        SYNTAX    INTEGER
        ACCESS    read-only
        STATUS    mandatory
        DESCRIPTION
            "An object containing the delay encountered in updating the 
            cached data."
        ::= { g3mmisum 3 }

    g3mmisumTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached 
            data is being retrieved and otherwise 'current'.This object 
            may be set to 'update' to force a refresh of the cache."
        ::= { g3mmisum 4 }

    g3mmisumTcount	OBJECT-TYPE
        SYNTAX    Gauge
        ACCESS    read-only
        STATUS    mandatory
        DESCRIPTION
            "A Gauge object containing the number of data records in the cache."
        ::= { g3mmisum 5 }

    g3mmisumTable	OBJECT-TYPE
        SYNTAX    SEQUENCE OF G3mmisumEntry
        ACCESS    not-accessible
        STATUS    mandatory
        DESCRIPTION
            "A list of g3mmisum entries."
        ::= { g3mmisum 6 }

    g3mmisumEntry	OBJECT-TYPE
        SYNTAX    G3mmisumEntry
        ACCESS    not-accessible
        STATUS    mandatory
        DESCRIPTION
            "A g3mmisum entry containing objects of the
            g3mmisum information sent by the switch."
        INDEX    { g3mmisumMeasHour }
        ::= { g3mmisumTable 1 }

    G3mmisumEntry ::= SEQUENCE {
        g3mmisumMeasHour
            INTEGER,
        g3mmisumYear
            INTEGER,
        g3mmisumMonth
            INTEGER,
        g3mmisumDay
            INTEGER,
        g3mmisumHour
            INTEGER,
        g3mmisumAvailablePorts
            INTEGER,
        g3mmisumAvailableUsage
            DisplayString,
        g3mmisumTotalUsage
            DisplayString,
        g3mmisumTotalAllocation
            INTEGER,
        g3mmisumMMIDenials
            INTEGER,
        g3mmisumOutofService
            INTEGER,
        g3mmisumPercentAPB
            DisplayString,
        g3mmisumPercentBlock
            DisplayString
        }

    g3mmisumMeasHour	OBJECT-TYPE
        SYNTAX    INTEGER
        ACCESS    read-only
        STATUS    mandatory
        DESCRIPTION
            "An object containing the hour for which these measurements apply
            (based on a 24-hour clock)."
        ::= { g3mmisumEntry 1 }

    g3mmisumYear	OBJECT-TYPE
        SYNTAX    INTEGER
        ACCESS    read-only
        STATUS    mandatory
        DESCRIPTION
            "An object containing the Year the command was executed."
        ::= { g3mmisumEntry 2 }

    g3mmisumMonth	OBJECT-TYPE
        SYNTAX    INTEGER
        ACCESS    read-only
        STATUS    mandatory
        DESCRIPTION
            "An object containing the Month the command was executed."
        ::= { g3mmisumEntry 3 }

    g3mmisumDay	OBJECT-TYPE
        SYNTAX    INTEGER
        ACCESS    read-only
        STATUS    mandatory
        DESCRIPTION
            "An object containing the Day the command was executed."
        ::= { g3mmisumEntry 4 }

    g3mmisumHour	OBJECT-TYPE
        SYNTAX    INTEGER
        ACCESS    read-only
        STATUS    mandatory
        DESCRIPTION
            "An object containing the Hour the command was executed."
        ::= { g3mmisumEntry 5 }

    g3mmisumAvailablePorts	OBJECT-TYPE
        SYNTAX    INTEGER
        ACCESS    read-only
        STATUS    mandatory
        DESCRIPTION
            "An object containing the total network MMI ports in the system
            (does not include any MMIs that are cabled to an ESM)."
        ::= { g3mmisumEntry 6 }

    g3mmisumAvailableUsage	OBJECT-TYPE
        SYNTAX    DisplayString (SIZE (0..5))
        ACCESS    read-only
        STATUS    mandatory
        DESCRIPTION
            "An object containing the total time that is available in the system
            for network MMI ports (in CCS units)."
        ::= { g3mmisumEntry 7 }

    g3mmisumTotalUsage	OBJECT-TYPE
        SYNTAX    DisplayString (SIZE (0..5))
        ACCESS    read-only
        STATUS    mandatory
        DESCRIPTION
            "An object containing the total time, in CCS units, that MMI ports
            are in use on a call. It includes the time that the ports are out 
            of service or maintenance busy. Usage is measured from the time
            the port is allocated until it is released."
        ::= { g3mmisumEntry 8 }

    g3mmisumTotalAllocation	OBJECT-TYPE
        SYNTAX    INTEGER
        ACCESS    read-only
        STATUS    mandatory
        DESCRIPTION
            "An object containing the total number of times that an MMI port
            was allocated to a call. Keep in mind that a 2-channel call
            occupies 2 ports, so this number does not necessarily reflect the
            number of calls that took place. Point-to-point calls do not use
            MMI resources, so these allocations are for conversion calls of 
            multimedia conferences."
        ::= { g3mmisumEntry 9 }

    g3mmisumMMIDenials	OBJECT-TYPE
        SYNTAX    INTEGER
        ACCESS    read-only
        STATUS    mandatory
        DESCRIPTION
            "An object containing the total number of times an MMI port was 
            needed but could not be allocated because all ports were busy."
        ::= { g3mmisumEntry 10 }

    g3mmisumOutofService	OBJECT-TYPE
        SYNTAX    INTEGER
        ACCESS    read-only
        STATUS    mandatory
        DESCRIPTION
            "An object containing the total time, in CCS units, that any MMI
            ports were out of service during any part of the measured interval."
        ::= { g3mmisumEntry 11 }

    g3mmisumPercentAPB	OBJECT-TYPE
        SYNTAX    DisplayString (SIZE (0..5))
        ACCESS    read-only
        STATUS    mandatory
        DESCRIPTION
            "An object containing the percentage of time during the measured
            interval that all MMI ports are unavailable to carry a new call."
        ::= { g3mmisumEntry 12 }

    g3mmisumPercentBlock	OBJECT-TYPE
        SYNTAX    DisplayString (SIZE (0..5))
        ACCESS    read-only
        STATUS    mandatory
        DESCRIPTION
            "An object containing the percentage of attempted allocations of
            MMI ports that are not successful (calculated as percent blockage =
            (MMI Denials/(Total Alloc + MMI Denials)) * 100)."
        ::= { g3mmisumEntry 13 }


    -- the g3pkmmisum group

    g3pkmmisumTage	OBJECT-TYPE
        SYNTAX    INTEGER
        ACCESS    read-only
        STATUS    mandatory
        DESCRIPTION
            "The number of timeticks since the peak multimedia interface 
            traffic (MMI) summary data was last extracted from the switch by 
            the Proxy Agent. This object along with the g3pkmmisumTintvl object 
            allows the Network Manager to determine the validity of the peak 
            MMI summary data in the cache and to control when the Proxy Agent 
            extracts the data from the switch."
        ::= { g3pkmmisum 1 }

    g3pkmmisumTintvl	OBJECT-TYPE
        SYNTAX    INTEGER
        ACCESS    read-write
        STATUS    mandatory
        DESCRIPTION
            "An object containing the interval for which the data extracted 
            from the switch is considered valid by the Proxy Agent.
            When a GET or GET-NEXT request for these peak MMI summary 
            objects is received by the agent it uses the g3pkmmisumTage and 
            g3pkmmisumTintvl objects to determine whether it should refresh 
            the cached peak MMI summary data."
        ::= { g3pkmmisum 2 }

    g3pkmmisumTdelay	OBJECT-TYPE
        SYNTAX    INTEGER
        ACCESS    read-only
        STATUS    mandatory
        DESCRIPTION
            "An object containing the delay encountered in updating the 
            cached data."
        ::= { g3pkmmisum 3 }

    g3pkmmisumTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached 
            data is being retrieved and otherwise 'current'.This object 
            may be set to 'update' to force a refresh of the cache."
        ::= { g3pkmmisum 4 }

    g3pkmmisumTcount	OBJECT-TYPE
        SYNTAX    Gauge
        ACCESS    read-only
        STATUS    mandatory
        DESCRIPTION
            "A Gauge object containing the number of data records in the cache."
        ::= { g3pkmmisum 5 }

    g3pkmmisumTable	OBJECT-TYPE
        SYNTAX    SEQUENCE OF G3pkmmisumEntry
        ACCESS    not-accessible
        STATUS    mandatory
        DESCRIPTION
            "A list of g3pkmmisum entries."
        ::= { g3pkmmisum 6 }

    g3pkmmisumEntry	OBJECT-TYPE
        SYNTAX    G3pkmmisumEntry
        ACCESS    not-accessible
        STATUS    mandatory
        DESCRIPTION
            "A g3pkmmisum entry containing objects of the
            g3pkmmisum information sent by the switch."
        INDEX    { g3pkmmisumMeasHour }
        ::= { g3pkmmisumTable 1 }

    G3pkmmisumEntry ::= SEQUENCE {
        g3pkmmisumMeasHour
            INTEGER,
        g3pkmmisumYear
            INTEGER,
        g3pkmmisumMonth
            INTEGER,
        g3pkmmisumDay
            INTEGER,
        g3pkmmisumHour
            INTEGER,
        g3pkmmisumAvailablePorts
            INTEGER,
        g3pkmmisumAvailableUsage
            DisplayString,
        g3pkmmisumTotalUsage
            DisplayString,
        g3pkmmisumTotalAllocation
            INTEGER,
        g3pkmmisumMMIDenials
            INTEGER,
        g3pkmmisumOutofService
            INTEGER,
        g3pkmmisumPercentAPB
            DisplayString,
        g3pkmmisumPercentBlock
            DisplayString
        }

    g3pkmmisumMeasHour	OBJECT-TYPE
        SYNTAX    INTEGER
        ACCESS    read-only
        STATUS    mandatory
        DESCRIPTION
            "An object containing the hour for which these measurements apply
            (based on a 24-hour clock)."
        ::= { g3pkmmisumEntry 1 }

    g3pkmmisumYear	OBJECT-TYPE
        SYNTAX    INTEGER
        ACCESS    read-only
        STATUS    mandatory
        DESCRIPTION
            "An object containing the Year the command was executed."
        ::= { g3pkmmisumEntry 2 }

    g3pkmmisumMonth	OBJECT-TYPE
        SYNTAX    INTEGER
        ACCESS    read-only
        STATUS    mandatory
        DESCRIPTION
            "An object containing the Month the command was executed."
        ::= { g3pkmmisumEntry 3 }

    g3pkmmisumDay	OBJECT-TYPE
        SYNTAX    INTEGER
        ACCESS    read-only
        STATUS    mandatory
        DESCRIPTION
            "An object containing the Day the command was executed."
        ::= { g3pkmmisumEntry 4 }

    g3pkmmisumHour	OBJECT-TYPE
        SYNTAX    INTEGER
        ACCESS    read-only
        STATUS    mandatory
        DESCRIPTION
            "An object containing the Hour the command was executed."
        ::= { g3pkmmisumEntry 5 }

    g3pkmmisumAvailablePorts	OBJECT-TYPE
        SYNTAX    INTEGER
        ACCESS    read-only
        STATUS    mandatory
        DESCRIPTION
            "An object containing the total network MMI ports in the system
            (does not include any MMIs that are cabled to an ESM)."
        ::= { g3pkmmisumEntry 6 }

    g3pkmmisumAvailableUsage	OBJECT-TYPE
        SYNTAX    DisplayString (SIZE (0..5))
        ACCESS    read-only
        STATUS    mandatory
        DESCRIPTION
            "An object containing the total time that is available in the system
            for network MMI ports (in CCS units)."
        ::= { g3pkmmisumEntry 7 }

    g3pkmmisumTotalUsage	OBJECT-TYPE
        SYNTAX    DisplayString (SIZE (0..5))
        ACCESS    read-only
        STATUS    mandatory
        DESCRIPTION
            "An object containing the total time, in CCS units, that MMI ports
            are in use on a call. It includes the time that the ports are out 
            of service or maintenance busy. Usage is measured from the time
            the port is allocated until it is released."
        ::= { g3pkmmisumEntry 8 }

    g3pkmmisumTotalAllocation	OBJECT-TYPE
        SYNTAX    INTEGER
        ACCESS    read-only
        STATUS    mandatory
        DESCRIPTION
            "An object containing the total number of times that an MMI port
            was allocated to a call. Keep in mind that a 2-channel call
            occupies 2 ports, so this number does not necessarily reflect the
            number of calls that took place. Point-to-point calls do not use
            MMI resources, so these allocations are for conversion calls of 
            multimedia conferences."
        ::= { g3pkmmisumEntry 9 }

    g3pkmmisumMMIDenials	OBJECT-TYPE
        SYNTAX    INTEGER
        ACCESS    read-only
        STATUS    mandatory
        DESCRIPTION
            "An object containing the total number of times an MMI port was 
            needed but could not be allocated because all ports were busy."
        ::= { g3pkmmisumEntry 10 }

    g3pkmmisumOutofService	OBJECT-TYPE
        SYNTAX    INTEGER
        ACCESS    read-only
        STATUS    mandatory
        DESCRIPTION
            "An object containing the total time, in CCS units, that any MMI
            ports were out of service during any part of the measured interval."
        ::= { g3pkmmisumEntry 11 }

    g3pkmmisumPercentAPB	OBJECT-TYPE
        SYNTAX    DisplayString (SIZE (0..5))
        ACCESS    read-only
        STATUS    mandatory
        DESCRIPTION
            "An object containing the percentage of time during the measured
            interval that all MMI ports are unavailable to carry a new call."
        ::= { g3pkmmisumEntry 12 }

    g3pkmmisumPercentBlock	OBJECT-TYPE
        SYNTAX    DisplayString (SIZE (0..5))
        ACCESS    read-only
        STATUS    mandatory
        DESCRIPTION
            "An object containing the percentage of attempted allocations of
            MMI ports that are not successful (calculated as percent blockage =
            (MMI Denials/(Total Alloc + MMI Denials)) * 100)."
        ::= { g3pkmmisumEntry 13 }


    -- the g3esmsum group

    g3esmsumTage	OBJECT-TYPE
        SYNTAX    INTEGER
        ACCESS    read-only
        STATUS    mandatory
        DESCRIPTION
            "The number of timeticks since the hourly expansion services module (ESM)
            summary data was last extracted from the switch by the Proxy 
            Agent.This object along with the g3esmsumTintvl object allows 
            the Network Manager to determine the validity of the hourly ESM summary 
            data in the cache and to control when the Proxy Agent extracts the 
            data from the switch."
        ::= { g3esmsum 1 }

    g3esmsumTintvl	OBJECT-TYPE
        SYNTAX    INTEGER
        ACCESS    read-write
        STATUS    mandatory
        DESCRIPTION
            "An object containing the interval for which the data extracted 
            from the switch is considered valid by the Proxy Agent.
            When a GET or GET-NEXT request for these hourly ESM summary 
            objects is received by the agent it uses the g3esmsumTage and 
            g3esmsumTintvl objects to determine whether it should refresh 
            the cached hourly ESM summary data."
        ::= { g3esmsum 2 }

    g3esmsumTdelay	OBJECT-TYPE
        SYNTAX    INTEGER
        ACCESS    read-only
        STATUS    mandatory
        DESCRIPTION
            "An object containing the delay encountered in updating the 
            cached data."
        ::= { g3esmsum 3 }

    g3esmsumTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached 
            data is being retrieved and otherwise 'current'.This object 
            may be set to 'update' to force a refresh of the cache."
        ::= { g3esmsum 4 }

    g3esmsumTcount	OBJECT-TYPE
        SYNTAX    Gauge
        ACCESS    read-only
        STATUS    mandatory
        DESCRIPTION
            "A Gauge object containing the number of data records in the cache."
        ::= { g3esmsum 5 }

    g3esmsumTable	OBJECT-TYPE
        SYNTAX    SEQUENCE OF G3esmsumEntry
        ACCESS    not-accessible
        STATUS    mandatory
        DESCRIPTION
            "A list of g3esmsum entries."
        ::= { g3esmsum 6 }

    g3esmsumEntry	OBJECT-TYPE
        SYNTAX    G3esmsumEntry
        ACCESS    not-accessible
        STATUS    mandatory
        DESCRIPTION
            "A g3esmsum entry containing objects of the
            g3esmsum information sent by the switch."
        INDEX    { g3esmsumMeasHour }
        ::= { g3esmsumTable 1 }

    G3esmsumEntry ::= SEQUENCE {
        g3esmsumMeasHour
            INTEGER,
        g3esmsumYear
            INTEGER,
        g3esmsumMonth
            INTEGER,
        g3esmsumDay
            INTEGER,
        g3esmsumHour
            INTEGER,
        g3esmsumAvailablePorts
            INTEGER,
        g3esmsumAvailableUsage
            DisplayString,
        g3esmsumTotalUsage
            DisplayString,
        g3esmsumTotalAllocation
            INTEGER,
        g3esmsumESMDenials
            INTEGER,
        g3esmsumOutofService
            INTEGER,
        g3esmsumPercentAPB
            DisplayString,
        g3esmsumPercentBlock
            DisplayString
        }

    g3esmsumMeasHour	OBJECT-TYPE
        SYNTAX    INTEGER
        ACCESS    read-only
        STATUS    mandatory
        DESCRIPTION
            "An object containing the hour for which these measurements apply
            (based on a 24-hour clock)."
        ::= { g3esmsumEntry 1 }

    g3esmsumYear	OBJECT-TYPE
        SYNTAX    INTEGER
        ACCESS    read-only
        STATUS    mandatory
        DESCRIPTION
            "An object containing the Year the command was executed."
        ::= { g3esmsumEntry 2 }

    g3esmsumMonth	OBJECT-TYPE
        SYNTAX    INTEGER
        ACCESS    read-only
        STATUS    mandatory
        DESCRIPTION
            "An object containing the Month the command was executed."
        ::= { g3esmsumEntry 3 }

    g3esmsumDay	OBJECT-TYPE
        SYNTAX    INTEGER
        ACCESS    read-only
        STATUS    mandatory
        DESCRIPTION
            "An object containing the Day the command was executed."
        ::= { g3esmsumEntry 4 }

    g3esmsumHour	OBJECT-TYPE
        SYNTAX    INTEGER
        ACCESS    read-only
        STATUS    mandatory
        DESCRIPTION
            "An object containing the Hour the command was executed."
        ::= { g3esmsumEntry 5 }

    g3esmsumAvailablePorts	OBJECT-TYPE
        SYNTAX    INTEGER
        ACCESS    read-only
        STATUS    mandatory
        DESCRIPTION
            "An object containing the total network ESM-MMI ports in the system."
        ::= { g3esmsumEntry 6 }

    g3esmsumAvailableUsage	OBJECT-TYPE
        SYNTAX    DisplayString (SIZE (0..5))
        ACCESS    read-only
        STATUS    mandatory
        DESCRIPTION
            "An object containing the total time that is available in the system
            for network ESM-MMI ports (in CCS units)."
        ::= { g3esmsumEntry 7 }

    g3esmsumTotalUsage	OBJECT-TYPE
        SYNTAX    DisplayString (SIZE (0..5))
        ACCESS    read-only
        STATUS    mandatory
        DESCRIPTION
            "An object containing the total time, in CCS units, that ESM-MMI ports
            are in use on a call. It includes the time that the ports are out 
            of service or maintenance busy. Usage is measured from the time
            the port is allocated until it is released."
        ::= { g3esmsumEntry 8 }

    g3esmsumTotalAllocation	OBJECT-TYPE
        SYNTAX    INTEGER
        ACCESS    read-only
        STATUS    mandatory
        DESCRIPTION
            "An object containing the total number of times that an ESM-MMI port
            was allocated to a call."
        ::= { g3esmsumEntry 9 }

    g3esmsumESMDenials	OBJECT-TYPE
        SYNTAX    INTEGER
        ACCESS    read-only
        STATUS    mandatory
        DESCRIPTION
            "An object containing the total number of times an ESM-MMI port was 
            needed but could not be allocated because all ports were busy."
        ::= { g3esmsumEntry 10 }

    g3esmsumOutofService	OBJECT-TYPE
        SYNTAX    INTEGER
        ACCESS    read-only
        STATUS    mandatory
        DESCRIPTION
            "An object containing the total time, in CCS units, that any ESM-MMI
            ports were out of service during any part of the measured interval."
        ::= { g3esmsumEntry 11 }

    g3esmsumPercentAPB	OBJECT-TYPE
        SYNTAX    DisplayString (SIZE (0..5))
        ACCESS    read-only
        STATUS    mandatory
        DESCRIPTION
            "An object containing the percentage of time during the measured
            interval that all ESM-MMI ports are unavailable to carry a new call."
        ::= { g3esmsumEntry 12 }

    g3esmsumPercentBlock	OBJECT-TYPE
        SYNTAX    DisplayString (SIZE (0..5))
        ACCESS    read-only
        STATUS    mandatory
        DESCRIPTION
            "An object containing the percentage of attempted allocations of
            ESM-MMI ports that are not successful (calculated as percent blockage =
            ((ESM Denials/(Total Alloc + ESM Denials)) * 100))."
        ::= { g3esmsumEntry 13 }


    -- the g3pkesmsum group

    g3pkesmsumTage	OBJECT-TYPE
        SYNTAX    INTEGER
        ACCESS    read-only
        STATUS    mandatory
        DESCRIPTION
            "The number of timeticks since the peak expansion services module (ESM)
            summary data was last extracted from the switch by the Proxy 
            Agent.This object along with the g3pkesmsumTintvl object allows 
            the Network Manager to determine the validity of the peak ESM summary 
            data in the cache and to control when the Proxy Agent extracts the 
            data from the switch."
        ::= { g3pkesmsum 1 }

    g3pkesmsumTintvl	OBJECT-TYPE
        SYNTAX    INTEGER
        ACCESS    read-write
        STATUS    mandatory
        DESCRIPTION
            "An object containing the interval for which the data extracted 
            from the switch is considered valid by the Proxy Agent.
            When a GET or GET-NEXT request for these peak ESM summary 
            objects is received by the agent it uses the g3pkesmsumTage and 
            g3pkesmsumTintvl objects to determine whether it should refresh 
            the cached peak ESM summary data."
        ::= { g3pkesmsum 2 }

    g3pkesmsumTdelay	OBJECT-TYPE
        SYNTAX    INTEGER
        ACCESS    read-only
        STATUS    mandatory
        DESCRIPTION
            "An object containing the delay encountered in updating the 
            cached data."
        ::= { g3pkesmsum 3 }

    g3pkesmsumTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached 
            data is being retrieved and otherwise 'current'.This object 
            may be set to 'update' to force a refresh of the cache."
        ::= { g3pkesmsum 4 }

    g3pkesmsumTcount	OBJECT-TYPE
        SYNTAX    Gauge
        ACCESS    read-only
        STATUS    mandatory
        DESCRIPTION
            "A Gauge object containing the number of data records in the cache."
        ::= { g3pkesmsum 5 }

    g3pkesmsumTable	OBJECT-TYPE
        SYNTAX    SEQUENCE OF G3pkesmsumEntry
        ACCESS    not-accessible
        STATUS    mandatory
        DESCRIPTION
            "A list of g3pkesmsum entries."
        ::= { g3pkesmsum 6 }

    g3pkesmsumEntry	OBJECT-TYPE
        SYNTAX    G3pkesmsumEntry
        ACCESS    not-accessible
        STATUS    mandatory
        DESCRIPTION
            "A g3pkesmsum entry containing objects of the
            g3pkesmsum information sent by the switch."
        INDEX    { g3pkesmsumMeasHour }
        ::= { g3pkesmsumTable 1 }

    G3pkesmsumEntry ::= SEQUENCE {
        g3pkesmsumMeasHour
            INTEGER,
        g3pkesmsumYear
            INTEGER,
        g3pkesmsumMonth
            INTEGER,
        g3pkesmsumDay
            INTEGER,
        g3pkesmsumHour
            INTEGER,
        g3pkesmsumAvailablePorts
            INTEGER,
        g3pkesmsumAvailableUsage
            DisplayString,
        g3pkesmsumTotalUsage
            DisplayString,
        g3pkesmsumTotalAllocation
            INTEGER,
        g3pkesmsumESMDenials
            INTEGER,
        g3pkesmsumOutofService
            INTEGER,
        g3pkesmsumPercentAPB
            DisplayString,
        g3pkesmsumPercentBlock
            DisplayString
        }

    g3pkesmsumMeasHour	OBJECT-TYPE
        SYNTAX    INTEGER
        ACCESS    read-only
        STATUS    mandatory
        DESCRIPTION
            "An object containing the hour for which these measurements apply
            (based on a 24-hour clock)."
        ::= { g3pkesmsumEntry 1 }

    g3pkesmsumYear	OBJECT-TYPE
        SYNTAX    INTEGER
        ACCESS    read-only
        STATUS    mandatory
        DESCRIPTION
            "An object containing the Year the command was executed."
        ::= { g3pkesmsumEntry 2 }

    g3pkesmsumMonth	OBJECT-TYPE
        SYNTAX    INTEGER
        ACCESS    read-only
        STATUS    mandatory
        DESCRIPTION
            "An object containing the Month the command was executed."
        ::= { g3pkesmsumEntry 3 }

    g3pkesmsumDay	OBJECT-TYPE
        SYNTAX    INTEGER
        ACCESS    read-only
        STATUS    mandatory
        DESCRIPTION
            "An object containing the Day the command was executed."
        ::= { g3pkesmsumEntry 4 }

    g3pkesmsumHour	OBJECT-TYPE
        SYNTAX    INTEGER
        ACCESS    read-only
        STATUS    mandatory
        DESCRIPTION
            "An object containing the Hour the command was executed."
        ::= { g3pkesmsumEntry 5 }

    g3pkesmsumAvailablePorts	OBJECT-TYPE
        SYNTAX    INTEGER
        ACCESS    read-only
        STATUS    mandatory
        DESCRIPTION
            "An object containing the total network ESM-MMI ports in the system."
        ::= { g3pkesmsumEntry 6 }

    g3pkesmsumAvailableUsage	OBJECT-TYPE
        SYNTAX    DisplayString (SIZE (0..5))
        ACCESS    read-only
        STATUS    mandatory
        DESCRIPTION
            "An object containing the total time that is available in the system
            for network ESM-MMI ports (in CCS units)."
        ::= { g3pkesmsumEntry 7 }

    g3pkesmsumTotalUsage	OBJECT-TYPE
        SYNTAX    DisplayString (SIZE (0..5))
        ACCESS    read-only
        STATUS    mandatory
        DESCRIPTION
            "An object containing the total time, in CCS units, that ESM-MMI ports
            are in use on a call. It includes the time that the ports are out 
            of service or maintenance busy. Usage is measured from the time
            the port is allocated until it is released."
        ::= { g3pkesmsumEntry 8 }

    g3pkesmsumTotalAllocation	OBJECT-TYPE
        SYNTAX    INTEGER
        ACCESS    read-only
        STATUS    mandatory
        DESCRIPTION
            "An object containing the total number of times that an ESM-MMI port
            was allocated to a call."
        ::= { g3pkesmsumEntry 9 }

    g3pkesmsumESMDenials	OBJECT-TYPE
        SYNTAX    INTEGER
        ACCESS    read-only
        STATUS    mandatory
        DESCRIPTION
            "An object containing the total number of times an ESM-MMI port was 
            needed but could not be allocated because all ports were busy."
        ::= { g3pkesmsumEntry 10 }

    g3pkesmsumOutofService	OBJECT-TYPE
        SYNTAX    INTEGER
        ACCESS    read-only
        STATUS    mandatory
        DESCRIPTION
            "An object containing the total time, in CCS units, that any ESM-MMI
            ports were out of service during any part of the measured interval."
        ::= { g3pkesmsumEntry 11 }

    g3pkesmsumPercentAPB	OBJECT-TYPE
        SYNTAX    DisplayString (SIZE (0..5))
        ACCESS    read-only
        STATUS    mandatory
        DESCRIPTION
            "An object containing the percentage of time during the measured
            interval that all ESM-MMI ports are unavailable to carry a new call."
        ::= { g3pkesmsumEntry 12 }

    g3pkesmsumPercentBlock	OBJECT-TYPE
        SYNTAX    DisplayString (SIZE (0..5))
        ACCESS    read-only
        STATUS    mandatory
        DESCRIPTION
            "An object containing the percentage of attempted allocations of
            ESM-MMI ports that are not successful (calculated as percent blockage =
            ((ESM Denials/(Total Alloc + ESM Denials)) * 100))."
        ::= { g3pkesmsumEntry 13 }


    -- the g3voicesum group

    g3voicesumTage	OBJECT-TYPE
        SYNTAX    INTEGER
        ACCESS    read-only
        STATUS    mandatory
        DESCRIPTION
            "The number of timeticks since the hourly voice conditioner (VC)
            summary data was last extracted from the switch by the Proxy 
            Agent.This object along with the g3voicesumTintvl object allows 
            the Network Manager to determine the validity of the hourly VC
            summary data in the cache and to control when the 
            Proxy Agent extracts the data from the switch."
        ::= { g3voicesum 1 }

    g3voicesumTintvl	OBJECT-TYPE
        SYNTAX    INTEGER
        ACCESS    read-write
        STATUS    mandatory
        DESCRIPTION
            "An object containing the interval for which the data extracted 
            from the switch is considered valid by the Proxy Agent.
            When a GET or GET-NEXT request for these hourly VC 
            summary objects is received by the agent it uses the g3voicesumTage 
            and g3voicesumTintvl objects to determine whether it should refresh 
            the cached hourly VC summary data."
        ::= { g3voicesum 2 }

    g3voicesumTdelay	OBJECT-TYPE
        SYNTAX    INTEGER
        ACCESS    read-only
        STATUS    mandatory
        DESCRIPTION
            "An object containing the delay encountered in updating the 
            cached data."
        ::= { g3voicesum 3 }

    g3voicesumTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached 
            data is being retrieved and otherwise 'current'.This object 
            may be set to 'update' to force a refresh of the cache."
        ::= { g3voicesum 4 }

    g3voicesumTcount	OBJECT-TYPE
        SYNTAX    Gauge
        ACCESS    read-only
        STATUS    mandatory
        DESCRIPTION
            "A Gauge object containing the number of data records in the cache."
        ::= { g3voicesum 5 }

    g3voicesumTable	OBJECT-TYPE
        SYNTAX    SEQUENCE OF G3voicesumEntry
        ACCESS    not-accessible
        STATUS    mandatory
        DESCRIPTION
            "A list of g3voicesum entries."
        ::= { g3voicesum 6 }

    g3voicesumEntry	OBJECT-TYPE
        SYNTAX    G3voicesumEntry
        ACCESS    not-accessible
        STATUS    mandatory
        DESCRIPTION
            "A g3voicesum entry containing objects of the
            g3voicesum information sent by the switch."
        INDEX    { g3voicesumMeasHour }
        ::= { g3voicesumTable 1 }

    G3voicesumEntry ::= SEQUENCE {
        g3voicesumMeasHour
            INTEGER,
        g3voicesumYear
            INTEGER,
        g3voicesumMonth
            INTEGER,
        g3voicesumDay
            INTEGER,
        g3voicesumHour
            INTEGER,
        g3voicesumAvailablePorts
            INTEGER,
        g3voicesumAvailableUsage
            DisplayString,
        g3voicesumH320Usage
            DisplayString,
        g3voicesumVoiceUsage
            DisplayString,
        g3voicesumTotalUsage
            DisplayString,
        g3voicesumH320Allocation
            INTEGER,
        g3voicesumVoiceAllocation
            INTEGER,
        g3voicesumTotalAllocation
            INTEGER,
        g3voicesumH320Denials
            INTEGER,
        g3voicesumVoiceDenials
            INTEGER,
        g3voicesumTotalDenials
            INTEGER,
        g3voicesumOutofService
            INTEGER,
        g3voicesumPercentAPB
            DisplayString,
        g3voicesumPercentBlock
            DisplayString
        }

    g3voicesumMeasHour	OBJECT-TYPE
        SYNTAX    INTEGER
        ACCESS    read-only
        STATUS    mandatory
        DESCRIPTION
            "An object containing the hour for which these measurements apply
            (based on a 24-hour clock)."
        ::= { g3voicesumEntry 1 }

    g3voicesumYear	OBJECT-TYPE
        SYNTAX    INTEGER
        ACCESS    read-only
        STATUS    mandatory
        DESCRIPTION
            "An object containing the Year the command was executed."
        ::= { g3voicesumEntry 2 }

    g3voicesumMonth	OBJECT-TYPE
        SYNTAX    INTEGER
        ACCESS    read-only
        STATUS    mandatory
        DESCRIPTION
            "An object containing the Month the command was executed."
        ::= { g3voicesumEntry 3 }

    g3voicesumDay	OBJECT-TYPE
        SYNTAX    INTEGER
        ACCESS    read-only
        STATUS    mandatory
        DESCRIPTION
            "An object containing the Day the command was executed."
        ::= { g3voicesumEntry 4 }

    g3voicesumHour	OBJECT-TYPE
        SYNTAX    INTEGER
        ACCESS    read-only
        STATUS    mandatory
        DESCRIPTION
            "An object containing the Hour the command was executed."
        ::= { g3voicesumEntry 5 }

    g3voicesumAvailablePorts	OBJECT-TYPE
        SYNTAX    INTEGER
        ACCESS    read-only
        STATUS    mandatory
        DESCRIPTION
            "An object containing the total number of VC ports in the system."
        ::= { g3voicesumEntry 6 }

    g3voicesumAvailableUsage	OBJECT-TYPE
        SYNTAX    DisplayString (SIZE (0..5))
        ACCESS    read-only
        STATUS    mandatory
        DESCRIPTION
            "An object containing the total time, in CCS units, that all VC
            ports are available in the system (calculated as number of MMI
            ports * 36)."
        ::= { g3voicesumEntry 7 }

    g3voicesumH320Usage	OBJECT-TYPE
        SYNTAX    DisplayString (SIZE (0..5))
        ACCESS    read-only
        STATUS    mandatory
        DESCRIPTION
            "An object containing the total time that VC ports are allocated
            to H320 endpoints."
        ::= { g3voicesumEntry 8 }

    g3voicesumVoiceUsage	OBJECT-TYPE
        SYNTAX    DisplayString (SIZE (0..5))
        ACCESS    read-only
        STATUS    mandatory
        DESCRIPTION
            "An object containing the total time that VC ports are allocated
            to voice endpoints."
        ::= { g3voicesumEntry 9 }

    g3voicesumTotalUsage	OBJECT-TYPE
        SYNTAX    DisplayString (SIZE (0..5))
        ACCESS    read-only
        STATUS    mandatory
        DESCRIPTION
            "An object containing the total time, in CCS units, that VC ports
            are unavailable to carry a new call. This includes time that the
            ports are busy on a call, out or service, or maintenance busy.
            Measured from the time that the port is allocated until it is
            released."
        ::= { g3voicesumEntry 10 }

    g3voicesumH320Allocation	OBJECT-TYPE
        SYNTAX    INTEGER
        ACCESS    read-only
        STATUS    mandatory
        DESCRIPTION
            "An object containing the total number of times a VC port was 
            allocated to a H320 call."
        ::= { g3voicesumEntry 11 }

    g3voicesumVoiceAllocation	OBJECT-TYPE
        SYNTAX    INTEGER
        ACCESS    read-only
        STATUS    mandatory
        DESCRIPTION
            "An object containing the total number of times a VC port was
            allocated to a voice call."
        ::= { g3voicesumEntry 12 }

    g3voicesumTotalAllocation	OBJECT-TYPE
        SYNTAX    INTEGER
        ACCESS    read-only
        STATUS    mandatory
        DESCRIPTION
            "An object containing the total number of times a VC port was
            allocated to any call. Each B-channel used on a multimedia call
            counts as one allocation."
        ::= { g3voicesumEntry 13 }

    g3voicesumH320Denials	OBJECT-TYPE
        SYNTAX    INTEGER
        ACCESS    read-only
        STATUS    mandatory
        DESCRIPTION
            "An object containing the number of times a port was needed for an
            H320 call, but was not available."
        ::= { g3voicesumEntry 14 }

    g3voicesumVoiceDenials	OBJECT-TYPE
        SYNTAX    INTEGER
        ACCESS    read-only
        STATUS    mandatory
        DESCRIPTION
            "An object containing the number of times a port was need for a
            voice call, but was not available."
        ::= { g3voicesumEntry 15 }

    g3voicesumTotalDenials	OBJECT-TYPE
        SYNTAX    INTEGER
        ACCESS    read-only
        STATUS    mandatory
        DESCRIPTION
            "An object containing the total number of times a VC port was needed
            for any call, but was not allocated because all VC ports were busy."
        ::= { g3voicesumEntry 16 }

    g3voicesumOutofService	OBJECT-TYPE
        SYNTAX    INTEGER
        ACCESS    read-only
        STATUS    mandatory
        DESCRIPTION
            "An object containing the total time, in CCS units, that any VC
            ports were out of service during any part of the measured interval."
        ::= { g3voicesumEntry 17 }

    g3voicesumPercentAPB	OBJECT-TYPE
        SYNTAX    DisplayString (SIZE (0..5))
        ACCESS    read-only
        STATUS    mandatory
        DESCRIPTION
            "An object containing the percentage of time during the measured
            interval that all VC ports are unavailable to carry a new call."
        ::= { g3voicesumEntry 18 }

    g3voicesumPercentBlock	OBJECT-TYPE
        SYNTAX    DisplayString (SIZE (0..5))
        ACCESS    read-only
        STATUS    mandatory
        DESCRIPTION
            "An object containing the percentage of attempted allocations of
            VC ports that are not successful. This value is calculated as
            percent blockage = ((Total VC Denials / (Total Alloc + Total VC
            Denials)) * 100)."
        ::= { g3voicesumEntry 19 }


    -- the g3pkvoicesum group

    g3pkvoicesumTage	OBJECT-TYPE
        SYNTAX    INTEGER
        ACCESS    read-only
        STATUS    mandatory
        DESCRIPTION
            "The number of timeticks since the peak voice conditioner (VC)
            summary data was last extracted from the switch by the Proxy 
            Agent.This object along with the g3pkvoicesumTintvl object allows 
            the Network Manager to determine the validity of the peak VC
            summary data in the cache and to control when the 
            Proxy Agent extracts the data from the switch."
        ::= { g3pkvoicesum 1 }

    g3pkvoicesumTintvl	OBJECT-TYPE
        SYNTAX    INTEGER
        ACCESS    read-write
        STATUS    mandatory
        DESCRIPTION
            "An object containing the interval for which the data extracted 
            from the switch is considered valid by the Proxy Agent.
            When a GET or GET-NEXT request for these peak VC summary 
            objects is received by the agent it uses the g3pkvoicesumTage and 
            g3pkvoicesumTintvl objects to determine whether it should refresh 
            the cached peak VC summary data."
        ::= { g3pkvoicesum 2 }

    g3pkvoicesumTdelay	OBJECT-TYPE
        SYNTAX    INTEGER
        ACCESS    read-only
        STATUS    mandatory
        DESCRIPTION
            "An object containing the delay encountered in updating the 
            cached data."
        ::= { g3pkvoicesum 3 }

    g3pkvoicesumTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached 
            data is being retrieved and otherwise 'current'.This object 
            may be set to 'update' to force a refresh of the cache."
        ::= { g3pkvoicesum 4 }

    g3pkvoicesumTcount	OBJECT-TYPE
        SYNTAX    Gauge
        ACCESS    read-only
        STATUS    mandatory
        DESCRIPTION
            "A Gauge object containing the number of data records in the cache."
        ::= { g3pkvoicesum 5 }

    g3pkvoicesumTable	OBJECT-TYPE
        SYNTAX    SEQUENCE OF G3pkvoicesumEntry
        ACCESS    not-accessible
        STATUS    mandatory
        DESCRIPTION
            "A list of g3pkvoicesum entries."
        ::= { g3pkvoicesum 6 }

    g3pkvoicesumEntry	OBJECT-TYPE
        SYNTAX    G3pkvoicesumEntry
        ACCESS    not-accessible
        STATUS    mandatory
        DESCRIPTION
            "A g3pkvoicesum entry containing objects of the
            g3pkvoicesum information sent by the switch."
        INDEX    { g3pkvoicesumMeasHour }
        ::= { g3pkvoicesumTable 1 }

    G3pkvoicesumEntry ::= SEQUENCE {
        g3pkvoicesumMeasHour
            INTEGER,
        g3pkvoicesumYear
            INTEGER,
        g3pkvoicesumMonth
            INTEGER,
        g3pkvoicesumDay
            INTEGER,
        g3pkvoicesumHour
            INTEGER,
        g3pkvoicesumAvailablePorts
            INTEGER,
        g3pkvoicesumAvailableUsage
            DisplayString,
        g3pkvoicesumH320Usage
            DisplayString,
        g3pkvoicesumVoiceUsage
            DisplayString,
        g3pkvoicesumTotalUsage
            DisplayString,
        g3pkvoicesumH320Allocation
            INTEGER,
        g3pkvoicesumVoiceAllocation
            INTEGER,
        g3pkvoicesumTotalAllocation
            INTEGER,
        g3pkvoicesumH320Denials
            INTEGER,
        g3pkvoicesumVoiceDenials
            INTEGER,
        g3pkvoicesumTotalDenials
            INTEGER,
        g3pkvoicesumOutofService
            INTEGER,
        g3pkvoicesumPercentAPB
            DisplayString,
        g3pkvoicesumPercentBlock
            DisplayString
        }

    g3pkvoicesumMeasHour	OBJECT-TYPE
        SYNTAX    INTEGER
        ACCESS    read-only
        STATUS    mandatory
        DESCRIPTION
            "An object containing the hour for which these measurements apply
            (based on a 24-hour clock)."
        ::= { g3pkvoicesumEntry 1 }

    g3pkvoicesumYear	OBJECT-TYPE
        SYNTAX    INTEGER
        ACCESS    read-only
        STATUS    mandatory
        DESCRIPTION
            "An object containing the Year the command was executed."
        ::= { g3pkvoicesumEntry 2 }

    g3pkvoicesumMonth	OBJECT-TYPE
        SYNTAX    INTEGER
        ACCESS    read-only
        STATUS    mandatory
        DESCRIPTION
            "An object containing the Month the command was executed."
        ::= { g3pkvoicesumEntry 3 }

    g3pkvoicesumDay	OBJECT-TYPE
        SYNTAX    INTEGER
        ACCESS    read-only
        STATUS    mandatory
        DESCRIPTION
            "An object containing the Day the command was executed."
        ::= { g3pkvoicesumEntry 4 }

    g3pkvoicesumHour	OBJECT-TYPE
        SYNTAX    INTEGER
        ACCESS    read-only
        STATUS    mandatory
        DESCRIPTION
            "An object containing the Hour the command was executed."
        ::= { g3pkvoicesumEntry 5 }

    g3pkvoicesumAvailablePorts	OBJECT-TYPE
        SYNTAX    INTEGER
        ACCESS    read-only
        STATUS    mandatory
        DESCRIPTION
            "An object containing the total number of VC ports in the system."
        ::= { g3pkvoicesumEntry 6 }

    g3pkvoicesumAvailableUsage	OBJECT-TYPE
        SYNTAX    DisplayString (SIZE (0..5))
        ACCESS    read-only
        STATUS    mandatory
        DESCRIPTION
            "An object containing the total time, in CCS units, that all VC
            ports are available in the system (calculated as number of MMI
            ports * 36)."
        ::= { g3pkvoicesumEntry 7 }

    g3pkvoicesumH320Usage	OBJECT-TYPE
        SYNTAX    DisplayString (SIZE (0..5))
        ACCESS    read-only
        STATUS    mandatory
        DESCRIPTION
            "An object containing the total time that VC ports are allocated
            to H320 endpoints."
        ::= { g3pkvoicesumEntry 8 }

    g3pkvoicesumVoiceUsage	OBJECT-TYPE
        SYNTAX    DisplayString (SIZE (0..5))
        ACCESS    read-only
        STATUS    mandatory
        DESCRIPTION
            "An object containing the total time that VC ports are allocated
            to voice endpoints."
        ::= { g3pkvoicesumEntry 9 }

    g3pkvoicesumTotalUsage	OBJECT-TYPE
        SYNTAX    DisplayString (SIZE (0..5))
        ACCESS    read-only
        STATUS    mandatory
        DESCRIPTION
            "An object containing the total time, in CCS units, that VC ports
            are unavailable to carry a new call. This includes time that the
            ports are busy on a call, out or service, or maintenance busy.
            Measured from the time that the port is allocated until it is
            released."
        ::= { g3pkvoicesumEntry 10 }

    g3pkvoicesumH320Allocation	OBJECT-TYPE
        SYNTAX    INTEGER
        ACCESS    read-only
        STATUS    mandatory
        DESCRIPTION
            "An object containing the total number of times a VC port was 
            allocated to a H320 call."
        ::= { g3pkvoicesumEntry 11 }

    g3pkvoicesumVoiceAllocation	OBJECT-TYPE
        SYNTAX    INTEGER
        ACCESS    read-only
        STATUS    mandatory
        DESCRIPTION
            "An object containing the total number of times a VC port was
            allocated to a voice call."
        ::= { g3pkvoicesumEntry 12 }

    g3pkvoicesumTotalAllocation	OBJECT-TYPE
        SYNTAX    INTEGER
        ACCESS    read-only
        STATUS    mandatory
        DESCRIPTION
            "An object containing the total number of times a VC port was
            allocated to any call. Each B-channel used on a multimedia call
            counts as one allocation."
        ::= { g3pkvoicesumEntry 13 }

    g3pkvoicesumH320Denials	OBJECT-TYPE
        SYNTAX    INTEGER
        ACCESS    read-only
        STATUS    mandatory
        DESCRIPTION
            "An object containing the number of times a port was needed for an
            H320 call, but was not available."
        ::= { g3pkvoicesumEntry 14 }

    g3pkvoicesumVoiceDenials	OBJECT-TYPE
        SYNTAX    INTEGER
        ACCESS    read-only
        STATUS    mandatory
        DESCRIPTION
            "An object containing the number of times a port was need for a
            voice call, but was not available."
        ::= { g3pkvoicesumEntry 15 }

    g3pkvoicesumTotalDenials	OBJECT-TYPE
        SYNTAX    INTEGER
        ACCESS    read-only
        STATUS    mandatory
        DESCRIPTION
            "An object containing the total number of times a VC port was needed
            for any call, but was not allocated because all VC ports were busy."
        ::= { g3pkvoicesumEntry 16 }

    g3pkvoicesumOutofService	OBJECT-TYPE
        SYNTAX    INTEGER
        ACCESS    read-only
        STATUS    mandatory
        DESCRIPTION
            "An object containing the total time, in CCS units, that any VC
            ports were out of service during any part of the measured interval."
        ::= { g3pkvoicesumEntry 17 }

    g3pkvoicesumPercentAPB	OBJECT-TYPE
        SYNTAX    DisplayString (SIZE (0..5))
        ACCESS    read-only
        STATUS    mandatory
        DESCRIPTION
            "An object containing the percentage of time during the measured
            interval that all VC ports are unavailable to carry a new call."
        ::= { g3pkvoicesumEntry 18 }

    g3pkvoicesumPercentBlock	OBJECT-TYPE
        SYNTAX    DisplayString (SIZE (0..5))
        ACCESS    read-only
        STATUS    mandatory
        DESCRIPTION
            "An object containing the percentage of attempted allocations of
            VC ports that are not successful. This value is calculated as
            percent blockage = ((Total VC Denials / (Total Alloc + Total VC
            Denials)) * 100)."
        ::= { g3pkvoicesumEntry 19 }


    -- the g3ipintlist group

    g3ipintlistTage	OBJECT-TYPE
        SYNTAX    INTEGER
        ACCESS    read-only
        STATUS    mandatory
        DESCRIPTION
            "The number of timeticks since the ip interface data
            was last extracted from the switch by the Proxy 
            Agent.This object along with the g3ipintlistTintvl object allows 
            the Network Manager to determine the validity of the ip interface
            data in the cache and to control when the Proxy Agent extracts 
            the data from the switch."
        ::= { g3ipintlist 1 }

    g3ipintlistTintvl	OBJECT-TYPE
        SYNTAX    INTEGER
        ACCESS    read-write
        STATUS    mandatory
        DESCRIPTION
            "An object containing the interval for which the data extracted 
            from the switch is considered valid by the Proxy Agent.
            When a GET or GET-NEXT request for these ip interface
            objects is received by the agent it uses the g3ipintlistTage and 
            g3ipintlistTintvl objects to determine whether it should refresh 
            the cached ip interface data."
        ::= { g3ipintlist 2 }

    g3ipintlistTdelay	OBJECT-TYPE
        SYNTAX    INTEGER
        ACCESS    read-only
        STATUS    mandatory
        DESCRIPTION
            "An object containing the delay encountered in updating the cached data"
        ::= { g3ipintlist 3 }

    g3ipintlistTretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3ipintlist 4 }

    g3ipintlistTcount	OBJECT-TYPE
        SYNTAX    Gauge
        ACCESS    read-only
        STATUS    mandatory
        DESCRIPTION
            "A Gauge object containing the number of data records in the cache."
        ::= { g3ipintlist 5 }

    g3ipintlistTable	OBJECT-TYPE
        SYNTAX    SEQUENCE OF G3ipintlistEntry
        ACCESS    not-accessible
        STATUS    mandatory
        DESCRIPTION
            "A list of g3ipintlist entries."
        ::= { g3ipintlist 6 }

    g3ipintlistEntry	OBJECT-TYPE
        SYNTAX    G3ipintlistEntry
        ACCESS    not-accessible
        STATUS    mandatory
        DESCRIPTION
            "A g3ipintlist entry containing objects of the
            g3ipintlist information sent by the switch."
        INDEX    { g3ipintlistNodeName }
        ::= { g3ipintlistTable 1 }

    G3ipintlistEntry ::= SEQUENCE {
        g3ipintlistNodeName
            DisplayString,
        g3ipintlistSlot
            DisplayString
        }

    g3ipintlistNodeName	OBJECT-TYPE
        SYNTAX    DisplayString (SIZE (0..15))
        ACCESS    read-only
        STATUS    mandatory
        DESCRIPTION
            "An object containing the the node-name for the ip interface"
        ::= { g3ipintlistEntry 1 }

    g3ipintlistSlot	OBJECT-TYPE
        SYNTAX    DisplayString (SIZE (0..5))
        ACCESS    read-only
        STATUS    mandatory
        DESCRIPTION
            "An object containing the the VAL, CLAN or MEDPRO board slot number "
        ::= { g3ipintlistEntry 2 }


    -- the g3stamedlist group

    g3stamedlistTage	OBJECT-TYPE
        SYNTAX    INTEGER
        ACCESS    read-only
        STATUS    mandatory
        DESCRIPTION
            "The number of timeticks since the media gateway status data was last
            extracted from the switch by the G3 Proxy Agent. This object
            along with the g3stamedlistTintvl object allows the Network Manager
            to determine the validity of the media gateway status data in the
            cache and to control when the proxy agent extracts the
            status media gateway data from the switch."
        ::= { g3stamedlist 1 }

    g3stamedlistTintvl	OBJECT-TYPE
        SYNTAX    INTEGER
        ACCESS    read-write
        STATUS    mandatory
        DESCRIPTION
            "An object containing the interval for which the data extracted 
            from the switch is considered valid by the Proxy Agent.
            When a GET or GET-NEXT request for these media gateway status
            objects is received by the agent it uses the g3stamedlistTage and 
            g3stamedlistTintvl objects to determine whether it should refresh 
            the cached media gateway status data."
        ::= { g3stamedlist 2 }

    g3stamedlistTdelay	OBJECT-TYPE
        SYNTAX    INTEGER
        ACCESS    read-only
        STATUS    mandatory
        DESCRIPTION
            "An object containing the delay encountered in updating the cached data"
        ::= { g3stamedlist 3 }

    g3stamedlistTretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3stamedlist 4 }

    g3stamedlistTcount	OBJECT-TYPE
        SYNTAX    Gauge
        ACCESS    read-only
        STATUS    mandatory
        DESCRIPTION
            "A Gauge object containing the number of data records in the cache."
        ::= { g3stamedlist 5 }

    g3stamedlistTable	OBJECT-TYPE
        SYNTAX    SEQUENCE OF G3stamedlistEntry
        ACCESS    not-accessible
        STATUS    mandatory
        DESCRIPTION
            "A list of g3stamedlist entries."
        ::= { g3stamedlist 6 }

    g3stamedlistEntry	OBJECT-TYPE
        SYNTAX    G3stamedlistEntry
        ACCESS    not-accessible
        STATUS    mandatory
        DESCRIPTION
            "A g3stamedlist entry containing objects of the
            g3stamedlist information sent by the switch."
        INDEX    { g3stamedlistGatewayStatus }
        ::= { g3stamedlistTable 1 }

    G3stamedlistEntry ::= SEQUENCE {
        g3stamedlistGatewayStatus
            DisplayString
        }

    g3stamedlistGatewayStatus	OBJECT-TYPE
        SYNTAX    DisplayString (SIZE (0..14))
        ACCESS    read-only
        STATUS    mandatory
        DESCRIPTION
            "An object containing the status of the first set of eight media
            gateways, including the number of major alarms, minor alarms,
            warnings, and the H.248 link status for each specific media gateway
            number."
        ::= { g3stamedlistEntry 1 }


    -- the g3lsplist group

    g3lsplistTage	OBJECT-TYPE
        SYNTAX    INTEGER
        ACCESS    read-only
        STATUS    mandatory
        DESCRIPTION
            "The number of timeticks since the survivable processor
            data was last extracted from the switch by the G3 Proxy Agent. This 
            object along with the g3lsplistTintvl object allows the Network Manager
            to determine the validity of the survivable processor data in the 
            cache and to control when the proxy agent extracts the survivable
            processor data from the switch."
        ::= { g3lsplist 1 }

    g3lsplistTintvl	OBJECT-TYPE
        SYNTAX    INTEGER
        ACCESS    read-write
        STATUS    mandatory
        DESCRIPTION
            "An object containing the interval for which the data extracted 
            from the switch is considered valid by the Proxy Agent.
            When a GET or GET-NEXT request for these survivable processor objects 
            is received by the agent it uses the g3lsplistTage and g3lsplistTintvl 
            objects to determine whether it should refresh the cached surivable
            processor data."
        ::= { g3lsplist 2 }

    g3lsplistTdelay	OBJECT-TYPE
        SYNTAX    INTEGER
        ACCESS    read-only
        STATUS    mandatory
        DESCRIPTION
            "An object containing the delay encountered in updating the cached data"
        ::= { g3lsplist 3 }

    g3lsplistTretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3lsplist 4 }

    g3lsplistTcount	OBJECT-TYPE
        SYNTAX    Gauge
        ACCESS    read-only
        STATUS    mandatory
        DESCRIPTION
            "A Gauge object containing the number of data records in the cache."
        ::= { g3lsplist 5 }

    g3lsplistTable	OBJECT-TYPE
        SYNTAX    SEQUENCE OF G3lsplistEntry
        ACCESS    not-accessible
        STATUS    mandatory
        DESCRIPTION
            "A list of g3lsplist entries."
        ::= { g3lsplist 6 }

    g3lsplistEntry	OBJECT-TYPE
        SYNTAX    G3lsplistEntry
        ACCESS    not-accessible
        STATUS    mandatory
        DESCRIPTION
            "A g3lsplist entry containing objects of the
            g3lsplist information sent by the switch."
        INDEX    { g3lsplistNodeName }
        ::= { g3lsplistTable 1 }

    G3lsplistEntry ::= SEQUENCE {
        g3lsplistNodeName
            DisplayString,
        g3lsplistIPAddr1
            DisplayString,
        g3lsplistIPAddr2
            DisplayString,
        g3lsplistIPAddr3
            DisplayString,
        g3lsplistIPAddr4
            DisplayString,
        g3lsplistAvailable
            DisplayString,
        g3lsplistXlnUpdated
            DisplayString,
        g3lsplistServiceState
            DisplayString,
        g3lsplistNetworkRegion
            DisplayString,
        g3lsplistType
            DisplayString,
        g3lsplistID
            DisplayString,
        g3lsplistRegistered
            DisplayString,
        g3lsplistActive
            DisplayString
        }

    g3lsplistNodeName	OBJECT-TYPE
        SYNTAX    DisplayString (SIZE (0..20))
        ACCESS    read-only
        STATUS    mandatory
        DESCRIPTION
            "An object containing the survivable processor node name."
        ::= { g3lsplistEntry 1 }

    g3lsplistIPAddr1	OBJECT-TYPE
        SYNTAX    DisplayString (SIZE (0..40))
        ACCESS    read-only
        STATUS    mandatory
        DESCRIPTION
            "An object containing the first part of the survivable processor 
            IP address on pre-3.1 CM releases. On CM 3.1 and greater, the 
            complete IP address is populated in this field."
        ::= { g3lsplistEntry 2 }

    g3lsplistIPAddr2	OBJECT-TYPE
        SYNTAX    DisplayString (SIZE (0..3))
        ACCESS    read-only
        STATUS    mandatory
        DESCRIPTION
            "An object containing the second part of the survivable processor IP
            address. This field is only populated on pre-3.1 CM releases."
        ::= { g3lsplistEntry 3 }

    g3lsplistIPAddr3	OBJECT-TYPE
        SYNTAX    DisplayString (SIZE (0..3))
        ACCESS    read-only
        STATUS    mandatory
        DESCRIPTION
            "An object containing the third part of the survivable processor IP
            address. This field is only populated on pre-3.1 CM releases."
        ::= { g3lsplistEntry 4 }

    g3lsplistIPAddr4	OBJECT-TYPE
        SYNTAX    DisplayString (SIZE (0..3))
        ACCESS    read-only
        STATUS    mandatory
        DESCRIPTION
            "An object containing the fourth part of the surivivable processor
            IP address. This field is only populated on pre-3.1 CM releases."
        ::= { g3lsplistEntry 5 }

    g3lsplistAvailable	OBJECT-TYPE
        SYNTAX    DisplayString (SIZE (0..5))
        ACCESS    read-only
        STATUS    mandatory
        DESCRIPTION
            "An object indicating the availability of the survivable processor
            (y(es) or n(o)). This field is only populated on older CM releases.
            This field has become obsolete."
        ::= { g3lsplistEntry 6 }

    g3lsplistXlnUpdated	OBJECT-TYPE
        SYNTAX    DisplayString (SIZE (0..17))
        ACCESS    read-only
        STATUS    mandatory
        DESCRIPTION
            "An object containing the date and time of the last translation
            update in the format mm/dd/hh:mm."
        ::= { g3lsplistEntry 7 }

    g3lsplistServiceState	OBJECT-TYPE
        SYNTAX    DisplayString (SIZE (0..15))
        ACCESS    read-only
        STATUS    mandatory
        DESCRIPTION
            "An object containing the service state of the survivable processor."
        ::= { g3lsplistEntry 8 }

    g3lsplistNetworkRegion	OBJECT-TYPE
        SYNTAX    DisplayString (SIZE (0..3))
        ACCESS    read-only
        STATUS    mandatory
        DESCRIPTION
            "An object containing the network region of the survivable processor."
        ::= { g3lsplistEntry 9 }

    g3lsplistType	OBJECT-TYPE
        SYNTAX    DisplayString (SIZE (0..5))
        ACCESS    read-only
        STATUS    mandatory
        DESCRIPTION
            "An object containing the type of the survivable processor (LSP
            or ESS)."
        ::= { g3lsplistEntry 10 }

    g3lsplistID	OBJECT-TYPE
        SYNTAX    DisplayString (SIZE (0..5))
        ACCESS    read-only
        STATUS    mandatory
        DESCRIPTION
            "An object containing the number of the survivable processor."
        ::= { g3lsplistEntry 11 }

    g3lsplistRegistered	OBJECT-TYPE
        SYNTAX    DisplayString (SIZE (0..1))
        ACCESS    read-only
        STATUS    mandatory
        DESCRIPTION
            "An object indicating whether the survivable processor is
            registered (y(es) or n(o))."
        ::= { g3lsplistEntry 12 }

    g3lsplistActive	OBJECT-TYPE
        SYNTAX    DisplayString (SIZE (0..1))
        ACCESS    read-only
        STATUS    mandatory
        DESCRIPTION
            "An object indicating the active state of survivable processor
            (y(es)or n(o))."
        ::= { g3lsplistEntry 13 }


    -- the g3eventhour group

    g3eventhourTage	OBJECT-TYPE
        SYNTAX    INTEGER
        ACCESS    read-only
        STATUS    mandatory
        DESCRIPTION
            "The number of timeticks since the last hour denial event
            data was last extracted from the switch by the G3 Proxy Agent. This 
            object along with the g3eventhourTintvl object allows the Network 
            Manager to determine the validity of the event data in the cache 
            and to control when the proxy agent extracts the event data from 
            the switch."
        ::= { g3eventhour 1 }

    g3eventhourTintvl	OBJECT-TYPE
        SYNTAX    INTEGER
        ACCESS    read-write
        STATUS    mandatory
        DESCRIPTION
            "An object containing the interval for which the data extracted 
            from the switch is considered valid by the Proxy Agent.
            When a GET or GET-NEXT request for these event objects is received 
            by the agent it uses the g3eventhourTage and g3eventhourTintvl objects 
            to determine whether it should refresh the cached event data."
        ::= { g3eventhour 2 }

    g3eventhourTdelay	OBJECT-TYPE
        SYNTAX    INTEGER
        ACCESS    read-only
        STATUS    mandatory
        DESCRIPTION
            "An object containing the delay encountered in updating the cached data."
        ::= { g3eventhour 3 }

    g3eventhourTretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3eventhour 4 }

    g3eventhourTcount	OBJECT-TYPE
        SYNTAX    Gauge
        ACCESS    read-only
        STATUS    mandatory
        DESCRIPTION
            "A Gauge object containing the number of data records in the cache."
        ::= { g3eventhour 5 }

    g3eventhourTable	OBJECT-TYPE
        SYNTAX    SEQUENCE OF G3eventhourEntry
        ACCESS    not-accessible
        STATUS    mandatory
        DESCRIPTION
            "A list of g3eventhour entries."
        ::= { g3eventhour 6 }

    g3eventhourEntry	OBJECT-TYPE
        SYNTAX    G3eventhourEntry
        ACCESS    not-accessible
        STATUS    mandatory
        DESCRIPTION
            "A g3eventhour entry containing objects of the
            g3eventhour information sent by the switch."
        INDEX    { g3eventhourEventType, g3eventhourIndex }
        ::= { g3eventhourTable 1 }

    G3eventhourEntry ::= SEQUENCE {
        g3eventhourEventType
            DisplayString,
        g3eventhourIndex
            INTEGER,
        g3eventhourEventDesc
            DisplayString,
        g3eventhourEventData1
            DisplayString,
        g3eventhourEventData2
            DisplayString,
        g3eventhourFirstMonth
            DisplayString,
        g3eventhourFirstDay
            DisplayString,
        g3eventhourFirstHour
            DisplayString,
        g3eventhourFirstMinute
            DisplayString,
        g3eventhourLastMonth
            DisplayString,
        g3eventhourLastDay
            DisplayString,
        g3eventhourLastHour
            DisplayString,
        g3eventhourLastMinute
            DisplayString,
        g3eventhourEventCount
            DisplayString
        }

    g3eventhourEventType	OBJECT-TYPE
        SYNTAX    DisplayString (SIZE (0..5))
        ACCESS    read-only
        STATUS    mandatory
        DESCRIPTION
            "An INTEGER object containing the event code number for a given
            denial event."
        ::= { g3eventhourEntry 1 }

    g3eventhourIndex	OBJECT-TYPE
        SYNTAX    INTEGER
        ACCESS    read-only
        STATUS    mandatory
        DESCRIPTION
            "An INTEGER object containing an index numbering the event entry
            for the type specified in EventType. This object along with
            EventType will serve as the instance identifier for the record entry."
        ::= { g3eventhourEntry 2 }

    g3eventhourEventDesc	OBJECT-TYPE
        SYNTAX    DisplayString (SIZE (0..25))
        ACCESS    read-only
        STATUS    mandatory
        DESCRIPTION
            "A DisplayString object containing the denial event description."
        ::= { g3eventhourEntry 3 }

    g3eventhourEventData1	OBJECT-TYPE
        SYNTAX    DisplayString (SIZE (0..9))
        ACCESS    read-only
        STATUS    mandatory
        DESCRIPTION
            "A DisplayString object containing the first half of the event data."
        ::= { g3eventhourEntry 4 }

    g3eventhourEventData2	OBJECT-TYPE
        SYNTAX    DisplayString (SIZE (0..8))
        ACCESS    read-only
        STATUS    mandatory
        DESCRIPTION
            "A DisplayString object containing the last half of the event data."
        ::= { g3eventhourEntry 5 }

    g3eventhourFirstMonth	OBJECT-TYPE
        SYNTAX    DisplayString (SIZE (0..2))
        ACCESS    read-only
        STATUS    mandatory
        DESCRIPTION
            "A DisplayString object containing the Month of the first occurrence."
        ::= { g3eventhourEntry 6 }

    g3eventhourFirstDay	OBJECT-TYPE
        SYNTAX    DisplayString (SIZE (0..2))
        ACCESS    read-only
        STATUS    mandatory
        DESCRIPTION
            "A DisplayString object containing the Day of the first occurrence."
        ::= { g3eventhourEntry 7 }

    g3eventhourFirstHour	OBJECT-TYPE
        SYNTAX    DisplayString (SIZE (0..2))
        ACCESS    read-only
        STATUS    mandatory
        DESCRIPTION
            "A DisplayString object containing the Hour of the first occurrence."
        ::= { g3eventhourEntry 8 }

    g3eventhourFirstMinute	OBJECT-TYPE
        SYNTAX    DisplayString (SIZE (0..2))
        ACCESS    read-only
        STATUS    mandatory
        DESCRIPTION
            "A DisplayString object containing the Minute of the first occurrence."
        ::= { g3eventhourEntry 9 }

    g3eventhourLastMonth	OBJECT-TYPE
        SYNTAX    DisplayString (SIZE (0..2))
        ACCESS    read-only
        STATUS    mandatory
        DESCRIPTION
            "A DisplayString object containing the Month of the last occurrence."
        ::= { g3eventhourEntry 10 }

    g3eventhourLastDay	OBJECT-TYPE
        SYNTAX    DisplayString (SIZE (0..2))
        ACCESS    read-only
        STATUS    mandatory
        DESCRIPTION
            "A DisplayString object containing the Day of the last occurrence."
        ::= { g3eventhourEntry 11 }

    g3eventhourLastHour	OBJECT-TYPE
        SYNTAX    DisplayString (SIZE (0..2))
        ACCESS    read-only
        STATUS    mandatory
        DESCRIPTION
            "A DisplayString object containing the Hour of the last occurrence."
        ::= { g3eventhourEntry 12 }

    g3eventhourLastMinute	OBJECT-TYPE
        SYNTAX    DisplayString (SIZE (0..2))
        ACCESS    read-only
        STATUS    mandatory
        DESCRIPTION
            "A DisplayString object containing the Minute of the last occurrence."
        ::= { g3eventhourEntry 13 }

    g3eventhourEventCount	OBJECT-TYPE
        SYNTAX    DisplayString (SIZE (0..3))
        ACCESS    read-only
        STATUS    mandatory
        DESCRIPTION
            "A DisplayString object containing the number of occurrences of
            the denial event."
        ::= { g3eventhourEntry 14 }


    -- the g3eventday group

    g3eventdayTage	OBJECT-TYPE
        SYNTAX    INTEGER
        ACCESS    read-only
        STATUS    mandatory
        DESCRIPTION
            "The number of timeticks since the last day denial event
            data was last extracted from the switch by the G3 Proxy Agent. This 
            object along with the g3eventdayTintvl object allows the Network 
            Manager to determine the validity of the event data in the cache 
            and to control when the proxy agent extracts the event data from 
            the switch."
        ::= { g3eventday 1 }

    g3eventdayTintvl	OBJECT-TYPE
        SYNTAX    INTEGER
        ACCESS    read-write
        STATUS    mandatory
        DESCRIPTION
            "An object containing the interval for which the data extracted 
            from the switch is considered valid by the Proxy Agent.
            When a GET or GET-NEXT request for these event objects is received 
            by the agent it uses the g3eventdayTage and g3eventdayTintvl objects 
            to determine whether it should refresh the cached event data."
        ::= { g3eventday 2 }

    g3eventdayTdelay	OBJECT-TYPE
        SYNTAX    INTEGER
        ACCESS    read-only
        STATUS    mandatory
        DESCRIPTION
            "An object containing the delay encountered in updating the cached data."
        ::= { g3eventday 3 }

    g3eventdayTretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3eventday 4 }

    g3eventdayTcount	OBJECT-TYPE
        SYNTAX    Gauge
        ACCESS    read-only
        STATUS    mandatory
        DESCRIPTION
            "A Gauge object containing the number of data records in the cache."
        ::= { g3eventday 5 }

    g3eventdayTable	OBJECT-TYPE
        SYNTAX    SEQUENCE OF G3eventdayEntry
        ACCESS    not-accessible
        STATUS    mandatory
        DESCRIPTION
            "A list of g3eventday entries."
        ::= { g3eventday 6 }

    g3eventdayEntry	OBJECT-TYPE
        SYNTAX    G3eventdayEntry
        ACCESS    not-accessible
        STATUS    mandatory
        DESCRIPTION
            "A g3eventday entry containing objects of the
            g3eventday information sent by the switch."
        INDEX    { g3eventdayEventType, g3eventdayIndex }
        ::= { g3eventdayTable 1 }

    G3eventdayEntry ::= SEQUENCE {
        g3eventdayEventType
            DisplayString,
        g3eventdayIndex
            INTEGER,
        g3eventdayEventDesc
            DisplayString,
        g3eventdayEventData1
            DisplayString,
        g3eventdayEventData2
            DisplayString,
        g3eventdayFirstMonth
            DisplayString,
        g3eventdayFirstDay
            DisplayString,
        g3eventdayFirstHour
            DisplayString,
        g3eventdayFirstMinute
            DisplayString,
        g3eventdayLastMonth
            DisplayString,
        g3eventdayLastDay
            DisplayString,
        g3eventdayLastHour
            DisplayString,
        g3eventdayLastMinute
            DisplayString,
        g3eventdayEventCount
            DisplayString
        }

    g3eventdayEventType	OBJECT-TYPE
        SYNTAX    DisplayString (SIZE (0..5))
        ACCESS    read-only
        STATUS    mandatory
        DESCRIPTION
            "An INTEGER object containing the event code number for a given
            denial event."
        ::= { g3eventdayEntry 1 }

    g3eventdayIndex	OBJECT-TYPE
        SYNTAX    INTEGER
        ACCESS    read-only
        STATUS    mandatory
        DESCRIPTION
            "An INTEGER object containing an index numbering the event entry
            for the type specified in EventType. This object along with
            EventType will serve as the instance identifier for the record entry."
        ::= { g3eventdayEntry 2 }

    g3eventdayEventDesc	OBJECT-TYPE
        SYNTAX    DisplayString (SIZE (0..25))
        ACCESS    read-only
        STATUS    mandatory
        DESCRIPTION
            "A DisplayString object containing the denial event description."
        ::= { g3eventdayEntry 3 }

    g3eventdayEventData1	OBJECT-TYPE
        SYNTAX    DisplayString (SIZE (0..9))
        ACCESS    read-only
        STATUS    mandatory
        DESCRIPTION
            "A DisplayString object containing the first half of the event data."
        ::= { g3eventdayEntry 4 }

    g3eventdayEventData2	OBJECT-TYPE
        SYNTAX    DisplayString (SIZE (0..8))
        ACCESS    read-only
        STATUS    mandatory
        DESCRIPTION
            "A DisplayString object containing the last half of the event data."
        ::= { g3eventdayEntry 5 }

    g3eventdayFirstMonth	OBJECT-TYPE
        SYNTAX    DisplayString (SIZE (0..2))
        ACCESS    read-only
        STATUS    mandatory
        DESCRIPTION
            "A DisplayString object containing the Month of the first occurrence."
        ::= { g3eventdayEntry 6 }

    g3eventdayFirstDay	OBJECT-TYPE
        SYNTAX    DisplayString (SIZE (0..2))
        ACCESS    read-only
        STATUS    mandatory
        DESCRIPTION
            "A DisplayString object containing the Day of the first occurrence."
        ::= { g3eventdayEntry 7 }

    g3eventdayFirstHour	OBJECT-TYPE
        SYNTAX    DisplayString (SIZE (0..2))
        ACCESS    read-only
        STATUS    mandatory
        DESCRIPTION
            "A DisplayString object containing the Hour of the first occurrence."
        ::= { g3eventdayEntry 8 }

    g3eventdayFirstMinute	OBJECT-TYPE
        SYNTAX    DisplayString (SIZE (0..2))
        ACCESS    read-only
        STATUS    mandatory
        DESCRIPTION
            "A DisplayString object containing the Minute of the first occurrence."
        ::= { g3eventdayEntry 9 }

    g3eventdayLastMonth	OBJECT-TYPE
        SYNTAX    DisplayString (SIZE (0..2))
        ACCESS    read-only
        STATUS    mandatory
        DESCRIPTION
            "A DisplayString object containing the Month of the last occurrence."
        ::= { g3eventdayEntry 10 }

    g3eventdayLastDay	OBJECT-TYPE
        SYNTAX    DisplayString (SIZE (0..2))
        ACCESS    read-only
        STATUS    mandatory
        DESCRIPTION
            "A DisplayString object containing the Day of the last occurrence."
        ::= { g3eventdayEntry 11 }

    g3eventdayLastHour	OBJECT-TYPE
        SYNTAX    DisplayString (SIZE (0..2))
        ACCESS    read-only
        STATUS    mandatory
        DESCRIPTION
            "A DisplayString object containing the Hour of the last occurrence."
        ::= { g3eventdayEntry 12 }

    g3eventdayLastMinute	OBJECT-TYPE
        SYNTAX    DisplayString (SIZE (0..2))
        ACCESS    read-only
        STATUS    mandatory
        DESCRIPTION
            "A DisplayString object containing the Minute of the last occurrence."
        ::= { g3eventdayEntry 13 }

    g3eventdayEventCount	OBJECT-TYPE
        SYNTAX    DisplayString (SIZE (0..3))
        ACCESS    read-only
        STATUS    mandatory
        DESCRIPTION
            "A DisplayString object containing the number of occurrences of
            the denial event."
        ::= { g3eventdayEntry 14 }


    -- the g3statregion group

    g3statregionTage	OBJECT-TYPE
        SYNTAX    INTEGER
        ACCESS    read-only
        STATUS    mandatory
        DESCRIPTION
            "The number of timeticks since the network region status data was last
            extracted from the switch by the G3 Proxy Agent. This object
            along with the g3statregionTintvl object allows the Network Manager
            to determine the validity of the network region status data in the
            cache and to control when the proxy agent extracts the network 
            region data from the switch."
        ::= { g3statregion 1 }

    g3statregionTintvl	OBJECT-TYPE
        SYNTAX    INTEGER
        ACCESS    read-write
        STATUS    mandatory
        DESCRIPTION
            "An object containing the interval for which the data extracted 
            from the switch is considered valid by the Proxy Agent.
            When a GET or GET-NEXT request for these network region status
            objects is received by the agent it uses the g3statregionTage and 
            g3statregionTintvl objects to determine whether it should refresh 
            the cached network region status data."
        ::= { g3statregion 2 }

    g3statregionTdelay	OBJECT-TYPE
        SYNTAX    INTEGER
        ACCESS    read-only
        STATUS    mandatory
        DESCRIPTION
            "An object containing the delay encountered in updating the cached data."
        ::= { g3statregion 3 }

    g3statregionTretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3statregion 4 }

    g3statregionTcount	OBJECT-TYPE
        SYNTAX    Gauge
        ACCESS    read-only
        STATUS    mandatory
        DESCRIPTION
            "A Gauge object containing the number of data records in the cache."
        ::= { g3statregion 5 }

    g3statregionTable	OBJECT-TYPE
        SYNTAX    SEQUENCE OF G3statregionEntry
        ACCESS    not-accessible
        STATUS    mandatory
        DESCRIPTION
            "A list of g3statregion entries."
        ::= { g3statregion 6 }

    g3statregionEntry	OBJECT-TYPE
        SYNTAX    G3statregionEntry
        ACCESS    not-accessible
        STATUS    mandatory
        DESCRIPTION
            "A g3statregion entry containing objects of the
            g3statregion information sent by the switch."
        INDEX    { g3statregionSourceRegion, g3statregionDestRegion }
        ::= { g3statregionTable 1 }

    G3statregionEntry ::= SEQUENCE {
        g3statregionSourceRegion
            INTEGER,
        g3statregionDestRegion
            INTEGER,
        g3statregionConnType
            DisplayString,
        g3statregionConnStatus
            DisplayString,
        g3statregionBWLimitValue
            DisplayString,
        g3statregionBWLimitUnits
            DisplayString,
        g3statregionBWUsedTx
            DisplayString,
        g3statregionBWUsedRx
            DisplayString,
        g3statregionNbrConnTx
            DisplayString,
        g3statregionNbrConnRx
            DisplayString,
        g3statregionDenialCount
            DisplayString
        }

    g3statregionSourceRegion	OBJECT-TYPE
        SYNTAX    INTEGER
        ACCESS    read-only
        STATUS    mandatory
        DESCRIPTION
            "An INTEGER object containing the IP network region that is the
            source of the VoIP traffic."
        ::= { g3statregionEntry 1 }

    g3statregionDestRegion	OBJECT-TYPE
        SYNTAX    INTEGER
        ACCESS    read-only
        STATUS    mandatory
        DESCRIPTION
            "An INTEGER object containing the IP network region that is the
            destination of the VoIP traffic."
        ::= { g3statregionEntry 2 }

    g3statregionConnType	OBJECT-TYPE
        SYNTAX    DisplayString (SIZE (0..8))
        ACCESS    read-only
        STATUS    mandatory
        DESCRIPTION
            "A DisplayString object containing the type of connection (either
            direct or indirect)."
        ::= { g3statregionEntry 3 }

    g3statregionConnStatus	OBJECT-TYPE
        SYNTAX    DisplayString (SIZE (0..4))
        ACCESS    read-only
        STATUS    mandatory
        DESCRIPTION
            "A DisplayString object containing the status of connection (either
            pass or fail)."
        ::= { g3statregionEntry 4 }

    g3statregionBWLimitValue	OBJECT-TYPE
        SYNTAX    DisplayString (SIZE (0..4))
        ACCESS    read-only
        STATUS    mandatory
        DESCRIPTION
            "A DisplayString object containing the administered bandwidth
            value."
        ::= { g3statregionEntry 5 }

    g3statregionBWLimitUnits	OBJECT-TYPE
        SYNTAX    DisplayString (SIZE (0..7))
        ACCESS    read-only
        STATUS    mandatory
        DESCRIPTION
            "A DisplayString object containing the administered bandwidth
            units (Calls, Kbits, Mbits, or NoLimit)."
        ::= { g3statregionEntry 6 }

    g3statregionBWUsedTx	OBJECT-TYPE
        SYNTAX    DisplayString (SIZE (0..5))
        ACCESS    read-only
        STATUS    mandatory
        DESCRIPTION
            "A DisplayString object containing the transmit bandwidth used
            for direct connections only."
        ::= { g3statregionEntry 7 }

    g3statregionBWUsedRx	OBJECT-TYPE
        SYNTAX    DisplayString (SIZE (0..6))
        ACCESS    read-only
        STATUS    mandatory
        DESCRIPTION
            "A DisplayString object containing the receive bandwidth used
            for direct connections only."
        ::= { g3statregionEntry 8 }

    g3statregionNbrConnTx	OBJECT-TYPE
        SYNTAX    DisplayString (SIZE (0..5))
        ACCESS    read-only
        STATUS    mandatory
        DESCRIPTION
            "A DisplayString object containing the transmit connection count
            for direct connections only."
        ::= { g3statregionEntry 9 }

    g3statregionNbrConnRx	OBJECT-TYPE
        SYNTAX    DisplayString (SIZE (0..5))
        ACCESS    read-only
        STATUS    mandatory
        DESCRIPTION
            "A DisplayString object containing the receive connection count
            for direct connections only."
        ::= { g3statregionEntry 10 }

    g3statregionDenialCount	OBJECT-TYPE
        SYNTAX    DisplayString (SIZE (0..3))
        ACCESS    read-only
        STATUS    mandatory
        DESCRIPTION
            "A DisplayString object containing the denial count."
        ::= { g3statregionEntry 11 }


    -- the g3ipnetregion group

    g3ipnetregionTage	OBJECT-TYPE
        SYNTAX    INTEGER
        ACCESS    read-only
        STATUS    mandatory
        DESCRIPTION
            "The number of timeticks since the network region data was last
            extracted from the switch by the G3 Proxy Agent. This object
            along with the g3ipnetregionTintvl object allows the Network Manager
            to determine the validity of the network region data in the
            cache and to control when the proxy agent extracts the network 
            region data from the switch."
        ::= { g3ipnetregion 1 }

    g3ipnetregionTintvl	OBJECT-TYPE
        SYNTAX    INTEGER
        ACCESS    read-write
        STATUS    mandatory
        DESCRIPTION
            "An object containing the interval for which the data extracted 
            from the switch is considered valid by the Proxy Agent.
            When a GET or GET-NEXT request for these network region 
            objects is received by the agent it uses the g3ipnetregionTage and 
            g3ipnetregionTintvl objects to determine whether it should refresh 
            the cached network region data."
        ::= { g3ipnetregion 2 }

    g3ipnetregionTdelay	OBJECT-TYPE
        SYNTAX    INTEGER
        ACCESS    read-only
        STATUS    mandatory
        DESCRIPTION
            "An object containing the delay encountered in updating the cached data."
        ::= { g3ipnetregion 3 }

    g3ipnetregionTretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3ipnetregion 4 }

    g3ipnetregionTcount	OBJECT-TYPE
        SYNTAX    Gauge
        ACCESS    read-only
        STATUS    mandatory
        DESCRIPTION
            "A Gauge object containing the number of data records in the cache."
        ::= { g3ipnetregion 5 }

    g3ipnetregionTable	OBJECT-TYPE
        SYNTAX    SEQUENCE OF G3ipnetregionEntry
        ACCESS    not-accessible
        STATUS    mandatory
        DESCRIPTION
            "A list of g3ipnetregion entries."
        ::= { g3ipnetregion 6 }

    g3ipnetregionEntry	OBJECT-TYPE
        SYNTAX    G3ipnetregionEntry
        ACCESS    not-accessible
        STATUS    mandatory
        DESCRIPTION
            "A g3ipnetregion entry containing objects of the
            g3ipnetregion information sent by the switch."
        INDEX    { g3ipnetregionRegion }
        ::= { g3ipnetregionTable 1 }

    G3ipnetregionEntry ::= SEQUENCE {
        g3ipnetregionRegion
            INTEGER,
        g3ipnetregionCCPHB
            INTEGER,
        g3ipnetregionAudioPHB
            INTEGER,
        g3ipnetregionCC8021Pri
            INTEGER,
        g3ipnetregionAudio8021Pri
            INTEGER,
        g3ipnetregionRSVPEnabled
            DisplayString,
        g3ipnetregionRSVPRefresh
            INTEGER,
        g3ipnetregionRSVPFailure
            DisplayString,
        g3ipnetregionRSVPProfile
            DisplayString,
        g3ipnetregionRSVPBBE
            INTEGER,
        g3ipnetregionLastError
            DisplayString
        }

    g3ipnetregionRegion	OBJECT-TYPE
        SYNTAX    INTEGER
        ACCESS    read-write
        STATUS    mandatory
        DESCRIPTION
            "An INTEGER object containing the IP network region number (value
            1-2000)."
        ::= { g3ipnetregionEntry 1 }

    g3ipnetregionCCPHB	OBJECT-TYPE
        SYNTAX    INTEGER
        ACCESS    read-write
        STATUS    mandatory
        DESCRIPTION
            "A DisplayString object containing the DiffServ/TOS Call Control
            PHB (value 0-63)."
        ::= { g3ipnetregionEntry 2 }

    g3ipnetregionAudioPHB	OBJECT-TYPE
        SYNTAX    INTEGER
        ACCESS    read-write
        STATUS    mandatory
        DESCRIPTION
            "A DisplayString object containing the DiffServ/TOS Audio PHB 
            (value 0-63)."
        ::= { g3ipnetregionEntry 3 }

    g3ipnetregionCC8021Pri	OBJECT-TYPE
        SYNTAX    INTEGER
        ACCESS    read-write
        STATUS    mandatory
        DESCRIPTION
            "A DisplayString object containing the Call Control 802.1p
            Priority (values 0-7)."
        ::= { g3ipnetregionEntry 4 }

    g3ipnetregionAudio8021Pri	OBJECT-TYPE
        SYNTAX    INTEGER
        ACCESS    read-write
        STATUS    mandatory
        DESCRIPTION
            "A DisplayString object containing the Audio 802.1p Priority
            (values 0-7)."
        ::= { g3ipnetregionEntry 5 }

    g3ipnetregionRSVPEnabled	OBJECT-TYPE
        SYNTAX    DisplayString (SIZE (0..1))
        ACCESS    read-write
        STATUS    mandatory
        DESCRIPTION
            "A DisplayString object containing a flag indicating whether RSVP
            is enabled (y or n)."
        ::= { g3ipnetregionEntry 6 }

    g3ipnetregionRSVPRefresh	OBJECT-TYPE
        SYNTAX    INTEGER
        ACCESS    read-write
        STATUS    mandatory
        DESCRIPTION
            "A DisplayString object containing the RSVP Refresh Rate (values
            1-99)."
        ::= { g3ipnetregionEntry 7 }

    g3ipnetregionRSVPFailure	OBJECT-TYPE
        SYNTAX    DisplayString (SIZE (0..1))
        ACCESS    read-write
        STATUS    mandatory
        DESCRIPTION
            "A DisplayString object containing a flag indicating whether retry
            on RSVP failure is enabled (y or n)."
        ::= { g3ipnetregionEntry 8 }

    g3ipnetregionRSVPProfile	OBJECT-TYPE
        SYNTAX    DisplayString (SIZE (0..18))
        ACCESS    read-write
        STATUS    mandatory
        DESCRIPTION
            "A DisplayString object containing the RSVP profile (controlled-load
            or guaranteed-service)."
        ::= { g3ipnetregionEntry 9 }

    g3ipnetregionRSVPBBE	OBJECT-TYPE
        SYNTAX    INTEGER
        ACCESS    read-write
        STATUS    mandatory
        DESCRIPTION
            "A DisplayString object containing the RSVP unreserved BBE PHB
            (values 0-63)."
        ::= { g3ipnetregionEntry 10 }

    g3ipnetregionLastError	OBJECT-TYPE
        SYNTAX    DisplayString (SIZE (0..100))
        ACCESS    read-only
        STATUS    mandatory
        DESCRIPTION
            "A DisplayString Object that contains the last error message
            encountered when attempting to change ip-network-region
            parameters."
        ::= { g3ipnetregionEntry 11 }


    -- the g3statmedpro group

    g3statmedproTage	OBJECT-TYPE
        SYNTAX    INTEGER
        ACCESS    read-only
        STATUS    mandatory
        DESCRIPTION
            "The number of timeticks since the media processor status data was
            extracted from the switch by the G3 Proxy Agent. This object
            along with the g3statmedproTintvl object allows the Network Manager
            to determine the validity of the media processor status  data in the
            cache and to control when the proxy agent extracts the
            media processor status data from the switch."
        ::= { g3statmedpro 1 }

    g3statmedproTintvl	OBJECT-TYPE
        SYNTAX    INTEGER
        ACCESS    read-write
        STATUS    mandatory
        DESCRIPTION
            "An object containing the interval for which the data extracted 
            from the switch is considered valid by the Proxy Agent.
            When a GET or GET-NEXT request for these media processor status 
            objects is received by the agent it uses the g3statmedproTage and 
            g3statmedproTintvl objects to determine whether it should refresh 
            the cached media processor status data."
        ::= { g3statmedpro 2 }

    g3statmedproTdelay	OBJECT-TYPE
        SYNTAX    INTEGER
        ACCESS    read-only
        STATUS    mandatory
        DESCRIPTION
            "An object containing the delay encountered in updating the cached data."
        ::= { g3statmedpro 3 }

    g3statmedproTretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3statmedpro 4 }

    g3statmedproTcount	OBJECT-TYPE
        SYNTAX    Gauge
        ACCESS    read-only
        STATUS    mandatory
        DESCRIPTION
            "A Gauge object containing the number of data records in the cache."
        ::= { g3statmedpro 5 }

    g3statmedproTable	OBJECT-TYPE
        SYNTAX    SEQUENCE OF G3statmedproEntry
        ACCESS    not-accessible
        STATUS    mandatory
        DESCRIPTION
            "A list of g3statmedpro entries."
        ::= { g3statmedpro 6 }

    g3statmedproEntry	OBJECT-TYPE
        SYNTAX    G3statmedproEntry
        ACCESS    not-accessible
        STATUS    mandatory
        DESCRIPTION
            "A g3statmedpro entry containing objects of the
            g3statmedpro information sent by the switch."
        INDEX    { g3statmedproBoardLoc }
        ::= { g3statmedproTable 1 }

    G3statmedproEntry ::= SEQUENCE {
        g3statmedproBoardLoc
            DisplayString,
        g3statmedproState
            DisplayString,
        g3statmedproNodeName
            DisplayString,
        g3statmedproSourceIP
            DisplayString,
        g3statmedproSubnetMask
            DisplayString,
        g3statmedproBroadCastAddr
            DisplayString,
        g3statmedproMACAddress
            DisplayString,
        g3statmedproEtherEnabled
            DisplayString,
        g3statmedproDSPChanStatus1
            DisplayString,
        g3statmedproDSPChanStatus2
            DisplayString,
        g3statmedproDSPChanStatus3
            DisplayString,
        g3statmedproDSPChanStatus4
            DisplayString,
        g3statmedproDupDSPChanStatus5
            DisplayString,
        g3statmedproDupDSPChanStatus6
            DisplayString,
        g3statmedproDupDSPChanStatus7
            DisplayString,
        g3statmedproDupDSPChanStatus8
            DisplayString,
        g3statmedproNetworkRegion
            DisplayString,
        g3statmedproAltNetworkRegion
            DisplayString,
        g3statmedproStandbyRefreshed
            DisplayString,
        g3statmedproSharedIP
            DisplayString,
        g3statmedproSharedVirtMAC
            DisplayString,
        g3statmedproDupBoardLoc
            DisplayString,
        g3statmedproDupState
            DisplayString,
        g3statmedproDupNodeName
            DisplayString,
        g3statmedproDupSourceIP
            DisplayString,
        g3statmedproDupSubnetMask
            DisplayString,
        g3statmedproDupBroadCastAddr
            DisplayString,
        g3statmedproDupMACAddress
            DisplayString,
        g3statmedproDupEtherEnabled
            DisplayString,
        g3statmedproLinkMPCL
            DisplayString,
        g3statmedproLinkEth
            DisplayString,
        g3statmedproLinkPeer
            DisplayString,
        g3statmedproAlarmMaj
            DisplayString,
        g3statmedproAlarmMin
            DisplayString,
        g3statmedproAlarmWrn
            DisplayString,
        g3statmedproDupLinkMPCL
            DisplayString,
        g3statmedproDupLinkEth
            DisplayString,
        g3statmedproDupLinkPeer
            DisplayString,
        g3statmedproDupAlarmMaj
            DisplayString,
        g3statmedproDupAlarmMin
            DisplayString,
        g3statmedproDupAlarmWrn
            DisplayString,
        g3statmedproLocked
            DisplayString,
        g3statmedproSourceIPV6
            DisplayString,
        g3statmedproIPV6SubnetMask
            DisplayString,
        g3statmedproIPV6GatewayAddr
            DisplayString,
        g3statmedproIPV6NodeName
            DisplayString,
        g3statmedproIPV6EtherEnable
            DisplayString
        }

    g3statmedproBoardLoc	OBJECT-TYPE
        SYNTAX    DisplayString (SIZE (0..5))
        ACCESS    read-only
        STATUS    mandatory
        DESCRIPTION
            "A DisplayString Object contains the media processor board location."
        ::= { g3statmedproEntry 1 }

    g3statmedproState	OBJECT-TYPE
        SYNTAX    DisplayString (SIZE (0..7))
        ACCESS    read-only
        STATUS    mandatory
        DESCRIPTION
            "A DisplayString Object that contains state of the media processor
            board (values can be 'active', 'standby' or 'init')."
        ::= { g3statmedproEntry 2 }

    g3statmedproNodeName	OBJECT-TYPE
        SYNTAX    DisplayString (SIZE (0..15))
        ACCESS    read-only
        STATUS    mandatory
        DESCRIPTION
            "A DisplayString Object that contains the node name for the
            media processor board."
        ::= { g3statmedproEntry 3 }

    g3statmedproSourceIP	OBJECT-TYPE
        SYNTAX    DisplayString (SIZE (0..16))
        ACCESS    read-only
        STATUS    mandatory
        DESCRIPTION
            "A DisplayString Object that contains the source IPV4 address for
            the media processor board."
        ::= { g3statmedproEntry 4 }

    g3statmedproSubnetMask	OBJECT-TYPE
        SYNTAX    DisplayString (SIZE (0..16))
        ACCESS    read-only
        STATUS    mandatory
        DESCRIPTION
            "A DisplayString Object that contains the IPV4 subnet mask for the
            media processor board."
        ::= { g3statmedproEntry 5 }

    g3statmedproBroadCastAddr	OBJECT-TYPE
        SYNTAX    DisplayString (SIZE (0..16))
        ACCESS    read-only
        STATUS    mandatory
        DESCRIPTION
            "A DisplayString Object that contains the broadcast IP address for
            the media processor board."
        ::= { g3statmedproEntry 6 }

    g3statmedproMACAddress	OBJECT-TYPE
        SYNTAX    DisplayString (SIZE (0..17))
        ACCESS    read-only
        STATUS    mandatory
        DESCRIPTION
            "A DisplayString Object that contains the MAC address of the
            media processor board."
        ::= { g3statmedproEntry 7 }

    g3statmedproEtherEnabled	OBJECT-TYPE
        SYNTAX    DisplayString (SIZE (0..3))
        ACCESS    read-only
        STATUS    mandatory
        DESCRIPTION
            "A DisplayString Object that designates whether or not the IP
            interface is enabled (yes or no) for the media processor board."
        ::= { g3statmedproEntry 8 }

    g3statmedproDSPChanStatus1	OBJECT-TYPE
        SYNTAX    DisplayString (SIZE (0..35))
        ACCESS    read-only
        STATUS    mandatory
        DESCRIPTION
            "A DisplayString Object that contains the service state of the
            respective DSP resource (for the media processor board)."
        ::= { g3statmedproEntry 9 }

    g3statmedproDSPChanStatus2	OBJECT-TYPE
        SYNTAX    DisplayString (SIZE (0..35))
        ACCESS    read-only
        STATUS    mandatory
        DESCRIPTION
            "See DESCRIPTION of g3statmedproDSPChanStatus1."
        ::= { g3statmedproEntry 10 }

    g3statmedproDSPChanStatus3	OBJECT-TYPE
        SYNTAX    DisplayString (SIZE (0..35))
        ACCESS    read-only
        STATUS    mandatory
        DESCRIPTION
            "See DESCRIPTION of g3statmedproDSPChanStatus1."
        ::= { g3statmedproEntry 11 }

    g3statmedproDSPChanStatus4	OBJECT-TYPE
        SYNTAX    DisplayString (SIZE (0..35))
        ACCESS    read-only
        STATUS    mandatory
        DESCRIPTION
            "See DESCRIPTION of g3statmedproDSPChanStatus1."
        ::= { g3statmedproEntry 12 }

    g3statmedproDupDSPChanStatus5	OBJECT-TYPE
        SYNTAX    DisplayString (SIZE (0..35))
        ACCESS    read-only
        STATUS    mandatory
        DESCRIPTION
            "A DisplayString Object that contains the service state of the
            respective DSP resource (for the duplicate media processor board)."
        ::= { g3statmedproEntry 13 }

    g3statmedproDupDSPChanStatus6	OBJECT-TYPE
        SYNTAX    DisplayString (SIZE (0..35))
        ACCESS    read-only
        STATUS    mandatory
        DESCRIPTION
            "See DESCRIPTION of g3statmedproDupDSPChanStatus5."
        ::= { g3statmedproEntry 14 }

    g3statmedproDupDSPChanStatus7	OBJECT-TYPE
        SYNTAX    DisplayString (SIZE (0..35))
        ACCESS    read-only
        STATUS    mandatory
        DESCRIPTION
            "See DESCRIPTION of g3statmedproDupDSPChanStatus5."
        ::= { g3statmedproEntry 15 }

    g3statmedproDupDSPChanStatus8	OBJECT-TYPE
        SYNTAX    DisplayString (SIZE (0..35))
        ACCESS    read-only
        STATUS    mandatory
        DESCRIPTION
            "See DESCRIPTION of g3statmedproDupDSPChanStatus5."
        ::= { g3statmedproEntry 16 }

    g3statmedproNetworkRegion	OBJECT-TYPE
        SYNTAX    DisplayString (SIZE (0..3))
        ACCESS    read-only
        STATUS    mandatory
        DESCRIPTION
            "A DisplayString Object that contains the network region number for
            the media processor board."
        ::= { g3statmedproEntry 17 }

    g3statmedproAltNetworkRegion	OBJECT-TYPE
        SYNTAX    DisplayString (SIZE (0..3))
        ACCESS    read-only
        STATUS    mandatory
        DESCRIPTION
            "A DisplayString Object that contains the alternate network region 
            number for the media processor board."
        ::= { g3statmedproEntry 18 }

    g3statmedproStandbyRefreshed	OBJECT-TYPE
        SYNTAX    DisplayString (SIZE (0..3))
        ACCESS    read-only
        STATUS    mandatory
        DESCRIPTION
            "A DisplayString Object that indicates whether the standby board
            in a duplicated pair of media processor boards is in sync with the 
            active board (yes or no)."
        ::= { g3statmedproEntry 19 }

    g3statmedproSharedIP	OBJECT-TYPE
        SYNTAX    DisplayString (SIZE (0..16))
        ACCESS    read-only
        STATUS    mandatory
        DESCRIPTION
            "A DisplayString Object that contains the shared virtual IP address
            between two duplicated media processor boards."
        ::= { g3statmedproEntry 20 }

    g3statmedproSharedVirtMAC	OBJECT-TYPE
        SYNTAX    DisplayString (SIZE (0..18))
        ACCESS    read-only
        STATUS    mandatory
        DESCRIPTION
            "A DisplayString Object that contains the shared virtual MAC address 
            between two duplicated media processor boards."
        ::= { g3statmedproEntry 21 }

    g3statmedproDupBoardLoc	OBJECT-TYPE
        SYNTAX    DisplayString (SIZE (0..5))
        ACCESS    read-only
        STATUS    mandatory
        DESCRIPTION
            "A DisplayString Object contains the duplicate media processor 
            board location."
        ::= { g3statmedproEntry 22 }

    g3statmedproDupState	OBJECT-TYPE
        SYNTAX    DisplayString (SIZE (0..7))
        ACCESS    read-only
        STATUS    mandatory
        DESCRIPTION
            "A DisplayString Object that contains state of the duplicate media 
            processor board (values can be 'active', 'standby' or 'init')."
        ::= { g3statmedproEntry 23 }

    g3statmedproDupNodeName	OBJECT-TYPE
        SYNTAX    DisplayString (SIZE (0..15))
        ACCESS    read-only
        STATUS    mandatory
        DESCRIPTION
            "A DisplayString Object that contains the node name for the
            duplicate media processor board."
        ::= { g3statmedproEntry 24 }

    g3statmedproDupSourceIP	OBJECT-TYPE
        SYNTAX    DisplayString (SIZE (0..16))
        ACCESS    read-only
        STATUS    mandatory
        DESCRIPTION
            "A DisplayString Object that contains the source IP address for
            the duplicate media processor board."
        ::= { g3statmedproEntry 25 }

    g3statmedproDupSubnetMask	OBJECT-TYPE
        SYNTAX    DisplayString (SIZE (0..16))
        ACCESS    read-only
        STATUS    mandatory
        DESCRIPTION
            "A DisplayString Object that contains the subnet mask for the
            duplicate media processor board."
        ::= { g3statmedproEntry 26 }

    g3statmedproDupBroadCastAddr	OBJECT-TYPE
        SYNTAX    DisplayString (SIZE (0..16))
        ACCESS    read-only
        STATUS    mandatory
        DESCRIPTION
            "A DisplayString Object that contains the broadcast IP address for
            the duplicate media processor board."
        ::= { g3statmedproEntry 27 }

    g3statmedproDupMACAddress	OBJECT-TYPE
        SYNTAX    DisplayString (SIZE (0..17))
        ACCESS    read-only
        STATUS    mandatory
        DESCRIPTION
            "A DisplayString Object that contains the MAC address of the
            media processor board."
        ::= { g3statmedproEntry 28 }

    g3statmedproDupEtherEnabled	OBJECT-TYPE
        SYNTAX    DisplayString (SIZE (0..3))
        ACCESS    read-only
        STATUS    mandatory
        DESCRIPTION
            "A DisplayString Object that designates whether or not the IP
            interface is enabled (yes or no) for the duplicate media processor 
            board."
        ::= { g3statmedproEntry 29 }

    g3statmedproLinkMPCL	OBJECT-TYPE
        SYNTAX    DisplayString (SIZE (0..2))
        ACCESS    read-only
        STATUS    mandatory
        DESCRIPTION
            "A DisplayString Object that indicates the status of the Media
            Processor Control Link ('up' or 'dn') for the media processor board."
        ::= { g3statmedproEntry 30 }

    g3statmedproLinkEth	OBJECT-TYPE
        SYNTAX    DisplayString (SIZE (0..2))
        ACCESS    read-only
        STATUS    mandatory
        DESCRIPTION
            "A DisplayString Object that indicates the status of the Ethernet
            Link ('up' or 'dn') for the media processor board."
        ::= { g3statmedproEntry 31 }

    g3statmedproLinkPeer	OBJECT-TYPE
        SYNTAX    DisplayString (SIZE (0..2))
        ACCESS    read-only
        STATUS    mandatory
        DESCRIPTION
            "A DisplayString Object that indicates the status of the Peer
            Link ('up' or 'dn') for the media processor board."
        ::= { g3statmedproEntry 32 }

    g3statmedproAlarmMaj	OBJECT-TYPE
        SYNTAX    DisplayString (SIZE (0..2))
        ACCESS    read-only
        STATUS    mandatory
        DESCRIPTION
            "A DisplayString Object that indicates the number of major alarms
            active on the media processor board. "
        ::= { g3statmedproEntry 33 }

    g3statmedproAlarmMin	OBJECT-TYPE
        SYNTAX    DisplayString (SIZE (0..2))
        ACCESS    read-only
        STATUS    mandatory
        DESCRIPTION
            "A DisplayString Object that indicates the number of minor alarms
            active on the media processor board. "
        ::= { g3statmedproEntry 34 }

    g3statmedproAlarmWrn	OBJECT-TYPE
        SYNTAX    DisplayString (SIZE (0..2))
        ACCESS    read-only
        STATUS    mandatory
        DESCRIPTION
            "A DisplayString Object that indicates the number of warning alarms
            active on the media processor board. "
        ::= { g3statmedproEntry 35 }

    g3statmedproDupLinkMPCL	OBJECT-TYPE
        SYNTAX    DisplayString (SIZE (0..2))
        ACCESS    read-only
        STATUS    mandatory
        DESCRIPTION
            "A DisplayString Object that indicates the status of the Media
            Processor Control Link ('up' or 'dn') for the duplicate media 
            processor board."
        ::= { g3statmedproEntry 36 }

    g3statmedproDupLinkEth	OBJECT-TYPE
        SYNTAX    DisplayString (SIZE (0..2))
        ACCESS    read-only
        STATUS    mandatory
        DESCRIPTION
            "A DisplayString Object that indicates the status of the Ethernet
            Link ('up' or 'dn') for the duplicate media processor board."
        ::= { g3statmedproEntry 37 }

    g3statmedproDupLinkPeer	OBJECT-TYPE
        SYNTAX    DisplayString (SIZE (0..2))
        ACCESS    read-only
        STATUS    mandatory
        DESCRIPTION
            "A DisplayString Object that indicates the status of the Peer
            Link ('up' or 'dn') for the duplicate media processor board."
        ::= { g3statmedproEntry 38 }

    g3statmedproDupAlarmMaj	OBJECT-TYPE
        SYNTAX    DisplayString (SIZE (0..2))
        ACCESS    read-only
        STATUS    mandatory
        DESCRIPTION
            "A DisplayString Object that indicates the number of major alarms
            active on the duplicate media processor board. "
        ::= { g3statmedproEntry 39 }

    g3statmedproDupAlarmMin	OBJECT-TYPE
        SYNTAX    DisplayString (SIZE (0..2))
        ACCESS    read-only
        STATUS    mandatory
        DESCRIPTION
            "A DisplayString Object that indicates the number of minor alarms
            active on the duplicate media processor board. "
        ::= { g3statmedproEntry 40 }

    g3statmedproDupAlarmWrn	OBJECT-TYPE
        SYNTAX    DisplayString (SIZE (0..2))
        ACCESS    read-only
        STATUS    mandatory
        DESCRIPTION
            "A DisplayString Object that indicates the number of warning alarms
            active on the duplicate media processor board. "
        ::= { g3statmedproEntry 41 }

    g3statmedproLocked	OBJECT-TYPE
        SYNTAX    DisplayString (SIZE (0..3))
        ACCESS    read-only
        STATUS    mandatory
        DESCRIPTION
            "A DisplayString Object that indicates whether the set medpro
            override and lock command argument is in use (yes or no)."
        ::= { g3statmedproEntry 42 }

    g3statmedproSourceIPV6	OBJECT-TYPE
        SYNTAX    DisplayString (SIZE (0..40))
        ACCESS    read-only
        STATUS    mandatory
        DESCRIPTION
            "A DisplayString Object that contains the source IPV6 address for
            the media processor board."
        ::= { g3statmedproEntry 43 }

    g3statmedproIPV6SubnetMask	OBJECT-TYPE
        SYNTAX    DisplayString (SIZE (0..40))
        ACCESS    read-only
        STATUS    mandatory
        DESCRIPTION
            "A DisplayString Object that contains the IPV6 subnet mask for the 
            media processor board."
        ::= { g3statmedproEntry 44 }

    g3statmedproIPV6GatewayAddr	OBJECT-TYPE
        SYNTAX    DisplayString (SIZE (0..40))
        ACCESS    read-only
        STATUS    mandatory
        DESCRIPTION
            "A DisplayString Object that contains the IPV6 address of the Gateway."
        ::= { g3statmedproEntry 45 }

    g3statmedproIPV6NodeName	OBJECT-TYPE
        SYNTAX    DisplayString (SIZE (0..15))
        ACCESS    read-only
        STATUS    mandatory
        DESCRIPTION
            "A DisplayString Object that contains the IPV6 node name for the	
            media processor board."
        ::= { g3statmedproEntry 46 }

    g3statmedproIPV6EtherEnable	OBJECT-TYPE
        SYNTAX    DisplayString (SIZE (0..3))
        ACCESS    read-only
        STATUS    mandatory
        DESCRIPTION
            "A DisplayString Object that designates whether or not the IPV6 
            interface is enabled (yes or no) for the media processor board.	"
        ::= { g3statmedproEntry 47 }


    -- the g3ipunreg group

    g3ipunregTage	OBJECT-TYPE
        SYNTAX    INTEGER
        ACCESS    read-only
        STATUS    mandatory
        DESCRIPTION
            "The number of timeticks since the list of unregistered IP phones
            was last extracted from the switch by the Proxy Agent. This object 
            along with the g3ipunregTintvl object allows the Network Manager 
            to determine the validity of the data in the cache and to control 
            when the Proxy Agent extracts the data from the switch."
        ::= { g3ipunreg 1 }

    g3ipunregTintvl	OBJECT-TYPE
        SYNTAX    INTEGER
        ACCESS    read-write
        STATUS    mandatory
        DESCRIPTION
            "An object containing the interval for which the data extracted 
            from the switch is considered valid by the Proxy Agent. When a 
            GET or GET-NEXT request for the data is received by the agent 
            it uses the g3ipunregTage and g3ipunregTintvl objects to determine 
            whether it should refresh the data."
        ::= { g3ipunreg 2 }

    g3ipunregTdelay	OBJECT-TYPE
        SYNTAX    INTEGER
        ACCESS    read-only
        STATUS    mandatory
        DESCRIPTION
            "An object containing the delay encountered in updating the 
            cached data."
        ::= { g3ipunreg 3 }

    g3ipunregTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached 
            data is being retrieved and otherwise 'current'.This object 
            may be set to 'update' to force a refresh of the cache."
        ::= { g3ipunreg 4 }

    g3ipunregTcount	OBJECT-TYPE
        SYNTAX    Gauge
        ACCESS    read-only
        STATUS    mandatory
        DESCRIPTION
            "A Gauge object containing the number of data records in the cache."
        ::= { g3ipunreg 5 }

    g3ipunregTable	OBJECT-TYPE
        SYNTAX    SEQUENCE OF G3ipunregEntry
        ACCESS    not-accessible
        STATUS    mandatory
        DESCRIPTION
            "A list of g3ipunreg entries."
        ::= { g3ipunreg 6 }

    g3ipunregEntry	OBJECT-TYPE
        SYNTAX    G3ipunregEntry
        ACCESS    not-accessible
        STATUS    mandatory
        DESCRIPTION
            "A g3ipunreg entry containing objects of the
            g3ipunreg information sent by the switch."
        INDEX    { g3ipunregStatExtn }
        ::= { g3ipunregTable 1 }

    G3ipunregEntry ::= SEQUENCE {
        g3ipunregStatExtn
            DisplayString,
        g3ipunregStatPort
            DisplayString,
        g3ipunregStatReg
            DisplayString
        }

    g3ipunregStatExtn	OBJECT-TYPE
        SYNTAX    DisplayString (SIZE (0..15))
        ACCESS    read-only
        STATUS    mandatory
        DESCRIPTION
            "An object containing the extension of the unregistered IP telephone."
        ::= { g3ipunregEntry 1 }

    g3ipunregStatPort	OBJECT-TYPE
        SYNTAX    DisplayString (SIZE (0..7))
        ACCESS    read-only
        STATUS    mandatory
        DESCRIPTION
            "An object containing the port location of the unregistered IP telephone."
        ::= { g3ipunregEntry 2 }

    g3ipunregStatReg	OBJECT-TYPE
        SYNTAX    DisplayString (SIZE (0..1))
        ACCESS    read-only
        STATUS    mandatory
        DESCRIPTION
            "An object containing the registration status of the IP telephone
            (y or n)."
        ::= { g3ipunregEntry 3 }


    -- the g3commlink group

    g3commlinkTage	OBJECT-TYPE
        SYNTAX    INTEGER
        ACCESS    read-only
        STATUS    mandatory
        DESCRIPTION
            "The number of timeticks since the communication interface link
            data was last extracted from the switch by the G3 Proxy Agent. This 
            object along with the g3commlinkTintvl object allows the Network Manager
            to determine the validity of the data in the cache and to control 
            when the proxy agent extracts the data from the switch."
        ::= { g3commlink 1 }

    g3commlinkTintvl	OBJECT-TYPE
        SYNTAX    INTEGER
        ACCESS    read-write
        STATUS    mandatory
        DESCRIPTION
            "An object containing the interval for which the data extracted 
            from the switch is considered valid by the Proxy Agent.
            When a GET or GET-NEXT request for these objects is received 
            by the agent it uses the g3commlinkTage and g3commlinkTintvl objects 
            to determine whether it should refresh the cached data."
        ::= { g3commlink 2 }

    g3commlinkTdelay	OBJECT-TYPE
        SYNTAX    INTEGER
        ACCESS    read-only
        STATUS    mandatory
        DESCRIPTION
            "An object containing the delay encountered in updating the cached data"
        ::= { g3commlink 3 }

    g3commlinkTretrieve	OBJECT-TYPE
        SYNTAX    INTEGER
		  {
			failed(1),	-- cache data is corrupted
			update(2),	-- update the cached data
			current(3)	-- cached data is current
		  }
        ACCESS    read-write
        STATUS    mandatory
        DESCRIPTION
            "An INTEGER object containing a flag that is 'update' if the cached
            data is being retrieved and otherwise 'current'.  This object may
            be set to 'update' to force a refresh of the cache."
        ::= { g3commlink 4 }

    g3commlinkTcount	OBJECT-TYPE
        SYNTAX    Gauge
        ACCESS    read-only
        STATUS    mandatory
        DESCRIPTION
            "A Gauge object containing the number of data records in the cache."
        ::= { g3commlink 5 }

    g3commlinkTable	OBJECT-TYPE
        SYNTAX    SEQUENCE OF G3commlinkEntry
        ACCESS    not-accessible
        STATUS    mandatory
        DESCRIPTION
            "A list of g3commlink entries."
        ::= { g3commlink 6 }

    g3commlinkEntry	OBJECT-TYPE
        SYNTAX    G3commlinkEntry
        ACCESS    not-accessible
        STATUS    mandatory
        DESCRIPTION
            "A g3commlink entry containing objects of the
            g3commlink information sent by the switch."
        INDEX    { g3commlinkLinkNumber }
        ::= { g3commlinkTable 1 }

    G3commlinkEntry ::= SEQUENCE {
        g3commlinkLinkNumber
            INTEGER,
        g3commlinkLinkType
            DisplayString,
        g3commlinkEnableLink
            DisplayString,
        g3commlinkEstablishConn
            DisplayString,
        g3commlinkExtension
            DisplayString,
        g3commlinkDestNumber
            DisplayString,
        g3commlinkConnModule
            DisplayString,
        g3commlinkName
            DisplayString
        }

    g3commlinkLinkNumber	OBJECT-TYPE
        SYNTAX    INTEGER
        ACCESS    read-only
        STATUS    mandatory
        DESCRIPTION
            "An object containing the system link number (1-99)."
        ::= { g3commlinkEntry 1 }

    g3commlinkLinkType	OBJECT-TYPE
        SYNTAX    DisplayString (SIZE (0..5))
        ACCESS    read-only
        STATUS    mandatory
        DESCRIPTION
            "An object containing the system link type."
        ::= { g3commlinkEntry 2 }

    g3commlinkEnableLink	OBJECT-TYPE
        SYNTAX    DisplayString (SIZE (0..1))
        ACCESS    read-only
        STATUS    mandatory
        DESCRIPTION
            "An object containing a flag indicating whether the link is
            enabled (y/n)."
        ::= { g3commlinkEntry 3 }

    g3commlinkEstablishConn	OBJECT-TYPE
        SYNTAX    DisplayString (SIZE (0..1))
        ACCESS    read-only
        STATUS    mandatory
        DESCRIPTION
            "An object containing a flag indicating whether a connection has
            been established (y/n)."
        ::= { g3commlinkEntry 4 }

    g3commlinkExtension	OBJECT-TYPE
        SYNTAX    DisplayString (SIZE (0..15))
        ACCESS    read-only
        STATUS    mandatory
        DESCRIPTION
            "An object containing the extension number of the link."
        ::= { g3commlinkEntry 5 }

    g3commlinkDestNumber	OBJECT-TYPE
        SYNTAX    DisplayString (SIZE (0..10))
        ACCESS    read-only
        STATUS    mandatory
        DESCRIPTION
            "An object containing the destination extension number."
        ::= { g3commlinkEntry 6 }

    g3commlinkConnModule	OBJECT-TYPE
        SYNTAX    DisplayString (SIZE (0..8))
        ACCESS    read-only
        STATUS    mandatory
        DESCRIPTION
            "An object containing the extension number of the connected data
            module."
        ::= { g3commlinkEntry 7 }

    g3commlinkName	OBJECT-TYPE
        SYNTAX    DisplayString (SIZE (0..27))
        ACCESS    read-only
        STATUS    mandatory
        DESCRIPTION
            "An object containing a description of the link."
        ::= { g3commlinkEntry 8 }


    -- the g3statlink group

    g3statlinkTage	OBJECT-TYPE
        SYNTAX    INTEGER
        ACCESS    read-only
        STATUS    mandatory
        DESCRIPTION
            "The number of timeticks since the link status was last extracted 
            from the switch by the Proxy Agent. This object along with the
            g3statlinkTintvl object allows the Network Manager to determine 
            the validity of the data in the cache and to control when the 
            Proxy Agent extracts the data from the switch."
        ::= { g3statlink 1 }

    g3statlinkTintvl	OBJECT-TYPE
        SYNTAX    INTEGER
        ACCESS    read-write
        STATUS    mandatory
        DESCRIPTION
            "An object containing the interval for which the data extracted 
            from the switch is considered valid by the Proxy Agent. When a 
            GET or GET-NEXT request for the data is received by the agent 
            it uses the g3statlinkTage and g3statlinkTintvl objects to determine 
            whether it should refresh the data."
        ::= { g3statlink 2 }

    g3statlinkTdelay	OBJECT-TYPE
        SYNTAX    INTEGER
        ACCESS    read-only
        STATUS    mandatory
        DESCRIPTION
            "An object containing the delay encountered in updating the 
            cached data."
        ::= { g3statlink 3 }

    g3statlinkTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached 
            data is being retrieved and otherwise 'current'.This object 
            may be set to 'update' to force a refresh of the cache."
        ::= { g3statlink 4 }

    g3statlinkTcount	OBJECT-TYPE
        SYNTAX    Gauge
        ACCESS    read-only
        STATUS    mandatory
        DESCRIPTION
            "A Gauge object containing the number of data records in the cache."
        ::= { g3statlink 5 }

    g3statlinkTable	OBJECT-TYPE
        SYNTAX    SEQUENCE OF G3statlinkEntry
        ACCESS    not-accessible
        STATUS    mandatory
        DESCRIPTION
            "A list of g3statlink entries."
        ::= { g3statlink 6 }

    g3statlinkEntry	OBJECT-TYPE
        SYNTAX    G3statlinkEntry
        ACCESS    not-accessible
        STATUS    mandatory
        DESCRIPTION
            "A g3statlink entry containing objects of the
            g3statlink information sent by the switch."
        INDEX    { g3statlinkSysLinkNumber }
        ::= { g3statlinkTable 1 }

    G3statlinkEntry ::= SEQUENCE {
        g3statlinkSysLinkNumber
            INTEGER,
        g3statlinkCLANBoardLoc
            DisplayString,
        g3statlinkDOLANSessions
            INTEGER,
        g3statlinkIncRcvdUniPkt
            INTEGER,
        g3statlinkIncRcvdMulPkt
            INTEGER,
        g3statlinkIncRcvdOctet
            INTEGER,
        g3statlinkIncDrpErrPkt
            INTEGER,
        g3statlinkIncDrpDisPkt
            INTEGER,
        g3statlinkOtgTransUniPkt
            INTEGER,
        g3statlinkOtgTransMulPkt
            INTEGER,
        g3statlinkOutTransOctet
            INTEGER,
        g3statlinkOtgDrpErrPkt
            INTEGER,
        g3statlinkOtgDrpDisPkt
            INTEGER
        }

    g3statlinkSysLinkNumber	OBJECT-TYPE
        SYNTAX    INTEGER
        ACCESS    read-only
        STATUS    mandatory
        DESCRIPTION
            "An object containing the system link number for the CLAN board."
        ::= { g3statlinkEntry 1 }

    g3statlinkCLANBoardLoc	OBJECT-TYPE
        SYNTAX    DisplayString (SIZE (0..8))
        ACCESS    read-only
        STATUS    mandatory
        DESCRIPTION
            "An object containing the location of the CLAN board."
        ::= { g3statlinkEntry 2 }

    g3statlinkDOLANSessions	OBJECT-TYPE
        SYNTAX    INTEGER
        ACCESS    read-only
        STATUS    mandatory
        DESCRIPTION
            "An object containing the number of current IP registrations
            through the CLAN board."
        ::= { g3statlinkEntry 3 }

    g3statlinkIncRcvdUniPkt	OBJECT-TYPE
        SYNTAX    INTEGER
        ACCESS    read-only
        STATUS    mandatory
        DESCRIPTION
            "An object containing the number of unicast packets received"
        ::= { g3statlinkEntry 4 }

    g3statlinkIncRcvdMulPkt	OBJECT-TYPE
        SYNTAX    INTEGER
        ACCESS    read-only
        STATUS    mandatory
        DESCRIPTION
            "An object containing the number of multicast packets received"
        ::= { g3statlinkEntry 5 }

    g3statlinkIncRcvdOctet	OBJECT-TYPE
        SYNTAX    INTEGER
        ACCESS    read-only
        STATUS    mandatory
        DESCRIPTION
            "An object containing the number of octects received"
        ::= { g3statlinkEntry 6 }

    g3statlinkIncDrpErrPkt	OBJECT-TYPE
        SYNTAX    INTEGER
        ACCESS    read-only
        STATUS    mandatory
        DESCRIPTION
            "An object containing the number of incomming error packets "
        ::= { g3statlinkEntry 7 }

    g3statlinkIncDrpDisPkt	OBJECT-TYPE
        SYNTAX    INTEGER
        ACCESS    read-only
        STATUS    mandatory
        DESCRIPTION
            "An object containing the number of incomming discard packets "
        ::= { g3statlinkEntry 8 }

    g3statlinkOtgTransUniPkt	OBJECT-TYPE
        SYNTAX    INTEGER
        ACCESS    read-only
        STATUS    mandatory
        DESCRIPTION
            "An object containing the number of unicast packets transmitted"
        ::= { g3statlinkEntry 9 }

    g3statlinkOtgTransMulPkt	OBJECT-TYPE
        SYNTAX    INTEGER
        ACCESS    read-only
        STATUS    mandatory
        DESCRIPTION
            "An object containing the number of multicast packets transmitted"
        ::= { g3statlinkEntry 10 }

    g3statlinkOutTransOctet	OBJECT-TYPE
        SYNTAX    INTEGER
        ACCESS    read-only
        STATUS    mandatory
        DESCRIPTION
            "An object containing the number of octects received"
        ::= { g3statlinkEntry 11 }

    g3statlinkOtgDrpErrPkt	OBJECT-TYPE
        SYNTAX    INTEGER
        ACCESS    read-only
        STATUS    mandatory
        DESCRIPTION
            "An object containing the number of outgoing error packets "
        ::= { g3statlinkEntry 12 }

    g3statlinkOtgDrpDisPkt	OBJECT-TYPE
        SYNTAX    INTEGER
        ACCESS    read-only
        STATUS    mandatory
        DESCRIPTION
            "An object containing the number of outgoing discard packets "
        ::= { g3statlinkEntry 13 }


    -- the g3covpath group

    g3covpathTage	OBJECT-TYPE
        SYNTAX    INTEGER
        ACCESS    read-only
        STATUS    mandatory
        DESCRIPTION
            "The number of timeticks since the coverage path data was last extracted 
            from the switch by the Proxy Agent. This object along with the
            g3covpathTintvl object allows the Network Manager to determine 
            the validity of the data in the cache and to control when the 
            Proxy Agent extracts the data from the switch."
        ::= { g3covpath 1 }

    g3covpathTintvl	OBJECT-TYPE
        SYNTAX    INTEGER
        ACCESS    read-write
        STATUS    mandatory
        DESCRIPTION
            "An object containing the interval for which the data extracted 
            from the switch is considered valid by the Proxy Agent. When a 
            GET or GET-NEXT request for the data is received by the agent 
            it uses the g3covpathTage and g3covpathTintvl objects to determine 
            whether it should refresh the data."
        ::= { g3covpath 2 }

    g3covpathTdelay	OBJECT-TYPE
        SYNTAX    INTEGER
        ACCESS    read-only
        STATUS    mandatory
        DESCRIPTION
            "An object containing the delay encountered in updating the 
            cached data."
        ::= { g3covpath 3 }

    g3covpathTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached 
            data is being retrieved and otherwise 'current'.This object 
            may be set to 'update' to force a refresh of the cache."
        ::= { g3covpath 4 }

    g3covpathTcount	OBJECT-TYPE
        SYNTAX    Gauge
        ACCESS    read-only
        STATUS    mandatory
        DESCRIPTION
            "A Gauge object containing the number of data records in the cache."
        ::= { g3covpath 5 }

    g3covpathTable	OBJECT-TYPE
        SYNTAX    SEQUENCE OF G3covpathEntry
        ACCESS    not-accessible
        STATUS    mandatory
        DESCRIPTION
            "A list of g3covpath entries."
        ::= { g3covpath 6 }

    g3covpathEntry	OBJECT-TYPE
        SYNTAX    G3covpathEntry
        ACCESS    not-accessible
        STATUS    mandatory
        DESCRIPTION
            "A g3covpath entry containing objects of the
            g3covpath information sent by the switch."
        INDEX    { g3covpathCoveragePath }
        ::= { g3covpathTable 1 }

    G3covpathEntry ::= SEQUENCE {
        g3covpathCoveragePath
            INTEGER,
        g3covpathMeasHour
            INTEGER,
        g3covpathCallsOffTotal
            INTEGER,
        g3covpathCallsOffAct
            INTEGER,
        g3covpathCallsOffBusy
            INTEGER,
        g3covpathCallsOffDA
            INTEGER,
        g3covpathCallsOffCA
            INTEGER,
        g3covpathCallsOffSAC
            INTEGER,
        g3covpathCallsOffCB
            INTEGER,
        g3covpathPoint1Ans
            DisplayString,
        g3covpathPoint2Ans
            DisplayString,
        g3covpathPoint3Ans
            DisplayString,
        g3covpathPoint4Ans
            DisplayString,
        g3covpathPoint5Ans
            DisplayString,
        g3covpathPoint6Ans
            DisplayString,
        g3covpathPoint1Aband
            DisplayString,
        g3covpathPoint2Aband
            DisplayString,
        g3covpathPoint3Aband
            DisplayString,
        g3covpathPoint4Aband
            DisplayString,
        g3covpathPoint5Aband
            DisplayString,
        g3covpathPoint6Aband
            DisplayString
        }

    g3covpathCoveragePath	OBJECT-TYPE
        SYNTAX    INTEGER
        ACCESS    read-only
        STATUS    mandatory
        DESCRIPTION
            "An object containing the measured coverage path."
        ::= { g3covpathEntry 1 }

    g3covpathMeasHour	OBJECT-TYPE
        SYNTAX    INTEGER
        ACCESS    read-only
        STATUS    mandatory
        DESCRIPTION
            "An object containing the starting time of the hour during which
            the greatest number of calls are offered to the coverage path."
        ::= { g3covpathEntry 2 }

    g3covpathCallsOffTotal	OBJECT-TYPE
        SYNTAX    INTEGER
        ACCESS    read-only
        STATUS    mandatory
        DESCRIPTION
            "An object containing the number of calls offered to the coverage
            path."
        ::= { g3covpathEntry 3 }

    g3covpathCallsOffAct	OBJECT-TYPE
        SYNTAX    INTEGER
        ACCESS    read-only
        STATUS    mandatory
        DESCRIPTION
            "An object containing the number of calls offered to the coverage
            path due to the principal being active."
        ::= { g3covpathEntry 4 }

    g3covpathCallsOffBusy	OBJECT-TYPE
        SYNTAX    INTEGER
        ACCESS    read-only
        STATUS    mandatory
        DESCRIPTION
            "An object containing the number of calls offered to the coverage
            path due to the principal being busy."
        ::= { g3covpathEntry 5 }

    g3covpathCallsOffDA	OBJECT-TYPE
        SYNTAX    INTEGER
        ACCESS    read-only
        STATUS    mandatory
        DESCRIPTION
            "An object containing the number of calls offered to the coverage
            path because the principal did not answer the call after the
            administered number of rings."
        ::= { g3covpathEntry 6 }

    g3covpathCallsOffCA	OBJECT-TYPE
        SYNTAX    INTEGER
        ACCESS    read-only
        STATUS    mandatory
        DESCRIPTION
            "An object containing the number of calls offered to the coverage
            path due to the principal's use of Cover All."
        ::= { g3covpathEntry 7 }

    g3covpathCallsOffSAC	OBJECT-TYPE
        SYNTAX    INTEGER
        ACCESS    read-only
        STATUS    mandatory
        DESCRIPTION
            "An object containing the number of calls offered to the coverage
            path due to the principal's use of Send All Calls or the calling
            party using Go To Coverage."
        ::= { g3covpathEntry 8 }

    g3covpathCallsOffCB	OBJECT-TYPE
        SYNTAX    INTEGER
        ACCESS    read-only
        STATUS    mandatory
        DESCRIPTION
            "An object containing the number of calls offered to the coverage
            path where the calling party used LWC or ACB before a coverage
            point answered the call."
        ::= { g3covpathEntry 9 }

    g3covpathPoint1Ans	OBJECT-TYPE
        SYNTAX    DisplayString (SIZE (0..4))
        ACCESS    read-only
        STATUS    mandatory
        DESCRIPTION
            "An object containing the total number of calls answered by the
            specified point."
        ::= { g3covpathEntry 10 }

    g3covpathPoint2Ans	OBJECT-TYPE
        SYNTAX    DisplayString (SIZE (0..4))
        ACCESS    read-only
        STATUS    mandatory
        DESCRIPTION
            "An object containing the total number of calls answered by the
            specified point."
        ::= { g3covpathEntry 11 }

    g3covpathPoint3Ans	OBJECT-TYPE
        SYNTAX    DisplayString (SIZE (0..4))
        ACCESS    read-only
        STATUS    mandatory
        DESCRIPTION
            "An object containing the total number of calls answered by the
            specified point."
        ::= { g3covpathEntry 12 }

    g3covpathPoint4Ans	OBJECT-TYPE
        SYNTAX    DisplayString (SIZE (0..4))
        ACCESS    read-only
        STATUS    mandatory
        DESCRIPTION
            "An object containing the total number of calls answered by the
            specified point."
        ::= { g3covpathEntry 13 }

    g3covpathPoint5Ans	OBJECT-TYPE
        SYNTAX    DisplayString (SIZE (0..4))
        ACCESS    read-only
        STATUS    mandatory
        DESCRIPTION
            "An object containing the total number of calls answered by the
            specified point."
        ::= { g3covpathEntry 14 }

    g3covpathPoint6Ans	OBJECT-TYPE
        SYNTAX    DisplayString (SIZE (0..4))
        ACCESS    read-only
        STATUS    mandatory
        DESCRIPTION
            "An object containing the total number of calls answered by the
            specified point."
        ::= { g3covpathEntry 15 }

    g3covpathPoint1Aband	OBJECT-TYPE
        SYNTAX    DisplayString (SIZE (0..4))
        ACCESS    read-only
        STATUS    mandatory
        DESCRIPTION
            "An object containing the total number of calls abandoned by the
            caller while ringing at the specified point."
        ::= { g3covpathEntry 16 }

    g3covpathPoint2Aband	OBJECT-TYPE
        SYNTAX    DisplayString (SIZE (0..4))
        ACCESS    read-only
        STATUS    mandatory
        DESCRIPTION
            "An object containing the total number of calls abandoned by the
            caller while ringing at the specified point."
        ::= { g3covpathEntry 17 }

    g3covpathPoint3Aband	OBJECT-TYPE
        SYNTAX    DisplayString (SIZE (0..4))
        ACCESS    read-only
        STATUS    mandatory
        DESCRIPTION
            "An object containing the total number of calls abandoned by the
            caller while ringing at the specified point."
        ::= { g3covpathEntry 18 }

    g3covpathPoint4Aband	OBJECT-TYPE
        SYNTAX    DisplayString (SIZE (0..4))
        ACCESS    read-only
        STATUS    mandatory
        DESCRIPTION
            "An object containing the total number of calls abandoned by the
            caller while ringing at the specified point."
        ::= { g3covpathEntry 19 }

    g3covpathPoint5Aband	OBJECT-TYPE
        SYNTAX    DisplayString (SIZE (0..4))
        ACCESS    read-only
        STATUS    mandatory
        DESCRIPTION
            "An object containing the total number of calls abandoned by the
            caller while ringing at the specified point."
        ::= { g3covpathEntry 20 }

    g3covpathPoint6Aband	OBJECT-TYPE
        SYNTAX    DisplayString (SIZE (0..4))
        ACCESS    read-only
        STATUS    mandatory
        DESCRIPTION
            "An object containing the total number of calls abandoned by the
            caller while ringing at the specified point."
        ::= { g3covpathEntry 21 }


    -- the g3pkcovpath group

    g3pkcovpathTage	OBJECT-TYPE
        SYNTAX    INTEGER
        ACCESS    read-only
        STATUS    mandatory
        DESCRIPTION
            "The number of timeticks since the coverage path data was last extracted 
            from the switch by the Proxy Agent. This object along with the
            g3pkcovpathTintvl object allows the Network Manager to determine 
            the validity of the data in the cache and to control when the 
            Proxy Agent extracts the data from the switch."
        ::= { g3pkcovpath 1 }

    g3pkcovpathTintvl	OBJECT-TYPE
        SYNTAX    INTEGER
        ACCESS    read-write
        STATUS    mandatory
        DESCRIPTION
            "An object containing the interval for which the data extracted 
            from the switch is considered valid by the Proxy Agent. When a 
            GET or GET-NEXT request for the data is received by the agent 
            it uses the g3pkcovpathTage and g3pkcovpathTintvl objects to determine 
            whether it should refresh the data."
        ::= { g3pkcovpath 2 }

    g3pkcovpathTdelay	OBJECT-TYPE
        SYNTAX    INTEGER
        ACCESS    read-only
        STATUS    mandatory
        DESCRIPTION
            "An object containing the delay encountered in updating the 
            cached data."
        ::= { g3pkcovpath 3 }

    g3pkcovpathTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached 
            data is being retrieved and otherwise 'current'.This object 
            may be set to 'update' to force a refresh of the cache."
        ::= { g3pkcovpath 4 }

    g3pkcovpathTcount	OBJECT-TYPE
        SYNTAX    Gauge
        ACCESS    read-only
        STATUS    mandatory
        DESCRIPTION
            "A Gauge object containing the number of data records in the cache."
        ::= { g3pkcovpath 5 }

    g3pkcovpathTable	OBJECT-TYPE
        SYNTAX    SEQUENCE OF G3pkcovpathEntry
        ACCESS    not-accessible
        STATUS    mandatory
        DESCRIPTION
            "A list of g3pkcovpath entries."
        ::= { g3pkcovpath 6 }

    g3pkcovpathEntry	OBJECT-TYPE
        SYNTAX    G3pkcovpathEntry
        ACCESS    not-accessible
        STATUS    mandatory
        DESCRIPTION
            "A g3pkcovpath entry containing objects of the
            g3pkcovpath information sent by the switch."
        INDEX    { g3pkcovpathCoveragePath }
        ::= { g3pkcovpathTable 1 }

    G3pkcovpathEntry ::= SEQUENCE {
        g3pkcovpathCoveragePath
            INTEGER,
        g3pkcovpathMeasHour
            INTEGER,
        g3pkcovpathCallsOffTotal
            INTEGER,
        g3pkcovpathCallsOffAct
            INTEGER,
        g3pkcovpathCallsOffBusy
            INTEGER,
        g3pkcovpathCallsOffDA
            INTEGER,
        g3pkcovpathCallsOffCA
            INTEGER,
        g3pkcovpathCallsOffSAC
            INTEGER,
        g3pkcovpathCallsOffCB
            INTEGER,
        g3pkcovpathPoint1Ans
            DisplayString,
        g3pkcovpathPoint2Ans
            DisplayString,
        g3pkcovpathPoint3Ans
            DisplayString,
        g3pkcovpathPoint4Ans
            DisplayString,
        g3pkcovpathPoint5Ans
            DisplayString,
        g3pkcovpathPoint6Ans
            DisplayString,
        g3pkcovpathPoint1Aband
            DisplayString,
        g3pkcovpathPoint2Aband
            DisplayString,
        g3pkcovpathPoint3Aband
            DisplayString,
        g3pkcovpathPoint4Aband
            DisplayString,
        g3pkcovpathPoint5Aband
            DisplayString,
        g3pkcovpathPoint6Aband
            DisplayString
        }

    g3pkcovpathCoveragePath	OBJECT-TYPE
        SYNTAX    INTEGER
        ACCESS    read-only
        STATUS    mandatory
        DESCRIPTION
            "An object containing the measured coverage path."
        ::= { g3pkcovpathEntry 1 }

    g3pkcovpathMeasHour	OBJECT-TYPE
        SYNTAX    INTEGER
        ACCESS    read-only
        STATUS    mandatory
        DESCRIPTION
            "An object containing the starting time of the hour during which
            the greatest number of calls are offered to the coverage path."
        ::= { g3pkcovpathEntry 2 }

    g3pkcovpathCallsOffTotal	OBJECT-TYPE
        SYNTAX    INTEGER
        ACCESS    read-only
        STATUS    mandatory
        DESCRIPTION
            "An object containing the number of calls offered to the coverage
            path."
        ::= { g3pkcovpathEntry 3 }

    g3pkcovpathCallsOffAct	OBJECT-TYPE
        SYNTAX    INTEGER
        ACCESS    read-only
        STATUS    mandatory
        DESCRIPTION
            "An object containing the number of calls offered to the coverage
            path due to the principal being active."
        ::= { g3pkcovpathEntry 4 }

    g3pkcovpathCallsOffBusy	OBJECT-TYPE
        SYNTAX    INTEGER
        ACCESS    read-only
        STATUS    mandatory
        DESCRIPTION
            "An object containing the number of calls offered to the coverage
            path due to the principal being busy."
        ::= { g3pkcovpathEntry 5 }

    g3pkcovpathCallsOffDA	OBJECT-TYPE
        SYNTAX    INTEGER
        ACCESS    read-only
        STATUS    mandatory
        DESCRIPTION
            "An object containing the number of calls offered to the coverage
            path because the principal did not answer the call after the
            administered number of rings."
        ::= { g3pkcovpathEntry 6 }

    g3pkcovpathCallsOffCA	OBJECT-TYPE
        SYNTAX    INTEGER
        ACCESS    read-only
        STATUS    mandatory
        DESCRIPTION
            "An object containing the number of calls offered to the coverage
            path due to the principal's use of Cover All."
        ::= { g3pkcovpathEntry 7 }

    g3pkcovpathCallsOffSAC	OBJECT-TYPE
        SYNTAX    INTEGER
        ACCESS    read-only
        STATUS    mandatory
        DESCRIPTION
            "An object containing the number of calls offered to the coverage
            path due to the principal's use of Send All Calls or the calling
            party using Go To Coverage."
        ::= { g3pkcovpathEntry 8 }

    g3pkcovpathCallsOffCB	OBJECT-TYPE
        SYNTAX    INTEGER
        ACCESS    read-only
        STATUS    mandatory
        DESCRIPTION
            "An object containing the number of calls offered to the coverage
            path where the calling party used LWC or ACB before a coverage
            point answered the call."
        ::= { g3pkcovpathEntry 9 }

    g3pkcovpathPoint1Ans	OBJECT-TYPE
        SYNTAX    DisplayString (SIZE (0..4))
        ACCESS    read-only
        STATUS    mandatory
        DESCRIPTION
            "An object containing the total number of calls answered by the
            specified point."
        ::= { g3pkcovpathEntry 10 }

    g3pkcovpathPoint2Ans	OBJECT-TYPE
        SYNTAX    DisplayString (SIZE (0..4))
        ACCESS    read-only
        STATUS    mandatory
        DESCRIPTION
            "An object containing the total number of calls answered by the
            specified point."
        ::= { g3pkcovpathEntry 11 }

    g3pkcovpathPoint3Ans	OBJECT-TYPE
        SYNTAX    DisplayString (SIZE (0..4))
        ACCESS    read-only
        STATUS    mandatory
        DESCRIPTION
            "An object containing the total number of calls answered by the
            specified point."
        ::= { g3pkcovpathEntry 12 }

    g3pkcovpathPoint4Ans	OBJECT-TYPE
        SYNTAX    DisplayString (SIZE (0..4))
        ACCESS    read-only
        STATUS    mandatory
        DESCRIPTION
            "An object containing the total number of calls answered by the
            specified point."
        ::= { g3pkcovpathEntry 13 }

    g3pkcovpathPoint5Ans	OBJECT-TYPE
        SYNTAX    DisplayString (SIZE (0..4))
        ACCESS    read-only
        STATUS    mandatory
        DESCRIPTION
            "An object containing the total number of calls answered by the
            specified point."
        ::= { g3pkcovpathEntry 14 }

    g3pkcovpathPoint6Ans	OBJECT-TYPE
        SYNTAX    DisplayString (SIZE (0..4))
        ACCESS    read-only
        STATUS    mandatory
        DESCRIPTION
            "An object containing the total number of calls answered by the
            specified point."
        ::= { g3pkcovpathEntry 15 }

    g3pkcovpathPoint1Aband	OBJECT-TYPE
        SYNTAX    DisplayString (SIZE (0..4))
        ACCESS    read-only
        STATUS    mandatory
        DESCRIPTION
            "An object containing the total number of calls abandoned by the
            caller while ringing at the specified point."
        ::= { g3pkcovpathEntry 16 }

    g3pkcovpathPoint2Aband	OBJECT-TYPE
        SYNTAX    DisplayString (SIZE (0..4))
        ACCESS    read-only
        STATUS    mandatory
        DESCRIPTION
            "An object containing the total number of calls abandoned by the
            caller while ringing at the specified point."
        ::= { g3pkcovpathEntry 17 }

    g3pkcovpathPoint3Aband	OBJECT-TYPE
        SYNTAX    DisplayString (SIZE (0..4))
        ACCESS    read-only
        STATUS    mandatory
        DESCRIPTION
            "An object containing the total number of calls abandoned by the
            caller while ringing at the specified point."
        ::= { g3pkcovpathEntry 18 }

    g3pkcovpathPoint4Aband	OBJECT-TYPE
        SYNTAX    DisplayString (SIZE (0..4))
        ACCESS    read-only
        STATUS    mandatory
        DESCRIPTION
            "An object containing the total number of calls abandoned by the
            caller while ringing at the specified point."
        ::= { g3pkcovpathEntry 19 }

    g3pkcovpathPoint5Aband	OBJECT-TYPE
        SYNTAX    DisplayString (SIZE (0..4))
        ACCESS    read-only
        STATUS    mandatory
        DESCRIPTION
            "An object containing the total number of calls abandoned by the
            caller while ringing at the specified point."
        ::= { g3pkcovpathEntry 20 }

    g3pkcovpathPoint6Aband	OBJECT-TYPE
        SYNTAX    DisplayString (SIZE (0..4))
        ACCESS    read-only
        STATUS    mandatory
        DESCRIPTION
            "An object containing the total number of calls abandoned by the
            caller while ringing at the specified point."
        ::= { g3pkcovpathEntry 21 }


    -- the g3principal group

    g3principalTage	OBJECT-TYPE
        SYNTAX    INTEGER
        ACCESS    read-only
        STATUS    mandatory
        DESCRIPTION
            "The number of timeticks since the coverage path data was last extracted 
            from the switch by the Proxy Agent. This object along with the
            g3principalTintvl object allows the Network Manager to determine 
            the validity of the data in the cache and to control when the 
            Proxy Agent extracts the data from the switch."
        ::= { g3principal 1 }

    g3principalTintvl	OBJECT-TYPE
        SYNTAX    INTEGER
        ACCESS    read-write
        STATUS    mandatory
        DESCRIPTION
            "An object containing the interval for which the data extracted 
            from the switch is considered valid by the Proxy Agent. When a 
            GET or GET-NEXT request for the data is received by the agent 
            it uses the g3principalTage and g3principalTintvl objects to determine 
            whether it should refresh the data."
        ::= { g3principal 2 }

    g3principalTdelay	OBJECT-TYPE
        SYNTAX    INTEGER
        ACCESS    read-only
        STATUS    mandatory
        DESCRIPTION
            "An object containing the delay encountered in updating the 
            cached data."
        ::= { g3principal 3 }

    g3principalTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached 
            data is being retrieved and otherwise 'current'.This object 
            may be set to 'update' to force a refresh of the cache."
        ::= { g3principal 4 }

    g3principalTcount	OBJECT-TYPE
        SYNTAX    Gauge
        ACCESS    read-only
        STATUS    mandatory
        DESCRIPTION
            "A Gauge object containing the number of data records in the cache."
        ::= { g3principal 5 }

    g3principalTable	OBJECT-TYPE
        SYNTAX    SEQUENCE OF G3principalEntry
        ACCESS    not-accessible
        STATUS    mandatory
        DESCRIPTION
            "A list of g3principal entries."
        ::= { g3principal 6 }

    g3principalEntry	OBJECT-TYPE
        SYNTAX    G3principalEntry
        ACCESS    not-accessible
        STATUS    mandatory
        DESCRIPTION
            "A g3principal entry containing objects of the
            g3principal information sent by the switch."
        INDEX    { g3principalExtensionTAC }
        ::= { g3principalTable 1 }

    G3principalEntry ::= SEQUENCE {
        g3principalExtensionTAC
            DisplayString,
        g3principalMeasHour
            INTEGER,
        g3principalCallsOffTotal
            INTEGER,
        g3principalCallsAband
            INTEGER,
        g3principalCallsRedirect
            INTEGER,
        g3principalCallsCAC
            INTEGER,
        g3principalCallsCBC
            INTEGER,
        g3principalCallsCDAC
            INTEGER,
        g3principalCallsCCAC
            INTEGER,
        g3principalCallsCSAC
            INTEGER,
        g3principalCallsCSCB
            INTEGER,
        g3principalCovPath1
            INTEGER,
        g3principalCovPath2
            INTEGER,
        g3principalCovPath3
            INTEGER,
        g3principalCovPath4
            INTEGER,
        g3principalCovPath5
            INTEGER,
        g3principalCovPath6
            INTEGER,
        g3principalCovPath7
            INTEGER,
        g3principalCovPath8
            INTEGER
        }

    g3principalExtensionTAC	OBJECT-TYPE
        SYNTAX    DisplayString (SIZE (0..15))
        ACCESS    read-only
        STATUS    mandatory
        DESCRIPTION
            "An object containing the measured coverage path."
        ::= { g3principalEntry 1 }

    g3principalMeasHour	OBJECT-TYPE
        SYNTAX    INTEGER
        ACCESS    read-only
        STATUS    mandatory
        DESCRIPTION
            "An object containing the starting time of the hour during which
            the greatest number of calls are offered to the principal."
        ::= { g3principalEntry 2 }

    g3principalCallsOffTotal	OBJECT-TYPE
        SYNTAX    INTEGER
        ACCESS    read-only
        STATUS    mandatory
        DESCRIPTION
            "An object containing the number of calls offered to the principal.
            path."
        ::= { g3principalEntry 3 }

    g3principalCallsAband	OBJECT-TYPE
        SYNTAX    INTEGER
        ACCESS    read-only
        STATUS    mandatory
        DESCRIPTION
            "An object containing the total number of abandoned calls, where
            the calling party hung up before the call was answered or sent to
            coverage."
        ::= { g3principalEntry 4 }

    g3principalCallsRedirect	OBJECT-TYPE
        SYNTAX    INTEGER
        ACCESS    read-only
        STATUS    mandatory
        DESCRIPTION
            "An object containing the total number of calls not answered by the
            principal and subsequently sent to coverage."
        ::= { g3principalEntry 5 }

    g3principalCallsCAC	OBJECT-TYPE
        SYNTAX    INTEGER
        ACCESS    read-only
        STATUS    mandatory
        DESCRIPTION
            "An object containing the number of calls sent to coverage by this
            principal due to the principal being active."
        ::= { g3principalEntry 6 }

    g3principalCallsCBC	OBJECT-TYPE
        SYNTAX    INTEGER
        ACCESS    read-only
        STATUS    mandatory
        DESCRIPTION
            "An object containing the number of calls to coverage by this
            principal due to the principal being busy."
        ::= { g3principalEntry 7 }

    g3principalCallsCDAC	OBJECT-TYPE
        SYNTAX    INTEGER
        ACCESS    read-only
        STATUS    mandatory
        DESCRIPTION
            "An object containing the number of calls sent to coverage by
            this principal because the principal didn't answer the call after
            the administered number of rings."
        ::= { g3principalEntry 8 }

    g3principalCallsCCAC	OBJECT-TYPE
        SYNTAX    INTEGER
        ACCESS    read-only
        STATUS    mandatory
        DESCRIPTION
            "An object containing the number of calls sent to coverage by
            this principal due to the principal's use of Cover All."
        ::= { g3principalEntry 9 }

    g3principalCallsCSAC	OBJECT-TYPE
        SYNTAX    INTEGER
        ACCESS    read-only
        STATUS    mandatory
        DESCRIPTION
            "An object containing the number of calls sent to coverage by
            this principal due to the principal's use of Send All Calls, or
            because the calling party used the Go To Cover feature."
        ::= { g3principalEntry 10 }

    g3principalCallsCSCB	OBJECT-TYPE
        SYNTAX    INTEGER
        ACCESS    read-only
        STATUS    mandatory
        DESCRIPTION
            "An object containing the number of calls offered to this
            principal where the calling party used LWC or ACB before the
            principal answered the call and before it went to coverage."
        ::= { g3principalEntry 11 }

    g3principalCovPath1	OBJECT-TYPE
        SYNTAX    INTEGER
        ACCESS    read-only
        STATUS    mandatory
        DESCRIPTION
            "An object containing a coverage path used by this principal."
        ::= { g3principalEntry 12 }

    g3principalCovPath2	OBJECT-TYPE
        SYNTAX    INTEGER
        ACCESS    read-only
        STATUS    mandatory
        DESCRIPTION
            "An object containing a coverage path used by this principal."
        ::= { g3principalEntry 13 }

    g3principalCovPath3	OBJECT-TYPE
        SYNTAX    INTEGER
        ACCESS    read-only
        STATUS    mandatory
        DESCRIPTION
            "An object containing a coverage path used by this principal."
        ::= { g3principalEntry 14 }

    g3principalCovPath4	OBJECT-TYPE
        SYNTAX    INTEGER
        ACCESS    read-only
        STATUS    mandatory
        DESCRIPTION
            "An object containing a coverage path used by this principal."
        ::= { g3principalEntry 15 }

    g3principalCovPath5	OBJECT-TYPE
        SYNTAX    INTEGER
        ACCESS    read-only
        STATUS    mandatory
        DESCRIPTION
            "An object containing a coverage path used by this principal."
        ::= { g3principalEntry 16 }

    g3principalCovPath6	OBJECT-TYPE
        SYNTAX    INTEGER
        ACCESS    read-only
        STATUS    mandatory
        DESCRIPTION
            "An object containing a coverage path used by this principal."
        ::= { g3principalEntry 17 }

    g3principalCovPath7	OBJECT-TYPE
        SYNTAX    INTEGER
        ACCESS    read-only
        STATUS    mandatory
        DESCRIPTION
            "An object containing a coverage path used by this principal."
        ::= { g3principalEntry 18 }

    g3principalCovPath8	OBJECT-TYPE
        SYNTAX    INTEGER
        ACCESS    read-only
        STATUS    mandatory
        DESCRIPTION
            "An object containing a coverage path used by this principal."
        ::= { g3principalEntry 19 }


    -- the g3pkprincipal group

    g3pkprincipalTage	OBJECT-TYPE
        SYNTAX    INTEGER
        ACCESS    read-only
        STATUS    mandatory
        DESCRIPTION
            "The number of timeticks since the coverage path data was last extracted 
            from the switch by the Proxy Agent. This object along with the
            g3principalTintvl object allows the Network Manager to determine 
            the validity of the data in the cache and to control when the 
            Proxy Agent extracts the data from the switch."
        ::= { g3pkprincipal 1 }

    g3pkprincipalTintvl	OBJECT-TYPE
        SYNTAX    INTEGER
        ACCESS    read-write
        STATUS    mandatory
        DESCRIPTION
            "An object containing the interval for which the data extracted 
            from the switch is considered valid by the Proxy Agent. When a 
            GET or GET-NEXT request for the data is received by the agent 
            it uses the g3principalTage and g3principalTintvl objects to determine 
            whether it should refresh the data."
        ::= { g3pkprincipal 2 }

    g3pkprincipalTdelay	OBJECT-TYPE
        SYNTAX    INTEGER
        ACCESS    read-only
        STATUS    mandatory
        DESCRIPTION
            "An object containing the delay encountered in updating the 
            cached data."
        ::= { g3pkprincipal 3 }

    g3pkprincipalTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached 
            data is being retrieved and otherwise 'current'.This object 
            may be set to 'update' to force a refresh of the cache."
        ::= { g3pkprincipal 4 }

    g3pkprincipalTcount	OBJECT-TYPE
        SYNTAX    Gauge
        ACCESS    read-only
        STATUS    mandatory
        DESCRIPTION
            "A Gauge object containing the number of data records in the cache."
        ::= { g3pkprincipal 5 }

    g3pkprincipalTable	OBJECT-TYPE
        SYNTAX    SEQUENCE OF G3pkprincipalEntry
        ACCESS    not-accessible
        STATUS    mandatory
        DESCRIPTION
            "A list of g3pkprincipal entries."
        ::= { g3pkprincipal 6 }

    g3pkprincipalEntry	OBJECT-TYPE
        SYNTAX    G3pkprincipalEntry
        ACCESS    not-accessible
        STATUS    mandatory
        DESCRIPTION
            "A g3pkprincipal entry containing objects of the
            g3pkprincipal information sent by the switch."
        INDEX    { g3pkprincipalExtensionTAC }
        ::= { g3pkprincipalTable 1 }

    G3pkprincipalEntry ::= SEQUENCE {
        g3pkprincipalExtensionTAC
            DisplayString,
        g3pkprincipalMeasHour
            INTEGER,
        g3pkprincipalCallsOffTotal
            INTEGER,
        g3pkprincipalCallsAband
            INTEGER,
        g3pkprincipalCallsRedirect
            INTEGER,
        g3pkprincipalCallsCAC
            INTEGER,
        g3pkprincipalCallsCBC
            INTEGER,
        g3pkprincipalCallsCDAC
            INTEGER,
        g3pkprincipalCallsCCAC
            INTEGER,
        g3pkprincipalCallsCSAC
            INTEGER,
        g3pkprincipalCallsCSCB
            INTEGER,
        g3pkprincipalCovPath1
            INTEGER,
        g3pkprincipalCovPath2
            INTEGER,
        g3pkprincipalCovPath3
            INTEGER,
        g3pkprincipalCovPath4
            INTEGER,
        g3pkprincipalCovPath5
            INTEGER,
        g3pkprincipalCovPath6
            INTEGER,
        g3pkprincipalCovPath7
            INTEGER,
        g3pkprincipalCovPath8
            INTEGER
        }

    g3pkprincipalExtensionTAC	OBJECT-TYPE
        SYNTAX    DisplayString (SIZE (0..15))
        ACCESS    read-only
        STATUS    mandatory
        DESCRIPTION
            "An object containing the measured coverage path."
        ::= { g3pkprincipalEntry 1 }

    g3pkprincipalMeasHour	OBJECT-TYPE
        SYNTAX    INTEGER
        ACCESS    read-only
        STATUS    mandatory
        DESCRIPTION
            "An object containing the starting time of the hour during which
            the greatest number of calls are offered to the principal."
        ::= { g3pkprincipalEntry 2 }

    g3pkprincipalCallsOffTotal	OBJECT-TYPE
        SYNTAX    INTEGER
        ACCESS    read-only
        STATUS    mandatory
        DESCRIPTION
            "An object containing the number of calls offered to the principal.
            path."
        ::= { g3pkprincipalEntry 3 }

    g3pkprincipalCallsAband	OBJECT-TYPE
        SYNTAX    INTEGER
        ACCESS    read-only
        STATUS    mandatory
        DESCRIPTION
            "An object containing the total number of abandoned calls, where
            the calling party hung up before the call was answered or sent to
            coverage."
        ::= { g3pkprincipalEntry 4 }

    g3pkprincipalCallsRedirect	OBJECT-TYPE
        SYNTAX    INTEGER
        ACCESS    read-only
        STATUS    mandatory
        DESCRIPTION
            "An object containing the total number of calls not answered by the
            principal and subsequently sent to coverage."
        ::= { g3pkprincipalEntry 5 }

    g3pkprincipalCallsCAC	OBJECT-TYPE
        SYNTAX    INTEGER
        ACCESS    read-only
        STATUS    mandatory
        DESCRIPTION
            "An object containing the number of calls sent to coverage by this
            principal due to the principal being active."
        ::= { g3pkprincipalEntry 6 }

    g3pkprincipalCallsCBC	OBJECT-TYPE
        SYNTAX    INTEGER
        ACCESS    read-only
        STATUS    mandatory
        DESCRIPTION
            "An object containing the number of calls to coverage by this
            principal due to the principal being busy."
        ::= { g3pkprincipalEntry 7 }

    g3pkprincipalCallsCDAC	OBJECT-TYPE
        SYNTAX    INTEGER
        ACCESS    read-only
        STATUS    mandatory
        DESCRIPTION
            "An object containing the number of calls sent to coverage by
            this principal because the principal didn't answer the call after
            the administered number of rings."
        ::= { g3pkprincipalEntry 8 }

    g3pkprincipalCallsCCAC	OBJECT-TYPE
        SYNTAX    INTEGER
        ACCESS    read-only
        STATUS    mandatory
        DESCRIPTION
            "An object containing the number of calls sent to coverage by
            this principal due to the principal's use of Cover All."
        ::= { g3pkprincipalEntry 9 }

    g3pkprincipalCallsCSAC	OBJECT-TYPE
        SYNTAX    INTEGER
        ACCESS    read-only
        STATUS    mandatory
        DESCRIPTION
            "An object containing the number of calls sent to coverage by
            this principal due to the principal's use of Send All Calls, or
            because the calling party used the Go To Cover feature."
        ::= { g3pkprincipalEntry 10 }

    g3pkprincipalCallsCSCB	OBJECT-TYPE
        SYNTAX    INTEGER
        ACCESS    read-only
        STATUS    mandatory
        DESCRIPTION
            "An object containing the number of calls offered to this
            principal where the calling party used LWC or ACB before the
            principal answered the call and before it went to coverage."
        ::= { g3pkprincipalEntry 11 }

    g3pkprincipalCovPath1	OBJECT-TYPE
        SYNTAX    INTEGER
        ACCESS    read-only
        STATUS    mandatory
        DESCRIPTION
            "An object containing a coverage path used by this principal."
        ::= { g3pkprincipalEntry 12 }

    g3pkprincipalCovPath2	OBJECT-TYPE
        SYNTAX    INTEGER
        ACCESS    read-only
        STATUS    mandatory
        DESCRIPTION
            "An object containing a coverage path used by this principal."
        ::= { g3pkprincipalEntry 13 }

    g3pkprincipalCovPath3	OBJECT-TYPE
        SYNTAX    INTEGER
        ACCESS    read-only
        STATUS    mandatory
        DESCRIPTION
            "An object containing a coverage path used by this principal."
        ::= { g3pkprincipalEntry 14 }

    g3pkprincipalCovPath4	OBJECT-TYPE
        SYNTAX    INTEGER
        ACCESS    read-only
        STATUS    mandatory
        DESCRIPTION
            "An object containing a coverage path used by this principal."
        ::= { g3pkprincipalEntry 15 }

    g3pkprincipalCovPath5	OBJECT-TYPE
        SYNTAX    INTEGER
        ACCESS    read-only
        STATUS    mandatory
        DESCRIPTION
            "An object containing a coverage path used by this principal."
        ::= { g3pkprincipalEntry 16 }

    g3pkprincipalCovPath6	OBJECT-TYPE
        SYNTAX    INTEGER
        ACCESS    read-only
        STATUS    mandatory
        DESCRIPTION
            "An object containing a coverage path used by this principal."
        ::= { g3pkprincipalEntry 17 }

    g3pkprincipalCovPath7	OBJECT-TYPE
        SYNTAX    INTEGER
        ACCESS    read-only
        STATUS    mandatory
        DESCRIPTION
            "An object containing a coverage path used by this principal."
        ::= { g3pkprincipalEntry 18 }

    g3pkprincipalCovPath8	OBJECT-TYPE
        SYNTAX    INTEGER
        ACCESS    read-only
        STATUS    mandatory
        DESCRIPTION
            "An object containing a coverage path used by this principal."
        ::= { g3pkprincipalEntry 19 }


    -- the g3esmain group

    g3esmainTage	OBJECT-TYPE
        SYNTAX    INTEGER
        ACCESS    read-only
        STATUS    mandatory
        DESCRIPTION
            "The number of timeticks since the coverage path data was last extracted
            from the switch by the Proxy Agent. This object along with the
            g3esmainTintvl object allows the Network Manager to determine
            the validity of the data in the cache and to control when the
            Proxy Agent extracts the data from the switch."
        ::= { g3esmain 1 }

    g3esmainTintvl	OBJECT-TYPE
        SYNTAX    INTEGER
        ACCESS    read-write
        STATUS    mandatory
        DESCRIPTION
            "An object containing the interval for which the data extracted
            from the switch is considered valid by the Proxy Agent. When a
            GET or GET-NEXT request for the data is received by the agent
            it uses the g3esmainTage and g3esmainTintvl objects to determine
            whether it should refresh the data."
        ::= { g3esmain 2 }

    g3esmainTdelay	OBJECT-TYPE
        SYNTAX    INTEGER
        ACCESS    read-only
        STATUS    mandatory
        DESCRIPTION
            "An object containing the delay encountered in updating the
            cached data."
        ::= { g3esmain 3 }

    g3esmainTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached
            data is being retrieved and otherwise 'current'.This object
             may be set to 'update' to force a refresh of the cache."
        ::= { g3esmain 4 }

    g3esmainTcount	OBJECT-TYPE
        SYNTAX    Gauge
        ACCESS    read-only
        STATUS    mandatory
        DESCRIPTION
            "A Gauge object containing the number of data records in the cache."
        ::= { g3esmain 5 }

    g3esmainTable	OBJECT-TYPE
        SYNTAX    SEQUENCE OF G3esmainEntry
        ACCESS    not-accessible
        STATUS    mandatory
        DESCRIPTION
            "A list of g3esmain entries."
        ::= { g3esmain 6 }

    g3esmainEntry	OBJECT-TYPE
        SYNTAX    G3esmainEntry
        ACCESS    not-accessible
        STATUS    mandatory
        DESCRIPTION
            "A g3esmain entry containing objects of the
            g3esmain information sent by the switch."
        INDEX    { g3esmainClusterId }
        ::= { g3esmainTable 1 }

    G3esmainEntry ::= SEQUENCE {
        g3esmainClusterId
            INTEGER,
        g3esmainPlatformType
            DisplayString,
        g3esmainServerAId
            DisplayString,
        g3esmainServerAIP1
            DisplayString,
        g3esmainServerAIP2
            DisplayString,
        g3esmainServerAIP3
            DisplayString,
        g3esmainServerAIP4
            DisplayString,
        g3esmainServerBId
            DisplayString,
        g3esmainServerBIP1
            DisplayString,
        g3esmainServerBIP2
            DisplayString,
        g3esmainServerBIP3
            DisplayString,
        g3esmainServerBIP4
            DisplayString,
        g3esmainPriorityScore
            DisplayString,
        g3esmainNetComm
            DisplayString,
        g3esmainSystemPref
            DisplayString,
        g3esmainLocalPref
            DisplayString,
        g3esmainLocalOnly
            DisplayString
        }

    g3esmainClusterId	OBJECT-TYPE
        SYNTAX    INTEGER
        ACCESS    read-only
        STATUS    mandatory
        DESCRIPTION
            "An object containing the unique module id, for the main server,
            from the license file for this cluster.This MIB group has become
            obsolete. The new MIB group is esmainsrv."
        ::= { g3esmainEntry 1 }

    g3esmainPlatformType	OBJECT-TYPE
        SYNTAX    DisplayString (SIZE (0..7))
        ACCESS    read-only
        STATUS    mandatory
        DESCRIPTION
            "An object containing the platform type (S8500 or S8700).This MIB
            group has become obsolete.The new MIB group is esmainsrv. "
        ::= { g3esmainEntry 2 }

    g3esmainServerAId	OBJECT-TYPE
        SYNTAX    DisplayString (SIZE (0..3))
        ACCESS    read-only
        STATUS    mandatory
        DESCRIPTION
            "An object containing the Server A id field. Acceptable values
            are 1-999 and it must be unique.This MIB group has become obsolete.
            The new MIB group is esmainsrv."
        ::= { g3esmainEntry 3 }

    g3esmainServerAIP1	OBJECT-TYPE
        SYNTAX    DisplayString (SIZE (0..3))
        ACCESS    read-only
        STATUS    mandatory
        DESCRIPTION
            "An object containing the first part of the IP Address for Server A.
            This MIB group has become obsolete. The new MIB group is esmainsrv."
        ::= { g3esmainEntry 4 }

    g3esmainServerAIP2	OBJECT-TYPE
        SYNTAX    DisplayString (SIZE (0..3))
        ACCESS    read-only
        STATUS    mandatory
        DESCRIPTION
            "An object containing the second part of the IP Address for Server A.
            This MIB group has become obsolete. The new MIB group is esmainsrv."
        ::= { g3esmainEntry 5 }

    g3esmainServerAIP3	OBJECT-TYPE
        SYNTAX    DisplayString (SIZE (0..3))
        ACCESS    read-only
        STATUS    mandatory
        DESCRIPTION
            "An object containing the third part of the IP Address for Server A.
            This MIB group has become obsolete. The new MIB group is esmainsrv."
        ::= { g3esmainEntry 6 }

    g3esmainServerAIP4	OBJECT-TYPE
        SYNTAX    DisplayString (SIZE (0..3))
        ACCESS    read-only
        STATUS    mandatory
        DESCRIPTION
            "An object containing the last part of the IP Address for Server A.
            This MIB group has become obsolete. The new MIB group is esmainsrv."
        ::= { g3esmainEntry 7 }

    g3esmainServerBId	OBJECT-TYPE
        SYNTAX    DisplayString (SIZE (0..3))
        ACCESS    read-only
        STATUS    mandatory
        DESCRIPTION
            "An object containing the Server B id field. Acceptable values
            are 1-999 and it must be unique (only available if the platform
            type is S8700).This MIB group has become obsolete. The new MIB 
            group is esmainsrv."
        ::= { g3esmainEntry 8 }

    g3esmainServerBIP1	OBJECT-TYPE
        SYNTAX    DisplayString (SIZE (0..3))
        ACCESS    read-only
        STATUS    mandatory
        DESCRIPTION
            "An object containing the first part of the IP Address for Server B.
            This MIB group has become obsolete. The new MIB group is esmainsrv."
        ::= { g3esmainEntry 9 }

    g3esmainServerBIP2	OBJECT-TYPE
        SYNTAX    DisplayString (SIZE (0..3))
        ACCESS    read-only
        STATUS    mandatory
        DESCRIPTION
            "An object containing the second part of the IP Address for Server B.
            This MIB group has become obsolete. The new MIB group is esmainsrv."
        ::= { g3esmainEntry 10 }

    g3esmainServerBIP3	OBJECT-TYPE
        SYNTAX    DisplayString (SIZE (0..3))
        ACCESS    read-only
        STATUS    mandatory
        DESCRIPTION
            "An object containing the third part of the IP Address for Server B.
            This MIB group has become obsolete. The new MIB group is esmainsrv."
        ::= { g3esmainEntry 11 }

    g3esmainServerBIP4	OBJECT-TYPE
        SYNTAX    DisplayString (SIZE (0..3))
        ACCESS    read-only
        STATUS    mandatory
        DESCRIPTION
            "An object containing the last part of the IP Address for Server B.
            This MIB group has become obsolete. The new MIB group is esmainsrv."
        ::= { g3esmainEntry 12 }

    g3esmainPriorityScore	OBJECT-TYPE
        SYNTAX    DisplayString (SIZE (0..3))
        ACCESS    read-only
        STATUS    mandatory
        DESCRIPTION
            "An object containing a numerical value that allows the customer
            to assign a preferred cluster (can accept values of 1-100; default
            is blank).This MIB group has become obsolete. The new MIB group is
            esmainsrv."
        ::= { g3esmainEntry 13 }

    g3esmainNetComm	OBJECT-TYPE
        SYNTAX    DisplayString (SIZE (0..2))
        ACCESS    read-only
        STATUS    mandatory
        DESCRIPTION
            "An object containing the region the ESS cluster is in (used for
            localization; can have values between 1-64; default is 1).
            This MIB group has become obsolete. The new MIB group is esmainsrv."
        ::= { g3esmainEntry 14 }

    g3esmainSystemPref	OBJECT-TYPE
        SYNTAX    DisplayString (SIZE (0..1))
        ACCESS    read-only
        STATUS    mandatory
        DESCRIPTION
            "An object containing a flag that provides the cluster with a
            weighting factor that makes it a candidate to provide service
            on a system-wide basis (values can be 'y' or 'n'; default is 'y').
            This MIB group has become obsolete. The new MIB group is esmainsrv."
        ::= { g3esmainEntry 15 }

    g3esmainLocalPref	OBJECT-TYPE
        SYNTAX    DisplayString (SIZE (0..1))
        ACCESS    read-only
        STATUS    mandatory
        DESCRIPTION
            "An object containing a flag that provides the cluster with a
            weighting factor that makes it a candidate to provide service
            in the same network community before clusters in other network
            communities would be selected (values can be 'y' or 'n'; default
            is 'n'). This MIB group has become obsolete. The new MIB group is
            esmainsrv."
        ::= { g3esmainEntry 16 }

    g3esmainLocalOnly	OBJECT-TYPE
        SYNTAX    DisplayString (SIZE (0..1))
        ACCESS    read-only
        STATUS    mandatory
        DESCRIPTION
            "An object containing a flag indicating that only clusters in the
            same network community can provide service (values can be 'y'
            or 'n'; default is 'n')s MIB group has become obsolete. 
            The new MIB group is esmainsrv."
        ::= { g3esmainEntry 17 }


    -- the g3esservers group

    g3esserversTage	OBJECT-TYPE
        SYNTAX    INTEGER
        ACCESS    read-only
        STATUS    mandatory
        DESCRIPTION
            "The number of timeticks since the coverage path data was last extracted 
            from the switch by the Proxy Agent. This object along with the
            g3esserversTintvl object allows the Network Manager to determine 
            the validity of the data in the cache and to control when the 
            Proxy Agent extracts the data from the switch."
        ::= { g3esservers 1 }

    g3esserversTintvl	OBJECT-TYPE
        SYNTAX    INTEGER
        ACCESS    read-write
        STATUS    mandatory
        DESCRIPTION
            "An object containing the interval for which the data extracted 
            from the switch is considered valid by the Proxy Agent. When a 
            GET or GET-NEXT request for the data is received by the agent 
            it uses the g3esserversTage and g3esserversTintvl objects to determine 
            whether it should refresh the data."
        ::= { g3esservers 2 }

    g3esserversTdelay	OBJECT-TYPE
        SYNTAX    INTEGER
        ACCESS    read-only
        STATUS    mandatory
        DESCRIPTION
            "An object containing the delay encountered in updating the 
            cached data."
        ::= { g3esservers 3 }

    g3esserversTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached 
            data is being retrieved and otherwise 'current'.This object 
            may be set to 'update' to force a refresh of the cache."
        ::= { g3esservers 4 }

    g3esserversTcount	OBJECT-TYPE
        SYNTAX    Gauge
        ACCESS    read-only
        STATUS    mandatory
        DESCRIPTION
            "A Gauge object containing the number of data records in the cache."
        ::= { g3esservers 5 }

    g3esserversTable	OBJECT-TYPE
        SYNTAX    SEQUENCE OF G3esserversEntry
        ACCESS    not-accessible
        STATUS    mandatory
        DESCRIPTION
            "A list of g3esservers entries."
        ::= { g3esservers 6 }

    g3esserversEntry	OBJECT-TYPE
        SYNTAX    G3esserversEntry
        ACCESS    not-accessible
        STATUS    mandatory
        DESCRIPTION
            "A g3esservers entry containing objects of the
            g3esservers information sent by the switch."
        INDEX    { g3esserversClusterId }
        ::= { g3esserversTable 1 }

    G3esserversEntry ::= SEQUENCE {
        g3esserversClusterId
            INTEGER,
        g3esserversPlatformType
            DisplayString,
        g3esserversServerAId
            DisplayString,
        g3esserversServerAIP1
            DisplayString,
        g3esserversServerAIP2
            DisplayString,
        g3esserversServerAIP3
            DisplayString,
        g3esserversServerAIP4
            DisplayString,
        g3esserversServerBId
            DisplayString,
        g3esserversServerBIP1
            DisplayString,
        g3esserversServerBIP2
            DisplayString,
        g3esserversServerBIP3
            DisplayString,
        g3esserversServerBIP4
            DisplayString,
        g3esserversPriorityScore
            DisplayString,
        g3esserversNetComm
            DisplayString,
        g3esserversSystemPref
            DisplayString,
        g3esserversLocalPref
            DisplayString,
        g3esserversLocalOnly
            DisplayString,
        g3esserversServerANodeName
            DisplayString,
        g3esserversServerBNodeName
            DisplayString
        }

    g3esserversClusterId	OBJECT-TYPE
        SYNTAX    INTEGER
        ACCESS    read-only
        STATUS    mandatory
        DESCRIPTION
            "An object containing the unique module id, for the enterprise
            survivable server, from the license file for this cluster.
            This MIB group has become obsolete. The new MIB group is survprocess."
        ::= { g3esserversEntry 1 }

    g3esserversPlatformType	OBJECT-TYPE
        SYNTAX    DisplayString (SIZE (0..7))
        ACCESS    read-only
        STATUS    mandatory
        DESCRIPTION
            "An object containing the platform type (S8500 or S8700).
            This MIB group has become obsolete. The new MIB group is survprocess."
        ::= { g3esserversEntry 2 }

    g3esserversServerAId	OBJECT-TYPE
        SYNTAX    DisplayString (SIZE (0..3))
        ACCESS    read-only
        STATUS    mandatory
        DESCRIPTION
            "An object containing the Server A id field. Acceptable values
            are 1-999 and it must be unique.This MIB group has become obsolete. 
            The new MIB group is survprocess."
        ::= { g3esserversEntry 3 }

    g3esserversServerAIP1	OBJECT-TYPE
        SYNTAX    DisplayString (SIZE (0..3))
        ACCESS    read-only
        STATUS    mandatory
        DESCRIPTION
            "An object containing the first part of the IP Address for Server A.
            This MIB group has become obsolete. The new MIB group is survprocess."
        ::= { g3esserversEntry 4 }

    g3esserversServerAIP2	OBJECT-TYPE
        SYNTAX    DisplayString (SIZE (0..3))
        ACCESS    read-only
        STATUS    mandatory
        DESCRIPTION
            "An object containing the second part of the IP Address for Server A.
            This MIB group has become obsolete. The new MIB group is survprocess."
        ::= { g3esserversEntry 5 }

    g3esserversServerAIP3	OBJECT-TYPE
        SYNTAX    DisplayString (SIZE (0..3))
        ACCESS    read-only
        STATUS    mandatory
        DESCRIPTION
            "An object containing the third part of the IP Address for Server A.
            This MIB group has become obsolete. The new MIB group is survprocess."
        ::= { g3esserversEntry 6 }

    g3esserversServerAIP4	OBJECT-TYPE
        SYNTAX    DisplayString (SIZE (0..3))
        ACCESS    read-only
        STATUS    mandatory
        DESCRIPTION
            "An object containing the last part of the IP Address for Server A.
            This MIB group has become obsolete. The new MIB group is survprocess."
        ::= { g3esserversEntry 7 }

    g3esserversServerBId	OBJECT-TYPE
        SYNTAX    DisplayString (SIZE (0..3))
        ACCESS    read-only
        STATUS    mandatory
        DESCRIPTION
            "An object containing the Server B id field. Acceptable values
            are 1-999 and it must be unique (only available if the platform
            type is S8700). The new MIB group is survprocess."
        ::= { g3esserversEntry 8 }

    g3esserversServerBIP1	OBJECT-TYPE
        SYNTAX    DisplayString (SIZE (0..3))
        ACCESS    read-only
        STATUS    mandatory
        DESCRIPTION
            "An object containing the first part of the IP Address for Server B.
            This MIB group has become obsolete. The new MIB group is survprocess."
        ::= { g3esserversEntry 9 }

    g3esserversServerBIP2	OBJECT-TYPE
        SYNTAX    DisplayString (SIZE (0..3))
        ACCESS    read-only
        STATUS    mandatory
        DESCRIPTION
            "An object containing the second part of the IP Address for Server B.
            This MIB group has become obsolete. The new MIB group is survprocess."
        ::= { g3esserversEntry 10 }

    g3esserversServerBIP3	OBJECT-TYPE
        SYNTAX    DisplayString (SIZE (0..3))
        ACCESS    read-only
        STATUS    mandatory
        DESCRIPTION
            "An object containing the third part of the IP Address for Server B.
            This MIB group has become obsolete. The new MIB group is survprocess."
        ::= { g3esserversEntry 11 }

    g3esserversServerBIP4	OBJECT-TYPE
        SYNTAX    DisplayString (SIZE (0..3))
        ACCESS    read-only
        STATUS    mandatory
        DESCRIPTION
            "An object containing the last part of the IP Address for Server B.
            This MIB group has become obsolete. The new MIB group is survprocess."
        ::= { g3esserversEntry 12 }

    g3esserversPriorityScore	OBJECT-TYPE
        SYNTAX    DisplayString (SIZE (0..3))
        ACCESS    read-only
        STATUS    mandatory
        DESCRIPTION
            "An object containing a numerical value that allows the customer
            to assign a preferred cluster (can accept values of 1-100; default
            is blank). This MIB group has become obsolete. 
            The new MIB group is survprocess."
        ::= { g3esserversEntry 13 }

    g3esserversNetComm	OBJECT-TYPE
        SYNTAX    DisplayString (SIZE (0..2))
        ACCESS    read-only
        STATUS    mandatory
        DESCRIPTION
            "An object containing the region the ESS cluster is in (used for
            localization; can have values between 1-64; default is 1).
            This MIB group has become obsolete. The new MIB group is survprocess."
        ::= { g3esserversEntry 14 }

    g3esserversSystemPref	OBJECT-TYPE
        SYNTAX    DisplayString (SIZE (0..1))
        ACCESS    read-only
        STATUS    mandatory
        DESCRIPTION
            "An object containing a flag that provides the cluster with a
            weighting factor that makes it a candidate to provide service
            on a system-wide basis (values can be 'y' or 'n'; default is 'y').
            This MIB group has become obsolete. The new MIB group is survprocess."
        ::= { g3esserversEntry 15 }

    g3esserversLocalPref	OBJECT-TYPE
        SYNTAX    DisplayString (SIZE (0..1))
        ACCESS    read-only
        STATUS    mandatory
        DESCRIPTION
            "An object containing a flag that provides the cluster with a
            weighting factor that makes it a candidate to provide service
            in the same network community before clusters in other network
            communities would be selected (values can be 'y' or 'n'; default
            is 'n').This MIB group has become obsolete. The new MIB group is
            survprocess."
        ::= { g3esserversEntry 16 }

    g3esserversLocalOnly	OBJECT-TYPE
        SYNTAX    DisplayString (SIZE (0..1))
        ACCESS    read-only
        STATUS    mandatory
        DESCRIPTION
            "An object containing a flag indicating that only clusters in the
            same network community can provide service (values can be 'y'
            or 'n'; default is 'n').This MIB group has become obsolete.
            The new MIB group is survprocess."
        ::= { g3esserversEntry 17 }

    g3esserversServerANodeName	OBJECT-TYPE
        SYNTAX    DisplayString (SIZE (0..15))
        ACCESS    read-only
        STATUS    mandatory
        DESCRIPTION
            "An object containing the node name of Server A.This MIB group has 
            become obsolete. The new MIB group is survprocess."
        ::= { g3esserversEntry 18 }

    g3esserversServerBNodeName	OBJECT-TYPE
        SYNTAX    DisplayString (SIZE (0..15))
        ACCESS    read-only
        STATUS    mandatory
        DESCRIPTION
            "An object containing the node name of Server B.	This MIB group has
            become obsolete. The new MIB group is survprocess.
            "
        ::= { g3esserversEntry 19 }


    -- the g3esparms group

    g3esparmsTage	OBJECT-TYPE
        SYNTAX    INTEGER
        ACCESS    read-only
        STATUS    mandatory
        DESCRIPTION
            "The number of timeticks since the coverage path data was last extracted 
            from the switch by the Proxy Agent. This object along with the
            g3esparmsTintvl object allows the Network Manager to determine 
            the validity of the data in the cache and to control when the 
            Proxy Agent extracts the data from the switch."
        ::= { g3esparms 1 }

    g3esparmsTintvl	OBJECT-TYPE
        SYNTAX    INTEGER
        ACCESS    read-write
        STATUS    mandatory
        DESCRIPTION
            "An object containing the interval for which the data extracted 
            from the switch is considered valid by the Proxy Agent. When a 
            GET or GET-NEXT request for the data is received by the agent 
            it uses the g3esparmsTage and g3esparmsTintvl objects to determine 
            whether it should refresh the data."
        ::= { g3esparms 2 }

    g3esparmsTdelay	OBJECT-TYPE
        SYNTAX    INTEGER
        ACCESS    read-only
        STATUS    mandatory
        DESCRIPTION
            "An object containing the delay encountered in updating the 
            cached data."
        ::= { g3esparms 3 }

    g3esparmsTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached 
            data is being retrieved and otherwise 'current'.This object 
            may be set to 'update' to force a refresh of the cache."
        ::= { g3esparms 4 }

    g3esparmsTcount	OBJECT-TYPE
        SYNTAX    Gauge
        ACCESS    read-only
        STATUS    mandatory
        DESCRIPTION
            "A Gauge object containing the number of data records in the cache."
        ::= { g3esparms 5 }

    g3esparmsNetCommunity1	OBJECT-TYPE
        SYNTAX    DisplayString (SIZE (0..2))
        ACCESS    read-only
        STATUS    mandatory
        DESCRIPTION
            "An object containing a network community value for the corresponding
            port network (can have values between 1-64; default is 1)."
        ::= { g3esparms 6 }

    g3esparmsNetCommunity2	OBJECT-TYPE
        SYNTAX    DisplayString (SIZE (0..2))
        ACCESS    read-only
        STATUS    mandatory
        DESCRIPTION
            "See DESCRIPTION of g3esparmsNetCommunity1."
        ::= { g3esparms 7 }

    g3esparmsNetCommunity3	OBJECT-TYPE
        SYNTAX    DisplayString (SIZE (0..2))
        ACCESS    read-only
        STATUS    mandatory
        DESCRIPTION
            "See DESCRIPTION of g3esparmsNetCommunity1."
        ::= { g3esparms 8 }

    g3esparmsNetCommunity4	OBJECT-TYPE
        SYNTAX    DisplayString (SIZE (0..2))
        ACCESS    read-only
        STATUS    mandatory
        DESCRIPTION
            "See DESCRIPTION of g3esparmsNetCommunity1."
        ::= { g3esparms 9 }

    g3esparmsNetCommunity5	OBJECT-TYPE
        SYNTAX    DisplayString (SIZE (0..2))
        ACCESS    read-only
        STATUS    mandatory
        DESCRIPTION
            "See DESCRIPTION of g3esparmsNetCommunity1."
        ::= { g3esparms 10 }

    g3esparmsNetCommunity6	OBJECT-TYPE
        SYNTAX    DisplayString (SIZE (0..2))
        ACCESS    read-only
        STATUS    mandatory
        DESCRIPTION
            "See DESCRIPTION of g3esparmsNetCommunity1."
        ::= { g3esparms 11 }

    g3esparmsNetCommunity7	OBJECT-TYPE
        SYNTAX    DisplayString (SIZE (0..2))
        ACCESS    read-only
        STATUS    mandatory
        DESCRIPTION
            "See DESCRIPTION of g3esparmsNetCommunity1."
        ::= { g3esparms 12 }

    g3esparmsNetCommunity8	OBJECT-TYPE
        SYNTAX    DisplayString (SIZE (0..2))
        ACCESS    read-only
        STATUS    mandatory
        DESCRIPTION
            "See DESCRIPTION of g3esparmsNetCommunity1."
        ::= { g3esparms 13 }

    g3esparmsNetCommunity9	OBJECT-TYPE
        SYNTAX    DisplayString (SIZE (0..2))
        ACCESS    read-only
        STATUS    mandatory
        DESCRIPTION
            "See DESCRIPTION of g3esparmsNetCommunity1."
        ::= { g3esparms 14 }

    g3esparmsNetCommunity10	OBJECT-TYPE
        SYNTAX    DisplayString (SIZE (0..2))
        ACCESS    read-only
        STATUS    mandatory
        DESCRIPTION
            "See DESCRIPTION of g3esparmsNetCommunity1."
        ::= { g3esparms 15 }

    g3esparmsNetCommunity11	OBJECT-TYPE
        SYNTAX    DisplayString (SIZE (0..2))
        ACCESS    read-only
        STATUS    mandatory
        DESCRIPTION
            "See DESCRIPTION of g3esparmsNetCommunity1."
        ::= { g3esparms 16 }

    g3esparmsNetCommunity12	OBJECT-TYPE
        SYNTAX    DisplayString (SIZE (0..2))
        ACCESS    read-only
        STATUS    mandatory
        DESCRIPTION
            "See DESCRIPTION of g3esparmsNetCommunity1."
        ::= { g3esparms 17 }

    g3esparmsNetCommunity13	OBJECT-TYPE
        SYNTAX    DisplayString (SIZE (0..2))
        ACCESS    read-only
        STATUS    mandatory
        DESCRIPTION
            "See DESCRIPTION of g3esparmsNetCommunity1."
        ::= { g3esparms 18 }

    g3esparmsNetCommunity14	OBJECT-TYPE
        SYNTAX    DisplayString (SIZE (0..2))
        ACCESS    read-only
        STATUS    mandatory
        DESCRIPTION
            "See DESCRIPTION of g3esparmsNetCommunity1."
        ::= { g3esparms 19 }

    g3esparmsNetCommunity15	OBJECT-TYPE
        SYNTAX    DisplayString (SIZE (0..2))
        ACCESS    read-only
        STATUS    mandatory
        DESCRIPTION
            "See DESCRIPTION of g3esparmsNetCommunity1."
        ::= { g3esparms 20 }

    g3esparmsNetCommunity16	OBJECT-TYPE
        SYNTAX    DisplayString (SIZE (0..2))
        ACCESS    read-only
        STATUS    mandatory
        DESCRIPTION
            "See DESCRIPTION of g3esparmsNetCommunity1."
        ::= { g3esparms 21 }

    g3esparmsNetCommunity17	OBJECT-TYPE
        SYNTAX    DisplayString (SIZE (0..2))
        ACCESS    read-only
        STATUS    mandatory
        DESCRIPTION
            "See DESCRIPTION of g3esparmsNetCommunity1."
        ::= { g3esparms 22 }

    g3esparmsNetCommunity18	OBJECT-TYPE
        SYNTAX    DisplayString (SIZE (0..2))
        ACCESS    read-only
        STATUS    mandatory
        DESCRIPTION
            "See DESCRIPTION of g3esparmsNetCommunity1."
        ::= { g3esparms 23 }

    g3esparmsNetCommunity19	OBJECT-TYPE
        SYNTAX    DisplayString (SIZE (0..2))
        ACCESS    read-only
        STATUS    mandatory
        DESCRIPTION
            "See DESCRIPTION of g3esparmsNetCommunity1."
        ::= { g3esparms 24 }

    g3esparmsNetCommunity20	OBJECT-TYPE
        SYNTAX    DisplayString (SIZE (0..2))
        ACCESS    read-only
        STATUS    mandatory
        DESCRIPTION
            "See DESCRIPTION of g3esparmsNetCommunity1."
        ::= { g3esparms 25 }

    g3esparmsNetCommunity21	OBJECT-TYPE
        SYNTAX    DisplayString (SIZE (0..2))
        ACCESS    read-only
        STATUS    mandatory
        DESCRIPTION
            "See DESCRIPTION of g3esparmsNetCommunity1."
        ::= { g3esparms 26 }

    g3esparmsNetCommunity22	OBJECT-TYPE
        SYNTAX    DisplayString (SIZE (0..2))
        ACCESS    read-only
        STATUS    mandatory
        DESCRIPTION
            "See DESCRIPTION of g3esparmsNetCommunity1."
        ::= { g3esparms 27 }

    g3esparmsNetCommunity23	OBJECT-TYPE
        SYNTAX    DisplayString (SIZE (0..2))
        ACCESS    read-only
        STATUS    mandatory
        DESCRIPTION
            "See DESCRIPTION of g3esparmsNetCommunity1."
        ::= { g3esparms 28 }

    g3esparmsNetCommunity24	OBJECT-TYPE
        SYNTAX    DisplayString (SIZE (0..2))
        ACCESS    read-only
        STATUS    mandatory
        DESCRIPTION
            "See DESCRIPTION of g3esparmsNetCommunity1."
        ::= { g3esparms 29 }

    g3esparmsNetCommunity25	OBJECT-TYPE
        SYNTAX    DisplayString (SIZE (0..2))
        ACCESS    read-only
        STATUS    mandatory
        DESCRIPTION
            "See DESCRIPTION of g3esparmsNetCommunity1."
        ::= { g3esparms 30 }

    g3esparmsNetCommunity26	OBJECT-TYPE
        SYNTAX    DisplayString (SIZE (0..2))
        ACCESS    read-only
        STATUS    mandatory
        DESCRIPTION
            "See DESCRIPTION of g3esparmsNetCommunity1."
        ::= { g3esparms 31 }

    g3esparmsNetCommunity27	OBJECT-TYPE
        SYNTAX    DisplayString (SIZE (0..2))
        ACCESS    read-only
        STATUS    mandatory
        DESCRIPTION
            "See DESCRIPTION of g3esparmsNetCommunity1."
        ::= { g3esparms 32 }

    g3esparmsNetCommunity28	OBJECT-TYPE
        SYNTAX    DisplayString (SIZE (0..2))
        ACCESS    read-only
        STATUS    mandatory
        DESCRIPTION
            "See DESCRIPTION of g3esparmsNetCommunity1."
        ::= { g3esparms 33 }

    g3esparmsNetCommunity29	OBJECT-TYPE
        SYNTAX    DisplayString (SIZE (0..2))
        ACCESS    read-only
        STATUS    mandatory
        DESCRIPTION
            "See DESCRIPTION of g3esparmsNetCommunity1."
        ::= { g3esparms 34 }

    g3esparmsNetCommunity30	OBJECT-TYPE
        SYNTAX    DisplayString (SIZE (0..2))
        ACCESS    read-only
        STATUS    mandatory
        DESCRIPTION
            "See DESCRIPTION of g3esparmsNetCommunity1."
        ::= { g3esparms 35 }

    g3esparmsNetCommunity31	OBJECT-TYPE
        SYNTAX    DisplayString (SIZE (0..2))
        ACCESS    read-only
        STATUS    mandatory
        DESCRIPTION
            "See DESCRIPTION of g3esparmsNetCommunity1."
        ::= { g3esparms 36 }

    g3esparmsNetCommunity32	OBJECT-TYPE
        SYNTAX    DisplayString (SIZE (0..2))
        ACCESS    read-only
        STATUS    mandatory
        DESCRIPTION
            "See DESCRIPTION of g3esparmsNetCommunity1."
        ::= { g3esparms 37 }

    g3esparmsNetCommunity33	OBJECT-TYPE
        SYNTAX    DisplayString (SIZE (0..2))
        ACCESS    read-only
        STATUS    mandatory
        DESCRIPTION
            "See DESCRIPTION of g3esparmsNetCommunity1."
        ::= { g3esparms 38 }

    g3esparmsNetCommunity34	OBJECT-TYPE
        SYNTAX    DisplayString (SIZE (0..2))
        ACCESS    read-only
        STATUS    mandatory
        DESCRIPTION
            "See DESCRIPTION of g3esparmsNetCommunity1."
        ::= { g3esparms 39 }

    g3esparmsNetCommunity35	OBJECT-TYPE
        SYNTAX    DisplayString (SIZE (0..2))
        ACCESS    read-only
        STATUS    mandatory
        DESCRIPTION
            "See DESCRIPTION of g3esparmsNetCommunity1."
        ::= { g3esparms 40 }

    g3esparmsNetCommunity36	OBJECT-TYPE
        SYNTAX    DisplayString (SIZE (0..2))
        ACCESS    read-only
        STATUS    mandatory
        DESCRIPTION
            "See DESCRIPTION of g3esparmsNetCommunity1."
        ::= { g3esparms 41 }

    g3esparmsNetCommunity37	OBJECT-TYPE
        SYNTAX    DisplayString (SIZE (0..2))
        ACCESS    read-only
        STATUS    mandatory
        DESCRIPTION
            "See DESCRIPTION of g3esparmsNetCommunity1."
        ::= { g3esparms 42 }

    g3esparmsNetCommunity38	OBJECT-TYPE
        SYNTAX    DisplayString (SIZE (0..2))
        ACCESS    read-only
        STATUS    mandatory
        DESCRIPTION
            "See DESCRIPTION of g3esparmsNetCommunity1."
        ::= { g3esparms 43 }

    g3esparmsNetCommunity39	OBJECT-TYPE
        SYNTAX    DisplayString (SIZE (0..2))
        ACCESS    read-only
        STATUS    mandatory
        DESCRIPTION
            "See DESCRIPTION of g3esparmsNetCommunity1."
        ::= { g3esparms 44 }

    g3esparmsNetCommunity40	OBJECT-TYPE
        SYNTAX    DisplayString (SIZE (0..2))
        ACCESS    read-only
        STATUS    mandatory
        DESCRIPTION
            "See DESCRIPTION of g3esparmsNetCommunity1."
        ::= { g3esparms 45 }

    g3esparmsNetCommunity41	OBJECT-TYPE
        SYNTAX    DisplayString (SIZE (0..2))
        ACCESS    read-only
        STATUS    mandatory
        DESCRIPTION
            "See DESCRIPTION of g3esparmsNetCommunity1."
        ::= { g3esparms 46 }

    g3esparmsNetCommunity42	OBJECT-TYPE
        SYNTAX    DisplayString (SIZE (0..2))
        ACCESS    read-only
        STATUS    mandatory
        DESCRIPTION
            "See DESCRIPTION of g3esparmsNetCommunity1."
        ::= { g3esparms 47 }

    g3esparmsNetCommunity43	OBJECT-TYPE
        SYNTAX    DisplayString (SIZE (0..2))
        ACCESS    read-only
        STATUS    mandatory
        DESCRIPTION
            "See DESCRIPTION of g3esparmsNetCommunity1."
        ::= { g3esparms 48 }

    g3esparmsNetCommunity44	OBJECT-TYPE
        SYNTAX    DisplayString (SIZE (0..2))
        ACCESS    read-only
        STATUS    mandatory
        DESCRIPTION
            "See DESCRIPTION of g3esparmsNetCommunity1."
        ::= { g3esparms 49 }

    g3esparmsNetCommunity45	OBJECT-TYPE
        SYNTAX    DisplayString (SIZE (0..2))
        ACCESS    read-only
        STATUS    mandatory
        DESCRIPTION
            "See DESCRIPTION of g3esparmsNetCommunity1."
        ::= { g3esparms 50 }

    g3esparmsNetCommunity46	OBJECT-TYPE
        SYNTAX    DisplayString (SIZE (0..2))
        ACCESS    read-only
        STATUS    mandatory
        DESCRIPTION
            "See DESCRIPTION of g3esparmsNetCommunity1."
        ::= { g3esparms 51 }

    g3esparmsNetCommunity47	OBJECT-TYPE
        SYNTAX    DisplayString (SIZE (0..2))
        ACCESS    read-only
        STATUS    mandatory
        DESCRIPTION
            "See DESCRIPTION of g3esparmsNetCommunity1."
        ::= { g3esparms 52 }

    g3esparmsNetCommunity48	OBJECT-TYPE
        SYNTAX    DisplayString (SIZE (0..2))
        ACCESS    read-only
        STATUS    mandatory
        DESCRIPTION
            "See DESCRIPTION of g3esparmsNetCommunity1."
        ::= { g3esparms 53 }

    g3esparmsNetCommunity49	OBJECT-TYPE
        SYNTAX    DisplayString (SIZE (0..2))
        ACCESS    read-only
        STATUS    mandatory
        DESCRIPTION
            "See DESCRIPTION of g3esparmsNetCommunity1."
        ::= { g3esparms 54 }

    g3esparmsNetCommunity50	OBJECT-TYPE
        SYNTAX    DisplayString (SIZE (0..2))
        ACCESS    read-only
        STATUS    mandatory
        DESCRIPTION
            "See DESCRIPTION of g3esparmsNetCommunity1."
        ::= { g3esparms 55 }

    g3esparmsNetCommunity51	OBJECT-TYPE
        SYNTAX    DisplayString (SIZE (0..2))
        ACCESS    read-only
        STATUS    mandatory
        DESCRIPTION
            "See DESCRIPTION of g3esparmsNetCommunity1."
        ::= { g3esparms 56 }

    g3esparmsNetCommunity52	OBJECT-TYPE
        SYNTAX    DisplayString (SIZE (0..2))
        ACCESS    read-only
        STATUS    mandatory
        DESCRIPTION
            "See DESCRIPTION of g3esparmsNetCommunity1."
        ::= { g3esparms 57 }

    g3esparmsNetCommunity53	OBJECT-TYPE
        SYNTAX    DisplayString (SIZE (0..2))
        ACCESS    read-only
        STATUS    mandatory
        DESCRIPTION
            "See DESCRIPTION of g3esparmsNetCommunity1."
        ::= { g3esparms 58 }

    g3esparmsNetCommunity54	OBJECT-TYPE
        SYNTAX    DisplayString (SIZE (0..2))
        ACCESS    read-only
        STATUS    mandatory
        DESCRIPTION
            "See DESCRIPTION of g3esparmsNetCommunity1."
        ::= { g3esparms 59 }

    g3esparmsNetCommunity55	OBJECT-TYPE
        SYNTAX    DisplayString (SIZE (0..2))
        ACCESS    read-only
        STATUS    mandatory
        DESCRIPTION
            "See DESCRIPTION of g3esparmsNetCommunity1."
        ::= { g3esparms 60 }

    g3esparmsNetCommunity56	OBJECT-TYPE
        SYNTAX    DisplayString (SIZE (0..2))
        ACCESS    read-only
        STATUS    mandatory
        DESCRIPTION
            "See DESCRIPTION of g3esparmsNetCommunity1."
        ::= { g3esparms 61 }

    g3esparmsNetCommunity57	OBJECT-TYPE
        SYNTAX    DisplayString (SIZE (0..2))
        ACCESS    read-only
        STATUS    mandatory
        DESCRIPTION
            "See DESCRIPTION of g3esparmsNetCommunity1."
        ::= { g3esparms 62 }

    g3esparmsNetCommunity58	OBJECT-TYPE
        SYNTAX    DisplayString (SIZE (0..2))
        ACCESS    read-only
        STATUS    mandatory
        DESCRIPTION
            "See DESCRIPTION of g3esparmsNetCommunity1."
        ::= { g3esparms 63 }

    g3esparmsNetCommunity59	OBJECT-TYPE
        SYNTAX    DisplayString (SIZE (0..2))
        ACCESS    read-only
        STATUS    mandatory
        DESCRIPTION
            "See DESCRIPTION of g3esparmsNetCommunity1."
        ::= { g3esparms 64 }

    g3esparmsNetCommunity60	OBJECT-TYPE
        SYNTAX    DisplayString (SIZE (0..2))
        ACCESS    read-only
        STATUS    mandatory
        DESCRIPTION
            "See DESCRIPTION of g3esparmsNetCommunity1."
        ::= { g3esparms 65 }

    g3esparmsNetCommunity61	OBJECT-TYPE
        SYNTAX    DisplayString (SIZE (0..2))
        ACCESS    read-only
        STATUS    mandatory
        DESCRIPTION
            "See DESCRIPTION of g3esparmsNetCommunity1."
        ::= { g3esparms 66 }

    g3esparmsNetCommunity62	OBJECT-TYPE
        SYNTAX    DisplayString (SIZE (0..2))
        ACCESS    read-only
        STATUS    mandatory
        DESCRIPTION
            "See DESCRIPTION of g3esparmsNetCommunity1."
        ::= { g3esparms 67 }

    g3esparmsNetCommunity63	OBJECT-TYPE
        SYNTAX    DisplayString (SIZE (0..2))
        ACCESS    read-only
        STATUS    mandatory
        DESCRIPTION
            "See DESCRIPTION of g3esparmsNetCommunity1."
        ::= { g3esparms 68 }

    g3esparmsNetCommunity64	OBJECT-TYPE
        SYNTAX    DisplayString (SIZE (0..2))
        ACCESS    read-only
        STATUS    mandatory
        DESCRIPTION
            "See DESCRIPTION of g3esparmsNetCommunity1."
        ::= { g3esparms 69 }

    g3esparmsAutoReturn	OBJECT-TYPE
        SYNTAX    DisplayString (SIZE (0..10))
        ACCESS    read-only
        STATUS    mandatory
        DESCRIPTION
            "An object containing the state of auto return (values can be
            'y' (yes), 'n' (no), or 's' (scheduled); default is 'n')."
        ::= { g3esparms 70 }

    g3esparmsDay	OBJECT-TYPE
        SYNTAX    DisplayString (SIZE (0..10))
        ACCESS    read-only
        STATUS    mandatory
        DESCRIPTION
            "An object containing the day of the week Saturday through
            Sunday (or every day) on which the auto return will occur (only
            applicable if AutoReturn is set to scheduled)."
        ::= { g3esparms 71 }

    g3esparmsHour	OBJECT-TYPE
        SYNTAX    DisplayString (SIZE (0..2))
        ACCESS    read-only
        STATUS    mandatory
        DESCRIPTION
            "An object containing the hour of the day (0-23) at which the auto 
            return will occur (only applicable if AutoReturn is set to scheduled)."
        ::= { g3esparms 72 }

    g3esparmsMinute	OBJECT-TYPE
        SYNTAX    DisplayString (SIZE (0..2))
        ACCESS    read-only
        STATUS    mandatory
        DESCRIPTION
            "An object containing the minute of the hour (0-59) at which the auto 
            return will occur (only applicable if AutoReturn is set to scheduled)."
        ::= { g3esparms 73 }

    g3esparmsNoServerTO	OBJECT-TYPE
        SYNTAX    DisplayString (SIZE (0..2))
        ACCESS    read-only
        STATUS    mandatory
        DESCRIPTION
            "An object containing a no service timeout interval indicating
            when the fail over will occur (can have values between 3-15
            minutes; default is 5 minutes)."
        ::= { g3esparms 74 }

    g3esparmsIPSIConnUp	OBJECT-TYPE
        SYNTAX    DisplayString (SIZE (0..5))
        ACCESS    read-only
        STATUS    mandatory
        DESCRIPTION
            "An object containing the number of minutes that an IPSI in a
            Port Network has a connection to the Main server and the Port
            Network is available for auto-return (can have values between
            3-120 or blank if the g3esparmsAutoReturn field is not set to 'y')."
        ::= { g3esparms 75 }

    g3esparmsPNColdresDT	OBJECT-TYPE
        SYNTAX    DisplayString (SIZE (0..2))
        ACCESS    read-only
        STATUS    mandatory
        DESCRIPTION
            "An object containing information about PN Cold Reset Delay Timer"
        ::= { g3esparms 76 }


    -- the g3mgrecrule group

    g3mgrecruleTage	OBJECT-TYPE
        SYNTAX    INTEGER
        ACCESS    read-only
        STATUS    mandatory
        DESCRIPTION
            "The number of timeticks since the coverage path data was last extracted 
            from the switch by the Proxy Agent. This object along with the
            g3mgrecruleTintvl object allows the Network Manager to determine 
            the validity of the data in the cache and to control when the 
            Proxy Agent extracts the data from the switch."
        ::= { g3mgrecrule 1 }

    g3mgrecruleTintvl	OBJECT-TYPE
        SYNTAX    INTEGER
        ACCESS    read-write
        STATUS    mandatory
        DESCRIPTION
            "An object containing the interval for which the data extracted 
            from the switch is considered valid by the Proxy Agent. When a 
            GET or GET-NEXT request for the data is received by the agent 
            it uses the g3mgrecruleTage and g3mgrecruleTintvl objects to determine 
            whether it should refresh the data."
        ::= { g3mgrecrule 2 }

    g3mgrecruleTdelay	OBJECT-TYPE
        SYNTAX    INTEGER
        ACCESS    read-only
        STATUS    mandatory
        DESCRIPTION
            "An object containing the delay encountered in updating the 
            cached data."
        ::= { g3mgrecrule 3 }

    g3mgrecruleTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached 
            data is being retrieved and otherwise 'current'.This object 
            may be set to 'update' to force a refresh of the cache."
        ::= { g3mgrecrule 4 }

    g3mgrecruleTcount	OBJECT-TYPE
        SYNTAX    Gauge
        ACCESS    read-only
        STATUS    mandatory
        DESCRIPTION
            "A Gauge object containing the number of data records in the cache."
        ::= { g3mgrecrule 5 }

    g3mgrecruleTable	OBJECT-TYPE
        SYNTAX    SEQUENCE OF G3mgrecruleEntry
        ACCESS    not-accessible
        STATUS    mandatory
        DESCRIPTION
            "A list of g3mgrecrule entries."
        ::= { g3mgrecrule 6 }

    g3mgrecruleEntry	OBJECT-TYPE
        SYNTAX    G3mgrecruleEntry
        ACCESS    not-accessible
        STATUS    mandatory
        DESCRIPTION
            "A g3mgrecrule entry containing objects of the
            g3mgrecrule information sent by the switch."
        INDEX    { g3mgrecruleGatewayNbr }
        ::= { g3mgrecruleTable 1 }

    G3mgrecruleEntry ::= SEQUENCE {
        g3mgrecruleGatewayNbr
            INTEGER,
        g3mgrecruleGatewayName
            DisplayString,
        g3mgrecruleRecRule
            DisplayString
        }

    g3mgrecruleGatewayNbr	OBJECT-TYPE
        SYNTAX    INTEGER
        ACCESS    read-only
        STATUS    mandatory
        DESCRIPTION
            "An object containing the media gateway number (1-250)."
        ::= { g3mgrecruleEntry 1 }

    g3mgrecruleGatewayName	OBJECT-TYPE
        SYNTAX    DisplayString (SIZE (0..20))
        ACCESS    read-only
        STATUS    mandatory
        DESCRIPTION
            "An object containing the name of the media gateway."
        ::= { g3mgrecruleEntry 2 }

    g3mgrecruleRecRule	OBJECT-TYPE
        SYNTAX    DisplayString (SIZE (0..30))
        ACCESS    read-only
        STATUS    mandatory
        DESCRIPTION
            "An object containing the recovery rule type that has been
            selected for the media gateway (possible values are 
            'immediately', '0-active-calls', 'time-day-window', or
            'time-window-OR-0-active-calls'."
        ::= { g3mgrecruleEntry 3 }


    -- the g3commproc group

    g3commprocTage	OBJECT-TYPE
        SYNTAX    INTEGER
        ACCESS    read-only
        STATUS    mandatory
        DESCRIPTION
            "The number of timeticks since the processor channel data was last 
            extracted from the switch by the Proxy Agent. This object along with 
            the g3commprocTintvl object allows the Network Manager to determine 
            the validity of the data in the cache and to control when the 
            agent extracts the data from the switch."
        ::= { g3commproc 1 }

    g3commprocTintvl	OBJECT-TYPE
        SYNTAX    INTEGER
        ACCESS    read-write
        STATUS    mandatory
        DESCRIPTION
            "An object containing the interval for which the data extracted 
            from the switch is considered valid by the agent. When a 
            GET or GET-NEXT request for the data is received by the agent 
            it uses the g3commprocTage and g3commprocTintvl objects to determine 
            whether it should refresh the data."
        ::= { g3commproc 2 }

    g3commprocTdelay	OBJECT-TYPE
        SYNTAX    INTEGER
        ACCESS    read-only
        STATUS    mandatory
        DESCRIPTION
            "An object containing the delay encountered in updating the 
            cached data."
        ::= { g3commproc 3 }

    g3commprocTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached 
            data is being retrieved and otherwise 'current'.This object 
            may be set to 'update' to force a refresh of the cache."
        ::= { g3commproc 4 }

    g3commprocTcount	OBJECT-TYPE
        SYNTAX    Gauge
        ACCESS    read-only
        STATUS    mandatory
        DESCRIPTION
            "A Gauge object containing the number of data records in the cache."
        ::= { g3commproc 5 }

    g3commprocTable	OBJECT-TYPE
        SYNTAX    SEQUENCE OF G3commprocEntry
        ACCESS    not-accessible
        STATUS    mandatory
        DESCRIPTION
            "A list of g3commproc entries."
        ::= { g3commproc 6 }

    g3commprocEntry	OBJECT-TYPE
        SYNTAX    G3commprocEntry
        ACCESS    not-accessible
        STATUS    mandatory
        DESCRIPTION
            "A g3commproc entry containing objects of the
            g3commproc information sent by the switch."
        INDEX    { g3commprocProcChan }
        ::= { g3commprocTable 1 }

    G3commprocEntry ::= SEQUENCE {
        g3commprocProcChan
            INTEGER,
        g3commprocEnable
            DisplayString,
        g3commprocApplication
            DisplayString,
        g3commprocGatewayTo
            DisplayString,
        g3commprocMode
            DisplayString,
        g3commprocInterfaceLink
            DisplayString,
        g3commprocInterfaceChan
            DisplayString,
        g3commprocDestNode
            DisplayString,
        g3commprocTempA
            DisplayString,
        g3commprocTempB
            DisplayString,
        g3commprocDestPort
            DisplayString,
        g3commprocSessionLocal
            DisplayString,
        g3commprocSessionRemote
            DisplayString,
        g3commprocMachID
            DisplayString
        }

    g3commprocProcChan	OBJECT-TYPE
        SYNTAX    INTEGER
        ACCESS    read-only
        STATUS    mandatory
        DESCRIPTION
            "An object containing the processor channel (1-384)."
        ::= { g3commprocEntry 1 }

    g3commprocEnable	OBJECT-TYPE
        SYNTAX    DisplayString (SIZE (0..1))
        ACCESS    read-only
        STATUS    mandatory
        DESCRIPTION
            "An object containing whether the processor channel is enabled
            (y or n)."
        ::= { g3commprocEntry 2 }

    g3commprocApplication	OBJECT-TYPE
        SYNTAX    DisplayString (SIZE (0..8))
        ACCESS    read-only
        STATUS    mandatory
        DESCRIPTION
            "An object containing the application type or adjunct connection
            used on the channel. Allowed values are 'audix', 'dcs', 'echo',
            'fp-mwi', 'gateway', 'mis', and 'qsig-mwi'."
        ::= { g3commprocEntry 3 }

    g3commprocGatewayTo	OBJECT-TYPE
        SYNTAX    DisplayString (SIZE (0..3))
        ACCESS    read-only
        STATUS    mandatory
        DESCRIPTION
            "An object identifying which processor channel the specific
            processor channel is serving as a gateway to (1-384 or blank)."
        ::= { g3commprocEntry 4 }

    g3commprocMode	OBJECT-TYPE
        SYNTAX    DisplayString (SIZE (0..1))
        ACCESS    read-only
        STATUS    mandatory
        DESCRIPTION
            "An object specifying the mode of the IP session (values include
            'c' for client, 's' for server, or blank)."
        ::= { g3commprocEntry 5 }

    g3commprocInterfaceLink	OBJECT-TYPE
        SYNTAX    DisplayString (SIZE (0..2))
        ACCESS    read-only
        STATUS    mandatory
        DESCRIPTION
            "An object that identifies the physical link carrying the processor
            channel (values include 1-99, 'p' for processor, or blank)."
        ::= { g3commprocEntry 6 }

    g3commprocInterfaceChan	OBJECT-TYPE
        SYNTAX    DisplayString (SIZE (0..5))
        ACCESS    read-only
        STATUS    mandatory
        DESCRIPTION
            "An object that identifies the channel number of the TCP/IP
            listen port channel to carry the processor channel (values 1-64 for
            link type x.25, 0 or 5000-64500 for ethernet or ppp with 0 meaning
            any port can be used)."
        ::= { g3commprocEntry 7 }

    g3commprocDestNode	OBJECT-TYPE
        SYNTAX    DisplayString (SIZE (0..15))
        ACCESS    read-only
        STATUS    mandatory
        DESCRIPTION
            "An object that identifies the server or adjunct at the far end of
            the link (values include either an adjunct name, server name,
            far end IP address, node name, or blank for local services)."
        ::= { g3commprocEntry 8 }

    g3commprocTempA	OBJECT-TYPE
        SYNTAX    DisplayString (SIZE (0..15))
        ACCESS    read-only
        STATUS    mandatory
        DESCRIPTION
            "An object internally used by the agent for data storage (will
            always return blank)."
        ::= { g3commprocEntry 9 }

    g3commprocTempB	OBJECT-TYPE
        SYNTAX    DisplayString (SIZE (0..15))
        ACCESS    read-only
        STATUS    mandatory
        DESCRIPTION
            "An object internally used by the agent for data storage (will
            always return blank)."
        ::= { g3commprocEntry 10 }

    g3commprocDestPort	OBJECT-TYPE
        SYNTAX    DisplayString (SIZE (0..5))
        ACCESS    read-only
        STATUS    mandatory
        DESCRIPTION
            "An object that identifies the port number of the destination
            (values 0 or 5000-64500 where 0 meaning any port can be used)."
        ::= { g3commprocEntry 11 }

    g3commprocSessionLocal	OBJECT-TYPE
        SYNTAX    DisplayString (SIZE (0..3))
        ACCESS    read-only
        STATUS    mandatory
        DESCRIPTION
            "An object that specifies the local session number (1-384 or blank)."
        ::= { g3commprocEntry 12 }

    g3commprocSessionRemote	OBJECT-TYPE
        SYNTAX    DisplayString (SIZE (0..3))
        ACCESS    read-only
        STATUS    mandatory
        DESCRIPTION
            "An object that specifies the remote session number (1-384 or blank)."
        ::= { g3commprocEntry 13 }

    g3commprocMachID	OBJECT-TYPE
        SYNTAX    DisplayString (SIZE (0..2))
        ACCESS    read-only
        STATUS    mandatory
        DESCRIPTION
            "An object that identifies the destination server ID defined on the
            dial plan of the destination server (values 1-99 or blank)."
        ::= { g3commprocEntry 14 }


    -- the g3intvl group

    g3intvltrkSleepintvl	OBJECT-TYPE
        SYNTAX    INTEGER
        ACCESS    read-write
        STATUS    mandatory
        DESCRIPTION
            "Sleep interval to be used between successive ossi requests.
            The SleepIntvl should be specified in terms of millisecs.
            Currently this interval will be used for g3trunksta MIB group only."
        ::= { g3intvl 1 }

    g3intvltrkSleepflag	OBJECT-TYPE
        SYNTAX    INTEGER
        ACCESS    read-write
        STATUS    mandatory
        DESCRIPTION
            "Flag indicating whether sleep is to be induced or not while doing a walk"
        ::= { g3intvl 2 }

    g3intvlPollingIntvl	OBJECT-TYPE
        SYNTAX    INTEGER
        ACCESS    read-write
        STATUS    mandatory
        DESCRIPTION
            "A integer value representing the time interval in which the Record
            would be repopulated."
        ::= { g3intvl 3 }


    -- the g3jitter group

    g3jitterTage	OBJECT-TYPE
        SYNTAX    INTEGER
        ACCESS    read-only
        STATUS    mandatory
        DESCRIPTION
            "The number of timeticks since the ip voice-stats data was last
            extracted from the switch by the Proxy Agent."
        ::= { g3jitter 1 }

    g3jitterTintvl	OBJECT-TYPE
        SYNTAX    INTEGER
        ACCESS    read-write
        STATUS    mandatory
        DESCRIPTION
            "An object containing the interval for which the ip voice stat
            data extracted from the switch is considered valid by the
            Proxy Agent."
        ::= { g3jitter 2 }

    g3jitterTdelay	OBJECT-TYPE
        SYNTAX    INTEGER
        ACCESS    read-only
        STATUS    mandatory
        DESCRIPTION
            "An object containing the delay encountered in updating
            the cached data."
        ::= { g3jitter 3 }

    g3jitterTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3jitter 4 }

    g3jitterTcount	OBJECT-TYPE
        SYNTAX    Gauge
        ACCESS    read-only
        STATUS    mandatory
        DESCRIPTION
            "A Gauge object containing the number of data records in the cache."
        ::= { g3jitter 5 }

    g3jitterTable	OBJECT-TYPE
        SYNTAX    SEQUENCE OF G3jitterEntry
        ACCESS    not-accessible
        STATUS    mandatory
        DESCRIPTION
            "A list of g3jitter entries."
        ::= { g3jitter 6 }

    g3jitterEntry	OBJECT-TYPE
        SYNTAX    G3jitterEntry
        ACCESS    not-accessible
        STATUS    mandatory
        DESCRIPTION
            "A g3jitter entry containing objects of the
            g3jitter information sent by the switch."
        INDEX    { g3jitterRegion, g3jitterTime }
        ::= { g3jitterTable 1 }

    G3jitterEntry ::= SEQUENCE {
        g3jitterRegion
            INTEGER,
        g3jitterBoardNum
            DisplayString,
        g3jitterCallingNum
            DisplayString,
        g3jitterCalledNum
            DisplayString,
        g3jitterTime
            INTEGER,
        g3jitterAvg
            INTEGER,
        g3jitterPeak
            INTEGER,
        g3jitterExceed
            DisplayString
        }

    g3jitterRegion	OBJECT-TYPE
        SYNTAX    INTEGER
        ACCESS    read-only
        STATUS    mandatory
        DESCRIPTION
            "An object containing the network region."
        ::= { g3jitterEntry 1 }

    g3jitterBoardNum	OBJECT-TYPE
        SYNTAX    DisplayString (SIZE (0..5))
        ACCESS    read-only
        STATUS    mandatory
        DESCRIPTION
            "An object containing the Medpro Board location information."
        ::= { g3jitterEntry 2 }

    g3jitterCallingNum	OBJECT-TYPE
        SYNTAX    DisplayString (SIZE (0..13))
        ACCESS    read-only
        STATUS    mandatory
        DESCRIPTION
            "An object containing the number of the endpoint initiating
            the call(near end)."
        ::= { g3jitterEntry 3 }

    g3jitterCalledNum	OBJECT-TYPE
        SYNTAX    DisplayString (SIZE (0..40))
        ACCESS    read-only
        STATUS    mandatory
        DESCRIPTION
            "An object containing the number of the endpoint that
            received the call (far end)."
        ::= { g3jitterEntry 4 }

    g3jitterTime	OBJECT-TYPE
        SYNTAX    INTEGER
        ACCESS    read-only
        STATUS    mandatory
        DESCRIPTION
            "An object containing the time at which the call was made."
        ::= { g3jitterEntry 5 }

    g3jitterAvg	OBJECT-TYPE
        SYNTAX    INTEGER
        ACCESS    read-only
        STATUS    mandatory
        DESCRIPTION
            "An object containing the average amount of jitter captured for the call."
        ::= { g3jitterEntry 6 }

    g3jitterPeak	OBJECT-TYPE
        SYNTAX    INTEGER
        ACCESS    read-only
        STATUS    mandatory
        DESCRIPTION
            "An object containing the peak amount of jitter captured for the call."
        ::= { g3jitterEntry 7 }

    g3jitterExceed	OBJECT-TYPE
        SYNTAX    DisplayString (SIZE (0..7))
        ACCESS    read-only
        STATUS    mandatory
        DESCRIPTION
            "An object containing the type of Voice/Network Statistics exception
            that occured during the call.It is implied by the type of report and
            can be either Jitter/Pktloss/RoundTripDelay."
        ::= { g3jitterEntry 8 }


    -- the g3pktloss group

    g3pktlossTage	OBJECT-TYPE
        SYNTAX    INTEGER
        ACCESS    read-only
        STATUS    mandatory
        DESCRIPTION
            "The number of timeticks since the ip voice-stats data was last
            extracted from the switch by the Proxy Agent."
        ::= { g3pktloss 1 }

    g3pktlossTintvl	OBJECT-TYPE
        SYNTAX    INTEGER
        ACCESS    read-write
        STATUS    mandatory
        DESCRIPTION
            "An object containing the interval for which the ip voice stat
            data extracted from the switch is considered valid by the
            Proxy Agent."
        ::= { g3pktloss 2 }

    g3pktlossTdelay	OBJECT-TYPE
        SYNTAX    INTEGER
        ACCESS    read-only
        STATUS    mandatory
        DESCRIPTION
            "An object containing the delay encountered in updating
            the cached data."
        ::= { g3pktloss 3 }

    g3pktlossTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3pktloss 4 }

    g3pktlossTcount	OBJECT-TYPE
        SYNTAX    Gauge
        ACCESS    read-only
        STATUS    mandatory
        DESCRIPTION
            "A Gauge object containing the number of data records in the cache"
        ::= { g3pktloss 5 }

    g3pktlossTable	OBJECT-TYPE
        SYNTAX    SEQUENCE OF G3pktlossEntry
        ACCESS    not-accessible
        STATUS    mandatory
        DESCRIPTION
            "A list of g3pktloss entries."
        ::= { g3pktloss 6 }

    g3pktlossEntry	OBJECT-TYPE
        SYNTAX    G3pktlossEntry
        ACCESS    not-accessible
        STATUS    mandatory
        DESCRIPTION
            "A g3pktloss entry containing objects of the
            g3pktloss information sent by the switch."
        INDEX    { g3pktlossRegion, g3pktlossTime }
        ::= { g3pktlossTable 1 }

    G3pktlossEntry ::= SEQUENCE {
        g3pktlossRegion
            INTEGER,
        g3pktlossBoardNum
            DisplayString,
        g3pktlossCallingNum
            DisplayString,
        g3pktlossCalledNum
            DisplayString,
        g3pktlossTime
            INTEGER,
        g3pktlossTotal
            INTEGER,
        g3pktlossPercent
            DisplayString,
        g3pktlossExceed
            DisplayString
        }

    g3pktlossRegion	OBJECT-TYPE
        SYNTAX    INTEGER
        ACCESS    read-only
        STATUS    mandatory
        DESCRIPTION
            "An object containing the network region."
        ::= { g3pktlossEntry 1 }

    g3pktlossBoardNum	OBJECT-TYPE
        SYNTAX    DisplayString (SIZE (0..5))
        ACCESS    read-only
        STATUS    mandatory
        DESCRIPTION
            "An object containing the Medpro Board location information."
        ::= { g3pktlossEntry 2 }

    g3pktlossCallingNum	OBJECT-TYPE
        SYNTAX    DisplayString (SIZE (0..13))
        ACCESS    read-only
        STATUS    mandatory
        DESCRIPTION
            "An object containing the the number of the endpoint initiating
            the call(near end)."
        ::= { g3pktlossEntry 3 }

    g3pktlossCalledNum	OBJECT-TYPE
        SYNTAX    DisplayString (SIZE (0..40))
        ACCESS    read-only
        STATUS    mandatory
        DESCRIPTION
            "An object containing the number of the endpoint that received
            the call (far end)."
        ::= { g3pktlossEntry 4 }

    g3pktlossTime	OBJECT-TYPE
        SYNTAX    INTEGER
        ACCESS    read-only
        STATUS    mandatory
        DESCRIPTION
            "An object containing the time at which the call was made."
        ::= { g3pktlossEntry 5 }

    g3pktlossTotal	OBJECT-TYPE
        SYNTAX    INTEGER
        ACCESS    read-only
        STATUS    mandatory
        DESCRIPTION
            "An object containing the total number of packets that were lost for
            the call.If the actual number of packets is greater than what can fit
            in this field, all 9999s shall be displayed."
        ::= { g3pktlossEntry 6 }

    g3pktlossPercent	OBJECT-TYPE
        SYNTAX    DisplayString (SIZE (0..3))
        ACCESS    read-only
        STATUS    mandatory
        DESCRIPTION
            "An object containing the packet loss for the call,shown 
            as a percentage."
        ::= { g3pktlossEntry 7 }

    g3pktlossExceed	OBJECT-TYPE
        SYNTAX    DisplayString (SIZE (0..12))
        ACCESS    read-only
        STATUS    mandatory
        DESCRIPTION
            "An object containing the type of Voice/Network Statistics exception
            that occured during the call.It is implied by the type of report and
            can be either Jitter/Pktloss/RoundTripDelay."
        ::= { g3pktlossEntry 8 }


    -- the g3rtdelay group

    g3rtdelayTage	OBJECT-TYPE
        SYNTAX    INTEGER
        ACCESS    read-only
        STATUS    mandatory
        DESCRIPTION
            "The number of timeticks since the ip voice-stats data was last
             extracted from the switch by the Proxy Agent."
        ::= { g3rtdelay 1 }

    g3rtdelayTintvl	OBJECT-TYPE
        SYNTAX    INTEGER
        ACCESS    read-write
        STATUS    mandatory
        DESCRIPTION
            "An object containing the interval for which the ip voice stat
            data extracted from the switch is considered valid by the
            Proxy Agent."
        ::= { g3rtdelay 2 }

    g3rtdelayTdelay	OBJECT-TYPE
        SYNTAX    INTEGER
        ACCESS    read-only
        STATUS    mandatory
        DESCRIPTION
            "An object containing the delay encountered in updating
            the cached data."
        ::= { g3rtdelay 3 }

    g3rtdelayTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3rtdelay 4 }

    g3rtdelayTcount	OBJECT-TYPE
        SYNTAX    Gauge
        ACCESS    read-only
        STATUS    mandatory
        DESCRIPTION
            "A Gauge object containing the number of data records in the cache."
        ::= { g3rtdelay 5 }

    g3rtdelayTable	OBJECT-TYPE
        SYNTAX    SEQUENCE OF G3rtdelayEntry
        ACCESS    not-accessible
        STATUS    mandatory
        DESCRIPTION
            "A list of g3rtdelay entries."
        ::= { g3rtdelay 6 }

    g3rtdelayEntry	OBJECT-TYPE
        SYNTAX    G3rtdelayEntry
        ACCESS    not-accessible
        STATUS    mandatory
        DESCRIPTION
            "A g3rtdelay entry containing objects of the
            g3rtdelay information sent by the switch."
        INDEX    { g3rtdelayRegion, g3rtdelayTime }
        ::= { g3rtdelayTable 1 }

    G3rtdelayEntry ::= SEQUENCE {
        g3rtdelayRegion
            INTEGER,
        g3rtdelayBoardNum
            DisplayString,
        g3rtdelayCallingNum
            DisplayString,
        g3rtdelayCalledNum
            DisplayString,
        g3rtdelayTime
            INTEGER,
        g3rtdelayAvg
            INTEGER,
        g3rtdelayPeak
            INTEGER,
        g3rtdelayExceed
            DisplayString
        }

    g3rtdelayRegion	OBJECT-TYPE
        SYNTAX    INTEGER
        ACCESS    read-only
        STATUS    mandatory
        DESCRIPTION
            "An object containing the network region."
        ::= { g3rtdelayEntry 1 }

    g3rtdelayBoardNum	OBJECT-TYPE
        SYNTAX    DisplayString (SIZE (0..5))
        ACCESS    read-only
        STATUS    mandatory
        DESCRIPTION
            "An object containing the Medpro Board location information."
        ::= { g3rtdelayEntry 2 }

    g3rtdelayCallingNum	OBJECT-TYPE
        SYNTAX    DisplayString (SIZE (0..13))
        ACCESS    read-only
        STATUS    mandatory
        DESCRIPTION
            "An object containing the the number of the endpoint initiating
            the call(near end)."
        ::= { g3rtdelayEntry 3 }

    g3rtdelayCalledNum	OBJECT-TYPE
        SYNTAX    DisplayString (SIZE (0..40))
        ACCESS    read-only
        STATUS    mandatory
        DESCRIPTION
            "An object containing the number of the endpoint that received the
            call (far end)."
        ::= { g3rtdelayEntry 4 }

    g3rtdelayTime	OBJECT-TYPE
        SYNTAX    INTEGER
        ACCESS    read-only
        STATUS    mandatory
        DESCRIPTION
            "An object containing the time at which the call was made."
        ::= { g3rtdelayEntry 5 }

    g3rtdelayAvg	OBJECT-TYPE
        SYNTAX    INTEGER
        ACCESS    read-only
        STATUS    mandatory
        DESCRIPTION
            "An object containing the average round trip delay for a packets."
        ::= { g3rtdelayEntry 6 }

    g3rtdelayPeak	OBJECT-TYPE
        SYNTAX    INTEGER
        ACCESS    read-only
        STATUS    mandatory
        DESCRIPTION
            "An object containing the peak round trip delay captured for the call"
        ::= { g3rtdelayEntry 7 }

    g3rtdelayExceed	OBJECT-TYPE
        SYNTAX    DisplayString (SIZE (0..9))
        ACCESS    read-only
        STATUS    mandatory
        DESCRIPTION
            "An object containing the type of Voice/Network Statistics exception
            that occured during the call.It is implied by the type of report and
            can be either Jitter/Pktloss/RoundTripDelay."
        ::= { g3rtdelayEntry 8 }


    -- the g3esmainsrv group

    g3esmainsrvClusterId	OBJECT-TYPE
        SYNTAX    INTEGER
        ACCESS    read-only
        STATUS    mandatory
        DESCRIPTION
            "An object containing the unique module id, for the main server
            from the license file for this cluster."
        ::= { g3esmainsrv 1 }

    g3esmainsrvPlatformType	OBJECT-TYPE
        SYNTAX    DisplayString (SIZE (0..7))
        ACCESS    read-only
        STATUS    mandatory
        DESCRIPTION
            "An object containing the platform type (S8500 or S8700)."
        ::= { g3esmainsrv 2 }

    g3esmainsrvServerAId	OBJECT-TYPE
        SYNTAX    INTEGER
        ACCESS    read-only
        STATUS    mandatory
        DESCRIPTION
            "An object containing the Server A id field. Acceptable values
            are 1-999 and it must be unique."
        ::= { g3esmainsrv 3 }

    g3esmainsrvServerAIP	OBJECT-TYPE
        SYNTAX    DisplayString (SIZE (0..41))
        ACCESS    read-only
        STATUS    mandatory
        DESCRIPTION
            "An object containing the IP Address for Server A."
        ::= { g3esmainsrv 4 }

    g3esmainsrvServerBId	OBJECT-TYPE
        SYNTAX    INTEGER
        ACCESS    read-only
        STATUS    mandatory
        DESCRIPTION
            "An object containing the Server B id field. Acceptable values
            are 1-999 and it must be unique (only available if the platform
            type is S8700)."
        ::= { g3esmainsrv 5 }

    g3esmainsrvServerBIP	OBJECT-TYPE
        SYNTAX    DisplayString (SIZE (0..41))
        ACCESS    read-only
        STATUS    mandatory
        DESCRIPTION
            "An object containing the  IP Address for Server B."
        ::= { g3esmainsrv 6 }

    g3esmainsrvPriorityScore	OBJECT-TYPE
        SYNTAX    DisplayString (SIZE (0..3))
        ACCESS    read-only
        STATUS    mandatory
        DESCRIPTION
            "An object containing a numerical value that allows the customer
            to assign a preferred cluster (can accept values of 1-100; default
            is blank)."
        ::= { g3esmainsrv 7 }

    g3esmainsrvNetComm	OBJECT-TYPE
        SYNTAX    DisplayString (SIZE (0..2))
        ACCESS    read-only
        STATUS    mandatory
        DESCRIPTION
            "An object containing the region the ESS cluster is in (used for
            localization; can have values between 1-64; default is 1)."
        ::= { g3esmainsrv 8 }

    g3esmainsrvSystemPref	OBJECT-TYPE
        SYNTAX    DisplayString (SIZE (0..1))
        ACCESS    read-only
        STATUS    mandatory
        DESCRIPTION
            "An object containing a flag that provides the cluster with a
            weighting factor that makes it a candidate to provide service
            on a system-wide basis (values can be 'y' or 'n'; default is 'y')."
        ::= { g3esmainsrv 9 }

    g3esmainsrvLocalPref	OBJECT-TYPE
        SYNTAX    DisplayString (SIZE (0..1))
        ACCESS    read-only
        STATUS    mandatory
        DESCRIPTION
            "An object containing a flag that provides the cluster with a
            weighting factor that makes it a candidate to provide service
            in the same network community before clusters in other network
            communities would be selected (values can be 'y' or 'n'; default
            is 'n')."
        ::= { g3esmainsrv 10 }

    g3esmainsrvLocalOnly	OBJECT-TYPE
        SYNTAX    DisplayString (SIZE (0..1))
        ACCESS    read-only
        STATUS    mandatory
        DESCRIPTION
            "An object containing a flag indicating that only clusters in the
            same network community can provide service (values can be 'y'
            or 'n'; default is 'n')."
        ::= { g3esmainsrv 11 }


    -- the g3survprocess group

    g3survprocessTage	OBJECT-TYPE
        SYNTAX    INTEGER
        ACCESS    read-only
        STATUS    mandatory
        DESCRIPTION
            "The number of timeticks since the coverage path data was last extracted
            from the switch by the Proxy Agent. This object along with the
            g3esserversTintvl object allows the Network Manager to determine
            the validity of the data in the cache and to control when the
            Proxy Agent extracts the data from the switch."
        ::= { g3survprocess 1 }

    g3survprocessTintvl	OBJECT-TYPE
        SYNTAX    INTEGER
        ACCESS    read-write
        STATUS    mandatory
        DESCRIPTION
            "An object containing the interval for which the data extracted
            from the switch is considered valid by the Proxy Agent. When a
            GET or GET-NEXT request for the data is received by the agent
            it uses the g3esserversTage and g3esserversTintvl objects to determine
            whether it should refresh the data."
        ::= { g3survprocess 2 }

    g3survprocessTdelay	OBJECT-TYPE
        SYNTAX    INTEGER
        ACCESS    read-only
        STATUS    mandatory
        DESCRIPTION
            "An object containing the delay encountered in updating the
            cached data."
        ::= { g3survprocess 3 }

    g3survprocessTretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached
            data is being retrieved and otherwise 'current'.This object
            may be set to 'update' to force a refresh of the cache."
        ::= { g3survprocess 4 }

    g3survprocessTcount	OBJECT-TYPE
        SYNTAX    Gauge
        ACCESS    read-only
        STATUS    mandatory
        DESCRIPTION
            "A Gauge object containing the number of data records in the cache."
        ::= { g3survprocess 5 }

    g3survprocessTable	OBJECT-TYPE
        SYNTAX    SEQUENCE OF G3survprocessEntry
        ACCESS    not-accessible
        STATUS    mandatory
        DESCRIPTION
            "A list of g3survprocess entries."
        ::= { g3survprocess 6 }

    g3survprocessEntry	OBJECT-TYPE
        SYNTAX    G3survprocessEntry
        ACCESS    not-accessible
        STATUS    mandatory
        DESCRIPTION
            "A g3survprocess entry containing objects of the
            g3survprocess information sent by the switch."
        INDEX    { g3survprocessClusterId }
        ::= { g3survprocessTable 1 }

    G3survprocessEntry ::= SEQUENCE {
        g3survprocessClusterId
            INTEGER,
        g3survprocessPlatformType
            DisplayString,
        g3survprocessActvesrvNodeName
            DisplayString,
        g3survprocessActivesrvIP
            DisplayString,
        g3survprocessServerAID
            DisplayString,
        g3survprocessServerAnodename
            DisplayString,
        g3survprocessServerAIP
            DisplayString,
        g3survprocessServerBID
            DisplayString,
        g3survprocessServerBnodename
            DisplayString,
        g3survprocessServerBIP
            DisplayString,
        g3survprocessSystemPref
            DisplayString,
        g3survprocessPriorityscore
            DisplayString,
        g3survprocessLocalPref
            DisplayString,
        g3survprocessLocalOnly
            DisplayString,
        g3survprocessActvservV6NodeName
            DisplayString,
        g3survprocessActivesrvV6IP
            DisplayString,
        g3survprocessServerAV6NodeName
            DisplayString,
        g3survprocessServerAV6IP
            DisplayString,
        g3survprocessServerBV6NodeName
            DisplayString,
        g3survprocessServerBV6IP
            DisplayString
        }

    g3survprocessClusterId	OBJECT-TYPE
        SYNTAX    INTEGER
        ACCESS    read-only
        STATUS    mandatory
        DESCRIPTION
            "An object containing the unique module id, for the enterprise
            survivable server, from the license file for this cluster."
        ::= { g3survprocessEntry 1 }

    g3survprocessPlatformType	OBJECT-TYPE
        SYNTAX    DisplayString (SIZE (0..7))
        ACCESS    read-only
        STATUS    mandatory
        DESCRIPTION
            "An object containing the platform type (S8500 or S8700)."
        ::= { g3survprocessEntry 2 }

    g3survprocessActvesrvNodeName	OBJECT-TYPE
        SYNTAX    DisplayString (SIZE (0..20))
        ACCESS    read-only
        STATUS    mandatory
        DESCRIPTION
            "An Object containing the name of the survivable processor."
        ::= { g3survprocessEntry 3 }

    g3survprocessActivesrvIP	OBJECT-TYPE
        SYNTAX    DisplayString (SIZE (0..40))
        ACCESS    read-only
        STATUS    mandatory
        DESCRIPTION
            "An object containing the  IP Address for Active Server in case of
            Duplex-ESS."
        ::= { g3survprocessEntry 4 }

    g3survprocessServerAID	OBJECT-TYPE
        SYNTAX    DisplayString (SIZE (0..3))
        ACCESS    read-only
        STATUS    mandatory
        DESCRIPTION
            "An object containing the server ID of Server A"
        ::= { g3survprocessEntry 5 }

    g3survprocessServerAnodename	OBJECT-TYPE
        SYNTAX    DisplayString (SIZE (0..20))
        ACCESS    read-only
        STATUS    mandatory
        DESCRIPTION
            "An object containing the nodename of Server A in case of Duplex-ess."
        ::= { g3survprocessEntry 6 }

    g3survprocessServerAIP	OBJECT-TYPE
        SYNTAX    DisplayString (SIZE (0..40))
        ACCESS    read-only
        STATUS    mandatory
        DESCRIPTION
            "An object containing the  IP Address for Server A."
        ::= { g3survprocessEntry 7 }

    g3survprocessServerBID	OBJECT-TYPE
        SYNTAX    DisplayString (SIZE (0..3))
        ACCESS    read-only
        STATUS    mandatory
        DESCRIPTION
            "An object containing the server ID of Server B"
        ::= { g3survprocessEntry 8 }

    g3survprocessServerBnodename	OBJECT-TYPE
        SYNTAX    DisplayString (SIZE (0..20))
        ACCESS    read-only
        STATUS    mandatory
        DESCRIPTION
            "An object containing the nodename of Server B in case of Duplex-ess"
        ::= { g3survprocessEntry 9 }

    g3survprocessServerBIP	OBJECT-TYPE
        SYNTAX    DisplayString (SIZE (0..40))
        ACCESS    read-only
        STATUS    mandatory
        DESCRIPTION
            "An object containing the  IP Address for Server B."
        ::= { g3survprocessEntry 10 }

    g3survprocessSystemPref	OBJECT-TYPE
        SYNTAX    DisplayString (SIZE (0..1))
        ACCESS    read-only
        STATUS    mandatory
        DESCRIPTION
            "An object containing a flag that provides the cluster with a
            weighting factor that makes it a candidate to provide service
            on a system-wide basis (values can be 'y' or 'n'; default is 'y')."
        ::= { g3survprocessEntry 11 }

    g3survprocessPriorityscore	OBJECT-TYPE
        SYNTAX    DisplayString (SIZE (0..3))
        ACCESS    read-only
        STATUS    mandatory
        DESCRIPTION
            "An object containing a numerical value that allows the customer
            to assign a preferred cluster (can accept values of 1-100; default
            is blank)."
        ::= { g3survprocessEntry 12 }

    g3survprocessLocalPref	OBJECT-TYPE
        SYNTAX    DisplayString (SIZE (0..1))
        ACCESS    read-only
        STATUS    mandatory
        DESCRIPTION
            "An object containing a flag that provides the cluster with a
            weighting factor that makes it a candidate to provide service
            in the same network community before clusters in other network
            communities would be selected (values can be 'y' or 'n'; default
            is 'n')."
        ::= { g3survprocessEntry 13 }

    g3survprocessLocalOnly	OBJECT-TYPE
        SYNTAX    DisplayString (SIZE (0..1))
        ACCESS    read-only
        STATUS    mandatory
        DESCRIPTION
            "An object containing a flag indicating that only clusters in the
            same network community can provide service (values can be 'y'
            or 'n'; default is 'n')."
        ::= { g3survprocessEntry 14 }

    g3survprocessActvservV6NodeName	OBJECT-TYPE
        SYNTAX    DisplayString (SIZE (0..20))
        ACCESS    read-only
        STATUS    mandatory
        DESCRIPTION
            "An Object containing the IPV6 name of the survivable processor."
        ::= { g3survprocessEntry 15 }

    g3survprocessActivesrvV6IP	OBJECT-TYPE
        SYNTAX    DisplayString (SIZE (0..40))
        ACCESS    read-only
        STATUS    mandatory
        DESCRIPTION
            "An object containing the  V6IP Address for Active Server in case of
            Duplex-ESS."
        ::= { g3survprocessEntry 16 }

    g3survprocessServerAV6NodeName	OBJECT-TYPE
        SYNTAX    DisplayString (SIZE (0..20))
        ACCESS    read-only
        STATUS    mandatory
        DESCRIPTION
            "An object containing the V6 nodename of Server A in case of Duplex-ess."
        ::= { g3survprocessEntry 17 }

    g3survprocessServerAV6IP	OBJECT-TYPE
        SYNTAX    DisplayString (SIZE (0..40))
        ACCESS    read-only
        STATUS    mandatory
        DESCRIPTION
            "An object containing the  IPV6 Address for Server A."
        ::= { g3survprocessEntry 18 }

    g3survprocessServerBV6NodeName	OBJECT-TYPE
        SYNTAX    DisplayString (SIZE (0..20))
        ACCESS    read-only
        STATUS    mandatory
        DESCRIPTION
            "An object containing the V6 nodename of ServerB in case of Duplex-ess."
        ::= { g3survprocessEntry 19 }

    g3survprocessServerBV6IP	OBJECT-TYPE
        SYNTAX    DisplayString (SIZE (0..40))
        ACCESS    read-only
        STATUS    mandatory
        ::= { g3survprocessEntry 20 }


    -- the g3nodenameipv4 group

    g3nodenameipv4Tage	OBJECT-TYPE
        SYNTAX    INTEGER
        ACCESS    read-only
        STATUS    mandatory
        DESCRIPTION
            "The number of timeticks since the node name data was last
            extracted from the switch by the MVSubAgent.  This object
            along with the g3nodenameintvl object allows the Network Manager
            to determine the validity of the node name data in the cache and to
            control when the MVSubAgent extracts the data from the switch.	"
        ::= { g3nodenameipv4 1 }

    g3nodenameipv4Tintvl	OBJECT-TYPE
        SYNTAX    INTEGER
        ACCESS    read-write
        STATUS    mandatory
        DESCRIPTION
            "An object containing the interval for which the node name
            data extracted from the switch is considered valid by the
            MVSubAgent. When a GET or GET-NEXT request for these node name
            objects is received by the agent it uses the g3nodenameTage
            and g3nodenameTintvl objects to determine whether it should refresh
            the cached nodenameTable.  If g3nodenamestmp + g3nodenameintvl is
            less than the current value of the sysUpTime object then the agent
            refreshes the nodenameTable cache.  In either case it responds to
            the requests it receives with the data it currently has in the cache."
        ::= { g3nodenameipv4 2 }

    g3nodenameipv4Tdelay	OBJECT-TYPE
        SYNTAX    INTEGER
        ACCESS    read-only
        STATUS    mandatory
        DESCRIPTION
            "An object containing the delay encountered in updating the cached data."
        ::= { g3nodenameipv4 3 }

    g3nodenameipv4Tretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may be set 
            to 'update' to force a refresh of the cache."
        ::= { g3nodenameipv4 4 }

    g3nodenameipv4Tcount	OBJECT-TYPE
        SYNTAX    Gauge
        ACCESS    read-only
        STATUS    mandatory
        DESCRIPTION
            "A Gauge object containing the number of data records in the cache."
        ::= { g3nodenameipv4 5 }

    g3nodenameipv4Table	OBJECT-TYPE
        SYNTAX    SEQUENCE OF G3nodenameipv4Entry
        ACCESS    not-accessible
        STATUS    mandatory
        DESCRIPTION
            "A list of g3nodenameipv4 entries."
        ::= { g3nodenameipv4 6 }

    g3nodenameipv4Entry	OBJECT-TYPE
        SYNTAX    G3nodenameipv4Entry
        ACCESS    not-accessible
        STATUS    mandatory
        DESCRIPTION
            "A g3nodenameipv4 entry containing objects of the
            g3nodenameipv4 information sent by the switch."
        INDEX    { g3nodenameipv4Name }
        ::= { g3nodenameipv4Table 1 }

    G3nodenameipv4Entry ::= SEQUENCE {
        g3nodenameipv4Name
            DisplayString,
        g3nodenameipv4Type
            DisplayString,
        g3nodenameipv4IP
            DisplayString
        }

    g3nodenameipv4Name	OBJECT-TYPE
        SYNTAX    DisplayString (SIZE (0..15))
        ACCESS    read-only
        STATUS    mandatory
        DESCRIPTION
            "This MIB variable displays the names of all the nodes that are
            administered on the system."
        ::= { g3nodenameipv4Entry 1 }

    g3nodenameipv4Type	OBJECT-TYPE
        SYNTAX    DisplayString (SIZE (0..5))
        ACCESS    read-only
        STATUS    mandatory
        DESCRIPTION
            "An object containing the type of the node."
        ::= { g3nodenameipv4Entry 2 }

    g3nodenameipv4IP	OBJECT-TYPE
        SYNTAX    DisplayString (SIZE (0..40))
        ACCESS    read-only
        STATUS    mandatory
        DESCRIPTION
            "An Object displaying the IPAddress of the node name"
        ::= { g3nodenameipv4Entry 3 }


    -- the g3nodenameipv6 group

    g3nodenameipv6Tage	OBJECT-TYPE
        SYNTAX    INTEGER
        ACCESS    read-only
        STATUS    mandatory
        DESCRIPTION
            "The number of timeticks since the node name data was last
            extracted from the switch by the MVSubAgent.  This object
            along with the g3nodenameintvl object allows the Network Manager
            to determine the validity of the node name data in the cache and to
            control when the MVSubAgent extracts the data from the switch."
        ::= { g3nodenameipv6 1 }

    g3nodenameipv6Tintvl	OBJECT-TYPE
        SYNTAX    INTEGER
        ACCESS    read-write
        STATUS    mandatory
        DESCRIPTION
            "An object containing the interval for which the node name
            data extracted from the switch is considered valid by the
            MVSubAgent.  When a GET or GET-NEXT request for these node name
            objects is received by the agent it uses the g3nodenameage
            and g3nodenameintvl objects to determine whether it should refresh
            the cached nodenameTable.  If g3nodenamestmp +
            g3nodenameintvl is less than the current value of the sysUpTime
            object then the agent refreshes the nodenameTable cache.  In
            either case it responds to the requests it receives with the data
             currently has in the cache."
        ::= { g3nodenameipv6 2 }

    g3nodenameipv6Tdelay	OBJECT-TYPE
        SYNTAX    INTEGER
        ACCESS    read-only
        STATUS    mandatory
        DESCRIPTION
            "An object containing the delay encountered in updating
            the cached data."
        ::= { g3nodenameipv6 3 }

    g3nodenameipv6Tretrieve	OBJECT-TYPE
        SYNTAX    INTEGER
		  {
			failed(1),	-- cache data is corrupted
			update(2),	-- update the cached data
			current(3)	-- cached data is current
		  }
        ACCESS    read-write
        STATUS    mandatory
        DESCRIPTION
            "An object containing a flag that is 'update' if the cached data
            is being retrieved and otherwise 'current'.  This object may
            be set to 'update' to force a refresh of the cache."
        ::= { g3nodenameipv6 4 }

    g3nodenameipv6Tcount	OBJECT-TYPE
        SYNTAX    Gauge
        ACCESS    read-only
        STATUS    mandatory
        DESCRIPTION
            "A Gauge object containing the number of data records in the cache."
        ::= { g3nodenameipv6 5 }

    g3nodenameipv6Table	OBJECT-TYPE
        SYNTAX    SEQUENCE OF G3nodenameipv6Entry
        ACCESS    not-accessible
        STATUS    mandatory
        DESCRIPTION
            "A list of g3nodenameipv6 entries."
        ::= { g3nodenameipv6 6 }

    g3nodenameipv6Entry	OBJECT-TYPE
        SYNTAX    G3nodenameipv6Entry
        ACCESS    not-accessible
        STATUS    mandatory
        DESCRIPTION
            "A g3nodenameipv6 entry containing objects of the
            g3nodenameipv6 information sent by the switch."
        INDEX    { g3nodenameipv6Name }
        ::= { g3nodenameipv6Table 1 }

    G3nodenameipv6Entry ::= SEQUENCE {
        g3nodenameipv6Name
            DisplayString,
        g3nodenameipv6Type
            DisplayString,
        g3nodenameipv6IP
            DisplayString
        }

    g3nodenameipv6Name	OBJECT-TYPE
        SYNTAX    DisplayString (SIZE (0..13))
        ACCESS    read-only
        STATUS    mandatory
        DESCRIPTION
            "This MIB variable displays the names of all the nodes that are
            administered on the system."
        ::= { g3nodenameipv6Entry 1 }

    g3nodenameipv6Type	OBJECT-TYPE
        SYNTAX    DisplayString (SIZE (0..5))
        ACCESS    read-only
        STATUS    mandatory
        DESCRIPTION
            "An object containing the type of the node"
        ::= { g3nodenameipv6Entry 2 }

    g3nodenameipv6IP	OBJECT-TYPE
        SYNTAX    DisplayString (SIZE (0..40))
        ACCESS    read-only
        STATUS    mandatory
        DESCRIPTION
            "An Object displaying the IPAddress"
        ::= { g3nodenameipv6Entry 3 }


    -- the g3lspall group

    g3lspallTage	OBJECT-TYPE
        SYNTAX    INTEGER
        ACCESS    read-only
        STATUS    mandatory
        DESCRIPTION
            "The number of timeticks since the survivable processor"
        ::= { g3lspall 1 }

    g3lspallTintvl	OBJECT-TYPE
        SYNTAX    INTEGER
        ACCESS    read-write
        STATUS    mandatory
        DESCRIPTION
            "An object containing the interval for which the data extracted"
        ::= { g3lspall 2 }

    g3lspallTdelay	OBJECT-TYPE
        SYNTAX    INTEGER
        ACCESS    read-only
        STATUS    mandatory
        DESCRIPTION
            "An object containing the delay encountered in updating the cached data"
        ::= { g3lspall 3 }

    g3lspallTretrieve	OBJECT-TYPE
        SYNTAX    INTEGER
		  {
			failed(1),	-- cache data is corrupted
			update(2),	-- update the cached data
			current(3)	-- cached data is current
		  }
        ACCESS    read-write
        STATUS    mandatory
        DESCRIPTION
            " An INTEGER object containing a flag that is 'update' if the cached"
        ::= { g3lspall 4 }

    g3lspallTcount	OBJECT-TYPE
        SYNTAX    Gauge
        ACCESS    read-only
        STATUS    mandatory
        DESCRIPTION
            "A Gauge object containing the number of data records in the cache."
        ::= { g3lspall 5 }

    g3lspallTable	OBJECT-TYPE
        SYNTAX    SEQUENCE OF G3lspallEntry
        ACCESS    not-accessible
        STATUS    mandatory
        DESCRIPTION
            "A list of g3lspall entries."
        ::= { g3lspall 6 }

    g3lspallEntry	OBJECT-TYPE
        SYNTAX    G3lspallEntry
        ACCESS    not-accessible
        STATUS    mandatory
        DESCRIPTION
            "A g3lspall entry containing objects of the
            g3lspall information sent by the switch."
        INDEX    { g3lspallLSP }
        ::= { g3lspallTable 1 }

    G3lspallEntry ::= SEQUENCE {
        g3lspallLSP
            INTEGER,
        g3lspallV4NodeName
            DisplayString,
        g3lspallV6NodeName
            DisplayString,
        g3lspallIPV4Addr
            DisplayString,
        g3lspallIPV6Addr
            DisplayString,
        g3lspallXlnUpdated
            DisplayString,
        g3lspallNetworkRegion
            DisplayString,
        g3lspallType
            DisplayString,
        g3lspallRegistered
            DisplayString,
        g3lspallActive
            DisplayString
        }

    g3lspallLSP	OBJECT-TYPE
        SYNTAX    INTEGER
        ACCESS    read-only
        STATUS    mandatory
        DESCRIPTION
            "An INTEGER object containing an index numbering the LSP records"
        ::= { g3lspallEntry 1 }

    g3lspallV4NodeName	OBJECT-TYPE
        SYNTAX    DisplayString (SIZE (0..20))
        ACCESS    read-only
        STATUS    mandatory
        DESCRIPTION
            "An object containing the V4  node name of the survivable processor."
        ::= { g3lspallEntry 2 }

    g3lspallV6NodeName	OBJECT-TYPE
        SYNTAX    DisplayString (SIZE (0..20))
        ACCESS    read-only
        STATUS    mandatory
        DESCRIPTION
            "An object containing the IPV6 node name of the survivable processor."
        ::= { g3lspallEntry 3 }

    g3lspallIPV4Addr	OBJECT-TYPE
        SYNTAX    DisplayString (SIZE (0..40))
        ACCESS    read-only
        STATUS    mandatory
        DESCRIPTION
            "An object containing the IPV4  address of the survivable processor."
        ::= { g3lspallEntry 4 }

    g3lspallIPV6Addr	OBJECT-TYPE
        SYNTAX    DisplayString (SIZE (0..40))
        ACCESS    read-only
        STATUS    mandatory
        DESCRIPTION
            "An object containing the IPV6 Address of the survivable processor."
        ::= { g3lspallEntry 5 }

    g3lspallXlnUpdated	OBJECT-TYPE
        SYNTAX    DisplayString (SIZE (0..17))
        ACCESS    read-only
        STATUS    mandatory
        DESCRIPTION
            "An object containing the date and time of the last translation"
        ::= { g3lspallEntry 6 }

    g3lspallNetworkRegion	OBJECT-TYPE
        SYNTAX    DisplayString (SIZE (0..3))
        ACCESS    read-only
        STATUS    mandatory
        DESCRIPTION
            "An object containing the network region of the survivable processor."
        ::= { g3lspallEntry 7 }

    g3lspallType	OBJECT-TYPE
        SYNTAX    DisplayString (SIZE (0..5))
        ACCESS    read-only
        STATUS    mandatory
        DESCRIPTION
            "An object containing the type of the survivable processor (LSP"
        ::= { g3lspallEntry 8 }

    g3lspallRegistered	OBJECT-TYPE
        SYNTAX    DisplayString (SIZE (0..1))
        ACCESS    read-only
        STATUS    mandatory
        DESCRIPTION
            "An object indicating whether the survivable processor is"
        ::= { g3lspallEntry 9 }

    g3lspallActive	OBJECT-TYPE
        SYNTAX    DisplayString (SIZE (0..1))
        ACCESS    read-only
        STATUS    mandatory
        DESCRIPTION
            "An object indicating the active state of survivable processor"
        ::= { g3lspallEntry 10 }


    -- the g3trunkstaOptions group

    g3trunkstaOptionsBeginAt	OBJECT-TYPE
        SYNTAX    INTEGER
        ACCESS    read-write
        STATUS    mandatory
        DESCRIPTION
            "An object containing the position to start from."
        ::= { g3trunkstaOptions 1 }

    g3trunkstaOptionsNumTrkGrps	OBJECT-TYPE
        SYNTAX    INTEGER
        ACCESS    read-write
        STATUS    mandatory
        DESCRIPTION
            "An object stating the Number of Trunk Groups to query."
        ::= { g3trunkstaOptions 2 }

    g3trunkstaOptionsTable	OBJECT-TYPE
        SYNTAX    SEQUENCE OF G3trunkstaOptionsEntry
        ACCESS    not-accessible
        STATUS    mandatory
        DESCRIPTION
            "A list of g3trunkstaOptions entries."
        ::= { g3trunkstaOptions 3 }

    g3trunkstaOptionsEntry	OBJECT-TYPE
        SYNTAX    G3trunkstaOptionsEntry
        ACCESS    not-accessible
        STATUS    mandatory
        DESCRIPTION
            "A g3trunkstaOptions entry containing objects of the
            g3trunkstaOptions information sent by the switch."
        INDEX    { g3trunkstaOptionsTrunkGroup, g3trunkstaOptionsMember }
        ::= { g3trunkstaOptionsTable 1 }

    G3trunkstaOptionsEntry ::= SEQUENCE {
        g3trunkstaOptionsTrunkGroup
            INTEGER,
        g3trunkstaOptionsMember
            INTEGER,
        g3trunkstaOptionsServiceState
            DisplayString,
        g3trunkstaOptionsMaintBusy
            DisplayString,
        g3trunkstaOptionsConnPort1
            DisplayString,
        g3trunkstaOptionsConnPort2
            DisplayString,
        g3trunkstaOptionsConnPort3
            DisplayString,
        g3trunkstaOptionsConnPort4
            DisplayString,
        g3trunkstaOptionsConnPort5
            DisplayString,
        g3trunkstaOptionsConnPort6
            DisplayString,
        g3trunkstaOptionsConnPort7
            DisplayString,
        g3trunkstaOptionsConnPort8
            DisplayString,
        g3trunkstaOptionsConnPort9
            DisplayString
        }

    g3trunkstaOptionsTrunkGroup	OBJECT-TYPE
        SYNTAX    INTEGER
        ACCESS    read-only
        STATUS    mandatory
        DESCRIPTION
            "An INTEGER Object that uniquely identifies an administered."
        ::= { g3trunkstaOptionsEntry 1 }

    g3trunkstaOptionsMember	OBJECT-TYPE
        SYNTAX    INTEGER
        ACCESS    read-only
        STATUS    mandatory
        DESCRIPTION
            "An INTEGER Object that uniquely identifies a trunk group member."
        ::= { g3trunkstaOptionsEntry 2 }

    g3trunkstaOptionsServiceState	OBJECT-TYPE
        SYNTAX    DisplayString (SIZE (0..18))
        ACCESS    read-only
        STATUS    mandatory
        DESCRIPTION
            "A DisplayString Object containing the service state of the trunk."
        ::= { g3trunkstaOptionsEntry 3 }

    g3trunkstaOptionsMaintBusy	OBJECT-TYPE
        SYNTAX    DisplayString (SIZE (0..4))
        ACCESS    read-only
        STATUS    mandatory
        DESCRIPTION
            "A DisplayString Object that indicates whether the trunk has
            been busiedfor maintenance."
        ::= { g3trunkstaOptionsEntry 4 }

    g3trunkstaOptionsConnPort1	OBJECT-TYPE
        SYNTAX    DisplayString (SIZE (0..10))
        ACCESS    read-only
        STATUS    mandatory
        DESCRIPTION
            "A DisplayString Object that contains the nth port connected"
        ::= { g3trunkstaOptionsEntry 5 }

    g3trunkstaOptionsConnPort2	OBJECT-TYPE
        SYNTAX    DisplayString (SIZE (0..10))
        ACCESS    read-only
        STATUS    mandatory
        DESCRIPTION
            "A DisplayString Object that contains the nth port connected"
        ::= { g3trunkstaOptionsEntry 6 }

    g3trunkstaOptionsConnPort3	OBJECT-TYPE
        SYNTAX    DisplayString (SIZE (0..10))
        ACCESS    read-only
        STATUS    mandatory
        DESCRIPTION
            "A DisplayString Object that contains the nth port connected"
        ::= { g3trunkstaOptionsEntry 7 }

    g3trunkstaOptionsConnPort4	OBJECT-TYPE
        SYNTAX    DisplayString (SIZE (0..10))
        ACCESS    read-only
        STATUS    mandatory
        DESCRIPTION
            "A DisplayString Object that contains the nth port connected"
        ::= { g3trunkstaOptionsEntry 8 }

    g3trunkstaOptionsConnPort5	OBJECT-TYPE
        SYNTAX    DisplayString (SIZE (0..10))
        ACCESS    read-only
        STATUS    mandatory
        DESCRIPTION
            "A DisplayString Object that contains the nth port connected"
        ::= { g3trunkstaOptionsEntry 9 }

    g3trunkstaOptionsConnPort6	OBJECT-TYPE
        SYNTAX    DisplayString (SIZE (0..10))
        ACCESS    read-only
        STATUS    mandatory
        DESCRIPTION
            "A DisplayString Object that contains the nth port connected"
        ::= { g3trunkstaOptionsEntry 10 }

    g3trunkstaOptionsConnPort7	OBJECT-TYPE
        SYNTAX    DisplayString (SIZE (0..10))
        ACCESS    read-only
        STATUS    mandatory
        DESCRIPTION
            "A DisplayString Object that contains the nth port connected"
        ::= { g3trunkstaOptionsEntry 11 }

    g3trunkstaOptionsConnPort8	OBJECT-TYPE
        SYNTAX    DisplayString (SIZE (0..10))
        ACCESS    read-only
        STATUS    mandatory
        DESCRIPTION
            "A DisplayString Object that contains the nth port connected"
        ::= { g3trunkstaOptionsEntry 12 }

    g3trunkstaOptionsConnPort9	OBJECT-TYPE
        SYNTAX    DisplayString (SIZE (0..10))
        ACCESS    read-only
        STATUS    mandatory
        DESCRIPTION
            "A DisplayString Object that contains the nth port connected"
        ::= { g3trunkstaOptionsEntry 13 }


    -- the g3statstaOptions group

    g3statstaOptionsBeginAt	OBJECT-TYPE
        SYNTAX    INTEGER
        ACCESS    read-write
        STATUS    mandatory
        DESCRIPTION
            "An object containing the position to start from."
        ::= { g3statstaOptions 1 }

    g3statstaOptionsNumStations	OBJECT-TYPE
        SYNTAX    INTEGER
        ACCESS    read-write
        STATUS    mandatory
        DESCRIPTION
            "An object stating the number of stations to query."
        ::= { g3statstaOptions 2 }

    g3statstaOptionsTable	OBJECT-TYPE
        SYNTAX    SEQUENCE OF G3statstaOptionsEntry
        ACCESS    not-accessible
        STATUS    mandatory
        DESCRIPTION
            "A list of g3statstaOptions entries."
        ::= { g3statstaOptions 3 }

    g3statstaOptionsEntry	OBJECT-TYPE
        SYNTAX    G3statstaOptionsEntry
        ACCESS    not-accessible
        STATUS    mandatory
        DESCRIPTION
            "A g3statstaOptions entry containing objects of the
            g3statstaOptions information sent by the switch."
        INDEX    { g3statstaOptionsExtension }
        ::= { g3statstaOptionsTable 1 }

    G3statstaOptionsEntry ::= SEQUENCE {
        g3statstaOptionsExtension
            DisplayString,
        g3statstaOptionsServiceState
            DisplayString,
        g3statstaOptionsMaintBusy
            DisplayString,
        g3statstaOptionsConnPort1
            DisplayString,
        g3statstaOptionsConnPort2
            DisplayString,
        g3statstaOptionsConnPort3
            DisplayString,
        g3statstaOptionsConnPort4
            DisplayString,
        g3statstaOptionsConnPort5
            DisplayString,
        g3statstaOptionsConnPort6
            DisplayString,
        g3statstaOptionsSACactive
            DisplayString,
        g3statstaOptionsCFdestExt
            DisplayString,
        g3statstaOptionsRingCutOff
            DisplayString,
        g3statstaOptionsSerialNbr
            DisplayString,
        g3statstaOptionsPartID
            DisplayString,
        g3statstaOptionsSwitchPort
            DisplayString,
        g3statstaOptionsSwitchIPAddr
            DisplayString,
        g3statstaOptionsSwitchIPPort
            DisplayString,
        g3statstaOptionsSetIPAddr
            DisplayString,
        g3statstaOptionsSetIPPort
            DisplayString
        }

    g3statstaOptionsExtension	OBJECT-TYPE
        SYNTAX    DisplayString (SIZE (0..15))
        ACCESS    read-only
        STATUS    mandatory
        DESCRIPTION
            "A DisplayString Object that uniquely identifies an administered station."
        ::= { g3statstaOptionsEntry 1 }

    g3statstaOptionsServiceState	OBJECT-TYPE
        SYNTAX    DisplayString (SIZE (0..22))
        ACCESS    read-only
        STATUS    mandatory
        DESCRIPTION
            "A DisplayString Object containing the service state of the station."
        ::= { g3statstaOptionsEntry 2 }

    g3statstaOptionsMaintBusy	OBJECT-TYPE
        SYNTAX    DisplayString (SIZE (0..4))
        ACCESS    read-only
        STATUS    mandatory
        DESCRIPTION
            "A DisplayString Object that indicates whether the station has
            been busied for maintenance."
        ::= { g3statstaOptionsEntry 3 }

    g3statstaOptionsConnPort1	OBJECT-TYPE
        SYNTAX    DisplayString (SIZE (0..10))
        ACCESS    read-only
        STATUS    mandatory
        DESCRIPTION
            "A DisplayString Object that contains the first port connected to 
            the station."
        ::= { g3statstaOptionsEntry 4 }

    g3statstaOptionsConnPort2	OBJECT-TYPE
        SYNTAX    DisplayString (SIZE (0..10))
        ACCESS    read-only
        STATUS    mandatory
        ::= { g3statstaOptionsEntry 5 }

    g3statstaOptionsConnPort3	OBJECT-TYPE
        SYNTAX    DisplayString (SIZE (0..10))
        ACCESS    read-only
        STATUS    mandatory
        ::= { g3statstaOptionsEntry 6 }

    g3statstaOptionsConnPort4	OBJECT-TYPE
        SYNTAX    DisplayString (SIZE (0..10))
        ACCESS    read-only
        STATUS    mandatory
        ::= { g3statstaOptionsEntry 7 }

    g3statstaOptionsConnPort5	OBJECT-TYPE
        SYNTAX    DisplayString (SIZE (0..10))
        ACCESS    read-only
        STATUS    mandatory
        ::= { g3statstaOptionsEntry 8 }

    g3statstaOptionsConnPort6	OBJECT-TYPE
        SYNTAX    DisplayString (SIZE (0..10))
        ACCESS    read-only
        STATUS    mandatory
        ::= { g3statstaOptionsEntry 9 }

    g3statstaOptionsSACactive	OBJECT-TYPE
        SYNTAX    DisplayString (SIZE (0..4))
        ACCESS    read-only
        STATUS    mandatory
        DESCRIPTION
            "A DisplayString Object that indicates whether SAC has been"
        ::= { g3statstaOptionsEntry 10 }

    g3statstaOptionsCFdestExt	OBJECT-TYPE
        SYNTAX    DisplayString (SIZE (0..17))
        ACCESS    read-only
        STATUS    mandatory
        DESCRIPTION
            "A DisplayString Object that contains the CF Destination Extension"
        ::= { g3statstaOptionsEntry 11 }

    g3statstaOptionsRingCutOff	OBJECT-TYPE
        SYNTAX    DisplayString (SIZE (0..8))
        ACCESS    read-only
        STATUS    mandatory
        DESCRIPTION
            "A DisplayString Object that indicates whether Ring Cut Off has
            been activated for the station."
        ::= { g3statstaOptionsEntry 12 }

    g3statstaOptionsSerialNbr	OBJECT-TYPE
        SYNTAX    DisplayString (SIZE (0..12))
        ACCESS    read-only
        STATUS    mandatory
        DESCRIPTION
            "A DisplayString Object that contains the serial number for the station."
        ::= { g3statstaOptionsEntry 13 }

    g3statstaOptionsPartID	OBJECT-TYPE
        SYNTAX    DisplayString (SIZE (0..11))
        ACCESS    read-only
        STATUS    mandatory
        DESCRIPTION
            "A DisplayString Object that contains the part id for the"
        ::= { g3statstaOptionsEntry 14 }

    g3statstaOptionsSwitchPort	OBJECT-TYPE
        SYNTAX    DisplayString (SIZE (0..8))
        ACCESS    read-only
        STATUS    mandatory
        DESCRIPTION
            "A DisplayString Object that contains the switch port for the station."
        ::= { g3statstaOptionsEntry 15 }

    g3statstaOptionsSwitchIPAddr	OBJECT-TYPE
        SYNTAX    DisplayString (SIZE (0..40))
        ACCESS    read-only
        STATUS    mandatory
        DESCRIPTION
            "A DisplayString Object that contains the switch-end IP address for the
            station."
        ::= { g3statstaOptionsEntry 16 }

    g3statstaOptionsSwitchIPPort	OBJECT-TYPE
        SYNTAX    DisplayString (SIZE (0..6))
        ACCESS    read-only
        STATUS    mandatory
        DESCRIPTION
            "A DisplayString Object that contains the switch-end IP port nbr for the"
        ::= { g3statstaOptionsEntry 17 }

    g3statstaOptionsSetIPAddr	OBJECT-TYPE
        SYNTAX    DisplayString (SIZE (0..40))
        ACCESS    read-only
        STATUS    mandatory
        DESCRIPTION
            "A DisplayString Object that contains the set-end IP address for the"
        ::= { g3statstaOptionsEntry 18 }

    g3statstaOptionsSetIPPort	OBJECT-TYPE
        SYNTAX    DisplayString (SIZE (0..6))
        ACCESS    read-only
        STATUS    mandatory
        DESCRIPTION
            "A DisplayString Object that contains the set-end IP port nbr for the"
        ::= { g3statstaOptionsEntry 19 }



    -- the busyrls group

    g3busyrlsAction	OBJECT-TYPE
        SYNTAX    INTEGER
		  {
			busyout(1),	  -- busyout specified object
			release(2),  	  -- release specified object
			campon-busyout(3) -- campon-busyout specified object
		  }
        ACCESS    read-write
        STATUS    mandatory
        DESCRIPTION
            "The last action performed on a specified object. This 
	    field must be set in conjunction with the g3busyrlsObject field."
        ::= { g3busyrls 1 }

    g3busyrlsObject	OBJECT-TYPE
        SYNTAX    INTEGER
		  {
			trunk(1),	   -- trunk group/member object
			board(2),	   -- board/port on board object
			media-processor(3) -- media-processor object
		  }
        ACCESS    read-write
        STATUS    mandatory
        DESCRIPTION
            "The object associated with the last action. This field 
	    must be set in conjunction with the g3busyrlsTrunkGroup,
	    g3busyrlsTrunkMember, g3busyrlsBoard, and g3busyrlsPort
	    fields. This field can only be set to 'media-processor'
	    if g3busyrlsAction is either 'campon-busyout' or 'release'."
        ::= { g3busyrls 2 }

    g3busyrlsTrunkGroup	OBJECT-TYPE
        SYNTAX    INTEGER
        ACCESS    read-write
        STATUS    mandatory
        DESCRIPTION
            "The trunk group number associated with the g3busyrlsObject
	    field. This field is only applicable if the g3busyrlsObject 
	    field is set to 'trunk'."
        ::= { g3busyrls 3 }

    g3busyrlsTrunkMember	OBJECT-TYPE
        SYNTAX    INTEGER
        ACCESS    read-write
        STATUS    mandatory
        DESCRIPTION
            "The trunk group member associated with the g3busyrlsObject
	    field. This field is only applicable if the g3busyrlsObject 
	    field is set to 'trunk'. This field either contains a
	    trunk member number (1-255) or a '0' if an entire trunk
	    group (all members) is to be operated on by the last action."
        ::= { g3busyrls 4 }

    g3busyrlsBoard	OBJECT-TYPE
        SYNTAX    DisplayString (SIZE (0..7))
        ACCESS    read-write
        STATUS    mandatory
        DESCRIPTION
            "A DisplayString that uniquely identifies a board location 
	    (cabinet(01-22):carrier(A-E):slot(01-20)) associated with the 
	    g3busyrlsObject field. This field is only applicable if the 
	    g3busyrlsObject field is set to 'board' or 'media-processor'."
        ::= { g3busyrls 5 }

    g3busyrlsPort	OBJECT-TYPE
        SYNTAX    INTEGER
        ACCESS    read-write
        STATUS    mandatory
        DESCRIPTION
            "The port location associated with the g3busyrlsObject
	    field. This field is only applicable if the g3busyrlsObject 
	    field is set to 'board'. This field either contains a
	    port location number (1-24) or a '0' if an entire board
	    (all ports on the board) are to be operated on by the 
	    last action."
        ::= { g3busyrls 6 }

    -- the g3client group

    g3clientTable		OBJECT-TYPE
	SYNTAX	SEQUENCE OF G3clientEntry
	ACCESS	not-accessible
	STATUS	mandatory
	DESCRIPTION
	    "A list of g3client entries."
	::= { g3client 1 }

    g3clientEntry		OBJECT-TYPE
	SYNTAX	G3clientEntry
	ACCESS	not-accessible
	STATUS	mandatory
	DESCRIPTION
	    "A g3client entry containing objects of the
	    g3client information for the G3 Proxy Agent."
	INDEX	{ g3clientTableIndex }
	::= { g3clientTable 1 }

    G3clientEntry ::= SEQUENCE {
	g3clientCommunity
	    DisplayString,
	g3clientCustomerId
	    DisplayString,
	g3clientDescription
	    DisplayString,
	g3clientExternalName
	    DisplayString,
	g3clientConnectStatus
	    DisplayString,
	g3clientTableIndex
	    INTEGER,
	g3clientSubmapType
	    INTEGER,
	g3clientState
	    INTEGER,
	g3clientSubmapName
	    DisplayString,
	g3clientConnectType
	    DisplayString,
	g3clientDynamicTimeout
	    INTEGER,
	g3clientEnumType
	    INTEGER,
	g3clientEnumState
	    INTEGER,
	g3clientDialString1
	    DisplayString,
	g3clientDialString2
	    DisplayString,
	g3clientProductID
	    DisplayString
	}

    g3clientCommunity		OBJECT-TYPE
	SYNTAX	DisplayString (SIZE (0..256))
	ACCESS	read-only
	STATUS	mandatory
	DESCRIPTION
	    "A DisplayString Object containing the Community substring for a
	    G3 client."
	::= { g3clientEntry 1 }


    g3clientCustomerId		OBJECT-TYPE
	SYNTAX	DisplayString (SIZE (0..256))
	ACCESS	read-only
	STATUS	mandatory
	DESCRIPTION
	    "A DisplayString Object containing the Customer ID for a
	    G3 client."
	::= { g3clientEntry 2 }

    g3clientDescription		OBJECT-TYPE
	SYNTAX	DisplayString (SIZE (0..256))
	ACCESS	read-only
	STATUS	mandatory
	DESCRIPTION
	    "A DisplayString Object containing the Description for a
	    G3 client."
	::= { g3clientEntry 3 }

    g3clientExternalName	OBJECT-TYPE
	SYNTAX	DisplayString (SIZE (0..256))
	ACCESS	read-only
	STATUS	mandatory
	DESCRIPTION
	    "A DisplayString Object containing the External Name for a
	    G3 client."
	::= { g3clientEntry 4 }

    g3clientConnectStatus	OBJECT-TYPE
	SYNTAX	DisplayString (SIZE (0..256))
	ACCESS	read-only
	STATUS	mandatory
	DESCRIPTION
	    "A DisplayString Object containing the Connection Status for a
	    G3 client."
	::= { g3clientEntry 5 }

    g3clientSubmapType	OBJECT-TYPE
        SYNTAX    INTEGER
        ACCESS    read-only
        STATUS    mandatory
        DESCRIPTION
            "The type of submap on which the managed node icon is to
	    be placed on the NMS ('generic' = '0', 'usa' = '1', and
	    'custom' = '2')."
        ::= { g3clientEntry 6 }

    g3clientState	OBJECT-TYPE
	SYNTAX	INTEGER
	ACCESS	read-only
	STATUS	mandatory
	DESCRIPTION
	    "An INTEGER object containing a numeric value representing the
	    state in which to place the managed node icon on the NMS if the
	    g3connectSubmapType is set to 'usa' ('Alabama' = '0', 'Alaska' 
	    = 1, . . . 'Wyoming' = 49)."
        ::= { g3clientEntry 7 }

    g3clientSubmapName	OBJECT-TYPE
	SYNTAX	DisplayString (SIZE (0..40))
	ACCESS	read-only
	STATUS	mandatory
	DESCRIPTION
	    "A DisplayString Object containing the submap name in which
	    to place the managed node icon on the NMS if g3clientSubmapType
	    is set to 'custom'."
	::= { g3clientEntry 8 }

    g3clientConnectType	OBJECT-TYPE
	SYNTAX	DisplayString (SIZE (0..7))
	ACCESS	read-only
	STATUS	mandatory
	DESCRIPTION
	    "A DisplayString Object containing the Connection Type for a
	    G3 client."
	::= { g3clientEntry 9 }

    g3clientDynamicTimeout	OBJECT-TYPE
	SYNTAX	INTEGER
	ACCESS	read-only
	STATUS	mandatory
	DESCRIPTION
	    "An INTEGER object containing the number of idle minutes to
	    wait before a dynamic connection is dropped."
	::= { g3clientEntry 10 }

    g3clientEnumType	OBJECT-TYPE
        SYNTAX    INTEGER
		{
			generic(1),
			usa(2),
			custom(3)
		}
        ACCESS    read-only
        STATUS    mandatory
        DESCRIPTION
            "The enumerated type of submap on which the managed node icon 
	    is to be placed on the NMS."
        ::= { g3clientEntry 11 }

    g3clientEnumState	OBJECT-TYPE
	SYNTAX	INTEGER
		  {
			alabama(1),
			alaska(2),
			arizona(3),
			arkansas(4),
			california(5),
			colorado(6),	
			connecticut(7),
			delaware(8),
			florida(9),
			georgia(10),
			hawaii(11),
			idaho(12),
			illinois(13),
			indiana(14),
			iowa(15),
			kansas(16),
			kentucky(17),
			louisiana(18),
			maine(19),
			maryland(20),
			massachusetts(21),
			michigan(22),
			minnesota(23),
			mississippi(24),
			missouri(25),
			montana(26),
			nebraska(27),
			nevada(28),
			new-hampshire(29),
			new-jersey(30),
			new-mexico(31),
			new-york(32),
			north-carolina(33),
			north-dakota(34),
			ohio(35),
			oklahoma(36),
			oregon(37),
			pennsylvania(38),
			rhode-island(39),
			south-carolina(40),
			south-dakota(41),
			tennessee(42),
			texas(43),
			utah(44),
			vermont(45),
			virginia(46),
			washington(47),
			west-virginia(48),
			wisconsin(49),
			wyoming(50)
		  }
	ACCESS	read-only
	STATUS	mandatory
	DESCRIPTION
	    "An INTEGER object containing an enumerated value of the state 
	    in which to place the managed node icon on the NMS if the
	    g3connectEnumType is set to 'usa'."
        ::= { g3clientEntry 12 }

    g3clientDialString1	OBJECT-TYPE
	SYNTAX	DisplayString (SIZE (0..40))
	ACCESS	read-only
	STATUS	mandatory
	DESCRIPTION
	    "A DisplayString Object containing the first dial string
	    administered for the managed node."
	::= { g3clientEntry 13 }

    g3clientDialString2	OBJECT-TYPE
	SYNTAX	DisplayString (SIZE (0..40))
	ACCESS	read-only
	STATUS	mandatory
	DESCRIPTION
	    "A DisplayString Object containing the second dial string
	    administered for the managed node."
	::= { g3clientEntry 14 }

    g3clientProductID	OBJECT-TYPE
	SYNTAX	DisplayString (SIZE (0..11))
	ACCESS	read-only
	STATUS	mandatory
	DESCRIPTION
	    "A DisplayString Object containing the product ID of the
	    managed node."
	::= { g3clientEntry 15 }

    g3clientTableIndex		OBJECT-TYPE
	SYNTAX	INTEGER
	ACCESS	not-accessible
	STATUS	mandatory
	DESCRIPTION
	    "An INTEGER object containing an index numbering the G3 client
	    entry."
	::= { g3clientEntry 16 }


    -- the g3agent group

    g3agentSubmapType	OBJECT-TYPE
        SYNTAX    DisplayString (SIZE (0..3))
        ACCESS    read-only
        STATUS    mandatory
        DESCRIPTION
            "A DisplayString object containing a value that indicates the 
	    default type of submap used in administering managed node
	    locations ('generic', 'usa', or 'custom')."
        ::= { g3agent 1 }

    g3agentState		OBJECT-TYPE
        SYNTAX    DisplayString (SIZE (0..3))
        ACCESS    read-only
        STATUS    mandatory
        DESCRIPTION
            "A DisplayString object containing a value that indicates the 
	    default state used in administering managed node locations if 
	    the g3agentSubmapType field is set to 'usa'."
        ::= { g3agent 2 }

    g3agentSubmapName	OBJECT-TYPE
        SYNTAX    DisplayString (SIZE (0..40))
        ACCESS    read-only
        STATUS    mandatory
        DESCRIPTION
            "A DisplayString Object that contains the default Submap Name 
	    used in administering managed node locations if the 
	    g3agentSubmapType field is set to 'custom'."
        ::= { g3agent 3 }

    g3agentRelease	OBJECT-TYPE
        SYNTAX    DisplayString (SIZE (0..11))
        ACCESS    read-only
        STATUS    mandatory
        DESCRIPTION
            "A DisplayString object containing the release of the Proxy
	    Agent."
        ::= { g3agent 4 }

    g3agentDomainName	OBJECT-TYPE
        SYNTAX    DisplayString (SIZE (0..256))
        ACCESS    read-only
        STATUS    mandatory
        DESCRIPTION
            "A DisplayString object containing the Domain Name of the Proxy
	    Agent."
        ::= { g3agent 5 }

    g3agentSnmpPolling	OBJECT-TYPE
        SYNTAX    INTEGER
		  {
			on(1),		-- definity snmp polling active
			off(2)		-- definity snmp polling inactive
		  }
        ACCESS    read-only
        STATUS    mandatory
        DESCRIPTION
            "This field identifies whether or not the Proxy Agent is 
	    configured to connect to and poll G3, ECS, and MCU node types
	    for data. The value of this field is determined at installation
	    time or set by services personnel in the field. If this field 
	    is on, by default the g3agentSnmpTraps field is also turned on. 
	    If it is turned off, g3agentSnmpTraps can either be turned on 
	    or off."
        ::= { g3agent 6 }

    g3agentSnmpTraps	OBJECT-TYPE
        SYNTAX    INTEGER
		  {
			on(1),		-- definity snmp traps active
			off(2)		-- definity snmp traps inactive
		  }
        ACCESS    read-only
        STATUS    mandatory
        DESCRIPTION
            "This field identifies whether or not the Agent is 
	    configured to provide SNMP traps to the NMS."
        ::= { g3agent 7 }

    g3agentSnmpSet	OBJECT-TYPE
        SYNTAX    INTEGER
		  {
			on(1),		-- definity snmp sets active
			off(2)		-- definity snmp sets inactive
		  }
        ACCESS    read-only
        STATUS    mandatory
        DESCRIPTION
            "This field identifies whether or not the Proxy Agent is 
	    configured to provide the customer with limited ability to
	    perform some maintenance commands on G3, ECS, and MCU node
	    types. The value of this field is determined at installation 
	    time or set by services personnel in the field. Since the
	    Proxy Agent does not currently support a secure version of
	    SNMP, this field should only be turned on if security is not
	    an issue."
        ::= { g3agent 8 }

    g3agentActiveName	OBJECT-TYPE
        SYNTAX    DisplayString (SIZE (0..30))
        ACCESS    read-only
        STATUS    mandatory
        DESCRIPTION
            "A DisplayString object containing the name of the aliased 
	    active server."
        ::= { g3agent 9 }

    g3agentActiveIP	OBJECT-TYPE
        SYNTAX    DisplayString (SIZE (0..40))
        ACCESS    read-only
        STATUS    mandatory
        DESCRIPTION
            "A DisplayString object containing the IP address of the
	    aliased active server."
        ::= { g3agent 10 }

    g3agentServer1Name	OBJECT-TYPE
        SYNTAX    DisplayString (SIZE (0..30))
        ACCESS    read-only
        STATUS    mandatory
        DESCRIPTION
            "A DisplayString object containing the name of server 1."
        ::= { g3agent 11 }

    g3agentServer1IP	OBJECT-TYPE
        SYNTAX    DisplayString (SIZE (0..40))
        ACCESS    read-only
        STATUS    mandatory
        DESCRIPTION
            "A DisplayString object containing the IP address of server 1."
        ::= { g3agent 12 }

    g3agentServer1State	OBJECT-TYPE
        SYNTAX    INTEGER
		  {
			active(1),		-- server currently active
			standby(2),		-- server currently standby
			dormant(3),		-- server not configured
			busyout(4)		-- server busied out
		  }
        ACCESS    read-only
        STATUS    mandatory
        DESCRIPTION
            "This field identifies whether server 1 is currently active
	    or on standby."
        ::= { g3agent 13 }

    g3agentServer2Name	OBJECT-TYPE
        SYNTAX    DisplayString (SIZE (0..30))
        ACCESS    read-only
        STATUS    mandatory
        DESCRIPTION
            "A DisplayString object containing the name of server 2."
        ::= { g3agent 14 }

    g3agentServer2IP	OBJECT-TYPE
        SYNTAX    DisplayString (SIZE (0..40))
        ACCESS    read-only
        STATUS    mandatory
        DESCRIPTION
            "A DisplayString object containing the IP address of server 2."
        ::= { g3agent 15 }

    g3agentServer2State	OBJECT-TYPE
        SYNTAX    INTEGER
		  {
			active(1),		-- server currently active
			standby(2),		-- server currently standby
			dormant(3),		-- server not configured
			busyout(4)		-- server busied out
		  }
        ACCESS    read-only
        STATUS    mandatory
        DESCRIPTION
            "This field identifies whether server 2 is currently active
	    or on standby."
        ::= { g3agent 16 }

    g3agentCLANIP	OBJECT-TYPE
        SYNTAX    DisplayString (SIZE (0..40))
        ACCESS    read-only
        STATUS    mandatory
        DESCRIPTION
            "A DisplayString object containing the registration IP address
	    for the LSP or ESS or blank (dependent on the values set in the
	    g3agentLspConfig and g3agentEssConfig variables)."
        ::= { g3agent 17 }

    g3agentPrim1IP	OBJECT-TYPE
        SYNTAX    DisplayString (SIZE (0..40))
        ACCESS    read-only
        STATUS    mandatory
        DESCRIPTION
            "A DisplayString object containing the file synchronization
	    address for Server A of the LSP or ESS or blank (dependent
	    on the values set in the g3agentLspConfig and g3agentEssConfig
	    variables)."
        ::= { g3agent 18 }

    g3agentPrim2IP	OBJECT-TYPE
        SYNTAX    DisplayString (SIZE (0..40))
        ACCESS    read-only
        STATUS    mandatory
        DESCRIPTION
            "A DisplayString object containing the file synchronization
	    address for Server B of the LSP or ESS or blank (dependent
	    on the values set in the g3agentLspConfig and g3agentEssConfig
	    variables)."
        ::= { g3agent 19 }

    g3agentServerType	OBJECT-TYPE
        SYNTAX    DisplayString (SIZE (0..20))
        ACCESS    read-only
        STATUS    mandatory
        DESCRIPTION
            "A DisplayString object containing the hardware server type."
        ::= { g3agent 20 }

    g3agentOfferType	OBJECT-TYPE
        SYNTAX    DisplayString (SIZE (0..20))
        ACCESS    read-only
        STATUS    mandatory
        DESCRIPTION
            "A DisplayString object containing the software offer type."
        ::= { g3agent 21 }

    g3agentLspConfig	OBJECT-TYPE
        SYNTAX    DisplayString (SIZE (0..20))
        ACCESS    read-only
        STATUS    mandatory
        DESCRIPTION
            "A DisplayString object indicating whether the switch is
	    configured as an LSP (possible values are 'lsp8700',
	    'lsp8300', 'icc', and 'unset')."
        ::= { g3agent 22 }

    g3agentEssConfig	OBJECT-TYPE
        SYNTAX    DisplayString (SIZE (0..20))
        ACCESS    read-only
        STATUS    mandatory
        DESCRIPTION
            "A DisplayString object indicating whether the switch is
	    configured as an ESS (possible values are 'ess8700',
	    'ess8500', 'main', and 'unset')."
        ::= { g3agent 23 }

    g3agentPrim3IP	OBJECT-TYPE
        SYNTAX    DisplayString (SIZE (0..40))
        ACCESS    read-only
        STATUS    mandatory
        DESCRIPTION
            "A DisplayString object containing the file synchronization
	    address for the alternate Server A of the LSP or ESS or 
	    blank (dependent on the values set in the g3agentLspConfig and 
	    g3agentEssConfig variables)."
        ::= { g3agent 24 }

    g3agentPrim4IP	OBJECT-TYPE
        SYNTAX    DisplayString (SIZE (0..40))
        ACCESS    read-only
        STATUS    mandatory
        DESCRIPTION
            "A DisplayString object containing the file synchronization
	    address for the alternate Server B of the LSP or ESS or 
	    blank (dependent on the values set in the g3agentLspConfig 
	    and g3agentEssConfig variables)."
        ::= { g3agent 25 }

    g3agentStdbyRefresh	OBJECT-TYPE
	SYNTAX	INTEGER
		{
			yes(1),		-- Standby Server Refreshed
			no(2)		-- Standby Server not Refreshed
		}
	ACCESS	read-only
	STATUS	mandatory
	DESCRIPTION
		"A DisplayString object containing the information whether 
		the Standby Server is Refreshed or not and is it ready to
		go for an interchange."
	::= { g3agent 26 }
    -- the g3trap group

    g3trapDestination		OBJECT-TYPE
	SYNTAX	DisplayString (SIZE (0..256))
	ACCESS	read-write
	STATUS	mandatory
	DESCRIPTION
	    "A DisplayString Object containing the trap destination 
	    IP address."
	::= { g3trap 1 }

    g3trapFilterNumber		OBJECT-TYPE
	SYNTAX	INTEGER
	ACCESS	read-write
	STATUS	mandatory
	DESCRIPTION
	    "An INTEGER object containing the filter number for the
	    specified trap destination IP address (1-500)."
	::= { g3trap 2 }

    g3trapApplicationID		OBJECT-TYPE
	SYNTAX	INTEGER
		{
			fpm(1),			-- Fault and Performance Manager
			cm-web(2),		-- CM Maintenance Web Interface
			avaya-3(3),		-- Avaya Reserved ID
			avaya-4(4),		-- Avaya Reserved ID
			avaya-5(5),		-- Avaya Reserved ID
			avaya-6(6),		-- Avaya Reserved ID
			avaya-7(7),		-- Avaya Reserved ID
			avaya-8(8),		-- Avaya Reserved ID
			avaya-9(9),		-- Avaya Reserved ID
			avaya-10(10),		-- Avaya Reserved ID
			avaya-11(11),		-- Avaya Reserved ID
			avaya-12(12),		-- Avaya Reserved ID
			avaya-13(13),		-- Avaya Reserved ID
			avaya-14(14),		-- Avaya Reserved ID
			avaya-15(15),		-- Avaya Reserved ID
			avaya-16(16),		-- Avaya Reserved ID
			avaya-17(17),		-- Avaya Reserved ID
			avaya-18(18),		-- Avaya Reserved ID
			avaya-19(19),		-- Avaya Reserved ID
			avaya-20(20),		-- Avaya Reserved ID
			avaya-21(21),		-- Avaya Reserved ID
			avaya-22(22),		-- Avaya Reserved ID
			avaya-23(23),		-- Avaya Reserved ID
			avaya-24(24),		-- Avaya Reserved ID
			avaya-25(25),		-- Avaya Reserved ID
			avaya-26(26),		-- Avaya Reserved ID
			avaya-27(27),		-- Avaya Reserved ID
			avaya-28(28),		-- Avaya Reserved ID
			avaya-29(29),		-- Avaya Reserved ID
			avaya-30(30),		-- Avaya Reserved ID
			avaya-31(31),		-- Avaya Reserved ID
			avaya-32(32),		-- Avaya Reserved ID
			avaya-33(33),		-- Avaya Reserved ID
			avaya-34(34),		-- Avaya Reserved ID
			avaya-35(35),		-- Avaya Reserved ID
			avaya-36(36),		-- Avaya Reserved ID
			avaya-37(37),		-- Avaya Reserved ID
			avaya-38(38),		-- Avaya Reserved ID
			avaya-39(39),		-- Avaya Reserved ID
			avaya-40(40),		-- Avaya Reserved ID
			avaya-41(41),		-- Avaya Reserved ID
			avaya-42(42),		-- Avaya Reserved ID
			avaya-43(43),		-- Avaya Reserved ID
			avaya-44(44),		-- Avaya Reserved ID
			avaya-45(45),		-- Avaya Reserved ID
			avaya-46(46),		-- Avaya Reserved ID
			avaya-47(47),		-- Avaya Reserved ID
			avaya-48(48),		-- Avaya Reserved ID
			avaya-49(49),		-- Avaya Reserved ID
			avaya-50(50),		-- Avaya Reserved ID
			customer-51(51),	-- Customer Reserved ID
			customer-52(52),	-- Customer Reserved ID
			customer-53(53),	-- Customer Reserved ID
			customer-54(54),	-- Customer Reserved ID
			customer-55(55),	-- Customer Reserved ID
			customer-56(56),	-- Customer Reserved ID
			customer-57(57),	-- Customer Reserved ID
			customer-58(58),	-- Customer Reserved ID
			customer-59(59),	-- Customer Reserved ID
			customer-60(60),	-- Customer Reserved ID
			customer-61(61),	-- Customer Reserved ID
			customer-62(62),	-- Customer Reserved ID
			customer-63(63),	-- Customer Reserved ID
			customer-64(64),	-- Customer Reserved ID
			customer-65(65),	-- Customer Reserved ID
			customer-66(66),	-- Customer Reserved ID
			customer-67(67),	-- Customer Reserved ID
			customer-68(68),	-- Customer Reserved ID
			customer-69(69),	-- Customer Reserved ID
			customer-70(70),	-- Customer Reserved ID
			customer-71(71),	-- Customer Reserved ID
			customer-72(72),	-- Customer Reserved ID
			customer-73(73),	-- Customer Reserved ID
			customer-74(74),	-- Customer Reserved ID
			customer-75(75),	-- Customer Reserved ID
			customer-76(76),	-- Customer Reserved ID
			customer-77(77),	-- Customer Reserved ID
			customer-78(78),	-- Customer Reserved ID
			customer-79(79),	-- Customer Reserved ID
			customer-80(80),	-- Customer Reserved ID
			customer-81(81),	-- Customer Reserved ID
			customer-82(82),	-- Customer Reserved ID
			customer-83(83),	-- Customer Reserved ID
			customer-84(84),	-- Customer Reserved ID
			customer-85(85),	-- Customer Reserved ID
			customer-86(86),	-- Customer Reserved ID
			customer-87(87),	-- Customer Reserved ID
			customer-88(88),	-- Customer Reserved ID
			customer-89(89),	-- Customer Reserved ID
			customer-90(90),	-- Customer Reserved ID
			customer-91(91),	-- Customer Reserved ID
			customer-92(92),	-- Customer Reserved ID
			customer-93(93),	-- Customer Reserved ID
			customer-94(94),	-- Customer Reserved ID
			customer-95(95),	-- Customer Reserved ID
			customer-96(96),	-- Customer Reserved ID
			customer-97(97),	-- Customer Reserved ID
			customer-98(98),	-- Customer Reserved ID
			customer-99(99),	-- Customer Reserved ID
			customer-100(100)	-- Customer Reserved ID
		}
	ACCESS	read-write
	STATUS	mandatory
	DESCRIPTION
	    "An INTEGER object containing an ID specifying from which
	    application the filter was administered. This field can take
	    on values of 1-100. IDs 1-50 are reserved for Avaya
	    applications. IDs 51-100 can be customer-defined to allow
	    a customer to identify the user or application that set up
	    the filter. Use of an application ID reserved for Avaya, 
	    when the filter is being administered from a non-Avaya
	    application, may cause handling of that alarm filter to 
	    operate incorrectly."
	::= { g3trap 3 }

    g3trapOperation		OBJECT-TYPE
	SYNTAX	INTEGER
		{
			add-replace(1),	-- add or replace filter
			delete(2) 	-- delete filter
		}
	ACCESS	read-write
	STATUS	mandatory
	DESCRIPTION
	    "This field indicates whether the alarm filter is 
	    to be added or deleted from the set of filters."
	::= { g3trap 4 }

    g3trapActive		OBJECT-TYPE
	SYNTAX	INTEGER
		{
			yes(1),
			no(2)
		}
	ACCESS	read-write
	STATUS	mandatory
	DESCRIPTION
	    "This field indicates whether or not active alarms
	    are to have traps generated. It is defaulted to 'no'. This field
	    only applies to CM and platform alarm filters."
	::= { g3trap 5 }

    g3trapResolved		OBJECT-TYPE
	SYNTAX	INTEGER
		{
			yes(1),
			no(2)
		}
	ACCESS	read-write
	STATUS	mandatory
	DESCRIPTION
	    "This field indicates whether or not resolved alarms
	    are to have traps generated. It is defaulted to 'no'. This field
	    only applies to CM and platform alarm filters."
	::= { g3trap 6 }

    g3trapMajor		OBJECT-TYPE
	SYNTAX	INTEGER
		{
			yes(1),
			no(2)
		}
	ACCESS	read-write
	STATUS	mandatory
	DESCRIPTION
	    "This field indicates whether or not major alarms
	    are to have traps generated. It is defaulted to 'no'. This field
	    only applies to CM and platform alarm filters."
	::= { g3trap 7 }

    g3trapMinor		OBJECT-TYPE
	SYNTAX	INTEGER
		{
			yes(1),
			no(2)
		}
	ACCESS	read-write
	STATUS	mandatory
	DESCRIPTION
	    "This field indicates whether or not minor alarms
	    are to have traps generated. It is defaulted to 'no'. This field
	    only applies to CM and platform alarm filters."
	::= { g3trap 8 }

    g3trapWarning		OBJECT-TYPE
	SYNTAX	INTEGER
		{
			yes(1),
			no(2)
		}
	ACCESS	read-write
	STATUS	mandatory
	DESCRIPTION
	    "This field indicates whether or not warning alarms
	    are to have traps generated. It is defaulted to 'no'. This field
	    only applies to CM and platform alarm filters."
	::= { g3trap 9 }

    g3trapInterval		OBJECT-TYPE
	SYNTAX	INTEGER
		{
			hour(1),
			day(2),
			week(3),
			month(4),
			all(5)
		}
	ACCESS	read-only
	STATUS	mandatory
	DESCRIPTION
	    "This field indicates the time window for which alarms
	    are to be collected. This is an old field that is now
	    obsolete."
	::= { g3trap 10 }

    g3trapFromMonth		OBJECT-TYPE
	SYNTAX	INTEGER
	ACCESS	read-only
	STATUS	mandatory
	DESCRIPTION
	    "This field indicates the month from which the alarm
	    polling is to begin (1-12). This is an old field that
	    is now obsolete."
	::= { g3trap 11 }

    g3trapFromDay		OBJECT-TYPE
	SYNTAX	INTEGER
	ACCESS	read-only
	STATUS	mandatory
	DESCRIPTION
	    "This field indicates the day of the month from which the alarm
	    polling is to begin (1-31). This is an old field that is
	    now obsolete."
	::= { g3trap 12 }

    g3trapFromHour		OBJECT-TYPE
	SYNTAX	INTEGER
	ACCESS	read-only
	STATUS	mandatory
	DESCRIPTION
	    "This field indicates the hour of the day from which the alarm
	    polling is to begin (0-23). This is an old field that is
	    now obsolete."
	::= { g3trap 13 }

    g3trapFromMinute		OBJECT-TYPE
	SYNTAX	INTEGER
	ACCESS	read-only
	STATUS	mandatory
	DESCRIPTION
	    "This field indicates the minute of the hour from which the alarm
	    polling is to begin (0-59). This is an old field that is
	    now obsolete."
	::= { g3trap 14 }

    g3trapToMonth		OBJECT-TYPE
	SYNTAX	INTEGER
	ACCESS	read-only
	STATUS	mandatory
	DESCRIPTION
	    "This field indicates the month from which the alarm
	    polling is to begin (1-12). This is an old field that is
	    now obsolete."
	::= { g3trap 15 }

    g3trapToDay		OBJECT-TYPE
	SYNTAX	INTEGER
	ACCESS	read-only
	STATUS	mandatory
	DESCRIPTION
	    "This field indicates the day of the month from which the alarm
	    polling is to begin (1-31). This is an old field that is
	    now obsolete."
	::= { g3trap 16 }

    g3trapToHour		OBJECT-TYPE
	SYNTAX	INTEGER
	ACCESS	read-only
	STATUS	mandatory
	DESCRIPTION
	    "This field indicates the hour of the day from which the alarm
	    polling is to begin (0-23). This is an old field that is
	    now obsolete."
	::= { g3trap 17 }

    g3trapToMinute		OBJECT-TYPE
	SYNTAX	INTEGER
	ACCESS	read-only
	STATUS	mandatory
	DESCRIPTION
	    "This field indicates the minute of the hour from which the alarm
	    polling is to begin (0-59). This is an old field that is
	    now obsolete."
	::= { g3trap 18 }

    g3trapMediaGateway		OBJECT-TYPE
	SYNTAX	INTEGER
	ACCESS	read-write
	STATUS	mandatory
	DESCRIPTION
	    "This field indicates the media gateway number (1-250) for
	    alarms to be trapped. This field only applies to CM alarm 
	    filters."
	::= { g3trap 19 }

    g3trapCabinet		OBJECT-TYPE
	SYNTAX	INTEGER
	ACCESS	read-write
	STATUS	mandatory
	DESCRIPTION
	    "This field indicates the cabinet number (1-64) for alarms 
	    to be trapped. This field only applies to CM alarm filters."
	::= { g3trap 20 }

    g3trapPortNetwork		OBJECT-TYPE
	SYNTAX	INTEGER
	ACCESS	read-only
	STATUS	mandatory
	DESCRIPTION
	    "This field indicates the port network number (1-64) for
	    alarms to be trapped. This field only applies
	    to CM alarm filters. It is a future place holder.
	    Currently setting of this field is not allowed."
	::= { g3trap 21 }

    g3trapBoardNumber		OBJECT-TYPE
	SYNTAX	DisplayString (SIZE (0..256))
	ACCESS	read-write
	STATUS	mandatory
	DESCRIPTION
	    "A DisplayString Object containing the board number
	    for alarms to be trapped. This field is
	    of the form cabinet(1-64):carrier(A-E):slot(0-20) or 
	    gateway(1-250):module(V1-V9). This field only applies
	    to CM alarm filters."
	::= { g3trap 22 }

    g3trapPort		OBJECT-TYPE
	SYNTAX	DisplayString (SIZE (0..256))
	ACCESS	read-write
	STATUS	mandatory
	DESCRIPTION
	    "A DisplayString Object containing the port number for 
	    alarms to be trapped. This field is of the 
	    form cabinet(1-64):carrier(A-E):slot(0-20):circuit(1-256) or 
	    gateway(1-250):module(V1-V9):circuit(1-31). This field only
	    applies to CM alarm filters."
	::= { g3trap 23 }

    g3trapCategory		OBJECT-TYPE
	SYNTAX	DisplayString (SIZE (0..256))
	ACCESS	read-write
	STATUS	mandatory
	DESCRIPTION
	    "This field contains the alarm category (if applicable).
	    This field only applies to CM alarm filters."
	::= { g3trap 24 }

    g3trapMaintenanceObject		OBJECT-TYPE
	SYNTAX	DisplayString (SIZE (0..256))
	ACCESS	read-write
	STATUS	mandatory
	DESCRIPTION
	    "This field contains the alarm maintenance object (if applicable).
	    This field only applies to CM alarm filters."
	::= { g3trap 25 }

    g3trapExtension		OBJECT-TYPE
	SYNTAX	DisplayString (SIZE (0..256))
	ACCESS	read-write
	STATUS	mandatory
	DESCRIPTION
	    "This field indicates the extension number for
	    alarms to be trapped. This field only applies
	    to CM alarm filters."
	::= { g3trap 26 }

    g3trapTrunkGroup		OBJECT-TYPE
	SYNTAX	INTEGER
	ACCESS	read-write
	STATUS	mandatory
	DESCRIPTION
	    "This field indicates the trunk group number for
	    alarms to be trapped (1-2000). This field only
	    applies to CM alarm filters."
	::= { g3trap 27 }

    g3trapTrunkMember		OBJECT-TYPE
	SYNTAX	INTEGER
	ACCESS	read-write
	STATUS	mandatory
	DESCRIPTION
	    "This field indicates the trunk member with a given trunk
	    group for alarms to be trapped (1-255). This field
	    only applies to CM alarm filters."
	::= { g3trap 28 }

    g3trapErrorCode		OBJECT-TYPE
	SYNTAX	DisplayString (SIZE (0..25))
	ACCESS	read-write
	STATUS	mandatory
	DESCRIPTION
	    "This field indicates the error code for alarms
	    to be trapped. This field only applies to CM alarm filters."
	::= { g3trap 29 }

    g3trapAlarmType		OBJECT-TYPE
	SYNTAX	DisplayString (SIZE (0..10))
	ACCESS	read-write
	STATUS	mandatory
	DESCRIPTION
	    "This field indicates the alarm type for alarms to be
	    trapped. The allowed values are 'A' for application alarms, 
	    '*' for security alarms, 'S' for system alarms, or 'M' for 
	    system management alarms. This field only applies to platform 
	    alarm filters."
	::= { g3trap 30 }

    g3trapAlarmSource		OBJECT-TYPE
	SYNTAX	DisplayString (SIZE (0..25))
	ACCESS	read-write
	STATUS	mandatory
	DESCRIPTION
	    "This field contains a string indicating the alarm source to
	    be trapped. The possible values are defined in CM alarm
	    maintenance rules. This field only applies to platform alarm 
	    filters."
	::= { g3trap 31 }

    g3trapEventID		OBJECT-TYPE
	SYNTAX	DisplayString (SIZE (0..10))
	ACCESS	read-write
	STATUS	mandatory
	DESCRIPTION
	    "This field contains an event ID associated with a specific
	    alarm source to be trapped. Possible event ID values are 
	    documented in CM maintenance documentation. This field only 
	    applies to platform alarm filters."
	::= { g3trap 32 }

    g3trapWarmRestart		OBJECT-TYPE
	SYNTAX	INTEGER
		{
			yes(1),
			no(2)
		}
	ACCESS	read-write
	STATUS	mandatory
	DESCRIPTION
	    "This field indicates whether or not WARM restarts are
	    to have traps generated. It is defaulted to 'no'. This field
	    only applies to system restart notifications."
	::= { g3trap 33 }

    g3trapCold2Restart		OBJECT-TYPE
	SYNTAX	INTEGER
		{
			yes(1),
			no(2)
		}
	ACCESS	read-write
	STATUS	mandatory
	DESCRIPTION
	    "This field indicates whether or not COLD2 restarts are
	    to have traps generated. It is defaulted to 'no'. This field
	    only applies to system restart notifications."
	::= { g3trap 34 }

    g3trapCold1Restart		OBJECT-TYPE
	SYNTAX	INTEGER
		{
			yes(1),
			no(2)
		}
	ACCESS	read-write
	STATUS	mandatory
	DESCRIPTION
	    "This field indicates whether or not COLD1 restarts are
	    to have traps generated. It is defaulted to 'no'. This field
	    only applies to system restart notifications."
	::= { g3trap 35 }

    g3trapReboot		OBJECT-TYPE
	SYNTAX	INTEGER
		{
			yes(1),
			no(2)
		}
	ACCESS	read-write
	STATUS	mandatory
	DESCRIPTION
	    "This field indicates whether or not REBOOT restarts are
	    to have traps generated. It is defaulted to 'no'. This field
	    only applies to system restart notifications."
	::= { g3trap 36 }

    g3trapXReboot		OBJECT-TYPE
	SYNTAX	INTEGER
		{
			yes(1),
			no(2)
		}
	ACCESS	read-write
	STATUS	mandatory
	DESCRIPTION
	    "This field indicates whether or not XREBOOT restarts are
	    to have traps generated. It is defaulted to 'no'. This field
	    only applies to system restart notifications."
	::= { g3trap 37 }

    g3trapHotPeiRestart		OBJECT-TYPE
	SYNTAX	INTEGER
		{
			yes(1),
			no(2)
		}
	ACCESS	read-write
	STATUS	mandatory
	DESCRIPTION
	    "This field indicates whether or not HOTPEI restarts are
	    to have traps generated. It is defaulted to 'no'. This field
	    only applies to system restart notifications."
	::= { g3trap 38 }

    g3trapInterchange		OBJECT-TYPE
	SYNTAX	DisplayString (SIZE (0..5))
	ACCESS	read-write
	STATUS	mandatory
	DESCRIPTION
	    "This field indicates whether or not only restarts involving
	    a interchange are to have traps generated. It can take on the
	    values 'y' (only restarts involving an interchange are trapped), 
	    'n' (only restarts involving no interchange are trapped), or
	    '-' (don't care - in other words restarts are trapped regardless
	    of whether an interchange occurred or not). It is defaulted
	    to '-'. This field only applies to system restart notifications."
	::= { g3trap 39 }

    g3trapCraftInitiated		OBJECT-TYPE
	SYNTAX	DisplayString (SIZE (0..5))
	ACCESS	read-write
	STATUS	mandatory
	DESCRIPTION
	    "This field indicates whether or not restarts that are craft 
	    initiated are to have traps generated. It can take on the
	    vaules 'y' (only craft initiated restarts are trapped), 'n'
	    (only restarts that are not craft initiated are trapped), or
	    '-' (don't care - in other workds restarts are trapped 
	    regardless of whether they were craft initiated or not). 
	    It is defaulted to '-'. This field only applies to system restart 
	    notifications."
	::= { g3trap 40 }

    g3trapFilterType		OBJECT-TYPE
	SYNTAX	INTEGER
		{
			cm-alarm(1),
			platform-alarm(2),
			restart-notification(3)
		}
	ACCESS	read-write
	STATUS	mandatory
	DESCRIPTION
	    "This field indicates the type of the filter. It is defaulted 
	    to a value of 'cm-alarm' if the user does not specify a filter
	    type when adding a new filter."
	::= { g3trap 41 }

    -- the g3filter group

    g3filterFilterStatus		OBJECT-TYPE
	SYNTAX	INTEGER
		{
			current(1),
			update(2),
			abort(3),
			save(4),
			clear(5),
			off(6),
			on(7)
		}
	ACCESS	read-write
	STATUS	mandatory
	DESCRIPTION
	    "This field indicates the state of alarm trap filter table. A
	    value of 'current' indicates that the set of alarm filters are
	    up-to-date and active and that no filter updates, via the g3trap
	    MIB group are currently taking place. A value of 'update' means 
	    that filter updates are taking place via SNMP sets of the 
	    g3trap MIB group variables. The rest of the values are settable 
	    by the user. When doing an SNMP set on this MIB variable the
	    g3filterApplication field must also be set to indicate what
	    application is requesting the set operation. For more details on
	    that field a full description is provided further down in the
	    MIB table. A value of 'abort' will cancelled any filter updates
	    in progress and return the filter table to its original state
	    before updates began. A value of 'save' will commit all pending
	    filter updates and the new/modified set of filters will become
	    active. A value of 'clear' will remove all active filters from
	    the filter table for the specified application ID. A value 
	    of 'off' will turn off the alarm trap handling processes, abort 
	    any filter updates in process, but will continue to store the 
	    current set of active filters. It's value will display when an 
	    SNMP get request is made if the user had previously set the 
	    filter status to that value or if alarm trap handling is on 
	    but no active filters exist.  A value of 'on' will reactivate 
	    the alarm trap handling processes using the currently stored 
	    set of active filters (by default the alarm trap handling 
	    processes turned on at agent startup if any active filters exist)."
	::= { g3filter 1 }

    g3filterTable		OBJECT-TYPE
	SYNTAX	SEQUENCE OF G3filterEntry
	ACCESS	not-accessible
	STATUS	mandatory
	DESCRIPTION
	    "A list of g3filter entries."
	::= { g3filter 2 }

    g3filterEntry		OBJECT-TYPE
	SYNTAX	G3filterEntry
	ACCESS	not-accessible
	STATUS	mandatory
	DESCRIPTION
	    "A g3filter entry containing objects of the active
	    filter information for CM alarms stored in the SNMP agent."
	INDEX	{ g3filterDestination, g3filterFilterNumber }
	::= { g3filterTable 1 }

    G3filterEntry ::= SEQUENCE {
	g3filterDestination
	    DisplayString,
	g3filterFilterNumber
	    INTEGER,
	g3filterApplicationID
	    INTEGER,
	g3filterActive
	    INTEGER,
	g3filterResolved
	    INTEGER,
	g3filterMajor
	    INTEGER,
	g3filterMinor
	    INTEGER,
	g3filterWarning
	    INTEGER,
	g3filterMediaGateway
	    INTEGER,
	g3filterCabinet
	    INTEGER,
	g3filterPortNetwork
	    INTEGER,
	g3filterBoardNumber
	    DisplayString,
	g3filterPort
	    DisplayString,
	g3filterCategory
	    DisplayString,
	g3filterMaintenanceObject
	    DisplayString,
	g3filterExtension
	    DisplayString,
	g3filterTrunkGroup
	    INTEGER,
	g3filterTrunkMember
	    INTEGER,
	g3filterErrorCode
	    DisplayString,
	g3filterTableIndex
	    INTEGER
	}

    g3filterDestination		OBJECT-TYPE
	SYNTAX	DisplayString (SIZE (0..256))
	ACCESS	read-only
	STATUS	mandatory
	DESCRIPTION
	    "A DisplayString Object containing the trap destination 
	    IP address."
	::= { g3filterEntry 1 }

    g3filterFilterNumber		OBJECT-TYPE
	SYNTAX	INTEGER
	ACCESS	read-only
	STATUS	mandatory
	DESCRIPTION
	    "An INTEGER object containing the filter number for the
	    specified trap destination IP address."
	::= { g3filterEntry 2 }

    g3filterApplicationID		OBJECT-TYPE
	SYNTAX	INTEGER
	ACCESS	read-only
	STATUS	mandatory
	DESCRIPTION
	    "An INTEGER object containing the application ID that
	    administered the alarm filter."
	::= { g3filterEntry 3 }

    g3filterActive		OBJECT-TYPE
	SYNTAX	INTEGER
		{
			yes(1),
			no(2)
		}
	ACCESS	read-only
	STATUS	mandatory
	DESCRIPTION
	    "This field indicates whether or not active alarms
	    are to have traps generated."
	::= { g3filterEntry 4 }

    g3filterResolved		OBJECT-TYPE
	SYNTAX	INTEGER
		{
			yes(1),
			no(2)
		}
	ACCESS	read-only
	STATUS	mandatory
	DESCRIPTION
	    "This field indicates whether or not resolved alarms
	    are to have traps generated."
	::= { g3filterEntry 5 }

    g3filterMajor		OBJECT-TYPE
	SYNTAX	INTEGER
		{
			yes(1),
			no(2)
		}
	ACCESS	read-only
	STATUS	mandatory
	DESCRIPTION
	    "This field indicates whether or not major alarms
	    are to have traps generated."
	::= { g3filterEntry 6 }

    g3filterMinor		OBJECT-TYPE
	SYNTAX	INTEGER
		{
			yes(1),
			no(2)
		}
	ACCESS	read-only
	STATUS	mandatory
	DESCRIPTION
	    "This field indicates whether or not minor alarms
	    are to have traps generated."
	::= { g3filterEntry 7 }

    g3filterWarning		OBJECT-TYPE
	SYNTAX	INTEGER
		{
			yes(1),
			no(2)
		}
	ACCESS	read-only
	STATUS	mandatory
	DESCRIPTION
	    "This field indicates whether or not warning alarms
	    are to have traps generated."
	::= { g3filterEntry 8 }

    g3filterMediaGateway		OBJECT-TYPE
	SYNTAX	INTEGER
	ACCESS	read-only
	STATUS	mandatory
	DESCRIPTION
	    "This field indicates the media gateway number (1-250) for
	    alarms to be trapped."
	::= { g3filterEntry 9 }

    g3filterCabinet		OBJECT-TYPE
	SYNTAX	INTEGER
	ACCESS	read-only
	STATUS	mandatory
	DESCRIPTION
	    "This field indicates the cabinet number (1-64) for
	    alarms to be trapped."
	::= { g3filterEntry 10 }

    g3filterPortNetwork		OBJECT-TYPE
	SYNTAX	INTEGER
	ACCESS	read-only
	STATUS	mandatory
	DESCRIPTION
	    "This field indicates the port network number (1-64) for
	    alarms to be trapped."
	::= { g3filterEntry 11 }

    g3filterBoardNumber		OBJECT-TYPE
	SYNTAX	DisplayString (SIZE (0..10))
	ACCESS	read-only
	STATUS	mandatory
	DESCRIPTION
	    "This field indicates the board location for alarms are to be
	    trapped."
	::= { g3filterEntry 12 }

    g3filterPort		OBJECT-TYPE
	SYNTAX	DisplayString (SIZE (0..14))
	ACCESS	read-only
	STATUS	mandatory
	DESCRIPTION
	    "This field indicates the port location for alarms are to be
	    trapped."
	::= { g3filterEntry 13 }

    g3filterCategory		OBJECT-TYPE
	SYNTAX	DisplayString (SIZE (0..20))
	ACCESS	read-only
	STATUS	mandatory
	DESCRIPTION
	    "This field indicates the alarm category for alarms are to be
	    trapped."
	::= { g3filterEntry 14 }

    g3filterMaintenanceObject		OBJECT-TYPE
	SYNTAX	DisplayString (SIZE (0..20))
	ACCESS	read-only
	STATUS	mandatory
	DESCRIPTION
	    "This field indicates the maintenance object name for
	    alarms are to be trapped."
	::= { g3filterEntry 15 }

    g3filterExtension		OBJECT-TYPE
	SYNTAX	DisplayString (SIZE (0..15))
	ACCESS	read-only
	STATUS	mandatory
	DESCRIPTION
	    "This field indicates the extension number for alarms are to be
	    trapped."
	::= { g3filterEntry 16 }

    g3filterTrunkGroup		OBJECT-TYPE
	SYNTAX	INTEGER
	ACCESS	read-only
	STATUS	mandatory
	DESCRIPTION
	    "This field indicates the trunk group number for
	    alarms are to be trapped (1-2000)."
	::= { g3filterEntry 17 }

    g3filterTrunkMember		OBJECT-TYPE
	SYNTAX	INTEGER
	ACCESS	read-only
	STATUS	mandatory
	DESCRIPTION
	    "This field indicates the trunk member with a given trunk
	    group for alarms are to be trapped (1-255)."
	::= { g3filterEntry 18 }

    g3filterErrorCode		OBJECT-TYPE
	SYNTAX	DisplayString (SIZE (0..25))
	ACCESS	read-only
	STATUS	mandatory
	DESCRIPTION
	    "This field indicates the error code for alarms are to be
	    trapped."
	::= { g3filterEntry 19 }

    g3filterTableIndex		OBJECT-TYPE
	SYNTAX	INTEGER
	ACCESS	not-accessible
	STATUS	mandatory
	DESCRIPTION
	    "An INTEGER object containing an index numbering the filter
	    entry."
	::= { g3filterEntry 20 }

    g3filterApplication		OBJECT-TYPE
	SYNTAX	INTEGER
		{
			fpm(1),			-- Fault and Performance Manager
			cm-web(2),		-- CM Maintenance Web Interface
			avaya-3(3),		-- Avaya Reserved ID
			avaya-4(4),		-- Avaya Reserved ID
			avaya-5(5),		-- Avaya Reserved ID
			avaya-6(6),		-- Avaya Reserved ID
			avaya-7(7),		-- Avaya Reserved ID
			avaya-8(8),		-- Avaya Reserved ID
			avaya-9(9),		-- Avaya Reserved ID
			avaya-10(10),		-- Avaya Reserved ID
			avaya-11(11),		-- Avaya Reserved ID
			avaya-12(12),		-- Avaya Reserved ID
			avaya-13(13),		-- Avaya Reserved ID
			avaya-14(14),		-- Avaya Reserved ID
			avaya-15(15),		-- Avaya Reserved ID
			avaya-16(16),		-- Avaya Reserved ID
			avaya-17(17),		-- Avaya Reserved ID
			avaya-18(18),		-- Avaya Reserved ID
			avaya-19(19),		-- Avaya Reserved ID
			avaya-20(20),		-- Avaya Reserved ID
			avaya-21(21),		-- Avaya Reserved ID
			avaya-22(22),		-- Avaya Reserved ID
			avaya-23(23),		-- Avaya Reserved ID
			avaya-24(24),		-- Avaya Reserved ID
			avaya-25(25),		-- Avaya Reserved ID
			avaya-26(26),		-- Avaya Reserved ID
			avaya-27(27),		-- Avaya Reserved ID
			avaya-28(28),		-- Avaya Reserved ID
			avaya-29(29),		-- Avaya Reserved ID
			avaya-30(30),		-- Avaya Reserved ID
			avaya-31(31),		-- Avaya Reserved ID
			avaya-32(32),		-- Avaya Reserved ID
			avaya-33(33),		-- Avaya Reserved ID
			avaya-34(34),		-- Avaya Reserved ID
			avaya-35(35),		-- Avaya Reserved ID
			avaya-36(36),		-- Avaya Reserved ID
			avaya-37(37),		-- Avaya Reserved ID
			avaya-38(38),		-- Avaya Reserved ID
			avaya-39(39),		-- Avaya Reserved ID
			avaya-40(40),		-- Avaya Reserved ID
			avaya-41(41),		-- Avaya Reserved ID
			avaya-42(42),		-- Avaya Reserved ID
			avaya-43(43),		-- Avaya Reserved ID
			avaya-44(44),		-- Avaya Reserved ID
			avaya-45(45),		-- Avaya Reserved ID
			avaya-46(46),		-- Avaya Reserved ID
			avaya-47(47),		-- Avaya Reserved ID
			avaya-48(48),		-- Avaya Reserved ID
			avaya-49(49),		-- Avaya Reserved ID
			avaya-50(50),		-- Avaya Reserved ID
			customer-51(51),	-- Customer Reserved ID
			customer-52(52),	-- Customer Reserved ID
			customer-53(53),	-- Customer Reserved ID
			customer-54(54),	-- Customer Reserved ID
			customer-55(55),	-- Customer Reserved ID
			customer-56(56),	-- Customer Reserved ID
			customer-57(57),	-- Customer Reserved ID
			customer-58(58),	-- Customer Reserved ID
			customer-59(59),	-- Customer Reserved ID
			customer-60(60),	-- Customer Reserved ID
			customer-61(61),	-- Customer Reserved ID
			customer-62(62),	-- Customer Reserved ID
			customer-63(63),	-- Customer Reserved ID
			customer-64(64),	-- Customer Reserved ID
			customer-65(65),	-- Customer Reserved ID
			customer-66(66),	-- Customer Reserved ID
			customer-67(67),	-- Customer Reserved ID
			customer-68(68),	-- Customer Reserved ID
			customer-69(69),	-- Customer Reserved ID
			customer-70(70),	-- Customer Reserved ID
			customer-71(71),	-- Customer Reserved ID
			customer-72(72),	-- Customer Reserved ID
			customer-73(73),	-- Customer Reserved ID
			customer-74(74),	-- Customer Reserved ID
			customer-75(75),	-- Customer Reserved ID
			customer-76(76),	-- Customer Reserved ID
			customer-77(77),	-- Customer Reserved ID
			customer-78(78),	-- Customer Reserved ID
			customer-79(79),	-- Customer Reserved ID
			customer-80(80),	-- Customer Reserved ID
			customer-81(81),	-- Customer Reserved ID
			customer-82(82),	-- Customer Reserved ID
			customer-83(83),	-- Customer Reserved ID
			customer-84(84),	-- Customer Reserved ID
			customer-85(85),	-- Customer Reserved ID
			customer-86(86),	-- Customer Reserved ID
			customer-87(87),	-- Customer Reserved ID
			customer-88(88),	-- Customer Reserved ID
			customer-89(89),	-- Customer Reserved ID
			customer-90(90),	-- Customer Reserved ID
			customer-91(91),	-- Customer Reserved ID
			customer-92(92),	-- Customer Reserved ID
			customer-93(93),	-- Customer Reserved ID
			customer-94(94),	-- Customer Reserved ID
			customer-95(95),	-- Customer Reserved ID
			customer-96(96),	-- Customer Reserved ID
			customer-97(97),	-- Customer Reserved ID
			customer-98(98),	-- Customer Reserved ID
			customer-99(99),	-- Customer Reserved ID
			customer-100(100)	-- Customer Reserved ID
		}
	ACCESS	read-write
	STATUS	mandatory
	DESCRIPTION
	    "An INTEGER object containing an ID specifying from which
	    application filtering was administered. This field can take
	    on values of 1-100. IDs 1-50 are reserved for Avaya
	    applications. IDs 51-100 can be customer-defined to allow
	    a customer to identify the user or application that set up
	    the filter. Use of an application ID reserved for Avaya, 
	    when the filter is being administered from a non-Avaya
	    application, may cause handling of that alarm filter to 
	    operate incorrectly. This field is only used in combination
	    with the g3filterFilterStatus field for setting the filter
	    status (see description of that field for more details). On 
	    an SNMP get request, the value of this field will always be 
	    reported as '0'."
	::= { g3filter 3 }

    g3filterTrapTest            OBJECT-TYPE
        SYNTAX    INTEGER
                  {
                        enable(1),    -- enable test trap generation
                        disable(2)    -- disable test trap generation
                  }
        ACCESS  read-write
        STATUS  mandatory
        DESCRIPTION
            "An INTEGER object specifying whether test trap generation is
             enabled or disabled. This field can be set to 1 to enable test
             trap generation.By default it is set to 2 disabled."
        ::= { g3filter 4 }

    -- the g3maintobj group

    g3maintobjTable		OBJECT-TYPE
	SYNTAX	SEQUENCE OF G3maintobjEntry
	ACCESS	not-accessible
	STATUS	mandatory
	DESCRIPTION
	    "A list of g3maintobj entries."
	::= { g3maintobj 1 }

    g3maintobjEntry		OBJECT-TYPE
	SYNTAX	G3maintobjEntry
	ACCESS	not-accessible
	STATUS	mandatory
	DESCRIPTION
	    "A g3maintobj entry containing a CM maintenance object string."
	INDEX	{ g3maintobjTableIndex }
	::= { g3maintobjTable 1 }

    G3maintobjEntry ::= SEQUENCE {
	g3maintobjMOname
	    DisplayString,
	g3maintobjTableIndex
	    INTEGER
	}

    g3maintobjMOname		OBJECT-TYPE
	SYNTAX	DisplayString (SIZE (0..25))
	ACCESS	read-only
	STATUS	mandatory
	DESCRIPTION
	    "A DisplayString Object containing a CM maintenance object
	    string."
	::= { g3maintobjEntry 1 }

    g3maintobjTableIndex		OBJECT-TYPE
	SYNTAX	INTEGER
	ACCESS	not-accessible
	STATUS	mandatory
	DESCRIPTION
	    "An INTEGER object containing an index numbering the maintenance
	    object entry."
	::= { g3maintobjEntry 2 }

    -- the g3category group

    g3categoryTable		OBJECT-TYPE
	SYNTAX	SEQUENCE OF G3categoryEntry
	ACCESS	not-accessible
	STATUS	mandatory
	DESCRIPTION
	    "A list of g3category entries."
	::= { g3category 1 }

    g3categoryEntry		OBJECT-TYPE
	SYNTAX	G3categoryEntry
	ACCESS	not-accessible
	STATUS	mandatory
	DESCRIPTION
	    "A g3category entry containing a CM alarm category and list of
	    maintenance objects associated with the category."
	INDEX	{ g3categoryTableIndex }
	::= { g3categoryTable 1 }

    G3categoryEntry ::= SEQUENCE {
	g3categoryCategory
	    DisplayString,
	g3categoryMOName
	    DisplayString,
	g3categoryTableIndex
	    INTEGER
	}

    g3categoryCategory		OBJECT-TYPE
	SYNTAX	DisplayString (SIZE (0..25))
	ACCESS	read-only
	STATUS	mandatory
	DESCRIPTION
	    "A DisplayString Object containing a CM alarm category
	    string."
	::= { g3categoryEntry 1 }

    g3categoryMOName		OBJECT-TYPE
	SYNTAX	DisplayString (SIZE (0..25))
	ACCESS	read-only
	STATUS	mandatory
	DESCRIPTION
	    "A DisplayString Object containing a CM maintenance object
	    name."
	::= { g3categoryEntry 2 }

    g3categoryTableIndex		OBJECT-TYPE
	SYNTAX	INTEGER
	ACCESS	not-accessible
	STATUS	mandatory
	DESCRIPTION
	    "An INTEGER object containing an index numbering the category
	    entry."
	::= { g3categoryEntry 3 }

    -- the g3platsrc group

    g3platsrcTable		OBJECT-TYPE
	SYNTAX	SEQUENCE OF G3platsrcEntry
	ACCESS	not-accessible
	STATUS	mandatory
	DESCRIPTION
	    "A list of g3platsrc entries."
	::= { g3platsrc 1 }

    g3platsrcEntry		OBJECT-TYPE
	SYNTAX	G3platsrcEntry
	ACCESS	not-accessible
	STATUS	mandatory
	DESCRIPTION
	    "A g3platsrc entry containing a platform alarm source."
	INDEX	{ g3platsrcTableIndex }
	::= { g3platsrcTable 1 }

    G3platsrcEntry ::= SEQUENCE {
	g3platsrcSource
	    DisplayString,
	g3platsrcTableIndex
	    INTEGER
	}

    g3platsrcSource		OBJECT-TYPE
	SYNTAX	DisplayString (SIZE (0..25))
	ACCESS	read-only
	STATUS	mandatory
	DESCRIPTION
	    "A DisplayString Object containing a platform alarm source
	    string."
	::= { g3platsrcEntry 1 }

    g3platsrcTableIndex		OBJECT-TYPE
	SYNTAX	INTEGER
	ACCESS	not-accessible
	STATUS	mandatory
	DESCRIPTION
	    "An INTEGER object containing an index numbering the alarm source
	    entry."
	::= { g3platsrcEntry 2 }

    -- the g3platfilt group

    g3platfiltTable		OBJECT-TYPE
	SYNTAX	SEQUENCE OF G3platfiltEntry
	ACCESS	not-accessible
	STATUS	mandatory
	DESCRIPTION
	    "A list of g3platfilt entries."
	::= { g3platfilt 1 }

    g3platfiltEntry		OBJECT-TYPE
	SYNTAX	G3platfiltEntry
	ACCESS	not-accessible
	STATUS	mandatory
	DESCRIPTION
	    "A g3platfilt entry containing objects of the active
	    filter information for platform alarms stored in the SNMP agent."
	INDEX	{ g3platfiltDestination, g3platfiltFilterNumber }
	::= { g3platfiltTable 1 }

    G3platfiltEntry ::= SEQUENCE {
	g3platfiltDestination
	    DisplayString,
	g3platfiltFilterNumber
	    INTEGER,
	g3platfiltApplicationID
	    INTEGER,
	g3platfiltActive
	    INTEGER,
	g3platfiltResolved
	    INTEGER,
	g3platfiltMajor
	    INTEGER,
	g3platfiltMinor
	    INTEGER,
	g3platfiltWarning
	    INTEGER,
	g3platfiltAlarmType
	    DisplayString,
	g3platfiltAlarmSource
	    DisplayString,
	g3platfiltEventID
	    DisplayString,
	g3platfiltTableIndex
	    INTEGER
	}

    g3platfiltDestination		OBJECT-TYPE
	SYNTAX	DisplayString (SIZE (0..256))
	ACCESS	read-only
	STATUS	mandatory
	DESCRIPTION
	    "A DisplayString Object containing the trap destination 
	    IP address."
	::= { g3platfiltEntry 1 }

    g3platfiltFilterNumber		OBJECT-TYPE
	SYNTAX	INTEGER
	ACCESS	read-only
	STATUS	mandatory
	DESCRIPTION
	    "An INTEGER object containing the platfilt number for the
	    specified trap destination IP address."
	::= { g3platfiltEntry 2 }

    g3platfiltApplicationID		OBJECT-TYPE
	SYNTAX	INTEGER
	ACCESS	read-only
	STATUS	mandatory
	DESCRIPTION
	    "An INTEGER object containing the application ID that
	    administered the alarm filter."
	::= { g3platfiltEntry 3 }

    g3platfiltActive		OBJECT-TYPE
	SYNTAX	INTEGER
		{
			yes(1),
			no(2)
		}
	ACCESS	read-only
	STATUS	mandatory
	DESCRIPTION
	    "This field indicates whether or not active alarms
	    are to have traps generated."
	::= { g3platfiltEntry 4 }

    g3platfiltResolved		OBJECT-TYPE
	SYNTAX	INTEGER
		{
			yes(1),
			no(2)
		}
	ACCESS	read-only
	STATUS	mandatory
	DESCRIPTION
	    "This field indicates whether or not resolved alarms
	    are to have traps generated."
	::= { g3platfiltEntry 5 }

    g3platfiltMajor		OBJECT-TYPE
	SYNTAX	INTEGER
		{
			yes(1),
			no(2)
		}
	ACCESS	read-only
	STATUS	mandatory
	DESCRIPTION
	    "This field indicates whether or not major alarms
	    are to have traps generated."
	::= { g3platfiltEntry 6 }

    g3platfiltMinor		OBJECT-TYPE
	SYNTAX	INTEGER
		{
			yes(1),
			no(2)
		}
	ACCESS	read-only
	STATUS	mandatory
	DESCRIPTION
	    "This field indicates whether or not minor alarms
	    are to have traps generated."
	::= { g3platfiltEntry 7 }

    g3platfiltWarning		OBJECT-TYPE
	SYNTAX	INTEGER
		{
			yes(1),
			no(2)
		}
	ACCESS	read-only
	STATUS	mandatory
	DESCRIPTION
	    "This field indicates whether or not warning alarms
	    are to have traps generated."
	::= { g3platfiltEntry 8 }

    g3platfiltAlarmType		OBJECT-TYPE
	SYNTAX	DisplayString (SIZE (0..10))
	ACCESS	read-only
	STATUS	mandatory
	DESCRIPTION
	    "This field indicates the alarm type for alarms to be
	    trapped. The allowed values are 'A' for application alarms, 
	    '*' for security alarms, 'S' for system alarms, or 'M' for 
	    system management alarms."
	::= { g3platfiltEntry 9 }

    g3platfiltAlarmSource		OBJECT-TYPE
	SYNTAX	DisplayString (SIZE (0..25))
	ACCESS	read-only
	STATUS	mandatory
	DESCRIPTION
	    "This field contains a string indicating the alarm source to
	    be trapped. The possible values are defined in CM alarm
	    maintenance rules."
	::= { g3platfiltEntry 10 }

    g3platfiltEventID		OBJECT-TYPE
	SYNTAX	DisplayString (SIZE (0..10))
	ACCESS	read-only
	STATUS	mandatory
	DESCRIPTION
	    "This field contains an event ID associated with a specific
	    alarm source to be trapped. Possible event ID values are 
	    documented in CM maintenance documentation."
	::= { g3platfiltEntry 11 }

    g3platfiltTableIndex		OBJECT-TYPE
	SYNTAX	INTEGER
	ACCESS	not-accessible
	STATUS	mandatory
	DESCRIPTION
	    "An INTEGER object containing an index numbering the filter
	    entry."
	::= { g3platfiltEntry 12 }

    -- the g3rstfilt group

    g3rstfiltTable		OBJECT-TYPE
	SYNTAX	SEQUENCE OF G3rstfiltEntry
	ACCESS	not-accessible
	STATUS	mandatory
	DESCRIPTION
	    "A list of g3rstfilt entries."
	::= { g3rstfilt 1 }

    g3rstfiltEntry		OBJECT-TYPE
	SYNTAX	G3rstfiltEntry
	ACCESS	not-accessible
	STATUS	mandatory
	DESCRIPTION
	    "A g3rstfilt entry containing objects of the active
	    filter information for system restart notifications stored 
	    in the SNMP agent."
	INDEX	{ g3rstfiltDestination, g3rstfiltFilterNumber }
	::= { g3rstfiltTable 1 }

    G3rstfiltEntry ::= SEQUENCE {
	g3rstfiltDestination
	    DisplayString,
	g3rstfiltFilterNumber
	    INTEGER,
	g3rstfiltApplicationID
	    INTEGER,
	g3rstfiltWarmRestart
	    INTEGER,
	g3rstfiltCold2Restart
	    INTEGER,
	g3rstfiltCold1Restart
	    INTEGER,
	g3rstfiltReboot
	    INTEGER,
	g3rstfiltXReboot
	    INTEGER,
	g3rstfiltHotPeiRestart
	    INTEGER,
	g3rstfiltInterchange
	    DisplayString,
	g3rstfiltCraftInitiated
	    DisplayString,
	g3rstfiltTableIndex
	    INTEGER
	}

    g3rstfiltDestination		OBJECT-TYPE
	SYNTAX	DisplayString (SIZE (0..256))
	ACCESS	read-only
	STATUS	mandatory
	DESCRIPTION
	    "A DisplayString Object containing the trap destination 
	    IP address."
	::= { g3rstfiltEntry 1 }

    g3rstfiltFilterNumber		OBJECT-TYPE
	SYNTAX	INTEGER
	ACCESS	read-only
	STATUS	mandatory
	DESCRIPTION
	    "An INTEGER object containing the rstfilt number for the
	    specified trap destination IP address."
	::= { g3rstfiltEntry 2 }

    g3rstfiltApplicationID		OBJECT-TYPE
	SYNTAX	INTEGER
	ACCESS	read-only
	STATUS	mandatory
	DESCRIPTION
	    "An INTEGER object containing the application ID that
	    administered the alarm filter."
	::= { g3rstfiltEntry 3 }

    g3rstfiltWarmRestart		OBJECT-TYPE
	SYNTAX	INTEGER
		{
			yes(1),
			no(2)
		}
	ACCESS	read-only
	STATUS	mandatory
	DESCRIPTION
	    "This field indicates whether or not WARM restarts are
	    to have traps generated."
	::= { g3rstfiltEntry 4 }

    g3rstfiltCold2Restart		OBJECT-TYPE
	SYNTAX	INTEGER
		{
			yes(1),
			no(2)
		}
	ACCESS	read-only
	STATUS	mandatory
	DESCRIPTION
	    "This field indicates whether or not COLD2 restarts are
	    to have traps generated."
	::= { g3rstfiltEntry 5 }

    g3rstfiltCold1Restart		OBJECT-TYPE
	SYNTAX	INTEGER
		{
			yes(1),
			no(2)
		}
	ACCESS	read-only
	STATUS	mandatory
	DESCRIPTION
	    "This field indicates whether or not COLD1 restarts are
	    to have traps generated."
	::= { g3rstfiltEntry 6 }

    g3rstfiltReboot		OBJECT-TYPE
	SYNTAX	INTEGER
		{
			yes(1),
			no(2)
		}
	ACCESS	read-only
	STATUS	mandatory
	DESCRIPTION
	    "This field indicates whether or not REBOOT restarts are
	    to have traps generated."
	::= { g3rstfiltEntry 7 }

    g3rstfiltXReboot		OBJECT-TYPE
	SYNTAX	INTEGER
		{
			yes(1),
			no(2)
		}
	ACCESS	read-only
	STATUS	mandatory
	DESCRIPTION
	    "This field indicates whether or not XREBOOT restarts are
	    to have traps generated."
	::= { g3rstfiltEntry 8 }

    g3rstfiltHotPeiRestart		OBJECT-TYPE
	SYNTAX	INTEGER
		{
			yes(1),
			no(2)
		}
	ACCESS	read-only
	STATUS	mandatory
	DESCRIPTION
	    "This field indicates whether or not HOTPEI restarts are
	    to have traps generated."
	::= { g3rstfiltEntry 9 }

    g3rstfiltInterchange		OBJECT-TYPE
	SYNTAX	DisplayString (SIZE (0..5))
	ACCESS	read-only
	STATUS	mandatory
	DESCRIPTION
	    "This field indicates whether or not restarts involving
	    a interchange are to have traps generated. A value of 'y'
	    indicates that only restarts involving an interchange are trapped.
	    A value of 'n' indicates that only restarts not involving
	    an interchange are trapped. A value of '-' indicates that a 
	    trap is generated whether an interchange occurred or not."
	::= { g3rstfiltEntry 10 }

    g3rstfiltCraftInitiated		OBJECT-TYPE
	SYNTAX	DisplayString (SIZE (0..5))
	ACCESS	read-only
	STATUS	mandatory
	DESCRIPTION
	    "This field indicates whether or restarts that are craft
	    initiated are to have traps generated. A value of 'y'
	    indicates that a trap would be generated only if the restart
	    was craft initiated. A value of 'n' indicates that a trap
	    would be generated only if the restart was not craft initiated.
	    A value of '-' indicates that a trap is generated whether
	    the restart was craft initiated or not."
	::= { g3rstfiltEntry 11 }

    g3rstfiltTableIndex		OBJECT-TYPE
	SYNTAX	INTEGER
	ACCESS	not-accessible
	STATUS	mandatory
	DESCRIPTION
	    "An INTEGER object containing an index numbering the filter
	    entry."
	::= { g3rstfiltEntry 12 }
END

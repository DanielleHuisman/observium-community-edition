-----------------------------------------------------------------------
--                            CVS HEADER                              
-----------------------------------------------------------------------
 
-----------------------------------------------------------------------
-- $RCSfile: gen.mib,v $
-----------------------------------------------------------------------
-- $Revision: 1.1 $
-----------------------------------------------------------------------
-- $Date: 2005/03/03 12:50:56 $ GMT
-----------------------------------------------------------------------
-- $Author: llevinsk $
-----------------------------------------------------------------------
-- $Source: /home/ccg/CCGcvsroot/ccg/mib/prv/src/gen.mib,v $
-----------------------------------------------------------------------
-- $Log: gen.mib,v $
-- Revision 1.1  2005/03/03 12:50:56  llevinsk
-- Unified Gateways Enviroment
--
-- Revision 1.1  2003/12/29 11:22:58  ysabbah
-- Initial revision taken from G350 R2
--
-- Revision 1.2  2003/11/06 06:50:39  iahiraz
-- merge R2 changes into CCG environment
--
-- Revision 1.1  2003/02/16 16:33:08  grub
-- move mibs definitions to plat
--
-- Revision 1.1  2002/11/12 15:47:00  oavitzur
-- *** empty log message ***
--
-- Revision 1.1  2001/08/27 13:17:36  dbeygelm
-- Init version for P330WAN.
--
-- Revision 1.1  2001/08/13 20:59:18  llevinsk
-- First version support full CRP/LB/L2/smartGeneral/System Mibs definition
--
-- Revision 1.2  2001/04/13 11:58:34  nhanigal
-- New gen.mib supporting the new P333R-LB OID
--
-- Revision 1.1  1999/08/12 13:31:43  llevinsk
-- Add mng and rmng support
--
--  Revision 10.3  1998/03/01  12:07:22  crp
--  Logical Change crp_2_0_2 (10.2) :
-- 
-- Revision 1.3  1997/10/05 15:01:24  dzebaida
-- Initial Revision
--
-----------------------------------------------------------------------
--

--==========================================================
--
-- MIB      : Generic                  Avaya Communication
--
-- Version  : 9.0.0                          1 April. 2001
--
--==========================================================
--
-- Copyright 1999, 2000, 2001 Avaya  Ltd.
-- All Rights Reserved.
--
-- Reproduction of this document is authorized on condition
-- that the foregoing copyright notice is included.
--
-- This Avaya SNMP Management Information Base 
-- Specification embodies Avaya confidential and
-- proprietary intellectual property.  Lucent Technologies retains all
-- title and ownership in the Specification, including any revisions
--
-- It is Avaya intent to encourage the widespread use of this
-- Specification in connection with the management of Avaya
-- products.
--
-- Avaya grants vendors, end-users, and other interested parties
-- a non-exclusive license to use this Specification in connection
-- with the management of Avaya products.
--
-- This Specification is supplied "as is," and Avaya makes
-- no warranty, either express or implied, as to the use,
-- operation, condition, or performance of the Specification.
--
--==========================================================
--
-- RCS
--
-- Version 9.0.0
-- 1 April 2001
-- 1. Add cajunP333RLBOID, sysOID for P333R-LB - Yigal N.
--
-- Version 8.9.9
-- 14 Apr. 2000
-- 1. Add cajunP130OID and cajunP360OID, sysOIDs for P130 and P360 respectively - Dan R.
--
-- Version 8.9.8
-- 20 Feb. 2000
-- 1. Add new sub-tree (36) under lennet tree, for policy mib - Yigal N.
--
-- Version 8.9.7 
-- 11 Jan. 2000
-- 1. Add sysOID for ATM uplink modules (Piccolo) - Yaron N.
-- 2. Change the name of P333TR to P333R - Yigal N.
--
-- Version 8.9.6
-- 7 June 1999
-- 1. Add cajunP122OID for cajunP122 standalone module - Ran I.
--
-- Version 8.9.5
-- 11 Mar. 1999
-- 1. Add cajunP330OID for P330 stacking family - Ygdal N.
-- 2. Add cajunP333TROID for Multi Layer module in P330 stacking family - Yigal N.
--
-- Version 8.9.4
-- 4 Jan. 1999
-- 1. Change cajunP210OID to cajunP120OID for LanOptics module - Ygdal N.
-- 2. Occupy new subtree 81.35 for CajunP120 - Ygdal N.
--
-- Version 8.9.3
-- 12 Dec. 1998
-- 1. Change name of lLET36-01BoxOID to lLET36-01-02BoxOID - Dan R.
--
-- Version 8.9.2
-- 3 Nov. 1998
-- 1. Add new sysObjectId (visage26PlusOID) for - Yechial C.
-- 2. Change the name of Meritage to M770 - Gidi N.
--
-- Version 8.9.1
-- 7 Oct. 1998
-- 1. Add new sysObjectId (cajunP210OID) for stand alone module - Ygdal N.
-- 2. Change the name of m3ls to mmls.
--
-- Version 8.9.0
-- 12 Apr. 1998
-- 1. Add new sysObjectId (meritageAtmOID) for meritage ATM switch - Gidi N.
-- 
-- Version 8.8.0
-- 24 Feb. 1998
-- 1. Add new sysObjectId for LBT155+ product - Dan R.
--
-- Version 8.7.0
-- 07 Jan. 1998
-- 1. Add new sysObjectId for Visage26 standalone (NetWiz product) - Zion S.
-- 2. Delete third group of SysObjectId related to lfe-1008 (Unused) - Yigal N.
-- 
-- Version 8.6.0
-- 28 Dec. 1997
-- 1. Add new sysObjectId for Meritage3LS its name is m3lsOID - Yigal N.
-- 
-- Version 8.5.1
-- 12 Aug. 1997
-- 1. Change title of this file.
-- 2. Version numbering was changed according to version numbering of madge products.
-- 3. Addition of two groups: crp(31) & maritage(32)
--
-- Version 8.5.0
-- 12 June 1997
-- 1. Add OIDs for Meritage family lntLetMeritageBoxOID(lBoxOID 14) and
-- lntMeritageBoxOID (lBoxOID 15 )
--
-- Version 8.0
-- Revision A. -   1. All madge OIDs included in this file (include smart devices)
-- 15-Nov-1996   2. Delete LRE, Multi switch and lannet legacy OIDs from the list
-- Revision B. -   1. Syntax error
-- 19-Nov-1996
-- Revision C. -   1. Rename sysOID of lsar to lsa2.
-- 19-Nov-1996
--
--========================================================

GEN-MIB DEFINITIONS ::= BEGIN

IMPORTS
      enterprises    FROM RFC1155-SMI;

lannet  OBJECT IDENTIFIER ::= { enterprises 81 }
madge  OBJECT IDENTIFIER ::= { enterprises 494 }

-- Obsolete Groups

-- lntStandard	OBJECT IDENTIFIER ::= { lannet 1 }    standard lannet tree
-- lntSpecific	OBJECT IDENTIFIER ::= { lannet 2 }    Specific LANNET tree
-- trSpecific	OBJECT IDENTIFIER ::= { lannet 3 }     Specific Token Ring  Tree
-- srlSpecific	OBJECT IDENTIFIER ::= { lannet 4 }    Specific serial tree
-- ltSpecific	OBJECT IDENTIFIER ::= { lannet 5 }    Specific Local Talk tree
-- lclSpecific	OBJECT IDENTIFIER ::= { lannet 6 }    Specific Clock Modules tree

-- Used Groups

-- chassis	OBJECT IDENTIFIER ::= { lannet 7 }  chassis group (config.mib file)
-- genGroup	OBJECT IDENTIFIER ::= { lannet 8 }  gen group (config.mib file)
-- genPort	OBJECT IDENTIFIER ::= { lannet 9 }  gen port group (config.mib file)
-- genIntPort	OBJECT IDENTIFIER ::= { lannet 10 }  gen internal port for all modules 
--                                                                                      (config.mib file)
-- softRedundancy OBJECT IDENTIFIER ::= { lannet 11 }  software redundancy group
--                                                     for software redundancy application (moduls.mib file)
-- eth		OBJECT IDENTIFIER ::= { lannet 12 }  eth 10/100 modules & NMA
--                                                                                      (moduls.mib file)
-- tok		OBJECT IDENTIFIER ::= { lannet 13 }  Tr group for tr modules
--                                                                                       (moduls.mib file)
-- ts		OBJECT IDENTIFIER ::= { lannet 14 }  Terminal server group
--                                                                                      (moduls.mib file)
-- ltalk		OBJECT IDENTIFIER ::= { lannet 15 }  Local Talk group (moduls.mib file)
-- cl		OBJECT IDENTIFIER ::= { lannet 16 }  Clock group (moduls.mib file)
-- lntOID	OBJECT IDENTIFIER ::= { lannet 17 }  Included in this file.
-- lntSecurity	OBJECT IDENTIFIER ::= { lannet 18 }  security group
-- lntLanSwitch	OBJECT IDENTIFIER ::= { lannet 19 }  switch group modules, NMA, VNS
--                                                                                       (applic.mib file)
-- deviceMgr	OBJECT IDENTIFIER ::= { lannet 20 }  device manager group
--							(Internal used)
-- bRouter	OBJECT IDENTIFIER ::= { lannet 21 }  bridges/routers group
--							(moduls.mib file)
-- probe		OBJECT IDENTIFIER ::= { lannet 22 }
-- lntTopology	OBJECT IDENTIFIER ::= { lannet 23 }  Terrain application (applic.mib file)
-- riscAgtTok	OBJECT IDENTIFIER ::= { lannet 24 }   based on Risc TR modules group
-- lntFddiGroup	OBJECT IDENTIFIER ::= { lannet 25 }   fddi modules, LSF100
--							(moduls.mib file)
-- atmEdge	OBJECT IDENTIFIER ::= { lannet 26 }  atm modules, LSA (atmedg.mib file)
-- smartDevices	OBJECT IDENTIFIER ::= { lannet 27 }  smart devices (smartd.mib file)
-- switchChip	OBJECT IDENTIFIER ::= { lannet 28 }  visage modules, visage NMA
--                                                                                      (xswtch.mib file)
-- cti		OBJECT IDENTIFIER ::= { lannet 29 }  lbt155 module (atmedg.mib file)
-- smon		OBJECT IDENTIFIER ::= { lannet 30 }  smon application (applic.mib file)
-- crp		OBJECT IDENTIFIER ::= { lannet 31 }  Routing application (croute.mib file)
-- meritage	OBJECT IDENTIFIER ::= { lannet 32 }  meritage family (mritag.mib file)
-- atmSwch 	OBJECT IDENTIFIER ::= { lannet 33 }  atm switch mib (atmswc.mib file)
-- prLane 	OBJECT IDENTIFIER ::= { lannet 34 }  propriety lane mib (prlane.mib file)
-- cajunP120	OBJECT IDENTIFIER ::= { lannet 35 }  CajunP120 subtree.
-- policy		OBJECT IDENTIFIER ::= { lannet 36 }  policy mib (policy.mib file)

lntOID		OBJECT IDENTIFIER ::= { lannet 17 } -- MADGE ESD OIDs group
deviceMgr	OBJECT IDENTIFIER ::= { lannet 20 } -- Device manager group (Internal used)
probe		OBJECT IDENTIFIER ::= { lannet 22 } -- Internal used


lBoxOID  OBJECT IDENTIFIER  ::= { lntOID 1 }
      
-- Implementation of this group is mandatory for all  Hub Agents
-- It defines OIDs which allow box identification.

lUnknownBoxOID	OBJECT IDENTIFIER ::= { lBoxOID 1 }
lLET18BoxOID		OBJECT IDENTIFIER ::= { lBoxOID 2 }
lLET3BoxOID		OBJECT IDENTIFIER ::= { lBoxOID 3 }
lLET36BoxOID		OBJECT IDENTIFIER ::= { lBoxOID 4 }
lLET18EBoxOID		OBJECT IDENTIFIER ::= { lBoxOID 5 }
lLERT40BoxOID	OBJECT IDENTIFIER ::= { lBoxOID 6 }
lLET10BoxOID		OBJECT IDENTIFIER ::= { lBoxOID 7 }
lFDX100BoxOID	OBJECT IDENTIFIER ::= { lBoxOID 8 }
lSTACKBoxOID		OBJECT IDENTIFIER ::= { lBoxOID 9 }
lLET20BoxOID		OBJECT IDENTIFIER ::= { lBoxOID 10 }
lLET36-01-02BoxOID	OBJECT IDENTIFIER ::= { lBoxOID 11 }
visageBoxOID		OBJECT IDENTIFIER ::= { lBoxOID 12 }
visage16155BoxOID	OBJECT IDENTIFIER ::= { lBoxOID 13 }
letM770BoxOID		OBJECT IDENTIFIER ::= { lBoxOID 14 }
m770BoxOID		OBJECT IDENTIFIER ::= { lBoxOID 15 }
m770AtmOID		OBJECT IDENTIFIER ::= { lBoxOID 16 }
cajunP330OID		OBJECT IDENTIFIER ::= { lBoxOID 17 } -- CajunP330 Stack family
cajunP130OID		OBJECT IDENTIFIER ::= { lBoxOID 18 } -- CajunP130  
cajunP360OID		OBJECT IDENTIFIER ::= { lBoxOID 19 } -- CajunP360 Stack family
					     
smartDevicesOID  OBJECT IDENTIFIER      ::= { lntOID 2 }

-- Implementation of this group is mandatory for all
-- Smart Devices Agents
-- It defines OIDs which allow box identification.

unknownDeviceOID	OBJECT IDENTIFIER ::= { smartDevicesOID  1 }
lsaOID		OBJECT IDENTIFIER ::= { smartDevicesOID  2 }
iasOID		OBJECT IDENTIFIER ::= { smartDevicesOID  3 }  -- integrated atm switch
collage530OID	OBJECT IDENTIFIER ::= { smartDevicesOID  4 }
eaxOID		OBJECT IDENTIFIER ::= { smartDevicesOID  5 }  -- Lea for Fore
lsfOID		OBJECT IDENTIFIER ::= { smartDevicesOID  6 }
lsa2OID		OBJECT IDENTIFIER ::= { smartDevicesOID  7 }
mmlsOID		OBJECT IDENTIFIER ::= { smartDevicesOID  8 }  -- Meritage MLS
visage26OID		OBJECT IDENTIFIER ::= { smartDevicesOID  9 }  -- Visage26 SA
lbt155plusOID	OBJECT IDENTIFIER ::= { smartDevicesOID  10 } -- LBT155+
cajunP120OID	OBJECT IDENTIFIER ::= { smartDevicesOID  11 } -- CajunP120 SA
visage26PlusOID	OBJECT IDENTIFIER ::= { smartDevicesOID  12 } -- Visage26Plus
cajunP333ROID	OBJECT IDENTIFIER ::= { smartDevicesOID  13 } -- CajunP333R
cajunP122OID	OBJECT IDENTIFIER ::= { smartDevicesOID  14 } -- CajunP122 SA
cajunP330AtmOID	OBJECT IDENTIFIER ::= { smartDevicesOID  15 } -- CajunP330 ATM Uplink 
cajunP333RLBOID	OBJECT IDENTIFIER ::= { smartDevicesOID  16 } -- CajunP333R-LB

END

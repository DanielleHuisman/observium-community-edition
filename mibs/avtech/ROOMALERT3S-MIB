--
--defines ROOMALERT3S-MIB for SNMP agent extension of Room Alert 3S
--Contents: Global Registration Module
--  Room Alert OIDs - Enterprise 20916
--Version: 1.0.0
--Date: 16 June 2021
--Developed By: AVTECH Software, Inc.

--
--Copyright (c) 2021 AVTECH Software, Inc.
--

ROOMALERT3S-MIB DEFINITIONS ::= BEGIN


IMPORTS
    enterprises
        FROM RFC1155-SMI
    OBJECT-TYPE
        FROM RFC-1212;


avtech OBJECT IDENTIFIER ::= { enterprises 20916 }
products OBJECT IDENTIFIER ::= { avtech 1 }
roomalert3S OBJECT IDENTIFIER ::= { products 13 }
sensors OBJECT IDENTIFIER ::= { roomalert3S 1 }
internal OBJECT IDENTIFIER ::= { sensors 1 }
digital OBJECT IDENTIFIER ::= { sensors 2 }
switch OBJECT IDENTIFIER ::= { sensors 3 }

temperature OBJECT IDENTIFIER ::= { internal 1 }

digital-sen1 OBJECT IDENTIFIER ::= { digital 1 }

traps OBJECT IDENTIFIER ::= { roomalert3S 2 }
externalrelays OBJECT IDENTIFIER ::= { roomalert3S 3 }
externalrelay1 OBJECT IDENTIFIER ::= { externalrelays 1 }

-- Room Alert 3S MIB
-- Parameters

internal-tempf OBJECT-TYPE
 SYNTAX INTEGER(0..65535)
 ACCESS read-only
 STATUS mandatory
 DESCRIPTION "The internal temperature reading in Fahrenheit."
::= { temperature 1 }

internal-tempc OBJECT-TYPE
 SYNTAX INTEGER(0..65535)
 ACCESS read-only
 STATUS mandatory
 DESCRIPTION "The internal temperature reading in Celsius."
::= { temperature 2 }

digital-sen1-1 OBJECT-TYPE
 SYNTAX INTEGER(0..65535)
 ACCESS read-only
 STATUS mandatory
 DESCRIPTION "If this sensor is a Temperature, Temp/Humidity, Temp/Analog, Temp/Active Power, or Digital Extreme Temperature sensor, this value represents the current temperature in Celsius."
::= { digital-sen1 1 }

digital-sen1-2 OBJECT-TYPE
 SYNTAX INTEGER(0..65535)
 ACCESS read-only
 STATUS mandatory
 DESCRIPTION "If this sensor is a Temperature, Temp/Humidity, Temp/Analog, Temp/Active Power, or Digital Extreme Temperature sensor, this value represents the current temperature in Fahrenheit."
::= { digital-sen1 2 }

digital-sen1-3 OBJECT-TYPE
 SYNTAX INTEGER(0..65535)
 ACCESS read-only
 STATUS mandatory
 DESCRIPTION "If this sensor is a Temp/Humidity sensor, this value represents the current relative humidity in % Relative Humidity. If this sensor is a Temp/Analog sensor, this value represents the current Voltage reading. If this is a Temp/Active Power sensor, this value represents the current power state (1=Power Detected, 0=No Power Detected). If this is a Digital Extreme Temperature sensor, this value represents the current temperature from the thermocouple in Celsius."
::= { digital-sen1 3 }

digital-sen1-4 OBJECT-TYPE
 SYNTAX INTEGER(0..65535)
 ACCESS read-only
 STATUS mandatory
 DESCRIPTION "If this sensor is a Temp/Humidity sensor, this value represents the current heat index in Fahrenheit. If this sensor is a Temp/Analog sensor, this value represents the current custom reading. If this is a Digital Extreme Temperature sensor, this value represents the current temperature from the thermocouple in Fahrenheit."
::= { digital-sen1 4 }

digital-sen1-5 OBJECT-TYPE
 SYNTAX INTEGER(0..65535)
 ACCESS read-only
 STATUS mandatory
 DESCRIPTION "If this sensor is a Temp/Humidity sensor, this value represents the current heat index in Celsius. If this is a Digital Extreme Temperature Sensor, this value is a fault code. 0 = no fault."
::= { digital-sen1 5 }


digital-sen1-6 OBJECT-TYPE
 SYNTAX INTEGER(0..65535)
 ACCESS read-only
 STATUS mandatory
 DESCRIPTION "If this sensor is a Temp/Humidity sensor, this value represents the current dew point in Celsius."
::= { digital-sen1 6 }

digital-sen1-7 OBJECT-TYPE
 SYNTAX INTEGER(0..65535)
 ACCESS read-only
 STATUS mandatory
 DESCRIPTION "If this sensor is a Temp/Humidity sensor, this value represents the current dew point in Fahrenheit."
::= { digital-sen1 7 }

switch-sen1 OBJECT-TYPE
 SYNTAX INTEGER(0..1)
 ACCESS read-only
 STATUS mandatory
 DESCRIPTION "The reading for switch sensor 1 (0 = OPEN, 1 = CLOSED)."
::= { switch 1 }

alarmmessage OBJECT-TYPE
 SYNTAX OCTET STRING
 ACCESS read-only
 STATUS mandatory
 DESCRIPTION "Last Alarm Message"
::= { traps 1 }


-- externalrelay1

externalrelay1-element-one OBJECT-TYPE
 SYNTAX INTEGER(0..1)
 ACCESS read-write
 STATUS mandatory
 DESCRIPTION "The status of the first element on external relay 1."
::= { externalrelay1 1 }

externalrelay1-element-two OBJECT-TYPE
 SYNTAX INTEGER(0..1)
 ACCESS read-write
 STATUS mandatory
 DESCRIPTION "The status of the second element on external relay 1."
::= { externalrelay1 2 }

externalrelay1-element-three OBJECT-TYPE
 SYNTAX INTEGER(0..1)
 ACCESS read-write
 STATUS mandatory
 DESCRIPTION "The status of the third element on external relay 1."
::= { externalrelay1 3 }

externalrelay1-element-four OBJECT-TYPE
 SYNTAX INTEGER(0..1)
 ACCESS read-write
 STATUS mandatory
 DESCRIPTION "The status of the fourth element on external relay 1."
::= { externalrelay1 4 }

externalrelay1-element-five OBJECT-TYPE
 SYNTAX INTEGER(0..1)
 ACCESS read-write
 STATUS mandatory
 DESCRIPTION "The status of the fifth element on external relay 1."
::= { externalrelay1 5 }

externalrelay1-element-six OBJECT-TYPE
 SYNTAX INTEGER(0..1)
 ACCESS read-write
 STATUS mandatory
 DESCRIPTION "The status of the sixth element on external relay 1."
::= { externalrelay1 6 }

externalrelay1-element-seven OBJECT-TYPE
 SYNTAX INTEGER(0..1)
 ACCESS read-write
 STATUS mandatory
 DESCRIPTION "The status of the seventh element on external relay 1."
::= { externalrelay1 7 }

externalrelay1-element-eight OBJECT-TYPE
 SYNTAX INTEGER(0..1)
 ACCESS read-write
 STATUS mandatory
 DESCRIPTION "The status of the eighth element on external relay 1"
::= { externalrelay1 8 }

END

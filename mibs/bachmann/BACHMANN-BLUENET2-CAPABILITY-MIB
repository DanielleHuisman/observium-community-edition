-- ********************************************************************
-- Bachmann GmbH, Stuttgart
-- BACHMANN-BLUENET2-MIB Version 1.x
--
-- Management Information Base for SNMP Network Management
--
-- Copyright 2013-2015 Bachmann GmbH.
-- All Rights Reserved.
--
-- ********************************************************************
-- File   : $RCSfile: BACHMANN-BLUENET2-CAPABILITY-MIB.txt,v $
-- Rev.   : $Revision: 1.3 $
-- Date   : $Date: 2015/09/22 16:45:34 $
-- Author : $Author: fis $
-- Id     : $Id: BACHMANN-BLUENET2-CAPABILITY-MIB.txt,v 1.3 2015/09/22 16:45:34 fis Exp $
-- ********************************************************************

BACHMANN-BLUENET2-CAPABILITY-MIB DEFINITIONS ::= BEGIN

        IMPORTS
                                AGENT-CAPABILITIES
        FROM                SNMPv2-CONF
                                MODULE-IDENTITY
        FROM                SNMPv2-SMI
                                icmpGroup,
                                ipGroup,
                                ipv4GeneralGroup
        FROM                IP-MIB
                                tcpBaseGroup,
                                tcpGroup
        FROM                TCP-MIB
                                udpBaseGroup,
                                udpGroup
        FROM                UDP-MIB
                                blueNet2Mib
        FROM                BACHMANN-BLUENET2-MIB;


blueNet2Capabilities        MODULE-IDENTITY
        LAST-UPDATED        "201506010000Z"
        ORGANIZATION        "Bachmann GmbH"
        CONTACT-INFO        "www.bachmann.com

                            Bachmann GmbH
                            Ernsthaldenstrasse 33
                            D-70565 Stuttgart
                            Germany, Europe

                            Tel. +49 711 86602-0
                            Fax  +49 711 86602-34
                            info@bachmann.com"
        DESCRIPTION         "Private agent capabilitiy MIB of BlueNet2 PDU SNMP agent."
        REVISION            "201506010000Z"
        DESCRIPTION         "Added next version blueNet2CapsV10100."
        REVISION            "201502010000Z"
        DESCRIPTION         "The initial version."
        ::=                 { blueNet2Mib       4 }

blueNet2CapsV10000          AGENT-CAPABILITIES
        PRODUCT-RELEASE     "V2.2.0"
        STATUS              current
        DESCRIPTION         "Bachmann GmbH : BlueNet2 PDU built-in capabilities."

        SUPPORTS            BACHMANN-BLUENET2-MIB
        INCLUDES            {
                                blueNet2CircuitGroup,
                                blueNet2ConfigurationGroup,
                                blueNet2DeviceGroup,
                                blueNet2IdentificationGroup,
                                blueNet2InformationGroup,
                                blueNet2ModbusGroup,
                                blueNet2NotificationGroup,
                                blueNet2NtpGroup,
                                blueNet2PhaseGroup,
                                blueNet2RcmGroup,
                                blueNet2SensorGroup,
                                blueNet2SmtpGroup,
                                blueNet2SnmpGroup,
                                blueNet2SocketGroupGroup,
                                blueNet2SyslogGroup,
                                blueNet2TrapGroup,
                                blueNet2VariableGroup,
                                blueNet2MPGroup,
                                blueNet2SpdGroup
                            }

        VARIATION           blueNet2ConfigurationGroup
        ACCESS              read-only
        DESCRIPTION         "implemented read only."

        VARIATION           blueNet2ModbusGroup
        ACCESS              read-only
        DESCRIPTION         "implemented read only."

        VARIATION           blueNet2NtpGroup
        ACCESS              read-only
        DESCRIPTION         "implemented read only."

        VARIATION           blueNet2SmtpGroup
        ACCESS              read-only
        DESCRIPTION         "implemented read only."

        VARIATION           blueNet2SnmpGroup
        ACCESS              read-only
        DESCRIPTION         "implemented read only."

        VARIATION           blueNet2SyslogGroup
        ACCESS              read-only
        DESCRIPTION         "implemented read only."

        SUPPORTS            ENTITY-MIB
        INCLUDES            {
                                entityGeneralGroup,
                                entityLogical2Group,
                                entityLogicalGroup,
                                entityMappingGroup,
                                entityNotificationsGroup,
                                entityPhysical2Group,
                                entityPhysical3Group,
                                entityPhysicalGroup
                            }

        VARIATION           entPhysicalSerialNum
        ACCESS              read-only
        DESCRIPTION         "implemented read only."

        VARIATION           entPhysicalUris
        ACCESS              read-only
        DESCRIPTION         "implemented read only."

        SUPPORTS            ENTITY-SENSOR-MIB
        INCLUDES            {
                                entitySensorValueGroup
                            }

        SUPPORTS            ENTITY-STATE-MIB
        INCLUDES            {
                                entStateGroup,
                                entStateNotificationsGroup
                            }

        SUPPORTS            HOST-RESOURCES-MIB
        INCLUDES            {
                                hrDeviceGroup,
                                hrSWRunGroup,
                                hrSWRunPerfGroup,
                                hrStorageGroup,
                                hrSystemGroup
                            }

        SUPPORTS            IF-MIB
        INCLUDES            {
                                ifCounterDiscontinuityGroup,
                                ifFixedLengthGroup,
                                ifGeneralGroup,
                                ifGeneralInformationGroup,
                                ifHCFixedLengthGroup,
                                ifHCPacketGroup,
                                ifOldObjectsGroup,
                                ifPacketGroup,
                                ifVHCPacketGroup
                            }

        SUPPORTS            IP-FORWARD-MIB
        INCLUDES            {
                                inetForwardCidrRouteGroup,
                                ipForwardCidrRouteGroup
                            }

        SUPPORTS            IP-MIB
        INCLUDES            {
                                icmpStatsGroup,
                                ipAddressGroup,
                                ipAddressPrefixGroup,
                                ipDefaultRouterGroup,
                                ipIfStatsGroup,
                                ipIfStatsHCOctetGroup,
                                ipIfStatsHCPacketGroup,
                                ipLastChangeGroup,
                                ipNetToPhysicalGroup,
                                ipSystemStatsGroup,
                                ipSystemStatsHCOctetGroup,
                                ipSystemStatsHCPacketGroup,
                                ipv4SystemStatsGroup,
                                ipv4SystemStatsHCPacketGroup,
                                ipv6GeneralGroup2,
                                ipv6ScopeGroup
                            }

        SUPPORTS            IPV6-MIB
        INCLUDES            {
                                ipv6GeneralGroup
                            }

        SUPPORTS            NOTIFICATION-LOG-MIB
        INCLUDES            {
                                notificationLogConfigGroup,
                                notificationLogStatsGroup
                            }

        SUPPORTS            PTOPO-MIB
        INCLUDES            {
                                ptopoConfigGroup,
                                ptopoDataGroup,
                                ptopoGeneralGroup
                            }

        SUPPORTS            RFC1213-MIB
        INCLUDES            {
                                icmpGroup,
                                ipGroup,
                                ipv4GeneralGroup,
                                tcpBaseGroup,
                                tcpGroup,
                                udpBaseGroup,
                                udpGroup
                            }

        SUPPORTS            SNMP-FRAMEWORK-MIB
        INCLUDES            {
                                snmpEngineGroup
                            }

        SUPPORTS            SNMP-MPD-MIB
        INCLUDES            {
                                snmpMPDGroup
                            }

        SUPPORTS            SNMP-TARGET-MIB
        INCLUDES            {
                                snmpTargetBasicGroup,
                                snmpTargetCommandResponderGroup,
                                snmpTargetResponseGroup
                            }

        SUPPORTS            SNMP-USER-BASED-SM-MIB
        INCLUDES            {
                                usmMIBBasicGroup
                            }

        SUPPORTS            SNMP-VIEW-BASED-ACM-MIB
        INCLUDES            {
                                vacmBasicGroup
                            }

        SUPPORTS            SNMPv2-MIB
        INCLUDES            {
                                snmpCommunityGroup,
                                snmpGroup,
                                snmpObsoleteGroup,
                                snmpSetGroup,
                                systemGroup
                            }

        SUPPORTS            TCP-MIB
        INCLUDES            {
                                tcpConnectionGroup,
                                tcpListenerGroup
                            }

        SUPPORTS            UDP-MIB
        INCLUDES            {
                                udpEndpointGroup
                            }

        ::=                 { blueNet2Capabilities 10000 }

blueNet2CapsV10100          AGENT-CAPABILITIES
        PRODUCT-RELEASE     "V2.2.0"
        STATUS              current
        DESCRIPTION         "Bachmann GmbH : BlueNet2 PDU built-in capabilities."

        SUPPORTS            BACHMANN-BLUENET2-MIB
        INCLUDES            {
                                blueNet2CircuitGroup,
                                blueNet2ConfigurationGroup,
                                blueNet2DeviceGroup,
                                blueNet2IdentificationGroup,
                                blueNet2InformationGroup,
                                blueNet2ModbusGroup,
                                blueNet2NotificationGroup,
                                blueNet2NtpGroup,
                                blueNet2PhaseGroup,
                                blueNet2RcmGroup,
                                blueNet2SensorGroup,
                                blueNet2SmtpGroup,
                                blueNet2SnmpGroup,
                                blueNet2SocketGroupGroup,
                                blueNet2SyslogGroup,
                                blueNet2TrapGroup,
                                blueNet2VariableGroup,
                                blueNet2MPGroup,
                                blueNet2SpdGroup
                            }

        VARIATION           blueNet2SnmpGroup
        ACCESS              read-only
        DESCRIPTION         "implemented read only."

        SUPPORTS            ENTITY-MIB
        INCLUDES            {
                                entityGeneralGroup,
                                entityLogical2Group,
                                entityLogicalGroup,
                                entityMappingGroup,
                                entityNotificationsGroup,
                                entityPhysical2Group,
                                entityPhysical3Group,
                                entityPhysicalGroup
                            }

        VARIATION           entPhysicalSerialNum
        ACCESS              read-only
        DESCRIPTION         "implemented read only."

        VARIATION           entPhysicalUris
        ACCESS              read-only
        DESCRIPTION         "implemented read only."

        SUPPORTS            ENTITY-SENSOR-MIB
        INCLUDES            {
                                entitySensorValueGroup
                            }

        SUPPORTS            ENTITY-STATE-MIB
        INCLUDES            {
                                entStateGroup,
                                entStateNotificationsGroup
                            }

        SUPPORTS            HOST-RESOURCES-MIB
        INCLUDES            {
                                hrDeviceGroup,
                                hrSWRunGroup,
                                hrSWRunPerfGroup,
                                hrStorageGroup,
                                hrSystemGroup
                            }

        SUPPORTS            IF-MIB
        INCLUDES            {
                                ifCounterDiscontinuityGroup,
                                ifFixedLengthGroup,
                                ifGeneralGroup,
                                ifGeneralInformationGroup,
                                ifHCFixedLengthGroup,
                                ifHCPacketGroup,
                                ifOldObjectsGroup,
                                ifPacketGroup,
                                ifVHCPacketGroup
                            }

        SUPPORTS            IP-FORWARD-MIB
        INCLUDES            {
                                inetForwardCidrRouteGroup,
                                ipForwardCidrRouteGroup
                            }

        SUPPORTS            IP-MIB
        INCLUDES            {
                                icmpStatsGroup,
                                ipAddressGroup,
                                ipAddressPrefixGroup,
                                ipDefaultRouterGroup,
                                ipIfStatsGroup,
                                ipIfStatsHCOctetGroup,
                                ipIfStatsHCPacketGroup,
                                ipLastChangeGroup,
                                ipNetToPhysicalGroup,
                                ipSystemStatsGroup,
                                ipSystemStatsHCOctetGroup,
                                ipSystemStatsHCPacketGroup,
                                ipv4SystemStatsGroup,
                                ipv4SystemStatsHCPacketGroup,
                                ipv6GeneralGroup2,
                                ipv6ScopeGroup
                            }

        SUPPORTS            IPV6-MIB
        INCLUDES            {
                                ipv6GeneralGroup
                            }

        SUPPORTS            NOTIFICATION-LOG-MIB
        INCLUDES            {
                                notificationLogConfigGroup,
                                notificationLogStatsGroup
                            }

        SUPPORTS            PTOPO-MIB
        INCLUDES            {
                                ptopoConfigGroup,
                                ptopoDataGroup,
                                ptopoGeneralGroup
                            }

        SUPPORTS            RFC1213-MIB
        INCLUDES            {
                                icmpGroup,
                                ipGroup,
                                ipv4GeneralGroup,
                                tcpBaseGroup,
                                tcpGroup,
                                udpBaseGroup,
                                udpGroup
                            }

        SUPPORTS            SNMP-FRAMEWORK-MIB
        INCLUDES            {
                                snmpEngineGroup
                            }

        SUPPORTS            SNMP-MPD-MIB
        INCLUDES            {
                                snmpMPDGroup
                            }

        SUPPORTS            SNMP-TARGET-MIB
        INCLUDES            {
                                snmpTargetBasicGroup,
                                snmpTargetCommandResponderGroup,
                                snmpTargetResponseGroup
                            }

        SUPPORTS            SNMP-USER-BASED-SM-MIB
        INCLUDES            {
                                usmMIBBasicGroup
                            }

        SUPPORTS            SNMP-VIEW-BASED-ACM-MIB
        INCLUDES            {
                                vacmBasicGroup
                            }

        SUPPORTS            SNMPv2-MIB
        INCLUDES            {
                                snmpCommunityGroup,
                                snmpGroup,
                                snmpObsoleteGroup,
                                snmpSetGroup,
                                systemGroup
                            }

        SUPPORTS            TCP-MIB
        INCLUDES            {
                                tcpConnectionGroup,
                                tcpListenerGroup
                            }

        SUPPORTS            UDP-MIB
        INCLUDES            {
                                udpEndpointGroup
                            }

        ::=                 { blueNet2Capabilities 10100 }
END

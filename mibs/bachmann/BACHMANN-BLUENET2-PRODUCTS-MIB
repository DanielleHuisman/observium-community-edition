-- ********************************************************************
-- Bachmann GmbH, Stuttgart
-- BACHMANN-BLUENET2-PRODUCTS-MIB Version 1.0
--
-- Management Information Base for SNMP Network Management
--
-- Copyright 2015 Bachmann GmbH.
-- All Rights Reserved.
--
-- ********************************************************************
-- File   : $RCSfile: BACHMANN-BLUENET2-PRODUCTS-MIB.txt,v $
-- Rev.   : $Revision: 1.3 $
-- Date   : $Date: 2015/06/24 17:50:54 $
-- Author : $Author: fis $
-- Id     : $Id: BACHMANN-BLUENET2-PRODUCTS-MIB.txt,v 1.3 2015/06/24 17:50:54 fis Exp $
-- ********************************************************************

BACHMANN-BLUENET2-PRODUCTS-MIB DEFINITIONS ::= BEGIN

        IMPORTS
                                MODULE-IDENTITY
        FROM                SNMPv2-SMI
                                blueNet2Mib
        FROM                BACHMANN-BLUENET2-MIB;


blueNet2Products   MODULE-IDENTITY
        LAST-UPDATED        "201503240000Z"
        ORGANIZATION        "Bachmann GmbH"
        CONTACT-INFO        "www.bachmann.com

                            Bachmann GmbH
                            Ernsthaldenstrasse 33
                            D-70565 Stuttgart
                            Germany, Europe

                            Tel. +49 711 86602-0
                            Fax  +49 711 86602-34
                            info@bachmann.com"
        DESCRIPTION         "The MIB module for representing BlueNet2 PDU SNMP agent product entities."
        REVISION            "201503240000Z"
        DESCRIPTION         "Initial Version of BlueNet2Products MIB."
--      ::=                 { iso(1) org(3) dod(6) internet(1) private(4) enterprises(1) bachmann(31770) blueNet2(2) blueNet2Products(1) }
        ::=                 { blueNet2Mib       1 }

-- ********************************************************************

--  bachmann                                        OBJECT IDENTIFIER ::= { enterprises        31770     }
--  blueNet2Mib                                     OBJECT IDENTIFIER ::= {   bachmann               2   }
--  blueNet2Products                                OBJECT IDENTIFIER ::= {     blueNet2Mib            1 }

--  used in ptopoConnDiscAlgorithm:
--  lldpMIB                                         OBJECT IDENTIFIER ::= { iso(1) std(0) iso8802(8802) ieee802dot1(1) ieee802dot1mibs(1) 2 }
--  dot1dStpDesignatedRoot                          OBJECT IDENTIFIER ::= { iso(1) org(3) dod(6) internet(1) mgmt(2) mib-2(1) dot1dBridge(17) dot1dStp(2) 5 }
--  ciscoCdpMIB                                     OBJECT IDENTIFIER ::= { enterprises cisco(9) ciscoMgmt(9) 23 }

--  used in entPhysicalVendorType:
--  arm                                             OBJECT IDENTIFIER ::= { enterprises          326     }
--  atmel                                           OBJECT IDENTIFIER ::= { enterprises          410     }
--  linux                                           OBJECT IDENTIFIER ::= { enterprises netsnmp(8072) netSnmpEnumerations(3) netSnmpAgentOIDs(2) 10 }

-- ********************************************************************

--  this values are leant on ENTITY-MIB PhysicalClass
    blueNet2ProductOther                            OBJECT IDENTIFIER ::= { blueNet2Products            1 }
    blueNet2ProductUnknown                          OBJECT IDENTIFIER ::= { blueNet2Products            2 }
    blueNet2ProductChassis                          OBJECT IDENTIFIER ::= { blueNet2Products            3 }
    blueNet2ProductBackplane                        OBJECT IDENTIFIER ::= { blueNet2Products            4 }
    blueNet2ProductContainer                        OBJECT IDENTIFIER ::= { blueNet2Products            5 }
    blueNet2ProductPowerSupply                      OBJECT IDENTIFIER ::= { blueNet2Products            6 }
    blueNet2ProductFan                              OBJECT IDENTIFIER ::= { blueNet2Products            7 }
    blueNet2ProductSensor                           OBJECT IDENTIFIER ::= { blueNet2Products            8 }
    blueNet2ProductPort                             OBJECT IDENTIFIER ::= { blueNet2Products            9 }
    blueNet2ProductModule                           OBJECT IDENTIFIER ::= { blueNet2Products           10 }
    blueNet2ProductStack                            OBJECT IDENTIFIER ::= { blueNet2Products           11 }

    blueNet2ProductCircuit                          OBJECT IDENTIFIER ::= { blueNet2Products          101 }
    blueNet2ProductPhase                            OBJECT IDENTIFIER ::= { blueNet2Products          102 }
    blueNet2ProductFuse                             OBJECT IDENTIFIER ::= { blueNet2Products          103 }
    blueNet2ProductSocket                           OBJECT IDENTIFIER ::= { blueNet2Products          104 }
    blueNet2ProductRcm                              OBJECT IDENTIFIER ::= { blueNet2Products          105 }
    blueNet2ProductSocketGroup                      OBJECT IDENTIFIER ::= { blueNet2Products          106 }
    blueNet2ProductVariable                         OBJECT IDENTIFIER ::= { blueNet2Products          107 }
    blueNet2ProductSpd                              OBJECT IDENTIFIER ::= { blueNet2Products          108 }

-- ********************************************************************
    
    blueNet2ProductChassisMonitored-1p-16A-16-4-0   OBJECT IDENTIFIER ::= { blueNet2ProductChassis    3004 }
    blueNet2ProductChassisMonitored-1p-32A-16-4-0   OBJECT IDENTIFIER ::= { blueNet2ProductChassis    3005 }
    blueNet2ProductChassisMonitored-1p-16A-16-0-4   OBJECT IDENTIFIER ::= { blueNet2ProductChassis    3006 }
    blueNet2ProductChassisMonitored-1p-32A-16-0-4   OBJECT IDENTIFIER ::= { blueNet2ProductChassis    3007 }
    blueNet2ProductChassisMonitored-3p-16A-0-6-0    OBJECT IDENTIFIER ::= { blueNet2ProductChassis    3008 }
    blueNet2ProductChassisMonitored-3p-32A-0-6-0    OBJECT IDENTIFIER ::= { blueNet2ProductChassis    3009 }
    blueNet2ProductChassisMonitored-3p-16A-18-3-0   OBJECT IDENTIFIER ::= { blueNet2ProductChassis    3010 }
    blueNet2ProductChassisMonitored-3p-16A-18-0-3   OBJECT IDENTIFIER ::= { blueNet2ProductChassis    3011 }
    blueNet2ProductChassisMonitored-3p-16A-24-6-0   OBJECT IDENTIFIER ::= { blueNet2ProductChassis    3012 }
    blueNet2ProductChassisMonitored-3p-32A-24-6-0   OBJECT IDENTIFIER ::= { blueNet2ProductChassis    3013 }
    blueNet2ProductChassisMonitored-3p-16A-24-0-6   OBJECT IDENTIFIER ::= { blueNet2ProductChassis    3014 }
    blueNet2ProductChassisMonitored-3p-32A-24-0-6   OBJECT IDENTIFIER ::= { blueNet2ProductChassis    3015 }
    blueNet2ProductChassisMonitored-3p-16A-24-6-6   OBJECT IDENTIFIER ::= { blueNet2ProductChassis    3016 }
    blueNet2ProductChassisMonitored-3p-32A-24-6-6   OBJECT IDENTIFIER ::= { blueNet2ProductChassis    3017 }
    blueNet2ProductChassisMonitored-3p-16A-36-6-0   OBJECT IDENTIFIER ::= { blueNet2ProductChassis    3018 }
    blueNet2ProductChassisMonitored-3p-32A-36-6-0   OBJECT IDENTIFIER ::= { blueNet2ProductChassis    3019 }
    blueNet2ProductChassisMonitored-3p-16A-36-0-6   OBJECT IDENTIFIER ::= { blueNet2ProductChassis    3020 }
    blueNet2ProductChassisMonitored-3p-32A-36-0-6   OBJECT IDENTIFIER ::= { blueNet2ProductChassis    3021 }
    blueNet2ProductChassisMonitored-3p-16A-18-3-0-RCM OBJECT IDENTIFIER ::= { blueNet2ProductChassis  3022 }
    blueNet2ProductChassisMonitored-3p-16A-18-0-3-RCM OBJECT IDENTIFIER ::= { blueNet2ProductChassis  3023 }
    blueNet2ProductChassisMonitored-3p-16A-24-6-0-RCM OBJECT IDENTIFIER ::= { blueNet2ProductChassis  3024 }
    blueNet2ProductChassisMonitored-3p-32A-24-6-0-RCM OBJECT IDENTIFIER ::= { blueNet2ProductChassis  3025 }
    blueNet2ProductChassisMonitored-3p-16A-36-6-0-RCM OBJECT IDENTIFIER ::= { blueNet2ProductChassis  3026 }
    blueNet2ProductChassisMonitoredUnspecified      OBJECT IDENTIFIER ::= { blueNet2ProductChassis    3499 }

    blueNet2ProductChassisMonitoredPerOutlet-1p-16A-18-4-0 OBJECT IDENTIFIER ::= { blueNet2ProductChassis   3500 }
    blueNet2ProductChassisMonitoredPerOutlet-1p-32A-16-4-0 OBJECT IDENTIFIER ::= { blueNet2ProductChassis   3501 }
    blueNet2ProductChassisMonitoredPerOutlet-1p-16A-18-0-4 OBJECT IDENTIFIER ::= { blueNet2ProductChassis   3502 }
    blueNet2ProductChassisMonitoredPerOutlet-1p-32A-16-0-4 OBJECT IDENTIFIER ::= { blueNet2ProductChassis   3503 }
    blueNet2ProductChassisMonitoredPerOutlet-3p-16A-0-6-0 OBJECT IDENTIFIER ::= { blueNet2ProductChassis    3504 }
    blueNet2ProductChassisMonitoredPerOutlet-3p-32A-0-6-0 OBJECT IDENTIFIER ::= { blueNet2ProductChassis    3505 }
    blueNet2ProductChassisMonitoredPerOutlet-3p-16A-18-3-0 OBJECT IDENTIFIER ::= { blueNet2ProductChassis   3506 }
    blueNet2ProductChassisMonitoredPerOutlet-3p-16A-18-0-3 OBJECT IDENTIFIER ::= { blueNet2ProductChassis   3507 }
    blueNet2ProductChassisMonitoredPerOutlet-3p-16A-24-6-0 OBJECT IDENTIFIER ::= { blueNet2ProductChassis   3508 }
    blueNet2ProductChassisMonitoredPerOutlet-3p-32A-24-6-0 OBJECT IDENTIFIER ::= { blueNet2ProductChassis   3509 }
    blueNet2ProductChassisMonitoredPerOutlet-3p-16A-24-0-6 OBJECT IDENTIFIER ::= { blueNet2ProductChassis   3510 }
    blueNet2ProductChassisMonitoredPerOutlet-3p-32A-24-0-6 OBJECT IDENTIFIER ::= { blueNet2ProductChassis   3511 }
    blueNet2ProductChassisMonitoredPerOutlet-3p-16A-24-6-6 OBJECT IDENTIFIER ::= { blueNet2ProductChassis   3512 }
    blueNet2ProductChassisMonitoredPerOutlet-3p-32A-24-6-6 OBJECT IDENTIFIER ::= { blueNet2ProductChassis   3513 }
    blueNet2ProductChassisMonitoredPerOutlet-3p-16A-36-6-0 OBJECT IDENTIFIER ::= { blueNet2ProductChassis   3514 }
    blueNet2ProductChassisMonitoredPerOutlet-3p-32A-36-6-0 OBJECT IDENTIFIER ::= { blueNet2ProductChassis   3515 }
    blueNet2ProductChassisMonitoredPerOutlet-3p-16A-36-0-6 OBJECT IDENTIFIER ::= { blueNet2ProductChassis   3516 }
    blueNet2ProductChassisMonitoredPerOutlet-3p-32A-36-0-6 OBJECT IDENTIFIER ::= { blueNet2ProductChassis   3517 }
    blueNet2ProductChassisMonitoredPerOutletUnspecified OBJECT IDENTIFIER ::= { blueNet2ProductChassis      3999 }

    blueNet2ProductChassisSwitched-1p-16A-8-0-0     OBJECT IDENTIFIER ::= { blueNet2ProductChassis   5000 }
    blueNet2ProductChassisSwitched-1p-16A-0-0-6     OBJECT IDENTIFIER ::= { blueNet2ProductChassis   5001 }
    blueNet2ProductChassisSwitchedUnspecified       OBJECT IDENTIFIER ::= { blueNet2ProductChassis   5499 }

    blueNet2ProductChassisManaged-1p-16A-18-4-0     OBJECT IDENTIFIER ::= { blueNet2ProductChassis   7000 }
    blueNet2ProductChassisManaged-1p-32A-16-4-0     OBJECT IDENTIFIER ::= { blueNet2ProductChassis   7001 }
    blueNet2ProductChassisManaged-1p-16A-18-0-4     OBJECT IDENTIFIER ::= { blueNet2ProductChassis   7002 }
    blueNet2ProductChassisManaged-1p-32A-16-0-4     OBJECT IDENTIFIER ::= { blueNet2ProductChassis   7003 }
    blueNet2ProductChassisManaged-3p-16A-0-6-0      OBJECT IDENTIFIER ::= { blueNet2ProductChassis   7004 }
    blueNet2ProductChassisManaged-3p-32A-0-6-0      OBJECT IDENTIFIER ::= { blueNet2ProductChassis   7005 }
    blueNet2ProductChassisManaged-3p-16A-18-3-0     OBJECT IDENTIFIER ::= { blueNet2ProductChassis   7006 }
    blueNet2ProductChassisManaged-3p-16A-18-0-3     OBJECT IDENTIFIER ::= { blueNet2ProductChassis   7007 }
    blueNet2ProductChassisManaged-3p-16A-24-6-0     OBJECT IDENTIFIER ::= { blueNet2ProductChassis   7008 }
    blueNet2ProductChassisManaged-3p-32A-24-6-0     OBJECT IDENTIFIER ::= { blueNet2ProductChassis   7009 }
    blueNet2ProductChassisManaged-3p-16A-24-0-6     OBJECT IDENTIFIER ::= { blueNet2ProductChassis   7010 }
    blueNet2ProductChassisManaged-3p-32A-24-0-6     OBJECT IDENTIFIER ::= { blueNet2ProductChassis   7011 }
    blueNet2ProductChassisManaged-3p-16A-24-6-6     OBJECT IDENTIFIER ::= { blueNet2ProductChassis   7012 }
    blueNet2ProductChassisManaged-3p-32A-24-6-6     OBJECT IDENTIFIER ::= { blueNet2ProductChassis   7013 }
    blueNet2ProductChassisManaged-3p-16A-36-6-0     OBJECT IDENTIFIER ::= { blueNet2ProductChassis   7014 }
    blueNet2ProductChassisManaged-3p-32A-36-6-0     OBJECT IDENTIFIER ::= { blueNet2ProductChassis   7015 }
    blueNet2ProductChassisManaged-3p-16A-36-0-6     OBJECT IDENTIFIER ::= { blueNet2ProductChassis   7016 }
    blueNet2ProductChassisManaged-3p-32A-36-0-6     OBJECT IDENTIFIER ::= { blueNet2ProductChassis   7017 }
    blueNet2ProductChassisManaged-3p-32A-18-6-0-RCM OBJECT IDENTIFIER ::= { blueNet2ProductChassis   7018 }
    blueNet2ProductChassisManagedUnspecified        OBJECT IDENTIFIER ::= { blueNet2ProductChassis   7499 }

    blueNet2ProductChassisManagedPerOutlet-1p-16A-18-4-0 OBJECT IDENTIFIER ::= { blueNet2ProductChassis   7500 }
    blueNet2ProductChassisManagedPerOutlet-1p-32A-16-4-0 OBJECT IDENTIFIER ::= { blueNet2ProductChassis   7501 }
    blueNet2ProductChassisManagedPerOutlet-1p-16A-18-0-4 OBJECT IDENTIFIER ::= { blueNet2ProductChassis   7502 }
    blueNet2ProductChassisManagedPerOutlet-1p-32A-16-0-4 OBJECT IDENTIFIER ::= { blueNet2ProductChassis   7503 }
    blueNet2ProductChassisManagedPerOutlet-3p-16A-0-6-0 OBJECT IDENTIFIER ::= { blueNet2ProductChassis    7504 }
    blueNet2ProductChassisManagedPerOutlet-3p-32A-0-6-0 OBJECT IDENTIFIER ::= { blueNet2ProductChassis    7505 }
    blueNet2ProductChassisManagedPerOutlet-3p-16A-18-3-0 OBJECT IDENTIFIER ::= { blueNet2ProductChassis   7506 }
    blueNet2ProductChassisManagedPerOutlet-3p-16A-18-0-3 OBJECT IDENTIFIER ::= { blueNet2ProductChassis   7507 }
    blueNet2ProductChassisManagedPerOutlet-3p-16A-24-6-0 OBJECT IDENTIFIER ::= { blueNet2ProductChassis   7508 }
    blueNet2ProductChassisManagedPerOutlet-3p-32A-24-6-0 OBJECT IDENTIFIER ::= { blueNet2ProductChassis   7509 }
    blueNet2ProductChassisManagedPerOutlet-3p-16A-24-0-6 OBJECT IDENTIFIER ::= { blueNet2ProductChassis   7510 }
    blueNet2ProductChassisManagedPerOutlet-3p-32A-24-0-6 OBJECT IDENTIFIER ::= { blueNet2ProductChassis   7511 }
    blueNet2ProductChassisManagedPerOutlet-3p-16A-24-6-6 OBJECT IDENTIFIER ::= { blueNet2ProductChassis   7512 }
    blueNet2ProductChassisManagedPerOutlet-3p-32A-24-6-6 OBJECT IDENTIFIER ::= { blueNet2ProductChassis   7513 }
    blueNet2ProductChassisManagedPerOutlet-3p-16A-36-6-0 OBJECT IDENTIFIER ::= { blueNet2ProductChassis   7514 }
    blueNet2ProductChassisManagedPerOutlet-3p-32A-36-6-0 OBJECT IDENTIFIER ::= { blueNet2ProductChassis   7515 }
    blueNet2ProductChassisManagedPerOutlet-3p-16A-36-0-6 OBJECT IDENTIFIER ::= { blueNet2ProductChassis   7516 }
    blueNet2ProductChassisManagedPerOutlet-3p-32A-36-0-6 OBJECT IDENTIFIER ::= { blueNet2ProductChassis   7517 }
    blueNet2ProductChassisManagedPerOutlet-3p-16A-24-6-0-RCM  OBJECT IDENTIFIER ::= { blueNet2ProductChassis   7521 }
    blueNet2ProductChassisManagedPerOutletUnspecified OBJECT IDENTIFIER ::= { blueNet2ProductChassis      7999 }

    blueNet2ProductChassisUnspecified               OBJECT IDENTIFIER ::= { blueNet2ProductChassis     65535 }

-- ********************************************************************

    blueNet2ProductContainerStandAlone              OBJECT IDENTIFIER ::= { blueNet2ProductContainer   1 }
    blueNet2ProductContainerStack                   OBJECT IDENTIFIER ::= { blueNet2ProductContainer   2 }
    blueNet2ProductContainerSocketGroup             OBJECT IDENTIFIER ::= { blueNet2ProductContainer   106 }
    blueNet2ProductContainerUnspecified             OBJECT IDENTIFIER ::= { blueNet2ProductContainer   65535 }

-- ********************************************************************

    blueNet2ProductPowerSupplyStandard              OBJECT IDENTIFIER ::= { blueNet2ProductPowerSupply 1 }
    blueNet2ProductPowerSupplyUnspecified           OBJECT IDENTIFIER ::= { blueNet2ProductPowerSupply 65535 }

-- ********************************************************************

--  the first values are leant on ENTITY-SENSOR-MIB EntitySensorDataType

    blueNet2ProductSensorTemperature                OBJECT IDENTIFIER ::= { blueNet2ProductSensor      1 }
    blueNet2ProductSensorTempHumidity               OBJECT IDENTIFIER ::= { blueNet2ProductSensor      2 }
    blueNet2ProductSensorGPIO                       OBJECT IDENTIFIER ::= { blueNet2ProductSensor      3 }
    blueNet2ProductSensorAccess                     OBJECT IDENTIFIER ::= { blueNet2ProductSensor      4 }
    blueNet2ProductSensorInternalGPIO               OBJECT IDENTIFIER ::= { blueNet2ProductSensor      16 }
    blueNet2ProductSensorHub                        OBJECT IDENTIFIER ::= { blueNet2ProductSensor      254 }
    blueNet2ProductSensorUndefined                  OBJECT IDENTIFIER ::= { blueNet2ProductSensor      255 }
    blueNet2ProductSensorUnspecified                OBJECT IDENTIFIER ::= { blueNet2ProductSensor      65535 }

-- ********************************************************************

    blueNet2ProductPortLoopback                     OBJECT IDENTIFIER ::= { blueNet2ProductPort        1 }
    blueNet2ProductPortEthernet                     OBJECT IDENTIFIER ::= { blueNet2ProductPort        2 }
    blueNet2ProductPortModbus                       OBJECT IDENTIFIER ::= { blueNet2ProductPort        3 }
    blueNet2ProductPortSimpleInternetTransition     OBJECT IDENTIFIER ::= { blueNet2ProductPort        4 }
    blueNet2ProductPortUSB                          OBJECT IDENTIFIER ::= { blueNet2ProductPort        5 }
    blueNet2ProductPortUnspecified                  OBJECT IDENTIFIER ::= { blueNet2ProductPort        65535 }

-- ********************************************************************

    blueNet2ProductModuleUnspecified                OBJECT IDENTIFIER ::= { blueNet2ProductModule      65535 }

-- ********************************************************************

    blueNet2ProductCircuit-1P                       OBJECT IDENTIFIER ::= { blueNet2ProductCircuit     1 }
    blueNet2ProductCircuit-3PDelta                  OBJECT IDENTIFIER ::= { blueNet2ProductCircuit     3 }
    blueNet2ProductCircuit-4PWYE                    OBJECT IDENTIFIER ::= { blueNet2ProductCircuit     4 }
    blueNet2ProductCircuit-US-1P                    OBJECT IDENTIFIER ::= { blueNet2ProductCircuit     11 }
    blueNet2ProductCircuit-US-2P                    OBJECT IDENTIFIER ::= { blueNet2ProductCircuit     12 }
    blueNet2ProductCircuit-US-3PDelta               OBJECT IDENTIFIER ::= { blueNet2ProductCircuit     13 }
    blueNet2ProductCircuit-US-4PWYE                 OBJECT IDENTIFIER ::= { blueNet2ProductCircuit     14 }
    blueNet2ProductCircuit-US-4PDelta               OBJECT IDENTIFIER ::= { blueNet2ProductCircuit     15 }
    blueNet2ProductCircuitUnspecified               OBJECT IDENTIFIER ::= { blueNet2ProductCircuit     65535 }

-- ********************************************************************

    blueNet2ProductPhase-PDU-Phase                  OBJECT IDENTIFIER ::= { blueNet2ProductPhase       1 }
    blueNet2ProductPhase-PU-Measurement-Group       OBJECT IDENTIFIER ::= { blueNet2ProductPhase       2 }
    blueNet2ProductPhase-PU-CEE17-16A-5P-400V       OBJECT IDENTIFIER ::= { blueNet2ProductPhase       3 }
    blueNet2ProductPhase-PU-CEE17-32A-5P-400V       OBJECT IDENTIFIER ::= { blueNet2ProductPhase       4 }
    blueNet2ProductPhase-PU-CEE17-63A-5P-400V       OBJECT IDENTIFIER ::= { blueNet2ProductPhase       5 }
    blueNet2ProductPhaseUnspecified                 OBJECT IDENTIFIER ::= { blueNet2ProductPhase       65535 }

-- ********************************************************************

    blueNet2ProductFuse-10B                         OBJECT IDENTIFIER ::= { blueNet2ProductFuse        1 }
    blueNet2ProductFuse-10C                         OBJECT IDENTIFIER ::= { blueNet2ProductFuse        2 }
    blueNet2ProductFuse-13B                         OBJECT IDENTIFIER ::= { blueNet2ProductFuse        10 }
    blueNet2ProductFuse-13C                         OBJECT IDENTIFIER ::= { blueNet2ProductFuse        11 }
    blueNet2ProductFuse-16B                         OBJECT IDENTIFIER ::= { blueNet2ProductFuse        20 }
    blueNet2ProductFuse-16C                         OBJECT IDENTIFIER ::= { blueNet2ProductFuse        21 }
    blueNet2ProductFuse-20B                         OBJECT IDENTIFIER ::= { blueNet2ProductFuse        30 }
    blueNet2ProductFuse-20C                         OBJECT IDENTIFIER ::= { blueNet2ProductFuse        31 }
    blueNet2ProductFuse-25B                         OBJECT IDENTIFIER ::= { blueNet2ProductFuse        40 }
    blueNet2ProductFuse-25C                         OBJECT IDENTIFIER ::= { blueNet2ProductFuse        41 }
    blueNet2ProductFuse-32B                         OBJECT IDENTIFIER ::= { blueNet2ProductFuse        50 }
    blueNet2ProductFuse-32C                         OBJECT IDENTIFIER ::= { blueNet2ProductFuse        51 }
    blueNet2ProductFuse-63B                         OBJECT IDENTIFIER ::= { blueNet2ProductFuse        60 }
    blueNet2ProductFuse-63C                         OBJECT IDENTIFIER ::= { blueNet2ProductFuse        61 }
    blueNet2ProductFuseInternal                     OBJECT IDENTIFIER ::= { blueNet2ProductFuse        254 }
    blueNet2ProductFuseUnspecified                  OBJECT IDENTIFIER ::= { blueNet2ProductFuse        65535 }

-- ********************************************************************

    blueNet2ProductSocket-C13                       OBJECT IDENTIFIER ::= { blueNet2ProductSocket      10 }
    blueNet2ProductSocket-C13LWL                    OBJECT IDENTIFIER ::= { blueNet2ProductSocket      11 }
    blueNet2ProductSocket-C19                       OBJECT IDENTIFIER ::= { blueNet2ProductSocket      20 }
    blueNet2ProductSocket-C19LWL                    OBJECT IDENTIFIER ::= { blueNet2ProductSocket      21 }
    blueNet2ProductSocket-CEE7-3                    OBJECT IDENTIFIER ::= { blueNet2ProductSocket      30 }
    blueNet2ProductSocket-CEE7-3LWL                 OBJECT IDENTIFIER ::= { blueNet2ProductSocket      31 }
    blueNet2ProductSocket-UTE                       OBJECT IDENTIFIER ::= { blueNet2ProductSocket      40 }
    blueNet2ProductSocket-UTELWL                    OBJECT IDENTIFIER ::= { blueNet2ProductSocket      41 }
    blueNet2ProductSocket-UK                        OBJECT IDENTIFIER ::= { blueNet2ProductSocket      50 }
    blueNet2ProductSocket-UKLWL                     OBJECT IDENTIFIER ::= { blueNet2ProductSocket      51 }
    blueNet2ProductSocket-NEMA15                    OBJECT IDENTIFIER ::= { blueNet2ProductSocket      60 }
    blueNet2ProductSocket-NEMA15LWL                 OBJECT IDENTIFIER ::= { blueNet2ProductSocket      61 }
    blueNet2ProductSocket-NEMAL6                    OBJECT IDENTIFIER ::= { blueNet2ProductSocket      70 }
    blueNet2ProductSocket-NEMAL6LWL                 OBJECT IDENTIFIER ::= { blueNet2ProductSocket      71 }
    blueNet2ProductSocket-PU-Phase-16A              OBJECT IDENTIFIER ::= { blueNet2ProductSocket      100 }
    blueNet2ProductSocket-PU-Phase-32A              OBJECT IDENTIFIER ::= { blueNet2ProductSocket      101 }
    blueNet2ProductSocket-PU-Phase-63A              OBJECT IDENTIFIER ::= { blueNet2ProductSocket      102 }
    blueNet2ProductSocket-PU-PHASE-CEE17-16A-3P-230V  OBJECT IDENTIFIER ::= { blueNet2ProductSocket      110 }
    blueNet2ProductSocket-PU-PHASE-CEE17-32A-3P-230V  OBJECT IDENTIFIER ::= { blueNet2ProductSocket      111 }
    blueNet2ProductSocket-PU-PHASE-CEE17-16A-5P-400V  OBJECT IDENTIFIER ::= { blueNet2ProductSocket       3 }
    blueNet2ProductSocket-PU-PHASE-CEE17-32A-5P-400V  OBJECT IDENTIFIER ::= { blueNet2ProductSocket       4 }
    blueNet2ProductSocket-PU-PHASE-CEE17-63A-5P-400V  OBJECT IDENTIFIER ::= { blueNet2ProductSocket       5 }
    blueNet2ProductSocketUnspecified                OBJECT IDENTIFIER ::= { blueNet2ProductSocket      65535 }

-- ********************************************************************

    blueNet2ProductRcm-B                            OBJECT IDENTIFIER ::= { blueNet2ProductRcm         2 }
    blueNet2ProductRcmUnspecified                   OBJECT IDENTIFIER ::= { blueNet2ProductRcm         65535 }

-- ********************************************************************

    blueNet2ProductSpdGeneric                       OBJECT IDENTIFIER ::= { blueNet2ProductSpd         1 }
    blueNet2ProductSpdUnspecified                   OBJECT IDENTIFIER ::= { blueNet2ProductSpd         65535 }

-- ********************************************************************

    blueNet2ProductVariableVoltage                  OBJECT IDENTIFIER ::= { blueNet2ProductVariable    1 }
    blueNet2ProductVariablePeakVoltage              OBJECT IDENTIFIER ::= { blueNet2ProductVariable    2 }
    blueNet2ProductVariableCurrent                  OBJECT IDENTIFIER ::= { blueNet2ProductVariable    4 }
    blueNet2ProductVariablePeakCurrent              OBJECT IDENTIFIER ::= { blueNet2ProductVariable    5 }
    blueNet2ProductVariableDifferentialCurrentAc    OBJECT IDENTIFIER ::= { blueNet2ProductVariable    7 }
    blueNet2ProductVariableDifferentialCurrentDc    OBJECT IDENTIFIER ::= { blueNet2ProductVariable    8 }
    blueNet2ProductVariableNeutralCurrent           OBJECT IDENTIFIER ::= { blueNet2ProductVariable    9 }
    blueNet2ProductVariablePhaseAngle               OBJECT IDENTIFIER ::= { blueNet2ProductVariable    16 }
    blueNet2ProductVariablePowerFactor              OBJECT IDENTIFIER ::= { blueNet2ProductVariable    17 }
    blueNet2ProductVariableApparentPower            OBJECT IDENTIFIER ::= { blueNet2ProductVariable    18 }
    blueNet2ProductVariableActivePower              OBJECT IDENTIFIER ::= { blueNet2ProductVariable    19 }
    blueNet2ProductVariablePeakActivePower          OBJECT IDENTIFIER ::= { blueNet2ProductVariable    20 }
    blueNet2ProductVariablePeakActivePowerUser      OBJECT IDENTIFIER ::= { blueNet2ProductVariable    21 }
    blueNet2ProductVariableReactivePower            OBJECT IDENTIFIER ::= { blueNet2ProductVariable    22 }
    blueNet2ProductVariableFrequency                OBJECT IDENTIFIER ::= { blueNet2ProductVariable    23 }
    blueNet2ProductVariablePeakNeutralCurrent       OBJECT IDENTIFIER ::= { blueNet2ProductVariable    24 }
    blueNet2ProductVariableApparentEnergyAccumulated OBJECT IDENTIFIER ::= { blueNet2ProductVariable   32 }
    blueNet2ProductVariableApparentEnergyDelta      OBJECT IDENTIFIER ::= { blueNet2ProductVariable    33 }
    blueNet2ProductVariableReactiveEnergyAccumulated OBJECT IDENTIFIER ::= { blueNet2ProductVariable   34 }
    blueNet2ProductVariableReactiveEnergyDelta      OBJECT IDENTIFIER ::= { blueNet2ProductVariable    35 }
    blueNet2ProductVariableActiveEnergyAccumulated  OBJECT IDENTIFIER ::= { blueNet2ProductVariable    36 }
    blueNet2ProductVariableActiveEnergyDelta        OBJECT IDENTIFIER ::= { blueNet2ProductVariable    37 }
    blueNet2ProductVariableActiveEnergyAccumulatedUser OBJECT IDENTIFIER ::= { blueNet2ProductVariable 38 }
    blueNet2ProductVariableActiveEnergyRuntime      OBJECT IDENTIFIER ::= { blueNet2ProductVariable    39 }
    blueNet2ProductVariableCustomEnergyRuntimeUser  OBJECT IDENTIFIER ::= { blueNet2ProductVariable    40 }
    blueNet2ProductVariableFuseState                OBJECT IDENTIFIER ::= { blueNet2ProductVariable    48 }
    blueNet2ProductVariableOrientation              OBJECT IDENTIFIER ::= { blueNet2ProductVariable    49 }
    blueNet2ProductVariableUsb                      OBJECT IDENTIFIER ::= { blueNet2ProductVariable    50 }
    blueNet2ProductVariableSocket                   OBJECT IDENTIFIER ::= { blueNet2ProductVariable    51 }
    blueNet2ProductVariablePduState                 OBJECT IDENTIFIER ::= { blueNet2ProductVariable    52 }
    blueNet2ProductVariableSensorState              OBJECT IDENTIFIER ::= { blueNet2ProductVariable    53 }
    blueNet2ProductVariableSensorType               OBJECT IDENTIFIER ::= { blueNet2ProductVariable    64 }
    blueNet2ProductVariableCircuitType              OBJECT IDENTIFIER ::= { blueNet2ProductVariable    65 }
    blueNet2ProductVariableFuseType                 OBJECT IDENTIFIER ::= { blueNet2ProductVariable    66 }
    blueNet2ProductVariableSocketType               OBJECT IDENTIFIER ::= { blueNet2ProductVariable    67 }
    blueNet2ProductVariableSocketColor              OBJECT IDENTIFIER ::= { blueNet2ProductVariable    68 }
    blueNet2ProductVariableTemperature              OBJECT IDENTIFIER ::= { blueNet2ProductVariable    256 }
    blueNet2ProductVariableHumidity                 OBJECT IDENTIFIER ::= { blueNet2ProductVariable    257 }
    blueNet2ProductVariableIoInputChannel1          OBJECT IDENTIFIER ::= { blueNet2ProductVariable    258 }
    blueNet2ProductVariableIoInputChannel2          OBJECT IDENTIFIER ::= { blueNet2ProductVariable    259 }
    blueNet2ProductVariableIoInputChannel3          OBJECT IDENTIFIER ::= { blueNet2ProductVariable    260 }
    blueNet2ProductVariableIoInputChannel4          OBJECT IDENTIFIER ::= { blueNet2ProductVariable    261 }
    blueNet2ProductVariableIoOutputChannel1         OBJECT IDENTIFIER ::= { blueNet2ProductVariable    262 }
    blueNet2ProductVariableIoOutputChannel2         OBJECT IDENTIFIER ::= { blueNet2ProductVariable    263 }
    blueNet2ProductVariableIoOutputChannel3         OBJECT IDENTIFIER ::= { blueNet2ProductVariable    264 }
    blueNet2ProductVariableIoOutputChannel4         OBJECT IDENTIFIER ::= { blueNet2ProductVariable    265 }
    blueNet2ProductVariableUnspecified              OBJECT IDENTIFIER ::= { blueNet2ProductVariable    65535 }

-- ********************************************************************

END

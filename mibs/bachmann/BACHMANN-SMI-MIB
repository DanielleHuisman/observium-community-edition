-- ********************************************************************
-- Bachmann GmbH, Stuttgart
-- BACHMANN-SMI Version 1.0
--
-- Management Information Base for SNMP Network Management
--
-- Copyright 2013 Bachmann GmbH.
-- All Rights Reserved.
--
-- ********************************************************************
-- File   : $RCSfile: BACHMANN-SMI.txt,v $
-- Rev.   : $Revision: 1.1.1.1 $
-- Date   : $Date: 2015/04/17 14:42:31 $
-- Author : $Author: fis $
-- Id     : $Id: BACHMANN-SMI.txt,v 1.1.1.1 2015/04/17 14:42:31 fis Exp $
-- ********************************************************************

BACHMANN-SMI-MIB DEFINITIONS ::= BEGIN

        IMPORTS
            enterprises,
            MODULE-IDENTITY
        FROM                SNMPv2-SMI;

bachmann MODULE-IDENTITY
        LAST-UPDATED        "201502010000Z"
        ORGANIZATION        "Bachmann GmbH"
        CONTACT-INFO        "www.bachmann.com
                            
                            Bachmann GmbH
                            Ernsthaldenstrasse 33
                            D-70565 Stuttgart
                            Germany, Europe
                            
                            Tel. +49 711 86602-0
                            Fax  +49 711 86602-34
                            info@bachmann.com"
        DESCRIPTION         "The Structure of Management Information Base for the enterprise Bachmann GmbH."
        REVISION            "201502010000Z"
        DESCRIPTION         "Initial version of this MIB module."
        ::=                 { enterprises       31770 }
--      ::=                 { iso(1) org(3) dod(6) internet(1) private(4) enterprises(1) bachmann(31770) }
--                            as assigned by IANA

END

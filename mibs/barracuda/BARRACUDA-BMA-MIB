--
-- BARRACUDA-BMA-MIB.txt:   Barracuda Message Archiver MIB
--
-- June 2013, David Fluck
--
-- Copyright (c) 2013 by Barracuda Networks, Inc.
-- All rights reserved.
--

BARRACUDA-BMA-MIB DEFINITIONS ::= BEGIN

IMPORTS
    MODULE-IDENTITY,
    OBJECT-TYPE,
    Gauge32,
    Integer32
        FROM SNMPv2-SMI
    DisplayString
        FROM SNMPv2-TC
    Float
        FROM NET-SNMP-TC
    barracuda
        FROM BARRACUDA-SMI;

bma MODULE-IDENTITY
    LAST-UPDATED    "201305300000Z"
    ORGANIZATION "Barracuda Networks, Inc."
    CONTACT-INFO
        "Barracuda Networks, Inc.
        3175 S. Winchester Blvd.
        Campbell, CA 95008"
    DESCRIPTION
        "Barracuda Message Archiver MIB."
::= { barracuda 6 }

-- OBJECT IDENTIFIER assignment for various groups

bmaMsgStats             OBJECT IDENTIFIER ::= { bma 5 }

bmaPerformanceStats     OBJECT IDENTIFIER ::= { bma 6 }
bmaCPUFanStats          OBJECT IDENTIFIER ::= { bmaPerformanceStats 2 }
bmaSystemTempStats      OBJECT IDENTIFIER ::= { bmaPerformanceStats 3 }
bmaCPUTempStats         OBJECT IDENTIFIER ::= { bmaPerformanceStats 4 }

bmaPolicyStats          OBJECT IDENTIFIER ::= { bma 7 }
bmaStorageStats         OBJECT IDENTIFIER ::= { bma 8 }

-- Objects maintained for backwards compatibility. Note: These descriptors
-- begin with uppercase letters and are therefore not standards-compliant.
-- They are left in for backwards compatibility.

QueueFiles OBJECT-TYPE
    SYNTAX      Gauge32
    MAX-ACCESS  read-only
    STATUS      deprecated
    DESCRIPTION
        "The number of messages in the Barracuda Message Archiver queue."
::= { bma 2 }

UnfinishedFiles OBJECT-TYPE
    SYNTAX      Gauge32
    MAX-ACCESS  read-only
    STATUS      deprecated
    DESCRIPTION
        "The number of unfinished files in the Barracuda Message Archiver queue."
::= { bma 3 }

IndexCount OBJECT-TYPE
    SYNTAX      Gauge32
    MAX-ACCESS  read-only
    STATUS      deprecated
    DESCRIPTION
        "The number of messages in the Barracuda Message Archiver index."
::= { bma 4 }

-- These are the new objects.

-- Message Statistics

inboundEmailsHour OBJECT-TYPE
    SYNTAX      Gauge32
    MAX-ACCESS  read-only
    STATUS      current
    DESCRIPTION
        "The number of inbound e-mails during the current hour."
::= { bmaMsgStats 1 }

inboundEmailsDay OBJECT-TYPE
    SYNTAX      Gauge32
    MAX-ACCESS  read-only
    STATUS      current
    DESCRIPTION
        "The number of inbound e-mails during the current calendar day (beginning at midnight)."
::= { bmaMsgStats 2 }

inboundEmailsTotal OBJECT-TYPE
    SYNTAX      Gauge32
    MAX-ACCESS  read-only
    STATUS      current
    DESCRIPTION
        "The number of inbound e-mails since installation or since the last reset of statistics."
::= { bmaMsgStats 3 }

internalEmailsHour OBJECT-TYPE
    SYNTAX      Gauge32
    MAX-ACCESS  read-only
    STATUS      current
    DESCRIPTION
        "The number of internal e-mails during the current hour."
::= { bmaMsgStats 4 }

internalEmailsDay OBJECT-TYPE
    SYNTAX      Gauge32
    MAX-ACCESS  read-only
    STATUS      current
    DESCRIPTION
        "The number of internal e-mails during the current calendar day (beginning at midnight)."
::= { bmaMsgStats 5 }

internalEmailsTotal OBJECT-TYPE
    SYNTAX      Gauge32
    MAX-ACCESS  read-only
    STATUS      current
    DESCRIPTION
        "The number of internal e-mails since installation or since the last reset of statistics."
::= { bmaMsgStats 6 }

outboundEmailsHour OBJECT-TYPE
    SYNTAX      Gauge32
    MAX-ACCESS  read-only
    STATUS      current
    DESCRIPTION
        "The number of outbound e-mails during the current hour."
::= { bmaMsgStats 7 }

outboundEmailsDay OBJECT-TYPE
    SYNTAX      Gauge32
    MAX-ACCESS  read-only
    STATUS      current
    DESCRIPTION
        "The number of outbound e-mails during the current calendar day (beginning at midnight)."
::= { bmaMsgStats 8 }

outboundEmailsTotal OBJECT-TYPE
    SYNTAX      Gauge32
    MAX-ACCESS  read-only
    STATUS      current
    DESCRIPTION
        "The number of outbound e-mails since installation or since the last reset of statistics."
::= { bmaMsgStats 9 }

appointmentsHour OBJECT-TYPE
    SYNTAX      Gauge32
    MAX-ACCESS  read-only
    STATUS      current
    DESCRIPTION
        "The number of appointments created or modified during the current hour."
::= { bmaMsgStats 10 }

appointmentsDay OBJECT-TYPE
    SYNTAX      Gauge32
    MAX-ACCESS  read-only
    STATUS      current
    DESCRIPTION
        "The number of appointments created or modified during the current calendar day (beginning at midnight)."
::= { bmaMsgStats 11 }

appointmentsTotal OBJECT-TYPE
    SYNTAX      Gauge32
    MAX-ACCESS  read-only
    STATUS      current
    DESCRIPTION
        "The number of appointments created or modified since installation or since the last reset of statistics."
::= { bmaMsgStats 12 }

contactsHour OBJECT-TYPE
    SYNTAX      Gauge32
    MAX-ACCESS  read-only
    STATUS      current
    DESCRIPTION
        "The number of contacts created or modified during the current hour."
::= { bmaMsgStats 13 }

contactsDay OBJECT-TYPE
    SYNTAX      Gauge32
    MAX-ACCESS  read-only
    STATUS      current
    DESCRIPTION
        "The number of contacts created or modified during the current calendar day (beginning at midnight)."
::= { bmaMsgStats 14 }

contactsTotal OBJECT-TYPE
    SYNTAX      Gauge32
    MAX-ACCESS  read-only
    STATUS      current
    DESCRIPTION
        "The number of contacts created or modified since installation or since the last reset of statistics."
::= { bmaMsgStats 15 }

distributionListHour OBJECT-TYPE
    SYNTAX      Gauge32
    MAX-ACCESS  read-only
    STATUS      current
    DESCRIPTION
        "The number of distribution lists created or modified during the current hour."
::= { bmaMsgStats 16 }

distributionListDay OBJECT-TYPE
    SYNTAX      Gauge32
    MAX-ACCESS  read-only
    STATUS      current
    DESCRIPTION
        "The number of distribution lists created or modified during the current calendar day (beginning at midnight)."
::= { bmaMsgStats 17 }

distributionListTotal OBJECT-TYPE
    SYNTAX      Gauge32
    MAX-ACCESS  read-only
    STATUS      current
    DESCRIPTION
        "The number of distribution lists created or modified since installation or since the last reset of statistics."
::= { bmaMsgStats 18 }

notesHour OBJECT-TYPE
    SYNTAX      Gauge32
    MAX-ACCESS  read-only
    STATUS      current
    DESCRIPTION
        "The number of notes created or modified during the current hour."
::= { bmaMsgStats 19 }

notesDay OBJECT-TYPE
    SYNTAX      Gauge32
    MAX-ACCESS  read-only
    STATUS      current
    DESCRIPTION
        "The number of notes created or modified during the current calendar day (beginning at midnight)."
::= { bmaMsgStats 20 }

notesTotal OBJECT-TYPE
    SYNTAX      Gauge32
    MAX-ACCESS  read-only
    STATUS      current
    DESCRIPTION
        "The number of notes created or modified since installation or since the last reset of statistics."
::= { bmaMsgStats 21 }

tasksHour OBJECT-TYPE
    SYNTAX      Gauge32
    MAX-ACCESS  read-only
    STATUS      current
    DESCRIPTION
        "The number of tasks created or modified during the current hour."
::= { bmaMsgStats 22 }

tasksDay OBJECT-TYPE
    SYNTAX      Gauge32
    MAX-ACCESS  read-only
    STATUS      current
    DESCRIPTION
        "The number of tasks created or modified during the current calendar day (beginning at midnight)."
::= { bmaMsgStats 23 }

tasksTotal OBJECT-TYPE
    SYNTAX      Gauge32
    MAX-ACCESS  read-only
    STATUS      current
    DESCRIPTION
        "The number of tasks created or modified since installation or since the last reset of statistics."
::= { bmaMsgStats 24 }

messagesHour OBJECT-TYPE
    SYNTAX      Gauge32
    MAX-ACCESS  read-only
    STATUS      current
    DESCRIPTION
        "The number of messages logged during the current hour."
::= { bmaMsgStats 25 }

messagesDay OBJECT-TYPE
    SYNTAX      Gauge32
    MAX-ACCESS  read-only
    STATUS      current
    DESCRIPTION
        "The number of messages logged during the current calendar day (beginning at midnight)."
::= { bmaMsgStats 26 }

messagesTotal OBJECT-TYPE
    SYNTAX      Gauge32
    MAX-ACCESS  read-only
    STATUS      current
    DESCRIPTION
        "The number of messages logged since installation or since the last reset of statistics."
::= { bmaMsgStats 27 }

otherHour OBJECT-TYPE
    SYNTAX      Gauge32
    MAX-ACCESS  read-only
    STATUS      current
    DESCRIPTION
        "The number of uncategorized messages logged during the current hour."
::= {bmaMsgStats 28 }

otherDay OBJECT-TYPE
    SYNTAX      Gauge32
    MAX-ACCESS  read-only
    STATUS      current
    DESCRIPTION
        "The number of uncategorized messages logged during the current calendar day (beginning at midnight)."
::= { bmaMsgStats 29 }

otherTotal OBJECT-TYPE
    SYNTAX      Gauge32
    MAX-ACCESS  read-only
    STATUS      current
    DESCRIPTION
        "The number of uncategorized messages logged since installation or since the last reset of statistics."
::= { bmaMsgStats 30 }

-- Performance Statistics

systemLoad OBJECT-TYPE
    SYNTAX      Gauge32 (0..100)
    UNITS       "%"
    MAX-ACCESS  read-only
    STATUS      current
    DESCRIPTION
        "The estimate of CPU and disk load on the system."
::= { bmaPerformanceStats 1 }

-- This is a separate branch to make it easy to add new CPU fan OIDs in the future.

cpu1FanSpeed OBJECT-TYPE
    SYNTAX      Gauge32
    UNITS       "RPM"
    MAX-ACCESS  read-only
    STATUS      current
    DESCRIPTION
        "CPU 1 fan speed in rotations per minute (RPM)."
::= { bmaCPUFanStats 1 }

cpu2FanSpeed OBJECT-TYPE
    SYNTAX      Gauge32
    UNITS       "RPM"
    MAX-ACCESS  read-only
    STATUS      current
    DESCRIPTION
        "CPU 2 fan speed in rotations per minute (RPM)."
::= { bmaCPUFanStats 2 }

-- This is a separate branch to make it easy to add system temperature OIDs in the future.

systemTemperature1 OBJECT-TYPE
    SYNTAX      Gauge32
    UNITS       "C"
    MAX-ACCESS  read-only
    STATUS      current
    DESCRIPTION
        "System temperature 1 in degrees Celsius."
::= { bmaSystemTempStats 1 }

cpu1Temperature OBJECT-TYPE
    SYNTAX      Gauge32
    UNITS       "C"
    MAX-ACCESS  read-only
    STATUS      current
    DESCRIPTION
        "Temperature of CPU 1 in degrees Celsius."
::= { bmaCPUTempStats 1 }

cpu2Temperature OBJECT-TYPE
    SYNTAX      Gauge32
    UNITS       "C"
    MAX-ACCESS  read-only
    STATUS      current
    DESCRIPTION
        "Temperature of CPU 2 in degrees Celsius."
::= { bmaCPUTempStats 2 }

firmwareStorage OBJECT-TYPE
    SYNTAX      Gauge32 (0..100)
    UNITS       "%"
    MAX-ACCESS  read-only
    STATUS      current
    DESCRIPTION
        "The total storage space occupied by the firmware."
::= { bmaPerformanceStats 5 }

mailLogStorage OBJECT-TYPE
    SYNTAX      Gauge32 (0..100)
    UNITS       "%"
    MAX-ACCESS  read-only
    STATUS      current
    DESCRIPTION
        "The total storage space occupied by mail and logs."
::= { bmaPerformanceStats 6 }

-- RAID stuff should go here. #####################################################################################################################

indexQueueLength OBJECT-TYPE
    SYNTAX      Gauge32
    MAX-ACCESS  read-only
    STATUS      current
    DESCRIPTION
        "The number of messages remaining in the index queue."
::= { bmaPerformanceStats 8 }

lastMessageArchived OBJECT-TYPE
    SYNTAX      DisplayString
    MAX-ACCESS  read-only
    STATUS      current
    DESCRIPTION
        "The date and time that the last message was archived (in GMT)."
::= { bmaPerformanceStats 9 }

messagesDeduplicated OBJECT-TYPE
    SYNTAX      Gauge32
    MAX-ACCESS  read-only
    STATUS      current
    DESCRIPTION
        "The number of messages that have been dedpulicated."
::= { bmaPerformanceStats 10 }

storageSaved OBJECT-TYPE
    SYNTAX      Gauge32
    UNITS       "bytes"
    MAX-ACCESS  read-only
    STATUS      current
    DESCRIPTION
        "The amount of storage saved by dedpulication (in bytes)."
::= { bmaPerformanceStats 11 }

cloudControlStatus OBJECT-TYPE
    SYNTAX      INTEGER {
                    connected(1),
                    notConnected(2),
                    notConfigured(3)
                }
    MAX-ACCESS  read-only
    STATUS      current
    DESCRIPTION
        "The status of Cloud Control."
::= { bmaPerformanceStats 12 }

-- Policy Statistics

personalInfoHour OBJECT-TYPE
    SYNTAX      Gauge32
    MAX-ACCESS  read-only
    STATUS      current
    DESCRIPTION
        "The number of messages found to contain personally identifiable information during the current hour."
::= { bmaPolicyStats 1 }

personalInfoDay OBJECT-TYPE
    SYNTAX      Gauge32
    MAX-ACCESS  read-only
    STATUS      current
    DESCRIPTION
        "The number of messages found to contain personally identifiable information during the current calendar day (beginning at midnight)."
::= { bmaPolicyStats 2 }

personalInfoTotal OBJECT-TYPE
    SYNTAX      Gauge32
    MAX-ACCESS  read-only
    STATUS      current
    DESCRIPTION
        "The number of messages found to contain personally identifiable information since installation or since the last reset of statistics."
::= { bmaPolicyStats 3 }

foulLanguageHour OBJECT-TYPE
    SYNTAX      Gauge32
    MAX-ACCESS  read-only
    STATUS      current
    DESCRIPTION
        "The number of messages found to contain foul language during the current hour."
::= { bmaPolicyStats 4 }

foulLanguageDay OBJECT-TYPE
    SYNTAX      Gauge32
    MAX-ACCESS  read-only
    STATUS      current
    DESCRIPTION
        "The number of messages found to contain foul language during the current calendar day (beginning at midnight)."
::= { bmaPolicyStats 5 }

foulLanguageTotal OBJECT-TYPE
    SYNTAX      Gauge32
    MAX-ACCESS  read-only
    STATUS      current
    DESCRIPTION
        "The number of messages found to contain foul language since installation or since the last reset of statistics."
::= { bmaPolicyStats 6 }

personalEmailHour OBJECT-TYPE
    SYNTAX      Gauge32
    MAX-ACCESS  read-only
    STATUS      current
    DESCRIPTION
        "The number of messages sent to and from non-business sites during the current hour."
::= { bmaPolicyStats 7 }

personalEmailDay OBJECT-TYPE
    SYNTAX      Gauge32
    MAX-ACCESS  read-only
    STATUS      current
    DESCRIPTION
        "The number of messages sent to and from non-business sites during the current calendar day (beginning at midnight)."
::= { bmaPolicyStats 8 }

personalEmailTotal OBJECT-TYPE
    SYNTAX      Gauge32
    MAX-ACCESS  read-only
    STATUS      current
    DESCRIPTION
        "The number of messages sent to and from non-business sites since installation or since the last reset of statistics."
::= { bmaPolicyStats 9 }

policyHour OBJECT-TYPE
    SYNTAX      Gauge32
    MAX-ACCESS  read-only
    STATUS      current
    DESCRIPTION
        "The number of messages that have triggered a policy during the current hour."
::= { bmaPolicyStats 10 }

policyDay OBJECT-TYPE
    SYNTAX      Gauge32
    MAX-ACCESS  read-only
    STATUS      current
    DESCRIPTION
        "The number of messages that have triggered a policy during the current calendar day (beginning at midnight)."
::= { bmaPolicyStats 11 }

policyTotal OBJECT-TYPE
    SYNTAX      Gauge32
    MAX-ACCESS  read-only
    STATUS      current
    DESCRIPTION
        "The number of messages that have triggered a policy since installation or since the last reset of statistics."
::= { bmaPolicyStats 12 }

customPolicyTable OBJECT-TYPE
    SYNTAX      SEQUENCE OF customPolicyEntry
    MAX-ACCESS  not-accessible
    STATUS      current
    DESCRIPTION
        "A table of custom policies as well as statistics for the current hour, the current calendar day (beginning at midnight),
         and since installation or since the last reset of statistics."
::= { bmaPolicyStats 13 }

customPolicyEntry OBJECT-TYPE
    SYNTAX      CustomPolicyEntry
    MAX-ACCESS  not-accessible
    STATUS      current
    DESCRIPTION
        "An entry containing custom policy information."
    INDEX { customPolicyIndex }
::= { customPolicyTable 1 }

CustomPolicyEntry ::= SEQUENCE {
    customPolicyIndex       Integer32,
    customPolicyName        DisplayString,
    customPolicyStatsHour   Gauge32,
    customPolicyStatsDay    Gauge32,
    customPolicyStatsTotal  Gauge32
}

customPolicyIndex OBJECT-TYPE
    SYNTAX      Integer32
    MAX-ACCESS  not-accessible
    STATUS      current
    DESCRIPTION
        "An index that uniquely represents a custom policy."
    ::= { customPolicyEntry 1 }

customPolicyName OBJECT-TYPE
    SYNTAX      DisplayString
    MAX-ACCESS  read-only
    STATUS      current
    DESCRIPTION
        "The name of the custom policy."
::= { customPolicyEntry 2 }

customPolicyStatsHour OBJECT-TYPE
    SYNTAX      Gauge32
    MAX-ACCESS  read-only
    STATUS      current
    DESCRIPTION
        "The number of custom policy violations during the current hour."
::= { customPolicyEntry 3 }

customPolicyStatsDay OBJECT-TYPE
    SYNTAX      Gauge32
    MAX-ACCESS  read-only
    STATUS      current
    DESCRIPTION
        "The number of custom policy violations during the current calendar day (beginning at midnight)."
::= { customPolicyEntry 4 }

customPolicyStatsTotal OBJECT-TYPE
    SYNTAX      Gauge32
    MAX-ACCESS  read-only
    STATUS      current
    DESCRIPTION
        "The number of custom policy violations since installation or since the last reset of statistics."
::= { customPolicyEntry 5 }

-- Storage Statistics

effectiveHour OBJECT-TYPE
    SYNTAX      Gauge32
    UNITS       "MB"
    MAX-ACCESS  read-only
    STATUS      current
    DESCRIPTION
        "The real combined size of all messages stored on the archiver during thecurrent hour."
::= { bmaStorageStats 1 }

effectiveDay OBJECT-TYPE
    SYNTAX      Gauge32
    UNITS       "MB"
    MAX-ACCESS  read-only
    STATUS      current
    DESCRIPTION
        "The real combined size of all messages stored on the archiver during the current calendar day (beginning at midnight)."
::= { bmaStorageStats 2 }

effectiveTotal OBJECT-TYPE
    SYNTAX      Gauge32
    UNITS       "MB"
    MAX-ACCESS  read-only
    STATUS      current
    DESCRIPTION
        "The real combined size of all messages stored on the archiver since installation or since the last reset of statistics."
::= { bmaStorageStats 3 }

onDiskSizeHour OBJECT-TYPE
    SYNTAX      Gauge32
    UNITS       "MB"
    MAX-ACCESS  read-only
    STATUS      current
    DESCRIPTION
        "The actual amount of storage used on the archiver during the current hour."
::= { bmaStorageStats 4 }

onDiskSizeDay OBJECT-TYPE
    SYNTAX      Gauge32
    UNITS       "MB"
    MAX-ACCESS  read-only
    STATUS      current
    DESCRIPTION
        "The actual amount of storage used on the archiver during the current calendar day (beginning at midnight)."
::= { bmaStorageStats 5 }

onDiskSizeTotal OBJECT-TYPE
    SYNTAX      Gauge32
    UNITS       "MB"
    MAX-ACCESS  read-only
    STATUS      current
    DESCRIPTION
        "The actual amount of storage used on the archiver since installation or since the last reset of statistics."
::= { bmaStorageStats 6 }

reductionHour OBJECT-TYPE
    SYNTAX      Integer32 (-100..100)
    UNITS       "%"
    MAX-ACCESS  read-only
    STATUS      current
    DESCRIPTION
        "The percentage of storage space saved by the compression mechanisms of the archiver during the current hour."
::= { bmaStorageStats 7 }

reductionDay OBJECT-TYPE
    SYNTAX      Integer32 (-100..100)
    UNITS       "%"
    MAX-ACCESS  read-only
    STATUS      current
    DESCRIPTION
        "The percentage of storage space saved by the compression mechanisms of the archiver during the current calendar day (beginning at midnight)."
::= { bmaStorageStats 8 }

reductionTotal OBJECT-TYPE
    SYNTAX      Integer32 (-100..100)
    UNITS       "%"
    MAX-ACCESS  read-only
    STATUS      current
    DESCRIPTION
        "The percentage of storage space saved by the compression mechanisms of the archiver since installation or since the last reset of statistics."
::= { bmaStorageStats 9 }

END

--
-- BARRACUDA-SMI.txt:   Barracuda Networks Structure of Management Information
--
-- June 2013, David A. Fluck
--
-- Copyright (c) 2013 by Barracuda Networks, Inc.
-- All rights reserved.
--

BARRACUDA-SMI DEFINITIONS ::= BEGIN

IMPORTS
    MODULE-IDENTITY,
    OBJECT-IDENTITY,
    enterprises
        FROM SNMPv2-SMI;
        
barracuda MODULE-IDENTITY
    LAST-UPDATED    "201305300000Z"
    ORGANIZATION    "Barracuda Networks, Inc."
    CONTACT-INFO
        "Barracuda Networks Inc.
         3175 S. Winchester Blvd.
         Campbell, CA 95008"
    DESCRIPTION
        "The Structure of Management Information for Barracuda Networks."
::= { enterprises 20632 }
END

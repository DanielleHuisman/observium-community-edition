--
-- NMS-EMSTRAP-MIB.my
-- MIB generated by MG-SOFT Visual MIB Builder Version 6.0  Build 88
-- Wednesday, July 22, 2015 at 14:58:01
--

	NMS-EMSTRAP-MIB DEFINITIONS ::= BEGIN
 
		IMPORTS
			nmsWorkGroup			
				FROM NMS-SMI			
			Integer32, OBJECT-TYPE, MODULE-IDENTITY, NOTIFICATION-TYPE			
				FROM SNMPv2-SMI;
	
	
		-- 1.3.6.1.4.1.3320.20.1
		eMSMibModule MODULE-IDENTITY 
			LAST-UPDATED "201507220950Z"		-- July 22, 2015 at 09:50 GMT
			ORGANIZATION 
				"Organization."
			CONTACT-INFO 
				"Contact-info."
			DESCRIPTION 
				"Description."
			::= { nmsWorkGroup 1 }

		
	
--
-- Node definitions
--
	
		-- 1.3.6.1.4.1.3320.20.1.1
		eMSTrapObject OBJECT IDENTIFIER ::= { eMSMibModule 1 }

		
		-- 1.3.6.1.4.1.3320.20.1.1.1
		eMSTrap OBJECT IDENTIFIER ::= { eMSTrapObject 1 }

		
		-- 1.3.6.1.4.1.3320.20.1.1.1.1
		eMSProcessTrap NOTIFICATION-TYPE
			OBJECTS { eMSProcess, eMSProcessLimit }
			STATUS current
			DESCRIPTION 
				"Send this trap when process have errors."
			::= { eMSTrap 1 }

		
		-- 1.3.6.1.4.1.3320.20.1.1.1.2
		eMSCPUTrap NOTIFICATION-TYPE
			OBJECTS { eMSCPURatio, eMSCPURatioLimit }
			STATUS current
			DESCRIPTION 
				"Send this trap when CPU radio is out of limit."
			::= { eMSTrap 2 }

		
		-- 1.3.6.1.4.1.3320.20.1.1.1.3
		eMSMemoryTrap NOTIFICATION-TYPE
			OBJECTS { eMSMemorySize, eMSMemoryUsed, eMSMemoryRatioLimit }
			STATUS current
			DESCRIPTION 
				"Send this trap when Memory radio is out of limit."
			::= { eMSTrap 3 }

		
		-- 1.3.6.1.4.1.3320.20.1.1.1.4
		eMSDiskTrap NOTIFICATION-TYPE
			OBJECTS { eMSDiskSize, eMSDiskUsed, eMSDiskRatioLimit }
			STATUS current
			DESCRIPTION 
				"Send this trap when Disk radio is out of limit."
			::= { eMSTrap 4 }

		
		-- 1.3.6.1.4.1.3320.20.1.1.1.5
		eMSDataTrap NOTIFICATION-TYPE
			OBJECTS { eMSDataSize, eMSDataUsed, eMSDataRatioLimit }
			STATUS current
			DESCRIPTION 
				"Send this trap when data radio is out of limit."
			::= { eMSTrap 5 }

		
		-- 1.3.6.1.4.1.3320.20.1.1.1.6
		eMSLicenseTrap NOTIFICATION-TYPE
			OBJECTS { eMSLicense, eMSLicenseLimit }
			STATUS current
			DESCRIPTION 
				"Send this trap when license is out of limit."
			::= { eMSTrap 6 }

		
		-- 1.3.6.1.4.1.3320.20.1.1.3
		eMSTrapInfo OBJECT IDENTIFIER ::= { eMSTrapObject 3 }

		
		-- 1.3.6.1.4.1.3320.20.1.1.3.1
		eMSProcess OBJECT-TYPE
			SYNTAX Integer32
			MAX-ACCESS accessible-for-notify
			STATUS current
			DESCRIPTION
				"Processes of nms "
			::= { eMSTrapInfo 1 }

		
		-- 1.3.6.1.4.1.3320.20.1.1.3.2
		eMSProcessLimit OBJECT-TYPE
			SYNTAX Integer32
			UNITS "%"
			MAX-ACCESS accessible-for-notify
			STATUS current
			DESCRIPTION
				"limit of processes in nms system."
			::= { eMSTrapInfo 2 }

		
		-- 1.3.6.1.4.1.3320.20.1.1.3.3
		eMSCPURatio OBJECT-TYPE
			SYNTAX Integer32
			UNITS "%"
			MAX-ACCESS accessible-for-notify
			STATUS current
			DESCRIPTION
				"cpu ratio of nms PC system."
			::= { eMSTrapInfo 3 }

		
		-- 1.3.6.1.4.1.3320.20.1.1.3.4
		eMSCPURatioLimit OBJECT-TYPE
			SYNTAX Integer32
			UNITS "%"
			MAX-ACCESS accessible-for-notify
			STATUS current
			DESCRIPTION
				"Send this trap when CPU radio is out of limit."
			::= { eMSTrapInfo 4 }

		
		-- 1.3.6.1.4.1.3320.20.1.1.3.5
		eMSMemorySize OBJECT-TYPE
			SYNTAX Integer32
			UNITS "MB"
			MAX-ACCESS accessible-for-notify
			STATUS current
			DESCRIPTION
				"Memory size of nms pc system."
			::= { eMSTrapInfo 5 }

		
		-- 1.3.6.1.4.1.3320.20.1.1.3.6
		eMSMemoryUsed OBJECT-TYPE
			SYNTAX Integer32
			UNITS "MB"
			MAX-ACCESS accessible-for-notify
			STATUS current
			DESCRIPTION
				"memory have use in nms PC system."
			::= { eMSTrapInfo 6 }

		
		-- 1.3.6.1.4.1.3320.20.1.1.3.7
		eMSMemoryRatioLimit OBJECT-TYPE
			SYNTAX Integer32
			UNITS "%"
			MAX-ACCESS accessible-for-notify
			STATUS current
			DESCRIPTION
				"Send this trap when Memory radio is out of limit."
			::= { eMSTrapInfo 7 }

		
		-- 1.3.6.1.4.1.3320.20.1.1.3.8
		eMSDiskSize OBJECT-TYPE
			SYNTAX Integer32
			UNITS "MB"
			MAX-ACCESS accessible-for-notify
			STATUS current
			DESCRIPTION
				"disk size of nms pc system."
			::= { eMSTrapInfo 8 }

		
		-- 1.3.6.1.4.1.3320.20.1.1.3.9
		eMSDiskUsed OBJECT-TYPE
			SYNTAX Integer32
			UNITS "MB"
			MAX-ACCESS accessible-for-notify
			STATUS current
			DESCRIPTION
				"disk size have been used in nms pc system."
			::= { eMSTrapInfo 9 }

		
		-- 1.3.6.1.4.1.3320.20.1.1.3.10
		eMSDiskRatioLimit OBJECT-TYPE
			SYNTAX Integer32
			UNITS "%"
			MAX-ACCESS accessible-for-notify
			STATUS current
			DESCRIPTION
				"Send this trap when Disk radio is out of limit."
			::= { eMSTrapInfo 10 }

		
		-- 1.3.6.1.4.1.3320.20.1.1.3.11
		eMSDataSize OBJECT-TYPE
			SYNTAX Integer32
			UNITS "MB"
			MAX-ACCESS accessible-for-notify
			STATUS current
			DESCRIPTION
				"data space size of nms pc system."
			::= { eMSTrapInfo 11 }

		
		-- 1.3.6.1.4.1.3320.20.1.1.3.12
		eMSDataUsed OBJECT-TYPE
			SYNTAX Integer32
			UNITS "MB"
			MAX-ACCESS accessible-for-notify
			STATUS current
			DESCRIPTION
				"data space have been use in nms pc system."
			::= { eMSTrapInfo 12 }

		
		-- 1.3.6.1.4.1.3320.20.1.1.3.13
		eMSDataRatioLimit OBJECT-TYPE
			SYNTAX Integer32
			UNITS "%"
			MAX-ACCESS accessible-for-notify
			STATUS current
			DESCRIPTION
				"Send this trap when data radio is out of limit."
			::= { eMSTrapInfo 13 }

		
		-- 1.3.6.1.4.1.3320.20.1.1.3.14
		eMSLicense OBJECT-TYPE
			SYNTAX Integer32
			MAX-ACCESS accessible-for-notify
			STATUS current
			DESCRIPTION
				"liscense of nms system."
			::= { eMSTrapInfo 14 }

		
		-- 1.3.6.1.4.1.3320.20.1.1.3.15
		eMSLicenseLimit OBJECT-TYPE
			SYNTAX Integer32
			MAX-ACCESS accessible-for-notify
			STATUS current
			DESCRIPTION
				"Send this trap when license is out of limit."
			::= { eMSTrapInfo 15 }

		
	
	END

--
-- NMS-EMSTRAP-MIB.my
--

--****************************************************************************
--
-- Copyright (c) 2009 Broadcom Corporation
--
-- This program is the proprietary software of Broadcom Corporation and/or
-- its licensors, and may only be used, duplicated, modified or distributed
-- pursuant to the terms and conditions of a separate, written license
-- agreement executed between you and Broadcom (an "Authorized License").
-- Except as set forth in an Authorized License, Broadcom grants no license
-- (express or implied), right to use, or waiver of any kind with respect to
-- the Software, and Broadcom expressly reserves all rights in and to the
-- Software and all intellectual property rights therein.  IF YOU HAVE NO
-- AUTHORIZED LICENSE, THEN YOU HAVE NO RIGHT TO USE THIS SOFTWARE IN ANY WAY,
-- AND SHOULD IMMEDIATELY NOTIFY BROADCOM AND DISCONTINUE ALL USE OF THE
-- SOFTWARE.  
--
-- Except as expressly set forth in the Authorized License,
--
-- 1.     This program, including its structure, sequence and organization,
-- constitutes the valuable trade secrets of Broadcom, and you shall use all
-- reasonable efforts to protect the confidentiality thereof, and to use this
-- information only in connection with your use of Broadcom integrated circuit
-- products.
--
-- 2.     TO THE MAXIMUM EXTENT PERMITTED BY LAW, THE SOFTWARE IS PROVIDED
-- "AS IS" AND WITH ALL FAULTS AND BROADCOM MAKES NO PROMISES, REPRESENTATIONS
-- OR WARRANTIES, EITHER EXPRESS, IMPLIED, STATUTORY, OR OTHERWISE, WITH
-- RESPECT TO THE SOFTWARE.  BROADCOM SPECIFICALLY DISCLAIMS ANY AND ALL
-- IMPLIED WARRANTIES OF TITLE, MERCHANTABILITY, NONINFRINGEMENT, FITNESS FOR
-- A PARTICULAR PURPOSE, LACK OF VIRUSES, ACCURACY OR COMPLETENESS, QUIET
-- ENJOYMENT, QUIET POSSESSION OR CORRESPONDENCE TO DESCRIPTION. YOU ASSUME
-- THE ENTIRE RISK ARISING OUT OF USE OR PERFORMANCE OF THE SOFTWARE.
--
-- 3.     TO THE MAXIMUM EXTENT PERMITTED BY LAW, IN NO EVENT SHALL BROADCOM
-- OR ITS LICENSORS BE LIABLE FOR (i) CONSEQUENTIAL, INCIDENTAL, SPECIAL,
-- INDIRECT, OR EXEMPLARY DAMAGES WHATSOEVER ARISING OUT OF OR IN ANY WAY
-- RELATING TO YOUR USE OF OR INABILITY TO USE THE SOFTWARE EVEN IF BROADCOM
-- HAS BEEN ADVISED OF THE POSSIBILITY OF SUCH DAMAGES; OR (ii) ANY AMOUNT IN
-- EXCESS OF THE AMOUNT ACTUALLY PAID FOR THE SOFTWARE ITSELF OR U.S. $1,
-- WHICHEVER IS GREATER. THESE LIMITATIONS SHALL APPLY NOTWITHSTANDING ANY
-- FAILURE OF ESSENTIAL PURPOSE OF ANY LIMITED REMEDY.
--
--****************************************************************************
--    Filename: brcm-battery-engineering.mib
--    Author:   Kevin O'Neal
--    Creation Date: June 10, 2009
--
--**************************************************************************
--    Description:
--
--		private MIB for engineering (not runtime) management of battery
--      features and functions.
--		
--**************************************************************************
--    Revision History:
--
--      See module identity.
--
--**************************************************************************

BRCM-BATTERY-ENGINEERING-MIB DEFINITIONS ::= BEGIN

IMPORTS
    MODULE-IDENTITY,
    OBJECT-IDENTITY,
    OBJECT-TYPE
        FROM SNMPv2-SMI
    cableDataEngineering
        FROM BRCM-CABLEDATA-ENGINEERING-MIB
    PositiveInteger
        FROM UPS-MIB;
                
batteryEngineering MODULE-IDENTITY
    LAST-UPDATED "200906100000Z"
    ORGANIZATION "Broadcom Corporation"
    CONTACT-INFO
        "	BANANA-CABLEDATA
                (cableData branch of the
                Broadcom Assigned Numbers and Naming Authority)
                Broadcom Corporation

        Postal: 4385 River Green Parkway
                Duluth, GA  30096
                USA

           Tel: +1 770 232-0018

        E-mail: banana-cabledata@broadcom.com"
    DESCRIPTION
        "Broadcom proprietary MIB for engineering management of objects related
         to battery powered devices."
    REVISION      "200906100000Z"
    DESCRIPTION
        "Initial version of this MIB module."
    ::= { cableDataEngineering 10 }

batteryEngrBase OBJECT IDENTIFIER ::= { batteryEngineering 1 }

battSimulatePowerSource OBJECT-TYPE
    SYNTAX      INTEGER {
                none(0),
                utility(1),
				battery(2)
    }
    MAX-ACCESS  read-write
    STATUS      current
    DESCRIPTION
        "This object can be used to simulate transitions to and from different
         power sources for the purpose of evaluating system response to such
         transitions.  Setting the object to utility(1) will dispatch an event
         indicating transition to utility power.  Setting the object to 
         battery(2) will dispatch an event indicating transition to battery 
         power.  Setting the object to none(0) will dispatch an event indicating
         a transition to the actual current power source, thus returning the
         system state to its actual current condition.
         
         Note that setting this object does not actually result in a power 
         source change, only in the publishing of an event that the power source
         has changed.  As a result, the object may be set to battery(2) even if
         no battery is installed, or utility(1) if the device is not currently
         attached to utility power.
         
         Further note that setting this object does not affect battery charging,
         state reported by objects in the BRCM-BATTERY-MGMT-MIB or UPS-MIB, etc."
    ::= { batteryEngrBase 1 }

END

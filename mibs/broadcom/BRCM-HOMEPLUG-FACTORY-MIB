--**************************************************************************
--                                                                          
--    Copyright 2004 Broadcom Corporation                                   
--    All Rights Reserved                                                   
--    No portions of this material may be reproduced in any form without the
--    written permission of:                                                
--             Broadcom Corporation                                         
--             16251 Laguna Canyon Road                                     
--             Irvine, California  92618                                    
--    All information contained in this document is Broadcom Corporation    
--    company private, proprietary, and trade secret.                       
--                                                                          
--                                                                          
--                                                                          
--**************************************************************************
--    Filename: brcm-homeplug-factory.mib
--    Author:   Kevin O'Neal
--    Creation Date: December 21, 2004
--
--**************************************************************************
--    Description:
--
--		Factory MIB for HomePlug settings
--		
--**************************************************************************
--    Revision History:
--
--**************************************************************************

BRCM-HOMEPLUG-FACTORY-MIB DEFINITIONS ::= BEGIN

IMPORTS
    MODULE-IDENTITY,
    OBJECT-TYPE,
    Unsigned32
        FROM SNMPv2-SMI
    TruthValue,
    MacAddress,
    DisplayString
        FROM SNMPv2-TC
    cableDataFactory
        FROM BRCM-CABLEDATA-FACTORY-MIB;
                
homeplugFactory MODULE-IDENTITY
    LAST-UPDATED "200412210000Z"
    ORGANIZATION "Broadcom Corporation"
    CONTACT-INFO
        "	BANANA-CABLEDATA
                (cableData branch of the
                Broadcom Assigned Numbers and Naming Authority)
                Broadcom Corporation

        Postal: 4385 River Green Parkway
                Duluth, GA  30096
                USA

           Tel: +1 770 232-0018

        E-mail: banana-cabledata@broadcom.com"
    DESCRIPTION
        "Broadcom cabledata factory MIB for HomePlug"
    REVISION      "200412210000Z"
    DESCRIPTION
            "Initial version of this MIB module."
    ::= { cableDataFactory 9 }
    
homeplugFactMacAddress OBJECT-TYPE
    SYNTAX      MacAddress
    MAX-ACCESS  read-write
    STATUS      current
    DESCRIPTION
       "The MAC address of the embedded HomePlug endpoint."
    ::= { homeplugFactory 1 }
    
homeplugFactDEKPassword OBJECT-TYPE
    SYNTAX      DisplayString (SIZE(4..24))
    MAX-ACCESS  read-write
    STATUS      current
    DESCRIPTION
       "The password that is used to generate the default encryption key.  Note
        that the password must only contain characters between 0x20 and 0x7F, 
        inclusive."
    ::= { homeplugFactory 2 }
    
homeplugFactNEKPassword OBJECT-TYPE
    SYNTAX      DisplayString (SIZE(4..24))
    MAX-ACCESS  read-write
    STATUS      current
    DESCRIPTION
       "The password that is used to generate the network encryption key.  Note
        that the password must only contain characters between 0x20 and 0x7F, 
        inclusive."
    ::= { homeplugFactory 3 }
    
END

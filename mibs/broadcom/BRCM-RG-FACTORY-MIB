--**************************************************************************
--                                                                          
--    Copyright 2007 Broadcom Corporation                                   
--    All Rights Reserved                                                   
--    No portions of this material may be reproduced in any form without the
--    written permission of:                                                
--             Broadcom Corporation                                         
--             16251 Laguna Canyon Road                                     
--             Irvine, California  92618                                    
--    All information contained in this document is Broadcom Corporation    
--    company private, proprietary, and trade secret.                       
--                                                                          
--                                                                          
--                                                                          
--**************************************************************************
--    Filename: brcm-rg-factory.mib
--    Author:   Kevin O'Neal
--    Creation Date: 30-january-2003
--
--**************************************************************************
--    Description:
--
--		private MIB for residential gateway factory
--		
--**************************************************************************
--    Revision History:
--
--**************************************************************************

BRCM-RG-FACTORY-MIB DEFINITIONS ::= BEGIN

IMPORTS
    MODULE-IDENTITY,
    OBJECT-TYPE,
    IpAddress
        FROM SNMPv2-SMI
    TruthValue,
    DisplayString
        FROM SNMPv2-TC
    cableDataFactory
        FROM BRCM-CABLEDATA-FACTORY-MIB;
                
residentialGatewayFactory MODULE-IDENTITY
    LAST-UPDATED "200702050000Z"
    ORGANIZATION "Broadcom Corporation"
    CONTACT-INFO
        "	BANANA-CABLEDATA
                (cableData branch of the
                Broadcom Assigned Numbers and Naming Authority)
                Broadcom Corporation

        Postal: 4385 River Green Parkway
                Duluth, GA  30096
                USA

           Tel: +1 770 232-0018

        E-mail: banana-cabledata@broadcom.com"
    DESCRIPTION
        "Broadcom proprietary MIB for management and configuration
         of objects used in manufacturing of residential gateway devices."
    REVISION      "200702050000Z"
    DESCRIPTION
        "Module description was updated."
    REVISION      "200301300000Z"
    DESCRIPTION
            "Initial version of this MIB module."
    ::= { cableDataFactory 7 }

-- rgFactoryBase: miscellaneous control/state objects for factory mode    
rgFactoryBase OBJECT IDENTIFIER ::= { residentialGatewayFactory 1 }
        
rgInitialMode OBJECT-TYPE
    SYNTAX      INTEGER {
                    disabled(1),
                    residentialGateway(2),
                    cableHome10(3),
                    cableHome11(4)
                }
    MAX-ACCESS  read-write
    STATUS      current
    DESCRIPTION
        "Sets the initial manufactured / default operational mode of the device 
         with regard to residential gateway behaviour."
    ::= { rgFactoryBase 1 }
    
rgRipAuthEnabled OBJECT-TYPE
    SYNTAX      TruthValue
    MAX-ACCESS  read-write
    STATUS      current
    DESCRIPTION
        "Enables or disables the RIP MD5 authentication."
    ::= { rgFactoryBase 2 }

rgRipAuthKeyValue OBJECT-TYPE
    SYNTAX      DisplayString (SIZE (0..16))
    MAX-ACCESS  read-write
    STATUS      current
    DESCRIPTION
        "Sets the RIP Auth key value."
    ::= { rgFactoryBase 3 }

rgRipAuthKeyId OBJECT-TYPE
    SYNTAX      INTEGER (0..256)
    MAX-ACCESS  read-write
    STATUS      current
    DESCRIPTION
        "Sets the RIP auth key ID"
    ::= { rgFactoryBase 4 }

rgRipReportingInterval OBJECT-TYPE
    SYNTAX      INTEGER (1..16535)
    UNITS       "seconds"
    MAX-ACCESS  read-write
    STATUS      current
    DESCRIPTION
        "Sets the RIP reporting interval."
    ::= { rgFactoryBase 5 }

rgRipUnicastDestIpAddress OBJECT-TYPE
    SYNTAX      IpAddress
    MAX-ACCESS  read-write
    STATUS      current
    DESCRIPTION
        "Sets the unicast destination IP address that will be used for RIP 
         messaging."
    ::= { rgFactoryBase 6 }

rgRipSubnetMask OBJECT-TYPE
    SYNTAX      IpAddress
    MAX-ACCESS  read-write
    STATUS      current
    DESCRIPTION
        "Sets the RIP subnet mask which is AND'ed with the WAN IP address."
    ::= { rgFactoryBase 7 }

END

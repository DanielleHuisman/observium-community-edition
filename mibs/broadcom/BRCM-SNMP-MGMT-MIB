--**************************************************************************
--                                                                          
--    Copyright 2007 Broadcom Corporation                                   
--    All Rights Reserved                                                   
--    No portions of this material may be reproduced in any form without the
--    written permission of:                                                
--             Broadcom Corporation                                         
--             16251 Laguna Canyon Road                                     
--             Irvine, California  92618                                    
--    All information contained in this document is Broadcom Corporation    
--    company private, proprietary, and trade secret.                       
--                                                                          
--                                                                          
--                                                                          
--**************************************************************************
--    Filename: brcm-snmp-mgmt.mib
--    Author:   Kevin O'Neal
--    Creation Date: 29-april-2003
--
--**************************************************************************
--    Description:
--
--		private MIB for runtime (not factory) SNMP management
--		
--**************************************************************************
--    Revision History:
--
--**************************************************************************

BRCM-SNMP-MGMT-MIB DEFINITIONS ::= BEGIN

IMPORTS
    MODULE-IDENTITY,
    OBJECT-TYPE,
    Unsigned32,
    Integer32
        FROM SNMPv2-SMI
    cableDataMgmtBase
        FROM BRCM-CABLEDATA-MGMT-MIB;
                
snmpMgmt MODULE-IDENTITY
    LAST-UPDATED "200702050000Z"
    ORGANIZATION "Broadcom Corporation"
    CONTACT-INFO
        "	BANANA-CABLEDATA
                (cableData branch of the
                Broadcom Assigned Numbers and Naming Authority)
                Broadcom Corporation

        Postal: 4385 River Green Parkway
                Duluth, GA  30096
                USA

           Tel: +1 770 232-0018

        E-mail: banana-cabledata@broadcom.com"
    DESCRIPTION
        "Broadcom proprietary MIB for runtime management and configuration
         of objects related to SNMP."
    REVISION      "200702050000Z"
    DESCRIPTION
        "Module description was updated.
         Compilability issues were cleaned up:
         - Chronological order of revision list was corrected."
    REVISION      "200610050000Z"
    DESCRIPTION
        "Added object snmpDscpTag."
    REVISION      "200304290000Z"
    DESCRIPTION
        "Initial version of this MIB module."
    ::= { cableDataMgmtBase 2 }
    
snmpUdpPort OBJECT-TYPE
    SYNTAX      Unsigned32 (1..65535)
    MAX-ACCESS  read-write
    STATUS      current
    DESCRIPTION
        "Controls and reflects the UDP port which will be listened for
         as the destination port on received SNMP packets and used as the 
         source port on subsequent SNMP replies.
         
         Setting this object will result in an immediate change of the SNMP
         port number, although the SNMP reply to the set request which modifies
         this value will still be sent using the port on which it was received.
         This prevents the sending SNMP manager from receiving a timeout on the 
         set request.  
         
         This value is NOT stored to non-volatile storage and will revert to the 
         default value on system reboot."
    DEFVAL { 161 }
    ::= { snmpMgmt 1 }

snmpNotifyUdpPort OBJECT-TYPE
    SYNTAX      Unsigned32 (1..65535)
    MAX-ACCESS  read-write
    STATUS      current
    DESCRIPTION
        "Controls and reflects the UDP port which will be used as the 
         destination port in SNMP notify packets, including traps and informs.
         
         This value is NOT stored to non-volatile storage and will revert to 
         the default value on system reboot."
    DEFVAL { 162 }
    ::= { snmpMgmt 2 }
    
snmpDscpTag OBJECT-TYPE
   SYNTAX       Integer32 (0..63)
   MAX-ACCESS   read-write
   STATUS       current
   DESCRIPTION
       "This object controls the value for the DSCP field (previously known as 
        ToS) in the IP header which will be used for all SNMP packets 
        originating from this device.
        
        This value is NOT stored to non-volatile storage and will revert to 
        the default value on system reboot."
   DEFVAL { 0 }
 ::= { snmpMgmt 3 }
 
END

--**************************************************************************
--                                                                          
--    Copyright 2007 Broadcom Corporation                                   
--    All Rights Reserved                                                   
--    No portions of this material may be reproduced in any form without the
--    written permission of:                                                
--             Broadcom Corporation                                         
--             16251 Laguna Canyon Road                                     
--             Irvine, California  92618                                    
--    All information contained in this document is Broadcom Corporation    
--    company private, proprietary, and trade secret.                       
--                                                                          
--                                                                          
--                                                                          
--**************************************************************************
--    Filename: brcm-thermal-mgmt.mib
--    Author:   Charles Eyles
--    Creation Date: October 4, 2006
--
--**************************************************************************
--    Description:
--
--		private MIB for runtime (not factory) management of the
--              Thermal Monitor
--		
--**************************************************************************
--    Revision History:
--
--**************************************************************************

BRCM-THERMAL-MGMT-MIB DEFINITIONS ::= BEGIN

IMPORTS
    MODULE-IDENTITY,
    OBJECT-TYPE,
    Integer32,
    Unsigned32
        FROM SNMPv2-SMI
    TruthValue,
    DateAndTime,
    DisplayString
        FROM SNMPv2-TC
    cableDataMgmtMIBObjects
        FROM BRCM-CABLEDATA-MGMT-MIB;
                
thermalMgmt MODULE-IDENTITY
    LAST-UPDATED "200702050000Z"
    ORGANIZATION "Broadcom Corporation"
    CONTACT-INFO
        "	BANANA-CABLEDATA
                (cableData branch of the
                Broadcom Assigned Numbers and Naming Authority)
                Broadcom Corporation

        Postal: 4385 River Green Parkway
                Duluth, GA  30096
                USA

           Tel: +1 770 232-0018

        E-mail: banana-cabledata@broadcom.com"
    DESCRIPTION
        "Broadcom proprietary MIB for runtime management and configuration
         of objects related to thermal monitor."
    REVISION      "200702050000Z"
    DESCRIPTION
        "Module description was updated. 
         Compilability issues were cleaned up:
         - Illegal character was removed from description of objects 
           thermalPowerOnThreshold and thermalPowerOffThreshold."
    REVISION      "200610040000Z"
    DESCRIPTION
        "Initial version of this MIB module."
    ::= { cableDataMgmtMIBObjects 11 }
    
thermalMgmtBase OBJECT IDENTIFIER ::= { thermalMgmt 1 }

thermalCurrentTemperature OBJECT-TYPE
    SYNTAX      Integer32
    UNITS       "degrees C"
    MAX-ACCESS  read-only
    STATUS      current
    DESCRIPTION
        "The Current Temperature of the Unit."
    ::= { thermalMgmtBase 1 }

thermalPowerOffThreshold OBJECT-TYPE
    SYNTAX      Integer32 (40..120)
    UNITS       "degrees C"
    MAX-ACCESS  read-write
    STATUS      current
    DESCRIPTION
        "Specifies the Temperature Threshold at which the Thermal Shutdown Controller
         will power down the unit. (40C to 120C). Note PowerOffThreshold must be
         greater than PowerOnThreshold."
    ::= { thermalMgmtBase 2 }

thermalPowerOnThreshold OBJECT-TYPE
    SYNTAX      Integer32 (40..120)
    UNITS       "degrees C"
    MAX-ACCESS  read-write
    STATUS      current
    DESCRIPTION
        "Specifies the Temperature Threshold at which the Thermal Shutdown Controller
         will switch power back on. (40C to 120C). Note PowerOnThreshold must be
         less than PowerOffThreshold."
    ::= { thermalMgmtBase 3 }

thermalPowerOnDelay OBJECT-TYPE
    SYNTAX      Unsigned32 (2..50)
    UNITS       "250 Milliseconds"
    MAX-ACCESS  read-write
    STATUS      current
    DESCRIPTION
        "This delay specifies the time between the Thermal Shutdown Controller detecting  
         that the Power On Threshold has been reached and when it actually switches 
         the unit back on. Its purpose is to allow power on the remainder of the board
         to stabilize. Serial communications are blocked during this delay, so it should 
         be chosen carefully. The delay is specified in multiples of 50 milliseconds
         2 to 50 ( 100ms - 2500ms ). The default is value is 5 yielding a delay
         of 250ms."
    ::= { thermalMgmtBase 4 }

thermalPowerOffDelay OBJECT-TYPE
    SYNTAX      Unsigned32 (5..60)
    UNITS       "Seconds"
    MAX-ACCESS  read-write
    STATUS      current
    DESCRIPTION
        "This delay is used to ensure the remainder of the board is completely powered 
         down prior to the Thermal Shutdown Circuit entering Over Temperature state. 
         Because some power supplies may experience a current trip when input power is 
         suddenly removed, this delay must be long enough to ensure the board will 
         successfully power back up following power removal. The delay is specified in 
         seconds; 5 to 60."
    ::= { thermalMgmtBase 5 }

thermalNotificationDelay OBJECT-TYPE
    SYNTAX      Unsigned32 (5..60)
    UNITS       "Seconds"
    MAX-ACCESS  read-write
    STATUS      current
    DESCRIPTION
        "This delay is used to allow the main processor time to clean up (i.e. preserve 
         state information in non-volatile memory, and/or gracefully shut down a battery 
         subsystem) prior to power being removed. The delay is specified in seconds 5 to 
         60. The default value is 10."
    ::= { thermalMgmtBase 6 }

thermalMonitorInitialized OBJECT-TYPE
    SYNTAX      TruthValue
    MAX-ACCESS  read-only
    STATUS      current
    DESCRIPTION
        "This object returns true if the thermal monitor has been successfully initialized."
    DEFVAL { false }
    ::= { thermalMgmtBase 7 }

END

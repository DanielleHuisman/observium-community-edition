BUFFALO-ROOT-MIB DEFINITIONS ::= BEGIN

	IMPORTS	enterprises	FROM RFC1155-SMI;

-- **************************************************************************
--
--  BUFFALO Inc. has the following enterprise object number that assigned
--   from IANA. see http://www.iana.org/assignments/enterprise-numbers
--
-- **************************************************************************

buffalo	MODULE-IDENTITY
	LAST-UPDATED "202003090000Z"
	ORGANIZATION "Buffalo Inc."
    CONTACT-INFO	"URI: http://buffalo.jp/products/catalog/storage/hd_lan_business.html
			 Contact: Network Business Unit
			 Buffalo Inc. 
			 3-30-20 Osu, Naka-ku, Nagoya city, Aichi, JAPAN"
	DESCRIPTION
		"Management Information Base module for BUFFALO private defined
		 objects.
		 Copyright (c) 2012 Buffalo Inc."
	::= {enterprises 5227}

-- **************************************************************************
--  Product definition: Buffalo supports (or used to be supported) enterprise 
-- defined MIB objects with the following products.
--  - Derived from SNMP Private MIB operation standard, Mar. 19 2009.
-- **************************************************************************

lsm-10-100-8			OBJECT IDENTIFIER ::= {buffalo 1} -- BUFFALO LSM10/100-8 Ethernet Switch
lsm-10-100-24			OBJECT IDENTIFIER ::= {buffalo 2} -- BUFFALO LSM10/100-24
lsm-l3-24				OBJECT IDENTIFIER ::= {buffalo 3} -- BUFFALO LSM-L3-24
wlm-series				OBJECT IDENTIFIER ::= {buffalo 4} -- BUFFALO AirStationPro WLM-SERIES - WLM-L11G/WLM2-SERIES
vsm-p12tx2i				OBJECT IDENTIFIER ::= {buffalo 5} -- BUFFALO VSM-P12TX2I
lsm-10-100-16w			OBJECT IDENTIFIER ::= {buffalo 6} -- BUFFALO LSM10/100-16W
lsm-10-100-24w			OBJECT IDENTIFIER ::= {buffalo 7} -- BUFFALO LSM10/100-24W
lsm2-l3-24				OBJECT IDENTIFIER ::= {buffalo 8} -- BUFFALO LSM2-L3-24
lsm-10-100-8w			OBJECT IDENTIFIER ::= {buffalo 9} -- BUFFALO LSM10/100-8W
lpv2-usb-tx1			OBJECT IDENTIFIER ::= {buffalo 10} -- BUFFALO LPV2-USB-TX1
bs-2024-gm				OBJECT IDENTIFIER ::= {buffalo 11} -- BUFFALO BS-2024GM
bs-poe-2024gm			OBJECT IDENTIFIER ::= {buffalo 12} -- BUFFALO BS-POE-2024GM
lpv3-u2					OBJECT IDENTIFIER ::= {buffalo 13} -- BUFFALO LPV3-U2/LPV3-U2S
bs-poe-2008m			OBJECT IDENTIFIER ::= {buffalo 14} -- BUFFALO BS-POE-2008M
bpv-pd-tx1				OBJECT IDENTIFIER ::= {buffalo 15} -- BUFFALO BPV-PD-TX1
bs-2108m				OBJECT IDENTIFIER ::= {buffalo 16} -- BUFFALO BS-2108M
bs-2016m				OBJECT IDENTIFIER ::= {buffalo 17} -- BUFFALO BS-2016M
airstationPro			OBJECT IDENTIFIER ::= {buffalo 18} -- BUFFALO AirStationPro - WAPM-HP-AM54G54/APG300N/AG300N
lpv3-u2-g54				OBJECT IDENTIFIER ::= {buffalo 19} -- BUFFALO LPV3-U2-G54
bs-g2016mr				OBJECT IDENTIFIER ::= {buffalo 20} -- BUFFALO BS-G2016MR
bs-g2024mr				OBJECT IDENTIFIER ::= {buffalo 21} -- BUFFALO BS-G2024MR
bs-g3024mr				OBJECT IDENTIFIER ::= {buffalo 22} -- BUFFALO BS-G3024MR
bs-g2008mr				OBJECT IDENTIFIER ::= {buffalo 24} -- BUFFALO BS-G2008MR
businessSwitch			OBJECT IDENTIFIER ::= {buffalo 25} -- BS-G Series - BS-G2008/BS-G2016MR/BS-G3024MR)
lpv3-tx1				OBJECT IDENTIFIER ::= {buffalo 26} -- BUFFALO LPV3-TX1
teraStation				OBJECT IDENTIFIER ::= {buffalo 27} -- BUFFALO TeraStation Series
-- **************************************************************************

END

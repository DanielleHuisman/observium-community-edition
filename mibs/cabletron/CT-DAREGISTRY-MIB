CT-DAREGISTRY-MIB DEFINITIONS ::= BEGIN
IMPORTS
--   DisplayString
--            FROM SNMPv2-TC-v1
    TimeTicks
            FROM RFC1155-SMI
    OBJECT-TYPE
            FROM RFC-1212
    cabletron
            FROM CTRON-OIDS;

 ctSSA   OBJECT IDENTIFIER ::= { cabletron 4497 }

--    SMI TimeTicks
--    SMI OBJECT-TYPE

    DisplayString ::= OCTET STRING

  ctDARegistryTable OBJECT-TYPE
       SYNTAX      SEQUENCE OF CtDARegistryEntry
       ACCESS      not-accessible
       STATUS      mandatory
       DESCRIPTION
               "A list of Demand Access WAN firmware components."
       ::= { ctSSA 1}

 ctDARegistryEntry OBJECT-TYPE
       SYNTAX      CtDARegistryEntry
       ACCESS  not-accessible
       STATUS      mandatory
       DESCRIPTION
               "An entry containing management information applicable
               to a particular subsystem."
       INDEX   { ctDARegistryIndex, ctDARegistryInstance }
       ::= { ctDARegistryTable 1 }

   CtDARegistryEntry ::=
       SEQUENCE {
           ctDARegistryIndex                 INTEGER,
           ctDARegistryInstance              INTEGER,
           ctDARegistryAdminStatus           INTEGER,
           ctDARegistryOperStatus            INTEGER,
           ctDARegistryLastChange            TimeTicks,
           ctDARegistryDescr                 DisplayString
       }


   ctDARegistryIndex OBJECT-TYPE
       SYNTAX      INTEGER(0..2147483647)
       ACCESS  read-only
       STATUS      mandatory
       DESCRIPTION
               "This is the category for this object."
       ::= { ctDARegistryEntry 1 }

   ctDARegistryInstance OBJECT-TYPE
       SYNTAX      INTEGER(0..2147483647)
       ACCESS      read-only
       STATUS      mandatory
       DESCRIPTION
               "This is a unique instance within the category for this
object."
       ::= { ctDARegistryEntry 2 }

   ctDARegistryAdminStatus OBJECT-TYPE
       SYNTAX  INTEGER {
                   up(1),       -- ready execute
                   down(2),
                   testing(3)   -- in some test mode
               }
       ACCESS  read-write
       STATUS      mandatory
       DESCRIPTION
               "The desired state of the subsystem.  The testing(3)
               state indicates that no operational functions can be
               passed.  When a managed system initializes, all
               subsystems start with ctDARegistryAdminStatus in the up(1)
               state.  As a result of either explicit management
               action or per configuration information retained by
               the managed system, ctDARegistryAdminStatus is then changed
to
               either the dowm(2) or testing(3) states (or remains in
               the up(1) state)."
       ::= { ctDARegistryEntry 3 }

   ctDARegistryOperStatus OBJECT-TYPE
       SYNTAX  INTEGER {
                   up(1),             -- ready to pass packets
                   down(2),
                   testing(3),        -- in some test mode
                   unknown(4),        -- status can not be determined
                                      -- for some reason.
                   dormant(5),        -- waiting for a lower layer
                   notPresent(6),     --
                   lowerLayerDown(7)  --
               }
       ACCESS  read-only
       STATUS      mandatory
       DESCRIPTION
               "The mandatory operational state of the subsystem.  The
               testing(3) state indicates that no operational functions
               can be passed.  If ctDARegistryAdminStatus is down(2) then
               ctDARegistryOperStatus should be down(2).  If
ctDARegistryAdminStatus is
               changed to up(1) then ctDARegistryOperStatus should change
to
               up(1) if the subsystem is ready to function; it should
change to
               dormant(5) if the subsystem is waiting for external
               actions; it should remain in the down(2)
               state if and only if there is a fault that prevents if
               from going to the up(1) state. The notPresent state is a
refinement
               on the down state which indicates that the relevant
interface is
               down specifically because some component (typically, a
hardware
               component) is not present in the managed system.
               The lowerLayerDown state is also a refinement on the down
state.
               This new state indicates that this system runs on top of
one or
               more interfaces (see ifStackTable) and that this system
is
               down specifically because one or more of these
lower-layer interfaces
               are down.       "
       ::= { ctDARegistryEntry 4 }

   ctDARegistryLastChange OBJECT-TYPE
       SYNTAX      TimeTicks
       ACCESS  read-only
       STATUS      mandatory
       DESCRIPTION
               "The value of sysUpTime at the time the subsystem
               entered its mandatory operational state.  If the
mandatory
               state was entered prior to the last re-initialization
               of the local network management subsystem, then this
               object contains a zero value."
       ::= { ctDARegistryEntry 5 }

   ctDARegistryDescr OBJECT-TYPE
       SYNTAX      DisplayString (SIZE (0..255))
       ACCESS  read-only
       STATUS      mandatory
       DESCRIPTION
               "A textual string that identifies the subsystem."
       ::= { ctDARegistryEntry 6 }


END

CT-DAWANCONN-MIB DEFINITIONS ::= BEGIN

--  ct-dawanconn-mib
--  Revision: 0.0.01
--  Date: June 29, 1999
--              
--  Cabletron Systems, Inc.
--  35 Industrial Way, P.O. Box 5005
--  Rochester, NH 03867-0505
--  (603) 332-9400
--  support@ctron.com

--  This module provides authoritative definitions for the
--  WAN
--
--  This module will be extended, as required.
--

--  Cabletron Systems reserves the right to make changes in
--  specification and other information contained in this document
--  without prior notice.  The reader should consult Cabletron Systems
--  to determine whether any such changes have been made.
--
--  In no event shall Cabletron Systems be liable for any incidental,
--  indirect, special, or consequential damages whatsoever (including
--  but not limited to lost profits) arising out of or related to this
--  document or the information contained in it, even if Cabletron
--  Systems has been advised of, known, or should have known, the
--  possibility of such damages.
--
--  Cabletron grants vendors, end-users, and other interested parties
--  a non-exclusive license to use this Specification in connection
--  with the management of Cabletron products.
--  Copyright June 99 Cabletron Systems
--
IMPORTS
    
    TimeStamp
            FROM SNMPv2-TC

    Gauge
            FROM RFC1155-SMI
    OBJECT-TYPE
            FROM RFC-1212
    
    cabletron
            FROM CTRON-OIDS;
   
   ctSSA OBJECT IDENTIFIER ::= { cabletron 4497 }
   
   daWanConnection OBJECT IDENTIFIER ::= {ctSSA 17}
      
   DisplayString ::= OCTET STRING

   daWanNumConnections OBJECT-TYPE
       SYNTAX      INTEGER(0..2147483647)
       ACCESS      read-only
       STATUS      mandatory
       DESCRIPTION
               "This is the total number of connection objects currently
                in the system."   
       ::= { daWanConnection 1 }

   daWanConnectionTable OBJECT-TYPE
       SYNTAX      SEQUENCE OF DaWanConnectionEntry
       ACCESS      not-accessible
       STATUS      mandatory
       DESCRIPTION
               "A list of Demand Access remote WAN connections"
       ::= { daWanConnection 2}

   daWanConnectionEntry OBJECT-TYPE
       SYNTAX      DaWanConnectionEntry
       ACCESS      not-accessible
       STATUS      mandatory
       DESCRIPTION
               "An entry containing wan connection information
                and statistics."
       INDEX   { daWanConnectionIndex }
       ::= { daWanConnectionTable 1 }

   DaWanConnectionEntry ::=
       SEQUENCE {
           daWanConnectionIndex                    INTEGER,
           daWanConnectionIfIndex                  INTEGER,
           daWanConnectionState                    INTEGER,
           daWanConnectionConnectControl           INTEGER,
           daWanConnectionConnectType              INTEGER,
           daWanConnectionDeviceIndex              INTEGER,
           daWanConnectionConnectSpeed             Gauge,
           daWanConnectionPeerAddress              DisplayString,
           daWanConnectionLocalAddress             DisplayString,
           daWanConnectionSubAddress               DisplayString,
           daWanConnectionInfoType                 INTEGER,
           daWanConnectionChargedUnits             INTEGER,
           daWanConnectionConnectTime              TimeStamp,
           daWanConnectionConnectDirection         INTEGER,
           daWanConnectionDisconnectTime       TimeStamp,
           daWanConnectionDisconnectDirection  INTEGER,
           daWanConnectionDisconnectCause      INTEGER,
           daWanConnectionDisconnectText       DisplayString
       }
   
   daWanConnectionIndex OBJECT-TYPE
       SYNTAX      INTEGER(0..2147483647)
       ACCESS      read-only
       STATUS      mandatory
       DESCRIPTION
               "This is the index into this table.  This index
                uniquely identifies the Connection."
       ::= { daWanConnectionEntry 1 }

   daWanConnectionIfIndex OBJECT-TYPE        
       SYNTAX      INTEGER
       ACCESS      read-only
       STATUS      mandatory
       DESCRIPTION
               "This is the ifIndex value of the wan connection group.
                If the ifIndex value is unknown, the value of this object
                will be zero."        
       ::= { daWanConnectionEntry 2 }

   daWanConnectionState OBJECT-TYPE
       SYNTAX INTEGER {
      inactive(1),      -- the call is inactive
      connecting(2),    -- an outbound call attempt is being made
      connected(3),     -- an incoming call is connected and is being validated
      active(4),        -- the call is active
      disconnecting(5), -- an outgoing disconnect is being processed
      disconnected(6)   -- an incoming disconnect is being processed
        }
       ACCESS      read-only
       STATUS      mandatory
       DESCRIPTION
               "This is the state of the Connection."
       ::= { daWanConnectionEntry 3 }

   daWanConnectionConnectControl OBJECT-TYPE
       SYNTAX      INTEGER 
                     {
                        connect(1),      -- initiates the connect action
                        disconnect(2),   -- initiates the disconnect action
                        unknown(3)       -- description
                     }
       ACCESS      read-write
       STATUS      mandatory
       DESCRIPTION
               "This object controls the desired state of the wan Connection.  
                Setting this object to connect(1) will initiate the 
                set of actions to bring the wan Connection to the active 
                state.  Only set the object to connect(1) when the current
                value of daWanConnectionState is inactive.  Setting this object
                to disconnect(2) will initiate the set of actions to bring 
                the wan Connection to the inactive state.  Only set this object 
                to disconnect(2) when the daWanConnectionState is active.
                After setting the Connection to connect(1) or disconnect(2), 
                refer to daWanConnectionState to determine the state of the 
                wan Connection.  Queries to daWanConnectionConnectControl return 
                unknown results."
       ::= { daWanConnectionEntry 4 }


   daWanConnectionConnectType OBJECT-TYPE
       SYNTAX      INTEGER{
                        digitalCircuit(1),
                        analogCircuit(2)
                        }
       ACCESS      read-only
       STATUS      mandatory
       DESCRIPTION
               "This specifies the type of the wan connection."
       ::= { daWanConnectionEntry 5 }
   
   daWanConnectionDeviceIndex OBJECT-TYPE
       SYNTAX      INTEGER
       ACCESS      read-only
       STATUS      mandatory
       DESCRIPTION
               "This is the index of the device that is associated with this connection.
                This value will be zero if there is no device associated with this device."
       ::= { daWanConnectionEntry 6 }

   daWanConnectionConnectSpeed OBJECT-TYPE        
       SYNTAX      Gauge
       ACCESS      read-only
       STATUS      mandatory
       DESCRIPTION
            "The information transfer speed in bits/second when calling
             this peer.  The detailed media specific information, e.g. information
             type and information transfer rate for ISDN circuits, has to be 
             extracted from this object.  If the transfer speed to be used is 
             unknown the value of this object may be zero."      
       ::= { daWanConnectionEntry 7 }
       
   daWanConnectionLocalAddress OBJECT-TYPE        
       SYNTAX      DisplayString (SIZE (0..255))
       ACCESS      read-only
       STATUS      mandatory
       DESCRIPTION
            "Call Address at which the connection will originate from.  Think of this
             as the set of characters following 'ATDT ' or the 'phone number' included in 
             a D channel call request.  The structure of this information will be 
             switch type specific.  If there is no address information required
             for reaching the peer, i.e., for leased lines, this object will be a 
             zero length string."  
       DEFVAL      { ''H }     -- the empty string
       ::= { daWanConnectionEntry 8 }

   daWanConnectionPeerAddress OBJECT-TYPE        
       SYNTAX      DisplayString (SIZE (0..255))
       ACCESS      read-only
       STATUS      mandatory
       DESCRIPTION
            "Calling Party Number information element, as for example passed in an 
             ISDN SETUP message by a PBX or switch, for incoming calls.  This address
             can be used to identify the peer.  If this address is either unknown or 
             identical to daWanConnectionLocalAddress, this object will be
             a zero length string." 
        ::= { daWanConnectionEntry 9 }
   
   daWanConnectionSubAddress OBJECT-TYPE        
       SYNTAX      DisplayString (SIZE (0..255))
       ACCESS      read-only
       STATUS      mandatory
       DESCRIPTION
               "Subaddress at which the connection will originate from.  If the subaddress is 
                undefined for the given media or unused, then the value is zero."
       DEFVAL      { ''H }     -- the empty string
       ::= { daWanConnectionEntry 10 }
       
   daWanConnectionInfoType OBJECT-TYPE        
        SYNTAX INTEGER 
         {
          other(1),
          speech(2),
          unrestrictedDigital(3),     -- 64k/s data
          unrestrictedDigital56(4),   -- with 56k rate adaption
          restrictedDigital(5),
          audio31(6),                 -- 3.1 kHz audio
          audio7(7),                  -- 7 kHz audio   
          video(8),
          packetSwitched(9),           
          fax(10)
         }
        ACCESS      read-only 
        STATUS      mandatory
        DESCRIPTION
            "The Information Transfer Capability to be used for this connection.
             speech(2) refers to a non-data connection, whereas audio31(6) and 
             audio7(7) refer to data mode connections."    
        DEFVAL      { other }
        ::= { daWanConnectionEntry 11 }

   daWanConnectionChargedUnits OBJECT-TYPE
       SYNTAX      INTEGER
       ACCESS      read-only
       STATUS      mandatory
       DESCRIPTION
            "The number of charged units for this connection.  For incoming calls or 
             if charging information is not supplied by the switch, the value of 
             this object will be zero."     
       ::= { daWanConnectionEntry 12 }
    
    daWanConnectionConnectTime OBJECT-TYPE
       SYNTAX      TimeStamp
       ACCESS      read-only
       STATUS      mandatory
       DESCRIPTION
            "The value of sysUpTime when this connection was completed.  This 
             object will be updated whenever a call is completed."
        ::= { daWanConnectionEntry 13 }

   daWanConnectionConnectDirection OBJECT-TYPE
        SYNTAX      INTEGER 
                      {
                        in(1),    
                        out(2)
                      }       
       ACCESS   read-only
       STATUS   mandatory
       DESCRIPTION
            "The direction from which this connect occurred."
        ::= { daWanConnectionEntry 14 }
   
   daWanConnectionDisconnectTime OBJECT-TYPE
       SYNTAX      TimeStamp
       ACCESS      read-only
       STATUS      mandatory
       DESCRIPTION
            "The value of sysUpTime when this call was disconnected.  This object
             will be updated whenever a call is disconnected."
        ::= { daWanConnectionEntry 15 }

   
   daWanConnectionDisconnectDirection OBJECT-TYPE
        SYNTAX      INTEGER 
                      {
                        in(1),    
                        out(2)
                      }       
       ACCESS   read-only
       STATUS   mandatory
       DESCRIPTION
            "The direction from which this disconnect occurred."
       ::= { daWanConnectionEntry 16 }

   daWanConnectionDisconnectCause OBJECT-TYPE
       SYNTAX   INTEGER       
       ACCESS   read-only
       STATUS   mandatory
       DESCRIPTION
            "The encoded network cause value associated with this call. This object 
             will be updated whenever a call is started or cleared.  The value of this 
             object will depend on the interface type as well as on the protocol and 
             protocol version being used on this interface."
       ::= { daWanConnectionEntry 17 }

   daWanConnectionDisconnectText OBJECT-TYPE
       SYNTAX   DisplayString (SIZE (0..255))
       ACCESS   read-only
       STATUS   mandatory
       DESCRIPTION
            "ASCII text describing the reason for this call termination.  This object 
             exists because it would be impossible for a management station to store all 
             possible cause values for all types of interfaces.  It should be used only if
             a management station is unable to decode the value of
             daWanConnectionDisconnectCause.  This object will be updated whenever a 
             call is started or cleared."       
       ::= { daWanConnectionEntry 18 }
       
END

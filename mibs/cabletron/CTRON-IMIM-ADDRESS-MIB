CTRON-IMIM-ADDRESS-MIB DEFINITIONS ::= BEGIN

	--  Cabletron intelligent MIM address MIB
	--  Revision: 1.00.00
	--  Part Number: 2170995
	--  Date: March 3, 1994

	--  Cabletron Systems, Inc.
	--  35 Industrial Way, P.O. Box 5005
	--  Rochester, NH 03867-0505
	--  (603) 332-9400
	--  support@ctron.com

	--  This module provides authoritative definitions for part
	--  of the naming tree below:
	--
	--		cabletron { enterprises 52 }
	--
	--  This module will be extended, as additional sub-sections
	--  of this naming tree are defined.
	--

	--  Cabletron Systems reserves the right to make changes in 
	--  specification and other information contained in this document 
	--  without prior notice.  The reader should consult Cabletron Systems
	--  to determine whether any such changes have been made.
	--
	--  In no event shall Cabletron Systems be liable for any incidental, 
	--  indirect, special, or consequential damages whatsoever (including 
	--  but not limited to lost profits) arising out of or related to this
	--  document or the information contained in it, even if Cabletron
	--  Systems has been advised of, known, or should have known, the 
	--  possibility of such damages.
	--
	--  Cabletron grants vendors, end-users, and other interested parties
	--  a non-exclusive license to use this Specification in connection
	--  with the management of Cabletron products.

	--  Copyright August 94 Cabletron Systems

--	This MIB is also known as the Backplane protocol MIB.  It provides
--	a list of MAC and IP addresses known for each physical module within
--	the chassis.  Physical modules are identified by the slot in which
--	they reside.

IMPORTS
	enterprises		FROM RFC1155-SMI
	OBJECT-TYPE		FROM RFC-1212;
 
cabletron		OBJECT IDENTIFIER ::= { enterprises 52 }
commsDevice		OBJECT IDENTIFIER ::= { cabletron 1 }
subsystem		OBJECT IDENTIFIER ::= { commsDevice 6 }
backplaneProtocol	OBJECT IDENTIFIER ::= { subsystem 5 }

-- Groups within the imim address MIB

imimAddress		OBJECT IDENTIFIER ::= { backplaneProtocol 1 }

 
-- The imimAddress group implementation of this group is mandatory. 
 
imimAddressTable	OBJECT-TYPE
SYNTAX	SEQUENCE OF ImimAddressEntry
ACCESS	not-accessible
STATUS	mandatory
DESCRIPTION
	"This table provides the IP and MAC address for each IMIM within a
	MMAC chassis."
 ::= { imimAddress 1 }

imimAddressEntry	OBJECT-TYPE
SYNTAX	ImimAddressEntry
ACCESS	not-accessible
STATUS	mandatory
DESCRIPTION
	"A specific IMIM address entry."
INDEX		{ imimAddressChassisSlot }
 ::= { imimAddressTable 1 }
 
ImimAddressEntry ::=
SEQUENCE {
 imimAddressChassisSlot
 	INTEGER,
 imimAddressMAC
	OCTET STRING,
 imimAddressIP
	OCTET STRING
}
 
imimAddressChassisSlot	OBJECT-TYPE
SYNTAX	INTEGER (1..8)
ACCESS	read-only
STATUS	mandatory
DESCRIPTION
	"The chassis slot number where the intelligent MIM resides
     to which this entry pertains."
 ::= { imimAddressEntry 1 }
 
imimAddressMAC	OBJECT-TYPE
SYNTAX	OCTET STRING (SIZE (6))
ACCESS	read-only
STATUS	mandatory
DESCRIPTION
 	"The MAC address of the intelligent MIM residing in the slot
 	 indexed by imimAddressChassisSlot."
 ::= { imimAddressEntry 2 }
 
imimAddressIP	OBJECT-TYPE
SYNTAX	OCTET STRING (SIZE (4))
ACCESS	read-only
STATUS	mandatory
DESCRIPTION
 	"The IP address of the intelligent MIM residing in the slot
 	 indexed by imimAddressChassisSlot."
 ::= { imimAddressEntry 3 }
 


backplaneHeartbeat      OBJECT-TYPE
SYNTAX	INTEGER {
        heartBeatPresent (1),
        heartBeatAbsent  (2),
        notSupported     (3)
        }

ACCESS	read-only
STATUS	mandatory
DESCRIPTION
 	"This object reports on the status of the backplane protocol heartbeat.
        This object is applicable only to intelligent MIMs residing in an MMAC
        chassis.

	If the heartbeat is detected from the management module (i.e. the
	intelligent MIM is in communication with the management module) then
        the value returned by this object is heartBeatPresent(1).

	If the heartbeat is not present, then the returned value is
	heartBeatAbsent(2).

	On intelligent MIMs that do not support the backplane protocol and
	management modules the value notSupported(3) is returned."
 ::= { imimAddress 2 }

END

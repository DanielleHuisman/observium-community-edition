--  nb55 MIB	EFDMIM SNMP MIB
	--  Revision:	2.06.00
	--  Part Number:  2170569
	--  Date: 	May 17, 1993

	--  Cabletron Systems, Inc.
	--  35 Industrial Way, P.O. Box 5005
	--  Rochester, NH 03867-0505
	--  (603) 332-9400
	--  support@ctron.com

	--  This module provides authoritative definitions for part
	--  of the naming tree below:
	--
	--		cabletron { enterprises 52 }
	--
	--  This module will be extended, as additional sub-sections
	--  of this naming tree are defined.
	--

	--  Cabletron Systems reserves the right to make changes in 
	--  specification and other information contained in this document 
	--  without prior notice.  The reader should consult Cabletron Systems
	--  to determine whether any such changes have been made.
	--
	--  In no event shall Cabletron Systems be liable for any incidental, 
	--  indirect, special, or consequential damages whatsoever (including 
	--  but not limited to lost profits) arising out of or related to this
	--  document or the information contained in it, even if Cabletron
	--  Systems has been advised of, known, or should have known, the 
	--  possibility of such damages.
	--
	--  Cabletron grants vendors, end-users, and other interested parties
	--  a non-exclusive license to use this Specification in connection
	--  with the management of Cabletron products.

	--  Copyright August 92 Cabletron Systems


 --
 --       This is the SNMP mib for Cabletron's EFDMIM.  The EFDMIM is sn
 --  ethernet to FDDI bridge that can run in either encapsulating or
 --  translating modes.  There are four types of basic data that can be
 --  accessed on the EFDMIM, Ring data, Port data, Phy data, and Device
 --  data.  Ring data contains information about each node on the FDDI ring.
 --  Port data contains information about each bridging port.  Phy data
 --  contains information about each FDDI PHY on the bridge, and Device data
 --  contains information about the bridge. Please note that this is NOT a 
 --  published mib!
 --
 -- ========================== Revision History ============================
 -- Revision  Change made to the revision:
 -- 2.5       A few syntax declarations were incorrect in 2.5.  The 
 -- 		  following mibs have been modified:
 --           efdmimBdgPortReceivedPkts    ( from Counter to INTEGER)
 --           efdmimBdgPortFilteredPkts    ( from Counter to INTEGER)
 --           efdmimBdgPortForwardedkts    ( from Counter to INTEGER)
 --           efdmimBdgPortTransmittedPkts ( from Counter to INTEGER)
 --           efdmimBdgPortErrorPkts       ( from Counter to INTEGER)
 --           efdmimRingMastePhys          ( from Counter to INTEGER)
 --           efdmimRingNonmastePhys       ( from Counter to INTEGER)
 --           efdmimDeviceReceivedPkts     ( from Counter to INTEGER)
 --           efdmimDeviceFilteredPkts     ( from Counter to INTEGER)
 --           efdmimDeviceForwardedkts     ( from Counter to INTEGER)
 --           efdmimDeviceTransmittedPkts  ( from Counter to INTEGER)
 --           efdmimRingUpTime             ( from INTEGER to Counter)
 --
 -- 2.4       To get the efdmim mib to compile with mosy & mib2schema, I
 --           changed all the enumerated 'false (0)' to 'false (2)'; the
 --           enumerated 'encapuslation (0)' to 'encapsulation (1); and
 --           the enumerated 'translation (1) to 'translation (2).
 --
 -- ======================== End of Revision History =======================


EFDMIM-MIB  DEFINITIONS  ::= BEGIN


IMPORTS        OBJECT-TYPE, Counter, enterprises  FROM RFC1155-SMI;

cabletron      OBJECT IDENTIFIER ::= { enterprises 52 }
commsDevice    OBJECT IDENTIFIER ::= { cabletron    1 }
subsystem      OBJECT IDENTIFIER ::= { commsDevice  6 }
nb55           OBJECT IDENTIFIER ::= { subsystem    4 }
rev1           OBJECT IDENTIFIER ::= { nb55         1 }




    efdmimRingTable     OBJECT-TYPE
          --OID         1.3.6.1.4.1.52.1.6.4.1.1
          SYNTAX        SEQUENCE OF EfdmimRingEntry
          ACCESS        not-accessible
          STATUS        mandatory
          DESCRIPTION   "An ordered list of fddi nodes found on the
                         Fddi Ring."
    ::= { rev1 1 }



    efdmimRingEntry   OBJECT-TYPE
          --OID         1.3.6.1.4.1.52.1.6.4.1.1.1
          SYNTAX        EfdmimRingEntry
          ACCESS        not-accessible
          STATUS        mandatory
          DESCRIPTION   "An fddi ring entry containing information common 
                         to all stations in a token path. All FDDI ring 
                         Entry elements have an instance id made up of an 
                         index followed by a canonical FDDI station 
                         address.  The indexes are ordered sequentially 1 
                         to n, and the corresponding FDDI addresses are 
                         ordered in reverse token flow.  Consider the 
                         following example: 

                          --->---[1]  00-00-1D-00-00-04
                          |              |  (arrows show token flow)
                          |              V
                          |      [3]  00-00-1D-00-00-01
                          |              |
                          |              V
                          |      [2]  00-00-1D-00-00-03
                          |              |
                          ----<----------/
                        
                       A get_next request with instance id = 0
                       will return  1.0.0.1D.0.0.4
                      
                       A get_next request with 
                       instance id= 1.0.0.1D.0.0.4
                       will return 2.0.0.1D.0.0.3
                     
                       A get_next request with
                       instance id= 2.0.0.1D.0.0.1
                       will return 3.0.0.1D.0.0.1
                       "
    ::= { efdmimRingTable 1 }



    EfdmimRingEntry ::=
      SEQUENCE {
               efdmimRingUpstreamMac    OCTET STRING,
               efdmimRingNodeClass      INTEGER,
               efdmimRingMacs           Counter,
               efdmimRingNonMasterPhys  Counter,
               efdmimRingMasterPhys     Counter,
               efdmimRingTopology       INTEGER,
               efdmimRingDuplicate      INTEGER,
               efdmimRingMacAddress     OCTET STRING
               }
       


    efdmimRingUpstreamMac    OBJECT-TYPE
          --OID          1.3.6.1.4.1.52.1.6.4.1.1.1.1
          SYNTAX         OCTET STRING  
          ACCESS         read-only
          STATUS         mandatory
          DESCRIPTION    "This is the 6 octet canonical representation of
                          the upstream neighbor's address.  The upstream
                          neighbor is the last MAC to receive the token
                          before this MAC. 
                          Please Note:   SMT Rev 6.2 and under 
                          specify the unknown address as 00-00-00-00-00-00. SMT 
                          revisions after 6.2 specify the unknown address as 
                          00-00-F8-00-00-00. "
    ::= { efdmimRingEntry 1 }



    efdmimRingNodeClass      OBJECT-TYPE
          --OID          1.3.6.1.4.1.52.1.6.4.1.1.1.2
          SYNTAX         INTEGER
          ACCESS         read-only
          STATUS         mandatory
          DESCRIPTION    "Reports if the node is a station or
                          a concentrator.
                          Legal values are:
                               station      (0)
                               concentrator (1)
                          "
    ::= { efdmimRingEntry 2 }



    efdmimRingMacs            OBJECT-TYPE
          --OID          1.3.6.1.4.1.52.1.6.4.1.1.1.3
          SYNTAX         Counter
          ACCESS         read-only
          STATUS         mandatory
          DESCRIPTION    "The number of MACs on this FDDI node."
    ::= { efdmimRingEntry 3 }

     

    efdmimRingNonMasterPhys OBJECT-TYPE
          --OID          1.3.6.1.4.1.52.1.6.4.1.1.1.4
          SYNTAX         INTEGER
          ACCESS         read-only
          STATUS         mandatory
          DESCRIPTION    "The sum of the all A-Ports,
                          B-Ports, and S-Ports on this node."
    ::= { efdmimRingEntry 4 }


     
    efdmimRingMasterPhys    OBJECT-TYPE
          --OID          1.3.6.1.4.1.52.1.6.4.1.1.1.5
          SYNTAX         INTEGER
          ACCESS         read-only
          STATUS         mandatory
          DESCRIPTION    "The number of master ports on this node.
                          Results will range from 0 to 255."
    ::= { efdmimRingEntry 5 }


     
    efdmimRingTopology        OBJECT-TYPE
          --OID          1.3.6.1.4.1.52.1.6.4.1.1.1.6
          SYNTAX         INTEGER
          ACCESS         read-only
          STATUS         mandatory
          DESCRIPTION    "A bit-mapped representation of the current state of 
                         the node. 

                            if this state:         Add 2**n where n=
                            Wrapped Node:             0
                            Unattached Concentrator:  1
                            A-A twisted ring:         2
                            B-B twisted ring:         3
                            Rooted Station:           4
                            SRF supported             5
                          
                          Wrapped Node: set when the node's cf-state is 
                                        Wrap-A, Wrap-B, Wrap-S, or Wrap-
                                        AB.
                          Unattached Concentrator:
                                        set when a concentrator 
                                        has no active A, B, or S ports.
                          A-A Twisted ring: A twisted ring has occurred 
                                        because this node's A port has  
                                        been connected to another port.
                          B-B Twisted ring: A twisted ring has occurred 
                                        because this node's B port has 
                                        been connected to another B 
                                        port.
                          Rooted Station:  This is a station who's A, B 
                                        and S ports are NOT active in 
                                        tree mode. If any A, B, or S  
                                        ports are active in TREE mode, 
                                        this is FALSE.
                          SRF supported: This node adheres to the status 
                                        reporting frame protocol. "
    ::= { efdmimRingEntry 6 }


     
    efdmimRingDuplicate       OBJECT-TYPE
          --OID          1.3.6.1.4.1.52.1.6.4.1.1.1.7
          SYNTAX         INTEGER
          ACCESS         read-only
          STATUS         mandatory
          DESCRIPTION    "A bit-mapped representation of duplicate 
                          address information.

                          if this state:         Add 2**n where n=
                          My Duplicate:                0
                          UNA Duplicate:               1
                          
                          My Duplicate:  This node has determined that it's 
                          MAC address is the same as the MAC address for 
                          another node on the ring. UNA Duplicate: The 
                          upstream neighbor of this node has determined that 
                          it's MAC address is the same as the MAC address for 
                          another node on the ring. "
    ::= { efdmimRingEntry 7 }


   efdmimRingMacAddress       OBJECT-TYPE
          --OID          1.3.6.1.4.1.52.1.6.4.1.1.1.8
          SYNTAX         OCTET STRING
          ACCESS         read-only
          STATUS         mandatory
          DESCRIPTION    "A canonical representation of the MAC address."  
    ::= { efdmimRingEntry 8 }



    efdmimBdgPortTable     OBJECT-TYPE
          --OID         1.3.6.1.4.1.52.1.6.4.1.2
          SYNTAX        SEQUENCE OF EfdmimBdgPortEntry
          ACCESS        not-accessible
          STATUS        mandatory
          DESCRIPTION   "This is a table of items that relate to bridge ports.  
                         Note there are 2 bridge (packet communication) ports 
                         on the EFDMIM, the ethernet port, and the FDDI 
                         port." 
    ::= { rev1 2 }



    efdmimBdgPortEntry   OBJECT-TYPE
          --OID         1.3.6.1.4.1.52.1.6.4.1.2.1
          SYNTAX        EfdmimBdgPortEntry
          ACCESS        not-accessible
          STATUS        mandatory
          DESCRIPTION   "This is an individual entry in the bridge port table.  
                         Note that each entry will contain an instance id of 
                         1 to represent the Ethernet port, and 2 to represent 
                         the FDDI port." 
   ::= { efdmimBdgPortTable 1 }

 

   EfdmimBdgPortEntry  ::=
      SEQUENCE {
                efdmimBdgPortState              OCTET STRING,
                efdmimBdgPortReceivedPkts       Counter,
                efdmimBdgPortFilteredPkts       Counter,
                efdmimBdgPortForwardedPkts      Counter,
                efdmimBdgPortTrasnmittedPkts    Counter,
                efdmimBdgPoerErrorPkts          Counter
               }



   efdmimBdgPortState    OBJECT-TYPE
          --OID         1.3.6.1.4.1.52.1.6.4.1.2.1.1
          SYNTAX        OCTET STRING
          ACCESS        read-only
          STATUS        optional
          DESCRIPTION   "This object is returned only if spanning tree is 
                         enabled on the bridge.  It returns a text string 
                         representing the current state of the port:  
                         'Disabled',  'Listening', 'Learning', 
                         'Forwarding', or 'Blocking'." 
   ::= { efdmimBdgPortEntry 1 }



   efdmimBdgPortReceivedPkts   OBJECT-TYPE
          --OID         1.3.6.1.4.1.52.1.6.4.1.2.1.2
          SYNTAX        INTEGER                      
          ACCESS        read-only
          STATUS        mandatory
          DESCRIPTION   "The number of frames received by the bridge through 
                         this port." 
   ::= { efdmimBdgPortEntry 2 }



   efdmimBdgPortFilteredPkts   OBJECT-TYPE
          --OID         1.3.6.1.4.1.52.1.6.4.1.2.1.3
          SYNTAX        INTEGER                      
          ACCESS        read-only
          STATUS        mandatory
          DESCRIPTION   "The number of frames filtered by the bridge at this 
                         port." 
   ::= { efdmimBdgPortEntry 3 }



   efdmimBdgPortForwardedPkts   OBJECT-TYPE
          --OID         1.3.6.1.4.1.52.1.6.4.1.2.1.4
          SYNTAX        INTEGER                      
          ACCESS        read-only
          STATUS        mandatory
          DESCRIPTION   "The number of frames forwarded by the bridge through 
                         this port." 
   ::= { efdmimBdgPortEntry 4 }



   efdmimBdgPortTransmittedPkts   OBJECT-TYPE
          --OID         1.3.6.1.4.1.52.1.6.4.1.2.1.5
          SYNTAX        INTEGER                      
          ACCESS        read-only
          STATUS        mandatory
          DESCRIPTION   "The number of frames transmitted on this port." 
   ::= { efdmimBdgPortEntry 5 }



   efdmimBdgPortErrorPkts   OBJECT-TYPE
          --OID         1.3.6.1.4.1.52.1.6.4.1.2.1.6
          SYNTAX        INTEGER                      
          ACCESS        read-only
          STATUS        mandatory
          DESCRIPTION   "The number of frame errors detected on this port."
   ::= { efdmimBdgPortEntry 6 }



   efdmimPhyTable     OBJECT-TYPE
          --OID         1.3.6.1.4.1.52.1.6.4.1.3
          SYNTAX        SEQUENCE OF EfdmimPhyEntry
          ACCESS        not-accessible
          STATUS        mandatory
          DESCRIPTION   "This is a table of data that pertains only to phys on 
                         the efdmim." 
   ::= { rev1 3 }



   efdmimPhyEntry   OBJECT-TYPE
          --OID         1.3.6.1.4.1.52.1.6.4.1.3.1
          SYNTAX        EfdmimPhyEntry
          ACCESS        not-accessible
          STATUS        mandatory
          DESCRIPTION   "This is a specific entry in the efdmimPhyTable that 
                         represents a specific attribute of a phy.  Note that 
                         phy entries that refer to PHY-A will use an instance 
                         identifier of 1 and phy entries that refer to PHY-B 
                         will use an instance identifier of 2." 
   ::= { efdmimPhyTable 1 }


 
   EfdmimPhyEntry  ::=
         SEQUENCE {
                  efdmimPhyWithold   INTEGER
                  }


   efdmimPhyWithold    OBJECT-TYPE
          --OID         1.3.6.1.4.1.52.1.6.4.1.3.1.1
          SYNTAX        INTEGER
          ACCESS        read-only
          STATUS        mandatory
          DESCRIPTION   "Describes if the phy is enabled but not allowed to be 
                         used due to a topology problem.
                         Legal values are:
                              none                  (0)  - PHY can be used
                              withold-because-M-M   (1)  - Don't use PHY
                              withold-because-Other (2)  - Don't use PHY
                         "
   ::= { efdmimPhyEntry 1 }



   efdmimDeviceStatus    OBJECT-TYPE
          --OID        1.3.6.1.4.1.52.1.6.4.1.20
          SYNTAX       OCTET STRING                      
          ACCESS        read-only
          STATUS        mandatory
          DESCRIPTION   "This is an Ascii string representation of the 
                         station's status. Responses include 'ON-LINE', 
                         'STAND BY', and 'DISABLED'." 
   ::= { rev1 20 }



   efdmimDeviceBdgName   OBJECT-TYPE
          --OID         1.3.6.1.4.1.52.1.6.4.1.21
          SYNTAX        OCTET STRING                        
          ACCESS        read-write
          STATUS        mandatory
          DESCRIPTION   "This is a user-defined name for the bridge. The name 
                         may contain up to 32 characters." 
   ::= { rev1 21 }



   efdmimDeviceType    OBJECT-TYPE
          --OID         1.3.6.1.4.1.52.1.6.4.1.22
          SYNTAX        OCTET STRING             
          ACCESS        read-only
          STATUS        mandatory
          DESCRIPTION   "This represents the type of bridge this is. The 
                         EFDMIM will always respond with 'EFDMIM'. " 
   ::= { rev1 22 }



   efdmimDeviceVersion    OBJECT-TYPE
          --OID         1.3.6.1.4.1.52.1.6.4.1.23
          SYNTAX        OCTET STRING                    
          ACCESS        read-only
          STATUS        mandatory
          DESCRIPTION   "A text string representing the firmware version 
                         installed in the bridge. " 
   ::= { rev1 23 }



   efdmimDeviceLocation    OBJECT-TYPE
          --OID         1.3.6.1.4.1.52.1.6.4.1.24
          SYNTAX        OCTET STRING                      
          ACCESS        read-write
          STATUS        mandatory
          DESCRIPTION   "A user defined name used to represent the location of 
                         the bridge. "                                          
   ::= { rev1 24 }



   efdmimDeviceUptime    OBJECT-TYPE
          --OID         1.3.6.1.4.1.52.1.6.4.1.25
          SYNTAX        Counter                      
          ACCESS        read-only
          STATUS        mandatory
          DESCRIPTION   "The number of seconds that have elapsed since the 
                         bridge reset or initialized. " 
   ::= { rev1 25 }



   efdmimDeviceDisableBridge    OBJECT-TYPE
          --OID          1.3.6.1.4.1.52.1.6.4.1.26
          SYNTAX         INTEGER
                              {
                              true  (1),
                              false (2)
                              }
          ACCESS        read-write
          STATUS        mandatory
          DESCRIPTION   "States whether or not the bridge is disabled.  To 
                         disable the bridge, set this value to 1.  To 
                         enable the bridge, set this value to 0. "
   ::= { rev1 26 }



   efdmimDeviceResetCounters   OBJECT-TYPE
          --OID          1.3.6.1.4.1.52.1.6.4.1.27
          SYNTAX         INTEGER
                              {
                              true  (1)
                              }
          ACCESS        write-only
          STATUS        mandatory
          DESCRIPTION   "This forces the EFDMIM to reset it's counters. 
                         Note: The efdmim will reset all it's counters 
                         except for the following: 
                             FDDI Frame count
                             FDDI Error count
                             FDDI Lost  count
                             FDDI Ring Oscillations.
                         "
   ::= { rev1 27 }



   efdmimDeviceSwitchSettings   OBJECT-TYPE
          --OID          1.3.6.1.4.1.52.1.6.4.1.28
          SYNTAX         INTEGER
          ACCESS        read-only
          STATUS        mandatory
          DESCRIPTION   "This describes the dip and jumper settings 
                         physically set on the efdmim board.      

                            Switch               multiply 2**n
                              Root                      0
                              Forward Broadcasts        1
                              Spanning Tree             2
                              BPDU Type                 3
                              Bypass                    4
                              Ring Select               5
                              Diagnostics               6
                              Mode                      7
                               
                       Root:               If 0, then spanning tree root is 
                                           selected.  If 1, then spanning 
                                           tree root is NOT selected.
                       Forward Broadcasts: If 0, then all broadcast packets 
                                           are forwarded.  If 1, then all 
                                           broadcasts packets are filtered.
                       Spanning Tree:      If 0, then spanning tree 
                                           facilities are enabled. If 1, 
                                           then spanning tree facilities 
                                           are disabled.
                       BPDU Type:          If 0, then spanning tree uses 
                                           the IEE bridge packet protocol. 
                                           If 1, then spanning tree uses 
                                           the DEC bridge packet protocol. 
                       Bypass:             If 0, then there is an optical 
                                           bypass physically attached to 
                                           the bridge.  If 1, then there is 
                                           not an optical bypass attached 
                                           to the bridge.
                       Ring Select:        If 0, the bridge should attach 
                                           to the primary FDDI ring 
                                           (Through-A mode).  If 1, the 
                                           bridge should attach to the 
                                           secondary FDDI ring (Through-B 
                                           mode). 
                       Diagnostics:        If 0, the bridge is in it's 
                                           normal mode of operation. If 1, 
                                           then the bridge is running self 
                                           diagnostics. 
                       Mode:               If 0, the bridge is an 
                                           encapsulating bridge (talks from 
                                           ethernet to ethernet using FDDI 
                                           only as a backbone). If 1, the 
                                           bridge is a translation bridge ( 
                                           talks ethernet to ethernet, and 
                                           ethernet to FDDI). 
                       "
   ::= { rev1 28 }



   efdmimDeviceReceivedPkts   OBJECT-TYPE
          --OID         1.3.6.1.4.1.52.1.6.4.1.29
          SYNTAX        INTEGER                      
          ACCESS        read-only
          STATUS        mandatory
          DESCRIPTION   "The aggregate number of frames received by the 
                         bridge through it's ports." 
   ::= { rev1 29}



   efdmimDeviceFilteredPkts   OBJECT-TYPE
          --OID         1.3.6.1.4.1.52.1.6.4.1.30
          SYNTAX        INTEGER                      
          ACCESS        read-only
          STATUS        mandatory
          DESCRIPTION   "The aggregate number of frames received and filtered 
                         by the bridge through it's ports." 
   ::= { rev1 30 }



   efdmimDeviceForwardedPkts   OBJECT-TYPE
          --OID         1.3.6.1.4.1.52.1.6.4.1.31
          SYNTAX        INTEGER                      
          ACCESS        read-only
          STATUS        mandatory
          DESCRIPTION   "The aggregate number of frames received and forwarded 
                         by the bridge through it's ports." 
   ::= { rev1 31 }



   efdmimDeviceTransmittedPkts   OBJECT-TYPE
          --OID         1.3.6.1.4.1.52.1.6.4.1.32
          SYNTAX        INTEGER                      
          ACCESS        read-only
          STATUS        mandatory
          DESCRIPTION   "The aggregate number of frames transmitted on it's 
                         ports." 
   ::= { rev1 32 }



   efdmimDeviceErrorPkts   OBJECT-TYPE
          --OID         1.3.6.1.4.1.52.1.6.4.1.33
          SYNTAX        INTEGER                      
          ACCESS        read-only
          STATUS        mandatory
          DESCRIPTION   "The aggregate number of frame errors detected on it's 
                         ports" 
   ::= { rev1 33 }



    efdmimCfmState  OBJECT-TYPE
          --OID          1.3.6.1.4.1.52.1.6.4.1.34
          SYNTAX         INTEGER
          ACCESS        read-only
          STATUS        mandatory
          DESCRIPTION   "The efdmim's current CFM state.
                         Legal values are:
                               isolated   (0)
                               wrap-A     (1)
                               wrap-B     (2)
                               wrap-AB    (3)
                               through-A  (4)
                               through-B  (5)
                               through-AB (6)
                               wrap-S     (7)
                        "
    ::= { rev1 34 }



    efdmimBypassAttached  OBJECT-TYPE
          --OID          1.3.6.1.4.1.52.1.6.4.1.35
          SYNTAX         INTEGER
                               {
                               true  (1),
                               false (2)
                               }
          ACCESS        read-only
          STATUS        mandatory
          DESCRIPTION   "Does the station has an optical bypass switch? "
    ::= { rev1 35}



    efdmimOscillations     OBJECT-TYPE
          --OID          1.3.6.1.4.1.52.1.6.4.1.36
          SYNTAX        Counter
          ACCESS        read-only
          STATUS        mandatory
          DESCRIPTION   "The number of times the claim/beacon
                        process has completed since power-up.
                        Note: This does not get reset when a reset counter 
                        command is issued. "
    ::= { rev1 36 }



    efdmimRingUpTime  OBJECT-TYPE
          --OID          1.3.6.1.4.1.52.1.6.4.1.37
          SYNTAX        Counter
          ACCESS        read-only
          STATUS        mandatory
          DESCRIPTION   "The elapsed time in seconds since the most recent 
                        ring oscillation.  Note: This returns 0 whenever the 
                        FDDI ring is down." 
    ::= { rev1 37 }



    efdmimDownstreamMac  OBJECT-TYPE
          --OID          1.3.6.1.4.1.52.1.6.4.1.38
          SYNTAX        OCTET STRING
          ACCESS        read-only
          STATUS        mandatory
          DESCRIPTION   "The address of this station's downstream MAC in 
                         canonical format. 
                         "
    ::= { rev1 38 }



    efdmimBypassStuck    OBJECT-TYPE
          --OID          1.3.6.1.4.1.52.1.6.4.1.39
          SYNTAX        INTEGER
                              {
                              true  (1),
                              false (2)
                              }
          ACCESS        read-only
          STATUS        mandatory
          DESCRIPTION   "True if the optical bypass switch is stuck
                         False if everything is ok. "
    ::= { rev1 39 }



   efdmimMode    OBJECT-TYPE
          --OID          1.3.6.1.4.1.52.1.6.4.1.40
          SYNTAX        INTEGER
                              {
                              encapsulation (1),
                              translation   (2)
                              }
          ACCESS        read-only
          STATUS        mandatory
          DESCRIPTION   " Encapsulation bridges talk using the FDDI ring as a 
                         back-bone only.  Translation bridges translates the 
                         packets into FDDI format." 
    ::= { rev1 40 }



   efdmimRmtState    OBJECT-TYPE
          --OID         1.3.6.1.4.1.52.1.6.4.1.41
          SYNTAX        INTEGER
          ACCESS        read-only
          STATUS        mandatory
          DESCRIPTION   "This represents what state the RMT state machine is 
                         in.  Legal values are:
                              isolated    (0)
                              non-Op      (1)
                              ring-Op     (2)
                              detect      (3)
                              non-Op-Dup  (4)
                              ring-Op-Dup (5)
                              directed    (6)
                              trace       (7)
                         "
   ::= { rev1 41 }



    efdmimDeviceBridgeAddr    OBJECT-TYPE
          --OID         1.3.6.1.4.1.52.1.6.4.1.42
          SYNTAX        OCTET STRING
          ACCESS        read-only
          STATUS        mandatory
          DESCRIPTION   "This returns the Bridge address in canonical 
                         format. "
    ::= { rev1 42 }



END

--
-- CAREL-mastercellasplit.MIB
-- MIB generated by CAREL
-- Friday, 14 March 2003
--

    CAREL-mastercellasplit-MIB DEFINITIONS ::= BEGIN
 
		IMPORTS
			OBJECT-GROUP
				FROM SNMPv2-CONF			
			sysContact, sysName, sysLocation			
				FROM SNMPv2-MIB
			enterprises, MODULE-IDENTITY			
				FROM SNMPv2-SMI;		
		
        mastercellasplitMIB MODULE-IDENTITY
      		LAST-UPDATED  "200303141725Z"		-- March 14, 2003 at 17:25 GMT
      		ORGANIZATION  "CAREL SpA"
      		CONTACT-INFO
                "
                        Simone Ravazzolo
                        Carel SpA
                        Via dell'Industria, 11
                        35020 Brugine (PD) Italy
                        Tel: +39 049 9716611
                        E-mail: simone.ravazzolo@carel.com
                "
      		DESCRIPTION
                "This is the MIB module for the mastercellasplit device."
			::= { instruments 1 }
	
	
--
-- Node definitions
--
	
		-- 1.3.6.1.4.1.9839
		carel OBJECT IDENTIFIER ::= { enterprises 9839 }
		
		-- 1.3.6.1.4.1.9839.1
		systm OBJECT IDENTIFIER ::= { carel 1 }
		
		-- 1.3.6.1.4.1.9839.1.1
		agentRelease OBJECT-TYPE
			SYNTAX Integer32
			UNITS "N/A"
			MAX-ACCESS read-only
			STATUS current
			DESCRIPTION "Release of the Agent."
		::= { systm 1 }
		
		-- 1.3.6.1.4.1.9839.1.2
		agentCode OBJECT-TYPE
			SYNTAX Integer32
			UNITS "N/A"
			MAX-ACCESS read-only
			STATUS current
			DESCRIPTION "Code of the Agent. 1=WebGate"
		::= { systm 2 }
		
		-- 1.3.6.1.4.1.9839.2
		instruments OBJECT IDENTIFIER ::= { carel 2 }
		
		-- 1.3.6.1.4.1.9839.2.0
		webGateInfo OBJECT IDENTIFIER ::= { instruments 0 }
		
		-- 1.3.6.1.4.1.9839.2.0.1
		agentParameters OBJECT IDENTIFIER ::= { webGateInfo 1 }
		
		-- 1.3.6.1.4.1.9839.2.0.1.1
		netSize OBJECT-TYPE
			SYNTAX Integer32 (1..16)
			UNITS "N/A"
			MAX-ACCESS read-write
			STATUS current
			DESCRIPTION "Network size. It corresponds to the number of units connected to the WebGate. "
		::= { agentParameters 1 }
		
		-- 1.3.6.1.4.1.9839.2.0.1.2
		baudRate OBJECT-TYPE
			SYNTAX Integer32 (1200 | 2400 |4800 |9600 | 19200)
			UNITS "N/A"
			MAX-ACCESS read-write
			STATUS current
			DESCRIPTION "Baudrate of the Carel network. "
		::= { agentParameters 2 }
		
		-- 1.3.6.1.4.1.9839.2.0.2
		unitTypeGroup OBJECT IDENTIFIER ::= { webGateInfo 2 }
		 
		-- 1.3.6.1.4.1.9839.2.0.2.1 
		unit1-Type OBJECT-TYPE
			SYNTAX DisplayString
			UNITS "N/A"
			MAX-ACCESS read-only
			STATUS current
			DESCRIPTION "Type of the unit having serial address 1. "
			::= { unitTypeGroup 1 }
			
		-- ... You will have how many unitX-Type objects as the value of netSize is

		-- 1.3.6.1.4.1.9839.2.0.3
		unitCodeGroup OBJECT IDENTIFIER ::= { webGateInfo 3 }
		
		-- 1.3.6.1.4.1.9839.2.0.3.1
		unit1-Code OBJECT-TYPE
			SYNTAX Integer32
			UNITS "N/A"
			MAX-ACCESS read-only
			STATUS current
			DESCRIPTION "Code of the unit having serial address 1. "
			::= { unitCodeGroup 1 }
			
		-- ... You will have how many unitX-Code objects as the value of netSize is
		
		-- 1.3.6.1.4.1.9839.2.0.4
		unitSoftwareReleaseGroup OBJECT IDENTIFIER ::= { webGateInfo 4 }
		
		-- 1.3.6.1.4.1.9839.2.0.3.1
		unit1-SoftwareRelease OBJECT-TYPE
			SYNTAX Integer32
			UNITS "N/A"
			MAX-ACCESS read-only
			STATUS current
			DESCRIPTION "Software release of the unit having serial address 1. "
			::= { unitSoftwareReleaseGroup 1 }
			
		-- ... You will have how many unitX-SoftwareRelease objects as the value of netSize is
		
		-- 1.3.6.1.4.1.9839.2.0.5
		unitMinSoftwareReleaseGroup OBJECT IDENTIFIER ::= { webGateInfo 5 }
		
		-- 1.3.6.1.4.1.9839.2.0.5.1
		unit1-MinSoftwareRelease OBJECT-TYPE
			SYNTAX Integer32
			UNITS "N/A"
			MAX-ACCESS read-only
			STATUS current
			DESCRIPTION "Minimum software release of the unit having serial address 1. "
			::= { unitMinSoftwareReleaseGroup 1 }
			
		-- ... You will have how many unitX-MinSoftwareRelease objects as the value of netSize is
		
		-- 1.3.6.1.4.1.9839.2.0.6
		unitMaxSoftwareReleaseGroup OBJECT IDENTIFIER ::= { webGateInfo 6 }
				
		-- 1.3.6.1.4.1.9839.2.0.6.1
		unit1-MaxSoftwareRelease OBJECT-TYPE
			SYNTAX Integer32
			UNITS "N/A"
			MAX-ACCESS read-only
			STATUS current
			DESCRIPTION "Maximum software release of the unit having serial address 1. "
			::= { unitMaxSoftwareReleaseGroup 1 }
			
		-- ... You will have how many unitX-MaxSoftwareRelease objects as the value of netSize is
			
		-- 1.3.6.1.4.1.9839.2.0.7
		unitNoAnswerCounterGroup OBJECT IDENTIFIER ::= { webGateInfo 7 }
		
		-- 1.3.6.1.4.1.9839.2.0.7.1
		unit1-NoAnswerCounter OBJECT-TYPE
			SYNTAX Integer32
			UNITS "N/A"
			MAX-ACCESS read-only
			STATUS current
			DESCRIPTION "No answer counter of the unit having serial address 1. "
			::= { unitNoAnswerCounterGroup 1 }
			
		-- ... You will have how many unitX-NoAnswerCounter objects as the value of netSize is
		
		-- 1.3.6.1.4.1.9839.2.0.8
		unitErrorChecksumCounterGroup OBJECT IDENTIFIER ::= { webGateInfo 8 }
		
		-- 1.3.6.1.4.1.9839.2.0.8.1
		unit1-ErrorChecksumCounter OBJECT-TYPE
			SYNTAX Integer32
			UNITS "N/A"
			MAX-ACCESS read-only
			STATUS current
			DESCRIPTION "Error checksum counter of the unit having serial address 1. "
			::= { unitErrorChecksumCounterGroup 1 }
			
		-- ... You will have how many unitX-ErrorChecksumCounter objects as the value of netSize is
		
		-- 1.3.6.1.4.1.9839.2.0.9
		unitTimeoutCounterGroup OBJECT IDENTIFIER ::= { webGateInfo 9 }
		
		-- 1.3.6.1.4.1.9839.2.0.9.1
		unit1-TimeoutCounter OBJECT-TYPE
			SYNTAX Integer32
			UNITS "N/A"
			MAX-ACCESS read-only
			STATUS current
			DESCRIPTION "Timeout counter of the unit having serial address 1. "
			::= { unitTimeoutCounterGroup 1 }
			
		-- ... You will have how many unitX-TimeoutCounter objects as the value of netSize is
		
		-- 1.3.6.1.4.1.9839.2.0.10
		unitOnLineStatusGroup OBJECT IDENTIFIER ::= { webGateInfo 10 }
		
		-- 1.3.6.1.4.1.9839.2.0.10.1
		unit1-OnLineStatus OBJECT-TYPE
			SYNTAX Integer32
			UNITS "N/A"
			MAX-ACCESS read-only
			STATUS current
			DESCRIPTION "On line status of the unit having serial address 1. "
			::= { unitOnLineStatusGroup 1 }
			
		-- ... You will have how many unitX-OnLineStatus objects as the value of netSize is
		
		-- 1.3.6.1.4.1.9839.2.1
        -- mastercellasplitMIB OBJECT IDENTIFIER ::= { instruments 1 }
		
        -- 1.3.6.1.4.1.9839.2.1.1
        digitalObjects OBJECT IDENTIFIER ::= { mastercellasplitMIB 1 }

        -- 1.3.6.1.4.1.9839.2.1.1.1
        cent_fhren_flag OBJECT-TYPE
                    SYNTAX Integer32 (0..1)
                    UNITS "flag"
                    MAX-ACCESS read-write
                    STATUS current
                    DESCRIPTION "Celsius or Fahrenheit selection"
                    DEFVAL { 0 }
                    ::= { digitalObjects 1 }

        -- 1.3.6.1.4.1.9839.2.1.1.2
        autoscale OBJECT-TYPE
                    SYNTAX Integer32 (0..1)
                    UNITS "flag"
                    MAX-ACCESS read-write
                    STATUS current
                    DESCRIPTION "Display decimals"
                    DEFVAL { 0 }
                    ::= { digitalObjects 2 }

        -- 1.3.6.1.4.1.9839.2.1.1.3
        defrostprobeselect OBJECT-TYPE
                    SYNTAX Integer32 (0..1)
                    UNITS "N/A"
                    MAX-ACCESS read-write
                    STATUS current
                    DESCRIPTION "Defrost with probe 3"
                    DEFVAL { 0 }
                    ::= { digitalObjects 3 }

        -- 1.3.6.1.4.1.9839.2.1.1.4
        sel_probe_term OBJECT-TYPE
                    SYNTAX Integer32 (0..1)
                    UNITS "N/A"
                    MAX-ACCESS read-write
                    STATUS current
                    DESCRIPTION "Enable used terminal brobe"
                    DEFVAL { 0 }
                    ::= { digitalObjects 4 }

        -- 1.3.6.1.4.1.9839.2.1.1.5
        pd_autostart_enable OBJECT-TYPE
                    SYNTAX Integer32 (0..1)
                    UNITS "N/A"
                    MAX-ACCESS read-write
                    STATUS current
                    DESCRIPTION "Autostart in pump down"
                    DEFVAL { 0 }
                    ::= { digitalObjects 5 }

        -- 1.3.6.1.4.1.9839.2.1.1.6
        defrost_cmd OBJECT-TYPE
                    SYNTAX Integer32 (0..1)
                    UNITS "N/A"
                    MAX-ACCESS read-write
                    STATUS current
                    DESCRIPTION "Type of defrost control"
                    DEFVAL { 0 }
                    ::= { digitalObjects 6 }

        -- 1.3.6.1.4.1.9839.2.1.1.7
        defrost_at_startup OBJECT-TYPE
                    SYNTAX Integer32 (0..1)
                    UNITS "flag"
                    MAX-ACCESS read-write
                    STATUS current
                    DESCRIPTION "Defrost on unit start-up"
                    DEFVAL { 0 }
                    ::= { digitalObjects 7 }

        -- 1.3.6.1.4.1.9839.2.1.1.8
        defrost_show OBJECT-TYPE
                    SYNTAX Integer32 (0..1)
                    UNITS "flag"
                    MAX-ACCESS read-write
                    STATUS current
                    DESCRIPTION "Display blocking during defrosting"
                    DEFVAL { 1 }
                    ::= { digitalObjects 8 }

        -- 1.3.6.1.4.1.9839.2.1.1.9
        defrost_priority OBJECT-TYPE
                    SYNTAX Integer32 (0..1)
                    UNITS "flag"
                    MAX-ACCESS read-write
                    STATUS current
                    DESCRIPTION "Defrost priority over compressor protection"
                    DEFVAL { 0 }
                    ::= { digitalObjects 9 }

        -- 1.3.6.1.4.1.9839.2.1.1.10
        fan_cfg OBJECT-TYPE
                    SYNTAX Integer32 (0..1)
                    UNITS "flag"
                    MAX-ACCESS read-write
                    STATUS current
                    DESCRIPTION "Fan management"
                    DEFVAL { 0 }
                    ::= { digitalObjects 10 }

        -- 1.3.6.1.4.1.9839.2.1.1.11
        fan_off_ctrl OBJECT-TYPE
                    SYNTAX Integer32 (0..1)
                    UNITS "flag"
                    MAX-ACCESS read-write
                    STATUS current
                    DESCRIPTION "Stop fans when compressor is off"
                    DEFVAL { 1 }
                    ::= { digitalObjects 11 }

        -- 1.3.6.1.4.1.9839.2.1.1.12
        fan_defrost_ctrl OBJECT-TYPE
                    SYNTAX Integer32 (0..1)
                    UNITS "flag"
                    MAX-ACCESS read-write
                    STATUS current
                    DESCRIPTION "Stop fans during defrosting"
                    DEFVAL { 1 }
                    ::= { digitalObjects 12 }

        -- 1.3.6.1.4.1.9839.2.1.1.13
        keyb_disabled OBJECT-TYPE
                    SYNTAX Integer32 (0..1)
                    UNITS "N/A"
                    MAX-ACCESS read-write
                    STATUS current
                    DESCRIPTION "Remote control programming enabling code"
                    DEFVAL { 0 }
                    ::= { digitalObjects 13 }

        -- 1.3.6.1.4.1.9839.2.1.1.16
        defrost_tout_alarm_ena OBJECT-TYPE
                    SYNTAX Integer32 (0..1)
                    UNITS "flag"
                    MAX-ACCESS read-write
                    STATUS current
                    DESCRIPTION "direct/reverse(SE) - ED alarm enabling all mods exc. ME"
                    DEFVAL { 0 }
                    ::= { digitalObjects 16 }

        -- 1.3.6.1.4.1.9839.2.1.1.17
        minmax_store_enable OBJECT-TYPE
                    SYNTAX Integer32 (0..1)
                    UNITS "flag"
                    MAX-ACCESS read-write
                    STATUS current
                    DESCRIPTION "Enable Min and Max temperatur monitorin"
                    DEFVAL { 0 }
                    ::= { digitalObjects 17 }

        -- 1.3.6.1.4.1.9839.2.1.1.18
        night_reg_probe OBJECT-TYPE
                    SYNTAX Integer32 (0..1)
                    UNITS "N/A"
                    MAX-ACCESS read-write
                    STATUS current
                    DESCRIPTION "Night regulation with product probe"
                    ::= { digitalObjects 18 }

        -- 1.3.6.1.4.1.9839.2.1.1.19
        haccp_reset OBJECT-TYPE
                    SYNTAX Integer32 (0..1)
                    UNITS "N/A"
                    MAX-ACCESS read-write
                    STATUS current
                    DESCRIPTION "reset alarm HACCP - HA - HF"
                    ::= { digitalObjects 19 }

        -- 1.3.6.1.4.1.9839.2.1.1.35
        s_comp OBJECT-TYPE
                    SYNTAX Integer32 (0..1)
                    UNITS "N/A"
                    MAX-ACCESS read-only
                    STATUS current
                    DESCRIPTION "Compressor relay status"
                    ::= { digitalObjects 35 }

        -- 1.3.6.1.4.1.9839.2.1.1.36
        s_fan OBJECT-TYPE
                    SYNTAX Integer32 (0..1)
                    UNITS "N/A"
                    MAX-ACCESS read-only
                    STATUS current
                    DESCRIPTION "Fan relay status"
                    ::= { digitalObjects 36 }

        -- 1.3.6.1.4.1.9839.2.1.1.37
        s_defrost OBJECT-TYPE
                    SYNTAX Integer32 (0..1)
                    UNITS "N/A"
                    MAX-ACCESS read-only
                    STATUS current
                    DESCRIPTION "Defrost relay status"
                    ::= { digitalObjects 37 }

        -- 1.3.6.1.4.1.9839.2.1.1.38
        s_aux_2 OBJECT-TYPE
                    SYNTAX Integer32 (0..1)
                    UNITS "N/A"
                    MAX-ACCESS read-write
                    STATUS current
                    DESCRIPTION "Aux relay status"
                    ::= { digitalObjects 38 }

        -- 1.3.6.1.4.1.9839.2.1.1.47
        dr_supervisor OBJECT-TYPE
                    SYNTAX Integer32 (0..1)
                    UNITS "N/A"
                    MAX-ACCESS read-write
                    STATUS current
                    DESCRIPTION "Start defrost request"
                    ::= { digitalObjects 47 }

        -- 1.3.6.1.4.1.9839.2.1.1.48
        dr_svendreq OBJECT-TYPE
                    SYNTAX Integer32 (0..1)
                    UNITS "N/A"
                    MAX-ACCESS read-write
                    STATUS current
                    DESCRIPTION "Stop defrost request"
                    ::= { digitalObjects 48 }

        -- 1.3.6.1.4.1.9839.2.1.1.51
        a1_e1 OBJECT-TYPE
                    SYNTAX Integer32 (0..1)
                    UNITS "N/A"
                    MAX-ACCESS read-only
                    STATUS current
                    DESCRIPTION "Probe 1 error"
                    ::= { digitalObjects 51 }

        -- 1.3.6.1.4.1.9839.2.1.1.52
        a1_e2 OBJECT-TYPE
                    SYNTAX Integer32 (0..1)
                    UNITS "N/A"
                    MAX-ACCESS read-only
                    STATUS current
                    DESCRIPTION "Probe 2 error"
                    ::= { digitalObjects 52 }

        -- 1.3.6.1.4.1.9839.2.1.1.53
        a1_e3 OBJECT-TYPE
                    SYNTAX Integer32 (0..1)
                    UNITS "N/A"
                    MAX-ACCESS read-only
                    STATUS current
                    DESCRIPTION "Probe 3 error"
                    ::= { digitalObjects 53 }

        -- 1.3.6.1.4.1.9839.2.1.1.54
        a1_ia OBJECT-TYPE
                    SYNTAX Integer32 (0..1)
                    UNITS "N/A"
                    MAX-ACCESS read-only
                    STATUS current
                    DESCRIPTION "Immediate external alarm"
                    ::= { digitalObjects 54 }

        -- 1.3.6.1.4.1.9839.2.1.1.55
        a1_da OBJECT-TYPE
                    SYNTAX Integer32 (0..1)
                    UNITS "N/A"
                    MAX-ACCESS read-only
                    STATUS current
                    DESCRIPTION "Delayed external alarm"
                    ::= { digitalObjects 55 }

        -- 1.3.6.1.4.1.9839.2.1.1.56
        a1_ea OBJECT-TYPE
                    SYNTAX Integer32 (0..1)
                    UNITS "N/A"
                    MAX-ACCESS read-only
                    STATUS current
                    DESCRIPTION "E2P/clock alarm"
                    ::= { digitalObjects 56 }

        -- 1.3.6.1.4.1.9839.2.1.1.57
        a1_re OBJECT-TYPE
                    SYNTAX Integer32 (0..1)
                    UNITS "N/A"
                    MAX-ACCESS read-only
                    STATUS current
                    DESCRIPTION "Control probe error"
                    ::= { digitalObjects 57 }

        -- 1.3.6.1.4.1.9839.2.1.1.58
        a1_id OBJECT-TYPE
                    SYNTAX Integer32 (0..1)
                    UNITS "N/A"
                    MAX-ACCESS read-only
                    STATUS current
                    DESCRIPTION "Duty setting from external contact"
                    ::= { digitalObjects 58 }

        -- 1.3.6.1.4.1.9839.2.1.1.59
        a2_hi OBJECT-TYPE
                    SYNTAX Integer32 (0..1)
                    UNITS "N/A"
                    MAX-ACCESS read-only
                    STATUS current
                    DESCRIPTION "High temperature alarm"
                    ::= { digitalObjects 59 }

        -- 1.3.6.1.4.1.9839.2.1.1.61
        a2_ha OBJECT-TYPE
                    SYNTAX Integer32 (0..1)
                    UNITS "N/A"
                    MAX-ACCESS read-only
                    STATUS current
                    DESCRIPTION "HACCP alarm, time exceeded"
                    ::= { digitalObjects 61 }

        -- 1.3.6.1.4.1.9839.2.1.1.62
        a2_hf OBJECT-TYPE
                    SYNTAX Integer32 (0..1)
                    UNITS "N/A"
                    MAX-ACCESS read-only
                    STATUS current
                    DESCRIPTION "HACCP alarm, power failure"
                    ::= { digitalObjects 62 }

        -- 1.3.6.1.4.1.9839.2.1.1.64
        a4_hc OBJECT-TYPE
                    SYNTAX Integer32 (0..1)
                    UNITS "N/A"
                    MAX-ACCESS read-only
                    STATUS current
                    DESCRIPTION "Alarm high temperature condensator"
                    ::= { digitalObjects 64 }

        -- 1.3.6.1.4.1.9839.2.1.1.65
        a4_pd OBJECT-TYPE
                    SYNTAX Integer32 (0..1)
                    UNITS "N/A"
                    MAX-ACCESS read-only
                    STATUS current
                    DESCRIPTION "Defrost ended by time-out"
                    ::= { digitalObjects 65 }

        -- 1.3.6.1.4.1.9839.2.1.1.66
        a4_bp OBJECT-TYPE
                    SYNTAX Integer32 (0..1)
                    UNITS "N/A"
                    MAX-ACCESS read-only
                    STATUS current
                    DESCRIPTION "Low temperature alarm"
                    ::= { digitalObjects 66 }



        -- 1.3.6.1.4.1.9839.2.1.2
        analogObjects OBJECT IDENTIFIER ::= { mastercellasplitMIB 2 }

        -- 1.3.6.1.4.1.9839.2.1.2.1
        probeoffset_3 OBJECT-TYPE
                    SYNTAX Integer32 (0..199)
                    UNITS "°C/°F x10"
                    MAX-ACCESS read-write
                    STATUS current
                    DESCRIPTION "Probe 3 calibration"
                    DEFVAL { 0 }
                    ::= { analogObjects 1 }

        -- 1.3.6.1.4.1.9839.2.1.2.2
        probeoffset_1 OBJECT-TYPE
                    SYNTAX Integer32 (0..199)
                    UNITS "°C/°F x10"
                    MAX-ACCESS read-write
                    STATUS current
                    DESCRIPTION "Calibration"
                    DEFVAL { 0 }
                    ::= { analogObjects 2 }

        -- 1.3.6.1.4.1.9839.2.1.2.3
        probeoffset_2 OBJECT-TYPE
                    SYNTAX Integer32 (0..199)
                    UNITS "°C/°F x10"
                    MAX-ACCESS read-write
                    STATUS current
                    DESCRIPTION "Defrost probe calibration"
                    DEFVAL { 0 }
                    ::= { analogObjects 3 }

        -- 1.3.6.1.4.1.9839.2.1.2.4
        fan_alarm_hyst OBJECT-TYPE
                    SYNTAX Integer32 (1..199)
                    UNITS "°C/°F x10"
                    MAX-ACCESS read-write
                    STATUS current
                    DESCRIPTION "Differential alarms and fans"
                    DEFVAL { 2 }
                    ::= { analogObjects 4 }

        -- 1.3.6.1.4.1.9839.2.1.2.5
        alarm_condenser OBJECT-TYPE
                    SYNTAX Integer32 (0..1990)
                    UNITS "°C/°F x10"
                    MAX-ACCESS read-write
                    STATUS current
                    DESCRIPTION "Alarm high temperature condensator"
                    DEFVAL { 0 }
                    ::= { analogObjects 5 }

        -- 1.3.6.1.4.1.9839.2.1.2.6
        alarm_condenser_delta OBJECT-TYPE
                    SYNTAX Integer32 (0..199)
                    UNITS "°C/°F x10"
                    MAX-ACCESS read-write
                    STATUS current
                    DESCRIPTION "Differential alarm high temperature condensator"
                    DEFVAL { 0 }
                    ::= { analogObjects 6 }

        -- 1.3.6.1.4.1.9839.2.1.2.9
        defrost_end_temp OBJECT-TYPE
                    SYNTAX Integer32 (-500..1990)
                    UNITS "°C/°F x10"
                    MAX-ACCESS read-write
                    STATUS current
                    DESCRIPTION "End defrost temperature set point"
                    DEFVAL { 40 }
                    ::= { analogObjects 9 }

        -- 1.3.6.1.4.1.9839.2.1.2.10
        fan_on_temp OBJECT-TYPE
                    SYNTAX Integer32 (-400..500)
                    UNITS "°C/°F x10"
                    MAX-ACCESS read-write
                    STATUS current
                    DESCRIPTION "Fan switching on temperature"
                    DEFVAL { 50 }
                    ::= { analogObjects 10 }

        -- 1.3.6.1.4.1.9839.2.1.2.11
        fan_on_cond OBJECT-TYPE
                    SYNTAX Integer32 (0..199)
                    UNITS "°C/°F x10"
                    MAX-ACCESS read-only
                    STATUS current
                    DESCRIPTION "Temperature off  condensator fan."
                    ::= { analogObjects 11 }

        -- 1.3.6.1.4.1.9839.2.1.2.12
        fan_cond_hyst OBJECT-TYPE
                    SYNTAX Integer32 (0..199)
                    UNITS "°C/°F x10"
                    MAX-ACCESS read-only
                    STATUS current
                    DESCRIPTION "Differential condensator fan"
                    ::= { analogObjects 12 }

        -- 1.3.6.1.4.1.9839.2.1.2.13
        setpoint_min OBJECT-TYPE
                    SYNTAX Integer32 (-500..32767)
                    UNITS "°C/°F x10"
                    MAX-ACCESS read-write
                    STATUS current
                    DESCRIPTION "Minimum set point value"
                    DEFVAL { -500 }
                    ::= { analogObjects 13 }

        -- 1.3.6.1.4.1.9839.2.1.2.14
        setpoint_max OBJECT-TYPE
                    SYNTAX Integer32 (-32767..1990)
                    UNITS "°C/°F x10"
                    MAX-ACCESS read-write
                    STATUS current
                    DESCRIPTION "Maximum set point value"
                    DEFVAL { 600 }
                    ::= { analogObjects 14 }

        -- 1.3.6.1.4.1.9839.2.1.2.15
        setpoint_night OBJECT-TYPE
                    SYNTAX Integer32 (0..200)
                    UNITS "°C/°F x10"
                    MAX-ACCESS read-write
                    STATUS current
                    DESCRIPTION "Automat set po. variat.for night-time operation"
                    DEFVAL { 30 }
                    ::= { analogObjects 15 }

        -- 1.3.6.1.4.1.9839.2.1.2.16
        reghyst OBJECT-TYPE
                    SYNTAX Integer32 (0..199)
                    UNITS "°C/°F x10"
                    MAX-ACCESS read-write
                    STATUS current
                    DESCRIPTION "Regulator differential"
                    DEFVAL { 200 }
                    ::= { analogObjects 16 }

        -- 1.3.6.1.4.1.9839.2.1.2.17
        max_store_value OBJECT-TYPE
                    SYNTAX Integer32 (0..0)
                    UNITS "°C/°F x10"
                    MAX-ACCESS read-only
                    STATUS current
                    DESCRIPTION "Maximun temperature read in the rt interval"
                    ::= { analogObjects 17 }

        -- 1.3.6.1.4.1.9839.2.1.2.18
        min_store_value OBJECT-TYPE
                    SYNTAX Integer32 (0..0)
                    UNITS "°C/°F x10"
                    MAX-ACCESS read-only
                    STATUS current
                    DESCRIPTION "Minimun temperature read in the interval"
                    ::= { analogObjects 18 }

        -- 1.3.6.1.4.1.9839.2.1.2.19
        setpoint OBJECT-TYPE
                    SYNTAX Integer32 (-32767..32767)
                    UNITS "°C/°F x10"
                    MAX-ACCESS read-write
                    STATUS current
                    DESCRIPTION "Setpoint"
                    ::= { analogObjects 19 }

        -- 1.3.6.1.4.1.9839.2.1.2.30
        probe_1 OBJECT-TYPE
                    SYNTAX Integer32 (-32767..32767)
                    UNITS "°C/°F x10"
                    MAX-ACCESS read-only
                    STATUS current
                    DESCRIPTION "Room temperature"
                    ::= { analogObjects 30 }

        -- 1.3.6.1.4.1.9839.2.1.2.31
        probe_2 OBJECT-TYPE
                    SYNTAX Integer32 (-32767..32767)
                    UNITS "°C/°F x10"
                    MAX-ACCESS read-only
                    STATUS current
                    DESCRIPTION "Evaporator temperature"
                    ::= { analogObjects 31 }



        -- 1.3.6.1.4.1.9839.2.1.3
        integerObjects OBJECT IDENTIFIER ::= { mastercellasplitMIB 3 }

        -- 1.3.6.1.4.1.9839.2.1.3.1
        probe_delay OBJECT-TYPE
                    SYNTAX Integer32 (1..15)
                    UNITS "N/A"
                    MAX-ACCESS read-write
                    STATUS current
                    DESCRIPTION "Measurement stability"
                    DEFVAL { 4 }
                    ::= { integerObjects 1 }

        -- 1.3.6.1.4.1.9839.2.1.3.2
        virt_probe OBJECT-TYPE
                    SYNTAX Integer32 (0..100)
                    UNITS "N/A"
                    MAX-ACCESS read-write
                    STATUS current
                    DESCRIPTION "Virtual probe"
                    DEFVAL { 0 }
                    ::= { integerObjects 2 }

        -- 1.3.6.1.4.1.9839.2.1.3.3
        defrostprobepresence OBJECT-TYPE
                    SYNTAX Integer32 (0..3)
                    UNITS "flag"
                    MAX-ACCESS read-write
                    STATUS current
                    DESCRIPTION "Presence of probes S2 and S3"
                    DEFVAL { 2 }
                    ::= { integerObjects 3 }

        -- 1.3.6.1.4.1.9839.2.1.3.4
        showprobe_t OBJECT-TYPE
                    SYNTAX Integer32 (0..4)
                    UNITS "flag"
                    MAX-ACCESS read-write
                    STATUS current
                    DESCRIPTION "Terminal configuration"
                    DEFVAL { 4 }
                    ::= { integerObjects 4 }

        -- 1.3.6.1.4.1.9839.2.1.3.5
        dig_in_term_cfg_1 OBJECT-TYPE
                    SYNTAX Integer32 (0..2)
                    UNITS "N/A"
                    MAX-ACCESS read-write
                    STATUS current
                    DESCRIPTION "Digital input configuration terminal n.1"
                    DEFVAL { 0 }
                    ::= { integerObjects 5 }

        -- 1.3.6.1.4.1.9839.2.1.3.6
        dig_in_term_cfg_2 OBJECT-TYPE
                    SYNTAX Integer32 (0..1)
                    UNITS "flag"
                    MAX-ACCESS read-write
                    STATUS current
                    DESCRIPTION "Digital input configuration terminal n.2"
                    DEFVAL { 0 }
                    ::= { integerObjects 6 }

        -- 1.3.6.1.4.1.9839.2.1.3.7
        dig_in_cfg_1 OBJECT-TYPE
                    SYNTAX Integer32 (0..10)
                    UNITS "N/A"
                    MAX-ACCESS read-write
                    STATUS current
                    DESCRIPTION "Configuring the multifunction digital input 1"
                    DEFVAL { 0 }
                    ::= { integerObjects 7 }

        -- 1.3.6.1.4.1.9839.2.1.3.8
        dig_in_cfg_2 OBJECT-TYPE
                    SYNTAX Integer32 (0..10)
                    UNITS "N/A"
                    MAX-ACCESS read-write
                    STATUS current
                    DESCRIPTION "Configuring the multifunction digital input 2"
                    DEFVAL { 0 }
                    ::= { integerObjects 8 }

        -- 1.3.6.1.4.1.9839.2.1.3.9
        alarm_input_delay OBJECT-TYPE
                    SYNTAX Integer32 (0..199)
                    UNITS "min"
                    MAX-ACCESS read-write
                    STATUS current
                    DESCRIPTION "Delay in registration of external alarm"
                    DEFVAL { 0 }
                    ::= { integerObjects 9 }

        -- 1.3.6.1.4.1.9839.2.1.3.10
        alarm_delay OBJECT-TYPE
                    SYNTAX Integer32 (0..199)
                    UNITS "min"
                    MAX-ACCESS read-write
                    STATUS current
                    DESCRIPTION "Temperature alarm delay"
                    DEFVAL { 120 }
                    ::= { integerObjects 10 }

        -- 1.3.6.1.4.1.9839.2.1.3.11
        comp_startup_delay OBJECT-TYPE
                    SYNTAX Integer32 (0..15)
                    UNITS "min."
                    MAX-ACCESS read-write
                    STATUS current
                    DESCRIPTION "Compressor start-up delay after unit start-up"
                    DEFVAL { 0 }
                    ::= { integerObjects 11 }

        -- 1.3.6.1.4.1.9839.2.1.3.12
        comp_s2s_delay OBJECT-TYPE
                    SYNTAX Integer32 (0..15)
                    UNITS "min."
                    MAX-ACCESS read-write
                    STATUS current
                    DESCRIPTION "Minimum time between two successive starts of the compressor"
                    DEFVAL { 0 }
                    ::= { integerObjects 12 }

        -- 1.3.6.1.4.1.9839.2.1.3.13
        comp_min_off_time OBJECT-TYPE
                    SYNTAX Integer32 (0..15)
                    UNITS "min."
                    MAX-ACCESS read-write
                    STATUS current
                    DESCRIPTION "Minimum compressor off-time"
                    DEFVAL { 0 }
                    ::= { integerObjects 13 }

        -- 1.3.6.1.4.1.9839.2.1.3.14
        comp_min_on_time OBJECT-TYPE
                    SYNTAX Integer32 (0..15)
                    UNITS "min."
                    MAX-ACCESS read-write
                    STATUS current
                    DESCRIPTION "Minimum compressor on-time"
                    DEFVAL { 0 }
                    ::= { integerObjects 14 }

        -- 1.3.6.1.4.1.9839.2.1.3.15
        rele_safety_cycle OBJECT-TYPE
                    SYNTAX Integer32 (0..100)
                    UNITS "min."
                    MAX-ACCESS read-write
                    STATUS current
                    DESCRIPTION "Relay safety see duty setting"
                    DEFVAL { 0 }
                    ::= { integerObjects 15 }

        -- 1.3.6.1.4.1.9839.2.1.3.16
        cc_alarm_delay OBJECT-TYPE
                    SYNTAX Integer32 (0..15)
                    UNITS "hours"
                    MAX-ACCESS read-write
                    STATUS current
                    DESCRIPTION "Alarm cut-out after continuous cycle"
                    DEFVAL { 2 }
                    ::= { integerObjects 16 }

        -- 1.3.6.1.4.1.9839.2.1.3.17
        max_pd_time OBJECT-TYPE
                    SYNTAX Integer32 (0..30)
                    UNITS "min."
                    MAX-ACCESS read-write
                    STATUS current
                    DESCRIPTION "Max time of pump down"
                    DEFVAL { 0 }
                    ::= { integerObjects 17 }

        -- 1.3.6.1.4.1.9839.2.1.3.18
        dly_valve_comp OBJECT-TYPE
                    SYNTAX Integer32 (0..60)
                    UNITS "sec."
                    MAX-ACCESS read-write
                    STATUS current
                    DESCRIPTION "Delay at the start of compressor"
                    DEFVAL { 10 }
                    ::= { integerObjects 18 }

        -- 1.3.6.1.4.1.9839.2.1.3.19
        comp_cc OBJECT-TYPE
                    SYNTAX Integer32 (0..15)
                    UNITS "hours"
                    MAX-ACCESS read-write
                    STATUS current
                    DESCRIPTION "Duration of continuos cycle"
                    DEFVAL { 0 }
                    ::= { integerObjects 19 }

        -- 1.3.6.1.4.1.9839.2.1.3.20
        defrost_type OBJECT-TYPE
                    SYNTAX Integer32 (0..3)
                    UNITS "flag"
                    MAX-ACCESS read-write
                    STATUS current
                    DESCRIPTION "Defrost parameters"
                    DEFVAL { 0 }
                    ::= { integerObjects 20 }

        -- 1.3.6.1.4.1.9839.2.1.3.21
        dly_def_gas OBJECT-TYPE
                    SYNTAX Integer32 (0..255)
                    UNITS "sec."
                    MAX-ACCESS read-write
                    STATUS current
                    DESCRIPTION "Delay insertion defrost"
                    DEFVAL { 0 }
                    ::= { integerObjects 21 }

        -- 1.3.6.1.4.1.9839.2.1.3.22
        defrost_delay OBJECT-TYPE
                    SYNTAX Integer32 (0..199)
                    UNITS "min"
                    MAX-ACCESS read-write
                    STATUS current
                    DESCRIPTION "Def delay after unit start-up or multi-function input"
                    DEFVAL { 0 }
                    ::= { integerObjects 22 }

        -- 1.3.6.1.4.1.9839.2.1.3.23
        alarm_delay_df_door OBJECT-TYPE
                    SYNTAX Integer32 (0..15)
                    UNITS "hours"
                    MAX-ACCESS read-write
                    STATUS current
                    DESCRIPTION "Duration of alarm cut-out after dripping."
                    DEFVAL { 1 }
                    ::= { integerObjects 23 }

        -- 1.3.6.1.4.1.9839.2.1.3.24
        dripping_interval OBJECT-TYPE
                    SYNTAX Integer32 (0..15)
                    UNITS "min"
                    MAX-ACCESS read-write
                    STATUS current
                    DESCRIPTION "Dripping time after defrost"
                    DEFVAL { 2 }
                    ::= { integerObjects 24 }

        -- 1.3.6.1.4.1.9839.2.1.3.25
        defrost_interval OBJECT-TYPE
                    SYNTAX Integer32 (0..199)
                    UNITS "hours"
                    MAX-ACCESS read-write
                    STATUS current
                    DESCRIPTION "Interval between defrost"
                    DEFVAL { 8 }
                    ::= { integerObjects 25 }

        -- 1.3.6.1.4.1.9839.2.1.3.26
        defrost_max_time OBJECT-TYPE
                    SYNTAX Integer32 (1..199)
                    UNITS "min"
                    MAX-ACCESS read-write
                    STATUS current
                    DESCRIPTION "Maximum defrost time"
                    DEFVAL { 30 }
                    ::= { integerObjects 26 }

        -- 1.3.6.1.4.1.9839.2.1.3.27
        fan_drip_interval OBJECT-TYPE
                    SYNTAX Integer32 (0..15)
                    UNITS "min"
                    MAX-ACCESS read-write
                    STATUS current
                    DESCRIPTION "Cut out after dripping"
                    DEFVAL { 1 }
                    ::= { integerObjects 27 }

        -- 1.3.6.1.4.1.9839.2.1.3.28
        aux1_cfg OBJECT-TYPE
                    SYNTAX Integer32 (0..11)
                    UNITS "flag"
                    MAX-ACCESS read-write
                    STATUS current
                    DESCRIPTION "Operating mode"
                    DEFVAL { 0 }
                    ::= { integerObjects 28 }

        -- 1.3.6.1.4.1.9839.2.1.3.29
        aux2_cfg OBJECT-TYPE
                    SYNTAX Integer32 (0..11)
                    UNITS "flag"
                    MAX-ACCESS read-write
                    STATUS current
                    DESCRIPTION "Disable keypad and/or the remote inhibition"
                    DEFVAL { 1 }
                    ::= { integerObjects 29 }

        -- 1.3.6.1.4.1.9839.2.1.3.30
        light_sens_1 OBJECT-TYPE
                    SYNTAX Integer32 (0..1)
                    UNITS "flag"
                    MAX-ACCESS read-write
                    STATUS current
                    DESCRIPTION "Light sensor 1 calibration"
                    DEFVAL { 1 }
                    ::= { integerObjects 30 }

        -- 1.3.6.1.4.1.9839.2.1.3.31
        sgl_all_min_rel OBJECT-TYPE
                    SYNTAX Integer32 (0..199)
                    UNITS "°C"
                    MAX-ACCESS read-only
                    STATUS current
                    DESCRIPTION "Light on time from photocell input"
                    DEFVAL { 10 }
                    ::= { integerObjects 31 }

        -- 1.3.6.1.4.1.9839.2.1.3.32
        minmax_acq_time OBJECT-TYPE
                    SYNTAX Integer32 (0..199)
                    UNITS "hours"
                    MAX-ACCESS read-only
                    STATUS current
                    DESCRIPTION "Actual interval in max/min. temperature reading"
                    ::= { integerObjects 32 }

        -- 1.3.6.1.4.1.9839.2.1.3.33
        haccp_ha_day OBJECT-TYPE
                    SYNTAX Integer32 (1..7)
                    UNITS "gg"
                    MAX-ACCESS read-only
                    STATUS current
                    DESCRIPTION "Event - day of week HA"
                    ::= { integerObjects 33 }

        -- 1.3.6.1.4.1.9839.2.1.3.34
        haccp_ha_hour OBJECT-TYPE
                    SYNTAX Integer32 (0..23)
                    UNITS "ore"
                    MAX-ACCESS read-only
                    STATUS current
                    DESCRIPTION "Event - hour HA"
                    ::= { integerObjects 34 }

        -- 1.3.6.1.4.1.9839.2.1.3.35
        haccp_ha_min OBJECT-TYPE
                    SYNTAX Integer32 (0..59)
                    UNITS "min."
                    MAX-ACCESS read-only
                    STATUS current
                    DESCRIPTION "Event - min HA"
                    ::= { integerObjects 35 }

        -- 1.3.6.1.4.1.9839.2.1.3.36
        haccp_hf_day OBJECT-TYPE
                    SYNTAX Integer32 (1..7)
                    UNITS "gg"
                    MAX-ACCESS read-only
                    STATUS current
                    DESCRIPTION "Event - day of week HF"
                    ::= { integerObjects 36 }

        -- 1.3.6.1.4.1.9839.2.1.3.37
        haccp_hf_hour OBJECT-TYPE
                    SYNTAX Integer32 (0..23)
                    UNITS "ore"
                    MAX-ACCESS read-only
                    STATUS current
                    DESCRIPTION "Event - hour HF"
                    ::= { integerObjects 37 }

        -- 1.3.6.1.4.1.9839.2.1.3.38
        haccp_hf_min OBJECT-TYPE
                    SYNTAX Integer32 (0..59)
                    UNITS "min."
                    MAX-ACCESS read-only
                    STATUS current
                    DESCRIPTION "Event - min HF"
                    ::= { integerObjects 38 }

        -- 1.3.6.1.4.1.9839.2.1.3.39
        haccp_rit_alarm OBJECT-TYPE
                    SYNTAX Integer32 (0..199)
                    UNITS "min."
                    MAX-ACCESS read-write
                    STATUS current
                    DESCRIPTION "HACCP alarm delay"
                    ::= { integerObjects 39 }

        -- 1.3.6.1.4.1.9839.2.1.3.40
        defrost_t1_dd OBJECT-TYPE
                    SYNTAX Integer32 (0..10)
                    UNITS "gg"
                    MAX-ACCESS read-write
                    STATUS current
                    DESCRIPTION "Defrost event 1 day"
                    ::= { integerObjects 40 }

        -- 1.3.6.1.4.1.9839.2.1.3.41
        defrost_t1_hh OBJECT-TYPE
                    SYNTAX Integer32 (0..23)
                    UNITS "ore"
                    MAX-ACCESS read-write
                    STATUS current
                    DESCRIPTION "Defrost event 1 hour"
                    ::= { integerObjects 41 }

        -- 1.3.6.1.4.1.9839.2.1.3.42
        defrost_t1_mm OBJECT-TYPE
                    SYNTAX Integer32 (0..59)
                    UNITS "min."
                    MAX-ACCESS read-write
                    STATUS current
                    DESCRIPTION "Defrost event 1 min"
                    ::= { integerObjects 42 }

        -- 1.3.6.1.4.1.9839.2.1.3.43
        defrost_t2_dd OBJECT-TYPE
                    SYNTAX Integer32 (0..10)
                    UNITS "gg"
                    MAX-ACCESS read-write
                    STATUS current
                    DESCRIPTION "Defrost event 2 day"
                    ::= { integerObjects 43 }

        -- 1.3.6.1.4.1.9839.2.1.3.44
        defrost_t2_hh OBJECT-TYPE
                    SYNTAX Integer32 (0..23)
                    UNITS "ore"
                    MAX-ACCESS read-write
                    STATUS current
                    DESCRIPTION "Defrost event 2 hour"
                    ::= { integerObjects 44 }

        -- 1.3.6.1.4.1.9839.2.1.3.45
        defrost_t2_mm OBJECT-TYPE
                    SYNTAX Integer32 (0..59)
                    UNITS "min"
                    MAX-ACCESS read-write
                    STATUS current
                    DESCRIPTION "Defrost event 2 min"
                    ::= { integerObjects 45 }

        -- 1.3.6.1.4.1.9839.2.1.3.46
        defrost_t3_dd OBJECT-TYPE
                    SYNTAX Integer32 (0..10)
                    UNITS "gg"
                    MAX-ACCESS read-write
                    STATUS current
                    DESCRIPTION "Defrost event 3 day"
                    ::= { integerObjects 46 }

        -- 1.3.6.1.4.1.9839.2.1.3.47
        defrost_t3_hh OBJECT-TYPE
                    SYNTAX Integer32 (0..23)
                    UNITS "ore"
                    MAX-ACCESS read-write
                    STATUS current
                    DESCRIPTION "Defrost event 3 hour"
                    ::= { integerObjects 47 }

        -- 1.3.6.1.4.1.9839.2.1.3.48
        defrost_t3_mm OBJECT-TYPE
                    SYNTAX Integer32 (0..59)
                    UNITS "min"
                    MAX-ACCESS read-write
                    STATUS current
                    DESCRIPTION "Defrost event 3 min"
                    ::= { integerObjects 48 }

        -- 1.3.6.1.4.1.9839.2.1.3.49
        defrost_t4_dd OBJECT-TYPE
                    SYNTAX Integer32 (0..10)
                    UNITS "gg"
                    MAX-ACCESS read-write
                    STATUS current
                    DESCRIPTION "Defrost event 4 day"
                    ::= { integerObjects 49 }

        -- 1.3.6.1.4.1.9839.2.1.3.50
        defrost_t4_hh OBJECT-TYPE
                    SYNTAX Integer32 (0..23)
                    UNITS "ore"
                    MAX-ACCESS read-write
                    STATUS current
                    DESCRIPTION "Defrost event 4 hour"
                    ::= { integerObjects 50 }

        -- 1.3.6.1.4.1.9839.2.1.3.51
        defrost_t4_mm OBJECT-TYPE
                    SYNTAX Integer32 (0..59)
                    UNITS "min"
                    MAX-ACCESS read-write
                    STATUS current
                    DESCRIPTION "Defrost event 4 min"
                    ::= { integerObjects 51 }

        -- 1.3.6.1.4.1.9839.2.1.3.53
        th OBJECT-TYPE
                    SYNTAX Integer32 (0..23)
                    UNITS "ore"
                    MAX-ACCESS read-write
                    STATUS current
                    DESCRIPTION "Hour"
                    ::= { integerObjects 53 }

        -- 1.3.6.1.4.1.9839.2.1.3.54
        tdow OBJECT-TYPE
                    SYNTAX Integer32 (1..7)
                    UNITS "gg"
                    MAX-ACCESS read-write
                    STATUS current
                    DESCRIPTION "Weekday"
                    ::= { integerObjects 54 }


	
	END

--
-- CAREL-mastercellasplit.MIB
--

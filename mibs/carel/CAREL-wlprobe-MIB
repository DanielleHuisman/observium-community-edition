--
-- CAREL-wlprobe.MIB
-- MIB generated by CAREL
-- Friday, 14 March 2003
--

    CAREL-wlprobe-MIB DEFINITIONS ::= BEGIN
 
		IMPORTS
			OBJECT-GROUP
				FROM SNMPv2-CONF			
			sysContact, sysName, sysLocation			
				FROM SNMPv2-MIB
			enterprises, MODULE-IDENTITY			
				FROM SNMPv2-SMI;		
		
        wlprobeMIB MODULE-IDENTITY
      		LAST-UPDATED  "200303141725Z"		-- March 14, 2003 at 17:25 GMT
      		ORGANIZATION  "CAREL SpA"
      		CONTACT-INFO
                "
                        Simone Ravazzolo
                        Carel SpA
                        Via dell'Industria, 11
                        35020 Brugine (PD) Italy
                        Tel: +39 049 9716611
                        E-mail: simone.ravazzolo@carel.com
                "
      		DESCRIPTION
                "This is the MIB module for the wlprobe device."
			::= { instruments 1 }
	
	
--
-- Node definitions
--
	
		-- 1.3.6.1.4.1.9839
		carel OBJECT IDENTIFIER ::= { enterprises 9839 }
		
		-- 1.3.6.1.4.1.9839.1
		systm OBJECT IDENTIFIER ::= { carel 1 }
		
		-- 1.3.6.1.4.1.9839.1.1
		agentRelease OBJECT-TYPE
			SYNTAX Integer32
			UNITS "N/A"
			MAX-ACCESS read-only
			STATUS current
			DESCRIPTION "Release of the Agent."
		::= { systm 1 }
		
		-- 1.3.6.1.4.1.9839.1.2
		agentCode OBJECT-TYPE
			SYNTAX Integer32
			UNITS "N/A"
			MAX-ACCESS read-only
			STATUS current
			DESCRIPTION "Code of the Agent. 1=WebGate"
		::= { systm 2 }
		
		-- 1.3.6.1.4.1.9839.2
		instruments OBJECT IDENTIFIER ::= { carel 2 }
		
		-- 1.3.6.1.4.1.9839.2.0
		webGateInfo OBJECT IDENTIFIER ::= { instruments 0 }
		
		-- 1.3.6.1.4.1.9839.2.0.1
		agentParameters OBJECT IDENTIFIER ::= { webGateInfo 1 }
		
		-- 1.3.6.1.4.1.9839.2.0.1.1
		netSize OBJECT-TYPE
			SYNTAX Integer32 (1..16)
			UNITS "N/A"
			MAX-ACCESS read-write
			STATUS current
			DESCRIPTION "Network size. It corresponds to the number of units connected to the WebGate. "
		::= { agentParameters 1 }
		
		-- 1.3.6.1.4.1.9839.2.0.1.2
		baudRate OBJECT-TYPE
			SYNTAX Integer32 (1200 | 2400 |4800 |9600 | 19200)
			UNITS "N/A"
			MAX-ACCESS read-write
			STATUS current
			DESCRIPTION "Baudrate of the Carel network. "
		::= { agentParameters 2 }
		
		-- 1.3.6.1.4.1.9839.2.0.2
		unitTypeGroup OBJECT IDENTIFIER ::= { webGateInfo 2 }
		 
		-- 1.3.6.1.4.1.9839.2.0.2.1 
		unit1-Type OBJECT-TYPE
			SYNTAX DisplayString
			UNITS "N/A"
			MAX-ACCESS read-only
			STATUS current
			DESCRIPTION "Type of the unit having serial address 1. "
			::= { unitTypeGroup 1 }
			
		-- ... You will have how many unitX-Type objects as the value of netSize is

		-- 1.3.6.1.4.1.9839.2.0.3
		unitCodeGroup OBJECT IDENTIFIER ::= { webGateInfo 3 }
		
		-- 1.3.6.1.4.1.9839.2.0.3.1
		unit1-Code OBJECT-TYPE
			SYNTAX Integer32
			UNITS "N/A"
			MAX-ACCESS read-only
			STATUS current
			DESCRIPTION "Code of the unit having serial address 1. "
			::= { unitCodeGroup 1 }
			
		-- ... You will have how many unitX-Code objects as the value of netSize is
		
		-- 1.3.6.1.4.1.9839.2.0.4
		unitSoftwareReleaseGroup OBJECT IDENTIFIER ::= { webGateInfo 4 }
		
		-- 1.3.6.1.4.1.9839.2.0.3.1
		unit1-SoftwareRelease OBJECT-TYPE
			SYNTAX Integer32
			UNITS "N/A"
			MAX-ACCESS read-only
			STATUS current
			DESCRIPTION "Software release of the unit having serial address 1. "
			::= { unitSoftwareReleaseGroup 1 }
			
		-- ... You will have how many unitX-SoftwareRelease objects as the value of netSize is
		
		-- 1.3.6.1.4.1.9839.2.0.5
		unitMinSoftwareReleaseGroup OBJECT IDENTIFIER ::= { webGateInfo 5 }
		
		-- 1.3.6.1.4.1.9839.2.0.5.1
		unit1-MinSoftwareRelease OBJECT-TYPE
			SYNTAX Integer32
			UNITS "N/A"
			MAX-ACCESS read-only
			STATUS current
			DESCRIPTION "Minimum software release of the unit having serial address 1. "
			::= { unitMinSoftwareReleaseGroup 1 }
			
		-- ... You will have how many unitX-MinSoftwareRelease objects as the value of netSize is
		
		-- 1.3.6.1.4.1.9839.2.0.6
		unitMaxSoftwareReleaseGroup OBJECT IDENTIFIER ::= { webGateInfo 6 }
				
		-- 1.3.6.1.4.1.9839.2.0.6.1
		unit1-MaxSoftwareRelease OBJECT-TYPE
			SYNTAX Integer32
			UNITS "N/A"
			MAX-ACCESS read-only
			STATUS current
			DESCRIPTION "Maximum software release of the unit having serial address 1. "
			::= { unitMaxSoftwareReleaseGroup 1 }
			
		-- ... You will have how many unitX-MaxSoftwareRelease objects as the value of netSize is
			
		-- 1.3.6.1.4.1.9839.2.0.7
		unitNoAnswerCounterGroup OBJECT IDENTIFIER ::= { webGateInfo 7 }
		
		-- 1.3.6.1.4.1.9839.2.0.7.1
		unit1-NoAnswerCounter OBJECT-TYPE
			SYNTAX Integer32
			UNITS "N/A"
			MAX-ACCESS read-only
			STATUS current
			DESCRIPTION "No answer counter of the unit having serial address 1. "
			::= { unitNoAnswerCounterGroup 1 }
			
		-- ... You will have how many unitX-NoAnswerCounter objects as the value of netSize is
		
		-- 1.3.6.1.4.1.9839.2.0.8
		unitErrorChecksumCounterGroup OBJECT IDENTIFIER ::= { webGateInfo 8 }
		
		-- 1.3.6.1.4.1.9839.2.0.8.1
		unit1-ErrorChecksumCounter OBJECT-TYPE
			SYNTAX Integer32
			UNITS "N/A"
			MAX-ACCESS read-only
			STATUS current
			DESCRIPTION "Error checksum counter of the unit having serial address 1. "
			::= { unitErrorChecksumCounterGroup 1 }
			
		-- ... You will have how many unitX-ErrorChecksumCounter objects as the value of netSize is
		
		-- 1.3.6.1.4.1.9839.2.0.9
		unitTimeoutCounterGroup OBJECT IDENTIFIER ::= { webGateInfo 9 }
		
		-- 1.3.6.1.4.1.9839.2.0.9.1
		unit1-TimeoutCounter OBJECT-TYPE
			SYNTAX Integer32
			UNITS "N/A"
			MAX-ACCESS read-only
			STATUS current
			DESCRIPTION "Timeout counter of the unit having serial address 1. "
			::= { unitTimeoutCounterGroup 1 }
			
		-- ... You will have how many unitX-TimeoutCounter objects as the value of netSize is
		
		-- 1.3.6.1.4.1.9839.2.0.10
		unitOnLineStatusGroup OBJECT IDENTIFIER ::= { webGateInfo 10 }
		
		-- 1.3.6.1.4.1.9839.2.0.10.1
		unit1-OnLineStatus OBJECT-TYPE
			SYNTAX Integer32
			UNITS "N/A"
			MAX-ACCESS read-only
			STATUS current
			DESCRIPTION "On line status of the unit having serial address 1. "
			::= { unitOnLineStatusGroup 1 }
			
		-- ... You will have how many unitX-OnLineStatus objects as the value of netSize is
		
		-- 1.3.6.1.4.1.9839.2.1
        -- wlprobeMIB OBJECT IDENTIFIER ::= { instruments 1 }
		
        -- 1.3.6.1.4.1.9839.2.1.1
        digitalObjects OBJECT IDENTIFIER ::= { wlprobeMIB 1 }

        -- 1.3.6.1.4.1.9839.2.1.1.1
        diginput1 OBJECT-TYPE
                    SYNTAX Integer32 (0..1)
                    UNITS "N/A"
                    MAX-ACCESS read-only
                    STATUS current
                    DESCRIPTION "Digital Input 1"
                    ::= { digitalObjects 1 }

        -- 1.3.6.1.4.1.9839.2.1.1.2
        diginput2 OBJECT-TYPE
                    SYNTAX Integer32 (0..1)
                    UNITS "N/A"
                    MAX-ACCESS read-only
                    STATUS current
                    DESCRIPTION "Digital Input 2"
                    ::= { digitalObjects 2 }

        -- 1.3.6.1.4.1.9839.2.1.1.3
        alrlowbatt OBJECT-TYPE
                    SYNTAX Integer32 (0..1)
                    UNITS "N/A"
                    MAX-ACCESS read-only
                    STATUS current
                    DESCRIPTION "Alarm low change battery"
                    ::= { digitalObjects 3 }

        -- 1.3.6.1.4.1.9839.2.1.1.4
        alrprobefault OBJECT-TYPE
                    SYNTAX Integer32 (0..1)
                    UNITS "N/A"
                    MAX-ACCESS read-only
                    STATUS current
                    DESCRIPTION "Alarm damaged probe (NTC)"
                    ::= { digitalObjects 4 }

        -- 1.3.6.1.4.1.9839.2.1.1.6
        alrhightempprobe1 OBJECT-TYPE
                    SYNTAX Integer32 (0..1)
                    UNITS "N/A"
                    MAX-ACCESS read-only
                    STATUS current
                    DESCRIPTION "Alarm high temperature probe 1"
                    ::= { digitalObjects 6 }

        -- 1.3.6.1.4.1.9839.2.1.1.7
        alrhightempprobe2 OBJECT-TYPE
                    SYNTAX Integer32 (0..1)
                    UNITS "N/A"
                    MAX-ACCESS read-only
                    STATUS current
                    DESCRIPTION "Alarm high temperature probe 2"
                    ::= { digitalObjects 7 }

        -- 1.3.6.1.4.1.9839.2.1.1.8
        alrlowtempprobe1 OBJECT-TYPE
                    SYNTAX Integer32 (0..1)
                    UNITS "N/A"
                    MAX-ACCESS read-only
                    STATUS current
                    DESCRIPTION "Alarm low temperature probe 1"
                    ::= { digitalObjects 8 }

        -- 1.3.6.1.4.1.9839.2.1.1.9
        alrlowtempprobe2 OBJECT-TYPE
                    SYNTAX Integer32 (0..1)
                    UNITS "N/A"
                    MAX-ACCESS read-only
                    STATUS current
                    DESCRIPTION "Alarm low temperature probe 2"
                    ::= { digitalObjects 9 }

        -- 1.3.6.1.4.1.9839.2.1.1.10
        hightempalrenabled OBJECT-TYPE
                    SYNTAX Integer32 (0..1)
                    UNITS "N/A"
                    MAX-ACCESS read-write
                    STATUS current
                    DESCRIPTION "High temperature alarm enable"
                    ::= { digitalObjects 10 }

        -- 1.3.6.1.4.1.9839.2.1.1.11
        diginputpol1 OBJECT-TYPE
                    SYNTAX Integer32 (0..1)
                    UNITS "N/A"
                    MAX-ACCESS read-write
                    STATUS current
                    DESCRIPTION "Polarity digital imput 1"
                    ::= { digitalObjects 11 }

        -- 1.3.6.1.4.1.9839.2.1.1.12
        diginputpol2 OBJECT-TYPE
                    SYNTAX Integer32 (0..1)
                    UNITS "N/A"
                    MAX-ACCESS read-write
                    STATUS current
                    DESCRIPTION "Polarity digital imput 2"
                    ::= { digitalObjects 12 }

        -- 1.3.6.1.4.1.9839.2.1.1.13
        alrdefrost OBJECT-TYPE
                    SYNTAX Integer32 (0..1)
                    UNITS "N/A"
                    MAX-ACCESS read-only
                    STATUS current
                    DESCRIPTION "Timeout defrost alarm"
                    ::= { digitalObjects 13 }



        -- 1.3.6.1.4.1.9839.2.1.2
        analogObjects OBJECT IDENTIFIER ::= { wlprobeMIB 2 }

        -- 1.3.6.1.4.1.9839.2.1.2.1
        probe1 OBJECT-TYPE
                    SYNTAX Integer32 (-32767..32767)
                    UNITS "N/A"
                    MAX-ACCESS read-only
                    STATUS current
                    DESCRIPTION "Temperature probe 1"
                    ::= { analogObjects 1 }

        -- 1.3.6.1.4.1.9839.2.1.2.2
        probe2 OBJECT-TYPE
                    SYNTAX Integer32 (-32767..32767)
                    UNITS "N/A"
                    MAX-ACCESS read-only
                    STATUS current
                    DESCRIPTION "Temperature probe 2"
                    ::= { analogObjects 2 }

        -- 1.3.6.1.4.1.9839.2.1.2.3
        thrshitempprobe1 OBJECT-TYPE
                    SYNTAX Integer32 (0..1250)
                    UNITS "N/A"
                    MAX-ACCESS read-write
                    STATUS current
                    DESCRIPTION "Threshold alarm high temperature probe 1"
                    ::= { analogObjects 3 }

        -- 1.3.6.1.4.1.9839.2.1.2.4
        thrshitempprobe2 OBJECT-TYPE
                    SYNTAX Integer32 (0..1250)
                    UNITS "N/A"
                    MAX-ACCESS read-write
                    STATUS current
                    DESCRIPTION "Threshold alarm high temperature probe 2"
                    ::= { analogObjects 4 }

        -- 1.3.6.1.4.1.9839.2.1.2.5
        thrslotempprobe1 OBJECT-TYPE
                    SYNTAX Integer32 (-500..100)
                    UNITS "N/A"
                    MAX-ACCESS read-write
                    STATUS current
                    DESCRIPTION "Threshold alarm low temperature probe 1"
                    ::= { analogObjects 5 }

        -- 1.3.6.1.4.1.9839.2.1.2.6
        thrslotempprobe2 OBJECT-TYPE
                    SYNTAX Integer32 (-500..100)
                    UNITS "N/A"
                    MAX-ACCESS read-write
                    STATUS current
                    DESCRIPTION "Threshold alarm low temperature probe 2"
                    ::= { analogObjects 6 }



        -- 1.3.6.1.4.1.9839.2.1.3
        integerObjects OBJECT IDENTIFIER ::= { wlprobeMIB 3 }

        -- 1.3.6.1.4.1.9839.2.1.3.1
        hightempdelay OBJECT-TYPE
                    SYNTAX Integer32 (0..120)
                    UNITS "min"
                    MAX-ACCESS read-write
                    STATUS current
                    DESCRIPTION "High temperature delay alarm"
                    ::= { integerObjects 1 }

        -- 1.3.6.1.4.1.9839.2.1.3.2
        defrostdelay OBJECT-TYPE
                    SYNTAX Integer32 (0..120)
                    UNITS "min"
                    MAX-ACCESS read-write
                    STATUS current
                    DESCRIPTION "Defrost delay alarm"
                    ::= { integerObjects 2 }

        -- 1.3.6.1.4.1.9839.2.1.3.3
        ampsignal OBJECT-TYPE
                    SYNTAX Integer32 (0..10)
                    UNITS "N/A"
                    MAX-ACCESS read-only
                    STATUS current
                    DESCRIPTION "Amplitude signal received"
                    ::= { integerObjects 3 }


	
	END

--
-- CAREL-wlprobe.MIB
--

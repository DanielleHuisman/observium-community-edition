--
-- EPON-EOC-MIB.my
-- MIB generated by MG-SOFT Visual MIB Builder Version 3.0 Build 253
-- Wednesday, June 15, 2011 at 18:05:47
--

	EPON-EOC-MIB DEFINITIONS ::= BEGIN
 
		IMPORTS
			enterprises, MODULE-IDENTITY, OBJECT-IDENTITY			
				FROM SNMPv2-SMI			
			TEXTUAL-CONVENTION			
				FROM SNMPv2-TC;
	
	
		eponeoc MODULE-IDENTITY 
			LAST-UPDATED "201005271056Z"		-- May 27, 2010 at 10:56 GMT
			ORGANIZATION 
				"epon eoc factory."
			CONTACT-INFO 
				""
			DESCRIPTION 
				"epon eoc common mib module"
			::= { enterprises 34592 }
		
	
--
-- Textual conventions
--
	
		OperSwitch ::= TEXTUAL-CONVENTION
			STATUS current
			DESCRIPTION 
				"Device function operation switch type"
			SYNTAX INTEGER
				{
				enable(1),
				disable(2)
				}
			
		DeviceStatus ::= TEXTUAL-CONVENTION
			STATUS current
			DESCRIPTION 
				"Device work status type. One device or dummy device may
				have following five work status:
				notPresent(1): the device is not present (not installed)
				offline(2):the device is present,but can not be communicated (or failed to get its info)
				online(3):the device is present and can be communicated
				normal(4):the device is online and work well
				abnormal(5): the device is online but work abnormal for some reason"
			SYNTAX INTEGER
				{
				notPresent(1),
				offline(2),
				online(3),
				normal(4),
				abnormal(5)
				}
			
		DataDirection ::= TEXTUAL-CONVENTION
			STATUS current
			DESCRIPTION 
				"A data channel normally have two direction, up and down"
			SYNTAX INTEGER
				{
				upstream(1),
				downstream(2)
				}
			
		DeviceOperation ::= TEXTUAL-CONVENTION
			STATUS current
			DESCRIPTION 
				"This type defines an operate action aggregate"
			SYNTAX INTEGER
				{
				reset(2),
				default(3),
				saveConfig(4),
				restore(5),
				delete(6)
				}
			
		LedStatus ::= TEXTUAL-CONVENTION
			STATUS current
			DESCRIPTION 
				"Led status"
			SYNTAX INTEGER
				{
				on(1),
				off(2),
				blink(3)
				}
			
		DeviceType ::= TEXTUAL-CONVENTION
			STATUS current
			DESCRIPTION 
				"Device type convention. Define all PBB device type value.
				
				----------------------------------
				| family | series | class | type |
				----------------------------------
				   8b        8b      8b      8b
				
				refer to document <pducuct type defines>"
			SYNTAX INTEGER
				{
				EPON(16842752),
				CHASSIS(16843009),
				OLT(16843265),
				PON(16843521),
				PON(16909057),
				EPON-1U(17105153),
				OLT(17105409),
				PON(17105665),
				ONU4D-B(16974081),
				ONU4D-B(16974082),
				ONU4D-B(16974083),
				ONU8D-B(16974084),
				ONU4D(16974085),
				ONU1D(16974086),
				ONU1D-G(16974087),
				ONU2D-G(16974088),
				ONU2D-GM(16974095),
				ONU4D-GM(16974094),
				ONU4D-P(16974089),
				ONU3D-M(16974090),
				ONU4D(16974091),
				ONU2D-M(16974092),
				ONU4D2P(16974337),
				ONU4D2P-P(16974338),
				ONU4D1R(16974593),
				ONU4D1R-P(16974594),
				ONU4D2P1R(16974849),
				ONU4D2P1R(17040129),
				ONU4D2P1R-P(16974850),
				ONU24D(17039617),
				
				ONU1FE(825241960),
				ONU1GE(825307496),
				ONU2GE(825307757),
				ONU4FE(825242728),
				ONU4GE(825308258),
				ONU4GE(825308269),
				ONU4FE1RF(858797160)
				}
			
	
--
-- Node definitions
--
	
		-- 1.3.6.1.4.1.34592.1
		ipProduct OBJECT-IDENTITY
			STATUS current
			DESCRIPTION 
				"Defines the base identifier containing the definition of ip products line.
				"
			::= { eponeoc 1 }
		
		-- 1.3.6.1.4.1.34592.1.1
		mediaConverter OBJECT-IDENTITY
			STATUS current
			DESCRIPTION 
				"Defines the base identifier for the subtree
				supported by media converter line products.
				"
			::= { ipProduct 1 }
		
		-- 1.3.6.1.4.1.34592.1.2
		switch OBJECT-IDENTITY
			STATUS current
			DESCRIPTION 
				"Defines the base identifier for the subtree
				supported by smartCPE Switch line products.
				"
			::= { ipProduct 2 }
		
		-- 1.3.6.1.4.1.34592.1.3
		epon OBJECT-IDENTITY
			STATUS current
			DESCRIPTION 
			""
			::= { ipProduct 3 }
		
		-- 1.3.6.1.4.1.34592.1.4
		eoc OBJECT-IDENTITY
			STATUS current
			DESCRIPTION 
			""
			::= { ipProduct 4 }
		
	
	END

--
-- EPON-EOC-MIB.my
--

--
 -- WWP-DHCP-CLIENT-MIB.my
 --
 --

 WWP-DHCP-CLIENT-MIB DEFINITIONS ::= BEGIN

 IMPORTS 		
   Integer32, Unsigned32, OBJECT-TYPE, MODULE-IDENTITY			
	    FROM SNMPv2-SMI			
   DisplayString, TruthValue			
	    FROM SNMPv2-TC						
   wwpModules			
	    FROM WWP-SMI;
	
	
 wwpDhcpClientMIB MODULE-IDENTITY
	    LAST-UPDATED "200104031700Z"
	    ORGANIZATION "World Wide Packets, Inc"
	    CONTACT-INFO
		    "   Mib Meister
		  	Postal: World Wide Packets
		        P.O. Box 950
		        Veradale, WA 99037
		        USA
		 	Phone:  +1 509 242 9000
			Email:  mib.meister@worldwidepackets.com"
	    DESCRIPTION
		    "The MIB module to configure DHCP on WWP products."
	    REVISION    "200104031700Z"
	    DESCRIPTION
		    "Initial creation."
	    ::= { wwpModules 18 }
						
 --
 -- Node definitions
 --
	
 wwpDhcpClientMIBObjects OBJECT IDENTIFIER ::= { wwpDhcpClientMIB 1 }
 
 -- Dhcp Clients
 --
 wwpDhcpClient OBJECT IDENTIFIER ::= { wwpDhcpClientMIBObjects 1 }

 		
 -- Notifications 
  
 wwpDhcpClientMIBNotificationPrefix  OBJECT IDENTIFIER ::= { wwpDhcpClientMIB 2 } 
 wwpDhcpClientMIBNotifications       OBJECT IDENTIFIER ::=  
                       { wwpDhcpClientMIBNotificationPrefix 0 }

 -- Conformance information 
 
 wwpDhcpClientMIBConformance OBJECT IDENTIFIER ::= { wwpDhcpClientMIB 3 } 
 wwpDhcpClientMIBCompliances OBJECT IDENTIFIER ::= { wwpDhcpClientMIBConformance 1 } 		
 wwpDhcpClientMIBGroups      OBJECT IDENTIFIER ::= { wwpDhcpClientMIBConformance 2 }


 wwpDhcpActivate     OBJECT-TYPE
     SYNTAX          TruthValue
     MAX-ACCESS      read-write
     STATUS          current
     DESCRIPTION
    	     "Activate the DHCP operation with a value of True(1) or 
             stop it with False(2)."
     DEFVAL { false }                
     ::= { wwpDhcpClient 1 }	
 				 		 

 wwpDhcpIfName   OBJECT-TYPE
     SYNTAX       DisplayString(SIZE (0..32))
     MAX-ACCESS   read-write
     STATUS       current
     DESCRIPTION
             "The ifName associated with the Dhcp Operation."
     DEFVAL  { "mgmt" }
     ::= { wwpDhcpClient 2 }

 wwpDhcpDiscoveryMsgInterval  OBJECT-TYPE
     SYNTAX          Integer32(0..2147483647)
     UNITS           "miliseconds"
     MAX-ACCESS      read-write
     STATUS          current     
     DESCRIPTION
             "The time interval for discovery messages issued before the client
             received the first reply."
     DEFVAL  { 125 }
     ::= { wwpDhcpClient 3 }

 wwpDhcpLeaseTime  OBJECT-TYPE
     SYNTAX          Integer32(0..2147483647)
     UNITS           "Hours"
     MAX-ACCESS      read-write
     STATUS          current     
     DESCRIPTION
             "The requested lease time option to be used with DHCPDISCOVER or 
             DHCPREQUEST messages."
     DEFVAL  { 24 }
     ::= { wwpDhcpClient 4 }

 END

 --
 -- WWP-DHCP-CLIENT-MIB.my
 --

--
 -- WWP-ENVIRON-MIB.my
 --
 --

 WWP-ENVIRON-MIB DEFINITIONS ::= BEGIN

 IMPORTS 		
	TEXTUAL-CONVENTION FROM SNMPv2-TC
     NOTIFICATION-TYPE, Counter32, Integer32, OBJECT-TYPE, MODULE-IDENTITY			
	    FROM SNMPv2-SMI
     TruthValue, DisplayString
            FROM SNMPv2-TC
     wwpModules			
	    FROM WWP-SMI;	

 wwpEnvironMIB MODULE-IDENTITY
	    LAST-UPDATED "200104031700Z"
	    ORGANIZATION "World Wide Packets, Inc"
	    CONTACT-INFO
		    "   Mib Meister
		  	Postal: World Wide Packets
		        P.O. Box 950
		        Veradale, WA 99037
		        USA
		 	Phone:  +1 509 242 9000
			Email:  mib.meister@worldwidepackets.com"
	    DESCRIPTION
		    "The MIB module for the WWP Specifc environment. It contains the 
                     environment variables for the WWP System."
            REVISION     "200304280000Z"  -- 28th April. 2003  
	    DESCRIPTION
		    "Updated the battery status. Added the four notifications
                    for the battery state change. The new added notification
                    wwpEnvPortalPowerSourceNotification replaces the 
                    wwpEnvPowerSwitchNotification."
	    REVISION     "200303110000Z"  -- 11th March. 2003  
	    DESCRIPTION
		    "Changed the temperature thresholds to be read-write.
		    Added Battery States and updated the notification for the 
		    battery states. Added dry contact, door and RF notifications."
	    REVISION    "200104031700Z"
	    DESCRIPTION
		    "Initial creation."
	    ::= { wwpModules 13 }

 
 --
 -- Textual conventions
 --

 PortList ::= TEXTUAL-CONVENTION
    STATUS      current
    DESCRIPTION
        "Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1'
        then that port is included in the set of ports; the port
        is not included if its bit has a value of '0'."
    SYNTAX      OCTET STRING (SIZE (0..255))						

 --
 -- Node definitions
 --
	
 wwpEnvironMIBObjects OBJECT IDENTIFIER ::= { wwpEnvironMIB 1 }
 
 wwpEnviron OBJECT IDENTIFIER ::= { wwpEnvironMIBObjects 1 }

 -- the Battery Module 

 wwpEnvBatteryModule OBJECT IDENTIFIER ::= { wwpEnviron 1 } 

 -- the Power Supply module group.
          
 wwpEnvPowerSupplyModule OBJECT IDENTIFIER ::= { wwpEnviron 2 }

 -- the Fan module group.
 
 wwpEnvFanModule  OBJECT IDENTIFIER ::= { wwpEnviron 3 } 

 -- the Temp Module

 wwpEnvTempSensor OBJECT IDENTIFIER ::= { wwpEnviron 4 }  

 -- The Port Power Management Module

 wwpEnvPortPowerMgmt OBJECT IDENTIFIER ::= { wwpEnviron 5 } 

 -- The Environ Notif Objects
 
 wwpEnvNotif   OBJECT IDENTIFIER ::= { wwpEnviron 6 }
 
 -- The Portal Battery Module 

 wwpEnvPortalBatteryModule OBJECT IDENTIFIER ::= { wwpEnviron 7 } 
 
 --  The Door Module
 
 wwpEnvDoorModule  OBJECT IDENTIFIER ::= { wwpEnviron 8 }

 --  The Dry Contact Module
 
 wwpEnvDryContactModule  OBJECT IDENTIFIER ::= { wwpEnviron 9 }

 -- The RF module
 
 wwpEnvRFModule  OBJECT IDENTIFIER ::= { wwpEnviron 10 }

 -- Notifications 
  
 wwpEnvironMIBNotificationPrefix  OBJECT IDENTIFIER ::= { wwpEnvironMIB 2 } 
 wwpEnvironMIBNotifications       OBJECT IDENTIFIER ::=  
                       { wwpEnvironMIBNotificationPrefix 0 }

 -- Conformance information 
 
 wwpEnvironMIBConformance OBJECT IDENTIFIER ::= { wwpEnvironMIB 3 } 
 wwpEnvironMIBCompliances OBJECT IDENTIFIER ::= { wwpEnvironMIBConformance 1 } 		
 wwpEnvironMIBGroups      OBJECT IDENTIFIER ::= { wwpEnvironMIBConformance 2 }


 wwpEnvBattStatus     OBJECT-TYPE
     SYNTAX           INTEGER {
	                   presentAndWorking(1),
                           presentButNotWorking(2),
		           notPresent(3)
	              } 
     MAX-ACCESS       read-only
     STATUS           current
     DESCRIPTION
	     "Describes the battery hardware the device is configured
	     with. For Portals, the Management station should use the
	     new added object wwpEnvPortalCurrentBattStatus
	     for the batery status."
     ::= { wwpEnvBatteryModule 1 }

 -- 
 -- Power Module
 --      
 wwpEnvPowerTable  OBJECT-TYPE
     SYNTAX      SEQUENCE OF WwpEnvPowerEntry
     MAX-ACCESS  not-accessible
     STATUS      current
     DESCRIPTION
             "A list of power supply entries."
     ::= { wwpEnvPowerSupplyModule 1 }

 wwpEnvPowerEntry     OBJECT-TYPE
     SYNTAX         WwpEnvPowerEntry
     MAX-ACCESS     not-accessible
     STATUS         current
     DESCRIPTION
             "An entry in the powerTable providing objects for a
             power supply."
     INDEX  { wwpEnvPowerSupplyNum }
     ::= { wwpEnvPowerTable 1 }

 WwpEnvPowerEntry ::=  SEQUENCE  {
     wwpEnvPowerSupplyNum         Integer32,
     wwpEnvPowerSupplyState       INTEGER,
     wwpEnvPowerSupplyType        INTEGER,
     wwpEnvPowerSupplyRedundancy  INTEGER 
 }

 wwpEnvPowerSupplyNum  OBJECT-TYPE
     SYNTAX            Integer32(1..2147483647) 
     MAX-ACCESS        read-only
     STATUS            current
     DESCRIPTION
             "Denotes the power supply."
     ::= { wwpEnvPowerEntry 1 }

 wwpEnvPowerSupplyState  OBJECT-TYPE
     SYNTAX  INTEGER  {
                  infoNotAvailable(1),
                  notInstalled(2),
                  installedAndOperating(3),
                  installedAndNotOperating(4)
              }
     MAX-ACCESS  read-only
     STATUS      current
     DESCRIPTION
             "Denotes the power supply's state."
     ::= { wwpEnvPowerEntry 2 }

 wwpEnvPowerSupplyType  OBJECT-TYPE
     SYNTAX       INTEGER  {
                       ac-dc(1),
                       dc-dc(2),
                       notSupported(3),  -- Object is not supported
                       highOutput(4), 
                       external(5)
                  }
      MAX-ACCESS  read-only
      STATUS      current
      DESCRIPTION
              "Denotes the power supply type."
      ::= { wwpEnvPowerEntry 3 }

 wwpEnvPowerSupplyRedundancy  OBJECT-TYPE
     SYNTAX  INTEGER  {
                  redundant(1),
                  notRedundant(2),
                  notSupported(3)  -- Object is not supported
             }
     MAX-ACCESS  read-only
     STATUS      current
     DESCRIPTION
             "Denotes whether or not the power supply is redundant."
     ::= { wwpEnvPowerEntry 4 }

 wwpEnvRedPowerSupplyNotifEnabled OBJECT-TYPE
     SYNTAX      TruthValue
     MAX-ACCESS  read-write
     STATUS      deprecated
     DESCRIPTION
             "This variable  indicates  whether  the  system
             generates the wwpEnvRedPowerSupplyNotification. 
             A false value prevents this notifications
             from being generated by this system."
    DEFVAL { true }
    ::= { wwpEnvPowerSupplyModule 2 }

 --
 --  The Fan module group
 --
 wwpEnvFanModuleTable  OBJECT-TYPE
     SYNTAX      SEQUENCE OF WwpEnvFanModuleEntry
     MAX-ACCESS  not-accessible
     STATUS      current
     DESCRIPTION
             "A list of fan module entries."
     ::= { wwpEnvFanModule 1 }

 wwpEnvFanModuleEntry  OBJECT-TYPE
     SYNTAX         WwpEnvFanModuleEntry
     MAX-ACCESS     not-accessible
     STATUS         current
     DESCRIPTION
             "An entry in the fan module Table providing objects for a
             fan module."
     INDEX  { wwpEnvFanModuleNum }
     ::= { wwpEnvFanModuleTable 1 }

 WwpEnvFanModuleEntry ::=  SEQUENCE  {
     wwpEnvFanModuleNum          Integer32,
     wwpEnvFanModuleState        INTEGER,
     wwpEnvFanAvgSpeed           Integer32,
     wwpEnvFanCurrentSpeed       Integer32,
     wwpEnvFanMinSpeed           Integer32
 }

 wwpEnvFanModuleNum  OBJECT-TYPE
     SYNTAX        Integer32 (1..2147483647)
     MAX-ACCESS    read-only 
     STATUS        current
     DESCRIPTION
             "Denotes the Fan module."
     ::= { wwpEnvFanModuleEntry 1 }

 wwpEnvFanModuleState OBJECT-TYPE
     SYNTAX        INTEGER  {
                        infoNotAvailable(1),
                        notInstalled(2),
                        installedAndOperating(3),
                        installedAndNotOperating(4)
                   }
     MAX-ACCESS    read-only
     STATUS        current
     DESCRIPTION
             "Denotes the fan modules state."
     ::= { wwpEnvFanModuleEntry 2 }

 wwpEnvFanAvgSpeed OBJECT-TYPE
     SYNTAX        Integer32 (0..2147483647)
     UNITS         "rpm"
     MAX-ACCESS    read-only
     STATUS        current
     DESCRIPTION
             "The fans average speed in RPM.  The average is calculated
	     on a continuous basis from system startup."
     ::= { wwpEnvFanModuleEntry 3 }

 wwpEnvFanCurrentSpeed OBJECT-TYPE
     SYNTAX        Integer32 (0..2147483647)
     UNITS         "rpm"
     MAX-ACCESS    read-only
     STATUS        current
     DESCRIPTION
    	     "The current speed of the fan in RPM."
     ::= { wwpEnvFanModuleEntry 4 }

 wwpEnvFanMinSpeed OBJECT-TYPE
     SYNTAX        Integer32 (0..2147483647)
     UNITS         "rpm"
     MAX-ACCESS    read-only
     STATUS        current
     DESCRIPTION
    	     "The minimum speed of the fan in RPM."
     ::= { wwpEnvFanModuleEntry 5 }
 
 
 wwpEnvFanModuleNotifEnabled OBJECT-TYPE
     SYNTAX      TruthValue
     MAX-ACCESS  read-write
     STATUS      current
     DESCRIPTION
             "This variable  indicates  whether  the  system
             generates the wwpEnvFanModuleNotification. 
             A false value prevents this notifications
             from being generated by this system."
    DEFVAL { true }
    ::= { wwpEnvFanModule 2 }

 --
 --  The Temp module group
 --
 wwpEnvTempSensorTable  OBJECT-TYPE
     SYNTAX      SEQUENCE OF WwpEnvTempSensorEntry
     MAX-ACCESS  not-accessible
     STATUS      current
     DESCRIPTION
             "A list of Temp Sensors entries."
     ::= { wwpEnvTempSensor 1 }

 wwpEnvTempSensorEntry  OBJECT-TYPE
     SYNTAX         WwpEnvTempSensorEntry
     MAX-ACCESS     not-accessible
     STATUS         current
     DESCRIPTION
             "An entry in the Temp Sensor Table providing objects for a
             Temp Sensor."
     INDEX  { wwpEnvTempSensorNum }
     ::= { wwpEnvTempSensorTable 1 }

 WwpEnvTempSensorEntry ::=  SEQUENCE  {
     wwpEnvTempSensorNum               Integer32,
     wwpEnvTempSensorValue             Integer32,
     wwpEnvTempSensorHighThreshold     Integer32,
     wwpEnvTempSensorLowThreshold      Integer32,
     wwpEnvTempSensorState             INTEGER
 }

 wwpEnvTempSensorNum  OBJECT-TYPE
     SYNTAX        Integer32 (1..2147483647)
     MAX-ACCESS    read-only 
     STATUS        current
     DESCRIPTION
             "Denotes the Temp sensor module."
     ::= { wwpEnvTempSensorEntry 1 }

 wwpEnvTempSensorValue OBJECT-TYPE
     SYNTAX        Integer32
     UNITS         "degrees Celsius"
     MAX-ACCESS    read-only
     STATUS        current
     DESCRIPTION
    	     "The value of temperature measured by the sensor 
              inside the device in degrees C."
     ::= { wwpEnvTempSensorEntry 2 }
 
 wwpEnvTempSensorHighThreshold   OBJECT-TYPE
     SYNTAX       Integer32
     UNITS        "degrees Celsius"
     MAX-ACCESS   read-write
     STATUS       current
     DESCRIPTION
	     "The highest value that the object wwpEnvTempSensorValue
              may obtain at which a wwpEnvMIBTempNotification is sent."
     ::= { wwpEnvTempSensorEntry 3 }

 wwpEnvTempSensorLowThreshold   OBJECT-TYPE
     SYNTAX       Integer32
     UNITS        "degrees Celsius"
     MAX-ACCESS   read-write
     STATUS       current
     DESCRIPTION
	     "The Lowest value that the object wwpEnvTempSensorValue
              may obtain at which a wwpEnvMIBTempNotification is sent."
     ::= { wwpEnvTempSensorEntry 4 }

 wwpEnvTempSensorState   OBJECT-TYPE
     SYNTAX       INTEGER {
                        higherThanThreshold(0),
                        normal(1),
                        lowerThanThreshold(2)
                  }
     MAX-ACCESS   read-only
     STATUS       current
     DESCRIPTION
	     "The state indicates whether the current temp is greater than,
             equal to or less than the threshold state."
     ::= { wwpEnvTempSensorEntry 5 }

 wwpEnvTempNotifEnabled OBJECT-TYPE
     SYNTAX      TruthValue
     MAX-ACCESS  read-write
     STATUS      current
     DESCRIPTION
             "This variable  indicates  whether  the  system
             generates the wwpEnvTempNotification. 
             A false value prevents this notifications
             from being generated by this system."
    DEFVAL { true }
    ::= { wwpEnvTempSensor 2 }

 --
 --  The Port Power Management group
 --
 wwpPortPowerMgmtTable  OBJECT-TYPE
     SYNTAX      SEQUENCE OF WwpPortPowerMgmtEntry
     MAX-ACCESS  not-accessible
     STATUS      current
     DESCRIPTION
             "A list of Port Power Management entries. This table affects
             the port power only when the input power supply is Battery."
     ::= { wwpEnvPortPowerMgmt 1 }

 wwpPortPowerMgmtEntry  OBJECT-TYPE
     SYNTAX         WwpPortPowerMgmtEntry
     MAX-ACCESS     not-accessible
     STATUS         current
     DESCRIPTION
             "An entry in the Port Power Mgmt Table providing objects for 
             Port Power Management."
     INDEX  { wwpEnvPortBankId }
     ::= { wwpPortPowerMgmtTable 1 }

 WwpPortPowerMgmtEntry ::=  SEQUENCE  {
     wwpEnvPortBankId              Integer32,
     wwpEnvPortMap                 PortList,
     wwpEnvPortBankOn              INTEGER
 }

 wwpEnvPortBankId  OBJECT-TYPE
     SYNTAX        Integer32 (1..2147483647)
     MAX-ACCESS    read-only 
     STATUS        current
     DESCRIPTION
             "Denotes the Port Bank module. A Bank is a set of ports
             for the power management when the source of the input 
             power is switched to battery."
     ::= { wwpPortPowerMgmtEntry 1 }

 wwpEnvPortMap     OBJECT-TYPE
     SYNTAX        PortList
     MAX-ACCESS    read-only 
     STATUS        current
     DESCRIPTION
             "The port map associated with this BankId."
     ::= { wwpPortPowerMgmtEntry 2 }

 wwpEnvPortBankOn  OBJECT-TYPE
     SYNTAX        INTEGER {
                        off(0),
                        on(1)
                   }
     MAX-ACCESS    read-write 
     STATUS        current
     DESCRIPTION
             "The object to decide whether the port related to this Bank 
             should be on or not if the input power supply is switched
             to Battery."
     ::= { wwpPortPowerMgmtEntry 3 }

 --
 -- notif group
 --  
 wwpPowerSwitchingOp OBJECT-TYPE
     SYNTAX         INTEGER {
                        none(0),
                        acToBattery(1),
                        bateryToAC(2)                     
                    }
     --MAX-ACCESS     accessible-for-notify
     MAX-ACCESS     read-only
     STATUS         current
     DESCRIPTION
             "The object to notify whether the input power supply is switching
             from ac to Battery or vice versa."
     ::= { wwpEnvNotif 1 }

 --
 -- portal battery group
 --
 wwpEnvPortalBatteryStatus     OBJECT-TYPE
     SYNTAX           INTEGER {
                           present(1),
	                   missing(2)
	              } 
     MAX-ACCESS       read-only
     STATUS           current
     DESCRIPTION
	     "Describes the current status of the 
             battery. If battery is connected then the
             status is indicated as 'present'." 
     ::= { wwpEnvPortalBatteryModule 1 }
  
 wwpEnvPortalBatteryVoltageLevel     OBJECT-TYPE
     SYNTAX           INTEGER {
                           normal(1),
	                   low(2)
	              } 
     MAX-ACCESS       read-only
     STATUS           current
     DESCRIPTION
	     "Describes the current voltage level of the 
             battery." 
     ::= { wwpEnvPortalBatteryModule 2 }
     
 wwpEnvPortalBatteryCondition  OBJECT-TYPE
     SYNTAX           INTEGER {
                           good(1),
	                   bad(2)
	              } 
     MAX-ACCESS       read-only
     STATUS           current
     DESCRIPTION
	     "Describes the current condition of the battery." 
     ::= { wwpEnvPortalBatteryModule 3 }
     
 wwpEnvPortalPowerSource OBJECT-TYPE
     SYNTAX           INTEGER {
                           primaryPower(1),
	                   battery(2)
	              } 
     MAX-ACCESS       read-only
     STATUS           current
     DESCRIPTION
	     "Describes the current power source for the device." 
     ::= { wwpEnvPortalBatteryModule 4 }
     
 wwpEnvBatteryNormalStateName     OBJECT-TYPE
     SYNTAX           DisplayString (SIZE(1..128))  
     MAX-ACCESS       read-write
     STATUS           current
     DESCRIPTION
	     "The state name associated with the low state
	     of the battery."
     ::= { wwpEnvPortalBatteryModule 5 }
     
 wwpEnvBatteryLowStateName     OBJECT-TYPE
     SYNTAX           DisplayString (SIZE(1..128))  
     MAX-ACCESS       read-write
     STATUS           current
     DESCRIPTION
	     "The state name associated with the normal state
	     of the battery."
     ::= { wwpEnvPortalBatteryModule 6 }

 wwpEnvBatteryGoodStateName     OBJECT-TYPE
     SYNTAX           DisplayString (SIZE(1..128))  
     MAX-ACCESS       read-write
     STATUS           current
     DESCRIPTION
	     "The state name associated with the good state
	     of the battery."
     ::= { wwpEnvPortalBatteryModule 7 }
 
 wwpEnvBatteryBadStateName     OBJECT-TYPE
     SYNTAX           DisplayString (SIZE(1..128))  
     MAX-ACCESS       read-write
     STATUS           current
     DESCRIPTION
	     "The state name associated with the bad state
	     of the battery."
     ::= { wwpEnvPortalBatteryModule 8 }
     
 wwpEnvBatteryPresentStateName     OBJECT-TYPE
     SYNTAX           DisplayString (SIZE(1..128))  
     MAX-ACCESS       read-write
     STATUS           current
     DESCRIPTION
	     "The state name associated with the battery state 
             'present'." 
     ::= { wwpEnvPortalBatteryModule 9 }
     
 wwpEnvBatteryMissingStateName     OBJECT-TYPE
     SYNTAX           DisplayString (SIZE(1..128))  
     MAX-ACCESS       read-write
     STATUS           current
     DESCRIPTION
	     "The state name associated with the battery state 
             'missing'." 
     ::= { wwpEnvPortalBatteryModule 10 }
    
 wwpEnvBatteryPowerPrimaryStateName     OBJECT-TYPE
     SYNTAX           DisplayString (SIZE(1..128))  
     MAX-ACCESS       read-write
     STATUS           current
     DESCRIPTION
             "The state name associated with the state when the
              device is on primary power." 
     ::= { wwpEnvPortalBatteryModule 11 }
      
 wwpEnvBatteryPowerBatteryStateName     OBJECT-TYPE
     SYNTAX           DisplayString (SIZE(1..128))  
     MAX-ACCESS       read-write
     STATUS           current
     DESCRIPTION
	     "The state name associated with the state when the
             device is on battery power." 
     ::= { wwpEnvPortalBatteryModule 12 }
     
 
      
 wwpEnvBatteryLowStateNotifEnabled OBJECT-TYPE
     SYNTAX      TruthValue
     MAX-ACCESS  read-write
     STATUS      current
     DESCRIPTION
             "This variable indicates whether the system
             will generate the wwpEnvPortalBatteryStatusNotification
             in case of battery state changing from normal to low
             or vice versa. 
             A false value prevents this notifications
             from being generated by this system."
    DEFVAL { true }
    ::= { wwpEnvPortalBatteryModule 13 }
     
 wwpEnvBatteryBadStateNotifEnabled OBJECT-TYPE
     SYNTAX      TruthValue
     MAX-ACCESS  read-write
     STATUS      current
     DESCRIPTION
             "This variable indicates whether the system
             will generate the wwpEnvPortalBatteryStatusNotification
             in case of battery state changing from good to bad
             or vice versa.
             A false value prevents this notifications
             from being generated by this system."
    DEFVAL { true }
    ::= { wwpEnvPortalBatteryModule 14 }
    
 wwpEnvBatteryMissingStateNotifEnabled OBJECT-TYPE
     SYNTAX      TruthValue
     MAX-ACCESS  read-write
     STATUS      current
     DESCRIPTION
             "This variable indicates whether the system
             will generate the wwpEnvPortalBatteryStatusNotification
             in case of battery state changing from present to missing
             or vice versa.
             A false value prevents this notifications
             from being generated by this system."
    DEFVAL { true }
    ::= { wwpEnvPortalBatteryModule 15 }
    
 wwpEnvBatteryPowerNotifEnabled OBJECT-TYPE
     SYNTAX      TruthValue
     MAX-ACCESS  read-write
     STATUS      current
     DESCRIPTION
             "This variable indicates whether the system
             will generate the wwpEnvPortalBatteryStatusNotification
             in case of input power changing from primary to battery
             or vice versa.
             A false value prevents this notifications
             from being generated by this system."
    DEFVAL { true }
    ::= { wwpEnvPortalBatteryModule 16 }
 
 wwpEnvBatteryPeriodicTrapsTimer OBJECT-TYPE
     SYNTAX            INTEGER(0..8760) 
     MAX-ACCESS        read-write
     STATUS            current
     DESCRIPTION
             "Adjusts the amount of time, in hours, when the current
             state of the battery is evaluated and status traps are
             automatically issued.  When set to zero (0) no periodic
             evaluation of the battery is performed."
     DEFVAL { 0 }
     ::= { wwpEnvPortalBatteryModule 17 }
     
 wwpEnvBatteryPowerUpTrapsEnable OBJECT-TYPE           
     SYNTAX      TruthValue
     MAX-ACCESS  read-write
     STATUS      current
     DESCRIPTION
             "When set to true, upon portal power-up the state of
             the battery is evaluated and status traps are issued.
             When set to false, no portal power-up battery state
             traps will be issued."
    DEFVAL { false }
    ::= { wwpEnvPortalBatteryModule 18 }
  
 --
 -- door group
 --
 wwpEnvDoorState      OBJECT-TYPE
     SYNTAX           INTEGER {
                          open(1),
			  close(2)
		      } 
     MAX-ACCESS       read-only
     STATUS           current
     DESCRIPTION
	     "The state of the door."
     ::= { wwpEnvDoorModule 1 }
     
 wwpEnvDoorNotifEnabled OBJECT-TYPE
     SYNTAX      TruthValue
     MAX-ACCESS  read-write
     STATUS      current
     DESCRIPTION
             "This variable  indicates  whether  the  system
             generates the wwpEnvDoorStateChgNotification. 
             A false value prevents this notifications
             from being generated by this system."
    DEFVAL { true }
    ::= { wwpEnvDoorModule 2 }

 --
 -- dry contact group
 --
 wwpEnvDryContactOpenStateName      OBJECT-TYPE
     SYNTAX           DisplayString ( SIZE(1..128))     
     MAX-ACCESS       read-write
     STATUS           current
     DESCRIPTION
	     "The state name associated with the open state
	     of the dry contact."
     ::= { wwpEnvDryContactModule 1 }
 
 wwpEnvDryContactOpenStateChgAccumulate   OBJECT-TYPE
     SYNTAX           INTEGER {
                          enable(1),
			  disable(2)
		      } 
     MAX-ACCESS       read-write
     STATUS           current
     DESCRIPTION
	     "Setting this object to 'enable' will cause the
	     system to accumulate open state changes." 
     ::= { wwpEnvDryContactModule 2 }
 
 wwpEnvDryContactOpenStateCount   OBJECT-TYPE
     SYNTAX           Counter32     
     MAX-ACCESS       read-only
     STATUS           current
     DESCRIPTION
	     "The number of times the dry contact has 
	     entered the open state." 
     ::= { wwpEnvDryContactModule 3 }
             
 wwpEnvDryContactOpenStateNotifEnabled OBJECT-TYPE
     SYNTAX      TruthValue
     MAX-ACCESS  read-write
     STATUS      current
     DESCRIPTION
             "This variable  indicates  whether  the  system
             generates the wwpEnvDryContactOpenStateNotification. 
             A false value prevents this notifications
             from being generated by this system."
    DEFVAL { true }
    ::= { wwpEnvDryContactModule 4 }
 
 wwpEnvDryContactCloseStateName      OBJECT-TYPE
     SYNTAX           DisplayString ( SIZE(1..128))     
     MAX-ACCESS       read-write
     STATUS           current
     DESCRIPTION
	     "The state name associated with the close state
	     of the dry contact."
     ::= { wwpEnvDryContactModule 5 }
 
 wwpEnvDryContactCloseStateChgAccumulate   OBJECT-TYPE
     SYNTAX           INTEGER {
                          enable(1),
			  disable(2)
		      } 
     MAX-ACCESS       read-write
     STATUS           current
     DESCRIPTION
	     "Setting this object to 'enable' will cause the
	     system to accumulate close state changes." 
     ::= { wwpEnvDryContactModule 6 }
 
 wwpEnvDryContactCloseStateCount   OBJECT-TYPE
     SYNTAX           Counter32     
     MAX-ACCESS       read-only
     STATUS           current
     DESCRIPTION
             "The number of times the dry contact has 
	     entered the close state."  
     ::= { wwpEnvDryContactModule 7 }
             
 wwpEnvDryContactCloseStateNotifEnabled OBJECT-TYPE
     SYNTAX      TruthValue
     MAX-ACCESS  read-write
     STATUS      current
     DESCRIPTION
             "This variable  indicates  whether  the  system
             generates the wwpEnvDryContactCloseStateNotification. 
             A false value prevents this notifications
             from being generated by this system."
    DEFVAL { true }
    ::= { wwpEnvDryContactModule 8 }
 
 --
 -- RF module
 --
 wwpEnvRFModuleState   OBJECT-TYPE
     SYNTAX           INTEGER {
                          enable(1),
			  disable(2)
		      } 
     MAX-ACCESS       read-write
     STATUS           current
     DESCRIPTION
	     "Setting this object to 'enable' will set the
	     the RF state to 'enable'." 
     ::= { wwpEnvRFModule 1 }
     
 wwpEnvRFModuleSignalDetect   OBJECT-TYPE
     SYNTAX           TruthValue     
     MAX-ACCESS       read-only
     STATUS           current
     DESCRIPTION
	     "The status of signal detect by the RF Module." 
     ::= { wwpEnvRFModule 2 }
            
 wwpEnvPowerSupplyStatusNotification NOTIFICATION-TYPE
	OBJECTS	{
                wwpEnvPowerSupplyNum, 
                wwpEnvPowerSupplyState,
                wwpEnvPowerSupplyType              
		}
	STATUS	current
	DESCRIPTION
		"A wwpEnvPowerSupplyStatusNotification is sent if a 
		power supply state is changed."
	::= { wwpEnvironMIBNotifications 1 }
 
 wwpEnvFanModuleNotification NOTIFICATION-TYPE
	OBJECTS	{
		wwpEnvFanModuleNum,
                wwpEnvFanModuleState                
		}
	STATUS	current
	DESCRIPTION
		"A wwpEnvFanModuleNotification is sent if the 
		fan state changes."
	::= { wwpEnvironMIBNotifications 2 }

 wwpEnvTempNotification NOTIFICATION-TYPE
	OBJECTS	{
                wwpEnvTempSensorState,
                wwpEnvTempSensorValue,
                wwpEnvTempSensorHighThreshold,
                wwpEnvTempSensorLowThreshold          
		}
	STATUS	current
	DESCRIPTION
		"A wwpEnvTempNotification is sent if the 
		wwpEnvTempSensorState is changed."
	::= { wwpEnvironMIBNotifications 3 }

 wwpEnvPowerSwitchNotification NOTIFICATION-TYPE
	OBJECTS	{
                wwpPowerSwitchingOp           
		}
	STATUS	current
	DESCRIPTION
		"A wwpEnvPowerSwitchNotification is sent if the 
		input power supply is switched to Battery from the 
                AC power or switched from the Battery to the AC Power."
	::= { wwpEnvironMIBNotifications 4 }

 wwpEnvPortalBatteryStatusNotification NOTIFICATION-TYPE
	OBJECTS	{
	        wwpEnvPortalBatteryStatus
                }
	STATUS	current
	DESCRIPTION
		"A wwpEnvPortalBatteryStatusNotification is sent if the 
		Battery status changes. If the device supports the 
                configurable battery state names, then the corresponding 
                battery state name should also be sent with this notification." 
	::= { wwpEnvironMIBNotifications 5 }

 wwpEnvPortalBatteryVoltageLevelNotification NOTIFICATION-TYPE
	OBJECTS	{
	        wwpEnvPortalBatteryVoltageLevel
                }
	STATUS	current
	DESCRIPTION
		"A wwpEnvPortalBatteryVoltageLevelNotification is sent if the 
		Battery voltage level changes from normal to low or vice versa.
                If the device supports the configurable battery state names, then 
                the corresponding battery state name should also be sent with 
                this notification." 
	::= { wwpEnvironMIBNotifications 6 }
 
 wwpEnvPortalBatteryConditionNotification NOTIFICATION-TYPE
	OBJECTS	{
	        wwpEnvPortalBatteryCondition
                }
	STATUS	current
	DESCRIPTION
		"A wwpEnvPortalBatteryConditionNotification is sent if the 
		Battery condition changes from good to bad or vice versa.
                If the device supports the configurable battery state names, then 
                the corresponding battery state name should also be sent with 
                this notification." 
	::= { wwpEnvironMIBNotifications 7 }
         
 wwpEnvPortalPowerSourceNotification NOTIFICATION-TYPE
	OBJECTS	{
	        wwpEnvPortalPowerSource
                }
	STATUS	current
	DESCRIPTION
		"A wwpEnvPortalPowerSourceNotification is sent if the 
		Battery input power source changes from battery to primary
                power or vice versa. A device which supports 
                wwpEnvPowerSwitchNotification should not support this
                notification. If the device supports the configurable 
                battery state names, then the corresponding battery state 
                name should also be sent with this notification." 
	::= { wwpEnvironMIBNotifications 8 }
        
 wwpEnvDoorStateChgNotification NOTIFICATION-TYPE
	OBJECTS	{
	        wwpEnvDoorState
                }
	STATUS	current
	DESCRIPTION
		"A wwpEnvDoorStateChgNotification is sent if the 
		door state changes." 
	::= { wwpEnvironMIBNotifications 9 }
	
 wwpEnvDryContactOpenStateNotification NOTIFICATION-TYPE
	OBJECTS	{
	        wwpEnvDryContactOpenStateName,
		wwpEnvDryContactOpenStateCount
                }
	STATUS	current
	DESCRIPTION
		"A wwpEnvDryContactOpenStateNotification is sent when the 
		dry contact enters in the open state." 
	::= { wwpEnvironMIBNotifications 10 }
	
 wwpEnvDryContactCloseStateNotification NOTIFICATION-TYPE
	OBJECTS	{
	        wwpEnvDryContactCloseStateName,
		wwpEnvDryContactCloseStateCount
                }
	STATUS	current
	DESCRIPTION
		"A wwpEnvDryContactCloseStateNotification is sent when the 
		dry contact enters in the close state." 
	::= { wwpEnvironMIBNotifications 11 }
	

 END

 --
 -- WWP-ENVIRON-MIB
 --

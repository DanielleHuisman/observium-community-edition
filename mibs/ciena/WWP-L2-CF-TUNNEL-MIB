--
 -- WWP-L2-CF-TUNNEL-MIB.my
 --
 --

 WWP-L2-CF-TUNNEL-MIB DEFINITIONS ::= BEGIN

 IMPORTS 		
   Counter32, TimeTicks, Integer32, Unsigned32, OBJECT-TYPE, MODULE-IDENTITY			
	FROM SNMPv2-SMI			
   DisplayString, MacAddress, TEXTUAL-CONVENTION, RowStatus, TruthValue			
	FROM SNMPv2-TC							
   wwpModules			
	FROM WWP-SMI;

	
 wwpL2CFTunnelMIB MODULE-IDENTITY
	    LAST-UPDATED "200502251700Z"
	    ORGANIZATION "World Wide Packets, Inc"
	    CONTACT-INFO
		    "   Mib Meister
		  	Postal: World Wide Packets
		        P.O. Box 950
		        Veradale, WA 99037
		        USA
		 	Phone:  +1 509 242 9000
			Email:  mib.meister@worldwidepackets.com"
	    DESCRIPTION
		    "This MIB module is for the Layer 2 Control Frame Tunneling in WWP Portal Products"
	    REVISION    "200503081600Z"
	    DESCRIPTION
		    "Initial creation."
	    ::= { wwpModules 53 }

 --
 -- Textual conventions
 --					

 VlanId ::= TEXTUAL-CONVENTION
    STATUS      current
    DESCRIPTION
        "A 12-bit VLAN ID used in the VLAN Tag header."
    SYNTAX      INTEGER (1..4094)


 --
 -- Node definitions
 --
	
 wwpL2CFTunnelMIBObjects OBJECT IDENTIFIER ::= { wwpL2CFTunnelMIB 1 }
 
 wwpL2CFTunnel  OBJECT IDENTIFIER ::= { wwpL2CFTunnelMIBObjects 1 }

 -- Notifications 
  
 wwpL2CFTunnelMIBNotificationPrefix  OBJECT IDENTIFIER ::= { wwpL2CFTunnelMIB 2 } 
 wwpL2CFTunnelMIBNotifications       OBJECT IDENTIFIER ::=  
                       { wwpL2CFTunnelMIBNotificationPrefix 0 }

 -- Conformance information 
 
 wwpL2CFTunnelMIBConformance OBJECT IDENTIFIER ::= { wwpL2CFTunnelMIB 3 } 
 wwpL2CFTunnelMIBCompliances OBJECT IDENTIFIER ::= { wwpL2CFTunnelMIBConformance 1 } 		
 wwpL2CFTunnelMIBGroups      OBJECT IDENTIFIER ::= { wwpL2CFTunnelMIBConformance 2 }


 --
 -- L2 Control Frame Tunnel table
 --

 wwpL2CFTunnelTable OBJECT-TYPE
     SYNTAX     SEQUENCE OF WwpL2CFTunnelEntry
     MAX-ACCESS not-accessible
     STATUS     current
     DESCRIPTION
	     "VLAN table"
     ::= { wwpL2CFTunnel 1 }
		
 wwpL2CFTunnelEntry OBJECT-TYPE
     SYNTAX      WwpL2CFTunnelEntry
     MAX-ACCESS  not-accessible
     STATUS      current
     DESCRIPTION
	     "table of vlans"
     INDEX { wwpL2CFTunnelVlanId }
     ::= { wwpL2CFTunnelTable 1 }
		
 WwpL2CFTunnelEntry ::=  SEQUENCE { 
     wwpL2CFTunnelVlanId       		VlanId,
	  wwpL2CFTunnelOperStatus		   INTEGER,
	  wwpL2CFTunnelAdminStatus		   INTEGER,
	  wwpL2CFTunnelPriority				INTEGER,
     wwpL2CFTunnelRowStatus			RowStatus
 }

 wwpL2CFTunnelVlanId OBJECT-TYPE
     SYNTAX      VlanId
     MAX-ACCESS  read-only
     STATUS      current
     DESCRIPTION
	     "802.1Q VLAN ID (1-4094)"
     ::= { wwpL2CFTunnelEntry 1 }

 wwpL2CFTunnelOperStatus OBJECT-TYPE
     SYNTAX        INTEGER {
			operActive(0),
			operVlanNotExist(1),
			operInvalidVlanPortTag(2),
			operInvalidVlanNumPorts(3),
			operInvalidCfg(4),
			operDisabled(5)
		   }
     MAX-ACCESS    read-only
     STATUS        current
     DESCRIPTION
	     "The current operational state of tunnel."
     ::= { wwpL2CFTunnelEntry 2 }

 wwpL2CFTunnelAdminStatus OBJECT-TYPE
     SYNTAX        INTEGER {
			disabled(0),
			enabled(1)
		   }
     MAX-ACCESS    read-write
     STATUS        current
     DESCRIPTION
	     "The administratively desired status of Layer 2 control frame handling."
	  DEFVAL	{ disabled }
     ::= { wwpL2CFTunnelEntry 3 }

 wwpL2CFTunnelPriority OBJECT-TYPE
     SYNTAX       INTEGER {	
		       p0(0),
		       p1(1),
		       p2(2),
		       p3(3),
		       p4(4),
		       p5(5),
		       p6(6),
		       p7(7)
		   }
     MAX-ACCESS    read-write
     STATUS        current
     DESCRIPTION
	     "The 802.1p packet priority to be assigned to packets associated
	      with this port that do not have an 802.1Q VLAN header."
	  DEFVAL	{ p6 }
     ::= { wwpL2CFTunnelEntry 4 }

 wwpL2CFTunnelRowStatus OBJECT-TYPE
     SYNTAX       RowStatus
     MAX-ACCESS   read-write
     STATUS       current
     DESCRIPTION
	     "Used to manage the creation and deletion of the 
	     conceptual rows in this table.

             To create a row in this table, a manager must
             set this object to 'createAndGo'.
				 The default state for wwpL2CFTunnelAdminStatus 
				 will be 'disabled'."
     ::= { wwpL2CFTunnelEntry 5 }
 

 --
 -- L2 control frame protocol table
 --
 wwpL2CFTProtocolTable OBJECT-TYPE
     SYNTAX     SEQUENCE OF WwpL2CFTProtocolEntry
     MAX-ACCESS not-accessible
     STATUS     current
     DESCRIPTION
            "The (conceptual) table listing the l2 control frame 
             protocol status tunnels."
     ::= { wwpL2CFTunnel 2 }
     
 wwpL2CFTProtocolEntry  OBJECT-TYPE
     SYNTAX       WwpL2CFTProtocolEntry
     MAX-ACCESS   not-accessible
     STATUS       current
     DESCRIPTION
             "The layer 2 control frame protocol tunnel 
              entry."
	 INDEX    { wwpL2CFTVlanId, wwpL2CFTProtocolNum }
     ::= { wwpL2CFTProtocolTable 1 }
     
 WwpL2CFTProtocolEntry ::=  SEQUENCE { 
		wwpL2CFTVlanId 			 VlanId,
		wwpL2CFTProtocolNum     INTEGER,
		wwpL2CFTDispositionType  INTEGER	
 }

 wwpL2CFTVlanId OBJECT-TYPE
     SYNTAX      VlanId
     MAX-ACCESS  read-only
     STATUS      current
     DESCRIPTION
	     "802.1Q VLAN ID (1-4094)"
     ::= { wwpL2CFTProtocolEntry 1 }

  wwpL2CFTProtocolNum OBJECT-TYPE
     SYNTAX      INTEGER {                     
                     l28021x(1),
                     bridge-grp-addr(2),
                     cdp(3),
                     dtp(4),
                     gvrp(5),
                     lacp(6),
                     marker-protocol(7),
                     oam(8),
                     pagp(9),
                     pvst(10),
                     stp-uplink-fast(11),
                     udld(12),
                     vlanbridge(13),
                     vtp(14),
                     lldp(15)
                 }
     MAX-ACCESS  read-only
     STATUS      current
     DESCRIPTION
        "This object represent the list of protocols the device 
         can support."
     ::= { wwpL2CFTProtocolEntry 2 }

  wwpL2CFTDispositionType OBJECT-TYPE
     SYNTAX      INTEGER {
                     discard(0),
                     peer(1),               
                     tunnel(2)               
                 }
     MAX-ACCESS  read-create
     STATUS      current
     DESCRIPTION
        "Setting this object to 'discard' will cause wwpL2CFTProtocolNum
         frames arriving at the specified port to be discarded.  
         NOTE: Setting this to 'peer' will cause the wwpL2CFTProtocolNum frame
         to be processed in the same manor as 'discard'.  
         Setting this to 'tunnel' will cause the wwpL2CFTProtocolNum frame to be 
         tunneled. The default disposition state of each protocol is controlled 
			by portal application."
     ::= { wwpL2CFTProtocolEntry 3 } 


-- -------------------------------------------------------------
-- L2 CF Statistics Table
-- -------------------------------------------------------------


wwpL2CFTStatsTable OBJECT-TYPE
    SYNTAX      SEQUENCE OF WwpL2CFTStatsEntry
    MAX-ACCESS  not-accessible
    STATUS      current
    DESCRIPTION
        "A table that contains the frame counters for Layer 2 control frame
		   handling."
    ::= { wwpL2CFTunnel 3 }


wwpL2CFTStatsEntry OBJECT-TYPE
    SYNTAX      WwpL2CFTStatsEntry
    MAX-ACCESS  not-accessible
    STATUS      current
    DESCRIPTION
        "A list of Link Aggregation Control Protocol statistics
        for each port on this device."
	 INDEX    { wwpL2CFTStatsVlanId, wwpL2CFTStatsProtocolNum }
    ::= { wwpL2CFTStatsTable 1 }


WwpL2CFTStatsEntry ::=
    SEQUENCE {
		wwpL2CFTStatsVlanId 			 	VlanId,
		wwpL2CFTStatsProtocolNum     	INTEGER,
		wwpL2CFTStatsPacketsRx			Counter32,
		wwpL2CFTStatsTunneledFrames	Counter32,
		wwpL2CFTStatsDecodedFrames		Counter32,
		wwpL2CFTStatsDecodedFailed		Counter32,
		wwpL2CFTStatsPeeredFrames		Counter32,
		wwpL2CFTStatsDiscardFrames		Counter32,
		wwpL2CFTStatsTunFrameSubPort	Counter32
    }

 wwpL2CFTStatsVlanId OBJECT-TYPE
     SYNTAX      VlanId
     MAX-ACCESS  read-only
     STATUS      current
     DESCRIPTION
	     "802.1Q VLAN ID (1-4094)"
     ::= { wwpL2CFTStatsEntry 1 }

  wwpL2CFTStatsProtocolNum OBJECT-TYPE
     SYNTAX      INTEGER {                     
                     l28021x(1),
                     bridge-grp-addr(2),
                     cdp(3),
                     dtp(4),
                     gvrp(5),
                     lacp(6),
                     marker-protocol(7),
                     oam(8),
                     pagp(9),
                     pvst(10),
                     stp-uplink-fast(11),
                     udld(12),
                     vlanbridge(13),
                     vtp(14)
                 }
     MAX-ACCESS  read-only
     STATUS      current
     DESCRIPTION
        "This object represent the list of protocols the device 
         can support."
     ::= { wwpL2CFTStatsEntry 2 }


wwpL2CFTStatsPacketsRx OBJECT-TYPE
    SYNTAX       Counter32
    MAX-ACCESS   read-only
    STATUS       current
    DESCRIPTION
        "The number of number of pkts ingressed matching protocol. 
		  This value is read-only."
    ::= { wwpL2CFTStatsEntry 3 }

wwpL2CFTStatsTunneledFrames OBJECT-TYPE
    SYNTAX       Counter32
    MAX-ACCESS   read-only
    STATUS       current
    DESCRIPTION
        "The number of number of pts that made tunneled. 
		  This value is read-only."
    ::= { wwpL2CFTStatsEntry 4 }
	 
wwpL2CFTStatsDecodedFrames OBJECT-TYPE
    SYNTAX       Counter32
    MAX-ACCESS   read-only
    STATUS       current
    DESCRIPTION
        "The number of came in tunneled, then restored. 
		  This value is read-only."
    ::= { wwpL2CFTStatsEntry 5 }
 
wwpL2CFTStatsDecodedFailed OBJECT-TYPE
    SYNTAX       Counter32
    MAX-ACCESS   read-only
    STATUS       current
    DESCRIPTION
        "The number of failed to untunnel. 
		  This value is read-only."
    ::= { wwpL2CFTStatsEntry 6 }
 
wwpL2CFTStatsPeeredFrames OBJECT-TYPE
    SYNTAX       Counter32
    MAX-ACCESS   read-only
    STATUS       current
    DESCRIPTION
        "The number of number of peered packets. 
		  This value is read-only."
    ::= { wwpL2CFTStatsEntry 7 }
 
wwpL2CFTStatsDiscardFrames OBJECT-TYPE
    SYNTAX       Counter32
    MAX-ACCESS   read-only
    STATUS       current
    DESCRIPTION
        "The number of number of discarded packets. 
		  This value is read-only."
    ::= { wwpL2CFTStatsEntry 8 }
 
wwpL2CFTStatsTunFrameSubPort OBJECT-TYPE
    SYNTAX       Counter32
    MAX-ACCESS   read-only
    STATUS       current
    DESCRIPTION
        "The number of number of tunneled frames received on subscriber port. 
		  This value is read-only."
    ::= { wwpL2CFTStatsEntry 9 }


-- -------------------------------------------------------------
-- L2 CF Global Statistics Table
-- -------------------------------------------------------------


wwpL2CFTGlobalStats OBJECT IDENTIFIER ::= { wwpL2CFTunnel 4 }

wwpL2CFTGlobalStatsPacketsRx OBJECT-TYPE
    SYNTAX       Counter32
    MAX-ACCESS   read-only
    STATUS       current
    DESCRIPTION
        "The total number of number of frames ingressed matching protocol. 
		  This value is read-only."
    ::= { wwpL2CFTGlobalStats 1 }

wwpL2CFTGlobalStatsTunneledFrames OBJECT-TYPE
    SYNTAX       Counter32
    MAX-ACCESS   read-only
    STATUS       current
    DESCRIPTION
        "The total number of number of frames that made tunneled. 
		  This total value is read-only."
    ::= { wwpL2CFTGlobalStats 2 }
	 
wwpL2CFTGlobalStatsDecodedFrames OBJECT-TYPE
    SYNTAX       Counter32
    MAX-ACCESS   read-only
    STATUS       current
    DESCRIPTION
        "The total number of frames that came in tunneled, then restored. 
		  This value is read-only."
    ::= { wwpL2CFTGlobalStats 3 }
 
wwpL2CFTGlobalStatsDecodedFailed OBJECT-TYPE
    SYNTAX       Counter32
    MAX-ACCESS   read-only
    STATUS       current
    DESCRIPTION
        "Specifies the total number of frames that failed to 
         'untunnel' on the vlan. 
		  This value is read-only."
    ::= { wwpL2CFTGlobalStats 4 }
 
wwpL2CFTGlobalStatsPeeredFrames OBJECT-TYPE
    SYNTAX       Counter32
    MAX-ACCESS   read-only
    STATUS       current
    DESCRIPTION
        "The total number of number of peered frames. 
		  This value is read-only."
    ::= { wwpL2CFTGlobalStats 5 }
 
wwpL2CFTGlobalStatsDiscardFrames OBJECT-TYPE
    SYNTAX       Counter32
    MAX-ACCESS   read-only
    STATUS       current
    DESCRIPTION
        "The total number of number of discarded frames. 
		  This value is read-only."
    ::= { wwpL2CFTGlobalStats 6 }
 
wwpL2CFTGlobalStatsTunFrameSubPort OBJECT-TYPE
    SYNTAX       Counter32
    MAX-ACCESS   read-only
    STATUS       current
    DESCRIPTION
        "The total number of number of tunneled frames received on subscriber port. 
		  This value is read-only."
    ::= { wwpL2CFTGlobalStats 7 }
    
 

 wwpL2CFTResetStatCounters OBJECT-TYPE
      SYNTAX           INTEGER {
                         none(0),
                         reset(1)
                       }
      MAX-ACCESS       read-write
      STATUS           current   
      DESCRIPTION
	      "To reset L2 control frame statistic counters , this object
              should be set to 'reset'. 
              
             A read on this object should return none(0)."
       ::= { wwpL2CFTunnel  5 }
 
 END
 
 --
 -- WWP-L2-CF-TUNNEL-MIB
 --

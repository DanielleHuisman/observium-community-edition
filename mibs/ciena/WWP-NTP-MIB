--
 -- WWP-NTP-MIB.my
 --
 --

 WWP-NTP-MIB DEFINITIONS ::= BEGIN

 IMPORTS 		
   IpAddress, Integer32, OBJECT-TYPE, MODULE-IDENTITY			
	    FROM SNMPv2-SMI			
   RowStatus, TEXTUAL-CONVENTION			
	    FROM SNMPv2-TC						
   wwpModules			
	    FROM WWP-SMI;
	
	
 wwpNtpMIB MODULE-IDENTITY
	    LAST-UPDATED "200104031700Z"
	    ORGANIZATION "World Wide Packets, Inc"
	    CONTACT-INFO
		    "   Mib Meister
		  	Postal: World Wide Packets
		        P.O. Box 950
		        Veradale, WA 99037
		        USA
		 	Phone:  +1 509 242 9000
			Email:  mib.meister@worldwidepackets.com"
	    DESCRIPTION
                    "This MIB module defines the generic managed objects
                     for NTP on WWP devices."  
            REVISION     "200303110000Z"  -- 11th March. 2003  
	    DESCRIPTION
		    "The description of wwpNtpPollFreq is updated."
	    REVISION    "200104031700Z"
	    DESCRIPTION
                     "Initial creation."   
	    ::= { wwpModules 5 }
						
 --
 -- Node definitions
 --
	
 wwpNtpMIBObjects OBJECT IDENTIFIER ::= { wwpNtpMIB 1 }
 wwpNtp OBJECT IDENTIFIER ::= { wwpNtpMIBObjects 1 }
 

 -- Notifications 
  
 wwpNtpMIBNotificationPrefix  OBJECT IDENTIFIER ::= { wwpNtpMIB 2 } 
 wwpNtpMIBNotifications    OBJECT IDENTIFIER ::=  
                       { wwpNtpMIBNotificationPrefix 0 }

 -- Conformance information 
 
 wwpNtpMIBConformance OBJECT IDENTIFIER ::= { wwpNtpMIB 3 } 
 wwpNtpMIBCompliances OBJECT IDENTIFIER ::= { wwpNtpMIBConformance 1 } 		
 wwpNtpMIBGroups      OBJECT IDENTIFIER ::= { wwpNtpMIBConformance 2 }

		
 wwpNtpRcvBroadcasts OBJECT-TYPE
     SYNTAX          INTEGER {
			  disable(0),
		          enable(1)
		     }
     MAX-ACCESS      read-write
     STATUS          current
     DESCRIPTION
	     "Enables or disables the reception of NTP broadcasts 
	      from a host. WWP products will only accept broadcasts from 
	      those NTP servers listed in the NTP table below."
     DEFVAL { enable }
     ::= { wwpNtp 1 }
		
 wwpNtpEnablePolling OBJECT-TYPE
     SYNTAX          INTEGER {
			  disable(0),
			  enable(1)
		     }
     MAX-ACCESS      read-write
     STATUS          current
     DESCRIPTION
	     "Enables or disables NTP polling."
     DEFVAL { disable }
     ::= { wwpNtp 2 }
		
 wwpNtpPollFreq OBJECT-TYPE
     SYNTAX      Integer32 (0..2147483647)
     MAX-ACCESS  read-write
     STATUS      current
     DESCRIPTION
	     "WWP products can also be configured to poll a server for the current
	      time every x seconds.  pollTime is in seconds."
     ::= { wwpNtp 3 }
		
 wwpNtpServerTable OBJECT-TYPE
     SYNTAX       SEQUENCE OF WwpNtpServerEntry
     MAX-ACCESS   not-accessible
     STATUS       current
     DESCRIPTION
	     "Table of NTP server information."
     ::= { wwpNtp 4 }
		
 wwpNtpServerEntry OBJECT-TYPE
     SYNTAX       WwpNtpServerEntry
     MAX-ACCESS   not-accessible
     STATUS       current
     DESCRIPTION
	     "An entry for each NTP server that the switch should be aware of."
     INDEX { wwpNtpServerIpAddr }
     ::= { wwpNtpServerTable 1 }
		 
 WwpNtpServerEntry ::= SEQUENCE { 
     wwpNtpServerIpAddr      IpAddress,
     wwpNtpServerRowStatus   RowStatus
 }


 wwpNtpServerIpAddr OBJECT-TYPE
     SYNTAX       IpAddress
     MAX-ACCESS   read-only
     STATUS       current
     DESCRIPTION
	     "The IP address of the NTP server."
     ::= { wwpNtpServerEntry 1 }
		
 wwpNtpServerRowStatus OBJECT-TYPE
     SYNTAX      RowStatus
     MAX-ACCESS  read-create
     STATUS      current
     DESCRIPTION
	     "To create a row in this table, a manager must
            set this object to 'createAndGo'."
     ::= { wwpNtpServerEntry 2 }
     
 END

 --
 -- WWP-NTP-MIB
 --

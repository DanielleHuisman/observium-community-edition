--
 -- WWP-SYSTEM-CONFIG-APPS-MIB.my
 --
 --

 WWP-SYSTEM-CONFIG-APPS-MIB DEFINITIONS ::= BEGIN

 IMPORTS 		
   NOTIFICATION-TYPE, Unsigned32, OBJECT-TYPE, MODULE-IDENTITY			
	    FROM SNMPv2-SMI			
   DisplayString, TruthValue			
	    FROM SNMPv2-TC						
   wwpModules			
	    FROM WWP-SMI;
	
	
 wwpSystemConfAppsMIB MODULE-IDENTITY
	    LAST-UPDATED "200104031700Z"
	    ORGANIZATION "World Wide Packets, Inc"
	    CONTACT-INFO
		    "   Mib Meister
		  	Postal: World Wide Packets
		        P.O. Box 950
		        Veradale, WA 99037
		        USA
		 	Phone:  +1 509 242 9000
			Email:  mib.meister@worldwidepackets.com"
	    DESCRIPTION
		    "The MIB module to define primary and backup configs and apps
                    for wwp products."
	    REVISION    "200104031700Z"
	    DESCRIPTION
		    "Initial creation."
	    ::= { wwpModules 20 }
						
 --
 -- Node definitions
 --
	
 wwpSystemConfAppsMIBObjects OBJECT IDENTIFIER ::= { wwpSystemConfAppsMIB 1 }
 
 -- SystemConf 
 --
 wwpSystemApps OBJECT IDENTIFIER ::= { wwpSystemConfAppsMIBObjects 1 }

 --
 -- SystemApps Bootp
 -- 
 wwpSystemConf OBJECT IDENTIFIER ::= { wwpSystemConfAppsMIBObjects 2 }

 
 -- Notifications 
  
 wwpSystemConfAppsMIBNotificationPrefix  OBJECT IDENTIFIER ::= { wwpSystemConfAppsMIB 2 } 
 wwpSystemConfAppsMIBNotifications       OBJECT IDENTIFIER ::=  
                       { wwpSystemConfAppsMIBNotificationPrefix 0 }

 -- Conformance information 
 
 wwpSystemConfAppsMIBConformance OBJECT IDENTIFIER ::= { wwpSystemConfAppsMIB 3 } 
 wwpSystemConfAppsMIBCompliances OBJECT IDENTIFIER ::= { wwpSystemConfAppsMIBConformance 1 } 		
 wwpSystemConfAppsMIBGroups      OBJECT IDENTIFIER ::= { wwpSystemConfAppsMIBConformance 2 }

 wwpSystemRunningApps OBJECT-TYPE
     SYNTAX     DisplayString
     MAX-ACCESS read-only
     STATUS     current
     DESCRIPTION
            "Name of the current running Apps."
    ::= { wwpSystemApps 1 }

 wwpSystemAppsSwapActivate  OBJECT-TYPE
     SYNTAX          TruthValue
     MAX-ACCESS      read-write
     STATUS          current
     DESCRIPTION
    	     "Setting this object to true swaps the primary and secondary APPS.
             The object return to false once the swap operation is completed."
       DEFVAL { false }                
       ::= { wwpSystemApps 2 }

 --
 --  The System Apps Table
 --

 wwpSystemAppsTable OBJECT-TYPE
     SYNTAX     SEQUENCE OF WwpSystemAppsEntry
     MAX-ACCESS not-accessible
     STATUS     current
     DESCRIPTION
            "The (conceptual) table listing the Apps"
    ::= { wwpSystemApps 3 }

 wwpSystemAppsEntry OBJECT-TYPE
    SYNTAX     WwpSystemAppsEntry
    MAX-ACCESS not-accessible
    STATUS     current
    DESCRIPTION
            "An entry (conceptual row) in the wwpSystemAppsTable."
    INDEX      { wwpSystemAppsImage }
    ::= { wwpSystemAppsTable 1 }

 WwpSystemAppsEntry ::= SEQUENCE {   
    wwpSystemAppsImage           INTEGER,
    wwpSystemAppsName            DisplayString
 }

 wwpSystemAppsImage    OBJECT-TYPE
     SYNTAX          INTEGER {
                        primary(1),
                        backup(2)
                     }
     MAX-ACCESS      read-only
     STATUS          current
     DESCRIPTION
    	     "The object indicates whether this image is primary or backup."               
       ::= { wwpSystemAppsEntry 1 }

 wwpSystemAppsName     OBJECT-TYPE
     SYNTAX          DisplayString
     MAX-ACCESS      read-only
     STATUS          current
     DESCRIPTION
    	     "The name of the Apps including the path."               
       ::= { wwpSystemAppsEntry 2 }

 wwpSystemBackupNotifEnabled OBJECT-TYPE
     SYNTAX      TruthValue
     MAX-ACCESS  read-write
     STATUS      current
     DESCRIPTION
             "This variable  indicates  whether  the  system
             generates the wwpSystemBackupAppNotification. 
             A false value prevents this notifications
             from being generated by this system."
    DEFVAL { true }
    ::= { wwpSystemApps 4 }
    	
 --
 --  The System Config Table
 --

 wwpSystemConfTable OBJECT-TYPE
     SYNTAX     SEQUENCE OF WwpSystemConfEntry
     MAX-ACCESS not-accessible
     STATUS     current
     DESCRIPTION
            "The (conceptual) table listing the configs"
    ::= { wwpSystemConf 1 }

 wwpSystemConfEntry OBJECT-TYPE
    SYNTAX     WwpSystemConfEntry
    MAX-ACCESS not-accessible
    STATUS     current
    DESCRIPTION
            "An entry (conceptual row) in the wwpSystemConfTable."
    INDEX      { wwpSystemConfIndex }
    ::= { wwpSystemConfTable 1 }


 WwpSystemConfEntry ::= SEQUENCE {
    wwpSystemConfIndex      INTEGER,   
    wwpSystemConfName       DisplayString 
 }
 
 wwpSystemConfIndex     OBJECT-TYPE
     SYNTAX             INTEGER(1..65535)
     MAX-ACCESS         read-only
     STATUS             current
     DESCRIPTION
    	     "Unique identifier to the table."               
       ::= { wwpSystemConfEntry 1 }
 
 wwpSystemConfName     OBJECT-TYPE
     SYNTAX          DisplayString
     MAX-ACCESS      read-only
     STATUS          current
     DESCRIPTION
    	     "The name of the Config file including the path."               
       ::= { wwpSystemConfEntry 2 }

 
 wwpSystemBootConfName   OBJECT-TYPE
     SYNTAX           DisplayString
     MAX-ACCESS       read-write
     STATUS           current
     DESCRIPTION
            "Name of the config file which will be used when the system is rebooted."
    ::= { wwpSystemConf 2 }


 wwpSystemConfSaveName   OBJECT-TYPE
     SYNTAX           DisplayString
     MAX-ACCESS       read-write
     STATUS           current
     DESCRIPTION
            "Name of the config file to which the current config should be saved."
    ::= { wwpSystemConf 3 }
    
 wwpSystemLoadBackupAppNotification NOTIFICATION-TYPE
	OBJECTS	{
	           wwpSystemAppsName    
                }
	STATUS	current
	DESCRIPTION
		"This notification will be sent, whenever the system 
		decide to load the backup image." 
	::= { wwpSystemConfAppsMIBNotifications 1 }
 
 END

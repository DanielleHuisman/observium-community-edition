--
 -- WWP-SYSTEM-CONTROL-MIB.my
 --
 --

 WWP-SYSTEM-CONTROL-MIB DEFINITIONS ::= BEGIN

 IMPORTS 		
   NOTIFICATION-TYPE, OBJECT-TYPE, MODULE-IDENTITY			
	    FROM SNMPv2-SMI			
   TruthValue, RowStatus, TEXTUAL-CONVENTION			
	    FROM SNMPv2-TC
   dot1dStpPort
            FROM BRIDGE-MIB 						
   wwpModules			
	    FROM WWP-SMI;
	
	
 wwpSysCtrlMIB MODULE-IDENTITY
	    LAST-UPDATED "200104031700Z"
	    ORGANIZATION "World Wide Packets, Inc"
	    CONTACT-INFO
		    "   Mib Meister
		  	Postal: World Wide Packets
		        P.O. Box 950
		        Veradale, WA 99037
		        USA
		 	Phone:  +1 509 242 9000
			Email:  mib.meister@worldwidepackets.com"
	    DESCRIPTION
		    "The MIB module for the WWP SysCtrl specific information."
	    REVISION    "200104031700Z"
	    DESCRIPTION
		    "Initial creation."
	    ::= { wwpModules 30 }
						
 --
 -- Node definitions
 --
	
 wwpSysCtrlMIBObjects OBJECT IDENTIFIER ::= { wwpSysCtrlMIB 1 }
 wwpSysCtrl OBJECT IDENTIFIER ::= { wwpSysCtrlMIBObjects 1 }
 

 -- Notifications 
  
 wwpSysCtrlMIBNotificationPrefix  OBJECT IDENTIFIER ::= { wwpSysCtrlMIB 2 } 
 wwpSysCtrlMIBNotifications    OBJECT IDENTIFIER ::=  
                       { wwpSysCtrlMIBNotificationPrefix 0 }

 -- Conformance information 
 
 wwpSysCtrlMIBConformance OBJECT IDENTIFIER ::= { wwpSysCtrlMIB 3 } 
 wwpSysCtrlMIBCompliances OBJECT IDENTIFIER ::= { wwpSysCtrlMIBConformance 1 } 		
 wwpSysCtrlMIBGroups      OBJECT IDENTIFIER ::= { wwpSysCtrlMIBConformance 2 }

		
 wwpSysCtrlBridgeRSTPEnable OBJECT-TYPE
     SYNTAX          TruthValue
     MAX-ACCESS      read-write
     STATUS          current
     DESCRIPTION
	     "when this object is set to 'true' the rstp operation
	      for the bridge is enabled. Setting this object to 'false' disable
              bridge rstp operations."
     DEFVAL { false }
     ::= { wwpSysCtrl 1 }

 		
 wwpSysCtrlLacpEnable OBJECT-TYPE
     SYNTAX          TruthValue
     MAX-ACCESS      read-write
     STATUS          current
     DESCRIPTION
	     "when this object is set to 'true' the Lacp operation
	      for the device is enabled. Setting this object to 'false' disable
              the Lacp operations."
     DEFVAL { false }
     ::= { wwpSysCtrl 2 }

 wwpPvstBpduReceived  NOTIFICATION-TYPE
	OBJECTS	   {  
	              dot1dStpPort    
		   }
	STATUS	   current
	DESCRIPTION  
		"A wwpPvstBpduReceived trap signifies that the SNMP entity, acting in
                 an agent role, has detected that a Per Vlan Spanning Tree (PVST)
		 BPDU was received on one of the ports sepcified by dot1dStpPort."
	::= { wwpSysCtrlMIBNotifications 1 } 

 END

 --
 -- WWP-SYSTEM-CONTROL-MIB
 --

--
 -- WWP-VOICE-GATEWAY-MIB.my
 --
 --

 WWP-VOICE-GATEWAY-MIB DEFINITIONS ::= BEGIN

 IMPORTS 
   Unsigned32, Counter32, IpAddress, Integer32, OBJECT-TYPE, MODULE-IDENTITY, NOTIFICATION-TYPE
	FROM SNMPv2-SMI			
   DisplayString, TruthValue, TEXTUAL-CONVENTION			
	FROM SNMPv2-TC			
   wwpModules			
	FROM WWP-SMI;
	
	
 wwpVoiceGatewayMIB MODULE-IDENTITY
       LAST-UPDATED "200211181700Z"
       ORGANIZATION "World Wide Packets, Inc"
       CONTACT-INFO
	            "   Mib Meister
		        Postal: World Wide Packets
			P.O. Box 950
			Veradale, WA 99037
			USA
			Phone:  +1 509 242 9000
		  	Email:  mib.meister@worldwidepackets.com"
       DESCRIPTION
	       "This MIB module degines the managed objects for WWP 
               voice gateway."
       REVISION     "200211181700Z"
       DESCRIPTION
               "Initial creation."
	 ::= { wwpModules 43 }
		
			
	
 --
 -- Node definitions
 --
	
 wwpVoiceGatewayMIBObjects OBJECT IDENTIFIER ::= { wwpVoiceGatewayMIB 1 }
	
 wwpVoiceGateway OBJECT IDENTIFIER ::= { wwpVoiceGatewayMIBObjects 1 }
 
 wwpVoiceGatewayMGCP    OBJECT IDENTIFIER ::= { wwpVoiceGateway 1 }
 
 wwpVoiceGatewayCountry OBJECT IDENTIFIER ::= { wwpVoiceGateway 2 }
 
 wwpVoiceGatewayCodec   OBJECT IDENTIFIER ::= { wwpVoiceGateway 3 }
 
 wwpVoiceGatewayAudio   OBJECT IDENTIFIER ::= { wwpVoiceGateway 4 }
 
 wwpVoiceGatewayStats   OBJECT IDENTIFIER ::= { wwpVoiceGateway 5 }

 wwpVoiceReset          OBJECT IDENTIFIER ::= { wwpVoiceGateway 6 }
 
 wwpVoiceSec            OBJECT IDENTIFIER ::= { wwpVoiceGateway 7 }

 wwpVoiceGatewayConfigCallAgent    OBJECT IDENTIFIER ::= { wwpVoiceGateway 8 }

 wwpVoiceGatewayConfigPots    OBJECT IDENTIFIER ::= { wwpVoiceGateway 9 }

 wwpVoiceGatewayConfigFax   OBJECT IDENTIFIER ::= { wwpVoiceGateway 10 }

 wwpVoiceGatewayConfigEndPoint   OBJECT IDENTIFIER ::= { wwpVoiceGateway 11 }
 
 wwpVoiceGatewayConfigNotifEntityCache   OBJECT IDENTIFIER ::= { wwpVoiceGateway 12 }
 
 wwpVoiceGatewayConfigJitterBuffer   OBJECT IDENTIFIER ::= { wwpVoiceGateway 13 }
 
 wwpVoiceGatewayConfigJitterBufferMinPeriod   OBJECT IDENTIFIER ::= { wwpVoiceGateway 14 }
 
 wwpVoiceGatewayConfigJitterBufferMaxPeriod   OBJECT IDENTIFIER ::= { wwpVoiceGateway 15 }
 
 wwpVoiceGatewayConfigJitterBufferTargetPeriod   OBJECT IDENTIFIER ::= { wwpVoiceGateway 16 }

 wwpVoiceGatewayConfigCodecOverride    OBJECT IDENTIFIER ::= { wwpVoiceGateway 17 }
  
 wwpVoiceGatewayConfigTestServerConnection    OBJECT IDENTIFIER ::= { wwpVoiceGateway 18 }
 
 wwpVoiceGatewayConfigLastServerResponseTime    OBJECT IDENTIFIER ::= { wwpVoiceGateway 19 }
     
 wwpVoiceGatewaySIP    OBJECT IDENTIFIER ::= { wwpVoiceGateway 20 }

 wwpVoiceGatewayConfigProtocolType    OBJECT IDENTIFIER ::= { wwpVoiceGateway 21 }
 
 wwpVoiceGatewayConfigProtocolEnable	OBJECT IDENTIFIER ::= { wwpVoiceGateway 22 }
 
 -- Notifications 
  
 wwpVoiceGatewayMIBNotificationPrefix  OBJECT IDENTIFIER ::= { wwpVoiceGatewayMIB 2 } 
 wwpVoiceGatewayMIBNotifications       OBJECT IDENTIFIER ::=  
                       { wwpVoiceGatewayMIBNotificationPrefix 0 }

 -- Conformance information 
 
 wwpVoiceGatewayMIBConformance OBJECT IDENTIFIER ::= { wwpVoiceGatewayMIB 3 } 
 wwpVoiceGatewayMIBCompliances OBJECT IDENTIFIER ::= { wwpVoiceGatewayMIBConformance 1 } 		
 wwpVoiceGatewayMIBGroups      OBJECT IDENTIFIER ::= { wwpVoiceGatewayMIBConformance 2 }   

       
 -- 
 -- MGCP Group
 --
 wwpVoiceGatewayEndPointTable OBJECT-TYPE
    SYNTAX      SEQUENCE OF WwpVoiceGatewayEndPointEntry
    MAX-ACCESS  not-accessible
    STATUS      current
    DESCRIPTION
        "A table of the voice gateway endpoints."
    ::= { wwpVoiceGatewayMGCP 1 }

 wwpVoiceGatewayEndPointEntry OBJECT-TYPE
    SYNTAX      WwpVoiceGatewayEndPointEntry
    MAX-ACCESS  not-accessible
    STATUS      current
    DESCRIPTION
        "An entry of the voice gateway endpoint."
    INDEX  {wwpVoiceGatewayEndPointId  }
    ::= { wwpVoiceGatewayEndPointTable 1 }

 WwpVoiceGatewayEndPointEntry ::= SEQUENCE {
    wwpVoiceGatewayEndPointId                Integer32,
    wwpVoiceGatewayEndpoint                  OCTET STRING
 }
 
 wwpVoiceGatewayEndPointId  OBJECT-TYPE
     SYNTAX       Integer32 (1..2147483647)
     MAX-ACCESS   read-only
     STATUS       current
     DESCRIPTION
             "Index for the the endpoint entry."
     ::= { wwpVoiceGatewayEndPointEntry 1 }
     
 wwpVoiceGatewayEndpoint   OBJECT-TYPE
     SYNTAX       DisplayString 
     MAX-ACCESS   read-write
     STATUS       current
     DESCRIPTION
             "The endpoint for the voice Gateway.
	     This object should be set to a zero length string
	     if the Management Station wish to use the Endpoint's 
	     IP Address as the Endpoint Domain Name.
	     
	     Endpoint identifiers have two parts: 
             The domain name of the gateway that is managing the endpoint.
             A local name within the gateway. The local name is hierarchical, 
	     for example, the local name of circuit number 13 in a multiplexed 
	     trunk that is connected to the physical interface named XYZ would 
	     be named as XYZ/13."
     DEFVAL { "" } 
     ::= { wwpVoiceGatewayEndPointEntry 2 }
  
 wwpVoiceGatewayCallAgentAddr OBJECT-TYPE
     SYNTAX          DisplayString 
     MAX-ACCESS      read-write
     STATUS          current
     DESCRIPTION
             "This object is used to configure either the domain 
             name or the IP address of the Call Agent 
             in standard dot notation.     

             The complete address of a default call agent is composed of  
             IP address/Domain Name and UDP port.
        
             wwpVoiceGatewayCallAgentAddr specifies address of the Call
	     Agent to which RSIP(RestartInProgress) message 
             is sent whenever system starts up or line goes up.
	 
	     Call agent address may be an IP address or fully qualified 
	     domain name (FQDN). This object should be set to zero length
	     string if the Management Stations wish to 
	     attempt to obtain the CA address from a DNS server
	    (highest priority MGCP CA is chosen)."
     ::= { wwpVoiceGatewayMGCP 2 }    	

 wwpVoiceGatewayCallAgentUDPPort OBJECT-TYPE
    SYNTAX      Integer32(1025..65535)
    MAX-ACCESS  read-write
    STATUS      current
    DESCRIPTION
            "This object is used to configure the UDP port
            of the Call Agent.

            The UDP port is used together with wwpVoiceGatewayCallAgentAddr to  
            specify the destination address of the call agent to which RSIP 
	    message is sent when system starts up or line goes up."
    DEFVAL { 2427 }  
    ::= { wwpVoiceGatewayMGCP 3 } 
     
  wwpVoiceGatewayCallAgentProtocol OBJECT-TYPE
     SYNTAX         INTEGER {
             ncs1(1),
		       rfc2705(2),
		       mgcp1Ncs1NoPackages(3)
		    }
     MAX-ACCESS     read-write
     STATUS         current
     DESCRIPTION
	     "Setting this object to 'rfc2705' will enable support of
	      RFC 2705 for this CallAgent (Only 'L' Event Package). Setting this object
	      to 'ncs1.0' will enable support of PacketCable NCS 1.0 for 
	      the CallAgent. Setting this object to 'mgcp1Ncs1NoPackages' will 
	      enable support of Mgcp 1.0 Ncs 1.0 no event package for the CallAgent."
     DEFVAL { rfc2705 } 
     ::= { wwpVoiceGatewayMGCP 4 }
     
  wwpVoiceGatewaySupportMessagePiggybacking OBJECT-TYPE
     SYNTAX         TruthValue
     MAX-ACCESS     read-write
     STATUS         current
     DESCRIPTION
	     "Setting this object to 'false' will disable message
	     Piggybacking for this Voice Gateway."
     DEFVAL { true } 
     ::= { wwpVoiceGatewayMGCP 5 }
	  
 wwpVoiceGatewayRsipKeepAliveEnable OBJECT-TYPE
      SYNTAX      TruthValue
     MAX-ACCESS   read-write
     STATUS       current
     DESCRIPTION     
             "Setting this object to 'enable' will configure the device to send periodic 
				 RSIP x-keepalive messages."
      DEFVAL { false }
      ::= { wwpVoiceGatewayMGCP 6 }

 wwpVoiceGatewayRsipKeepAliveInterval  OBJECT-TYPE
     SYNTAX         Integer32(10..600)
     UNITS          "seconds"    
     MAX-ACCESS     read-write
     STATUS         current
     DESCRIPTION
	     "Configures the interval at which RSIP x-keepalive messages are transmitted" 
     DEFVAL     { 30 }
    ::= { wwpVoiceGatewayMGCP 7}
 
 -- 
 --  Country Group
 --    
 wwpVoiceGatewayCountryCodes     OBJECT-TYPE
     SYNTAX         INTEGER {
                         usa(1),
                         dubai(2),
                         holland(3),
                         newZealand(4),
                         uk(5),
			 sweden(6)   
                    }
     MAX-ACCESS     read-write
     STATUS         current
     DESCRIPTION
	     "This object specifies the country for different 
	     tone and ring settings." 
     ::= { wwpVoiceGatewayCountry 1 }
	
 -- 
 -- Complex Codec Group
 --	
 wwpVoiceGatewayComplexCodec     OBJECT-TYPE
     SYNTAX         INTEGER {
                         none(1),
                         g711(2),
			 g723(3),
			 g726(4),
			 g729(5)   
                    }
     MAX-ACCESS     read-write
     STATUS         current
     DESCRIPTION
	     "Setting this object to 'g711(0)' will
	     only enable G711U and G711A Codec. If this object
	     is set to 'g729(3)', then G729A and G729AB
	     Codec will be used."
     ::= { wwpVoiceGatewayCodec 1 }
 
 wwpVoiceGatewaySilenceSuppression OBJECT-TYPE
     SYNTAX         INTEGER {
                        on(1),
			off(2)
		    }
     MAX-ACCESS     read-write
     STATUS         current
     DESCRIPTION
	     "Setting this object to 'false' will disable the
	     silence suppression for the complex codes specified by
	     wwpVoiceGatewayComplexCodec."
     ::= { wwpVoiceGatewayCodec 2 }
     
 wwpVoiceGatewayEchoCancellation OBJECT-TYPE
     SYNTAX         INTEGER {
                        on(1),
			off(2)
		    }
     MAX-ACCESS     read-write
     STATUS         current
     DESCRIPTION
	     "Setting this object to 'false' will disable the
	     echo cancellation for the complex codes specified by
	     wwpVoiceGatewayComplexCodec."
     ::= { wwpVoiceGatewayCodec 3 }
     
 wwpVoiceGatewayPacketizationMinPeriod  OBJECT-TYPE
     SYNTAX         Integer32
     UNITS          "milliseconds"    
     MAX-ACCESS     read-write
     STATUS         current
     DESCRIPTION
	     "Min packet time for the complex codes specified by
	     wwpVoiceGatewayComplexCodec. FOR G723 the packet time
	     is fixed to be 30ms." 
     ::= { wwpVoiceGatewayCodec 4 }
     
 wwpVoiceGatewayPacketizationMaxPeriod  OBJECT-TYPE
     SYNTAX         Integer32
     UNITS          "milliseconds"    
     MAX-ACCESS     read-write
     STATUS         current
     DESCRIPTION
	     "Max packet time for the complex codes specified by
	     wwpVoiceGatewayComplexCodec. FOR G723 the packet time
	     is fixed to be 30ms." 
     ::= { wwpVoiceGatewayCodec 5 }
 
 -- 
 --  Audio Group
 -- 
 wwpVoiceGatewayPayloadType  OBJECT-TYPE
     SYNTAX         Integer32(94..127)    
     MAX-ACCESS     read-write
     STATUS         current
     DESCRIPTION
	     "The Payload Format for the telephone events." 
     ::= { wwpVoiceGatewayAudio 1 }
     
 wwpVoiceGatewaySendEventsViaRFC2833  OBJECT-TYPE
     SYNTAX         TruthValue    
     MAX-ACCESS     read-write
     STATUS         current
     DESCRIPTION
	     "Setting this object to 'true' will cause the
	     voice gateway to send Telephone Events via RFC2833 
	     signalling using wwpVoiceGatewayPayloadType." 
     ::= { wwpVoiceGatewayAudio 2 }
     
 wwpVoiceGatewayDropVoicePktsDuringEvents  OBJECT-TYPE
     SYNTAX         TruthValue    
     MAX-ACCESS     read-write
     STATUS         current
     DESCRIPTION
	     "Setting this object to 'true' will cause the
	     voice gateway to drop voice packets during RFC2833 
	     Telephone Event packets." 
     ::= { wwpVoiceGatewayAudio 3 }
     
 wwpVoiceGatewaySquelchInbandDtmfAudio  OBJECT-TYPE
     SYNTAX         TruthValue    
     MAX-ACCESS     read-write
     STATUS         current
     DESCRIPTION
	     "Setting this object to 'true' will cause the
	     voice gateway to Squelch the Inband DTMF Audio." 
     ::= { wwpVoiceGatewayAudio 4 }
       
 -- 
 --  Stats Group
 -- 
 wwpVoiceGatewayPktsTx  OBJECT-TYPE
     SYNTAX         Counter32    
     MAX-ACCESS     read-only
     STATUS         current
     DESCRIPTION
	     "The total number of RTP data packets transmitted 
	     by the voice gateway since starting transmission on this connection." 
     ::= { wwpVoiceGatewayStats 1 }
     
 wwpVoiceGatewayOctetsTx  OBJECT-TYPE
     SYNTAX         Counter32    
     MAX-ACCESS     read-only
     STATUS         current
     DESCRIPTION
	     "The total number of payload octets (i.e., not including 
	     header or padding) transmitted in RTP data packets by the 
	     voice gateway since starting transmission on this connection. "
     ::= { wwpVoiceGatewayStats 2 }
     
 wwpVoiceGatewayPktsRx  OBJECT-TYPE
     SYNTAX         Counter32    
     MAX-ACCESS     read-only
     STATUS         current
     DESCRIPTION
	     "The total number of RTP data packets received by the 
	     voice gateway since starting reception on this connection."
     ::= { wwpVoiceGatewayStats 3 }
     
 wwpVoiceGatewayOctetsRx  OBJECT-TYPE
     SYNTAX         Counter32    
     MAX-ACCESS     read-only
     STATUS         current
     DESCRIPTION
	     "The total number of payload octets (i.e., not including header or
             padding) transmitted in RTP data packets by the voice gateway since 
	     starting transmission on this connection."
     ::= { wwpVoiceGatewayStats 4 }
   
 wwpVoiceGatewayPktsLost  OBJECT-TYPE
     SYNTAX         Counter32    
     MAX-ACCESS     read-only
     STATUS         current
     DESCRIPTION
             "The total number of RTP data packets that have been lost since the
             beginning of reception. This number is defined to be the number of
             packets expected less the number of packets actually received, where
             the number of packets received includes any which are late or
             duplicates." 
     ::= { wwpVoiceGatewayStats 5 }
  
 wwpVoiceGatewayIntervalJitter  OBJECT-TYPE
     SYNTAX         Integer32
     UNITS          "milliseconds"     
     MAX-ACCESS     read-only
     STATUS         current
     DESCRIPTION   
             "An estimate of the statistical variance of the RTP data packet
             interarrival time measured in milliseconds and expressed as an
             unsigned integer. The interarrival jitter J is defined to be the mean
             deviation (smoothed absolute value) of the difference D in packet
             spacing at the receiver compared to the sender for a pair of packets."
     ::= { wwpVoiceGatewayStats 6 }
   
 wwpVoiceGatewayLatency  OBJECT-TYPE
     SYNTAX         Integer32
     UNITS          "milliseconds"    
     MAX-ACCESS     read-only
     STATUS         current
     DESCRIPTION     
             "An estimate of the network latency, expressed in milliseconds. This
             is the average value of the difference between the NTP timestamp
             indicated by the senders of the RTCP messages and the NTP timestamp
             of the receivers, measured when this messages are received."
     ::= { wwpVoiceGatewayStats 7 } 

 wwpVoiceGatewayResetStatCounters OBJECT-TYPE
      SYNTAX           INTEGER {
                         none(0),
                         reset(1)
                       }
      MAX-ACCESS       read-write
      STATUS           current   
      DESCRIPTION
	      "To reset voice statistic counters , this object
              should be set to 'reset'. 
              
             A read on this object should return none(0)."
     ::= { wwpVoiceGatewayStats 8 } 
 


 
 wwpVoiceGatewayNumResets  OBJECT-TYPE
     SYNTAX       Unsigned32 (0..2147483647)
     MAX-ACCESS   read-only
     STATUS       current
     DESCRIPTION
	     "This object defines the number of times that the voice gateway has
	      been restarted."
      ::= { wwpVoiceReset 1 }
      
 wwpVoiceGatewayReset  OBJECT-TYPE
      SYNTAX      INTEGER {
		       none(0),
		       reset(1),
		       resetDefault(2)
	          }
     MAX-ACCESS   read-write
     STATUS       current
     DESCRIPTION     
             "Writing one of the specified values to this field causes
	      the specified type of reboot to occur.  
				
	      none is the value returned when this leaf is queried.
	      writing this value to the leaf will have no effect.
				
	      reset causes the voice gateway to restart using
	      its current configuration.
				 
	      resetDefault will reset the voice gateway to factory defaults."							
      DEFVAL { none }
      ::= { wwpVoiceReset 2 }
   
 wwpVoiceAccess OBJECT-TYPE
      SYNTAX      INTEGER {
		       allow(1),
		       deny(2)  
	          }
     MAX-ACCESS   read-write
     STATUS       current
     DESCRIPTION     
             "Setting this object to 'deny' will disable
             access to VMI from SMI when connected 
             via Telnet or console."							
      DEFVAL { allow }
      ::= { wwpVoiceSec 1 }
      
 wwpMgmtAccess OBJECT-TYPE
      SYNTAX      INTEGER {
		       allow(1),
		       deny(2)  
	          }
     MAX-ACCESS   read-write
     STATUS       current
     DESCRIPTION     
             "Setting this object to 'deny' will disable
             access to SMI from VMI when connected 
             via Telnet or console."							
      DEFVAL { allow }
      ::= { wwpVoiceSec 2 }
  
 --
 -- Call Agent OTA Modes
 -- 
 wwpVoiceCallAgentOtaModes OBJECT-TYPE
      SYNTAX      INTEGER {
		       ifOtaRecv(1),
		       sendOta(2)  
	          }
     MAX-ACCESS   read-write
     STATUS       current
     DESCRIPTION     
             "Setting this object to 'ifOtaRecv' will configure the device to send OTA 
	      if and only if OTA is received from call Agent.
	      Setting this object to 'sendOta' will configure the device to always send OTA 
	      sdp parameters."
      DEFVAL { sendOta }
      ::= { wwpVoiceGatewayConfigCallAgent 1 }
 
 wwpVoiceCallAgentEgressEvent OBJECT-TYPE
      SYNTAX      INTEGER {
		       sendIngressEgressNotif(1),
		       sendIngressNotif(2)  
	          }
     MAX-ACCESS   read-write
     STATUS       current
     DESCRIPTION     
             "Setting this object to 'sendIngressEgressNotif' will configure the device to send 
	      ingress and egress fax and modem tone notification. 
	      Setting this object to 'sendIngressNotif' will configure the device to send 
	      only ingress fax and modem tone notification."
      DEFVAL { sendIngressEgressNotif }
      ::= { wwpVoiceGatewayConfigCallAgent 2 }

 --
 -- Pot Lines
 -- 
 wwpVoiceCallAgentPotsLine OBJECT-TYPE
      SYNTAX      INTEGER {
		       enable1PotLine(1),
		       enable2PotLine(2)  
	          }
     MAX-ACCESS   read-write
     STATUS       current
     DESCRIPTION     
             "Setting this object to 'enable1PotLine' will configure the device to enable 
	      Line 1 only.
	      Setting this object to 'enable2PotLine' will configure the device to enable 
	      2 pots lines. 
	      Device 'may' require reboot to enable pot line changes."
      DEFVAL { enable2PotLine }
      ::= { wwpVoiceGatewayConfigPots 1 }
 
 --
 -- Autonomous Fax Mode
 -- 
 wwpVoiceAutonomousFaxState OBJECT-TYPE
      SYNTAX      INTEGER {
		       enable(1),
		       disable(2)  
	          }
     MAX-ACCESS   read-write
     STATUS       current
     DESCRIPTION     
             "Setting this object to 'enable' will configure the device to enable 
	      autonomous fax behavior.
	      Setting this object to 'disable' will configure the device to disable 
	      autonomous fax behavior."
      DEFVAL { disable }
      ::= { wwpVoiceGatewayConfigFax 1 }


 --
 -- Endpoint configuration
 -- 
 wwpVoiceEndPointName OBJECT-TYPE
      SYNTAX      INTEGER {		       
		       unknown(1),
		       ip(2),
		       mac(3),
		       hostName(4),
		       fqdn(5)
	          }
     MAX-ACCESS   read-write
     STATUS       current     
     DESCRIPTION     
             "Setting this object will control how a voip 
	     endpoint name will be determined.
	     This object cannot be set to 'unknown'."      
     DEFVAL     { ip }
      ::= { wwpVoiceGatewayConfigEndPoint 1 }

 --
 -- NotifiedEntity Cached DNS configuration
 -- 
 wwpVoiceNotifEntCache OBJECT-TYPE
     SYNTAX         Integer32(0..1440)    
     MAX-ACCESS     read-write
     STATUS         current
     DESCRIPTION
	     "Timeout in minutes for cached DNS lookups for MGCP RQNT 
	     Notified Entity field" 
     DEFVAL     { 1440 }
      ::= { wwpVoiceGatewayConfigNotifEntityCache 1 }

 --
 -- Adaptive Jitter Buffer Mode
 -- 
 wwpVoiceJitterOptionState OBJECT-TYPE
      SYNTAX      INTEGER {
		       disable(0),  
		       enable(1)
	          }
     MAX-ACCESS   read-write
     STATUS       current
     DESCRIPTION     
             "Setting this object to 'enable' will configure the jitter buffer to change
	      to an adaptive jitter buffer size.
	      Setting this object to 'disable' will configure the jitter buffer to use 
	      a fixed jitter buffer size."
      DEFVAL { disable }
      ::= { wwpVoiceGatewayConfigJitterBuffer 1 }


 wwpVoiceJitterBufferMinPeriod  OBJECT-TYPE
     SYNTAX         Integer32
     UNITS          "milliseconds"    
     MAX-ACCESS     read-write
     STATUS         current
     DESCRIPTION
	     "Minimum Holding time. Setting this value will 
	     limit the jitter buffer from adapting below this value.
	     The smallest period is fixed at 20ms." 
     ::= { wwpVoiceGatewayConfigJitterBufferMinPeriod 1 }
     

 wwpVoiceJitterBufferMaxPeriod  OBJECT-TYPE
     SYNTAX         Integer32
     UNITS          "milliseconds"    
     MAX-ACCESS     read-write
     STATUS         current
     DESCRIPTION
	     "Maximum Holding time. Setting this value will 
	     limit the jitter buffer from adapting above this value.
	     The largest period is fixed at 300ms." 
     ::= { wwpVoiceGatewayConfigJitterBufferMaxPeriod 1 }
     

 wwpVoiceJitterBufferTargetPeriod  OBJECT-TYPE
     SYNTAX         Integer32
     UNITS          "milliseconds"    
     MAX-ACCESS     read-write
     STATUS         current
     DESCRIPTION
	     "Target Holding time. Setting this value sets the 
	     initial jitter buffer size." 
     ::= { wwpVoiceGatewayConfigJitterBufferTargetPeriod 1 }
     
 wwpVoiceGatewayCodecOverride OBJECT-TYPE
      SYNTAX      INTEGER {
		       g711PCMU(1),
		       g711PCMA(2)
	          }
     MAX-ACCESS   read-write
     STATUS       current
     DESCRIPTION     
       "Selecting data codec override forces the default data codec 
       to the specified value, overriding the standard default data 
       codec which is tied to country code.
        1 = force specification of G711 PCMU as default codec
        2 = force specification of G711 PCMA as default codec "
    ::= { wwpVoiceGatewayConfigCodecOverride 1 }

wwpVoiceGatewayTestServerConnection OBJECT-TYPE
     SYNTAX       INTEGER {
		                  none(0)
	               }
     MAX-ACCESS   read-write
     STATUS       current
     DESCRIPTION
	     "Writing one of the specified values to this field causes
        mesages to be sent to voice server to test connectivity"
     DEFVAL { none }
 	::= { wwpVoiceGatewayConfigTestServerConnection 1 }
  
 wwpVoiceGatewayLastServerResponseTime   OBJECT-TYPE
     SYNTAX       OCTET STRING(SIZE(0..32))
     MAX-ACCESS   read-only
     STATUS       current
     DESCRIPTION
	     "Last server response timestamp. Used as part of testing
        voice server connectivity"
 	::= { wwpVoiceGatewayConfigLastServerResponseTime 1 } 
  
 -- 
 -- SIP Group
 --
 
 wwpVoiceGatewaySipSessionTimeoutPeriod  OBJECT-TYPE
     SYNTAX         Integer32(0..3600)
     UNITS          "seconds"    
     MAX-ACCESS     read-write
     STATUS         current
     DESCRIPTION
	     "Configures session expiration time in seconds.  
        Set value to 0 to disable" 
     DEFVAL     { 1800 }
    ::= { wwpVoiceGatewaySIP 1}

 wwpVoiceGatewaySipRegisterTimeoutPeriod  OBJECT-TYPE
     SYNTAX         Integer32(0..3600)
     UNITS          "seconds"    
     MAX-ACCESS     read-write
     STATUS         current
     DESCRIPTION
	     " Configures registration expiration time in seconds. 
        Used only when registrar is used.  
        Set value to 0 to disable." 
     DEFVAL     { 3600 }
    ::= { wwpVoiceGatewaySIP 2 }

 wwpVoiceGatewaySipForceQuotesState OBJECT-TYPE
      SYNTAX      INTEGER {
		       disable(0), 
		       enable(1)
	          }
     MAX-ACCESS   read-write
     STATUS       current
     DESCRIPTION     
             "Configuration to force display names to be 
             embraced by double quotes. "
      DEFVAL { disable }
    ::= { wwpVoiceGatewaySIP 3 }
   
 wwpVoiceGatewaySipPhoneLineTable OBJECT-TYPE
     SYNTAX     SEQUENCE OF WwpVoiceGatewaySipPhoneLineEntry
     MAX-ACCESS not-accessible
     STATUS     current
     DESCRIPTION
	     "SIP Pots Line table
        This table confures users for each POTs line"
     ::= { wwpVoiceGatewaySIP 4 }
		
 wwpVoiceGatewaySipPhoneLineEntry OBJECT-TYPE
     SYNTAX      WwpVoiceGatewaySipPhoneLineEntry
     MAX-ACCESS  not-accessible
     STATUS      current
     DESCRIPTION
	     "table of sip line configuration"
     INDEX { wwpVoiceGatewaySipLineId }
     ::= { wwpVoiceGatewaySipPhoneLineTable 1 }
		
 WwpVoiceGatewaySipPhoneLineEntry ::=  SEQUENCE { 
     wwpVoiceGatewaySipLineId                    Integer32,
     wwpVoiceGatewaySipPhoneNumber               OCTET STRING,
     wwpVoiceGatewaySipUserName                  OCTET STRING,
     wwpVoiceGatewaySipUserDisplayName           OCTET STRING,
     wwpVoiceGatewaySipUserPassword              OCTET STRING,
     wwpVoiceGatewaySipDialPlan                  OCTET STRING
 }

 wwpVoiceGatewaySipLineId OBJECT-TYPE
     SYNTAX         Integer32(1..2)    
     MAX-ACCESS     read-only
     STATUS         current
     DESCRIPTION
	     "Pots port Id"
     ::= { wwpVoiceGatewaySipPhoneLineEntry 1 }
		
 wwpVoiceGatewaySipPhoneNumber OBJECT-TYPE
     SYNTAX       OCTET STRING(SIZE(0..31))
     MAX-ACCESS   read-create
     STATUS       current
     DESCRIPTION
	     "Phone Number associated with this line."
     ::= { wwpVoiceGatewaySipPhoneLineEntry 2 }
     
 wwpVoiceGatewaySipUserName OBJECT-TYPE
     SYNTAX       OCTET STRING(SIZE(0..31))
     MAX-ACCESS   read-create
     STATUS       current
     DESCRIPTION
	     "User Name associated with this line."
     ::= { wwpVoiceGatewaySipPhoneLineEntry 3 }

 wwpVoiceGatewaySipUserDisplayName OBJECT-TYPE
     SYNTAX       OCTET STRING(SIZE(0..31))
     MAX-ACCESS   read-create
     STATUS       current
     DESCRIPTION
	     "User Display Name associated with this line."
     ::= { wwpVoiceGatewaySipPhoneLineEntry 4 }
     
 wwpVoiceGatewaySipUserPassword OBJECT-TYPE
     SYNTAX       OCTET STRING(SIZE(0..31))
     MAX-ACCESS   read-create
     STATUS       current
     DESCRIPTION
	     "User Password associated with this line."
     ::= { wwpVoiceGatewaySipPhoneLineEntry 5 }

  wwpVoiceGatewaySipDialPlan OBJECT-TYPE
     SYNTAX          OCTET STRING(SIZE(0..255)) 
     MAX-ACCESS      read-write
     STATUS          current
     DESCRIPTION     
             "Configuration for dial plan expression string.
             Note: subset of unix regular expressions supported."
    ::= { wwpVoiceGatewaySipPhoneLineEntry 6}

 
 wwpVoiceGatewaySipPhoneLineTimerTable OBJECT-TYPE
     SYNTAX     SEQUENCE OF WwpVoiceGatewaySipPhoneLineTimerEntry
     MAX-ACCESS not-accessible
     STATUS     current
     DESCRIPTION
	     "SIP Pots Line table
        This table configures users for each POTs line"
     ::= { wwpVoiceGatewaySIP 5 }
		
 wwpVoiceGatewaySipPhoneLineTimerEntry OBJECT-TYPE
     SYNTAX      WwpVoiceGatewaySipPhoneLineTimerEntry
     MAX-ACCESS  not-accessible
     STATUS      current
     DESCRIPTION
	     "Table of sip phone line configuration"
     INDEX { wwpVoiceGatewaySipTimerLineId }
     ::= { wwpVoiceGatewaySipPhoneLineTimerTable 1 }
		
 WwpVoiceGatewaySipPhoneLineTimerEntry ::=  SEQUENCE { 
     wwpVoiceGatewaySipTimerLineId        Integer32,
     wwpVoiceGatewaySipDialTimerLong      Integer32
 }

 wwpVoiceGatewaySipTimerLineId OBJECT-TYPE
     SYNTAX         Integer32(1..2)    
     MAX-ACCESS     read-only
     STATUS         current
     DESCRIPTION
	     "Pots port Id"
     ::= { wwpVoiceGatewaySipPhoneLineTimerEntry 1 }
    
wwpVoiceGatewaySipDialTimerLong OBJECT-TYPE
     SYNTAX         Integer32(0..10)    
     MAX-ACCESS     read-write
     STATUS         current
     DESCRIPTION
	     "Long Timeout for SIP dialing"
     ::= { wwpVoiceGatewaySipPhoneLineTimerEntry 2 }
     
 wwpVoiceGatewaySIPServers    OBJECT IDENTIFIER ::= { wwpVoiceGatewaySIP 6 }
 wwpVoiceGatewaySIPProxyServers    OBJECT IDENTIFIER ::= { wwpVoiceGatewaySIPServers 1 }
 wwpVoiceGatewaySIPRegistrarServers    OBJECT IDENTIFIER ::= { wwpVoiceGatewaySIPServers 2 }
 wwpVoiceGatewaySIPLogServers    OBJECT IDENTIFIER ::= { wwpVoiceGatewaySIPServers 3 }
 
 wwpVoiceGatewaySipProxyAddr OBJECT-TYPE
     SYNTAX          DisplayString 
     MAX-ACCESS      read-write
     STATUS          current
     DESCRIPTION
             "The complete address of a default Proxy is composed of  
             IP address/Domain Name and UDP port.
             wwpVoiceGatewayRegistrarAddr specifies address of the Proxy
             server to which SIP messages are sent.
             
             Proxy address may be an IP address or fully qualified 
             domain name (FQDN)."
    ::= { wwpVoiceGatewaySIPProxyServers 1 }

 wwpVoiceGatewaySipProxyPort OBJECT-TYPE
    SYNTAX      Integer32(1025..65535)
    MAX-ACCESS  read-write
    STATUS      current
    DESCRIPTION
            "This object is used to configure the UDP port
            of the SIP Proxy Server.

            The UDP port is used together with wwpVoiceGatewaySipProxyAddr to  
            specify the destination address of the Proxy to which SIP 
            messages are sent."
    DEFVAL { 5060 }  
    ::= { wwpVoiceGatewaySIPProxyServers 2 }


 wwpVoiceGatewaySipRegistrarAddr OBJECT-TYPE
     SYNTAX          DisplayString 
     MAX-ACCESS      read-write
     STATUS          current
     DESCRIPTION
             " The complete address of a default Registrar is composed of  
             IP address/Domain Name and UDP port.
        
             wwpVoiceGatewayRegistrarAddr specifies address of the Regsitrar
             to which SIP Registration messages are sent whenever system starts
             or line goes up.
             
             Registrar address may be an IP address or fully qualified 
             domain name (FQDN)."
    ::= { wwpVoiceGatewaySIPRegistrarServers 1 }

 wwpVoiceGatewaySipRegistrarPort OBJECT-TYPE
    SYNTAX      Integer32(1025..65535)
    MAX-ACCESS  read-write
    STATUS      current
    DESCRIPTION
            " This object is used to configure the UDP port
            of the SIP Registrar.

            The UDP port is used together with wwpVoiceGatewaySipRegistrarAddr to  
            specify the destination addressto which SIP Registration messages are
            sent when system starts or line goes up."
    DEFVAL { 5060 }  
    ::= { wwpVoiceGatewaySIPRegistrarServers 2 }
    
 wwpVoiceGatewaySipSyslogAddr OBJECT-TYPE
     SYNTAX          DisplayString 
     MAX-ACCESS      read-write
     STATUS          current
     DESCRIPTION
             " The complete address of a default SIP SysLog server is composed of  
             IP address/Domain Name and UDP port.
        
             wwpVoiceGatewaySipSyslogAddr specifies address of the SIP SysLog server
             to which SIP Log messages are sent.
             
             SysLog server address may be an IP address or fully qualified 
             domain name (FQDN)."
    ::= { wwpVoiceGatewaySIPLogServers 1 }

 wwpVoiceGatewaySipSyslogPort OBJECT-TYPE
    SYNTAX      Integer32(1..65535)
    MAX-ACCESS  read-write
    STATUS      current
    DESCRIPTION
            "This object is used to configure the UDP port
            of the SIP Log Servert.

            The UDP port is used together with wwpVoiceGatewaySipSyslogAddr to  
            specify the destination address to which SIP Log mesaages are
            sent when system starts or line goes up."
    DEFVAL { 514 }  
    ::= { wwpVoiceGatewaySIPLogServers 2 }

 wwpVoiceGatewaySipSyslogLogLevel OBJECT-TYPE
    SYNTAX      INTEGER(1..4)
    MAX-ACCESS  read-write
    STATUS      current
    DESCRIPTION
            "This object is used to configure the log level or verbosity of the SIP messages"
    DEFVAL { 2 }  
    ::= { wwpVoiceGatewaySIPLogServers 3 }
   
wwpVoiceGatewaySIPPreferredCodec OBJECT-TYPE
      SYNTAX      INTEGER {
		       g711(1), 
		       g729(2)
	          }
     MAX-ACCESS   read-write
     STATUS       current
     DESCRIPTION     
             "Configuration to set preferred codec. "
      DEFVAL { g711 }
    ::= { wwpVoiceGatewaySIP 7 }
 
 wwpVoiceGatewaySIPDtmfEventHandling OBJECT-TYPE
      SYNTAX      INTEGER {
		       audio(1), 
		       info(2),
				 rfc2833(3)
	          }
     MAX-ACCESS   read-write
     STATUS       current
     DESCRIPTION     
             "Configuration for device to send DTMF digits via SIP INFO message or in 
				 RTP RFC2833 event message in addition to the audio tone in RTP stream. 
				 The default is always an audio tone sent in the RTP stream."
      DEFVAL { audio }
    ::= { wwpVoiceGatewaySIP 8 }
	 
 --
 -- SIP Call Feature processing
 -- 
    
 wwpVoiceGatewaySIPCallFeatures    OBJECT IDENTIFIER ::= { wwpVoiceGatewaySIP 9 }

 wwpVoiceGatewayHookFlashEnable OBJECT-TYPE
      SYNTAX      TruthValue
     MAX-ACCESS   read-write
     STATUS       current
     DESCRIPTION     
             "Setting this object to 'true' will configure the device to process hook flash events..
	      Setting this object to 'false' will configure the device to ignore hookflash events."
      DEFVAL { true }
      ::= { wwpVoiceGatewaySIPCallFeatures 1 }

 --
 -- Protocol Selection
 -- 
	 
  wwpVoiceGatewayProtocolType OBJECT-TYPE
      SYNTAX      INTEGER {
		       mgcp(1),
				 sip(2)
	          }
     MAX-ACCESS   read-write
     STATUS       current
     DESCRIPTION     
             "Configuration to select VoIP protocol. Setting this value to 'mgcp' will allow the 
				 configuration the MGCP funtionality.
				 Setting this value to 'sip' will allow the configuration the SIP funtionality"
      DEFVAL { mgcp }
    ::= { wwpVoiceGatewayConfigProtocolType 1 }

  wwpVoiceGatewayProtocolEnable OBJECT-TYPE
      SYNTAX      TruthValue
     MAX-ACCESS   read-write
     STATUS       current
     DESCRIPTION     
             "Configuration to enable VoIP protocol. Setting this value to 'enable' 
				 will cause VoIP stack to start at bootup"
      DEFVAL { false }
    ::= { wwpVoiceGatewayConfigProtocolEnable 1 }


 END

 --
 -- WWP-VOICE-GATEWAY-MIB.my
 --

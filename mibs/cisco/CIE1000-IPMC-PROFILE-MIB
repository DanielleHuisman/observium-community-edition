-- *****************************************************************
-- IPMC-PROFILE-MIB:  Cisco private MIB
-- ****************************************************************

CIE1000-IPMC-PROFILE-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    cie1000SwitchMgmt FROM CISCO-IE1000-MIB
    CIE1000DisplayString FROM CIE1000-TC
    CIE1000RowEditorState FROM CIE1000-TC
    InetAddressIPv6 FROM INET-ADDRESS-MIB
    Integer32 FROM SNMPv2-SMI
    IpAddress FROM SNMPv2-SMI
    TruthValue FROM SNMPv2-TC
    ;

cie1000IpmcProfileMib MODULE-IDENTITY
    LAST-UPDATED "201407010000Z"
    ORGANIZATION
        "Cisco Systems, Inc."
    CONTACT-INFO
        "Cisco Systems
	 Customer Service

	 Postal: 170 West Tasman Drive
	 San Jose, CA  95134
	 USA

	 Tel: +1 800 553-NETS

	 E-mail: cs-snmp@cisco.com"
    DESCRIPTION
        "This is a private version of the IPMC Profile MIB"
    REVISION    "201407010000Z"
    DESCRIPTION
        "Initial version"
    ::= { cie1000SwitchMgmt 38 }


CIE1000IpmcProfileRuleActionType ::= TEXTUAL-CONVENTION
    STATUS      current
    DESCRIPTION
        "This enumeration indicates the configured action type for IPMC profile
         rule."
    SYNTAX      INTEGER { deny(0), permit(1) }

cie1000IpmcProfileMibObjects OBJECT IDENTIFIER
    ::= { cie1000IpmcProfileMib 1 }

cie1000IpmcProfileConfig OBJECT IDENTIFIER
    ::= { cie1000IpmcProfileMibObjects 2 }

cie1000IpmcProfileConfigGlobals OBJECT IDENTIFIER
    ::= { cie1000IpmcProfileConfig 1 }

cie1000IpmcProfileConfigGlobalsAdminState OBJECT-TYPE
    SYNTAX      TruthValue
    MAX-ACCESS  read-write
    STATUS      current
    DESCRIPTION
        "Enable/Disable the IPMC Profile global functionality."
    ::= { cie1000IpmcProfileConfigGlobals 1 }

cie1000IpmcProfileConfigMgmtTable OBJECT-TYPE
    SYNTAX      SEQUENCE OF CIE1000IpmcProfileConfigMgmtEntry
    MAX-ACCESS  not-accessible
    STATUS      current
    DESCRIPTION
        "This is a table for managing IPMC profile entries."
    ::= { cie1000IpmcProfileConfig 2 }

cie1000IpmcProfileConfigMgmtEntry OBJECT-TYPE
    SYNTAX      CIE1000IpmcProfileConfigMgmtEntry
    MAX-ACCESS  not-accessible
    STATUS      current
    DESCRIPTION
        "Each entry has a set of parameters"
    INDEX       { cie1000IpmcProfileConfigMgmtProfileName }
    ::= { cie1000IpmcProfileConfigMgmtTable 1 }

CIE1000IpmcProfileConfigMgmtEntry ::= SEQUENCE {
    cie1000IpmcProfileConfigMgmtProfileName         CIE1000DisplayString,
    cie1000IpmcProfileConfigMgmtProfileDescription  CIE1000DisplayString,
    cie1000IpmcProfileConfigMgmtAction              CIE1000RowEditorState
}

cie1000IpmcProfileConfigMgmtProfileName OBJECT-TYPE
    SYNTAX      CIE1000DisplayString (SIZE(0..16))
    MAX-ACCESS  accessible-for-notify
    STATUS      current
    DESCRIPTION
        "The name of the IPMC profile management entry."
    ::= { cie1000IpmcProfileConfigMgmtEntry 1 }

cie1000IpmcProfileConfigMgmtProfileDescription OBJECT-TYPE
    SYNTAX      CIE1000DisplayString (SIZE(0..64))
    MAX-ACCESS  read-write
    STATUS      current
    DESCRIPTION
        "The description of the IPMC Profile management entry."
    ::= { cie1000IpmcProfileConfigMgmtEntry 2 }

cie1000IpmcProfileConfigMgmtAction OBJECT-TYPE
    SYNTAX      CIE1000RowEditorState
    MAX-ACCESS  read-write
    STATUS      current
    DESCRIPTION
        "Action"
    ::= { cie1000IpmcProfileConfigMgmtEntry 100 }

cie1000IpmcProfileConfigMgmtTableRowEditor OBJECT IDENTIFIER
    ::= { cie1000IpmcProfileConfig 3 }

cie1000IpmcProfileConfigMgmtTableRowEditorProfileName OBJECT-TYPE
    SYNTAX      CIE1000DisplayString (SIZE(0..16))
    MAX-ACCESS  read-write
    STATUS      current
    DESCRIPTION
        "The name of the IPMC profile management entry."
    ::= { cie1000IpmcProfileConfigMgmtTableRowEditor 1 }

cie1000IpmcProfileConfigMgmtTableRowEditorProfileDescription OBJECT-TYPE
    SYNTAX      CIE1000DisplayString (SIZE(0..64))
    MAX-ACCESS  read-write
    STATUS      current
    DESCRIPTION
        "The description of the IPMC Profile management entry."
    ::= { cie1000IpmcProfileConfigMgmtTableRowEditor 2 }

cie1000IpmcProfileConfigMgmtTableRowEditorAction OBJECT-TYPE
    SYNTAX      CIE1000RowEditorState
    MAX-ACCESS  read-write
    STATUS      current
    DESCRIPTION
        "Action"
    ::= { cie1000IpmcProfileConfigMgmtTableRowEditor 100 }

cie1000IpmcProfileConfigIpv4AddrRangeTable OBJECT-TYPE
    SYNTAX      SEQUENCE OF CIE1000IpmcProfileConfigIpv4AddrRangeEntry
    MAX-ACCESS  not-accessible
    STATUS      current
    DESCRIPTION
        "This is a table for managing the IPv4 address range entries that will
         be applied for IPMC profile(s)."
    ::= { cie1000IpmcProfileConfig 4 }

cie1000IpmcProfileConfigIpv4AddrRangeEntry OBJECT-TYPE
    SYNTAX      CIE1000IpmcProfileConfigIpv4AddrRangeEntry
    MAX-ACCESS  not-accessible
    STATUS      current
    DESCRIPTION
        "Each entry has a set of parameters"
    INDEX       { cie1000IpmcProfileConfigIpv4AddrRangeRangeName }
    ::= { cie1000IpmcProfileConfigIpv4AddrRangeTable 1 }

CIE1000IpmcProfileConfigIpv4AddrRangeEntry ::= SEQUENCE {
    cie1000IpmcProfileConfigIpv4AddrRangeRangeName     CIE1000DisplayString,
    cie1000IpmcProfileConfigIpv4AddrRangeStartAddress  IpAddress,
    cie1000IpmcProfileConfigIpv4AddrRangeEndAddress    IpAddress,
    cie1000IpmcProfileConfigIpv4AddrRangeAction        CIE1000RowEditorState
}

cie1000IpmcProfileConfigIpv4AddrRangeRangeName OBJECT-TYPE
    SYNTAX      CIE1000DisplayString (SIZE(0..16))
    MAX-ACCESS  accessible-for-notify
    STATUS      current
    DESCRIPTION
        "The name of the IPMC profile address range entry."
    ::= { cie1000IpmcProfileConfigIpv4AddrRangeEntry 1 }

cie1000IpmcProfileConfigIpv4AddrRangeStartAddress OBJECT-TYPE
    SYNTAX      IpAddress
    MAX-ACCESS  read-write
    STATUS      current
    DESCRIPTION
        "The starting IPv4 address of the range that IPMC Profile performs
         checking."
    ::= { cie1000IpmcProfileConfigIpv4AddrRangeEntry 2 }

cie1000IpmcProfileConfigIpv4AddrRangeEndAddress OBJECT-TYPE
    SYNTAX      IpAddress
    MAX-ACCESS  read-write
    STATUS      current
    DESCRIPTION
        "The ending IPv4 address of the range that IPMC Profile performs
         checking."
    ::= { cie1000IpmcProfileConfigIpv4AddrRangeEntry 3 }

cie1000IpmcProfileConfigIpv4AddrRangeAction OBJECT-TYPE
    SYNTAX      CIE1000RowEditorState
    MAX-ACCESS  read-write
    STATUS      current
    DESCRIPTION
        "Action"
    ::= { cie1000IpmcProfileConfigIpv4AddrRangeEntry 100 }

cie1000IpmcProfileConfigIpv4AddrRangeTableRowEditor OBJECT IDENTIFIER
    ::= { cie1000IpmcProfileConfig 5 }

cie1000IpmcProfileConfigIpv4AddrRangeTableRowEditorRangeName OBJECT-TYPE
    SYNTAX      CIE1000DisplayString (SIZE(0..16))
    MAX-ACCESS  read-write
    STATUS      current
    DESCRIPTION
        "The name of the IPMC profile address range entry."
    ::= { cie1000IpmcProfileConfigIpv4AddrRangeTableRowEditor 1 }

cie1000IpmcProfileConfigIpv4AddrRangeTableRowEditorStartAddress OBJECT-TYPE
    SYNTAX      IpAddress
    MAX-ACCESS  read-write
    STATUS      current
    DESCRIPTION
        "The starting IPv4 address of the range that IPMC Profile performs
         checking."
    ::= { cie1000IpmcProfileConfigIpv4AddrRangeTableRowEditor 2 }

cie1000IpmcProfileConfigIpv4AddrRangeTableRowEditorEndAddress OBJECT-TYPE
    SYNTAX      IpAddress
    MAX-ACCESS  read-write
    STATUS      current
    DESCRIPTION
        "The ending IPv4 address of the range that IPMC Profile performs
         checking."
    ::= { cie1000IpmcProfileConfigIpv4AddrRangeTableRowEditor 3 }

cie1000IpmcProfileConfigIpv4AddrRangeTableRowEditorAction OBJECT-TYPE
    SYNTAX      CIE1000RowEditorState
    MAX-ACCESS  read-write
    STATUS      current
    DESCRIPTION
        "Action"
    ::= { cie1000IpmcProfileConfigIpv4AddrRangeTableRowEditor 100 }

cie1000IpmcProfileConfigIpv6AddrRangeTable OBJECT-TYPE
    SYNTAX      SEQUENCE OF CIE1000IpmcProfileConfigIpv6AddrRangeEntry
    MAX-ACCESS  not-accessible
    STATUS      current
    DESCRIPTION
        "This is a table for managing the IPv6 address range entries that will
         be applied for IPMC profile(s)."
    ::= { cie1000IpmcProfileConfig 6 }

cie1000IpmcProfileConfigIpv6AddrRangeEntry OBJECT-TYPE
    SYNTAX      CIE1000IpmcProfileConfigIpv6AddrRangeEntry
    MAX-ACCESS  not-accessible
    STATUS      current
    DESCRIPTION
        "Each entry has a set of parameters"
    INDEX       { cie1000IpmcProfileConfigIpv6AddrRangeRangeName }
    ::= { cie1000IpmcProfileConfigIpv6AddrRangeTable 1 }

CIE1000IpmcProfileConfigIpv6AddrRangeEntry ::= SEQUENCE {
    cie1000IpmcProfileConfigIpv6AddrRangeRangeName     CIE1000DisplayString,
    cie1000IpmcProfileConfigIpv6AddrRangeStartAddress  InetAddressIPv6,
    cie1000IpmcProfileConfigIpv6AddrRangeEndAddress    InetAddressIPv6,
    cie1000IpmcProfileConfigIpv6AddrRangeAction        CIE1000RowEditorState
}

cie1000IpmcProfileConfigIpv6AddrRangeRangeName OBJECT-TYPE
    SYNTAX      CIE1000DisplayString (SIZE(0..16))
    MAX-ACCESS  accessible-for-notify
    STATUS      current
    DESCRIPTION
        "The name of the IPMC profile address range entry."
    ::= { cie1000IpmcProfileConfigIpv6AddrRangeEntry 1 }

cie1000IpmcProfileConfigIpv6AddrRangeStartAddress OBJECT-TYPE
    SYNTAX      InetAddressIPv6
    MAX-ACCESS  read-write
    STATUS      current
    DESCRIPTION
        "The starting IPv6 address of the range that IPMC Profile performs
         checking."
    ::= { cie1000IpmcProfileConfigIpv6AddrRangeEntry 2 }

cie1000IpmcProfileConfigIpv6AddrRangeEndAddress OBJECT-TYPE
    SYNTAX      InetAddressIPv6
    MAX-ACCESS  read-write
    STATUS      current
    DESCRIPTION
        "The ending IPv6 address of the range that IPMC Profile performs
         checking."
    ::= { cie1000IpmcProfileConfigIpv6AddrRangeEntry 3 }

cie1000IpmcProfileConfigIpv6AddrRangeAction OBJECT-TYPE
    SYNTAX      CIE1000RowEditorState
    MAX-ACCESS  read-write
    STATUS      current
    DESCRIPTION
        "Action"
    ::= { cie1000IpmcProfileConfigIpv6AddrRangeEntry 100 }

cie1000IpmcProfileConfigIpv6AddrRangeTableRowEditor OBJECT IDENTIFIER
    ::= { cie1000IpmcProfileConfig 7 }

cie1000IpmcProfileConfigIpv6AddrRangeTableRowEditorRangeName OBJECT-TYPE
    SYNTAX      CIE1000DisplayString (SIZE(0..16))
    MAX-ACCESS  read-write
    STATUS      current
    DESCRIPTION
        "The name of the IPMC profile address range entry."
    ::= { cie1000IpmcProfileConfigIpv6AddrRangeTableRowEditor 1 }

cie1000IpmcProfileConfigIpv6AddrRangeTableRowEditorStartAddress OBJECT-TYPE
    SYNTAX      InetAddressIPv6
    MAX-ACCESS  read-write
    STATUS      current
    DESCRIPTION
        "The starting IPv6 address of the range that IPMC Profile performs
         checking."
    ::= { cie1000IpmcProfileConfigIpv6AddrRangeTableRowEditor 2 }

cie1000IpmcProfileConfigIpv6AddrRangeTableRowEditorEndAddress OBJECT-TYPE
    SYNTAX      InetAddressIPv6
    MAX-ACCESS  read-write
    STATUS      current
    DESCRIPTION
        "The ending IPv6 address of the range that IPMC Profile performs
         checking."
    ::= { cie1000IpmcProfileConfigIpv6AddrRangeTableRowEditor 3 }

cie1000IpmcProfileConfigIpv6AddrRangeTableRowEditorAction OBJECT-TYPE
    SYNTAX      CIE1000RowEditorState
    MAX-ACCESS  read-write
    STATUS      current
    DESCRIPTION
        "Action"
    ::= { cie1000IpmcProfileConfigIpv6AddrRangeTableRowEditor 100 }

cie1000IpmcProfileConfigRuleTable OBJECT-TYPE
    SYNTAX      SEQUENCE OF CIE1000IpmcProfileConfigRuleEntry
    MAX-ACCESS  not-accessible
    STATUS      current
    DESCRIPTION
        "This is a table for managing the filtering rules with respect to a set
         of address range used in a specific IPMC profile management entry."
    ::= { cie1000IpmcProfileConfig 8 }

cie1000IpmcProfileConfigRuleEntry OBJECT-TYPE
    SYNTAX      CIE1000IpmcProfileConfigRuleEntry
    MAX-ACCESS  not-accessible
    STATUS      current
    DESCRIPTION
        "Each entry has a set of parameters"
    INDEX       { cie1000IpmcProfileConfigRuleProfileName,
                  cie1000IpmcProfileConfigRuleRuleRange }
    ::= { cie1000IpmcProfileConfigRuleTable 1 }

CIE1000IpmcProfileConfigRuleEntry ::= SEQUENCE {
    cie1000IpmcProfileConfigRuleProfileName    CIE1000DisplayString,
    cie1000IpmcProfileConfigRuleRuleRange      CIE1000DisplayString,
    cie1000IpmcProfileConfigRuleNextRuleRange  CIE1000DisplayString,
    cie1000IpmcProfileConfigRuleRuleAction     CIE1000IpmcProfileRuleActionType,
    cie1000IpmcProfileConfigRuleRuleLog        TruthValue,
    cie1000IpmcProfileConfigRuleAction         CIE1000RowEditorState
}

cie1000IpmcProfileConfigRuleProfileName OBJECT-TYPE
    SYNTAX      CIE1000DisplayString (SIZE(0..16))
    MAX-ACCESS  accessible-for-notify
    STATUS      current
    DESCRIPTION
        "The name of the IPMC profile management entry."
    ::= { cie1000IpmcProfileConfigRuleEntry 1 }

cie1000IpmcProfileConfigRuleRuleRange OBJECT-TYPE
    SYNTAX      CIE1000DisplayString (SIZE(0..16))
    MAX-ACCESS  accessible-for-notify
    STATUS      current
    DESCRIPTION
        "The name of the IPMC profile address range used as a rule."
    ::= { cie1000IpmcProfileConfigRuleEntry 2 }

cie1000IpmcProfileConfigRuleNextRuleRange OBJECT-TYPE
    SYNTAX      CIE1000DisplayString (SIZE(0..16))
    MAX-ACCESS  read-write
    STATUS      current
    DESCRIPTION
        "The next rule's address range name that this IPMC Profile management
         entry performs checking."
    ::= { cie1000IpmcProfileConfigRuleEntry 3 }

cie1000IpmcProfileConfigRuleRuleAction OBJECT-TYPE
    SYNTAX      CIE1000IpmcProfileRuleActionType
    MAX-ACCESS  read-write
    STATUS      current
    DESCRIPTION
        "The filtering action while this IPMC Profile management entry performs
         checking. deny(0) will prohibit the IPMC control frames destined to
         protocol stack. permit(1) will pass the IPMC control frames destined to
         protocol stack."
    ::= { cie1000IpmcProfileConfigRuleEntry 4 }

cie1000IpmcProfileConfigRuleRuleLog OBJECT-TYPE
    SYNTAX      TruthValue
    MAX-ACCESS  read-write
    STATUS      current
    DESCRIPTION
        "Enable the IPMC Profile will log matched group address that is filtered
         by this rule with the corresponding action (deny or permit). Disable
         the IPMC Profile will not log any action for any group address whether
         or not to be filtered by this rule."
    ::= { cie1000IpmcProfileConfigRuleEntry 5 }

cie1000IpmcProfileConfigRuleAction OBJECT-TYPE
    SYNTAX      CIE1000RowEditorState
    MAX-ACCESS  read-write
    STATUS      current
    DESCRIPTION
        "Action"
    ::= { cie1000IpmcProfileConfigRuleEntry 100 }

cie1000IpmcProfileConfigRuleTableRowEditor OBJECT IDENTIFIER
    ::= { cie1000IpmcProfileConfig 9 }

cie1000IpmcProfileConfigRuleTableRowEditorProfileName OBJECT-TYPE
    SYNTAX      CIE1000DisplayString (SIZE(0..16))
    MAX-ACCESS  read-write
    STATUS      current
    DESCRIPTION
        "The name of the IPMC profile management entry."
    ::= { cie1000IpmcProfileConfigRuleTableRowEditor 1 }

cie1000IpmcProfileConfigRuleTableRowEditorRuleRange OBJECT-TYPE
    SYNTAX      CIE1000DisplayString (SIZE(0..16))
    MAX-ACCESS  read-write
    STATUS      current
    DESCRIPTION
        "The name of the IPMC profile address range used as a rule."
    ::= { cie1000IpmcProfileConfigRuleTableRowEditor 2 }

cie1000IpmcProfileConfigRuleTableRowEditorNextRuleRange OBJECT-TYPE
    SYNTAX      CIE1000DisplayString (SIZE(0..16))
    MAX-ACCESS  read-write
    STATUS      current
    DESCRIPTION
        "The next rule's address range name that this IPMC Profile management
         entry performs checking."
    ::= { cie1000IpmcProfileConfigRuleTableRowEditor 3 }

cie1000IpmcProfileConfigRuleTableRowEditorRuleAction OBJECT-TYPE
    SYNTAX      CIE1000IpmcProfileRuleActionType
    MAX-ACCESS  read-write
    STATUS      current
    DESCRIPTION
        "The filtering action while this IPMC Profile management entry performs
         checking. deny(0) will prohibit the IPMC control frames destined to
         protocol stack. permit(1) will pass the IPMC control frames destined to
         protocol stack."
    ::= { cie1000IpmcProfileConfigRuleTableRowEditor 4 }

cie1000IpmcProfileConfigRuleTableRowEditorRuleLog OBJECT-TYPE
    SYNTAX      TruthValue
    MAX-ACCESS  read-write
    STATUS      current
    DESCRIPTION
        "Enable the IPMC Profile will log matched group address that is filtered
         by this rule with the corresponding action (deny or permit). Disable
         the IPMC Profile will not log any action for any group address whether
         or not to be filtered by this rule."
    ::= { cie1000IpmcProfileConfigRuleTableRowEditor 5 }

cie1000IpmcProfileConfigRuleTableRowEditorAction OBJECT-TYPE
    SYNTAX      CIE1000RowEditorState
    MAX-ACCESS  read-write
    STATUS      current
    DESCRIPTION
        "Action"
    ::= { cie1000IpmcProfileConfigRuleTableRowEditor 100 }

cie1000IpmcProfileConfigPrecedenceTable OBJECT-TYPE
    SYNTAX      SEQUENCE OF CIE1000IpmcProfileConfigPrecedenceEntry
    MAX-ACCESS  not-accessible
    STATUS      current
    DESCRIPTION
        "This is a table for displaying the rule entries of a specific IPMC
         profile in precedence order."
    ::= { cie1000IpmcProfileConfig 10 }

cie1000IpmcProfileConfigPrecedenceEntry OBJECT-TYPE
    SYNTAX      CIE1000IpmcProfileConfigPrecedenceEntry
    MAX-ACCESS  not-accessible
    STATUS      current
    DESCRIPTION
        "Each entry has a set of parameters."
    INDEX       { cie1000IpmcProfileConfigPrecedenceProfileName,
                  cie1000IpmcProfileConfigPrecedenceRulePrecedence }
    ::= { cie1000IpmcProfileConfigPrecedenceTable 1 }

CIE1000IpmcProfileConfigPrecedenceEntry ::= SEQUENCE {
    cie1000IpmcProfileConfigPrecedenceProfileName     CIE1000DisplayString,
    cie1000IpmcProfileConfigPrecedenceRulePrecedence  Integer32,
    cie1000IpmcProfileConfigPrecedenceRuleRange       CIE1000DisplayString,
    cie1000IpmcProfileConfigPrecedenceNextRuleRange   CIE1000DisplayString,
    cie1000IpmcProfileConfigPrecedenceRuleAction      CIE1000IpmcProfileRuleActionType,
    cie1000IpmcProfileConfigPrecedenceRuleLog         TruthValue
}

cie1000IpmcProfileConfigPrecedenceProfileName OBJECT-TYPE
    SYNTAX      CIE1000DisplayString (SIZE(0..16))
    MAX-ACCESS  accessible-for-notify
    STATUS      current
    DESCRIPTION
        "The name of the IPMC profile management entry."
    ::= { cie1000IpmcProfileConfigPrecedenceEntry 1 }

cie1000IpmcProfileConfigPrecedenceRulePrecedence OBJECT-TYPE
    SYNTAX      Integer32 (0..2147483647)
    MAX-ACCESS  accessible-for-notify
    STATUS      current
    DESCRIPTION
        "The precedence of the IPMC profile rule entry."
    ::= { cie1000IpmcProfileConfigPrecedenceEntry 2 }

cie1000IpmcProfileConfigPrecedenceRuleRange OBJECT-TYPE
    SYNTAX      CIE1000DisplayString (SIZE(0..16))
    MAX-ACCESS  read-only
    STATUS      current
    DESCRIPTION
        "The name of the IPMC profile address range used as a rule."
    ::= { cie1000IpmcProfileConfigPrecedenceEntry 3 }

cie1000IpmcProfileConfigPrecedenceNextRuleRange OBJECT-TYPE
    SYNTAX      CIE1000DisplayString (SIZE(0..16))
    MAX-ACCESS  read-only
    STATUS      current
    DESCRIPTION
        "The next rule's address range name that this IPMC Profile management
         entry performs checking."
    ::= { cie1000IpmcProfileConfigPrecedenceEntry 4 }

cie1000IpmcProfileConfigPrecedenceRuleAction OBJECT-TYPE
    SYNTAX      CIE1000IpmcProfileRuleActionType
    MAX-ACCESS  read-only
    STATUS      current
    DESCRIPTION
        "The filtering action while this IPMC Profile management entry performs
         checking. deny(0) will prohibit the IPMC control frames destined to
         protocol stack. permit(1) will pass the IPMC control frames destined to
         protocol stack."
    ::= { cie1000IpmcProfileConfigPrecedenceEntry 5 }

cie1000IpmcProfileConfigPrecedenceRuleLog OBJECT-TYPE
    SYNTAX      TruthValue
    MAX-ACCESS  read-only
    STATUS      current
    DESCRIPTION
        "Enable the IPMC Profile will log matched group address that is filtered
         by this rule with the corresponding action (deny or permit). Disable
         the IPMC Profile will not log any action for any group address whether
         or not to be filtered by this rule."
    ::= { cie1000IpmcProfileConfigPrecedenceEntry 6 }

cie1000IpmcProfileMibConformance OBJECT IDENTIFIER
    ::= { cie1000IpmcProfileMib 2 }

cie1000IpmcProfileMibCompliances OBJECT IDENTIFIER
    ::= { cie1000IpmcProfileMibConformance 1 }

cie1000IpmcProfileMibGroups OBJECT IDENTIFIER
    ::= { cie1000IpmcProfileMibConformance 2 }

cie1000IpmcProfileConfigGlobalsInfoGroup OBJECT-GROUP
    OBJECTS     { cie1000IpmcProfileConfigGlobalsAdminState }
    STATUS      current
    DESCRIPTION
        "A collection of objects."
    ::= { cie1000IpmcProfileMibGroups 1 }

cie1000IpmcProfileConfigMgmtTableInfoGroup OBJECT-GROUP
    OBJECTS     { cie1000IpmcProfileConfigMgmtProfileName,
                  cie1000IpmcProfileConfigMgmtProfileDescription,
                  cie1000IpmcProfileConfigMgmtAction }
    STATUS      current
    DESCRIPTION
        "A collection of objects."
    ::= { cie1000IpmcProfileMibGroups 2 }

cie1000IpmcProfileConfigMgmtTableRowEditorInfoGroup OBJECT-GROUP
    OBJECTS     {                   cie1000IpmcProfileConfigMgmtTableRowEditorProfileName,
                  cie1000IpmcProfileConfigMgmtTableRowEditorProfileDescription,
                  cie1000IpmcProfileConfigMgmtTableRowEditorAction }
    STATUS      current
    DESCRIPTION
        "A collection of objects."
    ::= { cie1000IpmcProfileMibGroups 3 }

cie1000IpmcProfileConfigIpv4AddrRangeTableInfoGroup OBJECT-GROUP
    OBJECTS     { cie1000IpmcProfileConfigIpv4AddrRangeRangeName,
                  cie1000IpmcProfileConfigIpv4AddrRangeStartAddress,
                  cie1000IpmcProfileConfigIpv4AddrRangeEndAddress,
                  cie1000IpmcProfileConfigIpv4AddrRangeAction }
    STATUS      current
    DESCRIPTION
        "A collection of objects."
    ::= { cie1000IpmcProfileMibGroups 4 }

cie1000IpmcProfileConfigIpv4AddrRangeTableRowEditorInfoGroup OBJECT-GROUP
    OBJECTS     {                   cie1000IpmcProfileConfigIpv4AddrRangeTableRowEditorRangeName,
                  cie1000IpmcProfileConfigIpv4AddrRangeTableRowEditorStartAddress,
                  cie1000IpmcProfileConfigIpv4AddrRangeTableRowEditorEndAddress,
                  cie1000IpmcProfileConfigIpv4AddrRangeTableRowEditorAction }
    STATUS      current
    DESCRIPTION
        "A collection of objects."
    ::= { cie1000IpmcProfileMibGroups 5 }

cie1000IpmcProfileConfigIpv6AddrRangeTableInfoGroup OBJECT-GROUP
    OBJECTS     { cie1000IpmcProfileConfigIpv6AddrRangeRangeName,
                  cie1000IpmcProfileConfigIpv6AddrRangeStartAddress,
                  cie1000IpmcProfileConfigIpv6AddrRangeEndAddress,
                  cie1000IpmcProfileConfigIpv6AddrRangeAction }
    STATUS      current
    DESCRIPTION
        "A collection of objects."
    ::= { cie1000IpmcProfileMibGroups 6 }

cie1000IpmcProfileConfigIpv6AddrRangeTableRowEditorInfoGroup OBJECT-GROUP
    OBJECTS     {                   cie1000IpmcProfileConfigIpv6AddrRangeTableRowEditorRangeName,
                  cie1000IpmcProfileConfigIpv6AddrRangeTableRowEditorStartAddress,
                  cie1000IpmcProfileConfigIpv6AddrRangeTableRowEditorEndAddress,
                  cie1000IpmcProfileConfigIpv6AddrRangeTableRowEditorAction }
    STATUS      current
    DESCRIPTION
        "A collection of objects."
    ::= { cie1000IpmcProfileMibGroups 7 }

cie1000IpmcProfileConfigRuleTableInfoGroup OBJECT-GROUP
    OBJECTS     { cie1000IpmcProfileConfigRuleProfileName,
                  cie1000IpmcProfileConfigRuleRuleRange,
                  cie1000IpmcProfileConfigRuleNextRuleRange,
                  cie1000IpmcProfileConfigRuleRuleAction,
                  cie1000IpmcProfileConfigRuleRuleLog,
                  cie1000IpmcProfileConfigRuleAction }
    STATUS      current
    DESCRIPTION
        "A collection of objects."
    ::= { cie1000IpmcProfileMibGroups 8 }

cie1000IpmcProfileConfigRuleTableRowEditorInfoGroup OBJECT-GROUP
    OBJECTS     {                   cie1000IpmcProfileConfigRuleTableRowEditorProfileName,
                  cie1000IpmcProfileConfigRuleTableRowEditorRuleRange,
                  cie1000IpmcProfileConfigRuleTableRowEditorNextRuleRange,
                  cie1000IpmcProfileConfigRuleTableRowEditorRuleAction,
                  cie1000IpmcProfileConfigRuleTableRowEditorRuleLog,
                  cie1000IpmcProfileConfigRuleTableRowEditorAction }
    STATUS      current
    DESCRIPTION
        "A collection of objects."
    ::= { cie1000IpmcProfileMibGroups 9 }

cie1000IpmcProfileConfigPrecedenceTableInfoGroup OBJECT-GROUP
    OBJECTS     { cie1000IpmcProfileConfigPrecedenceProfileName,
                  cie1000IpmcProfileConfigPrecedenceRulePrecedence,
                  cie1000IpmcProfileConfigPrecedenceRuleRange,
                  cie1000IpmcProfileConfigPrecedenceNextRuleRange,
                  cie1000IpmcProfileConfigPrecedenceRuleAction,
                  cie1000IpmcProfileConfigPrecedenceRuleLog }
    STATUS      current
    DESCRIPTION
        "A collection of objects."
    ::= { cie1000IpmcProfileMibGroups 10 }

cie1000IpmcProfileMibCompliance MODULE-COMPLIANCE
    STATUS      current
    DESCRIPTION
        "The compliance statement for the implementation."

    MODULE      -- this module

    MANDATORY-GROUPS { cie1000IpmcProfileConfigGlobalsInfoGroup,
                       cie1000IpmcProfileConfigMgmtTableInfoGroup,
                       cie1000IpmcProfileConfigMgmtTableRowEditorInfoGroup,
                       cie1000IpmcProfileConfigIpv4AddrRangeTableInfoGroup,
                       cie1000IpmcProfileConfigIpv4AddrRangeTableRowEditorInfoGroup,
                       cie1000IpmcProfileConfigIpv6AddrRangeTableInfoGroup,
                       cie1000IpmcProfileConfigIpv6AddrRangeTableRowEditorInfoGroup,
                       cie1000IpmcProfileConfigRuleTableInfoGroup,
                       cie1000IpmcProfileConfigRuleTableRowEditorInfoGroup,
                       cie1000IpmcProfileConfigPrecedenceTableInfoGroup }

    ::= { cie1000IpmcProfileMibCompliances 1 }

END

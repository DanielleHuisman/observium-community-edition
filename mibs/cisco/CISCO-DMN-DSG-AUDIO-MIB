--*****************************************************************
-- CISCO_DMN_DSG_AUDIO.mib : Mib file for Audio Control and status.
--
-- August 2010, TEL MIB Team
--
-- Copyright (c) 1999-2012 Cisco Systems, Inc. All rights reserved.
--*****************************************************************

CISCO-DMN-DSG-AUDIO-MIB

DEFINITIONS ::= BEGIN

IMPORTS
    MODULE-IDENTITY,
    OBJECT-TYPE,Integer32
        FROM SNMPv2-SMI
    DisplayString
        FROM SNMPv2-TC
    OBJECT-GROUP, MODULE-COMPLIANCE
        FROM SNMPv2-CONF
    ciscoDSGUtilities
        FROM CISCO-DMN-DSG-ROOT-MIB;


ciscoDSGAudio  MODULE-IDENTITY
    LAST-UPDATED  "201307101220Z"
    ORGANIZATION    "Cisco Systems, Inc."
    CONTACT-INFO
       "Cisco Systems, Inc.
        Customer Service
        Postal: 170 W Tasman Drive
        San Jose, CA 95134
        USA
        Tel: +1 800 553 NETS

        E-mail: cs-ipsla@cisco.com"
    DESCRIPTION   "Cisco Audio Control MIB."

    REVISION       "201307101220Z"
    DESCRIPTION    "V01.00.08 2013-07-10
                   Updated audioLangList DESCRIPTION clause."

    REVISION       "201203070500Z"
    DESCRIPTION    "V01.00.07 2012-03-07
                    Updated for D9854 R4 Release."

    REVISION       "201008300500Z"
    DESCRIPTION    "V01.00.06 2010-08-30
                    Updated for adherence to SNMPv2 format."

    REVISION       "201005240630Z"
    DESCRIPTION    "V01.00.05 2010-05-24
                    The names of audioAC3Comp and audioDDPMode are
                    changed to audioDolbyDigitalComp
                    audioDolbyDigitalPlusMode respectively."

    REVISION       "201005211645Z"
    DESCRIPTION    "V01.00.04 2010-05-21
                    The enumerations of Audio PMT source item updated."

    REVISION       "201004120500Z"
    DESCRIPTION    "V01.00.03 2010-04-12
                    The objects audioDigitalComp
                    and audioDDPMode are updated."

    REVISION       "201003220500Z"
    DESCRIPTION    "V01.00.02 2010-03-22
                    The Syntax of Unsigned32 MIB objects whose
                    range is within the range
                    of Integer32, is updated to Integer32."

    REVISION       "201002121500Z"
    DESCRIPTION    "V01.00.01 2010-02-12
                    The Syntax of read-only objects is
                    updated to DisplayString."

    REVISION        "200912071200Z"
    DESCRIPTION     "V01.00.00 2009-12-07
                    Initial Version."

    ::= { ciscoDSGUtilities 15 }


--*****************************************************
--audioCtrlTable Branch
--*****************************************************


audioCtrlTable OBJECT-TYPE
     SYNTAX  SEQUENCE OF AudioCtrlEntry
     MAX-ACCESS  not-accessible
     STATUS  current
     DESCRIPTION
         "Audio decoder information"
     ::= { ciscoDSGAudio 1 }

audioCtrlEntry OBJECT-TYPE
     SYNTAX  AudioCtrlEntry
     MAX-ACCESS  not-accessible
     STATUS  current
     DESCRIPTION
         "Entry for audio channel is being viewed/edited."
     INDEX   { audioSelKey }
     ::= { audioCtrlTable 1 }

AudioCtrlEntry ::=  SEQUENCE
{
  audioSelKey                Integer32,
  audioMode                  INTEGER,
  audioDolbyDigitalComp      INTEGER,
  audioConsumerVolLeft       Integer32,
  audioConsumerVolRight      Integer32,
  audioProfAttenuationLeft   Integer32,
  audioProfAttenuationRight  Integer32,
  audioPmtSource             INTEGER,
  audioMuted                 INTEGER,
  audioDigitalComp           INTEGER,
  audioDolbyDigitalPlusMode  INTEGER,
  audioLangMenu              INTEGER,
  audioLangList              INTEGER,
  audioManualEntry           DisplayString
}

audioSelKey OBJECT-TYPE
     SYNTAX  Integer32(1..1)
     MAX-ACCESS  read-only
     STATUS  current
     DESCRIPTION
         "Selects which audio channel is being viewed/edited."
     ::= { audioCtrlEntry  1 }

audioMode OBJECT-TYPE
     SYNTAX  INTEGER {
             stereo(1),
             mixed(2),
             lMono(3),
             rMono(4)
         }
     MAX-ACCESS  read-write
     STATUS  current
     DESCRIPTION
         "Audio Mode: Stereo/Mixed/R-Mono/L-Mono."
     ::= { audioCtrlEntry  2 }

audioDolbyDigitalComp OBJECT-TYPE
     SYNTAX  INTEGER {
             rfMode(1),
             lineMode(2),
             custom0(4),
             custom1(3)
         }
     MAX-ACCESS  read-write
     STATUS  current
     DESCRIPTION
         "Dolby Digital (AC3) compression: RF Mode/Line/custom0/custom1  ."
     ::= { audioCtrlEntry  3 }

audioConsumerVolLeft OBJECT-TYPE
     SYNTAX  Integer32(0..60)
     MAX-ACCESS  read-write
     STATUS  current
     DESCRIPTION
         "Set Consumer Left Audio Volume: 0 to 60dB."
     ::= { audioCtrlEntry  4 }

audioConsumerVolRight OBJECT-TYPE
     SYNTAX  Integer32(0..60)
     MAX-ACCESS  read-write
     STATUS  current
     DESCRIPTION
         "Set Consumer Right Audio Volume: 0 to 60dB."
     ::= { audioCtrlEntry  5 }

audioProfAttenuationLeft OBJECT-TYPE
     SYNTAX  Integer32(0..1)
     MAX-ACCESS  read-only
     STATUS  current
     DESCRIPTION
         "Set Professional Attenuation Left: "
     ::= { audioCtrlEntry  6 }

audioProfAttenuationRight OBJECT-TYPE
     SYNTAX  Integer32(0..1)
     MAX-ACCESS  read-only
     STATUS  current
     DESCRIPTION
         "Set Professional Attenuation Right: "
     ::= { audioCtrlEntry  7 }

audioPmtSource OBJECT-TYPE
     SYNTAX  INTEGER{
             none(1),
             aud1(2),
             aud2(3),
             aud3(4),
             aud4(5),
             aud5(6),
             aud6(7),
             aud7(8),
             aud8(9),
             aud9(10),
             aud10(11),
             aud11(12),
             aud12(13),
             aud13(14),
             aud14(15),
             aud15(16),
             aud16(17),
             aud17(18),
             aud18(19),
             aud19(20),
             aud20(21),
             aud21(22),
             aud22(23),
             aud23(24),
             aud24(25),
             aud25(26),
             aud26(27),
             aud27(28),
             aud28(29),
             aud29(30),
             aud30(31),
             aud31(32),
             aud32(33),
             aud33(34),
             aud34(35),
             aud35(36),
             aud36(37),
             aud37(38),
             aud38(39),
             aud39(40),
             aud40(41),
             aud41(42),
             aud42(43),
             aud43(44),
             aud44(45),
             aud45(46),
             aud46(47),
             aud47(48),
             aud48(49),
             aud49(50),
             aud50(51),
             aud51(52),
             aud52(53),
             aud53(54),
             aud54(55),
             aud55(56),
             aud56(57),
             aud57(58),
             aud58(59),
             aud59(60),
             aud60(61),
             aud61(62),
             aud62(63),
             aud63(64),
             aud64(65)
         }
     MAX-ACCESS  read-write
     STATUS  current
     DESCRIPTION
         "PMT audio PID: AUD1/AUD2/AUD3/AUD4/.../AUD64/None."
     ::= { audioCtrlEntry  8 }

audioMuted OBJECT-TYPE
     SYNTAX  INTEGER{
             no(1),
             yes(2)
         }
     MAX-ACCESS  read-write
     STATUS  current
     DESCRIPTION
         "Mute or Unmute Audio."
     ::= { audioCtrlEntry  9 }

audioDigitalComp OBJECT-TYPE
     SYNTAX  INTEGER{
             pcm(1),
             compressed(2)
         }
     MAX-ACCESS  read-write
     STATUS  current
     DESCRIPTION
         "Audio Format: Dolby Digital/PCM/Compressed."
     ::= { audioCtrlEntry  10 }

audioDolbyDigitalPlusMode  OBJECT-TYPE
     SYNTAX  INTEGER {
             transcoding(1),
             passthrough(2)
        }
     MAX-ACCESS  read-write
     STATUS  current
     DESCRIPTION
         "Audio DDP(Dolby Digital Plus) Mode."
     ::= { audioCtrlEntry  11 }

audioLangMenu  OBJECT-TYPE
     SYNTAX  INTEGER {
             languageList(1),
             languageEntry(2),
             pmtOrder(3)
        }
     MAX-ACCESS  read-write
     STATUS  current
     DESCRIPTION
         "Select whether to chose the language based on the selection
        from the language list, from the PMT order, or from manual entry."
     ::= { audioCtrlEntry  12 }

audioLangList  OBJECT-TYPE
     SYNTAX  INTEGER {
             ara(1),
             btk(2),
             ben(3),
             bul(4),
             chi(5),
             cze(6),
             dan(7),
             dut(8),
             eng(9),
             fin(10),
             fre(11),
             ger(12),
             gre(13),
             heb(14),
             hin(15),
             hun(16),
             ice(17),
             ind(18),
             ita(19),
             jpn(20),
             kor(21),
             may(22),
             mul(23),
             nor(24),
             per(25),
             pol(26),
             por(27),
             rum(28),
             rus(29),
             san(30),
             scc(31),
             sin(32),
             slo(33),
             slv(34),
             som(35),
             spa(36),
             swe(37),
             tai(38),
             tam(39),
             tha(40),
             tur(41),
             ukr(42),
             vie(43)
         }
     MAX-ACCESS  read-write
     STATUS  current
     DESCRIPTION
         "Audio Language List.
          Language option slv(34) is only supported on D9865."
     ::= { audioCtrlEntry  13 }

audioManualEntry  OBJECT-TYPE
     SYNTAX  DisplayString (SIZE(0..3))
     MAX-ACCESS  read-write
     STATUS  current
     DESCRIPTION
         "Audio Manual Entry."
     ::= { audioCtrlEntry  14 }

-- *************************************
-- audioStatusTable Branch
-- *************************************

audioStatusTable OBJECT-TYPE
     SYNTAX  SEQUENCE OF AudioStatusEntry
     MAX-ACCESS  not-accessible
     STATUS  current
     DESCRIPTION
         "Audio Status Table."
     ::= { ciscoDSGAudio 2 }

audioStatusEntry OBJECT-TYPE
     SYNTAX  AudioStatusEntry
     MAX-ACCESS  not-accessible
     STATUS  current
     DESCRIPTION
         "Entry for audio channel is being viewed."
     INDEX   { audioStatusSelKey }
     ::= { audioStatusTable 1 }

AudioStatusEntry ::=  SEQUENCE
{
  audioStatusSelKey       Integer32,
  audioStatusFormat       INTEGER,
  audioStatusBitRate      DisplayString,
  audioStatusBufferLevel  DisplayString,
  audioStatusSFR          DisplayString,
  audioStatusMuted        INTEGER,
  audioStatusLanguage     DisplayString,
  audioStatusDDPMode      INTEGER,
  audioStatusDualMonoMode INTEGER
}

audioStatusSelKey OBJECT-TYPE
     SYNTAX  Integer32 (1..1)
     MAX-ACCESS  not-accessible
     STATUS  current
     DESCRIPTION
         "Selects which audio channel is being viewed."
     ::= { audioStatusEntry 1 }

audioStatusFormat OBJECT-TYPE
     SYNTAX  INTEGER {
             none(1),
             sine(2),
             pink(3),
             beep(4),
             mpeg1L1(5),
             mpeg1L2(6),
             mpeg2L1(7),
             mpeg2L2(8),
             dolbyDigital(9),
             loasAAC(10),
             adtsAAC(11),
             dolbyDigitalPlus(12),
             adtsHEAAC(13),
             loasHEAAC(14)
         }
     MAX-ACCESS  read-only
     STATUS  current
     DESCRIPTION
         "Audio Format."
     ::= { audioStatusEntry 2 }

audioStatusBitRate OBJECT-TYPE
     SYNTAX  DisplayString (SIZE(1..32))
     MAX-ACCESS  read-only
     STATUS  current
     DESCRIPTION
        "Audio Bitrate in Kilo bits(Kbits).The range is from 0 to
        4294967295 Kbits in steps of 1 Kbits."
     ::= { audioStatusEntry 3 }

audioStatusBufferLevel OBJECT-TYPE
     SYNTAX  DisplayString (SIZE(1..32))
     MAX-ACCESS  read-only
     STATUS  current
     DESCRIPTION
        "Level of audio input buffer in bytes.The range is from 0
        to 4294967295 bytes in steps of 1 byte."
     ::= { audioStatusEntry 4 }

audioStatusSFR OBJECT-TYPE
     SYNTAX  DisplayString (SIZE(1..32))
     MAX-ACCESS  read-only
     STATUS  current
     DESCRIPTION
        "Audio sampling frequency in Hz.The range is from 0
        to 4294967295 bytes in steps of 1 Hz."
     ::= { audioStatusEntry 5 }

audioStatusMuted OBJECT-TYPE
     SYNTAX  INTEGER {
             no(1),
             yes(2)
         }
     MAX-ACCESS  read-only
     STATUS  current
     DESCRIPTION
         "Current Mute State."
     ::= { audioStatusEntry 6 }

audioStatusLanguage OBJECT-TYPE
     SYNTAX  DisplayString (SIZE(1..16))
     MAX-ACCESS  read-only
     STATUS  current
     DESCRIPTION
         "Audio Language."
     ::= { audioStatusEntry 7 }

audioStatusDDPMode OBJECT-TYPE
     SYNTAX  INTEGER {
             off(1),
             ddp(2)
         }
     MAX-ACCESS  read-only
     STATUS  current
     DESCRIPTION
         "Audio DDP Mode."
     ::= { audioStatusEntry 8 }

audioStatusDualMonoMode OBJECT-TYPE
     SYNTAX  INTEGER {
             off(1),
             dualMono(2)
         }
     MAX-ACCESS  read-only
     STATUS  current
     DESCRIPTION
         "Dualmono Mode."
     ::= { audioStatusEntry 9 }

END

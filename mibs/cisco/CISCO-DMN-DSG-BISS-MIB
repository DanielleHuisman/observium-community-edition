--*****************************************************************
-- CISCO-DMN-DSG-BISS.mib: MIB file for board BISS information.
--
-- August 2010, Hemant Kumar R
--
-- Copyright (c) 2010 by Cisco Systems, Inc.
-- All rights reserved.
--*****************************************************************

-- ********************* start log section ************************
--  $Log::
-- ********************* end log section **************************

CISCO-DMN-DSG-BISS-MIB

DEFINITIONS ::= BEGIN

IMPORTS
    OBJECT-TYPE,
    MODULE-IDENTITY
        FROM SNMPv2-SMI
    DisplayString
        FROM SNMPv2-TC
    OBJECT-GROUP, MODULE-COMPLIANCE
        FROM SNMPv2-CONF
    ciscoDSGUtilities
        FROM CISCO-DMN-DSG-ROOT-MIB;


ciscoDSGBISS MODULE-IDENTITY
    LAST-UPDATED    "201008020700Z" -- August 2 2010 07:00:00 GMT
    ORGANIZATION    "Cisco Systems, Inc."
    CONTACT-INFO
       "Cisco Systems, Inc.
        Customer Service
        Postal: 170 W Tasman Drive
        San Jose, CA 95134
        USA
        Tel: +1 800 553 NETS

        E-mail: cs-ipsla@cisco.com"
    DESCRIPTION     "Cisco BISS MIB."

    REVISION        "201008020700Z"
    DESCRIPTION     "V01.00.00 2010-08-02
                    Initial Version."

    ::= { ciscoDSGUtilities 38 }

--*****************************
-- BISS Branch
--*****************************
bissMode OBJECT-TYPE
    SYNTAX  INTEGER {
                mode1(1),
                modeE(2)
            }
    MAX-ACCESS  read-write
    STATUS  current
    DESCRIPTION
        "BISS Mode Selection."
    ::= { ciscoDSGBISS 1 }

bissMode1SessionWord OBJECT-TYPE
    SYNTAX  DisplayString (SIZE(0..13))
    MAX-ACCESS  read-write
    STATUS  current
    DESCRIPTION
        "BISS Mode-1 Session Word."
    ::= { ciscoDSGBISS 2 }

bissModeESessionWord OBJECT-TYPE
    SYNTAX  DisplayString (SIZE(0..17))
    MAX-ACCESS  read-write
    STATUS  current
    DESCRIPTION
        "BISS Mode-E Encrypted Session Word."
    ::= { ciscoDSGBISS 3 }

bissModeEInjectedId OBJECT-TYPE
    SYNTAX  DisplayString (SIZE(0..15))
    MAX-ACCESS  read-write
    STATUS  current
    DESCRIPTION
        "BISS Mode-E Injected Id."
    ::= { ciscoDSGBISS 4 }

END

--*********************************************************************
-- CISCO-DMN-DSG-BKPRST.mib : Mib file for Backup and Restore Operation
--
-- August 2010, TEL MIB Team
--
-- Copyright (c) 1999-2012 by Cisco Systems, Inc. All rights reserved.
--*********************************************************************
CISCO-DMN-DSG-BKPRST-MIB

DEFINITIONS ::= BEGIN

IMPORTS
    MODULE-IDENTITY,
    OBJECT-TYPE, IpAddress, Integer32
        FROM SNMPv2-SMI
    DisplayString
        FROM SNMPv2-TC
    OBJECT-GROUP, MODULE-COMPLIANCE
        FROM SNMPv2-CONF
    ciscoDSGUtilities
        FROM CISCO-DMN-DSG-ROOT-MIB;


ciscoDSGBKPRST MODULE-IDENTITY
    LAST-UPDATED    "201203121700Z"
    ORGANIZATION    "Cisco Systems, Inc."
    CONTACT-INFO
       "Cisco Systems, Inc.
        Customer Service
        Postal: 170 W Tasman Drive
        San Jose, CA 95134
        USA
        Tel: +1 800 553 NETS

        E-mail: cs-ipsla@cisco.com"
    DESCRIPTION     "Cisco DSG Backup Restore MIB."

    REVISION        "201203261700Z"
    DESCRIPTION     "V01.00.05 2012-03-26
                    Updated enum list of backupRestoreDetailedStatus."

    REVISION        "201008300500Z"
    DESCRIPTION     "V01.00.04 2010-08-30
                    Updated for adherence to SNMPv2 format."

    REVISION        "201006170600Z"
    DESCRIPTION     "V01.00.03 2010-06-17
                     The enum options of backupRestoreDetailedStatus
                     is updated."

    REVISION        "201003220500Z"
    DESCRIPTION     "V01.00.02 2010-03-22
                     The Syntax of Unsigned32 MIB objects whose range
                     is within the range
                     of Integer32, is updated to Integer32."

    REVISION        "201002121500Z"
    DESCRIPTION     "V01.00.01 2010-02-12
                    The Syntax of read-only object is updated to
                    DisplayString."

    REVISION        "200911221500Z"
    DESCRIPTION     "V01.00.00 2009-11-22
                     Initial Version."

    ::= { ciscoDSGUtilities 3 }


backupRestoreInfo            OBJECT IDENTIFIER ::= { ciscoDSGBKPRST 1 }

-- *************************************
-- backupRestoreInfo Branch
-- *************************************

backupRestoreOperation OBJECT-TYPE
     SYNTAX  INTEGER {
             backup(1),
             restore(2),
             writeOnly(3)
          }
     MAX-ACCESS  read-write
     STATUS  current
     DESCRIPTION
         "Type of operation ( backup or restore ).
          Setting backup( 1 ) backs up the specified file to the
          FTP server.
          Setting restore( 2 ) restores the specified file from the
          FTP server."
     ::= { backupRestoreInfo 1 }

backupRestoreType OBJECT-TYPE
     SYNTAX  INTEGER {
             standard(1),
             extended(2),
             full(3)
          }
     MAX-ACCESS  read-write
     STATUS  current
     DESCRIPTION
         "Backup data sets to be included in the backup/restore file.
          Following backup options are available.
          Standard:To save the user settings to the backup file.
          Extended:To save user settings and tuning information to the 
          backup file.
          Full:To save user settings,tuning information and factory 
          defaults to the backup file."
     ::= { backupRestoreInfo 2 }

backupRestoreFileName OBJECT-TYPE
     SYNTAX  DisplayString (SIZE(0..119))
     MAX-ACCESS  read-write
     STATUS  current
     DESCRIPTION
         "Name of file to backup or restore."
     ::= { backupRestoreInfo 3 }

backupRestoreFtpServerIp OBJECT-TYPE
     SYNTAX  IpAddress
     MAX-ACCESS  read-write
     STATUS  current
     DESCRIPTION
        "FTP Server IP Address of the FTP server used to store 
        the backup/restore file.
          Format: ###.###.###.###, Range of ### is 0 to 255."
     ::= { backupRestoreInfo 4 }

backupRestoreFtpUsername OBJECT-TYPE
     SYNTAX  DisplayString (SIZE(0..32))
     MAX-ACCESS  read-write
     STATUS  current
     DESCRIPTION
         "FTP username to access the FTP Server."
     ::= { backupRestoreInfo 5 }

backupRestoreFtpPassword OBJECT-TYPE
     SYNTAX  DisplayString (SIZE(0..32))
     MAX-ACCESS  read-write
     STATUS  current
     DESCRIPTION
         "FTP password to access the FTP Server."
     ::= { backupRestoreInfo 6 }

backupRestoreFtpPortno OBJECT-TYPE
     SYNTAX  Integer32(1..65535)
     MAX-ACCESS  read-write
     STATUS  current
     DESCRIPTION
        "FTP port number of the FTP Server used to store the 
        backup\restore file."
     ::= { backupRestoreInfo 7 }

backupRestoreLastBackupFile OBJECT-TYPE
     SYNTAX  DisplayString (SIZE(0..119))
     MAX-ACCESS  read-only
     STATUS  current
     DESCRIPTION
         "Name of last backedup file."
     ::= { backupRestoreInfo 8 }

backupRestoreLastBackupTime OBJECT-TYPE
     SYNTAX  DisplayString (SIZE(0..32))
     MAX-ACCESS  read-only
     STATUS  current
     DESCRIPTION
         "Time of last backup."
     ::= { backupRestoreInfo 9 }

backupRestoreLastRestoreFile OBJECT-TYPE
     SYNTAX  DisplayString (SIZE(0..119))
     MAX-ACCESS  read-only
     STATUS  current
     DESCRIPTION
         "Name of last restored file."
     ::= { backupRestoreInfo 10 }

backupRestoreLastRestoreTime OBJECT-TYPE
     SYNTAX  DisplayString (SIZE(0..32))
     MAX-ACCESS  read-only
     STATUS  current
     DESCRIPTION
         "Time of last restore operation."
     ::= { backupRestoreInfo 11 }

backupRestoreOperationStatus OBJECT-TYPE
     SYNTAX  INTEGER {
             inprogress(1),
             pass(2),
             fail(3)
          }
     MAX-ACCESS  read-only
     STATUS  current
     DESCRIPTION
        "Backup/Restore Operation status ( inprogress,pass or failed )."
     ::= { backupRestoreInfo 12 }

backupRestoreDetailedStatus OBJECT-TYPE
     SYNTAX  INTEGER {
             idle(1),
             backupProcessing(2),
             backupConnecting(3),
             backupSendingFile(4),
             backupDone(5),
             backupFailed(6),
             restoreConnecting(7),
             restoreWaitingFile(8),
             restoreReceivingFile(9),
             restoreProcessing(10),
             restoreDone(11),
             restoreFailed(12),
             ftpFileTransferError(13),
             restoreFileCorrupted(14),
             restoreFileDesignationCodeMismatch(15),
             restoreFilePlatformTypeMismatch(16),
             restoreFileMissingFileInformation(17),
             restoreFileMissingPlatformType(18),
             restoreFileMissingDesignation(19),
             restoreFileMissingContents(20),
             restoreFileMissingRoot(21)
          }
     MAX-ACCESS  read-only
     STATUS  current
     DESCRIPTION
         "Detailed status of Backup/Restore operation."
       ::= { backupRestoreInfo 13 }

backupRestorePercentageComp OBJECT-TYPE
     SYNTAX  DisplayString (SIZE (1..32))
     MAX-ACCESS  read-only
     STATUS  current
     DESCRIPTION
        "Percentage of Backup/Restore operation Completed.
        The range is from 0 to 100 in steps of 1 percentage."
     ::= { backupRestoreInfo 14 }

END

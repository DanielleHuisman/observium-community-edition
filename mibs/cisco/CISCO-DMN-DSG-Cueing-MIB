--*****************************************************************
-- CISCO-DMN-DSG-Cueing.mib: MIB file for Board Cueing information.
--
-- August 2010, Hemant Kumar R
--
-- Copyright (c) 2010 by Cisco Systems, Inc.
-- All rights reserved.
--*****************************************************************

CISCO-DMN-DSG-Cueing-MIB

DEFINITIONS ::= BEGIN

IMPORTS
    OBJECT-TYPE,
    MODULE-IDENTITY, Integer32
        FROM SNMPv2-SMI
    OBJECT-GROUP, MODULE-COMPLIANCE
        FROM SNMPv2-CONF
    ciscoDSGUtilities
        FROM CISCO-DMN-DSG-ROOT-MIB;


ciscoDSGCueing MODULE-IDENTITY
    LAST-UPDATED    "201008300800Z" -- August 30 2010 08:00:00 GMT
    ORGANIZATION    "Cisco Systems, Inc."
    CONTACT-INFO
       "Cisco Systems, Inc.
        Customer Service
        Postal: 170 W Tasman Drive
        San Jose, CA 95134
        USA
        Tel: +1 800 553 NETS

        E-mail: cs-ipsla@cisco.com"
    DESCRIPTION     "Cisco Cueing MIB."

    REVISION        "201008300800Z"
    DESCRIPTION     "V01.00.00 2010-08-30
                    Initial Version."

    ::= { ciscoDSGUtilities 33 }

  cueingTable          OBJECT IDENTIFIER ::= { ciscoDSGCueing 11 }

--*****************************
-- Cueing Branch
--*****************************
cueingMode  OBJECT-TYPE
    SYNTAX  INTEGER{
            trigger(1),
            tone(2)
          }
    MAX-ACCESS read-write
    STATUS  current
    DESCRIPTION
        "Selection of Cueing Mode."
    ::= { ciscoDSGCueing 1 }

cueingTrigPol  OBJECT-TYPE
    SYNTAX  INTEGER{
                low(1),
                high(2)
            }
    MAX-ACCESS read-write
    STATUS  current
    DESCRIPTION
        "Selection of Cueing Trigger Polarity."
    ::= { ciscoDSGCueing 2 }

cueingRepeatCnt  OBJECT-TYPE
    SYNTAX  Integer32 (1..3)
    MAX-ACCESS read-write
    STATUS  current
    DESCRIPTION
        "Cueing Tone repeat count."
    ::= { ciscoDSGCueing 3 }

cueingTone  OBJECT-TYPE
    SYNTAX  Integer32 (0..80)
    MAX-ACCESS read-write
    STATUS  current
    DESCRIPTION
        "Cueing Tone duration in milliseconds."
    ::= { ciscoDSGCueing 4 }

cueingSilence  OBJECT-TYPE
    SYNTAX  Integer32 (0..80)
    MAX-ACCESS read-write
    STATUS  current
    DESCRIPTION
        "Silence duration in milliseconds."
    ::= { ciscoDSGCueing 5 }

cueingRelayMode  OBJECT-TYPE
    SYNTAX  INTEGER{
                alarm(1),
                trigger(2)
            }
    MAX-ACCESS read-write
    STATUS  current
    DESCRIPTION
        "Selection of Relay Mode."
    ::= { ciscoDSGCueing 6 }

cueingRelayTrigBit  OBJECT-TYPE
    SYNTAX  Integer32 (1..8)
    MAX-ACCESS read-write
    STATUS  current
    DESCRIPTION
        "Selection of Relay trigger bit."
    ::= { ciscoDSGCueing 7 }

cueingTestToneSequence  OBJECT-TYPE
    SYNTAX  Integer32 (0..999)
    MAX-ACCESS read-write
    STATUS  current
    DESCRIPTION
        "Cueing test tone sequence."
    ::= { ciscoDSGCueing 8 }

cueingTestToneStartStop  OBJECT-TYPE
    SYNTAX  INTEGER{
                start(1),
                stop(2)
            }
    MAX-ACCESS read-write
    STATUS  current
    DESCRIPTION
        "Cueing test tone start/stop."
    ::= { ciscoDSGCueing 9 }

cueingTestToneGo  OBJECT-TYPE
    SYNTAX  INTEGER{
                no(1),
                yes(2)
            }
    MAX-ACCESS read-write
    STATUS  current
    DESCRIPTION
        "Cueing test tone go."
    ::= { ciscoDSGCueing 10 }

--*****************************
-- Cueing Table Branch
--*****************************

--**************************************
-- Cueing Tone Sequence Table Branch
--**************************************
cueingToneSeqTable  OBJECT-TYPE
    SYNTAX  SEQUENCE OF CueingToneSeqEntry
    MAX-ACCESS not-accessible
    STATUS  current
    DESCRIPTION
        "Cueing Tone sequence Table."
    ::= { cueingTable 1}

cueingToneSeqEntry OBJECT-TYPE
    SYNTAX  CueingToneSeqEntry
    MAX-ACCESS  not-accessible
    STATUS  current
    DESCRIPTION
        "Entry for Cueing tone table."
    INDEX   { cueingToneSeqNum }
    ::= { cueingToneSeqTable  1 }

CueingToneSeqEntry ::=  SEQUENCE
{
    cueingToneSeqNum             Integer32,
    cueingToneSeqState           INTEGER,
    cueingToneSeqTones           Integer32,
    cueingToneSeqMode            INTEGER,
    cueingToneSeqDelay           Integer32
}

cueingToneSeqNum  OBJECT-TYPE
    SYNTAX  Integer32 (1..16)
    MAX-ACCESS not-accessible
    STATUS  current
    DESCRIPTION
        "Cueing Tone sequence number selection."
    ::= { cueingToneSeqEntry 1 }

cueingToneSeqState  OBJECT-TYPE
    SYNTAX  INTEGER {
                    disable(1),
                    enable(2)
                }
    MAX-ACCESS read-write
    STATUS  current
    DESCRIPTION
        "Contact Tone Sequence state selection."
    ::= { cueingToneSeqEntry 2 }

cueingToneSeqTones  OBJECT-TYPE
    SYNTAX  Integer32 (0..999)
    MAX-ACCESS read-write
    STATUS  current
    DESCRIPTION
        "Cueing Tone sequence tones."
    ::= { cueingToneSeqEntry 3 }

cueingToneSeqMode  OBJECT-TYPE
    SYNTAX  INTEGER {
                    start(1),
                    stop(2),
                    both(3)
                }
    MAX-ACCESS read-write
    STATUS  current
    DESCRIPTION
        "Contact Tone Sequence mode selection."
    ::= { cueingToneSeqEntry 4 }

cueingToneSeqDelay  OBJECT-TYPE
    SYNTAX  Integer32 (1..255)
    MAX-ACCESS read-write
    STATUS  current
    DESCRIPTION
        "Cueing Tone sequence delay in seconds."
    ::= { cueingToneSeqEntry 5 }

END

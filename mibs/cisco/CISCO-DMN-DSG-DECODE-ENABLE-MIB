--********************************************************************
-- CISCO-DMN-DSG-DECODE-ENABLE.mib : Mib file for Decoder Service Enable. 
--
-- August 2010, Tel MIB Team
--
--
-- Copyright (c) 1999-2009 by Cisco Systems, Inc.
-- All rights reserved.
--********************************************************************

CISCO-DMN-DSG-DECODE-ENABLE-MIB

DEFINITIONS ::= BEGIN

IMPORTS 
    MODULE-IDENTITY,
    OBJECT-TYPE
        FROM SNMPv2-SMI
    OBJECT-GROUP, MODULE-COMPLIANCE
        FROM SNMPv2-CONF
    ciscoDSGUtilities 
        FROM CISCO-DMN-DSG-ROOT-MIB;


ciscoDSGDecodeEnable  MODULE-IDENTITY
    LAST-UPDATED  "201008300600Z" -- August 30 2010 06:00:00 GMT
    ORGANIZATION    "Cisco Systems, Inc."
    CONTACT-INFO   
       "Cisco Systems, Inc.
        Customer Service 
        Postal: 170 W Tasman Drive
        San Jose, CA 95134
        USA  
        Tel: +1 800 553 NETS
        
        E-mail: cs-ipsla@cisco.com"
    DESCRIPTION   "Cisco Decoder Service Enable MIB."

    REVISION      "201008300600Z"
    DESCRIPTION   "V01.00.01 2010-08-30
                   Update for adherence to SNMPv2 format." 

                   REVISION      "200912071200Z"
    DESCRIPTION   "V01.00.00 2009-12-07
                   Initial Version." 

    ::= { ciscoDSGUtilities 13 }

-- *************************************
-- Decode Enable Table Branch
-- *************************************

decodeEnableTable OBJECT-TYPE
     SYNTAX  SEQUENCE OF DecodeEnableEntry
     MAX-ACCESS  not-accessible
     STATUS  current
     DESCRIPTION
         "Decode Service Enable Table."
     ::= { ciscoDSGDecodeEnable 1 }

decodeEnableEntry OBJECT-TYPE
     SYNTAX  DecodeEnableEntry
     MAX-ACCESS  not-accessible
     STATUS  current
     DESCRIPTION
         "Entry for Decoder Service Enable Table."
     INDEX   { decodeType }
     ::= { decodeEnableTable 1 }

DecodeEnableEntry ::=  SEQUENCE
{
  decodeType    INTEGER,
  decodeEnable  INTEGER
}

decodeType OBJECT-TYPE
     SYNTAX  INTEGER {
             video(1),
             audio1(2),
             audio2(3),
             audio3(4),
             audio4(5),
             vbi(6),
             data(7),
             mpe1(8),
             mpe2(9),
             mpe3(10),
             mpe4(11),
             mpe5(12),
             stt(13),
             dpi(14)
         }
     MAX-ACCESS  not-accessible
     STATUS  current
     DESCRIPTION
        "Decodeable Service type.
        This field used as a key for setting particular service
        to be enabled/disbled."
     ::= { decodeEnableEntry 1 }

decodeEnable OBJECT-TYPE
     SYNTAX  INTEGER {
             no(1),
             yes(2)
         }
     MAX-ACCESS  read-write
     STATUS  current
     DESCRIPTION
         "Enable or disable the decoder service."
     ::= { decodeEnableEntry 2 }

END

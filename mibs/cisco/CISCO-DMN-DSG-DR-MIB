--  **************************************************************************
--  CISCO_DMN_DSG_DR.mib: Feature MIB file for Disaster Recovery
--  
--  November 2013, Aakash Nigam
--
--  Copyright (c) Cisco Systems, Inc. 2012-2013. All rights reserved.
--  **************************************************************************

CISCO-DMN-DSG-DR-MIB

DEFINITIONS ::= BEGIN

IMPORTS
    OBJECT-TYPE,
    MODULE-IDENTITY, Integer32
        FROM SNMPv2-SMI
    DisplayString, RowStatus
        FROM SNMPv2-TC
    OBJECT-GROUP, MODULE-COMPLIANCE
        FROM SNMPv2-CONF        
    ciscoDSGUtilities
        FROM CISCO-DMN-DSG-ROOT-MIB;

ciscoDSGDR MODULE-IDENTITY
    LAST-UPDATED    "201408300800Z"
    ORGANIZATION    "Cisco Systems, Inc."
    CONTACT-INFO
        "Cisco Systems, Inc.
        Customer Service
        Postal: 170 W Tasman Drive
        San Jose, CA 95134
        USA
        Tel: +1 800 553 NETS

        E-mail: cs-ipsla@cisco.com"
    DESCRIPTION     "Cisco generic DR MIB."

    REVISION        "201408300800Z"
    DESCRIPTION     "V01.00.00 2014-04-14"

    ::= { ciscoDSGUtilities 43 }

drGlobalCfg        OBJECT IDENTIFIER ::= { ciscoDSGDR 1 }

--**************************************
-- DR Global Configuration Info 
--**************************************

enable OBJECT-TYPE
     SYNTAX  INTEGER {
             disable(1),
             enable(2)
             }
     MAX-ACCESS  read-write
     STATUS  current
     DESCRIPTION
         "Disable/Enable Disaster Recovery Feature"
     ::= { drGlobalCfg 1 }

sigLockTime OBJECT-TYPE
	SYNTAX  INTEGER (5..255)
        MAX-ACCESS  read-write
        STATUS  current
        DESCRIPTION
        "Signal Lock timer (In Seconds)"
     ::= { drGlobalCfg 2 }

sigLossTime OBJECT-TYPE
	SYNTAX  INTEGER (5..2160000)
        MAX-ACCESS  read-write
        STATUS  current
        DESCRIPTION
        "Signal Loss timer (In Seconds)"
     ::= { drGlobalCfg 3 }

verifyTimer OBJECT-TYPE
	SYNTAX  INTEGER (10..255)
        MAX-ACCESS  read-write
        STATUS  current
        DESCRIPTION
        "Verify timer (In Seconds)"
     ::= { drGlobalCfg 4 }   
     
profile OBJECT-TYPE
     SYNTAX  INTEGER {
             local(1),
             uplink(2)
             }
     MAX-ACCESS  read-write
     STATUS  current
     DESCRIPTION
         "Local/Uplink Disaster Recovery Profile"
     ::= { drGlobalCfg 5 }
    
--**************************************
-- DR BackupTransport Table
--**************************************       

backupTransportTable  OBJECT-TYPE
    SYNTAX  SEQUENCE OF BackupTransportEntry
    MAX-ACCESS not-accessible
    STATUS  current
    DESCRIPTION
        "DR BackupTransport Configuration Table."
    ::= { ciscoDSGDR 2}

backupTransportEntry OBJECT-TYPE
    SYNTAX  BackupTransportEntry
    MAX-ACCESS  not-accessible
    STATUS  current
    DESCRIPTION
        "Entry for Disaster Recovery BackupTransport Configuration."
    INDEX   { backupTransportIndex }
    ::= { backupTransportTable 1 } 
    
BackupTransportEntry ::=  SEQUENCE
{
    backupTransportIndex            Integer32,
    backupTransportSetIdx           Integer32,
    backupTransportDvbsFec          INTEGER,
    backupTransportEwFlag           INTEGER,
    backupTransportFrequency        Integer32,
    backupTransportRFInput          INTEGER,
    backupTransportModSys           INTEGER,
    backupTransportNetId            Integer32,
    backupTransportOrbitalPos       Integer32,
    backupTransportOrbpolarization  Integer32,
    backupTransportSymbRate         Integer32,
    backupTransportRollOffFactor    INTEGER,
    backupTransportRowstatus        INTEGER
}
      
backupTransportIndex OBJECT-TYPE
     SYNTAX  Integer32 (1..3)
     MAX-ACCESS  read-only
     STATUS  current
     DESCRIPTION
         "DR CSI record index"
     ::= { backupTransportEntry  1 }

backupTransportSetIdx OBJECT-TYPE
     SYNTAX  Integer32 (1..32)
     MAX-ACCESS  read-write
     STATUS  current
     DESCRIPTION
         "DR CSI Idx."
     ::= { backupTransportEntry 2 }

backupTransportDvbsFec OBJECT-TYPE
     SYNTAX  INTEGER {
             oneHalf(1),
             twoThirds(3),
             threeQuarters(4),
             fiveSixths(6),
             sevenEigths(7),
             auto(10)
          }
     MAX-ACCESS  read-write
     STATUS  current
     DESCRIPTION
         "DR DVBS Forward Error Correction: Forward Error Correction Rate.
         For DVB-S2 modulation only auto is applicable.
        For DVB-S modulation all options are applicable."
     ::= { backupTransportEntry 3 }

backupTransportEwFlag OBJECT-TYPE
     SYNTAX  INTEGER {
             east(1),
             west(2),
             notApplicable(3)
          }
     MAX-ACCESS  read-write
     STATUS  current
     DESCRIPTION
         "DR E/W Flag"
     ::= { backupTransportEntry 4 }

backupTransportFrequency OBJECT-TYPE
     SYNTAX  Integer32 (0..15000000)
     MAX-ACCESS  read-write
     STATUS  current
     DESCRIPTION
         "DR Frequency: The Satellite Downlink frequency in the range of
        0 to 15000000 KHz in steps of 1 KHz.."
     ::= { backupTransportEntry 5 }

backupTransportRFInput OBJECT-TYPE
     SYNTAX  INTEGER {
              rf1(1),
              rf2(2),
              rf3(3),
              rf4(4)          
          }
     MAX-ACCESS  read-write
     STATUS  current
     DESCRIPTION
         "DR Input: Select Input for tuning"
     ::= { backupTransportEntry 6 }

backupTransportModSys OBJECT-TYPE
     SYNTAX  INTEGER {
             qpsk_dvb-s(1),
             qpsk_dvb-S2(2)
          }
     MAX-ACCESS  read-write
     STATUS  current
     DESCRIPTION
         "DR Modulation System."
     ::= { backupTransportEntry 7 }

backupTransportNetId OBJECT-TYPE
     SYNTAX  Integer32 (0..65535)            
     MAX-ACCESS  read-write
     STATUS  current
     DESCRIPTION
         "Network Id."
     ::= { backupTransportEntry 8 }

backupTransportOrbitalPos  OBJECT-TYPE
     SYNTAX  Integer32(0..3600)
     MAX-ACCESS  read-write
     STATUS  current
     DESCRIPTION
         "DR Orbital Position"
     ::= { backupTransportEntry 9 }

backupTransportOrbpolarization OBJECT-TYPE
     SYNTAX  Integer32(0..3600)
     MAX-ACCESS  read-write
     STATUS  current
     DESCRIPTION
         "Orbital location Azimuth.The range is from 0 to 3600 in steps of 1. The scaling factor is 1 10th of a degree"
     ::= { backupTransportEntry 10 }

backupTransportSymbRate OBJECT-TYPE
     SYNTAX  Integer32 (10000..450000)
     MAX-ACCESS  read-write
     STATUS  current
     DESCRIPTION
         "Data rate on the transport stream in millions of symbols per second. Range is from 10000 to 450000 hectoSym/second in steps of 1 hectoSym/second. ( 1 hecto = 10^2 )."
     ::= { backupTransportEntry 11 }

backupTransportRollOffFactor OBJECT-TYPE
     SYNTAX  INTEGER {f35(1),f25(25),f20(3)
	         }
     MAX-ACCESS read-write
     STATUS current
     DESCRIPTION
          "DR Rollof Factor:Alpha filtering - for DVB-S: 0.20/0.35, for DVB-S2: 0.20/0.25/0.35. Roll off with scaling factor  of 1/100."
     ::= { backupTransportEntry 12 }

backupTransportRowstatus OBJECT-TYPE
     SYNTAX  INTEGER  {active(1),
     	     inactive(2),
     	     delete(3),
     	     add(4)}
     MAX-ACCESS read-write
     STATUS current
     DESCRIPTION
         "RowStatus."
     ::= { backupTransportEntry 13 }
         
--**************************************
-- DR BackupSet Table
--**************************************      
backupSetTable  OBJECT-TYPE
    SYNTAX  SEQUENCE OF BackupSetEntry
    MAX-ACCESS not-accessible
    STATUS  current
    DESCRIPTION
        "DR BackupSet Configuration Table."
    ::= { ciscoDSGDR 3}

backupSetEntry OBJECT-TYPE
    SYNTAX  BackupSetEntry
    MAX-ACCESS  not-accessible
    STATUS  current
    DESCRIPTION
        "Entry for Disaster Recovery BackupSet Configuration."
    INDEX   { backupSetPeid , backupSetRecid  }
    ::= { backupSetTable 1 }

BackupSetEntry ::= SEQUENCE
{
    backupSetPeid           Integer32,
    backupSetRecid          Integer32,
    backupSetCsiidx         Integer32,
    backupSetBkpch          Integer32,
    backupSetBkpchDispText	DisplayString,    
    backupSetRowStatus      INTEGER         
}

backupSetPeid  OBJECT-TYPE
    SYNTAX  Integer32 (1..32)
    MAX-ACCESS read-only
    STATUS  current
    DESCRIPTION
        "BackupSet PEId"
    ::= { backupSetEntry 1 }

backupSetRecid  OBJECT-TYPE
    SYNTAX  Integer32 (1..32)
    MAX-ACCESS read-only
    STATUS  current
    DESCRIPTION
        "Backup Set Record Index"
    ::= { backupSetEntry 2 }

backupSetCsiidx  OBJECT-TYPE
    SYNTAX  Integer32 (1..32)
    MAX-ACCESS read-only
    STATUS  current
    DESCRIPTION
        "CSI Index."
    ::= { backupSetEntry 3 }

backupSetBkpch  OBJECT-TYPE
    SYNTAX  Integer32 (0..65535)
    MAX-ACCESS read-write
    STATUS  current
    DESCRIPTION
        "Backup Channel."
    ::= { backupSetEntry 4 }
	
backupSetBkpchDispText OBJECT-TYPE
     SYNTAX  DisplayString (SIZE(0..8))
     MAX-ACCESS  read-only
     STATUS  current
     DESCRIPTION
         "Backup Channel Display Text"
     ::= { backupSetEntry 5 }	

backupSetRowStatus  OBJECT-TYPE
    SYNTAX  INTEGER {
             active(1),
             inactive(2)
          }
    MAX-ACCESS read-write
    STATUS  current
    DESCRIPTION
        "Backup Row Status."
    ::= { backupSetEntry 6 }

END

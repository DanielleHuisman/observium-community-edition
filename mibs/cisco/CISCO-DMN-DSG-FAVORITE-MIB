--*****************************************************************
-- CISCO-DMN-DSG-FAVORITE.mib: Favorites MIB file.
--
-- August 2010, TEL MIB Team.
--
-- Copyright (c) 2010 by Cisco Systems, Inc.
-- All rights reserved.
--*****************************************************************

CISCO-DMN-DSG-FAVORITE-MIB

DEFINITIONS ::= BEGIN

IMPORTS
    MODULE-IDENTITY,
    OBJECT-TYPE, Integer32
        FROM SNMPv2-SMI
    DisplayString, RowStatus
        FROM SNMPv2-TC
    OBJECT-GROUP, MODULE-COMPLIANCE
        FROM SNMPv2-CONF
    ciscoDSGUtilities
        FROM CISCO-DMN-DSG-ROOT-MIB;


ciscoDSGFavorite MODULE-IDENTITY
    LAST-UPDATED    "201008301100Z" -- August 30 2010 11:00:00 GMT
    ORGANIZATION    "Cisco Systems, Inc."
    CONTACT-INFO
       "Cisco Systems, Inc.
        Customer Service
        Postal: 170 W Tasman Drive
        San Jose, CA 95134
        USA
        Tel: +1 800 553 NETS
        E-mail: cs-ipsla@cisco.com"
    DESCRIPTION     "Cisco DSG Favorites MIB."

    REVISION        "201008301100Z"
    DESCRIPTION     "V01.00.02 2010-08-30
                    Updated for adherence to SNMPv2 format."

    REVISION        "201005110930Z"
    DESCRIPTION     "V01.00.01 2010-05-11
                    Default favorites option removed from
                    favoriteMapID."

    REVISION        "201004120600Z"
    DESCRIPTION     "V01.00.00 2010-04-12
                     Initial revision."

    ::= { ciscoDSGUtilities 29 }


favoriteCtrl              OBJECT IDENTIFIER ::= { ciscoDSGFavorite 1 }
favoriteTable             OBJECT IDENTIFIER ::= { ciscoDSGFavorite 2 }

-- *************************************
-- favoriteCtrl Branch
-- *************************************

favoriteCtrlID OBJECT-TYPE
     SYNTAX  INTEGER {
             favorite1(1),
             favorite2(2),
             favorite3(3),
             favorite4(4),
             favorite5(5),
             favorite6(6)
        }
     MAX-ACCESS  read-write
     STATUS  current
     DESCRIPTION
         "Favorite ID to be selected."
     ::= { favoriteCtrl 1 }

favoriteCtrlCmd OBJECT-TYPE
     SYNTAX  INTEGER {
             writeOnly(1),
             change(2)
        }
     MAX-ACCESS  read-write
     STATUS  current
     DESCRIPTION
         "Command used to change favorite."
     ::= { favoriteCtrl 2 }

favoriteChScanMode OBJECT-TYPE
     SYNTAX  INTEGER {
             all(1),
             authorizedOnly(2)
        }
     MAX-ACCESS  read-write
     STATUS  current
     DESCRIPTION
         "All Channels mode."
     ::= { favoriteCtrl 3 }

-- *************************************
-- favoriteTable Branch
-- *************************************

favoriteListTable OBJECT-TYPE
     SYNTAX  SEQUENCE OF FavoriteListEntry
     MAX-ACCESS  not-accessible
     STATUS  current
     DESCRIPTION
         "Favorites List table. "
     ::= { favoriteTable 1 }

favoriteListEntry OBJECT-TYPE
     SYNTAX  FavoriteListEntry
     MAX-ACCESS  not-accessible
     STATUS  current
     DESCRIPTION
         "Entry for Favorites List table."
     INDEX   { favoriteListID }
     ::= { favoriteListTable 1 }

FavoriteListEntry  ::=  SEQUENCE
{
    favoriteListID            INTEGER,
    favoriteListPosition      Integer32,
    favoriteListName          DisplayString,
    favoriteListType          INTEGER,
    favoriteListChLastViewed  Integer32,
    favoriteListRowStatus     RowStatus
}

favoriteListID OBJECT-TYPE
     SYNTAX  INTEGER {
             favorite1(1),
             favorite2(2),
             favorite3(3),
             favorite4(4),
             favorite5(5),
             favorite6(6)
        }
     MAX-ACCESS not-accessible
     STATUS  current
     DESCRIPTION
         "Index for Favorite List Table."
     ::= {favoriteListEntry 1 }

favoriteListPosition OBJECT-TYPE
     SYNTAX  Integer32(1..5)
     MAX-ACCESS read-create
     STATUS  current
     DESCRIPTION
         "Position of the favorite in the window."
     ::= {favoriteListEntry 2 }

favoriteListName OBJECT-TYPE
     SYNTAX  DisplayString(SIZE(0..31))
     MAX-ACCESS read-create
     STATUS  current
     DESCRIPTION
         "Name of the favorite."
     ::= {favoriteListEntry 3 }

favoriteListType OBJECT-TYPE
     SYNTAX  INTEGER {
            userRadio(1),
            userTv(2),
            providerRadio(3),
            providerTv(4)
        }
     MAX-ACCESS read-only
     STATUS  current
     DESCRIPTION
         "Type of the favorite."
     ::= {favoriteListEntry 4 }

favoriteListChLastViewed OBJECT-TYPE
     SYNTAX  Integer32(0..65535)
     MAX-ACCESS read-only
     STATUS  current
     DESCRIPTION
         "Last viewed channel in this favorite."
     ::= {favoriteListEntry 5 }

favoriteListRowStatus OBJECT-TYPE
     SYNTAX  RowStatus
     MAX-ACCESS read-create
     STATUS  current
     DESCRIPTION
         "Favorite List table row status.Used to add or delete rows in
          this table. Rows can be added only if the favorite to be
          added is non empty. Favorites to be added can be populated
          using favorite map table, favorite1( 1 ) and favorite2( 2 )
          are default favorites and cannot be edited."
     ::= {favoriteListEntry 6 }

-- *************************************
-- favoriteMapTable Branch
-- *************************************

favoriteMapTable OBJECT-TYPE
     SYNTAX  SEQUENCE OF FavoriteMapEntry
     MAX-ACCESS  not-accessible
     STATUS  current
     DESCRIPTION
         "Favorite Mapping table."
     ::= { favoriteTable 2 }

favoriteMapEntry OBJECT-TYPE
     SYNTAX  FavoriteMapEntry
     MAX-ACCESS  not-accessible
     STATUS  current
     DESCRIPTION
         "Entry for Favorite Map Table."
     INDEX   { favoriteMapID, favoriteMapChPosition }
     ::= { favoriteMapTable 1 }

FavoriteMapEntry ::=  SEQUENCE
{
    favoriteMapID            INTEGER,
    favoriteMapChPosition    Integer32,
    favoriteMapChNum         Integer32,
    favoriteMapRowStatus     RowStatus
}

favoriteMapID OBJECT-TYPE
     SYNTAX  INTEGER{
             favorite3(3),
             favorite4(4),
             favorite5(5),
             favorite6(6)
    }
     MAX-ACCESS not-accessible
     STATUS  current
     DESCRIPTION
         "Favorite key."
     ::= { favoriteMapEntry 1 }

favoriteMapChPosition OBJECT-TYPE
     SYNTAX  Integer32 (1..150)
     MAX-ACCESS not-accessible
     STATUS  current
     DESCRIPTION
         "Position of the channel in the favorite."
     ::= { favoriteMapEntry 2 }

favoriteMapChNum OBJECT-TYPE
     SYNTAX  Integer32(0..65535)
     MAX-ACCESS  read-create
     STATUS  current
     DESCRIPTION
         "Channel Number."
     ::= { favoriteMapEntry 3 }

favoriteMapRowStatus OBJECT-TYPE
     SYNTAX  RowStatus
     MAX-ACCESS read-create
     STATUS  current
     DESCRIPTION
         "Favorite Map table row status.Used to add or delete rows
         in this table."
     ::= { favoriteMapEntry 4 }

END

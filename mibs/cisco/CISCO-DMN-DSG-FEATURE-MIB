--  **************************************************************************
--  CISCO_DMN_DSG_Feature.mib: MIB file for installed options and features.
--
--  February 2012, Ming Yao
--
--  Copyright (c) Cisco Systems, Inc. 2012. All rights reserved.
--  **************************************************************************
    
CISCO-DMN-DSG-FEATURE-MIB DEFINITIONS ::= BEGIN

IMPORTS 
    MODULE-IDENTITY,
    OBJECT-TYPE,Integer32
        FROM SNMPv2-SMI
   DisplayString
        FROM SNMPv2-TC
    OBJECT-GROUP, MODULE-COMPLIANCE
        FROM SNMPv2-CONF
    ciscoDSGUtilities
        FROM CISCO-DMN-DSG-ROOT-MIB;


ciscoDSGFeature  MODULE-IDENTITY
    LAST-UPDATED "201202281800Z"
    ORGANIZATION "Cisco Systems, Inc."
    CONTACT-INFO   
                 "Cisco Systems, Inc.
                  Customer Service 
                  Postal: 170 W Tasman Drive
                  San Jose, CA 95134
                  USA  
                  Tel: +1 800 553 NETS
                  
                  E-mail: cs-ipsla@cisco.com"
    DESCRIPTION  "Cisco DSG Feature MIB."

    REVISION     "201202281800Z"
    DESCRIPTION  "V01.00.00 2012-02-28
                  Initial Version." 

    ::= { ciscoDSGUtilities 27 }

featureTable  OBJECT IDENTIFIER ::= { ciscoDSGFeature 2 }

-- *******************************
-- Licence Table
-- *******************************

featureLicenceTable OBJECT-TYPE
     SYNTAX  SEQUENCE OF FeatureLicenceEntry
     MAX-ACCESS  not-accessible
     STATUS  current
     DESCRIPTION
         "Licence status."
     ::= { featureTable 1 }

featureLicenceEntry OBJECT-TYPE
     SYNTAX  FeatureLicenceEntry
     MAX-ACCESS  not-accessible
     STATUS  current
     DESCRIPTION
         "Entry for licence status."
     INDEX   { featureLicenceIdx }
     ::= { featureLicenceTable 1 }

FeatureLicenceEntry ::=  SEQUENCE
{
  featureLicenceIdx        INTEGER,
  featureLicenceID         DisplayString,
  featureLicenceStatus     DisplayString
}

featureLicenceIdx OBJECT-TYPE
     SYNTAX  INTEGER(1..64)
     MAX-ACCESS  not-accessible
     STATUS  current
     DESCRIPTION
         "Index of Licence table."
     ::= { featureLicenceEntry 1 }

featureLicenceID OBJECT-TYPE
     SYNTAX  DisplayString (SIZE(1..32))
     MAX-ACCESS  read-only
     STATUS  current
     DESCRIPTION
        "The identification of features that require a licence."
     ::= { featureLicenceEntry 2 }

featureLicenceStatus OBJECT-TYPE
     SYNTAX  DisplayString (SIZE(1..32))
     MAX-ACCESS  read-only
     STATUS  current
     DESCRIPTION
        "The status of licence."
     ::= { featureLicenceEntry 3 }

-- *******************************
-- Installed Option Table
-- *******************************

installedOptionTable OBJECT-TYPE
     SYNTAX  SEQUENCE OF InstalledOptionEntry
     MAX-ACCESS  not-accessible
     STATUS  current
     DESCRIPTION
         "Status of installed option."
     ::= { featureTable 2 }

installedOptionEntry OBJECT-TYPE
     SYNTAX  InstalledOptionEntry
     MAX-ACCESS  not-accessible
     STATUS  current
     DESCRIPTION
         "Entry for installed options"
     INDEX   { installedOptionIdx }
     ::= { installedOptionTable 1 }

InstalledOptionEntry ::=  SEQUENCE
{
  installedOptionIdx        INTEGER,
  installedOptionID         DisplayString,
  installedOptionStatus     DisplayString
}

installedOptionIdx OBJECT-TYPE
     SYNTAX  INTEGER(1..64)
     MAX-ACCESS  not-accessible
     STATUS  current
     DESCRIPTION
         "Index of installed option table."
     ::= { installedOptionEntry 1 }

installedOptionID OBJECT-TYPE
     SYNTAX  DisplayString (SIZE(1..32))
     MAX-ACCESS  read-only
     STATUS  current
     DESCRIPTION
        "The identification of optional component."
     ::= { installedOptionEntry 2 }

installedOptionStatus OBJECT-TYPE
     SYNTAX  DisplayString (SIZE(1..32))
     MAX-ACCESS  read-only
     STATUS  current
     DESCRIPTION
        "The status of optional component."
     ::= { installedOptionEntry 3 }

END

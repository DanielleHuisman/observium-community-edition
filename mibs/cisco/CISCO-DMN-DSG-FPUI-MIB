--********************************************************************
-- CISCO-DMN-DSG-FPUI.mib : Mib file for Front Panel User Interface.
--
-- August 2010, TEL MIB Team
--
-- Copyright (c) 1999-2010 by Cisco Systems, Inc.
-- All rights reserved.
--*********************************************************************

CISCO-DMN-DSG-FPUI-MIB

DEFINITIONS ::= BEGIN

IMPORTS
    MODULE-IDENTITY,
    OBJECT-TYPE, Integer32
        FROM SNMPv2-SMI
    OBJECT-GROUP, MODULE-COMPLIANCE
        FROM SNMPv2-CONF
    ciscoDSGUtilities
        FROM CISCO-DMN-DSG-ROOT-MIB;


ciscoDSGFPUI  MODULE-IDENTITY
    LAST-UPDATED  "201008301100Z" -- August 30 2010 11:00:00 GMT
    ORGANIZATION    "Cisco Systems, Inc."
    CONTACT-INFO
       "Cisco Systems, Inc.
        Customer Service
        Postal: 170 W Tasman Drive
        San Jose, CA 95134
        USA
        Tel: +1 800 553 NETS

        E-mail: cs-ipsla@cisco.com"
    DESCRIPTION    "Cisco Front Panel User Interface MIB."

    REVISION       "201008301100Z"
    DESCRIPTION    "V01.00.02 2010-08-30
                   Updated for adherence to SNMPv2 format."

    REVISION       "201003220500Z"
    DESCRIPTION    "V01.00.01 2010-03-22
                    The Syntax of Unsigned32 MIB objects whose range
                    is within the range of Integer32, is updated to
                    Integer32."

    REVISION       "200912201200Z"
    DESCRIPTION    "V01.00.00 2009-12-20
                    Initial Version."

    ::= { ciscoDSGUtilities 24 }


--********************************
-- FPUI Branch
--********************************

fpuiKBLock  OBJECT-TYPE
     SYNTAX  INTEGER {
             disabled(1),
             enabled(2)
             }
     MAX-ACCESS  read-write
     STATUS  current
     DESCRIPTION
         "Controls the keyboard lock."
     ::= { ciscoDSGFPUI 1 }

fpuiKBLockTimeout  OBJECT-TYPE
     SYNTAX  Integer32(0..1800)
     MAX-ACCESS  read-write
     STATUS  current
     DESCRIPTION
         "Keyboard lock timeout."
     ::= { ciscoDSGFPUI 2 }

fpuiLCDContrast  OBJECT-TYPE
     SYNTAX  Integer32(0..30)
     MAX-ACCESS  read-write
     STATUS  current
     DESCRIPTION
         "LCD contrast setting."
     ::= { ciscoDSGFPUI 3 }

fpuiAWReminder  OBJECT-TYPE
     SYNTAX  INTEGER {
             disable(1),
             enable(2)
         }
     MAX-ACCESS  read-write
     STATUS  current
     DESCRIPTION
         "Enable/Disable flashing alarms and warnings on front panel."
     ::= { ciscoDSGFPUI 4 }

END

--********************************************************************
-- CISCO-DMN-DSG-LOCKLEVEL.mib : Mib file for Lock Level.
--
-- August 2010, TEL MIB Team
--
-- Copyright (c) 1999-2010 by Cisco Systems, Inc.
-- All rights reserved.
--********************************************************************

CISCO-DMN-DSG-LOCKLEVEL-MIB

DEFINITIONS ::= BEGIN

IMPORTS
    MODULE-IDENTITY,
    OBJECT-TYPE
        FROM SNMPv2-SMI
   DisplayString
        FROM SNMPv2-TC
    OBJECT-GROUP, MODULE-COMPLIANCE
        FROM SNMPv2-CONF
    ciscoDSGUtilities
        FROM CISCO-DMN-DSG-ROOT-MIB;

ciscoDSGLockLevel  MODULE-IDENTITY
    LAST-UPDATED  "201008301100Z" -- August 30 2010 11:00:00 GMT
    ORGANIZATION    "Cisco Systems, Inc."
    CONTACT-INFO
       "Cisco Systems, Inc.
        Customer Service
        Postal: 170 W Tasman Drive
        San Jose, CA 95134
        USA
        Tel: +1 800 553 NETS

        E-mail: cs-ipsla@cisco.com"
    DESCRIPTION   "Cisco Lock Level MIB."

    REVISION       "201008301100Z"
    DESCRIPTION    "V01.00.03 2010-08-30
                   Updated for adherence to SNMPv2 format."

    REVISION      "201006280600Z"
    DESCRIPTION   "V01.00.02 2010-06-28
                   Updated the description for lockLevel."

    REVISION      "201005240630Z"
    DESCRIPTION   "V01.00.01 2010-05-24
                   Updated the options for lockLevel."

    REVISION      "200912201200Z"
    DESCRIPTION   "V01.00.00 2009-12-20
                   Initial Version."

    ::= { ciscoDSGUtilities 22 }


--*********************************
-- Lock Level Branch
--*********************************

lockLevel OBJECT-TYPE
     SYNTAX  Integer32 (0..4)
     MAX-ACCESS  read-write
     STATUS  current
     DESCRIPTION
         "Lock Level.
          (0)   : All settings are unlocked.
          (1)   : All settings are unlocked except Factory reset,
                    IP settings and passwords.
          (2)   : All settings are unlocked except that presets,
                    tuning related items, and
                    dish setup are also locked.
          (3)   : All settings are locked except volume change.
          (4)   : All settings are locked (can be changed via 
                    NC uplink signal only).
         four is a read-only value."
     ::= { ciscoDSGLockLevel 1 }

lockLevelPWD OBJECT-TYPE
     SYNTAX  DisplayString(SIZE(0..4))
     MAX-ACCESS  read-write
     STATUS  current
     DESCRIPTION
         "Password to change Password and Lock Level."
     ::= { ciscoDSGLockLevel 2 }

lockLevelPWDCUR OBJECT-TYPE
     SYNTAX  DisplayString(SIZE(0..4))
     MAX-ACCESS  read-write
     STATUS  current
     DESCRIPTION
         "Confirm the Current Password."
     ::= { ciscoDSGLockLevel 3 }

lockLevelPWDNEW OBJECT-TYPE
     SYNTAX  DisplayString(SIZE(0..4))
     MAX-ACCESS  read-write
     STATUS  current
     DESCRIPTION
         "New Password."
     ::= { ciscoDSGLockLevel 4 }

lockLevelPWDCONF OBJECT-TYPE
     SYNTAX  DisplayString(SIZE(0..4))
     MAX-ACCESS  read-write
     STATUS  current
     DESCRIPTION
         "Confirm New Password."
     ::= { ciscoDSGLockLevel 5 }

END

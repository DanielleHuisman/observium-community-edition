--*****************************************************************
-- CISCO_DMN_DSG_MOIP.mib: MIB file for MPEG over IP control and status.
--
-- August 2010, Hemant Kumar R
--
-- Copyright (c) 2010 - 2012 by Cisco Systems, Inc. All rights reserved.
--*****************************************************************

CISCO-DMN-DSG-MOIP-MIB

DEFINITIONS ::= BEGIN

IMPORTS
    OBJECT-TYPE,
    MODULE-IDENTITY,Integer32,
    IpAddress
        FROM SNMPv2-SMI
    DisplayString
        FROM SNMPv2-TC
    OBJECT-GROUP, MODULE-COMPLIANCE
        FROM SNMPv2-CONF
    ciscoDSGUtilities
        FROM CISCO-DMN-DSG-ROOT-MIB;


ciscoDSGMOIP MODULE-IDENTITY
    LAST-UPDATED    "201203201100Z" -- March 20 2012 11:00:00 GMT
    ORGANIZATION    "Cisco Systems, Inc."
    CONTACT-INFO
       "Cisco Systems, Inc.
        Customer Service
        Postal: 170 W Tasman Drive
        San Jose, CA 95134
        USA
        Tel: +1 800 553 NETS

        E-mail: cs-ipsla@cisco.com"
    DESCRIPTION     "Cisco MOIP MIB."

    REVISION       "201203201100Z"
    DESCRIPTION    "V01.00.01 2012-03-20
                    Updated for D9854 R4 Release."

    REVISION        "201008240730Z"
    DESCRIPTION     "V01.00.00 2010-08-24
                    Initial Version."

    ::= { ciscoDSGUtilities 35 }

moipIPOTable                     OBJECT IDENTIFIER ::= { ciscoDSGMOIP 1 }

--*****************************
-- MOIP Branch
--*****************************

--**************************************
-- MOIP IPO Config Table
--**************************************
moipIPOConfigTable  OBJECT-TYPE
    SYNTAX  SEQUENCE OF MOIPIPOConfigEntry
    MAX-ACCESS not-accessible
    STATUS  current
    DESCRIPTION
        "MOIP IP Output Table."
    ::= { moipIPOTable 1 }

moipIPOConfigEntry OBJECT-TYPE
    SYNTAX  MOIPIPOConfigEntry
    MAX-ACCESS  not-accessible
    STATUS  current
    DESCRIPTION
        "Entry for DPM Aligned PMT table."
    INDEX   { moipIPOConfigID }
    ::= { moipIPOConfigTable 1 }

MOIPIPOConfigEntry ::=  SEQUENCE
{
    moipIPOConfigID                      Integer32,
    moipIPOConfigOutputEnabled           INTEGER,
    moipIPOConfigInstanceName            DisplayString,
    moipIPOConfigTPProtocol              INTEGER,
    moipIPOConfigIPVer                   DisplayString,
    moipIPOConfigDestIPAddr              IpAddress,
    moipIPOConfigSAPMulticastIPAddr      IpAddress,
    moipIPOConfigDestPort                Integer32,
    moipIPOConfigSrcPort                 Integer32,
    moipIPOConfigMinIPPerSec             Integer32,
    moipIPOConfigPCRAddition             INTEGER,
    moipIPOConfigPCRStartNewPkt          INTEGER,
    moipIPOConfigSendSAP                 INTEGER,
    moipIPOConfigUseSAPStr               INTEGER,
    moipIPOConfigMaxTransPktPerIP        Integer32,
    moipIPOConfigSAPStr                  DisplayString,
    moipIPOConfigInterfaceMode           INTEGER,
    moipIPOConfigBitRate                 Integer32,
    moipIPOConfigTOS                     Integer32,
    moipIPOConfigTTL                     Integer32,
    moipIPOConfigSAPDestPort             Integer32,
    moipIPOFECMode                       INTEGER,
    moipIPOFECColDepth                   Integer32,
    moipIPOFECRowWidth                   Integer32,
    moipIPOAnnexType                     INTEGER,
    moipIPOFEC1UDPPort                   Integer32,
    moipIPOFEC2UDPPort                   Integer32
}

moipIPOConfigID  OBJECT-TYPE
    SYNTAX  Integer32 (1..1)
    MAX-ACCESS read-only
    STATUS  current
    DESCRIPTION
        "MPEG Over IP Output Instance ID ."
     ::= { moipIPOConfigEntry 1 }

moipIPOConfigOutputEnabled  OBJECT-TYPE
    SYNTAX  INTEGER {
                    no(1),
                    yes(3)
                }
    MAX-ACCESS read-write
    STATUS  current
    DESCRIPTION
        "MPEG Over IP Output is enabled."
    ::= { moipIPOConfigEntry 2 }

moipIPOConfigInstanceName  OBJECT-TYPE
    SYNTAX  DisplayString(SIZE(0..32))
    MAX-ACCESS read-write
    STATUS  current
    DESCRIPTION
        "MPEG Over IP Output Name."
    ::= { moipIPOConfigEntry 3 }

moipIPOConfigTPProtocol  OBJECT-TYPE
    SYNTAX  INTEGER {
                    udp(1),
                    rtp(2)
                }
     MAX-ACCESS read-write
     STATUS  current
     DESCRIPTION
        "Transport Protocol to be used: UDP/ RPT."
    ::= { moipIPOConfigEntry 4 }

moipIPOConfigIPVer  OBJECT-TYPE
    SYNTAX    DisplayString (SIZE(0..255))
    MAX-ACCESS read-only
    STATUS  current
    DESCRIPTION
        "Internet Protocol version of the destination
        IP address:IPv4/IPv6."
    ::= { moipIPOConfigEntry 5 }

moipIPOConfigDestIPAddr  OBJECT-TYPE
    SYNTAX  IpAddress
    MAX-ACCESS read-write
    STATUS  current
    DESCRIPTION
        "MPEG Over IP Destination IP Address."
    ::= { moipIPOConfigEntry 6 }

moipIPOConfigSAPMulticastIPAddr  OBJECT-TYPE
    SYNTAX  IpAddress
    MAX-ACCESS read-write
    STATUS  current
    DESCRIPTION
        "MPEG Over IP Destination IP Address."
    ::= { moipIPOConfigEntry 7 }

moipIPOConfigDestPort  OBJECT-TYPE
    SYNTAX  Integer32 (1..65534)
    MAX-ACCESS read-write
    STATUS  current
    DESCRIPTION
        "Source UDP Port - 0 allows automatic Port Selection,
        enter a value to override.."
    ::= { moipIPOConfigEntry 8 }

moipIPOConfigSrcPort  OBJECT-TYPE
    SYNTAX  Integer32 (0..65535)
    MAX-ACCESS read-write
    STATUS  current
    DESCRIPTION
        "Source UDP Port - 0 allows automatic Port Selection,
        enter a value to override.."
    ::= { moipIPOConfigEntry 9 }

moipIPOConfigMinIPPerSec  OBJECT-TYPE
    SYNTAX  Integer32 (0..65535)
    MAX-ACCESS read-write
    STATUS  current
    DESCRIPTION
        "Minimum Number of IP Packets to be sent per second."
    ::= { moipIPOConfigEntry 10 }

moipIPOConfigPCRAddition  OBJECT-TYPE
    SYNTAX  INTEGER {
                    no(1),
                    yes(2)
                }
    MAX-ACCESS read-write
    STATUS  current
    DESCRIPTION
        "Program Clock Reference Addition. 
         This OID is read only on D9824, D9854-i and D9859 "
    ::= { moipIPOConfigEntry 11 }

moipIPOConfigPCRStartNewPkt  OBJECT-TYPE
    SYNTAX  INTEGER {
                    no(1),
                    yes(2)
                }
    MAX-ACCESS read-write
    STATUS  current
    DESCRIPTION
        "Enabling new Ethernet Packet when new 
         Program Clock Reference arrives."
    ::= { moipIPOConfigEntry 12 }

moipIPOConfigSendSAP  OBJECT-TYPE
    SYNTAX  INTEGER {
                    none(1),
                    rfc2327(2)
                }
    MAX-ACCESS read-write
    STATUS  current
    DESCRIPTION
        "Send SAP Messages."
    ::= { moipIPOConfigEntry 13 }

moipIPOConfigUseSAPStr  OBJECT-TYPE
    SYNTAX  INTEGER {
                    userString(1),
                    sdtChName(2)
                }
    MAX-ACCESS read-write
    STATUS  current
    DESCRIPTION
        "User Configured SAP String or PE1 SDT Channel name 
         as the Transport Name in the SAP."
    ::= { moipIPOConfigEntry 14 }

moipIPOConfigMaxTransPktPerIP  OBJECT-TYPE
    SYNTAX  Integer32 (1..7)
    MAX-ACCESS read-write
    STATUS  current
    DESCRIPTION
        "Maximum Number of Transport Packets per IP Packet."
    ::= { moipIPOConfigEntry 15 }

moipIPOConfigSAPStr  OBJECT-TYPE
    SYNTAX  DisplayString (SIZE(0..32))
    MAX-ACCESS read-write
    STATUS  current
    DESCRIPTION
        "User configured Session Announcement Protocol Transport
        Name to be used when DPMIPOConfigUseSAPStr is set to 'YES'."
    ::= { moipIPOConfigEntry 16 }

moipIPOConfigInterfaceMode  OBJECT-TYPE
    SYNTAX  INTEGER {
                    none(1),
                    data1(2),
                    data2(3),
                    both(4),
                    redundancy(5)                    
                }
    MAX-ACCESS read-write
    STATUS  current
    DESCRIPTION
        "MPEG Over IP Output port selection."
    ::= { moipIPOConfigEntry 17 }

moipIPOConfigBitRate  OBJECT-TYPE
    SYNTAX  Integer32 (0..206000000)
    MAX-ACCESS read-write
    STATUS  current
    DESCRIPTION
        "Maxmum ASI output rate in Mbps with scaling factor of 6."
    ::= { moipIPOConfigEntry 18 }


moipIPOConfigTOS  OBJECT-TYPE
    SYNTAX  Integer32 (0..255)
    MAX-ACCESS read-write
    STATUS  current
    DESCRIPTION
        "TOS field in IP header. This is an 8 bits field divided 
         into 5 sub-fields namely Precedence, D, T, R and Unused."
    ::= { moipIPOConfigEntry 19 }

moipIPOConfigTTL  OBJECT-TYPE
    SYNTAX  Integer32 (0..255)
    MAX-ACCESS read-write
    STATUS  current
    DESCRIPTION
        "Time to live. This is an 8 bits fiels that defines how 
         many hops an IP datagram can travel through."
    ::= { moipIPOConfigEntry 20 }

moipIPOConfigSAPDestPort  OBJECT-TYPE
    SYNTAX  Integer32 (1..65534)
    MAX-ACCESS read-write
    STATUS  current
    DESCRIPTION
        "SAP Destination Port Number."
    ::= { moipIPOConfigEntry 21 }

moipIPOFECMode  OBJECT-TYPE
    SYNTAX  INTEGER {
                    none(1),
                    oneD(2),
                    twoD(3)
                }
    MAX-ACCESS read-write
    STATUS  current
    DESCRIPTION
        "FEC Mode."
    ::= { moipIPOConfigEntry 22 }

moipIPOFECColDepth  OBJECT-TYPE
    SYNTAX  Integer32 (0..20)
    MAX-ACCESS read-write
    STATUS  current
    DESCRIPTION
        "FEC Column Depth (L Value)."
    ::= { moipIPOConfigEntry 23 }


moipIPOFECRowWidth  OBJECT-TYPE
    SYNTAX  Integer32 (0..20)
    MAX-ACCESS read-write
    STATUS  current
    DESCRIPTION
        "FEC Row Width (D Value)."
    ::= { moipIPOConfigEntry 24 }

moipIPOAnnexType  OBJECT-TYPE
    SYNTAX  INTEGER {
                    annexA(1),
                    annexB(2)
                }
    MAX-ACCESS read-write
    STATUS  current
    DESCRIPTION
        "FEC arrangement : Non block-aligned (Annex A in Pro-MPEG FEC, 
         Annex B in SMPTE 2022), Block-aligned (Annex B in Pro-MPEG FEC, 
         Annex C in SMPTE-2022)."
    ::= { moipIPOConfigEntry 25 }

moipIPOFEC1UDPPort  OBJECT-TYPE
    SYNTAX  Integer32 (2..65534)
    MAX-ACCESS read-write
    STATUS  current
    DESCRIPTION
        "UDP Port for FEC Columns Stream in step of 2. "
    ::= { moipIPOConfigEntry 26 }


moipIPOFEC2UDPPort  OBJECT-TYPE
    SYNTAX  Integer32 (2..65534)
    MAX-ACCESS read-write
    STATUS  current
    DESCRIPTION
        "UDP Port for FEC Rows Stream in step of 2."
    ::= { moipIPOConfigEntry 27 }


--**************************************
-- MOIP IPO Stream Status Table
--**************************************
moipIPOStreamStatusTable  OBJECT-TYPE
    SYNTAX  SEQUENCE OF MOIPIPOStreamStatusEntry
    MAX-ACCESS not-accessible
    STATUS  current
    DESCRIPTION
        "MOIP IP Output Table."
    ::= { moipIPOTable 2 }

moipIPOStreamStatusEntry OBJECT-TYPE
    SYNTAX  MOIPIPOStreamStatusEntry
    MAX-ACCESS  not-accessible
    STATUS  current
    DESCRIPTION
        "Entry for DPM Aligned PMT table."
    INDEX   { moipIPOStreamStatusID }
    ::= { moipIPOStreamStatusTable 1 }

MOIPIPOStreamStatusEntry ::=  SEQUENCE
{
    moipIPOStreamStatusID                   Integer32,
    moipIPOStreamStatusIntf1                INTEGER,
    moipIPOStreamStatusIntf2                INTEGER,
    moipIPOStreamStatusContentOvfl          INTEGER,
    moipIPOStreamStatusLinkOvfl             INTEGER
}

moipIPOStreamStatusID  OBJECT-TYPE
    SYNTAX  Integer32 (1..32)
    MAX-ACCESS read-only                                       
    STATUS  current
    DESCRIPTION
        "MPEG Over IP Output Instance ID ."
     ::= { moipIPOStreamStatusEntry 1 }

moipIPOStreamStatusIntf1  OBJECT-TYPE
    SYNTAX  INTEGER {
                    notInit(1),
                    stopped(2),
                    suspended(3),
                    muted(4),
                    active(5)
                }
    MAX-ACCESS read-only
    STATUS  current
    DESCRIPTION
        "Stream Status, Ethernet Port 1."
    ::= { moipIPOStreamStatusEntry 2 }

moipIPOStreamStatusIntf2  OBJECT-TYPE
    SYNTAX  INTEGER {
                    notInit(1),
                    stopped(2),
                    suspended(3),
                    muted(4),
                    active(5)
                }
    MAX-ACCESS read-only
    STATUS  current
    DESCRIPTION
        "Stream Status, Ethernet Port 2."
    ::= { moipIPOStreamStatusEntry 3 }

moipIPOStreamStatusContentOvfl  OBJECT-TYPE
    SYNTAX  INTEGER {
                    no(1),
                    yes(2)
                }
    MAX-ACCESS read-only
    STATUS  current
    DESCRIPTION
        "Content Overflow."
    ::= { moipIPOStreamStatusEntry 4 }

moipIPOStreamStatusLinkOvfl  OBJECT-TYPE
    SYNTAX  INTEGER {
                    no(1),
                    yes(2)
                }
    MAX-ACCESS read-only
    STATUS  current
    DESCRIPTION
        "Link Overflow."
    ::= { moipIPOStreamStatusEntry 5 }

--**************************************
-- MOIP IPO Info
--**************************************
moipIPOInfo                     OBJECT IDENTIFIER ::= { ciscoDSGMOIP 2 }

moipIPOStatsHWGlobalError  OBJECT-TYPE
    SYNTAX  INTEGER{
                    no(1),
                    yes(2)
                }
    MAX-ACCESS read-only
    STATUS  current
    DESCRIPTION
        "Critical MPEG over IP Engine Failure."
    ::= { moipIPOInfo 1 }

moipIPOStatsStreamError  OBJECT-TYPE
    SYNTAX  INTEGER{
                    no(1),
                    yes(2)
                }
    MAX-ACCESS read-only
    STATUS  current
    DESCRIPTION
        "MPEG over IP TS Overflow."
    ::= { moipIPOInfo 2 }

moipIPOStatsBandwidthConf  OBJECT-TYPE
    SYNTAX  DisplayString (SIZE(0..10))
    MAX-ACCESS read-only
    STATUS  current
    DESCRIPTION
        "Combined User Rate (Mbps)."
    ::= { moipIPOInfo 3 }

moipIPOStatsBandwidthActIntf1  OBJECT-TYPE
    SYNTAX  DisplayString (SIZE(0..10))
    MAX-ACCESS read-only
    STATUS  current
    DESCRIPTION
        "Actual Rate (Mbps), Ethernet Port 1."
    ::= { moipIPOInfo 4 }

moipIPOStatsBandwidthActIntf2  OBJECT-TYPE
    SYNTAX  DisplayString (SIZE(0..10))
    MAX-ACCESS read-only
    STATUS  current
    DESCRIPTION
        "Actual Rate (Mbps), Ethernet Port 2."
    ::= { moipIPOInfo 5 }

END

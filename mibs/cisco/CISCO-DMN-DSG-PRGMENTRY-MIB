--*****************************************************************
-- CISCO-DMN-DSG-PROGRAMENTRY.mib : Mib file for Program Entry.
--
-- October 2010, TEL MIB Team
--
-- Copyright (c) 1999-2010 by Cisco Systems, Inc.
-- All rights reserved.
--*****************************************************************

CISCO-DMN-DSG-PRGMENTRY-MIB

DEFINITIONS ::= BEGIN

IMPORTS
    MODULE-IDENTITY,
    OBJECT-TYPE, Unsigned32, Integer32
        FROM SNMPv2-SMI
    DisplayString
        FROM SNMPv2-TC
    OBJECT-GROUP, MODULE-COMPLIANCE
        FROM SNMPv2-CONF
    ciscoDSGUtilities
        FROM CISCO-DMN-DSG-ROOT-MIB;

ciscoDSGProgramEntry  MODULE-IDENTITY
    LAST-UPDATED    "201010130800Z" -- October 13 2010 08:00:00 GMT
    ORGANIZATION    "Cisco Systems, Inc."
    CONTACT-INFO
       "Cisco Systems, Inc.
        Customer Service
        Postal: 170 W Tasman Drive
        San Jose, CA 95134
        USA
        Tel: +1 800 553 NETS

        E-mail: cs-ipsla@cisco.com"
    DESCRIPTION     "Cisco DSG Program Entry MIB."

    REVISION       "201010130800Z"
    DESCRIPTION    "V01.00.07 2010-10-13
                   Updated for migrating D985X/D9865 MIB to generic 
                   logic."

                   REVISION       "201008301100Z"
    DESCRIPTION    "V01.00.06 2010-08-30
                   Updated for adherence to SNMPv2 format."

    REVISION       "201006170600Z"
    DESCRIPTION    "V01.00.05 2010-06-17
                    Updated the values of programEntryStatusCAID
                    and programEntryPIDIndex."

    REVISION       "201005251630Z"
    DESCRIPTION    "V01.00.04 2010-05-25
                    Enum option ac3 modified to Dolby Digital."

    REVISION       "201005070630Z"
    DESCRIPTION    "V01.00.03 2010-05-07
                    Commented programEntryControlCAResource as it is
                    for future."

    REVISION       "201003220500Z"
    DESCRIPTION    "V01.00.02 2010-03-22
                    The Syntax of Unsigned32 MIB objects whose range
                    is within the range of Integer32, is updated to
                    Integer32."

    REVISION       "201002121500Z"
    DESCRIPTION    "V01.00.01 2010-02-12
                    The Syntax of read-only objects is updated to
                    DisplayString."

    REVISION       "200911221500Z"
    DESCRIPTION    "V01.00.00 2009-11-22
                    Initial Version."

    ::= { ciscoDSGUtilities 4 }

programEntryTable     OBJECT IDENTIFIER ::= { ciscoDSGProgramEntry  2 }

-- *************************************
-- programEntryTable Branch
-- *************************************

-- *************************************
-- programEntryControlTable Branch
-- *************************************

programEntryControlTable OBJECT-TYPE
     SYNTAX  SEQUENCE OF ProgramEntryControlEntry
     MAX-ACCESS  not-accessible
     STATUS  current
     DESCRIPTION
         "Program Entry Control  Table."
     ::= { programEntryTable 1 }

programEntryControlEntry OBJECT-TYPE
     SYNTAX  ProgramEntryControlEntry
     MAX-ACCESS  not-accessible
     STATUS  current
     DESCRIPTION
         "Entry for Program Entry Control Table."
     INDEX   { programEntryControlIndex}
     ::= { programEntryControlTable 1 }

ProgramEntryControlEntry ::=  SEQUENCE
{
    programEntryControlIndex           Integer32,
    programEntryControlChNum           Integer32,
    --************* For future **************
    --programEntryControlCAResource      INTEGER,
    programEntryControlChCmd           INTEGER,
    programEntryControlResourceId      Unsigned32
}

programEntryControlIndex OBJECT-TYPE
     SYNTAX  Integer32 (1..32)
     MAX-ACCESS  not-accessible
     STATUS  current
     DESCRIPTION
         "Program entry index."
     ::= { programEntryControlEntry  1 }

programEntryControlChNum OBJECT-TYPE
     SYNTAX  Integer32 (0..65535)
     MAX-ACCESS  read-write
     STATUS  current
     DESCRIPTION
         "Program Entry channel number."
     ::= { programEntryControlEntry 2 }

--************* For future **************
--programEntryControlCAResource OBJECT-TYPE
--     SYNTAX INTEGER {
--            fta(1),
--            cam(2),
--            powervu(3),
--            auto(4)
--          }
--     MAX-ACCESS  read-write
--     STATUS  current
--     DESCRIPTION
--           "Select Program Conditional Access Resource."
--     ::= { programEntryControlEntry 3 }

programEntryControlChCmd OBJECT-TYPE
     SYNTAX  INTEGER {
             switch(1),
             up(2),
             down(3),
             last(4),
             writeOnly(5)
          }
     MAX-ACCESS  read-write
     STATUS  current
     DESCRIPTION
         "Command used to change channel.
          Setting switch( 1 ) switches to the channel specified by
          programEntryControlChNum ( not used ).
          Setting up( 2 ) displays the next immediate channel available .
          Setting down( 3 ) displays the previous immediate channel
          available.
          Setting last( 4 ) displays the channel selected last."
     ::= { programEntryControlEntry  4 }

programEntryControlResourceId OBJECT-TYPE
     SYNTAX  Unsigned32 (0..4294967295)
     MAX-ACCESS  read-write
     STATUS  current
     DESCRIPTION
         "Combined resource plus number."
     ::= { programEntryControlEntry  5 }


-- *************************************
-- programEntryStatusTable Branch
-- *************************************

programEntryStatusTable OBJECT-TYPE
     SYNTAX  SEQUENCE OF ProgramEntryStatusEntry
     MAX-ACCESS  not-accessible
     STATUS  current
     DESCRIPTION
         "Program Entry Status  Table."
     ::= { programEntryTable 2 }

programEntryStatusEntry OBJECT-TYPE
     SYNTAX  ProgramEntryStatusEntry
     MAX-ACCESS  not-accessible
     STATUS  current
     DESCRIPTION
         "Entry for Program Entry Status Table."
     INDEX   { programEntryStatusIndex }
     ::= { programEntryStatusTable 1 }

ProgramEntryStatusEntry ::=  SEQUENCE
{
    programEntryStatusIndex            Integer32,
    programEntryStatusChName           DisplayString,
    programEntryStatusCAAuth           INTEGER,
    programEntryStatusCAEncry          INTEGER,
    programEntryStatusCAScram          INTEGER,
    programEntryStatusCAID             INTEGER,
    programEntryStatusSRStatus         INTEGER,
    programEntryStatusSRType           INTEGER,
    programEntryStatusSRStartTime      DisplayString,
    programEntryStatusSREndTime        DisplayString,
    programEntryStatusPRGMStatus       INTEGER,
    programEntryStatusPMTPID           DisplayString,
    programEntryStatusPCRPID           DisplayString
    --************* For future **************
    -- programEntryStatusCombinedCAID     DisplayString
}

programEntryStatusIndex OBJECT-TYPE
     SYNTAX  Integer32 (1..32)
     MAX-ACCESS  not-accessible
     STATUS  current
     DESCRIPTION
         "Program entry Status index."
     ::= { programEntryStatusEntry  1 }

programEntryStatusChName OBJECT-TYPE
     SYNTAX  DisplayString (SIZE(0..63))
     MAX-ACCESS  read-only
     STATUS  current
     DESCRIPTION
         "Channel name from SDT."
     ::= { programEntryStatusEntry 2 }

programEntryStatusCAAuth OBJECT-TYPE
     SYNTAX  INTEGER {
             no(1),
             yes(2)
          }
     MAX-ACCESS  read-only
     STATUS  current
     DESCRIPTION
         "Channel Authorised Status."
     ::= { programEntryStatusEntry 3 }

programEntryStatusCAEncry OBJECT-TYPE
     SYNTAX  INTEGER {
             no(1),
             yes(2),
             unkn(3)
          }
     MAX-ACCESS  read-only
     STATUS  current
     DESCRIPTION
         "Channel Encrypted Status."
     ::= { programEntryStatusEntry 4 }

programEntryStatusCAScram OBJECT-TYPE
     SYNTAX  INTEGER {
             no(1),
             yes(2)
          }
     MAX-ACCESS  read-only
     STATUS  current
     DESCRIPTION
         "Channel Scrambled Status."
     ::= { programEntryStatusEntry 5 }

programEntryStatusCAID OBJECT-TYPE
     SYNTAX  INTEGER {
             unknown(1),
             fta(2),
             powervu(3),
             biss1(4),
             biss2(5),
             biss3(6),
             standardized(7),
             canalplus(8),
             ccett(9),
             deutscheTel(10),
             eurodec(11),
             franceTel(12),
             iredeto(13),
             jerroldGi(14),
             matraComm(15),
             nds(16),
             nokia(17),
             norwegianTel(18),
             ntl(19),
             philips(20),
             sony(21),
             tandbergTv(22),
             thomson(23),
             tvCom(24),
             hptCroatian(25),
             hrtCroatian(26),
             ibm(27),
             nera(28),
             betaTechnik(29),
             kudelski(30),
             titanIS(31),
             telefonica(32),
             stentor(33),
             tadiranScopus(34),
             barco(35),
             starguideDN(36),
             mentorDS(37),
             european(38),
             polycipher(39),
             generalIns(40),
             telemann(41),
             cryptoworks(42),
             tsinghua(43),
             easycas(44),
             alphacrypt(45),
             dvnHoldings(46),
             shanghaiADT(47),
             shenzhenKing(48),
             sky(49),
             dreamcrypt(50),
             thalescrypt(51),
             runcom(52),
             sidsa(53),
             beijingCom(54),
             latens(55),
             xcrypt(56),
             beijingDig(57),
             widevineTec(58),
             skTel(59),
             enigmaSys(60),
             reserved(61),
             ruscrypt(62),
             other(63)
          }
     MAX-ACCESS  read-only
     STATUS  current
     DESCRIPTION
         "Conditional Access System ID."
     ::= { programEntryStatusEntry 6 }

programEntryStatusSRStatus OBJECT-TYPE
     SYNTAX  INTEGER {
             notStarted(1),
             primary(2),
             alternate(3)
          }
     MAX-ACCESS  read-only
     STATUS  current
     DESCRIPTION
         "SR PE Status."
     ::= { programEntryStatusEntry 7 }

programEntryStatusSRType OBJECT-TYPE
     SYNTAX  INTEGER {
             none(1),
             scheduled(2),
             ca(3),
             cuetrigger(4)
          }
     MAX-ACCESS  read-only
     STATUS  current
     DESCRIPTION
         "SR Event Type."
     ::= { programEntryStatusEntry 8 }

programEntryStatusSRStartTime OBJECT-TYPE
     SYNTAX  DisplayString (SIZE(0..32))
     MAX-ACCESS  read-only
     STATUS  current
     DESCRIPTION
         "SR Event Start Time."
     ::= { programEntryStatusEntry 9 }

programEntryStatusSREndTime OBJECT-TYPE
     SYNTAX  DisplayString (SIZE(0..32))
     MAX-ACCESS  read-only
     STATUS  current
     DESCRIPTION
         "SR Event End Time"
     ::= { programEntryStatusEntry 10 }

programEntryStatusPRGMStatus OBJECT-TYPE
     SYNTAX  INTEGER {
             active(1),
             inactive(2)
          }
     MAX-ACCESS  read-only
     STATUS  current
     DESCRIPTION
         "Program Status."
     ::= { programEntryStatusEntry 11 }

programEntryStatusPMTPID OBJECT-TYPE
     SYNTAX  DisplayString (SIZE(0..32))
     MAX-ACCESS read-only
     STATUS current
     DESCRIPTION
         "Program map table program ID.The range is from 0 to 8192 in
         steps of 1."
     ::= {programEntryStatusEntry 12 }

programEntryStatusPCRPID OBJECT-TYPE
     SYNTAX  DisplayString (SIZE(0..32))
     MAX-ACCESS read-only
     STATUS current
     DESCRIPTION
         "Program clock reference program ID.The range is from 0 to
         8192 in steps of 1."
     ::= { programEntryStatusEntry 13 }

--************* For future **************
-- programEntryStatusCombinedCAID OBJECT-TYPE
--   SYNTAX  DisplayString (SIZE(0..32))
--   MAX-ACCESS  read-only
--   STATUS  current
--   DESCRIPTION
--       "Conditional Access ID Status."
--   ::= { programEntryStatusEntry 14 }


-- *************************************
-- programEntryPIDTable Branch
-- *************************************

programEntryPIDTable OBJECT-TYPE
     SYNTAX  SEQUENCE OF ProgramEntryPIDEntry
     MAX-ACCESS  not-accessible
     STATUS  current
     DESCRIPTION
         "Program Entry PID table."
     ::= { programEntryTable 3 }

programEntryPIDEntry OBJECT-TYPE
     SYNTAX  ProgramEntryPIDEntry
     MAX-ACCESS  not-accessible
     STATUS  current
     DESCRIPTION
         "Entry for Program Entry PID table."
     INDEX   { programEntryPIDPEIndex,programEntryPIDIndex }
     ::= { programEntryPIDTable 1 }

ProgramEntryPIDEntry ::=  SEQUENCE
{
    programEntryPIDPEIndex         Integer32,
    programEntryPIDIndex           Integer32,
    programEntryPIDTypeName        DisplayString,
    programEntryPIDTypeDetail      INTEGER,
    programEntryPIDValue           DisplayString,
    programEntryPIDPresent         INTEGER
}

programEntryPIDPEIndex OBJECT-TYPE
     SYNTAX  Integer32 (1..138)
     MAX-ACCESS  not-accessible
     STATUS  current
     DESCRIPTION
         "PID program Index."
     ::= { programEntryPIDEntry  1 }

programEntryPIDIndex OBJECT-TYPE
     SYNTAX  Integer32 (1..138)
     MAX-ACCESS  not-accessible
     STATUS  current
     DESCRIPTION
         "Program Index."
     ::= { programEntryPIDEntry  2 }

programEntryPIDTypeName OBJECT-TYPE
     SYNTAX  DisplayString (SIZE(0..32))
     MAX-ACCESS  read-only
     STATUS  current
     DESCRIPTION
         "Program Entry PID Type."
     ::= { programEntryPIDEntry  3 }

programEntryPIDTypeDetail OBJECT-TYPE
     SYNTAX  INTEGER {
             pcr(1),
             mpg1Vid(2),
             mpg2Vid(3),
             hdVid(4),
             mpg4Vid(5),
             iso422Vid(6),
             h264Vid(7),
             mpgAudL1(8),
             mpg2AudL1(9),
             mpgAudL2(10),
             mpg2AudL2(11),
             mpg4Aud(12),
             dvbDolbyDigital(13),
             dvbDolbyDigitalPlus(14),
             atscDolbyDigital(15),
             atscDolbyDigitalPlus(16),
             aacLsAud(17),
             haacLoAud(18),
             haacAdAud(19),
             dbeAud(20),
             dtsAud(21),
             dvbSubt(22),
             saSubt(23),
             dvbVbi(24),
             saVbi(25),
             dvbTtx(26),
             scteDpi(27),
             dvbMpe(28),
             dvbAsyn(29),
             dvbSyns(30),
             dvbSynd(31),
             dvbDcar(32),
             dvbOcar(33),
             saUtld(34),
             saHsd(35),
             saWbd(36),
             saCddl(37),
             ecm(38),
             emm(39),
             pmt(40),
             unknown(41),
             reserved(42)
          }
     MAX-ACCESS  read-only
     STATUS  current
     DESCRIPTION
         "Program Entry PID Type Detail."
     ::= { programEntryPIDEntry  4 }

programEntryPIDValue OBJECT-TYPE
     SYNTAX  DisplayString (SIZE(0..32))
     MAX-ACCESS  read-only
     STATUS  current
     DESCRIPTION
         "Program Entry PID value.The range is from 0 to 8192 in
         steps of 1."
     ::= { programEntryPIDEntry  5 }

programEntryPIDPresent OBJECT-TYPE
     SYNTAX  INTEGER {
             no(1),
             yes(2)
          }
     MAX-ACCESS  read-only
     STATUS  current
     DESCRIPTION
         "Program Entry PID packets present in stream."
     ::= { programEntryPIDEntry  6 }

END

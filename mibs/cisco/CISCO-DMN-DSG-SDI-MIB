--*****************************************************************
-- CISCO_DMN_DSG_SDI.mib: MIB file for SDI control and status.
--
-- August 2010, Hemant Kumar R
--
-- Copyright (c) 2010 - 2012 by Cisco Systems, Inc. All rights reserved.
--*****************************************************************

CISCO-DMN-DSG-SDI-MIB

DEFINITIONS ::= BEGIN

IMPORTS
    OBJECT-TYPE,
    MODULE-IDENTITY, Integer32, Counter32
        FROM SNMPv2-SMI
    OBJECT-GROUP, MODULE-COMPLIANCE
        FROM SNMPv2-CONF
    ciscoDSGUtilities
        FROM CISCO-DMN-DSG-ROOT-MIB;


ciscoDSGSDI MODULE-IDENTITY
    LAST-UPDATED    "201203201100Z" -- March 20 2012 11:00:00 GMT
    ORGANIZATION    "Cisco Systems, Inc."
    CONTACT-INFO
       "Cisco Systems, Inc.
        Customer Service
        Postal: 170 W Tasman Drive
        San Jose, CA 95134
        USA
        Tel: +1 800 553 NETS

        E-mail: cs-ipsla@cisco.com"
    DESCRIPTION     "Cisco SDI MIB."

    REVISION       "201203201100Z"
    DESCRIPTION    "V01.00.01 2012-03-20
                    Updated for D9854 R4 Release."

    REVISION        "201008240700Z"
    DESCRIPTION     "V01.00.00 2010-08-24
                    Initial Version."

    ::= { ciscoDSGUtilities 32 }

 sdiTable            OBJECT IDENTIFIER ::= { ciscoDSGSDI 2 }
 sdiInfo             OBJECT IDENTIFIER ::= { ciscoDSGSDI 1 }

--*****************************
-- SDI Vii Branch
--*****************************
sdiVii  OBJECT-TYPE
    SYNTAX  INTEGER{
                disabled(1),
                enabled(2)
            }
    MAX-ACCESS read-write
    STATUS  current
    DESCRIPTION
        "VII Control Disable/Enable."
    ::= { sdiInfo 1 }

vancGlobalStatusInterlaced   OBJECT-TYPE
    SYNTAX   INTEGER{ disabled(1), enabled(2) }
    MAX-ACCESS  read-only
    STATUS  current
    DESCRIPTION
        "Indicates if Output is Interlaced."
    ::= { sdiInfo 2 }

vancGlobalStatusFrames   OBJECT-TYPE
    SYNTAX   Counter32
    MAX-ACCESS read-only
    STATUS  current
    DESCRIPTION
        "Video Frames Per Second."
    ::= { sdiInfo 3 }

vancGlobalStatusLines  OBJECT-TYPE
    SYNTAX   Counter32
    MAX-ACCESS read-only
    STATUS  current
    DESCRIPTION
        "Lines Per Video Frame."
    ::= { sdiInfo 4 }

vancGlobalStatusWords  OBJECT-TYPE
    SYNTAX   Counter32
    MAX-ACCESS read-only
    STATUS  current
    DESCRIPTION
        "VANC Words Per Line."
    ::= { sdiInfo 5 }

vancGlobalStatusFirst  OBJECT-TYPE
    SYNTAX   Counter32
    MAX-ACCESS read-only
    STATUS  current
    DESCRIPTION
        "VANC Area: First Line."
    ::= { sdiInfo 6 }

vancGlobalStatusLast  OBJECT-TYPE
    SYNTAX   Counter32
    MAX-ACCESS read-only
    STATUS  current
    DESCRIPTION
        "VANC Area: Last Line."
    ::= { sdiInfo 7 }

vancGlobalStatusSwitch  OBJECT-TYPE
    SYNTAX   Counter32
    MAX-ACCESS read-only
    STATUS  current
    DESCRIPTION
        "VANC Area: Switch Line."
    ::= { sdiInfo 8 }

vancGlobalStatusMultiLine   OBJECT-TYPE
    SYNTAX   INTEGER{
                    disabled(1),
                    enabled(2)
                    }
    MAX-ACCESS read-only
    STATUS  current
    DESCRIPTION
        "Multi-line VANC Injection Support."
    ::= { sdiInfo 9 }

--*****************************
-- SDI Table Branch
--*****************************

--*********************************
-- VANC Configuration Table Branch
--*********************************

vancCfgTable OBJECT-TYPE
    SYNTAX  SEQUENCE OF VancCfgEntry
    MAX-ACCESS not-accessible
    STATUS  current
    DESCRIPTION
        "VANC Configuration Info Table"
    ::= { sdiTable 1 }

vancCfgEntry OBJECT-TYPE
    SYNTAX  VancCfgEntry
    MAX-ACCESS not-accessible
    STATUS current
    DESCRIPTION
        "VANC Configuration Entry."
    INDEX   {
                vancCfgSvcID
            }
    ::= { vancCfgTable 1 }

VancCfgEntry ::=  SEQUENCE
{
    vancCfgSvcID                INTEGER,
    vancCfgEnable               INTEGER,
    vancCfgOffset               Integer32
}

vancCfgSvcID OBJECT-TYPE
     SYNTAX  INTEGER {
                        eia708(1),
                        afd(2),
                        dpi(3),
                        smpte2031(4),
                        sdpOP47(5),
                        multiOP47(6)
                     }
     MAX-ACCESS  read-only
     STATUS  current
     DESCRIPTION
         "VANC Service Identifier."
     ::= { vancCfgEntry 1 }

vancCfgEnable OBJECT-TYPE
SYNTAX  INTEGER {
                    no(1),
                    yes(2)
                }
     MAX-ACCESS  read-write
     STATUS  current
     DESCRIPTION
         "VANC Service Enabled."
     ::= { vancCfgEntry 2 }

vancCfgOffset OBJECT-TYPE
SYNTAX  Integer32 (0..18)
     MAX-ACCESS  read-write
     STATUS  current
     DESCRIPTION
         "Offset From the First VANC Switch Line."
     ::= { vancCfgEntry 3 }

--*****************************
-- SDI Audio Slot Table Branch
--*****************************
sdiAudioSlotTable  OBJECT-TYPE
    SYNTAX  SEQUENCE OF SDIAudioSlotEntry
    MAX-ACCESS not-accessible
    STATUS  current
    DESCRIPTION
        "Table of SDI Audio Slot Information."
    ::= { sdiTable 2 }

sdiAudioSlotEntry OBJECT-TYPE
    SYNTAX  SDIAudioSlotEntry
    MAX-ACCESS  not-accessible
    STATUS  current
    DESCRIPTION
        "SDI Audio Slot Entry."
    INDEX   {
                sdiAudioSlotGroup,
                sdiAudioSlotPosition
            }
     ::= { sdiAudioSlotTable 1 }

SDIAudioSlotEntry ::=  SEQUENCE
{
    sdiAudioSlotGroup            Integer32,
    sdiAudioSlotPosition         Integer32,
    sdiAudioSlotAud              Integer32,
    sdiAudioSlotChan             Integer32
}

sdiAudioSlotGroup  OBJECT-TYPE
    SYNTAX  Integer32 (1..1)
    MAX-ACCESS read-only
    STATUS  current
    DESCRIPTION
        "Channel Grouping."
    ::= { sdiAudioSlotEntry 1 }

sdiAudioSlotPosition  OBJECT-TYPE
    SYNTAX  Integer32 (1..4)
    MAX-ACCESS read-only
    STATUS  current
    DESCRIPTION
        "HANC Position."
    ::= { sdiAudioSlotEntry 2 }

sdiAudioSlotAud  OBJECT-TYPE
    SYNTAX  Integer32 (1..2)
    MAX-ACCESS read-write
    STATUS  current
    DESCRIPTION
        "Source Audio."
    ::= { sdiAudioSlotEntry 3 }

sdiAudioSlotChan  OBJECT-TYPE
    SYNTAX  Integer32 (1..2)
    MAX-ACCESS read-write
    STATUS  current
    DESCRIPTION
        "Source Audio Channel."
    ::= { sdiAudioSlotEntry 4 }

--**********************************
-- VANC Service Status Table Branch
--**********************************

vancServiceStatusTable  OBJECT-TYPE
    SYNTAX  SEQUENCE OF VANCServiceStatusEntry
    MAX-ACCESS not-accessible
    STATUS  current
    DESCRIPTION
        "VANC Service Status Table."
    ::= { sdiTable 3 }

vancServiceStatusEntry OBJECT-TYPE
    SYNTAX  VANCServiceStatusEntry
    MAX-ACCESS  not-accessible
    STATUS  current
    DESCRIPTION
        "VANC Service Status Entry."
    INDEX   {
                vancServiceStatusServiceID
            }
     ::= { vancServiceStatusTable 1 }

VANCServiceStatusEntry ::=  SEQUENCE
{
    vancServiceStatusServiceID           INTEGER,
    vancServiceStatusActive              INTEGER,
    vancServiceStatusADJLine             Counter32,
    vancServiceStatusACTLineF1           Counter32,
    vancServiceStatusACTLineF2           Counter32,
    vancServiceStatusLinesMAX            Counter32,
    vancServiceStatusDataAvg             Counter32,
    vancServiceStatusPacketsOKAvg        Counter32,
    vancServiceStatusPacketsDroppedAvg   Counter32
}

vancServiceStatusServiceID OBJECT-TYPE
SYNTAX  INTEGER {
                    eia708(1),
                    afd(2),
                    dpi(3),
                    smpte2031(4),
                    sdpOP47(5),
                    multiOP47(6)
                }
     MAX-ACCESS  read-only
     STATUS  current
     DESCRIPTION
         "VANC Service Identifier."
     ::= { vancServiceStatusEntry 1 }

vancServiceStatusActive OBJECT-TYPE
SYNTAX  INTEGER {
                    no(1),
                    yes(2)
                }
     MAX-ACCESS  read-only
     STATUS  current
     DESCRIPTION
         "Offset From the First VANC Switch Line."
     ::= { vancServiceStatusEntry 2 }

vancServiceStatusADJLine OBJECT-TYPE
SYNTAX   Counter32
    MAX-ACCESS  read-only
    STATUS  current
    DESCRIPTION
        "Line Number Where VANC Service is Expected."
    ::= { vancServiceStatusEntry 3 }

vancServiceStatusACTLineF1 OBJECT-TYPE
SYNTAX   Counter32
    MAX-ACCESS  read-only
    STATUS  current
    DESCRIPTION
        "Line Number Where VANC Service is Located (In Top Field or Frame)."
    ::= { vancServiceStatusEntry 4 }

vancServiceStatusACTLineF2 OBJECT-TYPE
SYNTAX   Counter32
    MAX-ACCESS  read-only
    STATUS  current
    DESCRIPTION
        "Line Number Where VANC Service is Actually Located (In Bottom Field)."
    ::= { vancServiceStatusEntry 5 }

vancServiceStatusLinesMAX OBJECT-TYPE
SYNTAX   Counter32
    MAX-ACCESS  read-only
    STATUS  current
    DESCRIPTION
        "Max Number of Lines Used by VANC Service."
    ::= { vancServiceStatusEntry 6 }

vancServiceStatusDataAvg OBJECT-TYPE
SYNTAX   Counter32
    MAX-ACCESS  read-only
    STATUS  current
    DESCRIPTION
        "Average Size of VANC Service Data Per Frame."
    ::= { vancServiceStatusEntry 7 }

vancServiceStatusPacketsOKAvg OBJECT-TYPE
SYNTAX   Counter32
    MAX-ACCESS  read-only
    STATUS  current
    DESCRIPTION
        "Average Number of Transmitted VANC Packets Per Frame."
    ::= { vancServiceStatusEntry 8 }

vancServiceStatusPacketsDroppedAvg OBJECT-TYPE
SYNTAX   Counter32
    MAX-ACCESS  read-only
    STATUS  current
    DESCRIPTION
        "Average Number of Dropped VANC Packets Per Frame."
    ::= { vancServiceStatusEntry 9 }

END

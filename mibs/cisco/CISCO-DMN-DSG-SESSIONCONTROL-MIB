--*****************************************************************
-- CISCO-DMN-DSG-SESSIONCONTROL.mib : Mib file for Session Control.
--
-- August 2010, TEL MIB Team
--
--
-- Copyright (c) 1999-2010 by Cisco Systems, Inc.
-- All rights reserved.
--*****************************************************************

CISCO-DMN-DSG-SESSIONCONTROL-MIB 

DEFINITIONS ::= BEGIN

IMPORTS 
    OBJECT-TYPE,
    MODULE-IDENTITY
        FROM SNMPv2-SMI
    DisplayString
        FROM SNMPv2-TC
    OBJECT-GROUP, MODULE-COMPLIANCE
        FROM SNMPv2-CONF
    ciscoDSGUtilities 
        FROM CISCO-DMN-DSG-ROOT-MIB;


ciscoDSGSessionControl MODULE-IDENTITY
    LAST-UPDATED    "201008301100Z" -- August 30 2010 11:00:00 GMT
    ORGANIZATION    "Cisco Systems, Inc."
    CONTACT-INFO   
       "Cisco Systems, Inc.
        Customer Service 
        Postal: 170 W Tasman Drive
        San Jose, CA 95134
        USA  
        Tel: +1 800 553 NETS
        
        E-mail: cs-ipsla@cisco.com"
    DESCRIPTION     "Cisco DSG Session Control MIB."

    REVISION        "201008301100Z"
    DESCRIPTION     "V01.00.01 2010-08-30
                    Updated for adherence to SNMPv2 format."

    REVISION        "200911221500Z"
    DESCRIPTION     "V01.00.00 2009-11-22
                    Initial Version."
    
    ::= { ciscoDSGUtilities 6 }

--****************************************
-- Session Control Branch
--****************************************
 
sessionControlOpen OBJECT-TYPE
     SYNTAX  INTEGER {
             open(1),
             writeOnly(2)
          }
     MAX-ACCESS  read-write
     STATUS  current
     DESCRIPTION
         "Open the session. 1 indicates OPEN."
     ::= { ciscoDSGSessionControl 1 }

sessionControlClose OBJECT-TYPE
     SYNTAX  INTEGER {
             saveAndClose(1),
             ignoreAndClose(2),
             writeOnly(3)
          }
     MAX-ACCESS  read-write
     STATUS  current
     DESCRIPTION
         "Close the session."
     ::= { ciscoDSGSessionControl 2 }

sessionControlStatus OBJECT-TYPE
     SYNTAX  INTEGER {
             open(1),
             closed(2),
             expired(3),
             openWithInvalidConfig(4)
     }
     MAX-ACCESS  read-only
     STATUS  current
     DESCRIPTION
         "Status of the last opened session."
     ::= { ciscoDSGSessionControl 3 }

sessionControlValidateStatus OBJECT-TYPE
     SYNTAX  DisplayString (SIZE(0..250))
     MAX-ACCESS  read-only
     STATUS  current
     DESCRIPTION
         "If the sessioncontrolstatus object displays invalid
          configuration, this object displays the reason for
          invalidity."
     ::= { ciscoDSGSessionControl 4 }

END

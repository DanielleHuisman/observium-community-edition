--*****************************************************************
-- CISCO-DMN-DSG-SUBTITLES.mib : Mib file for Subtitles Selection.
--
-- August 2010, Tel MIB Team
--
--
-- Copyright (c) 1999-2010 by Cisco Systems, Inc.
-- All rights reserved.
--*****************************************************************

CISCO-DMN-DSG-SUBTITLES-MIB DEFINITIONS ::= BEGIN

IMPORTS 
    MODULE-IDENTITY,
    OBJECT-TYPE
        FROM SNMPv2-SMI
      DisplayString
        FROM SNMPv2-TC
    OBJECT-GROUP, MODULE-COMPLIANCE
        FROM SNMPv2-CONF
    ciscoDSGUtilities 
        FROM CISCO-DMN-DSG-ROOT-MIB;


ciscoDSGSubtitle  MODULE-IDENTITY
    LAST-UPDATED  "201307101220Z"
    ORGANIZATION    "Cisco Systems, Inc."
    CONTACT-INFO   
       "Cisco Systems, Inc.
        Customer Service 
        Postal: 170 W Tasman Drive
        San Jose, CA 95134
        USA  
        Tel: +1 800 553 NETS
        
        E-mail: cs-ipsla@cisco.com"
    DESCRIPTION   "Cisco Subtitles MIB."

    REVISION       "201307101220Z"
    DESCRIPTION    "V01.00.02 2013-07-10
                   Updated subtitlesLangList DESCRIPTION clause."

    REVISION       "201008301100Z"
    DESCRIPTION    "V01.00.01 2010-08-30
                   Updated for adherence to SNMPv2 format."

    REVISION      "200912071200Z"
    DESCRIPTION   "V01.00.00 2009-12-07
                   Initial Version." 

    ::= { ciscoDSGUtilities 16 }
                        

-- *************************************
-- ciscoDSGSubtitle Branch
-- *************************************

subtitlesOPMode OBJECT-TYPE
     SYNTAX  INTEGER {
             off(1),
             on(2),
             imiText(3),
             dvb(4)
         }
     MAX-ACCESS  read-write
     STATUS  current
     DESCRIPTION
         "Subtitles Mode: On/Off/Imitext/DVB."
     ::= { ciscoDSGSubtitle 1 }

subtitlesLangMenu OBJECT-TYPE
     SYNTAX  INTEGER {
             languageList(1),
             languageEntry(2),
             pmtOrder(3)
         }
     MAX-ACCESS  read-write
     STATUS  current
     DESCRIPTION
         "Language Preference by Language List, PMT Order or Manual
         Entry."
     ::= { ciscoDSGSubtitle 2 }

subtitlesLangList OBJECT-TYPE
     SYNTAX  INTEGER {
             ara(1),
             btk(2),
             ben(3),
             bul(4),
             chi(5),
             cze(6),
             dan(7),
             dut(8),
             eng(9),
             fin(10),
             fre(11),
             ger(12),
             gre(13),
             heb(14),
             hin(15),
             hun(16),
             ice(17),
             ind(18),
             ita(19),
             jpn(20),
             kor(21),
             may(22),
             mul(23),
             nor(24),
             per(25),
             pol(26),
             por(27),
             rum(28),
             rus(29),
             san(30),
             scc(31),
             sin(32),
             slo(33),
             slv(34),
             som(35),
             spa(36),
             swe(37),
             tai(38),
             tam(39),
             tha(40),
             tur(41),
             ukr(42),
             vie(43)
         }
     MAX-ACCESS  read-write
     STATUS  current
     DESCRIPTION
         "MPEG Languages Codes from the Language List. 
          Language option slv(34) is only supported on D9865."
     ::= { ciscoDSGSubtitle 3 }

subtitlesPMTOrder OBJECT-TYPE
     SYNTAX  INTEGER {
             first(1),
             second(2),
             third(3),
             fourth(4),
             fifth(5),
             sixth(6),
             seventh(7),
             eighth(8)
         }
     MAX-ACCESS  read-write
     STATUS  current
     DESCRIPTION
         "For Multiple Subtitle PIDs Select 1st, 2nd, 3rd, etc."
     ::= { ciscoDSGSubtitle 4 }

subtitlesManualEntry OBJECT-TYPE
     SYNTAX  DisplayString (SIZE(0..3))
     MAX-ACCESS  read-write
     STATUS  current
     DESCRIPTION
         "Preferred Language Code."
     ::= { ciscoDSGSubtitle 5 }

subtitlesIMITextPos OBJECT-TYPE
     SYNTAX  INTEGER {
             standard(1),
             extended(2)
         }
     MAX-ACCESS  read-write
     STATUS  current
     DESCRIPTION
         "Imitext Positioning: Standard/Extended."
     ::= { ciscoDSGSubtitle 6 }

subtitlesForeGround OBJECT-TYPE
     SYNTAX  INTEGER {
             auto(1),
             yellow(2),
             white(3)
         }
     MAX-ACCESS  read-write
     STATUS  current
     DESCRIPTION
         "Imitext Foreground Colour: Yellow/White/Auto."
     ::= { ciscoDSGSubtitle 7 }

subtitlesBackGround OBJECT-TYPE
     SYNTAX  INTEGER {
             none(1),
             auto(2),
             shadow(3),
             opaque(4),
             semi(5)
         }
     MAX-ACCESS  read-write
     STATUS  current
     DESCRIPTION
         "Imitext Background Colour: None/Auto/Shadow/Opaque/Semi."
     ::= { ciscoDSGSubtitle 8 }

END

--********************************************************************
-- CISCO-DMN-DSG-SYSTEMTOOL.mib: Mib file for System Tool Information.
--
-- August 2010, Hemant Kumar R
--
--
-- Copyright (c) 1999-2010 by Cisco Systems, Inc.
-- All rights reserved.
--*********************************************************************

CISCO-DMN-DSG-SYSTEMTOOL-MIB

DEFINITIONS ::= BEGIN

    IMPORTS
    OBJECT-TYPE,
    MODULE-IDENTITY
    FROM SNMPv2-SMI
    OBJECT-GROUP, MODULE-COMPLIANCE
    FROM SNMPv2-CONF
    ciscoDSGUtilities
    FROM CISCO-DMN-DSG-ROOT-MIB;

    ciscoDSGSystemTool  MODULE-IDENTITY
    LAST-UPDATED    "201008030900Z" -- August 03 2010 09:00:00 GMT
    ORGANIZATION    "Cisco Systems, Inc."
    CONTACT-INFO
    "Cisco Systems, Inc.
            Customer Service
            Postal: 170 W Tasman Drive
            San Jose, CA 95134
            USA
            Tel: +1 800 553 NETS

            E-mail: cs-ipsla@cisco.com"
    DESCRIPTION     "Cisco DSG System Tool MIB."

    REVISION        "201008030900Z"
    DESCRIPTION     "V01.00.01 2010-08-03
                    Item systemToolClearLogs is added."

    REVISION        "200912201500Z"
    DESCRIPTION     "V01.00.00 2009-12-20
                    Initial Version."

    ::= { ciscoDSGUtilities 8 }

systemTool           OBJECT IDENTIFIER ::= { ciscoDSGSystemTool 1 }

--*********************************
-- System Tool Branch
--*********************************

systemToolBanner  OBJECT-TYPE
    SYNTAX  INTEGER {
                disable(1),
                enable(2)
            }
    MAX-ACCESS  read-write
    STATUS current
    DESCRIPTION
        "Enable / Disable OSD Banner Messages."
    ::= { systemTool 1 }

systemToolReboot  OBJECT-TYPE
    SYNTAX  INTEGER {
                writeOnly(1),
                yes(2)
            }
    MAX-ACCESS  read-write
    STATUS current
    DESCRIPTION
        "Setting yes(2) reboots the system."
    ::= { systemTool 2 }

systemToolFactoryReset  OBJECT-TYPE
    SYNTAX  INTEGER {
                writeOnly(1),
                yes(2)
            }
    MAX-ACCESS  read-write
    STATUS current
    DESCRIPTION
        "Setting yes( 2 ) performs factory reset of the system."
    ::= { systemTool 3 }

systemToolCleanUnusedTables  OBJECT-TYPE
    SYNTAX  INTEGER {
                writeOnly(1),
                yes(2)
            }
    MAX-ACCESS  read-write
    STATUS current
    DESCRIPTION
        "Set this object to yes( 2 ) to clean up memory of parameters
        unused by this version."
    ::= { systemTool 4 }

systemToolCAMode  OBJECT-TYPE
    SYNTAX INTEGER {
                standard(1),
                open(2)
            }
    MAX-ACCESS  read-write
    STATUS  current
    DESCRIPTION
        "Custom Tuning Mode: Conditional Access Mode: Standard/ Open."
    ::= { systemTool 5 }

systemToolClearLogs  OBJECT-TYPE
    SYNTAX INTEGER {
                writeOnly(1),
                yes(2)
            }
    MAX-ACCESS  read-write
    STATUS  current
    DESCRIPTION
        "Set this object to yes( 2 ) to clean up memory of logs."
    ::= { systemTool 6 }

END

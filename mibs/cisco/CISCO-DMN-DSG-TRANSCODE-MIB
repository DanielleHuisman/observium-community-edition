--*****************************************************************
-- CISCO_DMN_DSG_Transcode.mib: MIB file for Video Transcode information.
--
-- February 2012, Ming Yao
-- October 2010, Hemant Kumar R
--
-- Copyright (c) 2010-2012 by Cisco Systems, Inc. All rights reserved.
--*****************************************************************

CISCO-DMN-DSG-TRANSCODE-MIB

DEFINITIONS ::= BEGIN

IMPORTS
    OBJECT-TYPE,
    MODULE-IDENTITY, Integer32
        FROM SNMPv2-SMI
    DisplayString
        FROM SNMPv2-TC
    OBJECT-GROUP, MODULE-COMPLIANCE
        FROM SNMPv2-CONF
    ciscoDSGUtilities
        FROM CISCO-DMN-DSG-ROOT-MIB;


ciscoDSGTranscode MODULE-IDENTITY
    LAST-UPDATED    "201307101220Z"
    ORGANIZATION    "Cisco Systems, Inc."
    CONTACT-INFO
       "Cisco Systems, Inc.
        Customer Service
        Postal: 170 W Tasman Drive
        San Jose, CA 95134
        USA
        Tel: +1 800 553 NETS

        E-mail: cs-ipsla@cisco.com"
    DESCRIPTION     "Cisco Transcode MIB."

    REVISION       "201307101220Z"
    DESCRIPTION    "V01.00.04 2013-07-10
                   Remove slv(34) from transcoderSubtLangList."

    REVISION        "201203201800Z"
    DESCRIPTION     "V01.00.03 2012-03-18
                    Updated for D9854 R4 release."

    REVISION        "201010130800Z"
    DESCRIPTION     "V01.00.02 2010-10-31
                    Updated enum values for transcoderCfgManualGOP
                    transcoderCfgSDHRes and transcoderCfgSDManualGOP."

    REVISION        "201008240700Z"
    DESCRIPTION     "V01.00.00 2010-08-24
                    Initial Version."

    ::= { ciscoDSGUtilities 37 }
    
transcoderInfo   OBJECT IDENTIFIER ::= { ciscoDSGTranscode 1 }
transcoderTable  OBJECT IDENTIFIER ::= { ciscoDSGTranscode 2 }

--**************************************
-- Transcoder Configuration Info Branch
--**************************************
transcoderLOIAction OBJECT-TYPE
     SYNTAX  INTEGER{
             blackOutput(1),
             noOutput(2)
     }
     MAX-ACCESS  read-write
     STATUS  current
     DESCRIPTION
         "Select whether outputs should transmit black
          or not transmit any data when there is a
          loss of input."
     ::= { transcoderInfo 1 }


--**************************************
-- Transcoder Configuration Table Branch
--**************************************
transcoderCfgTable  OBJECT-TYPE
     SYNTAX  SEQUENCE OF TranscoderCfgEntry
     MAX-ACCESS not-accessible
     STATUS  current
     DESCRIPTION
         "Transcoder Configuration Table."
     ::= { transcoderTable 1 }

transcoderCfgEntry OBJECT-TYPE
     SYNTAX  TranscoderCfgEntry
     MAX-ACCESS  not-accessible
     STATUS  current
     DESCRIPTION
         "Entry for Transcoder configuration table."
     INDEX  { transcoderCfgIndex }
     ::= { transcoderCfgTable 1 }

TranscoderCfgEntry ::=  SEQUENCE
{
    transcoderCfgIndex                        Integer32,
    transcoderCfgApplyInband                  INTEGER,
    transcoderCfgVRes                         INTEGER,
    transcoderCfgCCPkt1                     INTEGER,
    transcoderCfgCCPkt2                     INTEGER,
    transcoderCfgCCPkt3                     INTEGER,    -- Not user configurable
    transcoderCfgPCRRate                      INTEGER,    -- Not user configurable
--    transcoderCfgEia608                       INTEGER,    // Obsolete. Replaced by CCPkt
--    transcoderCfgEia708                       INTEGER,    // Obsolete. Replaced by CCPkt
    transcoderCfgHDHRes                       INTEGER,
    transcoderCfgHDBitrateMode                INTEGER,
    transcoderCfgHDBitRate                    INTEGER,
    transcoderCfgHDGOP                        INTEGER,
    transcoderCfgHDManualGOP                  INTEGER,
    transcoderCfgHD32PullDown                 INTEGER,
    transcoderCfgHDAspectRatio                INTEGER,    -- Not user configurable
    transcoderCfgHDARConversion               INTEGER,    -- Not user configurable
    transcoderCfgHDVideoPreproc               INTEGER,    -- Not user configurable
    transcoderCfgSDHRes                       INTEGER,
    transcoderCfgSDBitRateMode                INTEGER,
    transcoderCfgSDBitRate                    INTEGER,
    transcoderCfgSDGOP                        INTEGER,
    transcoderCfgSDManualGOP                  INTEGER,
    transcoderCfgSD32PullDown                 INTEGER,
    transcoderCfgSDAspectRatio                INTEGER,
    transcoderCfgSDARConversion               INTEGER,
    transcoderCfgSDVideoPreproc               INTEGER     -- Not user configurable
}

transcoderCfgIndex  OBJECT-TYPE
    SYNTAX  Integer32 (1..8)
    MAX-ACCESS read-only
    STATUS  current
    DESCRIPTION
        "Transcoder index."
    ::= { transcoderCfgEntry 1 }

transcoderCfgApplyInband  OBJECT-TYPE
    SYNTAX  INTEGER {
                        no(1),
                        yes(2)
                    }
    MAX-ACCESS read-write
    STATUS  current
    DESCRIPTION
        "Apply in band transcoder parameters."
    ::= { transcoderCfgEntry 2 }


transcoderCfgVRes  OBJECT-TYPE
    SYNTAX  INTEGER {
                        auto(1),
                        hdOut(4),
                        sdOut(5)
                    }
    MAX-ACCESS read-write
    STATUS  current
    DESCRIPTION
        "Selection for Vertical resolution."
    ::= { transcoderCfgEntry 3 }

transcoderCfgCCPkt1  OBJECT-TYPE
    SYNTAX  INTEGER {
                        none (1),
                        ccCEA708(2),
                        ccSCTE20(3)
               }
    MAX-ACCESS read-write
    STATUS  current
    DESCRIPTION
        "Transcode Closed Caption Packet 1."
    ::= { transcoderCfgEntry 4 }

transcoderCfgCCPkt2  OBJECT-TYPE
    SYNTAX  INTEGER {
                        none(1),
                        ccCEA708(2),
                        ccSCTE20(3)
                    }
    MAX-ACCESS read-write
    STATUS  current
    DESCRIPTION
        "Transcode Closed Caption Packet 2."
    ::= { transcoderCfgEntry 5 }

transcoderCfgCCPkt3  OBJECT-TYPE
    SYNTAX  INTEGER {
                        none(1),
                        ccCEA708(2),
                        ccSCTE20(3)
                    }
    MAX-ACCESS read-only
    STATUS  current
    DESCRIPTION
        "Transcode Closed Caption Packet 3."
    ::= { transcoderCfgEntry 6 }

transcoderCfgPCRRate  OBJECT-TYPE
    SYNTAX  INTEGER (10..1000)
    MAX-ACCESS read-only
    STATUS  current
    DESCRIPTION
        "PCR insertion rate in milliseconds."
    ::= { transcoderCfgEntry 7 }

--transcoderCfgEia608  OBJECT-TYPE
--    SYNTAX  INTEGER {
--                        pass(1),
--                        drop(2)
--                    }
--    MAX-ACCESS read-only
--    STATUS  current
--    DESCRIPTION
--        "Transcode EIA 608 CC Packet control."
--    ::= { transcoderCfgEntry 0 }

--transcoderCfgEia708  OBJECT-TYPE
--    SYNTAX  INTEGER {
--                        pass(1),
--                        drop(2)
--                    }
--    MAX-ACCESS read-only
--    STATUS  current
--    DESCRIPTION
--        "Transcode EIA 708 CC Packet control."
--    ::= { transcoderCfgEntry 0 }

transcoderCfgHDHRes  OBJECT-TYPE
    SYNTAX  INTEGER {
                        threeQuarter(1440),
                        full(1920)
                    }
    MAX-ACCESS read-write
    STATUS  current
    DESCRIPTION
        "High Definition Horizontal Resolution."
    ::= { transcoderCfgEntry 8 }

transcoderCfgHDBitrateMode  OBJECT-TYPE
    SYNTAX  INTEGER {
                        cbr(1),
                        vbr(2)
               }
    MAX-ACCESS read-write
    STATUS  current
    DESCRIPTION
        "HD Bit rate mode selection : Constant Bit Rate( cbr )/
        Variable Bit Rate ( vbr )."
    ::= { transcoderCfgEntry 9 }

transcoderCfgHDBitRate  OBJECT-TYPE
    SYNTAX  INTEGER (8000000..25000000)
    MAX-ACCESS read-write
    STATUS  current
    DESCRIPTION
        "HD bit rate in steps of 400bps.
         The Lower Limit is 8Mbps for D9859 and 10Mbps for D9858."
    ::= { transcoderCfgEntry 10 }

transcoderCfgHDGOP  OBJECT-TYPE
    SYNTAX  INTEGER {
                        iFrameSync(1),
                        userGop(2)
                    }
    MAX-ACCESS read-write
    STATUS  current
    DESCRIPTION
        "HD GOP selection."
    ::= { transcoderCfgEntry 11 }

transcoderCfgHDManualGOP  OBJECT-TYPE
    SYNTAX  INTEGER {
                        manualGOP10(10),
                        manualGOP122(122),
                        manualGOP152(152),
                        manualGOP242(242),
                        manualGOP302(302)
                    }
    MAX-ACCESS read-write
    STATUS  current
    DESCRIPTION
        "HD Manual GOP selection."
    ::= { transcoderCfgEntry 12 }

transcoderCfgHD32PullDown  OBJECT-TYPE
    SYNTAX  INTEGER {
                        disable(1),
                        enable(2)
               }
    MAX-ACCESS read-write
    STATUS  current
    DESCRIPTION
        "3-2 Pulldown enabling."
    ::= { transcoderCfgEntry 13 }

transcoderCfgHDAspectRatio  OBJECT-TYPE
    SYNTAX  INTEGER {
                        fourThird(1),
                       sixteenNinth(2)
               }
    MAX-ACCESS read-only
    STATUS  current
    DESCRIPTION
        "HD Output Aspect ratio."
    ::= { transcoderCfgEntry 14 }

transcoderCfgHDARConversion  OBJECT-TYPE
    SYNTAX  INTEGER {
                        none(1),
                        auto(2),
                        autoAFD(3),
                        fourByThreeLetterBox(4),
                        fourByThreePillarBox(5),
                        fourteenByNine(6),
                        fourByThreeFullHeight(7),
                        sixteenByNineFullWidth(8)
               }
    MAX-ACCESS read-only
    STATUS  current
    DESCRIPTION
        "HD Aspect ratio conversion."
    ::= { transcoderCfgEntry 15 }

transcoderCfgHDVideoPreproc  OBJECT-TYPE
    SYNTAX  INTEGER {
                        none(1),
                        deBlock(2),
                        mosquito(3),
                        edgeEnhancement(4)
                    }
    MAX-ACCESS read-only
    STATUS  current
    DESCRIPTION
        "Transcode HD Video Pre-processing."
    ::= { transcoderCfgEntry 16 }

transcoderCfgSDHRes  OBJECT-TYPE
    SYNTAX  INTEGER {
                        threeHundredAndFiftyTwo(352),
                        fourHundredAndEighty(480),
                        fiveHundredAndTwentyEight(528),
                        fiveHundredAndFourtyFour(544),
                        sevenHundredAndFour(704),
                        sevenHundredAndTwenty(720)
               }
    MAX-ACCESS read-write
    STATUS  current
    DESCRIPTION
        "Standard Definition Horizontal Resolution."
    ::= { transcoderCfgEntry 17 }

transcoderCfgSDBitRateMode  OBJECT-TYPE
    SYNTAX  INTEGER {
                        cbr(1),
                        vbr(2)
                    }
    MAX-ACCESS read-write
    STATUS  current
    DESCRIPTION
        "Transcode SD bit rate mode : Constant Bit Rate mode ( cbr )/
        Variable Bit Rate mode ( vbr )."
    ::= { transcoderCfgEntry 18 }

transcoderCfgSDBitRate  OBJECT-TYPE
    SYNTAX  INTEGER (2000000..15000000)
    MAX-ACCESS read-write
    STATUS  current
    DESCRIPTION
        "SD Bit rate in steps of 400."
    ::= { transcoderCfgEntry 19 }

transcoderCfgSDGOP  OBJECT-TYPE
    SYNTAX  INTEGER {
                        iFrameSync(1),
                        userGOPmn(2)
                    }
    MAX-ACCESS read-write
    STATUS  current
    DESCRIPTION
        "Transcode SD Group of Pictures-Format : Transparent/ Manual."
    ::= { transcoderCfgEntry 20 }

transcoderCfgSDManualGOP  OBJECT-TYPE
    SYNTAX  INTEGER {
                        manualgop10(10),
                        manualgop122(122),
                        manualgop152(152),
                        manualgop242(242),
                        manualgop302(302)
                    }
    MAX-ACCESS read-write
    STATUS  current
    DESCRIPTION
        "Transcode SD Manual Group of Pictures - Format values."
    ::= { transcoderCfgEntry 21 }

transcoderCfgSD32PullDown  OBJECT-TYPE
    SYNTAX  INTEGER {
                        disabled(1),
                        enabled(2)
                    }
    MAX-ACCESS read-write
    STATUS  current
    DESCRIPTION
        "Transcode SD 3:2 Pulldown: Enabled/ disabled."
    ::= { transcoderCfgEntry 22 }

transcoderCfgSDAspectRatio  OBJECT-TYPE
    SYNTAX  INTEGER {
                        fourThird(1),
                        sixteenNinth(2)
              }
    MAX-ACCESS read-write
    STATUS  current
    DESCRIPTION
        "Transcode SD Aspect ratio."
    ::= { transcoderCfgEntry 23 }

transcoderCfgSDARConversion  OBJECT-TYPE
    SYNTAX  INTEGER {
                        none(1),
                        auto(2),
                        autoAFD(3),
                        fourByThreeLetterBox(4),
                        fourByThreePillarBox(5),
                        fourteenByNine(6),
                        fourByThreeFullHeight(7),
                        sixteenByNineFullWidth(8)
                    }
    MAX-ACCESS read-write
    STATUS  current
    DESCRIPTION
        "Transcode SD Aspect ratio conversion."
    ::= { transcoderCfgEntry 24 }

transcoderCfgSDVideoPreproc  OBJECT-TYPE
    SYNTAX  INTEGER {
                        none(1),
                        deBlock(2),
                        mosquito(3),
                        edgeEnhancement(4)
                    }
    MAX-ACCESS read-only
    STATUS  current
    DESCRIPTION
        "Transcode SD Video Pre-processing."
    ::= { transcoderCfgEntry 25 }




--**************************************
-- Transcoder Status Table Branch
--**************************************
transcoderStatusTable  OBJECT-TYPE
    SYNTAX  SEQUENCE OF TranscoderStatusEntry
    MAX-ACCESS not-accessible
    STATUS  current
    DESCRIPTION
        "Transcoder status Table."
    ::= { transcoderTable 2}

transcoderStatusEntry OBJECT-TYPE
    SYNTAX  TranscoderStatusEntry
    MAX-ACCESS  not-accessible
    STATUS  current
    DESCRIPTION
        "Entry for transcoder status table."
    INDEX   { transcoderStatusIndex }
    ::= { transcoderStatusTable  1 }

TranscoderStatusEntry ::=  SEQUENCE
{
    transcoderStatusIndex           Integer32,
    transcoderStatusVideoStream     INTEGER
}

transcoderStatusIndex  OBJECT-TYPE
    SYNTAX  Integer32 (1..8)
    MAX-ACCESS read-only
    STATUS  current
    DESCRIPTION
        "Trancoder status index."
    ::= { transcoderStatusEntry 1 }

transcoderStatusVideoStream  OBJECT-TYPE
    SYNTAX  INTEGER {
                        unknown(1),
                        sd480i2997(2),
                        sd480i3000(3),
                        sd576i2500(4),
                        hd720p5000(5),
                        hd720p5994(6),
                        hd720p6000(7),
                        hd1080i2500(8),
                        hd1080i2997(9),
                        hd1080i3000(10),
                        unsupported(11)
                    }
    MAX-ACCESS read-only
    STATUS  current
    DESCRIPTION
        "Incoming stream format."
    ::= { transcoderStatusEntry 2 }


--**************************************
-- Transcoder Subtitles Table Branch
--**************************************
transcoderSubtTable  OBJECT-TYPE
    SYNTAX  SEQUENCE OF TranscoderSubtEntry
    MAX-ACCESS not-accessible
    STATUS  current
    DESCRIPTION
        "Transcoder Subtitle Table."
    ::= { transcoderTable 3}

transcoderSubtEntry OBJECT-TYPE
    SYNTAX  TranscoderSubtEntry
    MAX-ACCESS  not-accessible
    STATUS  current
    DESCRIPTION
        "Entry for transcoder subtitle burn-in table."
    INDEX   { transcoderSubtIndex }
    ::= { transcoderSubtTable  1 }

TranscoderSubtEntry ::=  SEQUENCE
{
    transcoderSubtIndex         Integer32,
    transcoderSubtOpMode        INTEGER,
    transcoderSubtLangMenu      INTEGER,
    transcoderSubtLangList      INTEGER,
    transcoderSubtPMTOrder      INTEGER,
    transcoderSubtManualEntry   DisplayString,
    transcoderSubtImitextPos    INTEGER,
    transcoderSubtForeGround    INTEGER,
    transcoderSubtBackGround    INTEGER
}

transcoderSubtIndex  OBJECT-TYPE
    SYNTAX  Integer32 (1..8)
    MAX-ACCESS read-only
    STATUS  current
    DESCRIPTION
        "Trancoder subtitle burn-in index."
    ::= { transcoderSubtEntry 1 }

transcoderSubtOpMode OBJECT-TYPE
     SYNTAX  INTEGER {
             off(1),
             on(2),
             imiText(3),
             dvb(4)
         }
     MAX-ACCESS  read-write
     STATUS  current
     DESCRIPTION
         "Subtitle Burn-In Subtitles Mode: On/Off/Imitext/DVB."
     ::= { transcoderSubtEntry 2 }

transcoderSubtLangMenu OBJECT-TYPE
     SYNTAX  INTEGER {
             languageList(1),
             languageEntry(2),
             pmtOrder(3)
         }
     MAX-ACCESS  read-write
     STATUS  current
     DESCRIPTION
         "Subtitle Burn-In Language Preference by Language List, PMT Order or Manual
         Entry."
     ::= { transcoderSubtEntry 3 }

transcoderSubtLangList OBJECT-TYPE
     SYNTAX  INTEGER {
             ara(1),
             btk(2),
             ben(3),
             bul(4),
             chi(5),
             cze(6),
             dan(7),
             dut(8),
             eng(9),
             fin(10),
             fre(11),
             ger(12),
             gre(13),
             heb(14),
             hin(15),
             hun(16),
             ice(17),
             ind(18),
             ita(19),
             jpn(20),
             kor(21),
             may(22),
             mul(23),
             nor(24),
             per(25),
             pol(26),
             por(27),
             rum(28),
             rus(29),
             san(30),
             scc(31),
             sin(32),
             slo(33),
             som(35),
             spa(36),
             swe(37),
             tai(38),
             tam(39),
             tha(40),
             tur(41),
             ukr(42),
             vie(43)
         }
     MAX-ACCESS  read-write
     STATUS  current
     DESCRIPTION
         "Subtitle Burn-In MPEG Languages Codes from the Language List."
     ::= { transcoderSubtEntry 4 }

transcoderSubtPMTOrder OBJECT-TYPE
     SYNTAX  INTEGER {
             first(1),
             second(2),
             third(3),
             fourth(4),
             fifth(5),
             sixth(6),
             seventh(7),
             eighth(8)
         }
     MAX-ACCESS  read-write
     STATUS  current
     DESCRIPTION
         "Subtitle Burn-In For Multiple Subtitle PIDs Select 1st, 2nd, 3rd, etc."
     ::= { transcoderSubtEntry 5 }

transcoderSubtManualEntry OBJECT-TYPE
     SYNTAX  DisplayString (SIZE(0..3))
     MAX-ACCESS  read-write
     STATUS  current
     DESCRIPTION
         "Subtitle Burn-In Preferred Language Code."
     ::= { transcoderSubtEntry 6 }

transcoderSubtImitextPos OBJECT-TYPE
     SYNTAX  INTEGER {
             standard(1),
             extended(2)
         }
     MAX-ACCESS  read-write
     STATUS  current
     DESCRIPTION
         "Subtitle Burn-In Imitext Positioning: Standard/Extended."
     ::= { transcoderSubtEntry 7 }

transcoderSubtForeGround OBJECT-TYPE
     SYNTAX  INTEGER {
             auto(1),
             yellow(2),
             white(3)
         }
     MAX-ACCESS  read-write
     STATUS  current
     DESCRIPTION
         "Subtitle Burn-In Imitext Foreground Colour: Yellow/White/Auto."
     ::= { transcoderSubtEntry 8 }

transcoderSubtBackGround OBJECT-TYPE
     SYNTAX  INTEGER {
             none(1),
             auto(2),
             shadow(3),
             opaque(4),
             semi(5)
         }
     MAX-ACCESS  read-write
     STATUS  current
     DESCRIPTION
         "Subtitle Burn-In Imitext Background Colour: None/Auto/Shadow/Opaque/Semi."
     ::= { transcoderSubtEntry 9 }

END

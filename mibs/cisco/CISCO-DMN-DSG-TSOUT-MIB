--*****************************************************************
-- CISCO_DMN_DSG_TSOUT.mib: MIB file for Transport output control and status.
--
-- August 2010, Hemant Kumar R
--
-- Copyright (c) 2010 - 2012 by Cisco Systems, Inc. All rights reserved.
--*****************************************************************

CISCO-DMN-DSG-TSOUT-MIB

DEFINITIONS ::= BEGIN

IMPORTS
    OBJECT-TYPE,
    MODULE-IDENTITY, Integer32
        FROM SNMPv2-SMI
    DisplayString
        FROM SNMPv2-TC
    OBJECT-GROUP, MODULE-COMPLIANCE
        FROM SNMPv2-CONF
    ciscoDSGUtilities
        FROM CISCO-DMN-DSG-ROOT-MIB;


ciscoDSGTSOUT MODULE-IDENTITY
    LAST-UPDATED    "201203201130Z" -- March 20 2012 11:30:00 GMT
    ORGANIZATION    "Cisco Systems, Inc."
    CONTACT-INFO
       "Cisco Systems, Inc.
        Customer Service
        Postal: 170 W Tasman Drive
        San Jose, CA 95134
        USA
        Tel: +1 800 553 NETS

        E-mail: cs-ipsla@cisco.com"
    DESCRIPTION     "Cisco SDI MIB."

    REVISION       "201203201100Z"
    DESCRIPTION    "V01.00.01 2012-03-20
                    Updated for D9854 R4 Release."

    REVISION        "201008240730Z"
    DESCRIPTION     "V01.00.00 2010-08-24
                    Initial Version."

    ::= { ciscoDSGUtilities 34 }

--*****************************
-- TSOUT Table Branch
--*****************************
tsoutTable  OBJECT-TYPE
     SYNTAX  SEQUENCE OF TSOUTEntry
     MAX-ACCESS not-accessible
     STATUS  current
     DESCRIPTION
         "Transport Stream Output Table."
     ::= { ciscoDSGTSOUT 1 }

tsoutEntry OBJECT-TYPE
     SYNTAX  TSOUTEntry
     MAX-ACCESS  not-accessible
     STATUS  current
     DESCRIPTION
         "Entry for Transport Stream output."
     INDEX   { tsoutID }
     ::= { tsoutTable 1 }

TSOUTEntry ::=  SEQUENCE
{
  tsoutID                        Integer32,
  tsoutInstanceName              DisplayString,
  tsoutOutputMode                INTEGER,
  tsoutDescrambleMode            INTEGER,
  tsoutRateControl               INTEGER,
  tsoutOutputRate                Integer32,
  tsoutInsertNullPkt             INTEGER,
  tsoutMOIPOutputMode            INTEGER
}

tsoutID  OBJECT-TYPE
     SYNTAX  Integer32 (1..2)
     MAX-ACCESS read-only
     STATUS  current
     DESCRIPTION
         "Transport Stream output instance Id."
     ::= { tsoutEntry 1 }

tsoutInstanceName  OBJECT-TYPE
     SYNTAX  DisplayString (SIZE(0..32))
     MAX-ACCESS read-only
     STATUS  current
     DESCRIPTION
         "Transport Stream output instance name."
     ::= { tsoutEntry 2 }

tsoutOutputMode  OBJECT-TYPE
     SYNTAX  INTEGER {
                    noOutput(1),
                    passThrough(2),
                    serviceChannelOnly(3),
                    mapPassthrough(4),
                    mapserviceChannelOnly(5),
                    fullDpmControl(6),
                    transcoding(7)
               }
     MAX-ACCESS read-write
     STATUS  current
     DESCRIPTION
         "Transport Stream output mode selction."
     ::= { tsoutEntry 3 }

tsoutDescrambleMode  OBJECT-TYPE
     SYNTAX  INTEGER {
                    deScrambled(1),
                    scrambled(2)
                }
     MAX-ACCESS read-write
     STATUS  current
     DESCRIPTION
         "Transport Stream output descramble mode selction."
     ::= { tsoutEntry 4 }

tsoutRateControl  OBJECT-TYPE
     SYNTAX  INTEGER {
                    auto(1),
                    user(2)
                }
     MAX-ACCESS read-write
     STATUS  current
     DESCRIPTION
         "Transport Stream output rate control selction.
          Auto should not be used if TS mode is Transcoding"
     ::= { tsoutEntry 5 }

tsoutOutputRate  OBJECT-TYPE
     SYNTAX  Integer32 (0..206000000)
     MAX-ACCESS read-write
     STATUS  current
     DESCRIPTION
         "Transport Stream output rate selction
          Range of 0 to 206 Mbps."
     ::= { tsoutEntry 6 }

tsoutInsertNullPkt  OBJECT-TYPE
     SYNTAX  INTEGER {
                    no(1),
                    yes(2)
                }
     MAX-ACCESS read-write
     STATUS  current
     DESCRIPTION
         "Insert null packet stuffing option."
     ::= { tsoutEntry 7 }

tsoutMOIPOutputMode  OBJECT-TYPE
     SYNTAX  INTEGER {
                    noOutput(1),
                    passThrough(2),
                    serviceChannelsOnly(3),
                    mapPassthrough(4),
                    mapServiceChannelsOnly(5),
                    fullDpmControl(6),
                    transcoding(7),
                    sptsServiceChannelsOnly(8),
                    sptsMapServiceChannelsOnly(9),
                    sptsFullDpmControl(10)
                }
     MAX-ACCESS read-write
     STATUS  current
     DESCRIPTION
         "MoIP Transport Stream output mode selection."
     ::= { tsoutEntry 8 }

--*****************************
-- TSOUT Status Table
--*****************************
tsoutStatusTable  OBJECT-TYPE
     SYNTAX  SEQUENCE OF TSOUTStatusEntry
     MAX-ACCESS not-accessible
     STATUS  current
     DESCRIPTION
         "Transport Stream Output Status Table."
     ::= { ciscoDSGTSOUT 2 }

tsoutStatusEntry OBJECT-TYPE
     SYNTAX  TSOUTStatusEntry
     MAX-ACCESS  not-accessible
     STATUS  current
     DESCRIPTION
         "Entry for Transport Stream output status."
     INDEX  { tsoutStatusID }
     ::= { tsoutStatusTable 1 }

TSOUTStatusEntry ::=  SEQUENCE
{
    tsoutStatusID                   Integer32,
    tsoutStatusInstanceName         DisplayString,
    tsoutStatusRate                 Integer32,
    tsoutStatusFree                 Integer32
}

tsoutStatusID  OBJECT-TYPE
     SYNTAX  Integer32 (1..2)
     MAX-ACCESS not-accessible
     STATUS  current
     DESCRIPTION
         "Transport Stream output status instance Id."
     ::= { tsoutStatusEntry 1 }

tsoutStatusInstanceName  OBJECT-TYPE
     SYNTAX  DisplayString (SIZE(0..32))
     MAX-ACCESS read-only
     STATUS  current
     DESCRIPTION
         "Transport Stream output status instance name."
     ::= { tsoutStatusEntry 2 }

tsoutStatusRate  OBJECT-TYPE
     SYNTAX  Integer32 (0..2147483647)
     MAX-ACCESS read-only
     STATUS  current
     DESCRIPTION
         "Transport Stream output rate status."
     ::= { tsoutStatusEntry 3 }

tsoutStatusFree  OBJECT-TYPE
     SYNTAX  Integer32 (0..2147483647)
     MAX-ACCESS read-only
     STATUS  current
     DESCRIPTION
         "Transport Stream output bandwidth free."
     ::= { tsoutStatusEntry 4 }

END

--*****************************************************************
-- CISCO_DMN_DSG_VBI.mib: MIB file for VBI control and status.
--
-- July 2010, Hemant Kumar R
--
-- Copyright (c) 2010 - 2012 Cisco Systems, Inc. All rights reserved.
--*****************************************************************

CISCO-DMN-DSG-VBI-MIB

DEFINITIONS ::= BEGIN

IMPORTS
    OBJECT-TYPE,
    MODULE-IDENTITY
        FROM SNMPv2-SMI
    OBJECT-GROUP, MODULE-COMPLIANCE
        FROM SNMPv2-CONF
    ciscoDSGUtilities
        FROM CISCO-DMN-DSG-ROOT-MIB;


ciscoDSGVBI MODULE-IDENTITY
    LAST-UPDATED    "201203201000Z" -- March 20 2012 10:00:00 GMT
    ORGANIZATION    "Cisco Systems, Inc."
    CONTACT-INFO
       "Cisco Systems, Inc.
        Customer Service
        Postal: 170 W Tasman Drive
        San Jose, CA 95134
        USA
        Tel: +1 800 553 NETS

        E-mail: cs-ipsla@cisco.com"
    DESCRIPTION     "Cisco VBI MIB."

    REVISION       "201203201000Z"
    DESCRIPTION    "V01.00.01 2012-03-20
                    Updated for D9854 R4 Release."

    REVISION        "201007261000Z"
    DESCRIPTION     "V01.00.00 2010-07-26
                    Initial Version."

    ::= { ciscoDSGUtilities 31 }

--*****************************
-- VBI Branch
--*****************************
vbiVitsFlag17  OBJECT-TYPE
    SYNTAX  INTEGER{
                    disable(1),
                    enable(2)
                }
    MAX-ACCESS read-write
    STATUS  current
    DESCRIPTION
        "VITS PAL line 17 Enabled/Disabled."
    ::= { ciscoDSGVBI 1 }

vbiVitsFlag18  OBJECT-TYPE
    SYNTAX  INTEGER{
                disable(1),
                enable(2)
            }
    MAX-ACCESS read-write
    STATUS  current
    DESCRIPTION
        "VITS PAL line 18 Enabled/Disabled."
    ::= { ciscoDSGVBI 2 }

vbiVitsFlag330  OBJECT-TYPE
    SYNTAX  INTEGER{
                disable(1),
                enable(2)
            }
    MAX-ACCESS read-write
    STATUS  current
    DESCRIPTION
        "VITS PAL line 330 Enabled/Disabled."
    ::= { ciscoDSGVBI 3 }

vbiVitsFlag331  OBJECT-TYPE
    SYNTAX  INTEGER{
                disable(1),
                enable(2)
            }
    MAX-ACCESS read-write
    STATUS  current
    DESCRIPTION
        "VITS PAL line 331 Enabled/Disabled."
    ::= { ciscoDSGVBI 4 }

vbiVitcMode  OBJECT-TYPE
    SYNTAX  INTEGER{
                passthrough(1),
                suppress(2),
                autoGenerate(3)
            }
    MAX-ACCESS read-write
    STATUS  current
    DESCRIPTION
        "Select VITC Mode: auto-gen,pass-through or suppress"
    ::= { ciscoDSGVBI 5 }

vbiTimeCode  OBJECT-TYPE
    SYNTAX  INTEGER{
                ltc(1),
                vitc(2),
                both(3)
            }
    MAX-ACCESS read-write
    STATUS  current
    DESCRIPTION
        "Select VITC Time Code: LTC or VITC"
    ::= { ciscoDSGVBI 6 }

vbiColorMode  OBJECT-TYPE
    SYNTAX  INTEGER{
                disable(1),
                enable(2)
            }
    MAX-ACCESS read-write
    STATUS  current
    DESCRIPTION
        "Select whether to enable VITC Color Mode"
    ::= { ciscoDSGVBI 7 }

vbiDelayComp  OBJECT-TYPE
    SYNTAX  INTEGER{
                disable(1),
                enable(2)
            }
    MAX-ACCESS read-write
    STATUS  current
    DESCRIPTION
        "Select whether to enable VITC Delay Comp"
    ::= { ciscoDSGVBI 8 }

vbiDropFrame  OBJECT-TYPE
    SYNTAX  INTEGER{
                disable(1),
                enable(2)
            }
    MAX-ACCESS read-write
    STATUS  current
    DESCRIPTION
        "Select whether to enable VITC Drop Frame"
    ::= { ciscoDSGVBI 9 }

vbiVitcStatus  OBJECT-TYPE
    SYNTAX  INTEGER{
                ltc(1),
                vitc(2),
                both(3),
                undefined(4)
            }
    MAX-ACCESS read-only
    STATUS  current
    DESCRIPTION
        "Output VITC status"
    ::= { ciscoDSGVBI 10 }


END

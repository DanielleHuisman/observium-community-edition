--*****************************************************************
-- CISCO-DMN-DSG-VIDEO.mib : Mib file for Video Control.
--
-- October 2010, Tel MIB Team
--
-- Copyright (c) 1999-2010 by Cisco Systems, Inc.
-- All rights reserved.
--*****************************************************************

CISCO-DMN-DSG-VIDEO-MIB

DEFINITIONS ::= BEGIN

IMPORTS
    MODULE-IDENTITY,
    OBJECT-TYPE, Integer32
        FROM SNMPv2-SMI
    DisplayString
        FROM SNMPv2-TC
    OBJECT-GROUP, MODULE-COMPLIANCE
        FROM SNMPv2-CONF
    ciscoDSGUtilities
        FROM CISCO-DMN-DSG-ROOT-MIB;


ciscoDSGVideo  MODULE-IDENTITY
    LAST-UPDATED  "201010130800Z" -- October 13 2010 08:00:00 GMT
    ORGANIZATION    "Cisco Systems, Inc."
    CONTACT-INFO
       "Cisco Systems, Inc.
        Customer Service
        Postal: 170 W Tasman Drive
        San Jose, CA 95134
        USA
        Tel: +1 800 553 NETS

        E-mail: cs-ipsla@cisco.com"
    DESCRIPTION   "Cisco DSG Video MIB."

    REVISION        "201010130800Z"
    DESCRIPTION     "V01.00.04 2010-10-13
                    Updated videoPVFormat options for
                    migrating D985X/D9865 to generic logic."

                    REVISION        "201008301100Z"
    DESCRIPTION     "V01.00.03 2010-08-30
                    Updated for adherence to SNMPv2 format."

    REVISION       "201003220500Z"
    DESCRIPTION    "V01.00.02 2010-03-22
                    The Syntax of Unsigned32 MIB objects whose range
                    is within the range of Integer32, is updated to
                    Integer32."

    REVISION       "201002121200Z"
    DESCRIPTION    "V01.00.01 2010-02-12
                    The Syntax of read-only objects is updated to
                    DisplayString."

    REVISION       "200912071200Z"
    DESCRIPTION    "V01.00.00 2009-12-07
                    Initial Version."

    ::= { ciscoDSGUtilities 14 }


-- *************************************
-- videoCtrlTable Branch
-- *************************************

videoCtrlTable OBJECT-TYPE
     SYNTAX  SEQUENCE OF VideoCtrlEntry
     MAX-ACCESS  not-accessible
     STATUS  current
     DESCRIPTION
         "Video Control Table."
     ::= { ciscoDSGVideo 1 }

videoCtrlEntry OBJECT-TYPE
     SYNTAX  VideoCtrlEntry
     MAX-ACCESS  not-accessible
     STATUS  current
     DESCRIPTION
         "Entry for Video Control Table."
     INDEX { videoCtrlInstance }
     ::= { videoCtrlTable 1 }

VideoCtrlEntry ::= SEQUENCE
{
  videoCtrlInstance      Integer32,
  videoPVFormat          INTEGER,
  videoSDFormat          INTEGER,
  videoTriSynch          INTEGER,
  videoCutoff            INTEGER,
  aspectRatioSD          INTEGER,
  aspectRatioSelection   INTEGER,
  closedCaptionPrefMode  INTEGER
}

videoCtrlInstance OBJECT-TYPE
     SYNTAX  Integer32 (1..1)
     MAX-ACCESS  not-accessible
     STATUS  current
     DESCRIPTION
         "Instance for Video Control Table."
     ::= { videoCtrlEntry 1 }

videoPVFormat OBJECT-TYPE
     SYNTAX  INTEGER {
             auto(1),
             hd1080i(2),
             hd720p(3),
             sd(4)
         }
     MAX-ACCESS  read-write
     STATUS  current
     DESCRIPTION
         "Primary Video Format: 1080i/720p/SD/Auto."
     ::= { videoCtrlEntry 2 }

videoSDFormat OBJECT-TYPE
     SYNTAX  INTEGER {
             auto(1),
             ntsc(2),
             palBG(3),
             palD(4),
             palI(5),
             palM(6),
             palNAR(7),
             ntscJ(8)
         }
     MAX-ACCESS  read-write
     STATUS  current
     DESCRIPTION
         "Standard Definition Video Format: PAL-B/G /PAL-D/PAL-I/PAL-M/
         PAL-N(AR)/NTSC/NTSC-J/AUTO."
     ::= { videoCtrlEntry 3 }

videoTriSynch OBJECT-TYPE
     SYNTAX  INTEGER {
             disabled(1),
             enabled(2)
         }
     MAX-ACCESS  read-write
     STATUS  current
     DESCRIPTION
         "Component Tri-Sync Enabled/Disabled."
     ::= { videoCtrlEntry 4 }

videoCutoff OBJECT-TYPE
     SYNTAX  INTEGER {
             disable(1),
             enable(2)
         }
     MAX-ACCESS  read-write
     STATUS  current
     DESCRIPTION
         "Enable/Disable cutting video when an alarm occurs."
     ::= { videoCtrlEntry 5 }

aspectRatioSD OBJECT-TYPE
     SYNTAX  INTEGER {
             fourThird(1),
             sixteenNinth(2)
         }
     MAX-ACCESS  read-write
     STATUS  current
     DESCRIPTION
         "Standard Definition Aspect Ratio: 4:3/16:9."
     ::= { videoCtrlEntry 6 }

aspectRatioSelection OBJECT-TYPE
     SYNTAX  INTEGER {
             none(1),
             auto(2),
             autoAFD(3),
             sixteenByNineLetterBox(4),
             fourByThreePillarBox(5),
             fourteenByNine(6),
             fourByThreeCCO(7),
             sixteenByNineSCALE(8)
         }
     MAX-ACCESS  read-write
     STATUS  current
     DESCRIPTION
         "Aspect Ratio Selection."
     ::= { videoCtrlEntry 7 }

closedCaptionPrefMode OBJECT-TYPE
     SYNTAX  INTEGER {
             auto(1),
             saCustom(2),
             eia708(3),
             type3(4),
             type4SA(5),
             type4ATSC(6),
             reserved(7),
             dvs157(8)
         }
     MAX-ACCESS  read-write
     STATUS  current
     DESCRIPTION
         "Preferred Closed Captioning Mode if multiple in stream."
     ::= { videoCtrlEntry 8 }

--***************************************
--videoStatusTable
--***************************************

videoStatusTable OBJECT-TYPE
     SYNTAX  SEQUENCE OF VideoStatusEntry
     MAX-ACCESS  not-accessible
     STATUS  current
     DESCRIPTION
         "Video Status Table."
     ::= { ciscoDSGVideo 2 }

videoStatusEntry OBJECT-TYPE
     SYNTAX  VideoStatusEntry
     MAX-ACCESS  not-accessible
     STATUS  current
     DESCRIPTION
         "Entry for Video Status Table."
     INDEX { videoStatusInstance }
     ::= { videoStatusTable 1 }

VideoStatusEntry ::= SEQUENCE
{
  videoStatusInstance    Integer32,
  videoStream            INTEGER,
  videoPVOutput          INTEGER,
  videoSDOutput          INTEGER,
  videoBitRate           DisplayString,
  video32PullDown        INTEGER,
  videoFPS               DisplayString,
  videoSynchMode         INTEGER,
  videoEncoding          INTEGER,
  aspectRatioConversion  INTEGER,
  aspectRatioStreamAR    INTEGER,
  aspectRatioWSSMode     INTEGER,
  aspectRatioWSSStatus   INTEGER,
  closedCaptionActOP     INTEGER
}

videoStatusInstance OBJECT-TYPE
     SYNTAX  Integer32 (1..1)
     MAX-ACCESS  not-accessible
     STATUS  current
     DESCRIPTION
         "Instance for Video Status Table."
     ::= { videoStatusEntry 1 }

videoStream OBJECT-TYPE
     SYNTAX  INTEGER {
             sd480i2997(1),
             sd480i3000(2),
             sd576i2500(3),
             hd720p5000(4),
             hd720p5994(5),
             hd720p6000(6),
             hd1080i2500(7),
             hd1080i2997(8),
             hd1080i3000(9),
             unknown(10),
             unsupported(11)
         }
     MAX-ACCESS  read-only
     STATUS  current
     DESCRIPTION
         "Video Stream Format."
     ::= { videoStatusEntry 2 }

videoPVOutput OBJECT-TYPE
     SYNTAX  INTEGER {
             hd1080i(1),
             hd720p(2)
         }
     MAX-ACCESS  read-only
     STATUS  current
     DESCRIPTION
         "Primary Video Actual Output Format."
     ::= { videoStatusEntry 3 }

videoSDOutput OBJECT-TYPE
     SYNTAX  INTEGER {
             ntsc(1),
             palBG(2),
             palD(3),
             palI(4),
             palM(5),
             palNAR(6),
             ntscJ(7)
         }
     MAX-ACCESS  read-only
     STATUS  current
     DESCRIPTION
         "Standard Definition Actual Video Output Format."
     ::= { videoStatusEntry 4 }

videoBitRate OBJECT-TYPE
     SYNTAX  DisplayString (SIZE(0..32))
     MAX-ACCESS  read-only
     STATUS  current
     DESCRIPTION
         "Video Bitrate in Mbps.The range is from 0.0 to
         4294.967295 Mbps in steps of 0.000001 Mbps."
     ::= { videoStatusEntry 5 }

video32PullDown OBJECT-TYPE
     SYNTAX  INTEGER {
             yes(1),
             no(2),
             recent(3)
         }
     MAX-ACCESS  read-only
     STATUS  current
     DESCRIPTION
         "3:2 Pulldown: Yes/No/Recent."
     ::= { videoStatusEntry 6 }

videoFPS OBJECT-TYPE
     SYNTAX  DisplayString (SIZE(0..32))
     MAX-ACCESS  read-only
     STATUS  current
     DESCRIPTION
         "Frames per Second ( fps ).The range is from 0.0 to
         4294967.295 fps."
     ::= { videoStatusEntry 7 }

videoSynchMode OBJECT-TYPE
     SYNTAX  INTEGER {
             auto(1),
             manual(2)
         }
     MAX-ACCESS  read-only
     STATUS  current
     DESCRIPTION
         "Synchronization Mode: Auto/Manual."
     ::= { videoStatusEntry 8 }

videoEncoding OBJECT-TYPE
     SYNTAX  INTEGER {
             unknown(1),
             mpeg1(2),
             mpeg2(3),
             h264(4),
             vc1(5),
             mpeg4p2(6)
         }
     MAX-ACCESS  read-only
     STATUS  current
     DESCRIPTION
         "Encoding format of the incoming video stream."
     ::= { videoStatusEntry 9 }

aspectRatioConversion OBJECT-TYPE
     SYNTAX  INTEGER {
             none(1),
             fourByThreeLetterBox(2),
             fourByThreePillarBox(3),
             fourteenByNineLetterBox(4),
             fourteenByNinePillarBox(5),
             fourByThreeCCO(6),
             sixteenByNineCCO(7),
             sixteenByNineLBToFourteenByNineLB(8),
             fourByThreePBToFourteenByNinePB(9)
         }
     MAX-ACCESS  read-only
     STATUS  current
     DESCRIPTION
         "Actual Aspect Ratio Conversion."
     ::= { videoStatusEntry 10 }

aspectRatioStreamAR OBJECT-TYPE
     SYNTAX  INTEGER {
             fourByThree(1),
             sixteenByNine(2),
             twoTwentyOneByHundred(3),
             square(4),
             unavailable(5)
         }
     MAX-ACCESS  read-only
     STATUS  current
     DESCRIPTION
         "Actual Video Stream Aspect Ratio."
     ::= { videoStatusEntry 11 }

aspectRatioWSSMode OBJECT-TYPE
     SYNTAX  INTEGER {
             passthrough(1),
             suppress(2),
             autoModify(3),
             autoCreate(4)
         }
     MAX-ACCESS  read-write
     STATUS  current
     DESCRIPTION
         "Widescreen Signalling Mode."
     ::= { videoStatusEntry 12 }

aspectRatioWSSStatus OBJECT-TYPE
     SYNTAX  INTEGER {
             fourByThreeFullFormat(1),
             sixteenByNineLetterBoxCentre(2),
             sixteenByNineLetterBoxTop(3),
             greaterThanSixteenByNineLetterBoxCentre(4),
             fourteenByNineLetterBoxCentre(5),
             fourteenByNineLetterBoxTop(6),
             fourteenByNineFullFormatCentre(7),
             sixteenByNineFullFormat(8),
             undefined(9)
         }
     MAX-ACCESS  read-only
     STATUS  current
     DESCRIPTION
         "Widescreen Signalling Status."
     ::= { videoStatusEntry 13 }

closedCaptionActOP OBJECT-TYPE
     SYNTAX  INTEGER {
             auto(1),
             saCustom(2),
             eia708(3),
             type3(4),
             type4SA(5),
             type4ATSC(6),
             reserved(7),
             dvs157(8)
         }
     MAX-ACCESS  read-only
     STATUS  current
     DESCRIPTION
         "Actual Closed Captioning Output Mode."
     ::= { videoStatusEntry 14 }

END

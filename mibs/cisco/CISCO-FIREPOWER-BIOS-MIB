-- *********************************************************************
-- CISCO-FIREPOWER-BIOS-MIB.my
-- 
-- MIB representation of the Cisco Firepower
-- BIOS management information model package
-- 
-- Created March 2020 by Charles Bullis
-- 
-- Copyright (c) 2005-2020 Cisco Systems, Inc. All rights reserved.
-- 
-- *********************************************************************

CISCO-FIREPOWER-BIOS-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerMIBObjects,
    CfprManagedObjectId,
    CfprManagedObjectDn
        FROM CISCO-FIREPOWER-MIB
    CfprBiosBootDevErrorCode,
    CfprBiosBootDevGrpType,
    CfprBiosBootDevOrder,
    CfprBiosDefaultAction,
    CfprBiosSupportedAction,
    CfprBiosVfACPI10SupportVpACPI10Support,
    CfprBiosVfAllUSBDevicesVpAllUSBDevices,
    CfprBiosVfAltitudeVpAltitude,
    CfprBiosVfAssertNMIOnPERRVpAssertNMIOnPERR,
    CfprBiosVfAssertNMIOnSERRVpAssertNMIOnSERR,
    CfprBiosVfBootOptionRetryVpBootOptionRetry,
    CfprBiosVfCPUPerformanceVpCPUPerformance,
    CfprBiosVfConsoleRedirectionVpBaudRate,
    CfprBiosVfConsoleRedirectionVpConsoleRedirection,
    CfprBiosVfConsoleRedirectionVpFlowControl,
    CfprBiosVfConsoleRedirectionVpLegacyOSRedirection,
    CfprBiosVfConsoleRedirectionVpPuttyKeyPad,
    CfprBiosVfConsoleRedirectionVpTerminalType,
    CfprBiosVfCoreMultiProcessingVpCoreMultiProcessing,
    CfprBiosVfDRAMClockThrottlingVpDRAMClockThrottling,
    CfprBiosVfDirectCacheAccessVpDirectCacheAccess,
    CfprBiosVfDramRefreshRateVpDramRefreshRate,
    CfprBiosVfEnhancedIntelSpeedStepTechVpEnhancedIntelSpeedStepTech,
    CfprBiosVfExecuteDisableBitVpExecuteDisableBit,
    CfprBiosVfFRB2TimerVpFRB2Timer,
    CfprBiosVfFrequencyFloorOverrideVpFrequencyFloorOverride,
    CfprBiosVfFrontPanelLockoutVpFrontPanelLockout,
    CfprBiosVfIntelEntrySASRAIDModuleVpSASRAID,
    CfprBiosVfIntelEntrySASRAIDModuleVpSASRAIDModule,
    CfprBiosVfIntelHyperThreadingTechVpIntelHyperThreadingTech,
    CfprBiosVfIntelTurboBoostTechVpIntelTurboBoostTech,
    CfprBiosVfIntelVTForDirectedIOVpIntelVTDATSSupport,
    CfprBiosVfIntelVTForDirectedIOVpIntelVTDCoherencySupport,
    CfprBiosVfIntelVTForDirectedIOVpIntelVTDInterruptRemapping,
    CfprBiosVfIntelVTForDirectedIOVpIntelVTDPassThroughDMASupport,
    CfprBiosVfIntelVTForDirectedIOVpIntelVTForDirectedIO,
    CfprBiosVfIntelVirtualizationTechnologyVpIntelVirtTechnology,
    CfprBiosVfInterleaveConfigurationVpChannelInterleaving,
    CfprBiosVfInterleaveConfigurationVpMemoryInterleaving,
    CfprBiosVfInterleaveConfigurationVpRankInterleaving,
    CfprBiosVfLocalX2ApicVpLocalX2Apic,
    CfprBiosVfLvDIMMSupportVpLvDDRMode,
    CfprBiosVfMaxVariableMTRRSettingVpProcessorMtrr,
    CfprBiosVfMaximumMemoryBelow4GBVpMaximumMemoryBelow4GB,
    CfprBiosVfMemoryMappedIOAbove4GBVpMemoryMappedIOAbove4GB,
    CfprBiosVfMirroringModeVpMirroringMode,
    CfprBiosVfNUMAOptimizedVpNUMAOptimized,
    CfprBiosVfOSBootWatchdogTimerPolicyVpOSBootWatchdogTimerPolicy,
    CfprBiosVfOSBootWatchdogTimerTimeoutVpOSBootWatchdogTimerTimeout,
    CfprBiosVfOSBootWatchdogTimerVpOSBootWatchdogTimer,
    CfprBiosVfOnboardSATAControllerVpOnboardSATAController,
    CfprBiosVfOnboardSATAControllerVpSATAMode,
    CfprBiosVfOnboardStorageVpOnboardSCUStorageSupport,
    CfprBiosVfOptionROMEnableVpState,
    CfprBiosVfOptionROMLoadVpLoad,
    CfprBiosVfPCISlotLinkSpeedVpPCIeSlot10LinkSpeed,
    CfprBiosVfPCISlotLinkSpeedVpPCIeSlot1LinkSpeed,
    CfprBiosVfPCISlotLinkSpeedVpPCIeSlot2LinkSpeed,
    CfprBiosVfPCISlotLinkSpeedVpPCIeSlot3LinkSpeed,
    CfprBiosVfPCISlotLinkSpeedVpPCIeSlot4LinkSpeed,
    CfprBiosVfPCISlotLinkSpeedVpPCIeSlot5LinkSpeed,
    CfprBiosVfPCISlotLinkSpeedVpPCIeSlot6LinkSpeed,
    CfprBiosVfPCISlotLinkSpeedVpPCIeSlot7LinkSpeed,
    CfprBiosVfPCISlotLinkSpeedVpPCIeSlot8LinkSpeed,
    CfprBiosVfPCISlotLinkSpeedVpPCIeSlot9LinkSpeed,
    CfprBiosVfPCISlotOptionROMEnableVpPCIeSlotHBAOptionROM,
    CfprBiosVfPCISlotOptionROMEnableVpPCIeSlotMLOMOptionROM,
    CfprBiosVfPCISlotOptionROMEnableVpPCIeSlotN1OptionROM,
    CfprBiosVfPCISlotOptionROMEnableVpPCIeSlotN2OptionROM,
    CfprBiosVfPCISlotOptionROMEnableVpPCIeSlotSASOptionROM,
    CfprBiosVfPCISlotOptionROMEnableVpSlot10State,
    CfprBiosVfPCISlotOptionROMEnableVpSlot1State,
    CfprBiosVfPCISlotOptionROMEnableVpSlot2State,
    CfprBiosVfPCISlotOptionROMEnableVpSlot3State,
    CfprBiosVfPCISlotOptionROMEnableVpSlot4State,
    CfprBiosVfPCISlotOptionROMEnableVpSlot5State,
    CfprBiosVfPCISlotOptionROMEnableVpSlot6State,
    CfprBiosVfPCISlotOptionROMEnableVpSlot7State,
    CfprBiosVfPCISlotOptionROMEnableVpSlot8State,
    CfprBiosVfPCISlotOptionROMEnableVpSlot9State,
    CfprBiosVfPCISlotOptionROMEnableVpSlotMezzState,
    CfprBiosVfPOSTErrorPauseVpPOSTErrorPause,
    CfprBiosVfPSTATECoordinationVpPSTATECoordination,
    CfprBiosVfPackageCStateLimitVpPackageCStateLimit,
    CfprBiosVfProcessorC1EVpProcessorC1E,
    CfprBiosVfProcessorC3ReportVpProcessorC3Report,
    CfprBiosVfProcessorC6ReportVpProcessorC6Report,
    CfprBiosVfProcessorC7ReportVpProcessorC7Report,
    CfprBiosVfProcessorCStateVpProcessorCState,
    CfprBiosVfProcessorEnergyConfigurationVpEnergyPerformance,
    CfprBiosVfProcessorEnergyConfigurationVpPowerTechnology,
    CfprBiosVfProcessorPrefetchConfigVpAdjacentCacheLinePrefetcher,
    CfprBiosVfProcessorPrefetchConfigVpDCUIPPrefetcher,
    CfprBiosVfProcessorPrefetchConfigVpDCUStreamerPrefetch,
    CfprBiosVfProcessorPrefetchConfigVpHardwarePrefetcher,
    CfprBiosVfQPILinkFrequencySelectVpQPILinkFrequencySelect,
    CfprBiosVfQuietBootVpQuietBoot,
    CfprBiosVfResumeOnACPowerLossVpResumeOnACPowerLoss,
    CfprBiosVfScrubPoliciesVpDemandScrub,
    CfprBiosVfScrubPoliciesVpPatrolScrub,
    CfprBiosVfSelectMemoryRASConfigurationVpSelectMemoryRASConf,
    CfprBiosVfSerialPortAEnableVpSerialPortAEnable,
    CfprBiosVfSparingModeVpSparingMode,
    CfprBiosVfSriovConfigVpSriov,
    CfprBiosVfTPMSupportVpTPMSupport,
    CfprBiosVfFPRMBootModeControlVpUEFIBootMode,
    CfprBiosVfFPRMBootOrderRuleControlVpFPRMBootOrderRule,
    CfprBiosVfUEFIOSUseLegacyVideoVpUEFIOSUseLegacyVideo,
    CfprBiosVfUSBBootConfigVpLegacyUSBSupport,
    CfprBiosVfUSBBootConfigVpMakeDeviceNonBootable,
    CfprBiosVfUSBConfigurationVpLegacyUSBSupport,
    CfprBiosVfUSBConfigurationVpXHCIMode,
    CfprBiosVfUSBFrontPanelAccessLockVpUSBFrontPanelLock,
    CfprBiosVfUSBPortConfigurationVpPort6064Emulation,
    CfprBiosVfUSBPortConfigurationVpUSBPortFront,
    CfprBiosVfUSBPortConfigurationVpUSBPortInternal,
    CfprBiosVfUSBPortConfigurationVpUSBPortKVM,
    CfprBiosVfUSBPortConfigurationVpUSBPortRear,
    CfprBiosVfUSBPortConfigurationVpUSBPortSDCard,
    CfprBiosVfUSBPortConfigurationVpUSBPortVMedia,
    CfprBiosVfUSBSysIdlePowerOptimizingSettingVpUSBIdlePowerOptimize,
    CfprBiosVfVGAPriorityVpVGAPriority,
    CfprPolicyPolicyOwner
        FROM CISCO-FIREPOWER-TC-MIB;

cfprBiosObjects MODULE-IDENTITY
    LAST-UPDATED    "202003100000Z"
    ORGANIZATION    "Cisco Systems Inc."
    CONTACT-INFO
        "Cisco Systems
        Customer Service
        
        Postal: 170 W Tasman Drive
        San Jose, CA  95134
        USA
        
        Tel: +1 800 553-NETS
        
        E-mail: firepower-mibs@cisco.com"
    DESCRIPTION
        "MIB representation of the Cisco Firepower
        BIOS management information model package"
    ::= { ciscoFirepowerMIBObjects 5 }

cfprBiosBOTTable OBJECT-TYPE
    SYNTAX           SEQUENCE OF CfprBiosBOTEntry
    MAX-ACCESS       not-accessible
    STATUS           current
    DESCRIPTION
        "Cisco Firepower bios:BOT managed object table"
    ::= { cfprBiosObjects 1 }

cfprBiosBOTEntry OBJECT-TYPE
    SYNTAX           CfprBiosBOTEntry
    MAX-ACCESS       not-accessible
    STATUS           current
    DESCRIPTION
        "Entry for the cfprBiosBOTTable table."
    INDEX { cfprBiosBOTInstanceId }
    ::= { cfprBiosBOTTable 1 }

CfprBiosBOTEntry ::= SEQUENCE {
    cfprBiosBOTInstanceId                                            CfprManagedObjectId,
    cfprBiosBOTDn                                                    CfprManagedObjectDn,
    cfprBiosBOTRn                                                    SnmpAdminString,
    cfprBiosBOTLastUpdate                                            DateAndTime
}

cfprBiosBOTInstanceId OBJECT-TYPE
    SYNTAX       CfprManagedObjectId
    MAX-ACCESS   not-accessible
    STATUS       current
    DESCRIPTION
        "Instance identifier of the managed object."
    ::= { cfprBiosBOTEntry 1 }

cfprBiosBOTDn OBJECT-TYPE
    SYNTAX       CfprManagedObjectDn
    MAX-ACCESS   read-only
    STATUS       current
    DESCRIPTION
        "Cisco Firepower bios:BOT:dn managed object property"
    ::= { cfprBiosBOTEntry 2 }

cfprBiosBOTRn OBJECT-TYPE
    SYNTAX       SnmpAdminString
    MAX-ACCESS   read-only
    STATUS       current
    DESCRIPTION
        "Cisco Firepower bios:BOT:rn managed object property"
    ::= { cfprBiosBOTEntry 3 }

cfprBiosBOTLastUpdate OBJECT-TYPE
    SYNTAX       DateAndTime
    MAX-ACCESS   read-only
    STATUS       current
    DESCRIPTION
        "Cisco Firepower bios:BOT:lastUpdate managed object property"
    ::= { cfprBiosBOTEntry 4 }

cfprBiosBootDevTable OBJECT-TYPE
    SYNTAX           SEQUENCE OF CfprBiosBootDevEntry
    MAX-ACCESS       not-accessible
    STATUS           current
    DESCRIPTION
        "Cisco Firepower bios:BootDev managed object table"
    ::= { cfprBiosObjects 2 }

cfprBiosBootDevEntry OBJECT-TYPE
    SYNTAX           CfprBiosBootDevEntry
    MAX-ACCESS       not-accessible
    STATUS           current
    DESCRIPTION
        "Entry for the cfprBiosBootDevTable table."
    INDEX { cfprBiosBootDevInstanceId }
    ::= { cfprBiosBootDevTable 1 }

CfprBiosBootDevEntry ::= SEQUENCE {
    cfprBiosBootDevInstanceId                                        CfprManagedObjectId,
    cfprBiosBootDevDn                                                CfprManagedObjectDn,
    cfprBiosBootDevRn                                                SnmpAdminString,
    cfprBiosBootDevDescr                                             SnmpAdminString,
    cfprBiosBootDevDeviceName                                        SnmpAdminString,
    cfprBiosBootDevErrValue                                          CfprBiosBootDevErrorCode,
    cfprBiosBootDevOrder                                             CfprBiosBootDevOrder
}

cfprBiosBootDevInstanceId OBJECT-TYPE
    SYNTAX       CfprManagedObjectId
    MAX-ACCESS   not-accessible
    STATUS       current
    DESCRIPTION
        "Instance identifier of the managed object."
    ::= { cfprBiosBootDevEntry 1 }

cfprBiosBootDevDn OBJECT-TYPE
    SYNTAX       CfprManagedObjectDn
    MAX-ACCESS   read-only
    STATUS       current
    DESCRIPTION
        "Cisco Firepower bios:BootDev:dn managed object property"
    ::= { cfprBiosBootDevEntry 2 }

cfprBiosBootDevRn OBJECT-TYPE
    SYNTAX       SnmpAdminString
    MAX-ACCESS   read-only
    STATUS       current
    DESCRIPTION
        "Cisco Firepower bios:BootDev:rn managed object property"
    ::= { cfprBiosBootDevEntry 3 }

cfprBiosBootDevDescr OBJECT-TYPE
    SYNTAX       SnmpAdminString
    MAX-ACCESS   read-only
    STATUS       current
    DESCRIPTION
        "Cisco Firepower bios:BootDev:descr managed object property"
    ::= { cfprBiosBootDevEntry 4 }

cfprBiosBootDevDeviceName OBJECT-TYPE
    SYNTAX       SnmpAdminString
    MAX-ACCESS   read-only
    STATUS       current
    DESCRIPTION
        "Cisco Firepower bios:BootDev:deviceName managed object property"
    ::= { cfprBiosBootDevEntry 5 }

cfprBiosBootDevErrValue OBJECT-TYPE
    SYNTAX       CfprBiosBootDevErrorCode
    MAX-ACCESS   read-only
    STATUS       current
    DESCRIPTION
        "Cisco Firepower bios:BootDev:errValue managed object property"
    ::= { cfprBiosBootDevEntry 6 }

cfprBiosBootDevOrder OBJECT-TYPE
    SYNTAX       CfprBiosBootDevOrder
    MAX-ACCESS   read-only
    STATUS       current
    DESCRIPTION
        "Cisco Firepower bios:BootDev:order managed object property"
    ::= { cfprBiosBootDevEntry 7 }

cfprBiosBootDevGrpTable OBJECT-TYPE
    SYNTAX           SEQUENCE OF CfprBiosBootDevGrpEntry
    MAX-ACCESS       not-accessible
    STATUS           current
    DESCRIPTION
        "Cisco Firepower bios:BootDevGrp managed object table"
    ::= { cfprBiosObjects 3 }

cfprBiosBootDevGrpEntry OBJECT-TYPE
    SYNTAX           CfprBiosBootDevGrpEntry
    MAX-ACCESS       not-accessible
    STATUS           current
    DESCRIPTION
        "Entry for the cfprBiosBootDevGrpTable table."
    INDEX { cfprBiosBootDevGrpInstanceId }
    ::= { cfprBiosBootDevGrpTable 1 }

CfprBiosBootDevGrpEntry ::= SEQUENCE {
    cfprBiosBootDevGrpInstanceId                                     CfprManagedObjectId,
    cfprBiosBootDevGrpDn                                             CfprManagedObjectDn,
    cfprBiosBootDevGrpRn                                             SnmpAdminString,
    cfprBiosBootDevGrpDescr                                          SnmpAdminString,
    cfprBiosBootDevGrpDeviceName                                     SnmpAdminString,
    cfprBiosBootDevGrpErrVal                                         CfprBiosBootDevErrorCode,
    cfprBiosBootDevGrpOrder                                          CfprBiosBootDevOrder,
    cfprBiosBootDevGrpType                                           CfprBiosBootDevGrpType
}

cfprBiosBootDevGrpInstanceId OBJECT-TYPE
    SYNTAX       CfprManagedObjectId
    MAX-ACCESS   not-accessible
    STATUS       current
    DESCRIPTION
        "Instance identifier of the managed object."
    ::= { cfprBiosBootDevGrpEntry 1 }

cfprBiosBootDevGrpDn OBJECT-TYPE
    SYNTAX       CfprManagedObjectDn
    MAX-ACCESS   read-only
    STATUS       current
    DESCRIPTION
        "Cisco Firepower bios:BootDevGrp:dn managed object property"
    ::= { cfprBiosBootDevGrpEntry 2 }

cfprBiosBootDevGrpRn OBJECT-TYPE
    SYNTAX       SnmpAdminString
    MAX-ACCESS   read-only
    STATUS       current
    DESCRIPTION
        "Cisco Firepower bios:BootDevGrp:rn managed object property"
    ::= { cfprBiosBootDevGrpEntry 3 }

cfprBiosBootDevGrpDescr OBJECT-TYPE
    SYNTAX       SnmpAdminString
    MAX-ACCESS   read-only
    STATUS       current
    DESCRIPTION
        "Cisco Firepower bios:BootDevGrp:descr managed object property"
    ::= { cfprBiosBootDevGrpEntry 4 }

cfprBiosBootDevGrpDeviceName OBJECT-TYPE
    SYNTAX       SnmpAdminString
    MAX-ACCESS   read-only
    STATUS       current
    DESCRIPTION
        "Cisco Firepower bios:BootDevGrp:deviceName managed
        object property"
    ::= { cfprBiosBootDevGrpEntry 5 }

cfprBiosBootDevGrpErrVal OBJECT-TYPE
    SYNTAX       CfprBiosBootDevErrorCode
    MAX-ACCESS   read-only
    STATUS       current
    DESCRIPTION
        "Cisco Firepower bios:BootDevGrp:errVal managed object property"
    ::= { cfprBiosBootDevGrpEntry 6 }

cfprBiosBootDevGrpOrder OBJECT-TYPE
    SYNTAX       CfprBiosBootDevOrder
    MAX-ACCESS   read-only
    STATUS       current
    DESCRIPTION
        "Cisco Firepower bios:BootDevGrp:order managed object property"
    ::= { cfprBiosBootDevGrpEntry 7 }

cfprBiosBootDevGrpType OBJECT-TYPE
    SYNTAX       CfprBiosBootDevGrpType
    MAX-ACCESS   read-only
    STATUS       current
    DESCRIPTION
        "Cisco Firepower bios:BootDevGrp:type managed object property"
    ::= { cfprBiosBootDevGrpEntry 8 }

cfprBiosFeatureRefTable OBJECT-TYPE
    SYNTAX           SEQUENCE OF CfprBiosFeatureRefEntry
    MAX-ACCESS       not-accessible
    STATUS           current
    DESCRIPTION
        "Cisco Firepower bios:FeatureRef managed object table"
    ::= { cfprBiosObjects 4 }

cfprBiosFeatureRefEntry OBJECT-TYPE
    SYNTAX           CfprBiosFeatureRefEntry
    MAX-ACCESS       not-accessible
    STATUS           current
    DESCRIPTION
        "Entry for the cfprBiosFeatureRefTable table."
    INDEX { cfprBiosFeatureRefInstanceId }
    ::= { cfprBiosFeatureRefTable 1 }

CfprBiosFeatureRefEntry ::= SEQUENCE {
    cfprBiosFeatureRefInstanceId                                     CfprManagedObjectId,
    cfprBiosFeatureRefDn                                             CfprManagedObjectDn,
    cfprBiosFeatureRefRn                                             SnmpAdminString,
    cfprBiosFeatureRefFtrMoClassName                                 SnmpAdminString,
    cfprBiosFeatureRefIsSupported                                    CfprBiosSupportedAction,
    cfprBiosFeatureRefName                                           SnmpAdminString
}

cfprBiosFeatureRefInstanceId OBJECT-TYPE
    SYNTAX       CfprManagedObjectId
    MAX-ACCESS   not-accessible
    STATUS       current
    DESCRIPTION
        "Instance identifier of the managed object."
    ::= { cfprBiosFeatureRefEntry 1 }

cfprBiosFeatureRefDn OBJECT-TYPE
    SYNTAX       CfprManagedObjectDn
    MAX-ACCESS   read-only
    STATUS       current
    DESCRIPTION
        "Cisco Firepower bios:FeatureRef:dn managed object property"
    ::= { cfprBiosFeatureRefEntry 2 }

cfprBiosFeatureRefRn OBJECT-TYPE
    SYNTAX       SnmpAdminString
    MAX-ACCESS   read-only
    STATUS       current
    DESCRIPTION
        "Cisco Firepower bios:FeatureRef:rn managed object property"
    ::= { cfprBiosFeatureRefEntry 3 }

cfprBiosFeatureRefFtrMoClassName OBJECT-TYPE
    SYNTAX       SnmpAdminString
    MAX-ACCESS   read-only
    STATUS       current
    DESCRIPTION
        "Cisco Firepower bios:FeatureRef:ftrMoClassName
        managed object property"
    ::= { cfprBiosFeatureRefEntry 4 }

cfprBiosFeatureRefIsSupported OBJECT-TYPE
    SYNTAX       CfprBiosSupportedAction
    MAX-ACCESS   read-only
    STATUS       current
    DESCRIPTION
        "Cisco Firepower bios:FeatureRef:isSupported managed
        object property"
    ::= { cfprBiosFeatureRefEntry 5 }

cfprBiosFeatureRefName OBJECT-TYPE
    SYNTAX       SnmpAdminString
    MAX-ACCESS   read-only
    STATUS       current
    DESCRIPTION
        "Cisco Firepower bios:FeatureRef:name managed object property"
    ::= { cfprBiosFeatureRefEntry 6 }

cfprBiosParameterRefTable OBJECT-TYPE
    SYNTAX           SEQUENCE OF CfprBiosParameterRefEntry
    MAX-ACCESS       not-accessible
    STATUS           current
    DESCRIPTION
        "Cisco Firepower bios:ParameterRef managed object table"
    ::= { cfprBiosObjects 5 }

cfprBiosParameterRefEntry OBJECT-TYPE
    SYNTAX           CfprBiosParameterRefEntry
    MAX-ACCESS       not-accessible
    STATUS           current
    DESCRIPTION
        "Entry for the cfprBiosParameterRefTable table."
    INDEX { cfprBiosParameterRefInstanceId }
    ::= { cfprBiosParameterRefTable 1 }

CfprBiosParameterRefEntry ::= SEQUENCE {
    cfprBiosParameterRefInstanceId                                   CfprManagedObjectId,
    cfprBiosParameterRefDn                                           CfprManagedObjectDn,
    cfprBiosParameterRefRn                                           SnmpAdminString,
    cfprBiosParameterRefIsSupported                                  CfprBiosSupportedAction,
    cfprBiosParameterRefName                                         SnmpAdminString,
    cfprBiosParameterRefPropertyName                                 SnmpAdminString
}

cfprBiosParameterRefInstanceId OBJECT-TYPE
    SYNTAX       CfprManagedObjectId
    MAX-ACCESS   not-accessible
    STATUS       current
    DESCRIPTION
        "Instance identifier of the managed object."
    ::= { cfprBiosParameterRefEntry 1 }

cfprBiosParameterRefDn OBJECT-TYPE
    SYNTAX       CfprManagedObjectDn
    MAX-ACCESS   read-only
    STATUS       current
    DESCRIPTION
        "Cisco Firepower bios:ParameterRef:dn managed object property"
    ::= { cfprBiosParameterRefEntry 2 }

cfprBiosParameterRefRn OBJECT-TYPE
    SYNTAX       SnmpAdminString
    MAX-ACCESS   read-only
    STATUS       current
    DESCRIPTION
        "Cisco Firepower bios:ParameterRef:rn managed object property"
    ::= { cfprBiosParameterRefEntry 3 }

cfprBiosParameterRefIsSupported OBJECT-TYPE
    SYNTAX       CfprBiosSupportedAction
    MAX-ACCESS   read-only
    STATUS       current
    DESCRIPTION
        "Cisco Firepower bios:ParameterRef:isSupported
        managed object property"
    ::= { cfprBiosParameterRefEntry 4 }

cfprBiosParameterRefName OBJECT-TYPE
    SYNTAX       SnmpAdminString
    MAX-ACCESS   read-only
    STATUS       current
    DESCRIPTION
        "Cisco Firepower bios:ParameterRef:name managed object property"
    ::= { cfprBiosParameterRefEntry 5 }

cfprBiosParameterRefPropertyName OBJECT-TYPE
    SYNTAX       SnmpAdminString
    MAX-ACCESS   read-only
    STATUS       current
    DESCRIPTION
        "Cisco Firepower bios:ParameterRef:propertyName
        managed object property"
    ::= { cfprBiosParameterRefEntry 6 }

cfprBiosRefTable OBJECT-TYPE
    SYNTAX           SEQUENCE OF CfprBiosRefEntry
    MAX-ACCESS       not-accessible
    STATUS           current
    DESCRIPTION
        "Cisco Firepower bios:Ref managed object table"
    ::= { cfprBiosObjects 6 }

cfprBiosRefEntry OBJECT-TYPE
    SYNTAX           CfprBiosRefEntry
    MAX-ACCESS       not-accessible
    STATUS           current
    DESCRIPTION
        "Entry for the cfprBiosRefTable table."
    INDEX { cfprBiosRefInstanceId }
    ::= { cfprBiosRefTable 1 }

CfprBiosRefEntry ::= SEQUENCE {
    cfprBiosRefInstanceId                                            CfprManagedObjectId,
    cfprBiosRefDn                                                    CfprManagedObjectDn,
    cfprBiosRefRn                                                    SnmpAdminString,
    cfprBiosRefIsSupported                                           CfprBiosSupportedAction
}

cfprBiosRefInstanceId OBJECT-TYPE
    SYNTAX       CfprManagedObjectId
    MAX-ACCESS   not-accessible
    STATUS       current
    DESCRIPTION
        "Instance identifier of the managed object."
    ::= { cfprBiosRefEntry 1 }

cfprBiosRefDn OBJECT-TYPE
    SYNTAX       CfprManagedObjectDn
    MAX-ACCESS   read-only
    STATUS       current
    DESCRIPTION
        "Cisco Firepower bios:Ref:dn managed object property"
    ::= { cfprBiosRefEntry 2 }

cfprBiosRefRn OBJECT-TYPE
    SYNTAX       SnmpAdminString
    MAX-ACCESS   read-only
    STATUS       current
    DESCRIPTION
        "Cisco Firepower bios:Ref:rn managed object property"
    ::= { cfprBiosRefEntry 3 }

cfprBiosRefIsSupported OBJECT-TYPE
    SYNTAX       CfprBiosSupportedAction
    MAX-ACCESS   read-only
    STATUS       current
    DESCRIPTION
        "Cisco Firepower bios:Ref:isSupported managed object property"
    ::= { cfprBiosRefEntry 4 }

cfprBiosSettingRefTable OBJECT-TYPE
    SYNTAX           SEQUENCE OF CfprBiosSettingRefEntry
    MAX-ACCESS       not-accessible
    STATUS           current
    DESCRIPTION
        "Cisco Firepower bios:SettingRef managed object table"
    ::= { cfprBiosObjects 7 }

cfprBiosSettingRefEntry OBJECT-TYPE
    SYNTAX           CfprBiosSettingRefEntry
    MAX-ACCESS       not-accessible
    STATUS           current
    DESCRIPTION
        "Entry for the cfprBiosSettingRefTable table."
    INDEX { cfprBiosSettingRefInstanceId }
    ::= { cfprBiosSettingRefTable 1 }

CfprBiosSettingRefEntry ::= SEQUENCE {
    cfprBiosSettingRefInstanceId                                     CfprManagedObjectId,
    cfprBiosSettingRefDn                                             CfprManagedObjectDn,
    cfprBiosSettingRefRn                                             SnmpAdminString,
    cfprBiosSettingRefConstantName                                   SnmpAdminString,
    cfprBiosSettingRefIsDefault                                      CfprBiosDefaultAction,
    cfprBiosSettingRefIsSupported                                    CfprBiosSupportedAction,
    cfprBiosSettingRefName                                           SnmpAdminString
}

cfprBiosSettingRefInstanceId OBJECT-TYPE
    SYNTAX       CfprManagedObjectId
    MAX-ACCESS   not-accessible
    STATUS       current
    DESCRIPTION
        "Instance identifier of the managed object."
    ::= { cfprBiosSettingRefEntry 1 }

cfprBiosSettingRefDn OBJECT-TYPE
    SYNTAX       CfprManagedObjectDn
    MAX-ACCESS   read-only
    STATUS       current
    DESCRIPTION
        "Cisco Firepower bios:SettingRef:dn managed object property"
    ::= { cfprBiosSettingRefEntry 2 }

cfprBiosSettingRefRn OBJECT-TYPE
    SYNTAX       SnmpAdminString
    MAX-ACCESS   read-only
    STATUS       current
    DESCRIPTION
        "Cisco Firepower bios:SettingRef:rn managed object property"
    ::= { cfprBiosSettingRefEntry 3 }

cfprBiosSettingRefConstantName OBJECT-TYPE
    SYNTAX       SnmpAdminString
    MAX-ACCESS   read-only
    STATUS       current
    DESCRIPTION
        "Cisco Firepower bios:SettingRef:constantName managed
        object property"
    ::= { cfprBiosSettingRefEntry 4 }

cfprBiosSettingRefIsDefault OBJECT-TYPE
    SYNTAX       CfprBiosDefaultAction
    MAX-ACCESS   read-only
    STATUS       current
    DESCRIPTION
        "Cisco Firepower bios:SettingRef:isDefault managed
        object property"
    ::= { cfprBiosSettingRefEntry 5 }

cfprBiosSettingRefIsSupported OBJECT-TYPE
    SYNTAX       CfprBiosSupportedAction
    MAX-ACCESS   read-only
    STATUS       current
    DESCRIPTION
        "Cisco Firepower bios:SettingRef:isSupported managed
        object property"
    ::= { cfprBiosSettingRefEntry 6 }

cfprBiosSettingRefName OBJECT-TYPE
    SYNTAX       SnmpAdminString
    MAX-ACCESS   read-only
    STATUS       current
    DESCRIPTION
        "Cisco Firepower bios:SettingRef:name managed object property"
    ::= { cfprBiosSettingRefEntry 7 }

cfprBiosSettingsTable OBJECT-TYPE
    SYNTAX           SEQUENCE OF CfprBiosSettingsEntry
    MAX-ACCESS       not-accessible
    STATUS           current
    DESCRIPTION
        "Cisco Firepower bios:Settings managed object table"
    ::= { cfprBiosObjects 8 }

cfprBiosSettingsEntry OBJECT-TYPE
    SYNTAX           CfprBiosSettingsEntry
    MAX-ACCESS       not-accessible
    STATUS           current
    DESCRIPTION
        "Entry for the cfprBiosSettingsTable table."
    INDEX { cfprBiosSettingsInstanceId }
    ::= { cfprBiosSettingsTable 1 }

CfprBiosSettingsEntry ::= SEQUENCE {
    cfprBiosSettingsInstanceId                                       CfprManagedObjectId,
    cfprBiosSettingsDn                                               CfprManagedObjectDn,
    cfprBiosSettingsRn                                               SnmpAdminString
}

cfprBiosSettingsInstanceId OBJECT-TYPE
    SYNTAX       CfprManagedObjectId
    MAX-ACCESS   not-accessible
    STATUS       current
    DESCRIPTION
        "Instance identifier of the managed object."
    ::= { cfprBiosSettingsEntry 1 }

cfprBiosSettingsDn OBJECT-TYPE
    SYNTAX       CfprManagedObjectDn
    MAX-ACCESS   read-only
    STATUS       current
    DESCRIPTION
        "Cisco Firepower bios:Settings:dn managed object property"
    ::= { cfprBiosSettingsEntry 2 }

cfprBiosSettingsRn OBJECT-TYPE
    SYNTAX       SnmpAdminString
    MAX-ACCESS   read-only
    STATUS       current
    DESCRIPTION
        "Cisco Firepower bios:Settings:rn managed object property"
    ::= { cfprBiosSettingsEntry 3 }

cfprBiosTokenFeatureGroupTable OBJECT-TYPE
    SYNTAX           SEQUENCE OF CfprBiosTokenFeatureGroupEntry
    MAX-ACCESS       not-accessible
    STATUS           current
    DESCRIPTION
        "Cisco Firepower bios:TokenFeatureGroup managed object table"
    ::= { cfprBiosObjects 79 }

cfprBiosTokenFeatureGroupEntry OBJECT-TYPE
    SYNTAX           CfprBiosTokenFeatureGroupEntry
    MAX-ACCESS       not-accessible
    STATUS           current
    DESCRIPTION
        "Entry for the cfprBiosTokenFeatureGroupTable table."
    INDEX { cfprBiosTokenFeatureGroupInstanceId }
    ::= { cfprBiosTokenFeatureGroupTable 1 }

CfprBiosTokenFeatureGroupEntry ::= SEQUENCE {
    cfprBiosTokenFeatureGroupInstanceId                              CfprManagedObjectId,
    cfprBiosTokenFeatureGroupDn                                      CfprManagedObjectDn,
    cfprBiosTokenFeatureGroupRn                                      SnmpAdminString,
    cfprBiosTokenFeatureGroupName                                    SnmpAdminString,
    cfprBiosTokenFeatureGroupSupportedByDefault                      CfprBiosSupportedAction
}

cfprBiosTokenFeatureGroupInstanceId OBJECT-TYPE
    SYNTAX       CfprManagedObjectId
    MAX-ACCESS   not-accessible
    STATUS       current
    DESCRIPTION
        "Instance identifier of the managed object."
    ::= { cfprBiosTokenFeatureGroupEntry 1 }

cfprBiosTokenFeatureGroupDn OBJECT-TYPE
    SYNTAX       CfprManagedObjectDn
    MAX-ACCESS   read-only
    STATUS       current
    DESCRIPTION
        "Cisco Firepower bios:TokenFeatureGroup:dn managed
        object property"
    ::= { cfprBiosTokenFeatureGroupEntry 2 }

cfprBiosTokenFeatureGroupRn OBJECT-TYPE
    SYNTAX       SnmpAdminString
    MAX-ACCESS   read-only
    STATUS       current
    DESCRIPTION
        "Cisco Firepower bios:TokenFeatureGroup:rn managed
        object property"
    ::= { cfprBiosTokenFeatureGroupEntry 3 }

cfprBiosTokenFeatureGroupName OBJECT-TYPE
    SYNTAX       SnmpAdminString
    MAX-ACCESS   read-only
    STATUS       current
    DESCRIPTION
        "Cisco Firepower bios:TokenFeatureGroup:name managed
        object property"
    ::= { cfprBiosTokenFeatureGroupEntry 4 }

cfprBiosTokenFeatureGroupSupportedByDefault OBJECT-TYPE
    SYNTAX       CfprBiosSupportedAction
    MAX-ACCESS   read-only
    STATUS       current
    DESCRIPTION
        "Cisco Firepower bios:TokenFeatureGroup:supportedByDefault
        managed object property"
    ::= { cfprBiosTokenFeatureGroupEntry 5 }

cfprBiosTokenParamTable OBJECT-TYPE
    SYNTAX           SEQUENCE OF CfprBiosTokenParamEntry
    MAX-ACCESS       not-accessible
    STATUS           current
    DESCRIPTION
        "Cisco Firepower bios:TokenParam managed object table"
    ::= { cfprBiosObjects 80 }

cfprBiosTokenParamEntry OBJECT-TYPE
    SYNTAX           CfprBiosTokenParamEntry
    MAX-ACCESS       not-accessible
    STATUS           current
    DESCRIPTION
        "Entry for the cfprBiosTokenParamTable table."
    INDEX { cfprBiosTokenParamInstanceId }
    ::= { cfprBiosTokenParamTable 1 }

CfprBiosTokenParamEntry ::= SEQUENCE {
    cfprBiosTokenParamInstanceId                                     CfprManagedObjectId,
    cfprBiosTokenParamDn                                             CfprManagedObjectDn,
    cfprBiosTokenParamRn                                             SnmpAdminString,
    cfprBiosTokenParamLegacyPropId                                   SnmpAdminString,
    cfprBiosTokenParamParamName                                      SnmpAdminString,
    cfprBiosTokenParamTargetTokenName                                SnmpAdminString,
    cfprBiosTokenParamUiGroupName                                    SnmpAdminString
}

cfprBiosTokenParamInstanceId OBJECT-TYPE
    SYNTAX       CfprManagedObjectId
    MAX-ACCESS   not-accessible
    STATUS       current
    DESCRIPTION
        "Instance identifier of the managed object."
    ::= { cfprBiosTokenParamEntry 1 }

cfprBiosTokenParamDn OBJECT-TYPE
    SYNTAX       CfprManagedObjectDn
    MAX-ACCESS   read-only
    STATUS       current
    DESCRIPTION
        "Cisco Firepower bios:TokenParam:dn managed object property"
    ::= { cfprBiosTokenParamEntry 2 }

cfprBiosTokenParamRn OBJECT-TYPE
    SYNTAX       SnmpAdminString
    MAX-ACCESS   read-only
    STATUS       current
    DESCRIPTION
        "Cisco Firepower bios:TokenParam:rn managed object property"
    ::= { cfprBiosTokenParamEntry 3 }

cfprBiosTokenParamLegacyPropId OBJECT-TYPE
    SYNTAX       SnmpAdminString
    MAX-ACCESS   read-only
    STATUS       current
    DESCRIPTION
        "Cisco Firepower bios:TokenParam:legacyPropId managed
        object property"
    ::= { cfprBiosTokenParamEntry 4 }

cfprBiosTokenParamParamName OBJECT-TYPE
    SYNTAX       SnmpAdminString
    MAX-ACCESS   read-only
    STATUS       current
    DESCRIPTION
        "Cisco Firepower bios:TokenParam:paramName managed
        object property"
    ::= { cfprBiosTokenParamEntry 5 }

cfprBiosTokenParamTargetTokenName OBJECT-TYPE
    SYNTAX       SnmpAdminString
    MAX-ACCESS   read-only
    STATUS       current
    DESCRIPTION
        "Cisco Firepower bios:TokenParam:targetTokenName
        managed object property"
    ::= { cfprBiosTokenParamEntry 6 }

cfprBiosTokenParamUiGroupName OBJECT-TYPE
    SYNTAX       SnmpAdminString
    MAX-ACCESS   read-only
    STATUS       current
    DESCRIPTION
        "Cisco Firepower bios:TokenParam:uiGroupName managed
        object property"
    ::= { cfprBiosTokenParamEntry 7 }

cfprBiosTokenSettingsTable OBJECT-TYPE
    SYNTAX           SEQUENCE OF CfprBiosTokenSettingsEntry
    MAX-ACCESS       not-accessible
    STATUS           current
    DESCRIPTION
        "Cisco Firepower bios:TokenSettings managed object table"
    ::= { cfprBiosObjects 81 }

cfprBiosTokenSettingsEntry OBJECT-TYPE
    SYNTAX           CfprBiosTokenSettingsEntry
    MAX-ACCESS       not-accessible
    STATUS           current
    DESCRIPTION
        "Entry for the cfprBiosTokenSettingsTable table."
    INDEX { cfprBiosTokenSettingsInstanceId }
    ::= { cfprBiosTokenSettingsTable 1 }

CfprBiosTokenSettingsEntry ::= SEQUENCE {
    cfprBiosTokenSettingsInstanceId                                  CfprManagedObjectId,
    cfprBiosTokenSettingsDn                                          CfprManagedObjectDn,
    cfprBiosTokenSettingsRn                                          SnmpAdminString,
    cfprBiosTokenSettingsBiosRetSettingName                          SnmpAdminString,
    cfprBiosTokenSettingsIsAssigned                                  TruthValue,
    cfprBiosTokenSettingsLegacyPropVal                               SnmpAdminString,
    cfprBiosTokenSettingsSettingsMoRn                                SnmpAdminString,
    cfprBiosTokenSettingsTargetTokenValue                            SnmpAdminString
}

cfprBiosTokenSettingsInstanceId OBJECT-TYPE
    SYNTAX       CfprManagedObjectId
    MAX-ACCESS   not-accessible
    STATUS       current
    DESCRIPTION
        "Instance identifier of the managed object."
    ::= { cfprBiosTokenSettingsEntry 1 }

cfprBiosTokenSettingsDn OBJECT-TYPE
    SYNTAX       CfprManagedObjectDn
    MAX-ACCESS   read-only
    STATUS       current
    DESCRIPTION
        "Cisco Firepower bios:TokenSettings:dn managed object property"
    ::= { cfprBiosTokenSettingsEntry 2 }

cfprBiosTokenSettingsRn OBJECT-TYPE
    SYNTAX       SnmpAdminString
    MAX-ACCESS   read-only
    STATUS       current
    DESCRIPTION
        "Cisco Firepower bios:TokenSettings:rn managed object property"
    ::= { cfprBiosTokenSettingsEntry 3 }

cfprBiosTokenSettingsBiosRetSettingName OBJECT-TYPE
    SYNTAX       SnmpAdminString
    MAX-ACCESS   read-only
    STATUS       current
    DESCRIPTION
        "Cisco Firepower bios:TokenSettings:biosRetSettingName
        managed object property"
    ::= { cfprBiosTokenSettingsEntry 4 }

cfprBiosTokenSettingsIsAssigned OBJECT-TYPE
    SYNTAX       TruthValue
    MAX-ACCESS   read-only
    STATUS       current
    DESCRIPTION
        "Cisco Firepower bios:TokenSettings:isAssigned
        managed object property"
    ::= { cfprBiosTokenSettingsEntry 5 }

cfprBiosTokenSettingsLegacyPropVal OBJECT-TYPE
    SYNTAX       SnmpAdminString
    MAX-ACCESS   read-only
    STATUS       current
    DESCRIPTION
        "Cisco Firepower bios:TokenSettings:legacyPropVal
        managed object property"
    ::= { cfprBiosTokenSettingsEntry 6 }

cfprBiosTokenSettingsSettingsMoRn OBJECT-TYPE
    SYNTAX       SnmpAdminString
    MAX-ACCESS   read-only
    STATUS       current
    DESCRIPTION
        "Cisco Firepower bios:TokenSettings:settingsMoRn
        managed object property"
    ::= { cfprBiosTokenSettingsEntry 7 }

cfprBiosTokenSettingsTargetTokenValue OBJECT-TYPE
    SYNTAX       SnmpAdminString
    MAX-ACCESS   read-only
    STATUS       current
    DESCRIPTION
        "Cisco Firepower bios:TokenSettings:targetTokenValue
        managed object property"
    ::= { cfprBiosTokenSettingsEntry 8 }

cfprBiosUnitTable OBJECT-TYPE
    SYNTAX           SEQUENCE OF CfprBiosUnitEntry
    MAX-ACCESS       not-accessible
    STATUS           current
    DESCRIPTION
        "Cisco Firepower bios:Unit managed object table"
    ::= { cfprBiosObjects 9 }

cfprBiosUnitEntry OBJECT-TYPE
    SYNTAX           CfprBiosUnitEntry
    MAX-ACCESS       not-accessible
    STATUS           current
    DESCRIPTION
        "Entry for the cfprBiosUnitTable table."
    INDEX { cfprBiosUnitInstanceId }
    ::= { cfprBiosUnitTable 1 }

CfprBiosUnitEntry ::= SEQUENCE {
    cfprBiosUnitInstanceId                                           CfprManagedObjectId,
    cfprBiosUnitDn                                                   CfprManagedObjectDn,
    cfprBiosUnitRn                                                   SnmpAdminString,
    cfprBiosUnitInitSeq                                              SnmpAdminString,
    cfprBiosUnitInitTs                                               DateAndTime,
    cfprBiosUnitModel                                                SnmpAdminString,
    cfprBiosUnitRevision                                             SnmpAdminString,
    cfprBiosUnitSerial                                               SnmpAdminString,
    cfprBiosUnitVendor                                               SnmpAdminString
}

cfprBiosUnitInstanceId OBJECT-TYPE
    SYNTAX       CfprManagedObjectId
    MAX-ACCESS   not-accessible
    STATUS       current
    DESCRIPTION
        "Instance identifier of the managed object."
    ::= { cfprBiosUnitEntry 1 }

cfprBiosUnitDn OBJECT-TYPE
    SYNTAX       CfprManagedObjectDn
    MAX-ACCESS   read-only
    STATUS       current
    DESCRIPTION
        "Cisco Firepower bios:Unit:dn managed object property"
    ::= { cfprBiosUnitEntry 2 }

cfprBiosUnitRn OBJECT-TYPE
    SYNTAX       SnmpAdminString
    MAX-ACCESS   read-only
    STATUS       current
    DESCRIPTION
        "Cisco Firepower bios:Unit:rn managed object property"
    ::= { cfprBiosUnitEntry 3 }

cfprBiosUnitInitSeq OBJECT-TYPE
    SYNTAX       SnmpAdminString
    MAX-ACCESS   read-only
    STATUS       current
    DESCRIPTION
        "Cisco Firepower bios:Unit:initSeq managed object property"
    ::= { cfprBiosUnitEntry 4 }

cfprBiosUnitInitTs OBJECT-TYPE
    SYNTAX       DateAndTime
    MAX-ACCESS   read-only
    STATUS       current
    DESCRIPTION
        "Cisco Firepower bios:Unit:initTs managed object property"
    ::= { cfprBiosUnitEntry 5 }

cfprBiosUnitModel OBJECT-TYPE
    SYNTAX       SnmpAdminString
    MAX-ACCESS   read-only
    STATUS       current
    DESCRIPTION
        "Cisco Firepower bios:Unit:model managed object property"
    ::= { cfprBiosUnitEntry 6 }

cfprBiosUnitRevision OBJECT-TYPE
    SYNTAX       SnmpAdminString
    MAX-ACCESS   read-only
    STATUS       current
    DESCRIPTION
        "Cisco Firepower bios:Unit:revision managed object property"
    ::= { cfprBiosUnitEntry 7 }

cfprBiosUnitSerial OBJECT-TYPE
    SYNTAX       SnmpAdminString
    MAX-ACCESS   read-only
    STATUS       current
    DESCRIPTION
        "Cisco Firepower bios:Unit:serial managed object property"
    ::= { cfprBiosUnitEntry 8 }

cfprBiosUnitVendor OBJECT-TYPE
    SYNTAX       SnmpAdminString
    MAX-ACCESS   read-only
    STATUS       current
    DESCRIPTION
        "Cisco Firepower bios:Unit:vendor managed object property"
    ::= { cfprBiosUnitEntry 9 }

cfprBiosVIdentityParamsTable OBJECT-TYPE
    SYNTAX           SEQUENCE OF CfprBiosVIdentityParamsEntry
    MAX-ACCESS       not-accessible
    STATUS           current
    DESCRIPTION
        "Cisco Firepower bios:VIdentityParams managed object table"
    ::= { cfprBiosObjects 10 }

cfprBiosVIdentityParamsEntry OBJECT-TYPE
    SYNTAX           CfprBiosVIdentityParamsEntry
    MAX-ACCESS       not-accessible
    STATUS           current
    DESCRIPTION
        "Entry for the cfprBiosVIdentityParamsTable table."
    INDEX { cfprBiosVIdentityParamsInstanceId }
    ::= { cfprBiosVIdentityParamsTable 1 }

CfprBiosVIdentityParamsEntry ::= SEQUENCE {
    cfprBiosVIdentityParamsInstanceId                                CfprManagedObjectId,
    cfprBiosVIdentityParamsDn                                        CfprManagedObjectDn,
    cfprBiosVIdentityParamsRn                                        SnmpAdminString,
    cfprBiosVIdentityParamsLsServerName                              SnmpAdminString,
    cfprBiosVIdentityParamsLsServerTmplName                          SnmpAdminString,
    cfprBiosVIdentityParamsSysName                                   SnmpAdminString
}

cfprBiosVIdentityParamsInstanceId OBJECT-TYPE
    SYNTAX       CfprManagedObjectId
    MAX-ACCESS   not-accessible
    STATUS       current
    DESCRIPTION
        "Instance identifier of the managed object."
    ::= { cfprBiosVIdentityParamsEntry 1 }

cfprBiosVIdentityParamsDn OBJECT-TYPE
    SYNTAX       CfprManagedObjectDn
    MAX-ACCESS   read-only
    STATUS       current
    DESCRIPTION
        "Cisco Firepower bios:VIdentityParams:dn managed object property"
    ::= { cfprBiosVIdentityParamsEntry 2 }

cfprBiosVIdentityParamsRn OBJECT-TYPE
    SYNTAX       SnmpAdminString
    MAX-ACCESS   read-only
    STATUS       current
    DESCRIPTION
        "Cisco Firepower bios:VIdentityParams:rn managed object property"
    ::= { cfprBiosVIdentityParamsEntry 3 }

cfprBiosVIdentityParamsLsServerName OBJECT-TYPE
    SYNTAX       SnmpAdminString
    MAX-ACCESS   read-only
    STATUS       current
    DESCRIPTION
        "Cisco Firepower bios:VIdentityParams:lsServerName
        managed object property"
    ::= { cfprBiosVIdentityParamsEntry 4 }

cfprBiosVIdentityParamsLsServerTmplName OBJECT-TYPE
    SYNTAX       SnmpAdminString
    MAX-ACCESS   read-only
    STATUS       current
    DESCRIPTION
        "Cisco Firepower bios:VIdentityParams:lsServerTmplName
        managed object property"
    ::= { cfprBiosVIdentityParamsEntry 5 }

cfprBiosVIdentityParamsSysName OBJECT-TYPE
    SYNTAX       SnmpAdminString
    MAX-ACCESS   read-only
    STATUS       current
    DESCRIPTION
        "Cisco Firepower bios:VIdentityParams:sysName managed
        object property"
    ::= { cfprBiosVIdentityParamsEntry 6 }

cfprBiosVProfileTable OBJECT-TYPE
    SYNTAX           SEQUENCE OF CfprBiosVProfileEntry
    MAX-ACCESS       not-accessible
    STATUS           current
    DESCRIPTION
        "Cisco Firepower bios:VProfile managed object table"
    ::= { cfprBiosObjects 11 }

cfprBiosVProfileEntry OBJECT-TYPE
    SYNTAX           CfprBiosVProfileEntry
    MAX-ACCESS       not-accessible
    STATUS           current
    DESCRIPTION
        "Entry for the cfprBiosVProfileTable table."
    INDEX { cfprBiosVProfileInstanceId }
    ::= { cfprBiosVProfileTable 1 }

CfprBiosVProfileEntry ::= SEQUENCE {
    cfprBiosVProfileInstanceId                                       CfprManagedObjectId,
    cfprBiosVProfileDn                                               CfprManagedObjectDn,
    cfprBiosVProfileRn                                               SnmpAdminString,
    cfprBiosVProfileDescr                                            SnmpAdminString,
    cfprBiosVProfileIntId                                            SnmpAdminString,
    cfprBiosVProfileName                                             SnmpAdminString,
    cfprBiosVProfilePolicyLevel                                      Gauge32,
    cfprBiosVProfilePolicyOwner                                      CfprPolicyPolicyOwner,
    cfprBiosVProfileRebootOnUpdate                                   TruthValue
}

cfprBiosVProfileInstanceId OBJECT-TYPE
    SYNTAX       CfprManagedObjectId
    MAX-ACCESS   not-accessible
    STATUS       current
    DESCRIPTION
        "Instance identifier of the managed object."
    ::= { cfprBiosVProfileEntry 1 }

cfprBiosVProfileDn OBJECT-TYPE
    SYNTAX       CfprManagedObjectDn
    MAX-ACCESS   read-only
    STATUS       current
    DESCRIPTION
        "Cisco Firepower bios:VProfile:dn managed object property"
    ::= { cfprBiosVProfileEntry 2 }

cfprBiosVProfileRn OBJECT-TYPE
    SYNTAX       SnmpAdminString
    MAX-ACCESS   read-only
    STATUS       current
    DESCRIPTION
        "Cisco Firepower bios:VProfile:rn managed object property"
    ::= { cfprBiosVProfileEntry 3 }

cfprBiosVProfileDescr OBJECT-TYPE
    SYNTAX       SnmpAdminString
    MAX-ACCESS   read-only
    STATUS       current
    DESCRIPTION
        "Cisco Firepower bios:VProfile:descr managed object property"
    ::= { cfprBiosVProfileEntry 4 }

cfprBiosVProfileIntId OBJECT-TYPE
    SYNTAX       SnmpAdminString
    MAX-ACCESS   read-only
    STATUS       current
    DESCRIPTION
        "Cisco Firepower bios:VProfile:intId managed object property"
    ::= { cfprBiosVProfileEntry 5 }

cfprBiosVProfileName OBJECT-TYPE
    SYNTAX       SnmpAdminString
    MAX-ACCESS   read-only
    STATUS       current
    DESCRIPTION
        "Cisco Firepower bios:VProfile:name managed object property"
    ::= { cfprBiosVProfileEntry 6 }

cfprBiosVProfilePolicyLevel OBJECT-TYPE
    SYNTAX       Gauge32
    MAX-ACCESS   read-only
    STATUS       current
    DESCRIPTION
        "Cisco Firepower bios:VProfile:policyLevel managed
        object property"
    ::= { cfprBiosVProfileEntry 7 }

cfprBiosVProfilePolicyOwner OBJECT-TYPE
    SYNTAX       CfprPolicyPolicyOwner
    MAX-ACCESS   read-only
    STATUS       current
    DESCRIPTION
        "Cisco Firepower bios:VProfile:policyOwner managed
        object property"
    ::= { cfprBiosVProfileEntry 8 }

cfprBiosVProfileRebootOnUpdate OBJECT-TYPE
    SYNTAX       TruthValue
    MAX-ACCESS   read-only
    STATUS       current
    DESCRIPTION
        "Cisco Firepower bios:VProfile:rebootOnUpdate managed
        object property"
    ::= { cfprBiosVProfileEntry 9 }

cfprBiosVfACPI10SupportTable OBJECT-TYPE
    SYNTAX           SEQUENCE OF CfprBiosVfACPI10SupportEntry
    MAX-ACCESS       not-accessible
    STATUS           current
    DESCRIPTION
        "Cisco Firepower bios:VfACPI10Support managed object table"
    ::= { cfprBiosObjects 12 }

cfprBiosVfACPI10SupportEntry OBJECT-TYPE
    SYNTAX           CfprBiosVfACPI10SupportEntry
    MAX-ACCESS       not-accessible
    STATUS           current
    DESCRIPTION
        "Entry for the cfprBiosVfACPI10SupportTable table."
    INDEX { cfprBiosVfACPI10SupportInstanceId }
    ::= { cfprBiosVfACPI10SupportTable 1 }

CfprBiosVfACPI10SupportEntry ::= SEQUENCE {
    cfprBiosVfACPI10SupportInstanceId                                CfprManagedObjectId,
    cfprBiosVfACPI10SupportDn                                        CfprManagedObjectDn,
    cfprBiosVfACPI10SupportRn                                        SnmpAdminString,
    cfprBiosVfACPI10SupportVpACPI10Support                           CfprBiosVfACPI10SupportVpACPI10Support,
    cfprBiosVfACPI10SupportSupportedByDefault                        CfprBiosSupportedAction
}

cfprBiosVfACPI10SupportInstanceId OBJECT-TYPE
    SYNTAX       CfprManagedObjectId
    MAX-ACCESS   not-accessible
    STATUS       current
    DESCRIPTION
        "Instance identifier of the managed object."
    ::= { cfprBiosVfACPI10SupportEntry 1 }

cfprBiosVfACPI10SupportDn OBJECT-TYPE
    SYNTAX       CfprManagedObjectDn
    MAX-ACCESS   read-only
    STATUS       current
    DESCRIPTION
        "Cisco Firepower bios:VfACPI10Support:dn managed object property"
    ::= { cfprBiosVfACPI10SupportEntry 2 }

cfprBiosVfACPI10SupportRn OBJECT-TYPE
    SYNTAX       SnmpAdminString
    MAX-ACCESS   read-only
    STATUS       current
    DESCRIPTION
        "Cisco Firepower bios:VfACPI10Support:rn managed object property"
    ::= { cfprBiosVfACPI10SupportEntry 3 }

cfprBiosVfACPI10SupportVpACPI10Support OBJECT-TYPE
    SYNTAX       CfprBiosVfACPI10SupportVpACPI10Support
    MAX-ACCESS   read-only
    STATUS       current
    DESCRIPTION
        "Cisco Firepower bios:VfACPI10Support:vpACPI10Support
        managed object property"
    ::= { cfprBiosVfACPI10SupportEntry 4 }

cfprBiosVfACPI10SupportSupportedByDefault OBJECT-TYPE
    SYNTAX       CfprBiosSupportedAction
    MAX-ACCESS   read-only
    STATUS       current
    DESCRIPTION
        "Cisco Firepower bios:VfACPI10Support:supportedByDefault
        managed object property"
    ::= { cfprBiosVfACPI10SupportEntry 5 }

cfprBiosVfAllUSBDevicesTable OBJECT-TYPE
    SYNTAX           SEQUENCE OF CfprBiosVfAllUSBDevicesEntry
    MAX-ACCESS       not-accessible
    STATUS           current
    DESCRIPTION
        "Cisco Firepower bios:VfAllUSBDevices managed object table"
    ::= { cfprBiosObjects 13 }

cfprBiosVfAllUSBDevicesEntry OBJECT-TYPE
    SYNTAX           CfprBiosVfAllUSBDevicesEntry
    MAX-ACCESS       not-accessible
    STATUS           current
    DESCRIPTION
        "Entry for the cfprBiosVfAllUSBDevicesTable table."
    INDEX { cfprBiosVfAllUSBDevicesInstanceId }
    ::= { cfprBiosVfAllUSBDevicesTable 1 }

CfprBiosVfAllUSBDevicesEntry ::= SEQUENCE {
    cfprBiosVfAllUSBDevicesInstanceId                                CfprManagedObjectId,
    cfprBiosVfAllUSBDevicesDn                                        CfprManagedObjectDn,
    cfprBiosVfAllUSBDevicesRn                                        SnmpAdminString,
    cfprBiosVfAllUSBDevicesVpAllUSBDevices                           CfprBiosVfAllUSBDevicesVpAllUSBDevices,
    cfprBiosVfAllUSBDevicesSupportedByDefault                        CfprBiosSupportedAction
}

cfprBiosVfAllUSBDevicesInstanceId OBJECT-TYPE
    SYNTAX       CfprManagedObjectId
    MAX-ACCESS   not-accessible
    STATUS       current
    DESCRIPTION
        "Instance identifier of the managed object."
    ::= { cfprBiosVfAllUSBDevicesEntry 1 }

cfprBiosVfAllUSBDevicesDn OBJECT-TYPE
    SYNTAX       CfprManagedObjectDn
    MAX-ACCESS   read-only
    STATUS       current
    DESCRIPTION
        "Cisco Firepower bios:VfAllUSBDevices:dn managed object property"
    ::= { cfprBiosVfAllUSBDevicesEntry 2 }

cfprBiosVfAllUSBDevicesRn OBJECT-TYPE
    SYNTAX       SnmpAdminString
    MAX-ACCESS   read-only
    STATUS       current
    DESCRIPTION
        "Cisco Firepower bios:VfAllUSBDevices:rn managed object property"
    ::= { cfprBiosVfAllUSBDevicesEntry 3 }

cfprBiosVfAllUSBDevicesVpAllUSBDevices OBJECT-TYPE
    SYNTAX       CfprBiosVfAllUSBDevicesVpAllUSBDevices
    MAX-ACCESS   read-only
    STATUS       current
    DESCRIPTION
        "Cisco Firepower bios:VfAllUSBDevices:vpAllUSBDevices
        managed object property"
    ::= { cfprBiosVfAllUSBDevicesEntry 4 }

cfprBiosVfAllUSBDevicesSupportedByDefault OBJECT-TYPE
    SYNTAX       CfprBiosSupportedAction
    MAX-ACCESS   read-only
    STATUS       current
    DESCRIPTION
        "Cisco Firepower bios:VfAllUSBDevices:supportedByDefault
        managed object property"
    ::= { cfprBiosVfAllUSBDevicesEntry 5 }

cfprBiosVfAltitudeTable OBJECT-TYPE
    SYNTAX           SEQUENCE OF CfprBiosVfAltitudeEntry
    MAX-ACCESS       not-accessible
    STATUS           current
    DESCRIPTION
        "Cisco Firepower bios:VfAltitude managed object table"
    ::= { cfprBiosObjects 14 }

cfprBiosVfAltitudeEntry OBJECT-TYPE
    SYNTAX           CfprBiosVfAltitudeEntry
    MAX-ACCESS       not-accessible
    STATUS           current
    DESCRIPTION
        "Entry for the cfprBiosVfAltitudeTable table."
    INDEX { cfprBiosVfAltitudeInstanceId }
    ::= { cfprBiosVfAltitudeTable 1 }

CfprBiosVfAltitudeEntry ::= SEQUENCE {
    cfprBiosVfAltitudeInstanceId                                     CfprManagedObjectId,
    cfprBiosVfAltitudeDn                                             CfprManagedObjectDn,
    cfprBiosVfAltitudeRn                                             SnmpAdminString,
    cfprBiosVfAltitudeVpAltitude                                     CfprBiosVfAltitudeVpAltitude,
    cfprBiosVfAltitudeSupportedByDefault                             CfprBiosSupportedAction
}

cfprBiosVfAltitudeInstanceId OBJECT-TYPE
    SYNTAX       CfprManagedObjectId
    MAX-ACCESS   not-accessible
    STATUS       current
    DESCRIPTION
        "Instance identifier of the managed object."
    ::= { cfprBiosVfAltitudeEntry 1 }

cfprBiosVfAltitudeDn OBJECT-TYPE
    SYNTAX       CfprManagedObjectDn
    MAX-ACCESS   read-only
    STATUS       current
    DESCRIPTION
        "Cisco Firepower bios:VfAltitude:dn managed object property"
    ::= { cfprBiosVfAltitudeEntry 2 }

cfprBiosVfAltitudeRn OBJECT-TYPE
    SYNTAX       SnmpAdminString
    MAX-ACCESS   read-only
    STATUS       current
    DESCRIPTION
        "Cisco Firepower bios:VfAltitude:rn managed object property"
    ::= { cfprBiosVfAltitudeEntry 3 }

cfprBiosVfAltitudeVpAltitude OBJECT-TYPE
    SYNTAX       CfprBiosVfAltitudeVpAltitude
    MAX-ACCESS   read-only
    STATUS       current
    DESCRIPTION
        "Cisco Firepower bios:VfAltitude:vpAltitude managed
        object property"
    ::= { cfprBiosVfAltitudeEntry 4 }

cfprBiosVfAltitudeSupportedByDefault OBJECT-TYPE
    SYNTAX       CfprBiosSupportedAction
    MAX-ACCESS   read-only
    STATUS       current
    DESCRIPTION
        "Cisco Firepower bios:VfAltitude:supportedByDefault
        managed object property"
    ::= { cfprBiosVfAltitudeEntry 5 }

cfprBiosVfAssertNMIOnPERRTable OBJECT-TYPE
    SYNTAX           SEQUENCE OF CfprBiosVfAssertNMIOnPERREntry
    MAX-ACCESS       not-accessible
    STATUS           current
    DESCRIPTION
        "Cisco Firepower bios:VfAssertNMIOnPERR managed object table"
    ::= { cfprBiosObjects 15 }

cfprBiosVfAssertNMIOnPERREntry OBJECT-TYPE
    SYNTAX           CfprBiosVfAssertNMIOnPERREntry
    MAX-ACCESS       not-accessible
    STATUS           current
    DESCRIPTION
        "Entry for the cfprBiosVfAssertNMIOnPERRTable table."
    INDEX { cfprBiosVfAssertNMIOnPERRInstanceId }
    ::= { cfprBiosVfAssertNMIOnPERRTable 1 }

CfprBiosVfAssertNMIOnPERREntry ::= SEQUENCE {
    cfprBiosVfAssertNMIOnPERRInstanceId                              CfprManagedObjectId,
    cfprBiosVfAssertNMIOnPERRDn                                      CfprManagedObjectDn,
    cfprBiosVfAssertNMIOnPERRRn                                      SnmpAdminString,
    cfprBiosVfAssertNMIOnPERRVpAssertNMIOnPERR                       CfprBiosVfAssertNMIOnPERRVpAssertNMIOnPERR,
    cfprBiosVfAssertNMIOnPERRSupportedByDefault                      CfprBiosSupportedAction
}

cfprBiosVfAssertNMIOnPERRInstanceId OBJECT-TYPE
    SYNTAX       CfprManagedObjectId
    MAX-ACCESS   not-accessible
    STATUS       current
    DESCRIPTION
        "Instance identifier of the managed object."
    ::= { cfprBiosVfAssertNMIOnPERREntry 1 }

cfprBiosVfAssertNMIOnPERRDn OBJECT-TYPE
    SYNTAX       CfprManagedObjectDn
    MAX-ACCESS   read-only
    STATUS       current
    DESCRIPTION
        "Cisco Firepower bios:VfAssertNMIOnPERR:dn managed
        object property"
    ::= { cfprBiosVfAssertNMIOnPERREntry 2 }

cfprBiosVfAssertNMIOnPERRRn OBJECT-TYPE
    SYNTAX       SnmpAdminString
    MAX-ACCESS   read-only
    STATUS       current
    DESCRIPTION
        "Cisco Firepower bios:VfAssertNMIOnPERR:rn managed
        object property"
    ::= { cfprBiosVfAssertNMIOnPERREntry 3 }

cfprBiosVfAssertNMIOnPERRVpAssertNMIOnPERR OBJECT-TYPE
    SYNTAX       CfprBiosVfAssertNMIOnPERRVpAssertNMIOnPERR
    MAX-ACCESS   read-only
    STATUS       current
    DESCRIPTION
        "Cisco Firepower bios:VfAssertNMIOnPERR:vpAssertNMIOnPERR
        managed object property"
    ::= { cfprBiosVfAssertNMIOnPERREntry 4 }

cfprBiosVfAssertNMIOnPERRSupportedByDefault OBJECT-TYPE
    SYNTAX       CfprBiosSupportedAction
    MAX-ACCESS   read-only
    STATUS       current
    DESCRIPTION
        "Cisco Firepower bios:VfAssertNMIOnPERR:supportedByDefault
        managed object property"
    ::= { cfprBiosVfAssertNMIOnPERREntry 5 }

cfprBiosVfAssertNMIOnSERRTable OBJECT-TYPE
    SYNTAX           SEQUENCE OF CfprBiosVfAssertNMIOnSERREntry
    MAX-ACCESS       not-accessible
    STATUS           current
    DESCRIPTION
        "Cisco Firepower bios:VfAssertNMIOnSERR managed object table"
    ::= { cfprBiosObjects 16 }

cfprBiosVfAssertNMIOnSERREntry OBJECT-TYPE
    SYNTAX           CfprBiosVfAssertNMIOnSERREntry
    MAX-ACCESS       not-accessible
    STATUS           current
    DESCRIPTION
        "Entry for the cfprBiosVfAssertNMIOnSERRTable table."
    INDEX { cfprBiosVfAssertNMIOnSERRInstanceId }
    ::= { cfprBiosVfAssertNMIOnSERRTable 1 }

CfprBiosVfAssertNMIOnSERREntry ::= SEQUENCE {
    cfprBiosVfAssertNMIOnSERRInstanceId                              CfprManagedObjectId,
    cfprBiosVfAssertNMIOnSERRDn                                      CfprManagedObjectDn,
    cfprBiosVfAssertNMIOnSERRRn                                      SnmpAdminString,
    cfprBiosVfAssertNMIOnSERRVpAssertNMIOnSERR                       CfprBiosVfAssertNMIOnSERRVpAssertNMIOnSERR,
    cfprBiosVfAssertNMIOnSERRSupportedByDefault                      CfprBiosSupportedAction
}

cfprBiosVfAssertNMIOnSERRInstanceId OBJECT-TYPE
    SYNTAX       CfprManagedObjectId
    MAX-ACCESS   not-accessible
    STATUS       current
    DESCRIPTION
        "Instance identifier of the managed object."
    ::= { cfprBiosVfAssertNMIOnSERREntry 1 }

cfprBiosVfAssertNMIOnSERRDn OBJECT-TYPE
    SYNTAX       CfprManagedObjectDn
    MAX-ACCESS   read-only
    STATUS       current
    DESCRIPTION
        "Cisco Firepower bios:VfAssertNMIOnSERR:dn managed
        object property"
    ::= { cfprBiosVfAssertNMIOnSERREntry 2 }

cfprBiosVfAssertNMIOnSERRRn OBJECT-TYPE
    SYNTAX       SnmpAdminString
    MAX-ACCESS   read-only
    STATUS       current
    DESCRIPTION
        "Cisco Firepower bios:VfAssertNMIOnSERR:rn managed
        object property"
    ::= { cfprBiosVfAssertNMIOnSERREntry 3 }

cfprBiosVfAssertNMIOnSERRVpAssertNMIOnSERR OBJECT-TYPE
    SYNTAX       CfprBiosVfAssertNMIOnSERRVpAssertNMIOnSERR
    MAX-ACCESS   read-only
    STATUS       current
    DESCRIPTION
        "Cisco Firepower bios:VfAssertNMIOnSERR:vpAssertNMIOnSERR
        managed object property"
    ::= { cfprBiosVfAssertNMIOnSERREntry 4 }

cfprBiosVfAssertNMIOnSERRSupportedByDefault OBJECT-TYPE
    SYNTAX       CfprBiosSupportedAction
    MAX-ACCESS   read-only
    STATUS       current
    DESCRIPTION
        "Cisco Firepower bios:VfAssertNMIOnSERR:supportedByDefault
        managed object property"
    ::= { cfprBiosVfAssertNMIOnSERREntry 5 }

cfprBiosVfBootOptionRetryTable OBJECT-TYPE
    SYNTAX           SEQUENCE OF CfprBiosVfBootOptionRetryEntry
    MAX-ACCESS       not-accessible
    STATUS           current
    DESCRIPTION
        "Cisco Firepower bios:VfBootOptionRetry managed object table"
    ::= { cfprBiosObjects 17 }

cfprBiosVfBootOptionRetryEntry OBJECT-TYPE
    SYNTAX           CfprBiosVfBootOptionRetryEntry
    MAX-ACCESS       not-accessible
    STATUS           current
    DESCRIPTION
        "Entry for the cfprBiosVfBootOptionRetryTable table."
    INDEX { cfprBiosVfBootOptionRetryInstanceId }
    ::= { cfprBiosVfBootOptionRetryTable 1 }

CfprBiosVfBootOptionRetryEntry ::= SEQUENCE {
    cfprBiosVfBootOptionRetryInstanceId                              CfprManagedObjectId,
    cfprBiosVfBootOptionRetryDn                                      CfprManagedObjectDn,
    cfprBiosVfBootOptionRetryRn                                      SnmpAdminString,
    cfprBiosVfBootOptionRetryVpBootOptionRetry                       CfprBiosVfBootOptionRetryVpBootOptionRetry,
    cfprBiosVfBootOptionRetrySupportedByDefault                      CfprBiosSupportedAction
}

cfprBiosVfBootOptionRetryInstanceId OBJECT-TYPE
    SYNTAX       CfprManagedObjectId
    MAX-ACCESS   not-accessible
    STATUS       current
    DESCRIPTION
        "Instance identifier of the managed object."
    ::= { cfprBiosVfBootOptionRetryEntry 1 }

cfprBiosVfBootOptionRetryDn OBJECT-TYPE
    SYNTAX       CfprManagedObjectDn
    MAX-ACCESS   read-only
    STATUS       current
    DESCRIPTION
        "Cisco Firepower bios:VfBootOptionRetry:dn managed
        object property"
    ::= { cfprBiosVfBootOptionRetryEntry 2 }

cfprBiosVfBootOptionRetryRn OBJECT-TYPE
    SYNTAX       SnmpAdminString
    MAX-ACCESS   read-only
    STATUS       current
    DESCRIPTION
        "Cisco Firepower bios:VfBootOptionRetry:rn managed
        object property"
    ::= { cfprBiosVfBootOptionRetryEntry 3 }

cfprBiosVfBootOptionRetryVpBootOptionRetry OBJECT-TYPE
    SYNTAX       CfprBiosVfBootOptionRetryVpBootOptionRetry
    MAX-ACCESS   read-only
    STATUS       current
    DESCRIPTION
        "Cisco Firepower bios:VfBootOptionRetry:vpBootOptionRetry
        managed object property"
    ::= { cfprBiosVfBootOptionRetryEntry 4 }

cfprBiosVfBootOptionRetrySupportedByDefault OBJECT-TYPE
    SYNTAX       CfprBiosSupportedAction
    MAX-ACCESS   read-only
    STATUS       current
    DESCRIPTION
        "Cisco Firepower bios:VfBootOptionRetry:supportedByDefault
        managed object property"
    ::= { cfprBiosVfBootOptionRetryEntry 5 }

cfprBiosVfCPUPerformanceTable OBJECT-TYPE
    SYNTAX           SEQUENCE OF CfprBiosVfCPUPerformanceEntry
    MAX-ACCESS       not-accessible
    STATUS           current
    DESCRIPTION
        "Cisco Firepower bios:VfCPUPerformance managed object table"
    ::= { cfprBiosObjects 18 }

cfprBiosVfCPUPerformanceEntry OBJECT-TYPE
    SYNTAX           CfprBiosVfCPUPerformanceEntry
    MAX-ACCESS       not-accessible
    STATUS           current
    DESCRIPTION
        "Entry for the cfprBiosVfCPUPerformanceTable table."
    INDEX { cfprBiosVfCPUPerformanceInstanceId }
    ::= { cfprBiosVfCPUPerformanceTable 1 }

CfprBiosVfCPUPerformanceEntry ::= SEQUENCE {
    cfprBiosVfCPUPerformanceInstanceId                               CfprManagedObjectId,
    cfprBiosVfCPUPerformanceDn                                       CfprManagedObjectDn,
    cfprBiosVfCPUPerformanceRn                                       SnmpAdminString,
    cfprBiosVfCPUPerformanceVpCPUPerformance                         CfprBiosVfCPUPerformanceVpCPUPerformance,
    cfprBiosVfCPUPerformanceSupportedByDefault                       CfprBiosSupportedAction
}

cfprBiosVfCPUPerformanceInstanceId OBJECT-TYPE
    SYNTAX       CfprManagedObjectId
    MAX-ACCESS   not-accessible
    STATUS       current
    DESCRIPTION
        "Instance identifier of the managed object."
    ::= { cfprBiosVfCPUPerformanceEntry 1 }

cfprBiosVfCPUPerformanceDn OBJECT-TYPE
    SYNTAX       CfprManagedObjectDn
    MAX-ACCESS   read-only
    STATUS       current
    DESCRIPTION
        "Cisco Firepower bios:VfCPUPerformance:dn managed object property"
    ::= { cfprBiosVfCPUPerformanceEntry 2 }

cfprBiosVfCPUPerformanceRn OBJECT-TYPE
    SYNTAX       SnmpAdminString
    MAX-ACCESS   read-only
    STATUS       current
    DESCRIPTION
        "Cisco Firepower bios:VfCPUPerformance:rn managed object property"
    ::= { cfprBiosVfCPUPerformanceEntry 3 }

cfprBiosVfCPUPerformanceVpCPUPerformance OBJECT-TYPE
    SYNTAX       CfprBiosVfCPUPerformanceVpCPUPerformance
    MAX-ACCESS   read-only
    STATUS       current
    DESCRIPTION
        "Cisco Firepower bios:VfCPUPerformance:vpCPUPerformance
        managed object property"
    ::= { cfprBiosVfCPUPerformanceEntry 4 }

cfprBiosVfCPUPerformanceSupportedByDefault OBJECT-TYPE
    SYNTAX       CfprBiosSupportedAction
    MAX-ACCESS   read-only
    STATUS       current
    DESCRIPTION
        "Cisco Firepower bios:VfCPUPerformance:supportedByDefault
        managed object property"
    ::= { cfprBiosVfCPUPerformanceEntry 5 }

cfprBiosVfConsoleRedirectionTable OBJECT-TYPE
    SYNTAX           SEQUENCE OF CfprBiosVfConsoleRedirectionEntry
    MAX-ACCESS       not-accessible
    STATUS           current
    DESCRIPTION
        "Cisco Firepower bios:VfConsoleRedirection managed object table"
    ::= { cfprBiosObjects 19 }

cfprBiosVfConsoleRedirectionEntry OBJECT-TYPE
    SYNTAX           CfprBiosVfConsoleRedirectionEntry
    MAX-ACCESS       not-accessible
    STATUS           current
    DESCRIPTION
        "Entry for the cfprBiosVfConsoleRedirectionTable table."
    INDEX { cfprBiosVfConsoleRedirectionInstanceId }
    ::= { cfprBiosVfConsoleRedirectionTable 1 }

CfprBiosVfConsoleRedirectionEntry ::= SEQUENCE {
    cfprBiosVfConsoleRedirectionInstanceId                           CfprManagedObjectId,
    cfprBiosVfConsoleRedirectionDn                                   CfprManagedObjectDn,
    cfprBiosVfConsoleRedirectionRn                                   SnmpAdminString,
    cfprBiosVfConsoleRedirectionVpBaudRate                           CfprBiosVfConsoleRedirectionVpBaudRate,
    cfprBiosVfConsoleRedirectionVpConsoleRedirection                 CfprBiosVfConsoleRedirectionVpConsoleRedirection,
    cfprBiosVfConsoleRedirectionVpFlowControl                        CfprBiosVfConsoleRedirectionVpFlowControl,
    cfprBiosVfConsoleRedirectionVpLegacyOSRedirection                CfprBiosVfConsoleRedirectionVpLegacyOSRedirection,
    cfprBiosVfConsoleRedirectionVpPuttyKeyPad                        CfprBiosVfConsoleRedirectionVpPuttyKeyPad,
    cfprBiosVfConsoleRedirectionVpTerminalType                       CfprBiosVfConsoleRedirectionVpTerminalType,
    cfprBiosVfConsoleRedirectionSupportedByDefault                   CfprBiosSupportedAction
}

cfprBiosVfConsoleRedirectionInstanceId OBJECT-TYPE
    SYNTAX       CfprManagedObjectId
    MAX-ACCESS   not-accessible
    STATUS       current
    DESCRIPTION
        "Instance identifier of the managed object."
    ::= { cfprBiosVfConsoleRedirectionEntry 1 }

cfprBiosVfConsoleRedirectionDn OBJECT-TYPE
    SYNTAX       CfprManagedObjectDn
    MAX-ACCESS   read-only
    STATUS       current
    DESCRIPTION
        "Cisco Firepower bios:VfConsoleRedirection:dn managed
        object property"
    ::= { cfprBiosVfConsoleRedirectionEntry 2 }

cfprBiosVfConsoleRedirectionRn OBJECT-TYPE
    SYNTAX       SnmpAdminString
    MAX-ACCESS   read-only
    STATUS       current
    DESCRIPTION
        "Cisco Firepower bios:VfConsoleRedirection:rn managed
        object property"
    ::= { cfprBiosVfConsoleRedirectionEntry 3 }

cfprBiosVfConsoleRedirectionVpBaudRate OBJECT-TYPE
    SYNTAX       CfprBiosVfConsoleRedirectionVpBaudRate
    MAX-ACCESS   read-only
    STATUS       current
    DESCRIPTION
        "Cisco Firepower bios:VfConsoleRedirection:vpBaudRate
        managed object property"
    ::= { cfprBiosVfConsoleRedirectionEntry 4 }

cfprBiosVfConsoleRedirectionVpConsoleRedirection OBJECT-TYPE
    SYNTAX       CfprBiosVfConsoleRedirectionVpConsoleRedirection
    MAX-ACCESS   read-only
    STATUS       current
    DESCRIPTION
        "Cisco Firepower bios:VfConsoleRedirection:vpConsoleRedirection
        managed object property"
    ::= { cfprBiosVfConsoleRedirectionEntry 5 }

cfprBiosVfConsoleRedirectionVpFlowControl OBJECT-TYPE
    SYNTAX       CfprBiosVfConsoleRedirectionVpFlowControl
    MAX-ACCESS   read-only
    STATUS       current
    DESCRIPTION
        "Cisco Firepower bios:VfConsoleRedirection:vpFlowControl
        managed object property"
    ::= { cfprBiosVfConsoleRedirectionEntry 6 }

cfprBiosVfConsoleRedirectionVpLegacyOSRedirection OBJECT-TYPE
    SYNTAX       CfprBiosVfConsoleRedirectionVpLegacyOSRedirection
    MAX-ACCESS   read-only
    STATUS       current
    DESCRIPTION
        "Cisco Firepower bios:VfConsoleRedirection:vpLegacyOSRedirection
        managed object property"
    ::= { cfprBiosVfConsoleRedirectionEntry 7 }

cfprBiosVfConsoleRedirectionVpPuttyKeyPad OBJECT-TYPE
    SYNTAX       CfprBiosVfConsoleRedirectionVpPuttyKeyPad
    MAX-ACCESS   read-only
    STATUS       current
    DESCRIPTION
        "Cisco Firepower bios:VfConsoleRedirection:vpPuttyKeyPad
        managed object property"
    ::= { cfprBiosVfConsoleRedirectionEntry 8 }

cfprBiosVfConsoleRedirectionVpTerminalType OBJECT-TYPE
    SYNTAX       CfprBiosVfConsoleRedirectionVpTerminalType
    MAX-ACCESS   read-only
    STATUS       current
    DESCRIPTION
        "Cisco Firepower bios:VfConsoleRedirection:vpTerminalType
        managed object property"
    ::= { cfprBiosVfConsoleRedirectionEntry 9 }

cfprBiosVfConsoleRedirectionSupportedByDefault OBJECT-TYPE
    SYNTAX       CfprBiosSupportedAction
    MAX-ACCESS   read-only
    STATUS       current
    DESCRIPTION
        "Cisco Firepower bios:VfConsoleRedirection:supportedByDefault
        managed object property"
    ::= { cfprBiosVfConsoleRedirectionEntry 10 }

cfprBiosVfCoreMultiProcessingTable OBJECT-TYPE
    SYNTAX           SEQUENCE OF CfprBiosVfCoreMultiProcessingEntry
    MAX-ACCESS       not-accessible
    STATUS           current
    DESCRIPTION
        "Cisco Firepower bios:VfCoreMultiProcessing managed object table"
    ::= { cfprBiosObjects 20 }

cfprBiosVfCoreMultiProcessingEntry OBJECT-TYPE
    SYNTAX           CfprBiosVfCoreMultiProcessingEntry
    MAX-ACCESS       not-accessible
    STATUS           current
    DESCRIPTION
        "Entry for the cfprBiosVfCoreMultiProcessingTable table."
    INDEX { cfprBiosVfCoreMultiProcessingInstanceId }
    ::= { cfprBiosVfCoreMultiProcessingTable 1 }

CfprBiosVfCoreMultiProcessingEntry ::= SEQUENCE {
    cfprBiosVfCoreMultiProcessingInstanceId                          CfprManagedObjectId,
    cfprBiosVfCoreMultiProcessingDn                                  CfprManagedObjectDn,
    cfprBiosVfCoreMultiProcessingRn                                  SnmpAdminString,
    cfprBiosVfCoreMultiProcessingVpCoreMultiProcessing               CfprBiosVfCoreMultiProcessingVpCoreMultiProcessing,
    cfprBiosVfCoreMultiProcessingSupportedByDefault                  CfprBiosSupportedAction
}

cfprBiosVfCoreMultiProcessingInstanceId OBJECT-TYPE
    SYNTAX       CfprManagedObjectId
    MAX-ACCESS   not-accessible
    STATUS       current
    DESCRIPTION
        "Instance identifier of the managed object."
    ::= { cfprBiosVfCoreMultiProcessingEntry 1 }

cfprBiosVfCoreMultiProcessingDn OBJECT-TYPE
    SYNTAX       CfprManagedObjectDn
    MAX-ACCESS   read-only
    STATUS       current
    DESCRIPTION
        "Cisco Firepower bios:VfCoreMultiProcessing:dn
        managed object property"
    ::= { cfprBiosVfCoreMultiProcessingEntry 2 }

cfprBiosVfCoreMultiProcessingRn OBJECT-TYPE
    SYNTAX       SnmpAdminString
    MAX-ACCESS   read-only
    STATUS       current
    DESCRIPTION
        "Cisco Firepower bios:VfCoreMultiProcessing:rn
        managed object property"
    ::= { cfprBiosVfCoreMultiProcessingEntry 3 }

cfprBiosVfCoreMultiProcessingVpCoreMultiProcessing OBJECT-TYPE
    SYNTAX       CfprBiosVfCoreMultiProcessingVpCoreMultiProcessing
    MAX-ACCESS   read-only
    STATUS       current
    DESCRIPTION
        "Cisco Firepower bios:VfCoreMultiProcessing:vpCoreMultiProcessing
        managed object property"
    ::= { cfprBiosVfCoreMultiProcessingEntry 4 }

cfprBiosVfCoreMultiProcessingSupportedByDefault OBJECT-TYPE
    SYNTAX       CfprBiosSupportedAction
    MAX-ACCESS   read-only
    STATUS       current
    DESCRIPTION
        "Cisco Firepower bios:VfCoreMultiProcessing:supportedByDefault
        managed object property"
    ::= { cfprBiosVfCoreMultiProcessingEntry 5 }

cfprBiosVfDRAMClockThrottlingTable OBJECT-TYPE
    SYNTAX           SEQUENCE OF CfprBiosVfDRAMClockThrottlingEntry
    MAX-ACCESS       not-accessible
    STATUS           current
    DESCRIPTION
        "Cisco Firepower bios:VfDRAMClockThrottling managed object table"
    ::= { cfprBiosObjects 21 }

cfprBiosVfDRAMClockThrottlingEntry OBJECT-TYPE
    SYNTAX           CfprBiosVfDRAMClockThrottlingEntry
    MAX-ACCESS       not-accessible
    STATUS           current
    DESCRIPTION
        "Entry for the cfprBiosVfDRAMClockThrottlingTable table."
    INDEX { cfprBiosVfDRAMClockThrottlingInstanceId }
    ::= { cfprBiosVfDRAMClockThrottlingTable 1 }

CfprBiosVfDRAMClockThrottlingEntry ::= SEQUENCE {
    cfprBiosVfDRAMClockThrottlingInstanceId                          CfprManagedObjectId,
    cfprBiosVfDRAMClockThrottlingDn                                  CfprManagedObjectDn,
    cfprBiosVfDRAMClockThrottlingRn                                  SnmpAdminString,
    cfprBiosVfDRAMClockThrottlingVpDRAMClockThrottling               CfprBiosVfDRAMClockThrottlingVpDRAMClockThrottling,
    cfprBiosVfDRAMClockThrottlingSupportedByDefault                  CfprBiosSupportedAction
}

cfprBiosVfDRAMClockThrottlingInstanceId OBJECT-TYPE
    SYNTAX       CfprManagedObjectId
    MAX-ACCESS   not-accessible
    STATUS       current
    DESCRIPTION
        "Instance identifier of the managed object."
    ::= { cfprBiosVfDRAMClockThrottlingEntry 1 }

cfprBiosVfDRAMClockThrottlingDn OBJECT-TYPE
    SYNTAX       CfprManagedObjectDn
    MAX-ACCESS   read-only
    STATUS       current
    DESCRIPTION
        "Cisco Firepower bios:VfDRAMClockThrottling:dn
        managed object property"
    ::= { cfprBiosVfDRAMClockThrottlingEntry 2 }

cfprBiosVfDRAMClockThrottlingRn OBJECT-TYPE
    SYNTAX       SnmpAdminString
    MAX-ACCESS   read-only
    STATUS       current
    DESCRIPTION
        "Cisco Firepower bios:VfDRAMClockThrottling:rn
        managed object property"
    ::= { cfprBiosVfDRAMClockThrottlingEntry 3 }

cfprBiosVfDRAMClockThrottlingVpDRAMClockThrottling OBJECT-TYPE
    SYNTAX       CfprBiosVfDRAMClockThrottlingVpDRAMClockThrottling
    MAX-ACCESS   read-only
    STATUS       current
    DESCRIPTION
        "Cisco Firepower bios:VfDRAMClockThrottling:vpDRAMClockThrottling
        managed object property"
    ::= { cfprBiosVfDRAMClockThrottlingEntry 4 }

cfprBiosVfDRAMClockThrottlingSupportedByDefault OBJECT-TYPE
    SYNTAX       CfprBiosSupportedAction
    MAX-ACCESS   read-only
    STATUS       current
    DESCRIPTION
        "Cisco Firepower bios:VfDRAMClockThrottling:supportedByDefault
        managed object property"
    ::= { cfprBiosVfDRAMClockThrottlingEntry 5 }

cfprBiosVfDirectCacheAccessTable OBJECT-TYPE
    SYNTAX           SEQUENCE OF CfprBiosVfDirectCacheAccessEntry
    MAX-ACCESS       not-accessible
    STATUS           current
    DESCRIPTION
        "Cisco Firepower bios:VfDirectCacheAccess managed object table"
    ::= { cfprBiosObjects 22 }

cfprBiosVfDirectCacheAccessEntry OBJECT-TYPE
    SYNTAX           CfprBiosVfDirectCacheAccessEntry
    MAX-ACCESS       not-accessible
    STATUS           current
    DESCRIPTION
        "Entry for the cfprBiosVfDirectCacheAccessTable table."
    INDEX { cfprBiosVfDirectCacheAccessInstanceId }
    ::= { cfprBiosVfDirectCacheAccessTable 1 }

CfprBiosVfDirectCacheAccessEntry ::= SEQUENCE {
    cfprBiosVfDirectCacheAccessInstanceId                            CfprManagedObjectId,
    cfprBiosVfDirectCacheAccessDn                                    CfprManagedObjectDn,
    cfprBiosVfDirectCacheAccessRn                                    SnmpAdminString,
    cfprBiosVfDirectCacheAccessVpDirectCacheAccess                   CfprBiosVfDirectCacheAccessVpDirectCacheAccess,
    cfprBiosVfDirectCacheAccessSupportedByDefault                    CfprBiosSupportedAction
}

cfprBiosVfDirectCacheAccessInstanceId OBJECT-TYPE
    SYNTAX       CfprManagedObjectId
    MAX-ACCESS   not-accessible
    STATUS       current
    DESCRIPTION
        "Instance identifier of the managed object."
    ::= { cfprBiosVfDirectCacheAccessEntry 1 }

cfprBiosVfDirectCacheAccessDn OBJECT-TYPE
    SYNTAX       CfprManagedObjectDn
    MAX-ACCESS   read-only
    STATUS       current
    DESCRIPTION
        "Cisco Firepower bios:VfDirectCacheAccess:dn managed
        object property"
    ::= { cfprBiosVfDirectCacheAccessEntry 2 }

cfprBiosVfDirectCacheAccessRn OBJECT-TYPE
    SYNTAX       SnmpAdminString
    MAX-ACCESS   read-only
    STATUS       current
    DESCRIPTION
        "Cisco Firepower bios:VfDirectCacheAccess:rn managed
        object property"
    ::= { cfprBiosVfDirectCacheAccessEntry 3 }

cfprBiosVfDirectCacheAccessVpDirectCacheAccess OBJECT-TYPE
    SYNTAX       CfprBiosVfDirectCacheAccessVpDirectCacheAccess
    MAX-ACCESS   read-only
    STATUS       current
    DESCRIPTION
        "Cisco Firepower bios:VfDirectCacheAccess:vpDirectCacheAccess
        managed object property"
    ::= { cfprBiosVfDirectCacheAccessEntry 4 }

cfprBiosVfDirectCacheAccessSupportedByDefault OBJECT-TYPE
    SYNTAX       CfprBiosSupportedAction
    MAX-ACCESS   read-only
    STATUS       current
    DESCRIPTION
        "Cisco Firepower bios:VfDirectCacheAccess:supportedByDefault
        managed object property"
    ::= { cfprBiosVfDirectCacheAccessEntry 5 }

cfprBiosVfDramRefreshRateTable OBJECT-TYPE
    SYNTAX           SEQUENCE OF CfprBiosVfDramRefreshRateEntry
    MAX-ACCESS       not-accessible
    STATUS           current
    DESCRIPTION
        "Cisco Firepower bios:VfDramRefreshRate managed object table"
    ::= { cfprBiosObjects 23 }

cfprBiosVfDramRefreshRateEntry OBJECT-TYPE
    SYNTAX           CfprBiosVfDramRefreshRateEntry
    MAX-ACCESS       not-accessible
    STATUS           current
    DESCRIPTION
        "Entry for the cfprBiosVfDramRefreshRateTable table."
    INDEX { cfprBiosVfDramRefreshRateInstanceId }
    ::= { cfprBiosVfDramRefreshRateTable 1 }

CfprBiosVfDramRefreshRateEntry ::= SEQUENCE {
    cfprBiosVfDramRefreshRateInstanceId                              CfprManagedObjectId,
    cfprBiosVfDramRefreshRateDn                                      CfprManagedObjectDn,
    cfprBiosVfDramRefreshRateRn                                      SnmpAdminString,
    cfprBiosVfDramRefreshRateVpDramRefreshRate                       CfprBiosVfDramRefreshRateVpDramRefreshRate,
    cfprBiosVfDramRefreshRateSupportedByDefault                      CfprBiosSupportedAction
}

cfprBiosVfDramRefreshRateInstanceId OBJECT-TYPE
    SYNTAX       CfprManagedObjectId
    MAX-ACCESS   not-accessible
    STATUS       current
    DESCRIPTION
        "Instance identifier of the managed object."
    ::= { cfprBiosVfDramRefreshRateEntry 1 }

cfprBiosVfDramRefreshRateDn OBJECT-TYPE
    SYNTAX       CfprManagedObjectDn
    MAX-ACCESS   read-only
    STATUS       current
    DESCRIPTION
        "Cisco Firepower bios:VfDramRefreshRate:dn managed
        object property"
    ::= { cfprBiosVfDramRefreshRateEntry 2 }

cfprBiosVfDramRefreshRateRn OBJECT-TYPE
    SYNTAX       SnmpAdminString
    MAX-ACCESS   read-only
    STATUS       current
    DESCRIPTION
        "Cisco Firepower bios:VfDramRefreshRate:rn managed
        object property"
    ::= { cfprBiosVfDramRefreshRateEntry 3 }

cfprBiosVfDramRefreshRateVpDramRefreshRate OBJECT-TYPE
    SYNTAX       CfprBiosVfDramRefreshRateVpDramRefreshRate
    MAX-ACCESS   read-only
    STATUS       current
    DESCRIPTION
        "Cisco Firepower bios:VfDramRefreshRate:vpDramRefreshRate
        managed object property"
    ::= { cfprBiosVfDramRefreshRateEntry 4 }

cfprBiosVfDramRefreshRateSupportedByDefault OBJECT-TYPE
    SYNTAX       CfprBiosSupportedAction
    MAX-ACCESS   read-only
    STATUS       current
    DESCRIPTION
        "Cisco Firepower bios:VfDramRefreshRate:supportedByDefault
        managed object property"
    ::= { cfprBiosVfDramRefreshRateEntry 5 }

cfprBiosVfEnhancedIntelSpeedStepTechTable OBJECT-TYPE
    SYNTAX           SEQUENCE OF CfprBiosVfEnhancedIntelSpeedStepTechEntry
    MAX-ACCESS       not-accessible
    STATUS           current
    DESCRIPTION
        "Cisco Firepower bios:VfEnhancedIntelSpeedStepTech
        managed object table"
    ::= { cfprBiosObjects 24 }

cfprBiosVfEnhancedIntelSpeedStepTechEntry OBJECT-TYPE
    SYNTAX           CfprBiosVfEnhancedIntelSpeedStepTechEntry
    MAX-ACCESS       not-accessible
    STATUS           current
    DESCRIPTION
        "Entry for the cfprBiosVfEnhancedIntelSpeedStepTechTable table."
    INDEX { cfprBiosVfEnhancedIntelSpeedStepTechInstanceId }
    ::= { cfprBiosVfEnhancedIntelSpeedStepTechTable 1 }

CfprBiosVfEnhancedIntelSpeedStepTechEntry ::= SEQUENCE {
    cfprBiosVfEnhancedIntelSpeedStepTechInstanceId                   CfprManagedObjectId,
    cfprBiosVfEnhancedIntelSpeedStepTechDn                           CfprManagedObjectDn,
    cfprBiosVfEnhancedIntelSpeedStepTechRn                           SnmpAdminString,
    cfprBiosVfEnhancedIntelSpeedStepTechVpEnhancedIntelSpeedStepTech CfprBiosVfEnhancedIntelSpeedStepTechVpEnhancedIntelSpeedStepTech,
    cfprBiosVfEnhancedIntelSpeedStepTechSupportedByDefault           CfprBiosSupportedAction
}

cfprBiosVfEnhancedIntelSpeedStepTechInstanceId OBJECT-TYPE
    SYNTAX       CfprManagedObjectId
    MAX-ACCESS   not-accessible
    STATUS       current
    DESCRIPTION
        "Instance identifier of the managed object."
    ::= { cfprBiosVfEnhancedIntelSpeedStepTechEntry 1 }

cfprBiosVfEnhancedIntelSpeedStepTechDn OBJECT-TYPE
    SYNTAX       CfprManagedObjectDn
    MAX-ACCESS   read-only
    STATUS       current
    DESCRIPTION
        "Cisco Firepower bios:VfEnhancedIntelSpeedStepTech:dn
        managed object property"
    ::= { cfprBiosVfEnhancedIntelSpeedStepTechEntry 2 }

cfprBiosVfEnhancedIntelSpeedStepTechRn OBJECT-TYPE
    SYNTAX       SnmpAdminString
    MAX-ACCESS   read-only
    STATUS       current
    DESCRIPTION
        "Cisco Firepower bios:VfEnhancedIntelSpeedStepTech:rn
        managed object property"
    ::= { cfprBiosVfEnhancedIntelSpeedStepTechEntry 3 }

cfprBiosVfEnhancedIntelSpeedStepTechVpEnhancedIntelSpeedStepTech OBJECT-TYPE
    SYNTAX       CfprBiosVfEnhancedIntelSpeedStepTechVpEnhancedIntelSpeedStepTech
    MAX-ACCESS   read-only
    STATUS       current
    DESCRIPTION
        "Cisco Firepower bios:VfEnhancedIntelSpeedStepTech:vpEnhancedIntel
        SpeedStepTech managed object property"
    ::= { cfprBiosVfEnhancedIntelSpeedStepTechEntry 4 }

cfprBiosVfEnhancedIntelSpeedStepTechSupportedByDefault OBJECT-TYPE
    SYNTAX       CfprBiosSupportedAction
    MAX-ACCESS   read-only
    STATUS       current
    DESCRIPTION
        "Cisco Firepower bios:VfEnhancedIntelSpeedStepTech:supportedByDefa
        ult managed object property"
    ::= { cfprBiosVfEnhancedIntelSpeedStepTechEntry 5 }

cfprBiosVfExecuteDisableBitTable OBJECT-TYPE
    SYNTAX           SEQUENCE OF CfprBiosVfExecuteDisableBitEntry
    MAX-ACCESS       not-accessible
    STATUS           current
    DESCRIPTION
        "Cisco Firepower bios:VfExecuteDisableBit managed object table"
    ::= { cfprBiosObjects 25 }

cfprBiosVfExecuteDisableBitEntry OBJECT-TYPE
    SYNTAX           CfprBiosVfExecuteDisableBitEntry
    MAX-ACCESS       not-accessible
    STATUS           current
    DESCRIPTION
        "Entry for the cfprBiosVfExecuteDisableBitTable table."
    INDEX { cfprBiosVfExecuteDisableBitInstanceId }
    ::= { cfprBiosVfExecuteDisableBitTable 1 }

CfprBiosVfExecuteDisableBitEntry ::= SEQUENCE {
    cfprBiosVfExecuteDisableBitInstanceId                            CfprManagedObjectId,
    cfprBiosVfExecuteDisableBitDn                                    CfprManagedObjectDn,
    cfprBiosVfExecuteDisableBitRn                                    SnmpAdminString,
    cfprBiosVfExecuteDisableBitVpExecuteDisableBit                   CfprBiosVfExecuteDisableBitVpExecuteDisableBit,
    cfprBiosVfExecuteDisableBitSupportedByDefault                    CfprBiosSupportedAction
}

cfprBiosVfExecuteDisableBitInstanceId OBJECT-TYPE
    SYNTAX       CfprManagedObjectId
    MAX-ACCESS   not-accessible
    STATUS       current
    DESCRIPTION
        "Instance identifier of the managed object."
    ::= { cfprBiosVfExecuteDisableBitEntry 1 }

cfprBiosVfExecuteDisableBitDn OBJECT-TYPE
    SYNTAX       CfprManagedObjectDn
    MAX-ACCESS   read-only
    STATUS       current
    DESCRIPTION
        "Cisco Firepower bios:VfExecuteDisableBit:dn managed
        object property"
    ::= { cfprBiosVfExecuteDisableBitEntry 2 }

cfprBiosVfExecuteDisableBitRn OBJECT-TYPE
    SYNTAX       SnmpAdminString
    MAX-ACCESS   read-only
    STATUS       current
    DESCRIPTION
        "Cisco Firepower bios:VfExecuteDisableBit:rn managed
        object property"
    ::= { cfprBiosVfExecuteDisableBitEntry 3 }

cfprBiosVfExecuteDisableBitVpExecuteDisableBit OBJECT-TYPE
    SYNTAX       CfprBiosVfExecuteDisableBitVpExecuteDisableBit
    MAX-ACCESS   read-only
    STATUS       current
    DESCRIPTION
        "Cisco Firepower bios:VfExecuteDisableBit:vpExecuteDisableBit
        managed object property"
    ::= { cfprBiosVfExecuteDisableBitEntry 4 }

cfprBiosVfExecuteDisableBitSupportedByDefault OBJECT-TYPE
    SYNTAX       CfprBiosSupportedAction
    MAX-ACCESS   read-only
    STATUS       current
    DESCRIPTION
        "Cisco Firepower bios:VfExecuteDisableBit:supportedByDefault
        managed object property"
    ::= { cfprBiosVfExecuteDisableBitEntry 5 }

cfprBiosVfFRB2TimerTable OBJECT-TYPE
    SYNTAX           SEQUENCE OF CfprBiosVfFRB2TimerEntry
    MAX-ACCESS       not-accessible
    STATUS           current
    DESCRIPTION
        "Cisco Firepower bios:VfFRB2Timer managed object table"
    ::= { cfprBiosObjects 26 }

cfprBiosVfFRB2TimerEntry OBJECT-TYPE
    SYNTAX           CfprBiosVfFRB2TimerEntry
    MAX-ACCESS       not-accessible
    STATUS           current
    DESCRIPTION
        "Entry for the cfprBiosVfFRB2TimerTable table."
    INDEX { cfprBiosVfFRB2TimerInstanceId }
    ::= { cfprBiosVfFRB2TimerTable 1 }

CfprBiosVfFRB2TimerEntry ::= SEQUENCE {
    cfprBiosVfFRB2TimerInstanceId                                    CfprManagedObjectId,
    cfprBiosVfFRB2TimerDn                                            CfprManagedObjectDn,
    cfprBiosVfFRB2TimerRn                                            SnmpAdminString,
    cfprBiosVfFRB2TimerVpFRB2Timer                                   CfprBiosVfFRB2TimerVpFRB2Timer,
    cfprBiosVfFRB2TimerSupportedByDefault                            CfprBiosSupportedAction
}

cfprBiosVfFRB2TimerInstanceId OBJECT-TYPE
    SYNTAX       CfprManagedObjectId
    MAX-ACCESS   not-accessible
    STATUS       current
    DESCRIPTION
        "Instance identifier of the managed object."
    ::= { cfprBiosVfFRB2TimerEntry 1 }

cfprBiosVfFRB2TimerDn OBJECT-TYPE
    SYNTAX       CfprManagedObjectDn
    MAX-ACCESS   read-only
    STATUS       current
    DESCRIPTION
        "Cisco Firepower bios:VfFRB2Timer:dn managed object property"
    ::= { cfprBiosVfFRB2TimerEntry 2 }

cfprBiosVfFRB2TimerRn OBJECT-TYPE
    SYNTAX       SnmpAdminString
    MAX-ACCESS   read-only
    STATUS       current
    DESCRIPTION
        "Cisco Firepower bios:VfFRB2Timer:rn managed object property"
    ::= { cfprBiosVfFRB2TimerEntry 3 }

cfprBiosVfFRB2TimerVpFRB2Timer OBJECT-TYPE
    SYNTAX       CfprBiosVfFRB2TimerVpFRB2Timer
    MAX-ACCESS   read-only
    STATUS       current
    DESCRIPTION
        "Cisco Firepower bios:VfFRB2Timer:vpFRB2Timer managed
        object property"
    ::= { cfprBiosVfFRB2TimerEntry 4 }

cfprBiosVfFRB2TimerSupportedByDefault OBJECT-TYPE
    SYNTAX       CfprBiosSupportedAction
    MAX-ACCESS   read-only
    STATUS       current
    DESCRIPTION
        "Cisco Firepower bios:VfFRB2Timer:supportedByDefault
        managed object property"
    ::= { cfprBiosVfFRB2TimerEntry 5 }

cfprBiosVfFrequencyFloorOverrideTable OBJECT-TYPE
    SYNTAX           SEQUENCE OF CfprBiosVfFrequencyFloorOverrideEntry
    MAX-ACCESS       not-accessible
    STATUS           current
    DESCRIPTION
        "Cisco Firepower bios:VfFrequencyFloorOverride
        managed object table"
    ::= { cfprBiosObjects 27 }

cfprBiosVfFrequencyFloorOverrideEntry OBJECT-TYPE
    SYNTAX           CfprBiosVfFrequencyFloorOverrideEntry
    MAX-ACCESS       not-accessible
    STATUS           current
    DESCRIPTION
        "Entry for the cfprBiosVfFrequencyFloorOverrideTable table."
    INDEX { cfprBiosVfFrequencyFloorOverrideInstanceId }
    ::= { cfprBiosVfFrequencyFloorOverrideTable 1 }

CfprBiosVfFrequencyFloorOverrideEntry ::= SEQUENCE {
    cfprBiosVfFrequencyFloorOverrideInstanceId                       CfprManagedObjectId,
    cfprBiosVfFrequencyFloorOverrideDn                               CfprManagedObjectDn,
    cfprBiosVfFrequencyFloorOverrideRn                               SnmpAdminString,
    cfprBiosVfFrequencyFloorOverrideVpFrequencyFloorOverride         CfprBiosVfFrequencyFloorOverrideVpFrequencyFloorOverride,
    cfprBiosVfFrequencyFloorOverrideSupportedByDefault               CfprBiosSupportedAction
}

cfprBiosVfFrequencyFloorOverrideInstanceId OBJECT-TYPE
    SYNTAX       CfprManagedObjectId
    MAX-ACCESS   not-accessible
    STATUS       current
    DESCRIPTION
        "Instance identifier of the managed object."
    ::= { cfprBiosVfFrequencyFloorOverrideEntry 1 }

cfprBiosVfFrequencyFloorOverrideDn OBJECT-TYPE
    SYNTAX       CfprManagedObjectDn
    MAX-ACCESS   read-only
    STATUS       current
    DESCRIPTION
        "Cisco Firepower bios:VfFrequencyFloorOverride:dn
        managed object property"
    ::= { cfprBiosVfFrequencyFloorOverrideEntry 2 }

cfprBiosVfFrequencyFloorOverrideRn OBJECT-TYPE
    SYNTAX       SnmpAdminString
    MAX-ACCESS   read-only
    STATUS       current
    DESCRIPTION
        "Cisco Firepower bios:VfFrequencyFloorOverride:rn
        managed object property"
    ::= { cfprBiosVfFrequencyFloorOverrideEntry 3 }

cfprBiosVfFrequencyFloorOverrideVpFrequencyFloorOverride OBJECT-TYPE
    SYNTAX       CfprBiosVfFrequencyFloorOverrideVpFrequencyFloorOverride
    MAX-ACCESS   read-only
    STATUS       current
    DESCRIPTION
        "Cisco Firepower bios:VfFrequencyFloorOverride:vpFrequencyFloorOve
        rride managed object property"
    ::= { cfprBiosVfFrequencyFloorOverrideEntry 4 }

cfprBiosVfFrequencyFloorOverrideSupportedByDefault OBJECT-TYPE
    SYNTAX       CfprBiosSupportedAction
    MAX-ACCESS   read-only
    STATUS       current
    DESCRIPTION
        "Cisco Firepower bios:VfFrequencyFloorOverride:supportedByDefault
        managed object property"
    ::= { cfprBiosVfFrequencyFloorOverrideEntry 5 }

cfprBiosVfFrontPanelLockoutTable OBJECT-TYPE
    SYNTAX           SEQUENCE OF CfprBiosVfFrontPanelLockoutEntry
    MAX-ACCESS       not-accessible
    STATUS           current
    DESCRIPTION
        "Cisco Firepower bios:VfFrontPanelLockout managed object table"
    ::= { cfprBiosObjects 28 }

cfprBiosVfFrontPanelLockoutEntry OBJECT-TYPE
    SYNTAX           CfprBiosVfFrontPanelLockoutEntry
    MAX-ACCESS       not-accessible
    STATUS           current
    DESCRIPTION
        "Entry for the cfprBiosVfFrontPanelLockoutTable table."
    INDEX { cfprBiosVfFrontPanelLockoutInstanceId }
    ::= { cfprBiosVfFrontPanelLockoutTable 1 }

CfprBiosVfFrontPanelLockoutEntry ::= SEQUENCE {
    cfprBiosVfFrontPanelLockoutInstanceId                            CfprManagedObjectId,
    cfprBiosVfFrontPanelLockoutDn                                    CfprManagedObjectDn,
    cfprBiosVfFrontPanelLockoutRn                                    SnmpAdminString,
    cfprBiosVfFrontPanelLockoutVpFrontPanelLockout                   CfprBiosVfFrontPanelLockoutVpFrontPanelLockout,
    cfprBiosVfFrontPanelLockoutSupportedByDefault                    CfprBiosSupportedAction
}

cfprBiosVfFrontPanelLockoutInstanceId OBJECT-TYPE
    SYNTAX       CfprManagedObjectId
    MAX-ACCESS   not-accessible
    STATUS       current
    DESCRIPTION
        "Instance identifier of the managed object."
    ::= { cfprBiosVfFrontPanelLockoutEntry 1 }

cfprBiosVfFrontPanelLockoutDn OBJECT-TYPE
    SYNTAX       CfprManagedObjectDn
    MAX-ACCESS   read-only
    STATUS       current
    DESCRIPTION
        "Cisco Firepower bios:VfFrontPanelLockout:dn managed
        object property"
    ::= { cfprBiosVfFrontPanelLockoutEntry 2 }

cfprBiosVfFrontPanelLockoutRn OBJECT-TYPE
    SYNTAX       SnmpAdminString
    MAX-ACCESS   read-only
    STATUS       current
    DESCRIPTION
        "Cisco Firepower bios:VfFrontPanelLockout:rn managed
        object property"
    ::= { cfprBiosVfFrontPanelLockoutEntry 3 }

cfprBiosVfFrontPanelLockoutVpFrontPanelLockout OBJECT-TYPE
    SYNTAX       CfprBiosVfFrontPanelLockoutVpFrontPanelLockout
    MAX-ACCESS   read-only
    STATUS       current
    DESCRIPTION
        "Cisco Firepower bios:VfFrontPanelLockout:vpFrontPanelLockout
        managed object property"
    ::= { cfprBiosVfFrontPanelLockoutEntry 4 }

cfprBiosVfFrontPanelLockoutSupportedByDefault OBJECT-TYPE
    SYNTAX       CfprBiosSupportedAction
    MAX-ACCESS   read-only
    STATUS       current
    DESCRIPTION
        "Cisco Firepower bios:VfFrontPanelLockout:supportedByDefault
        managed object property"
    ::= { cfprBiosVfFrontPanelLockoutEntry 5 }

cfprBiosVfIntelEntrySASRAIDModuleTable OBJECT-TYPE
    SYNTAX           SEQUENCE OF CfprBiosVfIntelEntrySASRAIDModuleEntry
    MAX-ACCESS       not-accessible
    STATUS           current
    DESCRIPTION
        "Cisco Firepower bios:VfIntelEntrySASRAIDModule
        managed object table"
    ::= { cfprBiosObjects 29 }

cfprBiosVfIntelEntrySASRAIDModuleEntry OBJECT-TYPE
    SYNTAX           CfprBiosVfIntelEntrySASRAIDModuleEntry
    MAX-ACCESS       not-accessible
    STATUS           current
    DESCRIPTION
        "Entry for the cfprBiosVfIntelEntrySASRAIDModuleTable table."
    INDEX { cfprBiosVfIntelEntrySASRAIDModuleInstanceId }
    ::= { cfprBiosVfIntelEntrySASRAIDModuleTable 1 }

CfprBiosVfIntelEntrySASRAIDModuleEntry ::= SEQUENCE {
    cfprBiosVfIntelEntrySASRAIDModuleInstanceId                      CfprManagedObjectId,
    cfprBiosVfIntelEntrySASRAIDModuleDn                              CfprManagedObjectDn,
    cfprBiosVfIntelEntrySASRAIDModuleRn                              SnmpAdminString,
    cfprBiosVfIntelEntrySASRAIDModuleVpSASRAID                       CfprBiosVfIntelEntrySASRAIDModuleVpSASRAID,
    cfprBiosVfIntelEntrySASRAIDModuleVpSASRAIDModule                 CfprBiosVfIntelEntrySASRAIDModuleVpSASRAIDModule,
    cfprBiosVfIntelEntrySASRAIDModuleSupportedByDefault              CfprBiosSupportedAction
}

cfprBiosVfIntelEntrySASRAIDModuleInstanceId OBJECT-TYPE
    SYNTAX       CfprManagedObjectId
    MAX-ACCESS   not-accessible
    STATUS       current
    DESCRIPTION
        "Instance identifier of the managed object."
    ::= { cfprBiosVfIntelEntrySASRAIDModuleEntry 1 }

cfprBiosVfIntelEntrySASRAIDModuleDn OBJECT-TYPE
    SYNTAX       CfprManagedObjectDn
    MAX-ACCESS   read-only
    STATUS       current
    DESCRIPTION
        "Cisco Firepower bios:VfIntelEntrySASRAIDModule:dn
        managed object property"
    ::= { cfprBiosVfIntelEntrySASRAIDModuleEntry 2 }

cfprBiosVfIntelEntrySASRAIDModuleRn OBJECT-TYPE
    SYNTAX       SnmpAdminString
    MAX-ACCESS   read-only
    STATUS       current
    DESCRIPTION
        "Cisco Firepower bios:VfIntelEntrySASRAIDModule:rn
        managed object property"
    ::= { cfprBiosVfIntelEntrySASRAIDModuleEntry 3 }

cfprBiosVfIntelEntrySASRAIDModuleVpSASRAID OBJECT-TYPE
    SYNTAX       CfprBiosVfIntelEntrySASRAIDModuleVpSASRAID
    MAX-ACCESS   read-only
    STATUS       current
    DESCRIPTION
        "Cisco Firepower bios:VfIntelEntrySASRAIDModule:vpSASRAID
        managed object property"
    ::= { cfprBiosVfIntelEntrySASRAIDModuleEntry 4 }

cfprBiosVfIntelEntrySASRAIDModuleVpSASRAIDModule OBJECT-TYPE
    SYNTAX       CfprBiosVfIntelEntrySASRAIDModuleVpSASRAIDModule
    MAX-ACCESS   read-only
    STATUS       current
    DESCRIPTION
        "Cisco Firepower bios:VfIntelEntrySASRAIDModule:vpSASRAIDModule
        managed object property"
    ::= { cfprBiosVfIntelEntrySASRAIDModuleEntry 5 }

cfprBiosVfIntelEntrySASRAIDModuleSupportedByDefault OBJECT-TYPE
    SYNTAX       CfprBiosSupportedAction
    MAX-ACCESS   read-only
    STATUS       current
    DESCRIPTION
        "Cisco Firepower bios:VfIntelEntrySASRAIDModule:supportedByDefault
         managed object property"
    ::= { cfprBiosVfIntelEntrySASRAIDModuleEntry 6 }

cfprBiosVfIntelHyperThreadingTechTable OBJECT-TYPE
    SYNTAX           SEQUENCE OF CfprBiosVfIntelHyperThreadingTechEntry
    MAX-ACCESS       not-accessible
    STATUS           current
    DESCRIPTION
        "Cisco Firepower bios:VfIntelHyperThreadingTech
        managed object table"
    ::= { cfprBiosObjects 30 }

cfprBiosVfIntelHyperThreadingTechEntry OBJECT-TYPE
    SYNTAX           CfprBiosVfIntelHyperThreadingTechEntry
    MAX-ACCESS       not-accessible
    STATUS           current
    DESCRIPTION
        "Entry for the cfprBiosVfIntelHyperThreadingTechTable table."
    INDEX { cfprBiosVfIntelHyperThreadingTechInstanceId }
    ::= { cfprBiosVfIntelHyperThreadingTechTable 1 }

CfprBiosVfIntelHyperThreadingTechEntry ::= SEQUENCE {
    cfprBiosVfIntelHyperThreadingTechInstanceId                      CfprManagedObjectId,
    cfprBiosVfIntelHyperThreadingTechDn                              CfprManagedObjectDn,
    cfprBiosVfIntelHyperThreadingTechRn                              SnmpAdminString,
    cfprBiosVfIntelHyperThreadingTechVpIntelHyperThreadingTech       CfprBiosVfIntelHyperThreadingTechVpIntelHyperThreadingTech,
    cfprBiosVfIntelHyperThreadingTechSupportedByDefault              CfprBiosSupportedAction
}

cfprBiosVfIntelHyperThreadingTechInstanceId OBJECT-TYPE
    SYNTAX       CfprManagedObjectId
    MAX-ACCESS   not-accessible
    STATUS       current
    DESCRIPTION
        "Instance identifier of the managed object."
    ::= { cfprBiosVfIntelHyperThreadingTechEntry 1 }

cfprBiosVfIntelHyperThreadingTechDn OBJECT-TYPE
    SYNTAX       CfprManagedObjectDn
    MAX-ACCESS   read-only
    STATUS       current
    DESCRIPTION
        "Cisco Firepower bios:VfIntelHyperThreadingTech:dn
        managed object property"
    ::= { cfprBiosVfIntelHyperThreadingTechEntry 2 }

cfprBiosVfIntelHyperThreadingTechRn OBJECT-TYPE
    SYNTAX       SnmpAdminString
    MAX-ACCESS   read-only
    STATUS       current
    DESCRIPTION
        "Cisco Firepower bios:VfIntelHyperThreadingTech:rn
        managed object property"
    ::= { cfprBiosVfIntelHyperThreadingTechEntry 3 }

cfprBiosVfIntelHyperThreadingTechVpIntelHyperThreadingTech OBJECT-TYPE
    SYNTAX       CfprBiosVfIntelHyperThreadingTechVpIntelHyperThreadingTech
    MAX-ACCESS   read-only
    STATUS       current
    DESCRIPTION
        "Cisco Firepower bios:VfIntelHyperThreadingTech:vpIntelHyperThread
        ingTech managed object property"
    ::= { cfprBiosVfIntelHyperThreadingTechEntry 4 }

cfprBiosVfIntelHyperThreadingTechSupportedByDefault OBJECT-TYPE
    SYNTAX       CfprBiosSupportedAction
    MAX-ACCESS   read-only
    STATUS       current
    DESCRIPTION
        "Cisco Firepower bios:VfIntelHyperThreadingTech:supportedByDefault
         managed object property"
    ::= { cfprBiosVfIntelHyperThreadingTechEntry 5 }

cfprBiosVfIntelTurboBoostTechTable OBJECT-TYPE
    SYNTAX           SEQUENCE OF CfprBiosVfIntelTurboBoostTechEntry
    MAX-ACCESS       not-accessible
    STATUS           current
    DESCRIPTION
        "Cisco Firepower bios:VfIntelTurboBoostTech managed object table"
    ::= { cfprBiosObjects 31 }

cfprBiosVfIntelTurboBoostTechEntry OBJECT-TYPE
    SYNTAX           CfprBiosVfIntelTurboBoostTechEntry
    MAX-ACCESS       not-accessible
    STATUS           current
    DESCRIPTION
        "Entry for the cfprBiosVfIntelTurboBoostTechTable table."
    INDEX { cfprBiosVfIntelTurboBoostTechInstanceId }
    ::= { cfprBiosVfIntelTurboBoostTechTable 1 }

CfprBiosVfIntelTurboBoostTechEntry ::= SEQUENCE {
    cfprBiosVfIntelTurboBoostTechInstanceId                          CfprManagedObjectId,
    cfprBiosVfIntelTurboBoostTechDn                                  CfprManagedObjectDn,
    cfprBiosVfIntelTurboBoostTechRn                                  SnmpAdminString,
    cfprBiosVfIntelTurboBoostTechVpIntelTurboBoostTech               CfprBiosVfIntelTurboBoostTechVpIntelTurboBoostTech,
    cfprBiosVfIntelTurboBoostTechSupportedByDefault                  CfprBiosSupportedAction
}

cfprBiosVfIntelTurboBoostTechInstanceId OBJECT-TYPE
    SYNTAX       CfprManagedObjectId
    MAX-ACCESS   not-accessible
    STATUS       current
    DESCRIPTION
        "Instance identifier of the managed object."
    ::= { cfprBiosVfIntelTurboBoostTechEntry 1 }

cfprBiosVfIntelTurboBoostTechDn OBJECT-TYPE
    SYNTAX       CfprManagedObjectDn
    MAX-ACCESS   read-only
    STATUS       current
    DESCRIPTION
        "Cisco Firepower bios:VfIntelTurboBoostTech:dn
        managed object property"
    ::= { cfprBiosVfIntelTurboBoostTechEntry 2 }

cfprBiosVfIntelTurboBoostTechRn OBJECT-TYPE
    SYNTAX       SnmpAdminString
    MAX-ACCESS   read-only
    STATUS       current
    DESCRIPTION
        "Cisco Firepower bios:VfIntelTurboBoostTech:rn
        managed object property"
    ::= { cfprBiosVfIntelTurboBoostTechEntry 3 }

cfprBiosVfIntelTurboBoostTechVpIntelTurboBoostTech OBJECT-TYPE
    SYNTAX       CfprBiosVfIntelTurboBoostTechVpIntelTurboBoostTech
    MAX-ACCESS   read-only
    STATUS       current
    DESCRIPTION
        "Cisco Firepower bios:VfIntelTurboBoostTech:vpIntelTurboBoostTech
        managed object property"
    ::= { cfprBiosVfIntelTurboBoostTechEntry 4 }

cfprBiosVfIntelTurboBoostTechSupportedByDefault OBJECT-TYPE
    SYNTAX       CfprBiosSupportedAction
    MAX-ACCESS   read-only
    STATUS       current
    DESCRIPTION
        "Cisco Firepower bios:VfIntelTurboBoostTech:supportedByDefault
        managed object property"
    ::= { cfprBiosVfIntelTurboBoostTechEntry 5 }

cfprBiosVfIntelVTForDirectedIOTable OBJECT-TYPE
    SYNTAX           SEQUENCE OF CfprBiosVfIntelVTForDirectedIOEntry
    MAX-ACCESS       not-accessible
    STATUS           current
    DESCRIPTION
        "Cisco Firepower bios:VfIntelVTForDirectedIO managed object table"
    ::= { cfprBiosObjects 32 }

cfprBiosVfIntelVTForDirectedIOEntry OBJECT-TYPE
    SYNTAX           CfprBiosVfIntelVTForDirectedIOEntry
    MAX-ACCESS       not-accessible
    STATUS           current
    DESCRIPTION
        "Entry for the cfprBiosVfIntelVTForDirectedIOTable table."
    INDEX { cfprBiosVfIntelVTForDirectedIOInstanceId }
    ::= { cfprBiosVfIntelVTForDirectedIOTable 1 }

CfprBiosVfIntelVTForDirectedIOEntry ::= SEQUENCE {
    cfprBiosVfIntelVTForDirectedIOInstanceId                         CfprManagedObjectId,
    cfprBiosVfIntelVTForDirectedIODn                                 CfprManagedObjectDn,
    cfprBiosVfIntelVTForDirectedIORn                                 SnmpAdminString,
    cfprBiosVfIntelVTForDirectedIOVpIntelVTDATSSupport               CfprBiosVfIntelVTForDirectedIOVpIntelVTDATSSupport,
    cfprBiosVfIntelVTForDirectedIOVpIntelVTDCoherencySupport         CfprBiosVfIntelVTForDirectedIOVpIntelVTDCoherencySupport,
    cfprBiosVfIntelVTForDirectedIOVpIntelVTDInterruptRemapping       CfprBiosVfIntelVTForDirectedIOVpIntelVTDInterruptRemapping,
    cfprBiosVfIntelVTForDirectedIOVpIntelVTDPassThroughDMASupport    CfprBiosVfIntelVTForDirectedIOVpIntelVTDPassThroughDMASupport,
    cfprBiosVfIntelVTForDirectedIOVpIntelVTForDirectedIO             CfprBiosVfIntelVTForDirectedIOVpIntelVTForDirectedIO,
    cfprBiosVfIntelVTForDirectedIOSupportedByDefault                 CfprBiosSupportedAction
}

cfprBiosVfIntelVTForDirectedIOInstanceId OBJECT-TYPE
    SYNTAX       CfprManagedObjectId
    MAX-ACCESS   not-accessible
    STATUS       current
    DESCRIPTION
        "Instance identifier of the managed object."
    ::= { cfprBiosVfIntelVTForDirectedIOEntry 1 }

cfprBiosVfIntelVTForDirectedIODn OBJECT-TYPE
    SYNTAX       CfprManagedObjectDn
    MAX-ACCESS   read-only
    STATUS       current
    DESCRIPTION
        "Cisco Firepower bios:VfIntelVTForDirectedIO:dn
        managed object property"
    ::= { cfprBiosVfIntelVTForDirectedIOEntry 2 }

cfprBiosVfIntelVTForDirectedIORn OBJECT-TYPE
    SYNTAX       SnmpAdminString
    MAX-ACCESS   read-only
    STATUS       current
    DESCRIPTION
        "Cisco Firepower bios:VfIntelVTForDirectedIO:rn
        managed object property"
    ::= { cfprBiosVfIntelVTForDirectedIOEntry 3 }

cfprBiosVfIntelVTForDirectedIOVpIntelVTDATSSupport OBJECT-TYPE
    SYNTAX       CfprBiosVfIntelVTForDirectedIOVpIntelVTDATSSupport
    MAX-ACCESS   read-only
    STATUS       current
    DESCRIPTION
        "Cisco Firepower bios:VfIntelVTForDirectedIO:vpIntelVTDATSSupport
        managed object property"
    ::= { cfprBiosVfIntelVTForDirectedIOEntry 4 }

cfprBiosVfIntelVTForDirectedIOVpIntelVTDCoherencySupport OBJECT-TYPE
    SYNTAX       CfprBiosVfIntelVTForDirectedIOVpIntelVTDCoherencySupport
    MAX-ACCESS   read-only
    STATUS       current
    DESCRIPTION
        "Cisco Firepower bios:VfIntelVTForDirectedIO:vpIntelVTDCoherencySu
        pport managed object property"
    ::= { cfprBiosVfIntelVTForDirectedIOEntry 5 }

cfprBiosVfIntelVTForDirectedIOVpIntelVTDInterruptRemapping OBJECT-TYPE
    SYNTAX       CfprBiosVfIntelVTForDirectedIOVpIntelVTDInterruptRemapping
    MAX-ACCESS   read-only
    STATUS       current
    DESCRIPTION
        "Cisco Firepower bios:VfIntelVTForDirectedIO:vpIntelVTDInterruptRe
        mapping managed object property"
    ::= { cfprBiosVfIntelVTForDirectedIOEntry 6 }

cfprBiosVfIntelVTForDirectedIOVpIntelVTDPassThroughDMASupport OBJECT-TYPE
    SYNTAX       CfprBiosVfIntelVTForDirectedIOVpIntelVTDPassThroughDMASupport
    MAX-ACCESS   read-only
    STATUS       current
    DESCRIPTION
        "Cisco Firepower bios:VfIntelVTForDirectedIO:vpIntelVTDPassThrough
        DMASupport managed object property"
    ::= { cfprBiosVfIntelVTForDirectedIOEntry 7 }

cfprBiosVfIntelVTForDirectedIOVpIntelVTForDirectedIO OBJECT-TYPE
    SYNTAX       CfprBiosVfIntelVTForDirectedIOVpIntelVTForDirectedIO
    MAX-ACCESS   read-only
    STATUS       current
    DESCRIPTION
        "Cisco Firepower bios:VfIntelVTForDirectedIO:vpIntelVTForDirectedI
        O managed object property"
    ::= { cfprBiosVfIntelVTForDirectedIOEntry 8 }

cfprBiosVfIntelVTForDirectedIOSupportedByDefault OBJECT-TYPE
    SYNTAX       CfprBiosSupportedAction
    MAX-ACCESS   read-only
    STATUS       current
    DESCRIPTION
        "Cisco Firepower bios:VfIntelVTForDirectedIO:supportedByDefault
        managed object property"
    ::= { cfprBiosVfIntelVTForDirectedIOEntry 9 }

cfprBiosVfIntelVirtualizationTechnologyTable OBJECT-TYPE
    SYNTAX           SEQUENCE OF CfprBiosVfIntelVirtualizationTechnologyEntry
    MAX-ACCESS       not-accessible
    STATUS           current
    DESCRIPTION
        "Cisco Firepower bios:VfIntelVirtualizationTechnology
        managed object table"
    ::= { cfprBiosObjects 33 }

cfprBiosVfIntelVirtualizationTechnologyEntry OBJECT-TYPE
    SYNTAX           CfprBiosVfIntelVirtualizationTechnologyEntry
    MAX-ACCESS       not-accessible
    STATUS           current
    DESCRIPTION
        "Entry for the cfprBiosVfIntelVirtualizationTechnologyTable table."
    INDEX { cfprBiosVfIntelVirtualizationTechnologyInstanceId }
    ::= { cfprBiosVfIntelVirtualizationTechnologyTable 1 }

CfprBiosVfIntelVirtualizationTechnologyEntry ::= SEQUENCE {
    cfprBiosVfIntelVirtualizationTechnologyInstanceId                CfprManagedObjectId,
    cfprBiosVfIntelVirtualizationTechnologyDn                        CfprManagedObjectDn,
    cfprBiosVfIntelVirtualizationTechnologyRn                        SnmpAdminString,
    cfprBiosVfIntelVirtualizationTechnologyVpIntelVirtualizationTechnology CfprBiosVfIntelVirtualizationTechnologyVpIntelVirtTechnology,
    cfprBiosVfIntelVirtualizationTechnologySupportedByDefault        CfprBiosSupportedAction
}

cfprBiosVfIntelVirtualizationTechnologyInstanceId OBJECT-TYPE
    SYNTAX       CfprManagedObjectId
    MAX-ACCESS   not-accessible
    STATUS       current
    DESCRIPTION
        "Instance identifier of the managed object."
    ::= { cfprBiosVfIntelVirtualizationTechnologyEntry 1 }

cfprBiosVfIntelVirtualizationTechnologyDn OBJECT-TYPE
    SYNTAX       CfprManagedObjectDn
    MAX-ACCESS   read-only
    STATUS       current
    DESCRIPTION
        "Cisco Firepower bios:VfIntelVirtualizationTechnology:dn
        managed object property"
    ::= { cfprBiosVfIntelVirtualizationTechnologyEntry 2 }

cfprBiosVfIntelVirtualizationTechnologyRn OBJECT-TYPE
    SYNTAX       SnmpAdminString
    MAX-ACCESS   read-only
    STATUS       current
    DESCRIPTION
        "Cisco Firepower bios:VfIntelVirtualizationTechnology:rn
        managed object property"
    ::= { cfprBiosVfIntelVirtualizationTechnologyEntry 3 }

cfprBiosVfIntelVirtualizationTechnologyVpIntelVirtualizationTechnology OBJECT-TYPE
    SYNTAX       CfprBiosVfIntelVirtualizationTechnologyVpIntelVirtTechnology
    MAX-ACCESS   read-only
    STATUS       current
    DESCRIPTION
        "Cisco Firepower bios:VfIntelVirtualizationTechnology:vpIntelVirtu
        alizationTechnology managed object property"
    ::= { cfprBiosVfIntelVirtualizationTechnologyEntry 4 }

cfprBiosVfIntelVirtualizationTechnologySupportedByDefault OBJECT-TYPE
    SYNTAX       CfprBiosSupportedAction
    MAX-ACCESS   read-only
    STATUS       current
    DESCRIPTION
        "Cisco Firepower bios:VfIntelVirtualizationTechnology:supportedByD
        efault managed object property"
    ::= { cfprBiosVfIntelVirtualizationTechnologyEntry 5 }

cfprBiosVfInterleaveConfigurationTable OBJECT-TYPE
    SYNTAX           SEQUENCE OF CfprBiosVfInterleaveConfigurationEntry
    MAX-ACCESS       not-accessible
    STATUS           current
    DESCRIPTION
        "Cisco Firepower bios:VfInterleaveConfiguration
        managed object table"
    ::= { cfprBiosObjects 34 }

cfprBiosVfInterleaveConfigurationEntry OBJECT-TYPE
    SYNTAX           CfprBiosVfInterleaveConfigurationEntry
    MAX-ACCESS       not-accessible
    STATUS           current
    DESCRIPTION
        "Entry for the cfprBiosVfInterleaveConfigurationTable table."
    INDEX { cfprBiosVfInterleaveConfigurationInstanceId }
    ::= { cfprBiosVfInterleaveConfigurationTable 1 }

CfprBiosVfInterleaveConfigurationEntry ::= SEQUENCE {
    cfprBiosVfInterleaveConfigurationInstanceId                      CfprManagedObjectId,
    cfprBiosVfInterleaveConfigurationDn                              CfprManagedObjectDn,
    cfprBiosVfInterleaveConfigurationRn                              SnmpAdminString,
    cfprBiosVfInterleaveConfigurationVpChannelInterleaving           CfprBiosVfInterleaveConfigurationVpChannelInterleaving,
    cfprBiosVfInterleaveConfigurationVpMemoryInterleaving            CfprBiosVfInterleaveConfigurationVpMemoryInterleaving,
    cfprBiosVfInterleaveConfigurationVpRankInterleaving              CfprBiosVfInterleaveConfigurationVpRankInterleaving,
    cfprBiosVfInterleaveConfigurationSupportedByDefault              CfprBiosSupportedAction
}

cfprBiosVfInterleaveConfigurationInstanceId OBJECT-TYPE
    SYNTAX       CfprManagedObjectId
    MAX-ACCESS   not-accessible
    STATUS       current
    DESCRIPTION
        "Instance identifier of the managed object."
    ::= { cfprBiosVfInterleaveConfigurationEntry 1 }

cfprBiosVfInterleaveConfigurationDn OBJECT-TYPE
    SYNTAX       CfprManagedObjectDn
    MAX-ACCESS   read-only
    STATUS       current
    DESCRIPTION
        "Cisco Firepower bios:VfInterleaveConfiguration:dn
        managed object property"
    ::= { cfprBiosVfInterleaveConfigurationEntry 2 }

cfprBiosVfInterleaveConfigurationRn OBJECT-TYPE
    SYNTAX       SnmpAdminString
    MAX-ACCESS   read-only
    STATUS       current
    DESCRIPTION
        "Cisco Firepower bios:VfInterleaveConfiguration:rn
        managed object property"
    ::= { cfprBiosVfInterleaveConfigurationEntry 3 }

cfprBiosVfInterleaveConfigurationVpChannelInterleaving OBJECT-TYPE
    SYNTAX       CfprBiosVfInterleaveConfigurationVpChannelInterleaving
    MAX-ACCESS   read-only
    STATUS       current
    DESCRIPTION
        "Cisco Firepower bios:VfInterleaveConfiguration:vpChannelInterleav
        ing managed object property"
    ::= { cfprBiosVfInterleaveConfigurationEntry 4 }

cfprBiosVfInterleaveConfigurationVpMemoryInterleaving OBJECT-TYPE
    SYNTAX       CfprBiosVfInterleaveConfigurationVpMemoryInterleaving
    MAX-ACCESS   read-only
    STATUS       current
    DESCRIPTION
        "Cisco Firepower bios:VfInterleaveConfiguration:vpMemoryInterleavi
        ng managed object property"
    ::= { cfprBiosVfInterleaveConfigurationEntry 5 }

cfprBiosVfInterleaveConfigurationVpRankInterleaving OBJECT-TYPE
    SYNTAX       CfprBiosVfInterleaveConfigurationVpRankInterleaving
    MAX-ACCESS   read-only
    STATUS       current
    DESCRIPTION
        "Cisco Firepower bios:VfInterleaveConfiguration:vpRankInterleaving
         managed object property"
    ::= { cfprBiosVfInterleaveConfigurationEntry 6 }

cfprBiosVfInterleaveConfigurationSupportedByDefault OBJECT-TYPE
    SYNTAX       CfprBiosSupportedAction
    MAX-ACCESS   read-only
    STATUS       current
    DESCRIPTION
        "Cisco Firepower bios:VfInterleaveConfiguration:supportedByDefault
         managed object property"
    ::= { cfprBiosVfInterleaveConfigurationEntry 7 }

cfprBiosVfLocalX2ApicTable OBJECT-TYPE
    SYNTAX           SEQUENCE OF CfprBiosVfLocalX2ApicEntry
    MAX-ACCESS       not-accessible
    STATUS           current
    DESCRIPTION
        "Cisco Firepower bios:VfLocalX2Apic managed object table"
    ::= { cfprBiosObjects 35 }

cfprBiosVfLocalX2ApicEntry OBJECT-TYPE
    SYNTAX           CfprBiosVfLocalX2ApicEntry
    MAX-ACCESS       not-accessible
    STATUS           current
    DESCRIPTION
        "Entry for the cfprBiosVfLocalX2ApicTable table."
    INDEX { cfprBiosVfLocalX2ApicInstanceId }
    ::= { cfprBiosVfLocalX2ApicTable 1 }

CfprBiosVfLocalX2ApicEntry ::= SEQUENCE {
    cfprBiosVfLocalX2ApicInstanceId                                  CfprManagedObjectId,
    cfprBiosVfLocalX2ApicDn                                          CfprManagedObjectDn,
    cfprBiosVfLocalX2ApicRn                                          SnmpAdminString,
    cfprBiosVfLocalX2ApicVpLocalX2Apic                               CfprBiosVfLocalX2ApicVpLocalX2Apic,
    cfprBiosVfLocalX2ApicSupportedByDefault                          CfprBiosSupportedAction
}

cfprBiosVfLocalX2ApicInstanceId OBJECT-TYPE
    SYNTAX       CfprManagedObjectId
    MAX-ACCESS   not-accessible
    STATUS       current
    DESCRIPTION
        "Instance identifier of the managed object."
    ::= { cfprBiosVfLocalX2ApicEntry 1 }

cfprBiosVfLocalX2ApicDn OBJECT-TYPE
    SYNTAX       CfprManagedObjectDn
    MAX-ACCESS   read-only
    STATUS       current
    DESCRIPTION
        "Cisco Firepower bios:VfLocalX2Apic:dn managed object property"
    ::= { cfprBiosVfLocalX2ApicEntry 2 }

cfprBiosVfLocalX2ApicRn OBJECT-TYPE
    SYNTAX       SnmpAdminString
    MAX-ACCESS   read-only
    STATUS       current
    DESCRIPTION
        "Cisco Firepower bios:VfLocalX2Apic:rn managed object property"
    ::= { cfprBiosVfLocalX2ApicEntry 3 }

cfprBiosVfLocalX2ApicVpLocalX2Apic OBJECT-TYPE
    SYNTAX       CfprBiosVfLocalX2ApicVpLocalX2Apic
    MAX-ACCESS   read-only
    STATUS       current
    DESCRIPTION
        "Cisco Firepower bios:VfLocalX2Apic:vpLocalX2Apic
        managed object property"
    ::= { cfprBiosVfLocalX2ApicEntry 4 }

cfprBiosVfLocalX2ApicSupportedByDefault OBJECT-TYPE
    SYNTAX       CfprBiosSupportedAction
    MAX-ACCESS   read-only
    STATUS       current
    DESCRIPTION
        "Cisco Firepower bios:VfLocalX2Apic:supportedByDefault
        managed object property"
    ::= { cfprBiosVfLocalX2ApicEntry 5 }

cfprBiosVfLvDIMMSupportTable OBJECT-TYPE
    SYNTAX           SEQUENCE OF CfprBiosVfLvDIMMSupportEntry
    MAX-ACCESS       not-accessible
    STATUS           current
    DESCRIPTION
        "Cisco Firepower bios:VfLvDIMMSupport managed object table"
    ::= { cfprBiosObjects 36 }

cfprBiosVfLvDIMMSupportEntry OBJECT-TYPE
    SYNTAX           CfprBiosVfLvDIMMSupportEntry
    MAX-ACCESS       not-accessible
    STATUS           current
    DESCRIPTION
        "Entry for the cfprBiosVfLvDIMMSupportTable table."
    INDEX { cfprBiosVfLvDIMMSupportInstanceId }
    ::= { cfprBiosVfLvDIMMSupportTable 1 }

CfprBiosVfLvDIMMSupportEntry ::= SEQUENCE {
    cfprBiosVfLvDIMMSupportInstanceId                                CfprManagedObjectId,
    cfprBiosVfLvDIMMSupportDn                                        CfprManagedObjectDn,
    cfprBiosVfLvDIMMSupportRn                                        SnmpAdminString,
    cfprBiosVfLvDIMMSupportVpLvDDRMode                               CfprBiosVfLvDIMMSupportVpLvDDRMode,
    cfprBiosVfLvDIMMSupportSupportedByDefault                        CfprBiosSupportedAction
}

cfprBiosVfLvDIMMSupportInstanceId OBJECT-TYPE
    SYNTAX       CfprManagedObjectId
    MAX-ACCESS   not-accessible
    STATUS       current
    DESCRIPTION
        "Instance identifier of the managed object."
    ::= { cfprBiosVfLvDIMMSupportEntry 1 }

cfprBiosVfLvDIMMSupportDn OBJECT-TYPE
    SYNTAX       CfprManagedObjectDn
    MAX-ACCESS   read-only
    STATUS       current
    DESCRIPTION
        "Cisco Firepower bios:VfLvDIMMSupport:dn managed object property"
    ::= { cfprBiosVfLvDIMMSupportEntry 2 }

cfprBiosVfLvDIMMSupportRn OBJECT-TYPE
    SYNTAX       SnmpAdminString
    MAX-ACCESS   read-only
    STATUS       current
    DESCRIPTION
        "Cisco Firepower bios:VfLvDIMMSupport:rn managed object property"
    ::= { cfprBiosVfLvDIMMSupportEntry 3 }

cfprBiosVfLvDIMMSupportVpLvDDRMode OBJECT-TYPE
    SYNTAX       CfprBiosVfLvDIMMSupportVpLvDDRMode
    MAX-ACCESS   read-only
    STATUS       current
    DESCRIPTION
        "Cisco Firepower bios:VfLvDIMMSupport:vpLvDDRMode
        managed object property"
    ::= { cfprBiosVfLvDIMMSupportEntry 4 }

cfprBiosVfLvDIMMSupportSupportedByDefault OBJECT-TYPE
    SYNTAX       CfprBiosSupportedAction
    MAX-ACCESS   read-only
    STATUS       current
    DESCRIPTION
        "Cisco Firepower bios:VfLvDIMMSupport:supportedByDefault
        managed object property"
    ::= { cfprBiosVfLvDIMMSupportEntry 5 }

cfprBiosVfMaxVariableMTRRSettingTable OBJECT-TYPE
    SYNTAX           SEQUENCE OF CfprBiosVfMaxVariableMTRRSettingEntry
    MAX-ACCESS       not-accessible
    STATUS           current
    DESCRIPTION
        "Cisco Firepower bios:VfMaxVariableMTRRSetting
        managed object table"
    ::= { cfprBiosObjects 37 }

cfprBiosVfMaxVariableMTRRSettingEntry OBJECT-TYPE
    SYNTAX           CfprBiosVfMaxVariableMTRRSettingEntry
    MAX-ACCESS       not-accessible
    STATUS           current
    DESCRIPTION
        "Entry for the cfprBiosVfMaxVariableMTRRSettingTable table."
    INDEX { cfprBiosVfMaxVariableMTRRSettingInstanceId }
    ::= { cfprBiosVfMaxVariableMTRRSettingTable 1 }

CfprBiosVfMaxVariableMTRRSettingEntry ::= SEQUENCE {
    cfprBiosVfMaxVariableMTRRSettingInstanceId                       CfprManagedObjectId,
    cfprBiosVfMaxVariableMTRRSettingDn                               CfprManagedObjectDn,
    cfprBiosVfMaxVariableMTRRSettingRn                               SnmpAdminString,
    cfprBiosVfMaxVariableMTRRSettingVpProcessorMtrr                  CfprBiosVfMaxVariableMTRRSettingVpProcessorMtrr,
    cfprBiosVfMaxVariableMTRRSettingSupportedByDefault               CfprBiosSupportedAction
}

cfprBiosVfMaxVariableMTRRSettingInstanceId OBJECT-TYPE
    SYNTAX       CfprManagedObjectId
    MAX-ACCESS   not-accessible
    STATUS       current
    DESCRIPTION
        "Instance identifier of the managed object."
    ::= { cfprBiosVfMaxVariableMTRRSettingEntry 1 }

cfprBiosVfMaxVariableMTRRSettingDn OBJECT-TYPE
    SYNTAX       CfprManagedObjectDn
    MAX-ACCESS   read-only
    STATUS       current
    DESCRIPTION
        "Cisco Firepower bios:VfMaxVariableMTRRSetting:dn
        managed object property"
    ::= { cfprBiosVfMaxVariableMTRRSettingEntry 2 }

cfprBiosVfMaxVariableMTRRSettingRn OBJECT-TYPE
    SYNTAX       SnmpAdminString
    MAX-ACCESS   read-only
    STATUS       current
    DESCRIPTION
        "Cisco Firepower bios:VfMaxVariableMTRRSetting:rn
        managed object property"
    ::= { cfprBiosVfMaxVariableMTRRSettingEntry 3 }

cfprBiosVfMaxVariableMTRRSettingVpProcessorMtrr OBJECT-TYPE
    SYNTAX       CfprBiosVfMaxVariableMTRRSettingVpProcessorMtrr
    MAX-ACCESS   read-only
    STATUS       current
    DESCRIPTION
        "Cisco Firepower bios:VfMaxVariableMTRRSetting:vpProcessorMtrr
        managed object property"
    ::= { cfprBiosVfMaxVariableMTRRSettingEntry 4 }

cfprBiosVfMaxVariableMTRRSettingSupportedByDefault OBJECT-TYPE
    SYNTAX       CfprBiosSupportedAction
    MAX-ACCESS   read-only
    STATUS       current
    DESCRIPTION
        "Cisco Firepower bios:VfMaxVariableMTRRSetting:supportedByDefault
        managed object property"
    ::= { cfprBiosVfMaxVariableMTRRSettingEntry 5 }

cfprBiosVfMaximumMemoryBelow4GBTable OBJECT-TYPE
    SYNTAX           SEQUENCE OF CfprBiosVfMaximumMemoryBelow4GBEntry
    MAX-ACCESS       not-accessible
    STATUS           current
    DESCRIPTION
        "Cisco Firepower bios:VfMaximumMemoryBelow4GB managed
        object table"
    ::= { cfprBiosObjects 38 }

cfprBiosVfMaximumMemoryBelow4GBEntry OBJECT-TYPE
    SYNTAX           CfprBiosVfMaximumMemoryBelow4GBEntry
    MAX-ACCESS       not-accessible
    STATUS           current
    DESCRIPTION
        "Entry for the cfprBiosVfMaximumMemoryBelow4GBTable table."
    INDEX { cfprBiosVfMaximumMemoryBelow4GBInstanceId }
    ::= { cfprBiosVfMaximumMemoryBelow4GBTable 1 }

CfprBiosVfMaximumMemoryBelow4GBEntry ::= SEQUENCE {
    cfprBiosVfMaximumMemoryBelow4GBInstanceId                        CfprManagedObjectId,
    cfprBiosVfMaximumMemoryBelow4GBDn                                CfprManagedObjectDn,
    cfprBiosVfMaximumMemoryBelow4GBRn                                SnmpAdminString,
    cfprBiosVfMaximumMemoryBelow4GBVpMaximumMemoryBelow4GB           CfprBiosVfMaximumMemoryBelow4GBVpMaximumMemoryBelow4GB,
    cfprBiosVfMaximumMemoryBelow4GBSupportedByDefault                CfprBiosSupportedAction
}

cfprBiosVfMaximumMemoryBelow4GBInstanceId OBJECT-TYPE
    SYNTAX       CfprManagedObjectId
    MAX-ACCESS   not-accessible
    STATUS       current
    DESCRIPTION
        "Instance identifier of the managed object."
    ::= { cfprBiosVfMaximumMemoryBelow4GBEntry 1 }

cfprBiosVfMaximumMemoryBelow4GBDn OBJECT-TYPE
    SYNTAX       CfprManagedObjectDn
    MAX-ACCESS   read-only
    STATUS       current
    DESCRIPTION
        "Cisco Firepower bios:VfMaximumMemoryBelow4GB:dn
        managed object property"
    ::= { cfprBiosVfMaximumMemoryBelow4GBEntry 2 }

cfprBiosVfMaximumMemoryBelow4GBRn OBJECT-TYPE
    SYNTAX       SnmpAdminString
    MAX-ACCESS   read-only
    STATUS       current
    DESCRIPTION
        "Cisco Firepower bios:VfMaximumMemoryBelow4GB:rn
        managed object property"
    ::= { cfprBiosVfMaximumMemoryBelow4GBEntry 3 }

cfprBiosVfMaximumMemoryBelow4GBVpMaximumMemoryBelow4GB OBJECT-TYPE
    SYNTAX       CfprBiosVfMaximumMemoryBelow4GBVpMaximumMemoryBelow4GB
    MAX-ACCESS   read-only
    STATUS       current
    DESCRIPTION
        "Cisco Firepower bios:VfMaximumMemoryBelow4GB:vpMaximumMemoryBelow
        4GB managed object property"
    ::= { cfprBiosVfMaximumMemoryBelow4GBEntry 4 }

cfprBiosVfMaximumMemoryBelow4GBSupportedByDefault OBJECT-TYPE
    SYNTAX       CfprBiosSupportedAction
    MAX-ACCESS   read-only
    STATUS       current
    DESCRIPTION
        "Cisco Firepower bios:VfMaximumMemoryBelow4GB:supportedByDefault
        managed object property"
    ::= { cfprBiosVfMaximumMemoryBelow4GBEntry 5 }

cfprBiosVfMemoryMappedIOAbove4GBTable OBJECT-TYPE
    SYNTAX           SEQUENCE OF CfprBiosVfMemoryMappedIOAbove4GBEntry
    MAX-ACCESS       not-accessible
    STATUS           current
    DESCRIPTION
        "Cisco Firepower bios:VfMemoryMappedIOAbove4GB
        managed object table"
    ::= { cfprBiosObjects 39 }

cfprBiosVfMemoryMappedIOAbove4GBEntry OBJECT-TYPE
    SYNTAX           CfprBiosVfMemoryMappedIOAbove4GBEntry
    MAX-ACCESS       not-accessible
    STATUS           current
    DESCRIPTION
        "Entry for the cfprBiosVfMemoryMappedIOAbove4GBTable table."
    INDEX { cfprBiosVfMemoryMappedIOAbove4GBInstanceId }
    ::= { cfprBiosVfMemoryMappedIOAbove4GBTable 1 }

CfprBiosVfMemoryMappedIOAbove4GBEntry ::= SEQUENCE {
    cfprBiosVfMemoryMappedIOAbove4GBInstanceId                       CfprManagedObjectId,
    cfprBiosVfMemoryMappedIOAbove4GBDn                               CfprManagedObjectDn,
    cfprBiosVfMemoryMappedIOAbove4GBRn                               SnmpAdminString,
    cfprBiosVfMemoryMappedIOAbove4GBVpMemoryMappedIOAbove4GB         CfprBiosVfMemoryMappedIOAbove4GBVpMemoryMappedIOAbove4GB,
    cfprBiosVfMemoryMappedIOAbove4GBSupportedByDefault               CfprBiosSupportedAction
}

cfprBiosVfMemoryMappedIOAbove4GBInstanceId OBJECT-TYPE
    SYNTAX       CfprManagedObjectId
    MAX-ACCESS   not-accessible
    STATUS       current
    DESCRIPTION
        "Instance identifier of the managed object."
    ::= { cfprBiosVfMemoryMappedIOAbove4GBEntry 1 }

cfprBiosVfMemoryMappedIOAbove4GBDn OBJECT-TYPE
    SYNTAX       CfprManagedObjectDn
    MAX-ACCESS   read-only
    STATUS       current
    DESCRIPTION
        "Cisco Firepower bios:VfMemoryMappedIOAbove4GB:dn
        managed object property"
    ::= { cfprBiosVfMemoryMappedIOAbove4GBEntry 2 }

cfprBiosVfMemoryMappedIOAbove4GBRn OBJECT-TYPE
    SYNTAX       SnmpAdminString
    MAX-ACCESS   read-only
    STATUS       current
    DESCRIPTION
        "Cisco Firepower bios:VfMemoryMappedIOAbove4GB:rn
        managed object property"
    ::= { cfprBiosVfMemoryMappedIOAbove4GBEntry 3 }

cfprBiosVfMemoryMappedIOAbove4GBVpMemoryMappedIOAbove4GB OBJECT-TYPE
    SYNTAX       CfprBiosVfMemoryMappedIOAbove4GBVpMemoryMappedIOAbove4GB
    MAX-ACCESS   read-only
    STATUS       current
    DESCRIPTION
        "Cisco Firepower bios:VfMemoryMappedIOAbove4GB:vpMemoryMappedIOAbo
        ve4GB managed object property"
    ::= { cfprBiosVfMemoryMappedIOAbove4GBEntry 4 }

cfprBiosVfMemoryMappedIOAbove4GBSupportedByDefault OBJECT-TYPE
    SYNTAX       CfprBiosSupportedAction
    MAX-ACCESS   read-only
    STATUS       current
    DESCRIPTION
        "Cisco Firepower bios:VfMemoryMappedIOAbove4GB:supportedByDefault
        managed object property"
    ::= { cfprBiosVfMemoryMappedIOAbove4GBEntry 5 }

cfprBiosVfMirroringModeTable OBJECT-TYPE
    SYNTAX           SEQUENCE OF CfprBiosVfMirroringModeEntry
    MAX-ACCESS       not-accessible
    STATUS           current
    DESCRIPTION
        "Cisco Firepower bios:VfMirroringMode managed object table"
    ::= { cfprBiosObjects 40 }

cfprBiosVfMirroringModeEntry OBJECT-TYPE
    SYNTAX           CfprBiosVfMirroringModeEntry
    MAX-ACCESS       not-accessible
    STATUS           current
    DESCRIPTION
        "Entry for the cfprBiosVfMirroringModeTable table."
    INDEX { cfprBiosVfMirroringModeInstanceId }
    ::= { cfprBiosVfMirroringModeTable 1 }

CfprBiosVfMirroringModeEntry ::= SEQUENCE {
    cfprBiosVfMirroringModeInstanceId                                CfprManagedObjectId,
    cfprBiosVfMirroringModeDn                                        CfprManagedObjectDn,
    cfprBiosVfMirroringModeRn                                        SnmpAdminString,
    cfprBiosVfMirroringModeVpMirroringMode                           CfprBiosVfMirroringModeVpMirroringMode,
    cfprBiosVfMirroringModeSupportedByDefault                        CfprBiosSupportedAction
}

cfprBiosVfMirroringModeInstanceId OBJECT-TYPE
    SYNTAX       CfprManagedObjectId
    MAX-ACCESS   not-accessible
    STATUS       current
    DESCRIPTION
        "Instance identifier of the managed object."
    ::= { cfprBiosVfMirroringModeEntry 1 }

cfprBiosVfMirroringModeDn OBJECT-TYPE
    SYNTAX       CfprManagedObjectDn
    MAX-ACCESS   read-only
    STATUS       current
    DESCRIPTION
        "Cisco Firepower bios:VfMirroringMode:dn managed object property"
    ::= { cfprBiosVfMirroringModeEntry 2 }

cfprBiosVfMirroringModeRn OBJECT-TYPE
    SYNTAX       SnmpAdminString
    MAX-ACCESS   read-only
    STATUS       current
    DESCRIPTION
        "Cisco Firepower bios:VfMirroringMode:rn managed object property"
    ::= { cfprBiosVfMirroringModeEntry 3 }

cfprBiosVfMirroringModeVpMirroringMode OBJECT-TYPE
    SYNTAX       CfprBiosVfMirroringModeVpMirroringMode
    MAX-ACCESS   read-only
    STATUS       current
    DESCRIPTION
        "Cisco Firepower bios:VfMirroringMode:vpMirroringMode
        managed object property"
    ::= { cfprBiosVfMirroringModeEntry 4 }

cfprBiosVfMirroringModeSupportedByDefault OBJECT-TYPE
    SYNTAX       CfprBiosSupportedAction
    MAX-ACCESS   read-only
    STATUS       current
    DESCRIPTION
        "Cisco Firepower bios:VfMirroringMode:supportedByDefault
        managed object property"
    ::= { cfprBiosVfMirroringModeEntry 5 }

cfprBiosVfNUMAOptimizedTable OBJECT-TYPE
    SYNTAX           SEQUENCE OF CfprBiosVfNUMAOptimizedEntry
    MAX-ACCESS       not-accessible
    STATUS           current
    DESCRIPTION
        "Cisco Firepower bios:VfNUMAOptimized managed object table"
    ::= { cfprBiosObjects 41 }

cfprBiosVfNUMAOptimizedEntry OBJECT-TYPE
    SYNTAX           CfprBiosVfNUMAOptimizedEntry
    MAX-ACCESS       not-accessible
    STATUS           current
    DESCRIPTION
        "Entry for the cfprBiosVfNUMAOptimizedTable table."
    INDEX { cfprBiosVfNUMAOptimizedInstanceId }
    ::= { cfprBiosVfNUMAOptimizedTable 1 }

CfprBiosVfNUMAOptimizedEntry ::= SEQUENCE {
    cfprBiosVfNUMAOptimizedInstanceId                                CfprManagedObjectId,
    cfprBiosVfNUMAOptimizedDn                                        CfprManagedObjectDn,
    cfprBiosVfNUMAOptimizedRn                                        SnmpAdminString,
    cfprBiosVfNUMAOptimizedVpNUMAOptimized                           CfprBiosVfNUMAOptimizedVpNUMAOptimized,
    cfprBiosVfNUMAOptimizedSupportedByDefault                        CfprBiosSupportedAction
}

cfprBiosVfNUMAOptimizedInstanceId OBJECT-TYPE
    SYNTAX       CfprManagedObjectId
    MAX-ACCESS   not-accessible
    STATUS       current
    DESCRIPTION
        "Instance identifier of the managed object."
    ::= { cfprBiosVfNUMAOptimizedEntry 1 }

cfprBiosVfNUMAOptimizedDn OBJECT-TYPE
    SYNTAX       CfprManagedObjectDn
    MAX-ACCESS   read-only
    STATUS       current
    DESCRIPTION
        "Cisco Firepower bios:VfNUMAOptimized:dn managed object property"
    ::= { cfprBiosVfNUMAOptimizedEntry 2 }

cfprBiosVfNUMAOptimizedRn OBJECT-TYPE
    SYNTAX       SnmpAdminString
    MAX-ACCESS   read-only
    STATUS       current
    DESCRIPTION
        "Cisco Firepower bios:VfNUMAOptimized:rn managed object property"
    ::= { cfprBiosVfNUMAOptimizedEntry 3 }

cfprBiosVfNUMAOptimizedVpNUMAOptimized OBJECT-TYPE
    SYNTAX       CfprBiosVfNUMAOptimizedVpNUMAOptimized
    MAX-ACCESS   read-only
    STATUS       current
    DESCRIPTION
        "Cisco Firepower bios:VfNUMAOptimized:vpNUMAOptimized
        managed object property"
    ::= { cfprBiosVfNUMAOptimizedEntry 4 }

cfprBiosVfNUMAOptimizedSupportedByDefault OBJECT-TYPE
    SYNTAX       CfprBiosSupportedAction
    MAX-ACCESS   read-only
    STATUS       current
    DESCRIPTION
        "Cisco Firepower bios:VfNUMAOptimized:supportedByDefault
        managed object property"
    ::= { cfprBiosVfNUMAOptimizedEntry 5 }

cfprBiosVfOSBootWatchdogTimerTable OBJECT-TYPE
    SYNTAX           SEQUENCE OF CfprBiosVfOSBootWatchdogTimerEntry
    MAX-ACCESS       not-accessible
    STATUS           current
    DESCRIPTION
        "Cisco Firepower bios:VfOSBootWatchdogTimer managed object table"
    ::= { cfprBiosObjects 42 }

cfprBiosVfOSBootWatchdogTimerEntry OBJECT-TYPE
    SYNTAX           CfprBiosVfOSBootWatchdogTimerEntry
    MAX-ACCESS       not-accessible
    STATUS           current
    DESCRIPTION
        "Entry for the cfprBiosVfOSBootWatchdogTimerTable table."
    INDEX { cfprBiosVfOSBootWatchdogTimerInstanceId }
    ::= { cfprBiosVfOSBootWatchdogTimerTable 1 }

CfprBiosVfOSBootWatchdogTimerEntry ::= SEQUENCE {
    cfprBiosVfOSBootWatchdogTimerInstanceId                          CfprManagedObjectId,
    cfprBiosVfOSBootWatchdogTimerDn                                  CfprManagedObjectDn,
    cfprBiosVfOSBootWatchdogTimerRn                                  SnmpAdminString,
    cfprBiosVfOSBootWatchdogTimerVpOSBootWatchdogTimer               CfprBiosVfOSBootWatchdogTimerVpOSBootWatchdogTimer,
    cfprBiosVfOSBootWatchdogTimerSupportedByDefault                  CfprBiosSupportedAction
}

cfprBiosVfOSBootWatchdogTimerInstanceId OBJECT-TYPE
    SYNTAX       CfprManagedObjectId
    MAX-ACCESS   not-accessible
    STATUS       current
    DESCRIPTION
        "Instance identifier of the managed object."
    ::= { cfprBiosVfOSBootWatchdogTimerEntry 1 }

cfprBiosVfOSBootWatchdogTimerDn OBJECT-TYPE
    SYNTAX       CfprManagedObjectDn
    MAX-ACCESS   read-only
    STATUS       current
    DESCRIPTION
        "Cisco Firepower bios:VfOSBootWatchdogTimer:dn
        managed object property"
    ::= { cfprBiosVfOSBootWatchdogTimerEntry 2 }

cfprBiosVfOSBootWatchdogTimerRn OBJECT-TYPE
    SYNTAX       SnmpAdminString
    MAX-ACCESS   read-only
    STATUS       current
    DESCRIPTION
        "Cisco Firepower bios:VfOSBootWatchdogTimer:rn
        managed object property"
    ::= { cfprBiosVfOSBootWatchdogTimerEntry 3 }

cfprBiosVfOSBootWatchdogTimerVpOSBootWatchdogTimer OBJECT-TYPE
    SYNTAX       CfprBiosVfOSBootWatchdogTimerVpOSBootWatchdogTimer
    MAX-ACCESS   read-only
    STATUS       current
    DESCRIPTION
        "Cisco Firepower bios:VfOSBootWatchdogTimer:vpOSBootWatchdogTimer
        managed object property"
    ::= { cfprBiosVfOSBootWatchdogTimerEntry 4 }

cfprBiosVfOSBootWatchdogTimerSupportedByDefault OBJECT-TYPE
    SYNTAX       CfprBiosSupportedAction
    MAX-ACCESS   read-only
    STATUS       current
    DESCRIPTION
        "Cisco Firepower bios:VfOSBootWatchdogTimer:supportedByDefault
        managed object property"
    ::= { cfprBiosVfOSBootWatchdogTimerEntry 5 }

cfprBiosVfOSBootWatchdogTimerPolicyTable OBJECT-TYPE
    SYNTAX           SEQUENCE OF CfprBiosVfOSBootWatchdogTimerPolicyEntry
    MAX-ACCESS       not-accessible
    STATUS           current
    DESCRIPTION
        "Cisco Firepower bios:VfOSBootWatchdogTimerPolicy
        managed object table"
    ::= { cfprBiosObjects 43 }

cfprBiosVfOSBootWatchdogTimerPolicyEntry OBJECT-TYPE
    SYNTAX           CfprBiosVfOSBootWatchdogTimerPolicyEntry
    MAX-ACCESS       not-accessible
    STATUS           current
    DESCRIPTION
        "Entry for the cfprBiosVfOSBootWatchdogTimerPolicyTable table."
    INDEX { cfprBiosVfOSBootWatchdogTimerPolicyInstanceId }
    ::= { cfprBiosVfOSBootWatchdogTimerPolicyTable 1 }

CfprBiosVfOSBootWatchdogTimerPolicyEntry ::= SEQUENCE {
    cfprBiosVfOSBootWatchdogTimerPolicyInstanceId                    CfprManagedObjectId,
    cfprBiosVfOSBootWatchdogTimerPolicyDn                            CfprManagedObjectDn,
    cfprBiosVfOSBootWatchdogTimerPolicyRn                            SnmpAdminString,
    cfprBiosVfOSBootWatchdogTimerPolicyVpOSBootWatchdogTimerPolicy   CfprBiosVfOSBootWatchdogTimerPolicyVpOSBootWatchdogTimerPolicy,
    cfprBiosVfOSBootWatchdogTimerPolicySupportedByDefault            CfprBiosSupportedAction
}

cfprBiosVfOSBootWatchdogTimerPolicyInstanceId OBJECT-TYPE
    SYNTAX       CfprManagedObjectId
    MAX-ACCESS   not-accessible
    STATUS       current
    DESCRIPTION
        "Instance identifier of the managed object."
    ::= { cfprBiosVfOSBootWatchdogTimerPolicyEntry 1 }

cfprBiosVfOSBootWatchdogTimerPolicyDn OBJECT-TYPE
    SYNTAX       CfprManagedObjectDn
    MAX-ACCESS   read-only
    STATUS       current
    DESCRIPTION
        "Cisco Firepower bios:VfOSBootWatchdogTimerPolicy:dn
        managed object property"
    ::= { cfprBiosVfOSBootWatchdogTimerPolicyEntry 2 }

cfprBiosVfOSBootWatchdogTimerPolicyRn OBJECT-TYPE
    SYNTAX       SnmpAdminString
    MAX-ACCESS   read-only
    STATUS       current
    DESCRIPTION
        "Cisco Firepower bios:VfOSBootWatchdogTimerPolicy:rn
        managed object property"
    ::= { cfprBiosVfOSBootWatchdogTimerPolicyEntry 3 }

cfprBiosVfOSBootWatchdogTimerPolicyVpOSBootWatchdogTimerPolicy OBJECT-TYPE
    SYNTAX       CfprBiosVfOSBootWatchdogTimerPolicyVpOSBootWatchdogTimerPolicy
    MAX-ACCESS   read-only
    STATUS       current
    DESCRIPTION
        "Cisco Firepower bios:VfOSBootWatchdogTimerPolicy:vpOSBootWatchdog
        TimerPolicy managed object property"
    ::= { cfprBiosVfOSBootWatchdogTimerPolicyEntry 4 }

cfprBiosVfOSBootWatchdogTimerPolicySupportedByDefault OBJECT-TYPE
    SYNTAX       CfprBiosSupportedAction
    MAX-ACCESS   read-only
    STATUS       current
    DESCRIPTION
        "Cisco Firepower bios:VfOSBootWatchdogTimerPolicy:supportedByDefau
        lt managed object property"
    ::= { cfprBiosVfOSBootWatchdogTimerPolicyEntry 5 }

cfprBiosVfOSBootWatchdogTimerTimeoutTable OBJECT-TYPE
    SYNTAX           SEQUENCE OF CfprBiosVfOSBootWatchdogTimerTimeoutEntry
    MAX-ACCESS       not-accessible
    STATUS           current
    DESCRIPTION
        "Cisco Firepower bios:VfOSBootWatchdogTimerTimeout
        managed object table"
    ::= { cfprBiosObjects 44 }

cfprBiosVfOSBootWatchdogTimerTimeoutEntry OBJECT-TYPE
    SYNTAX           CfprBiosVfOSBootWatchdogTimerTimeoutEntry
    MAX-ACCESS       not-accessible
    STATUS           current
    DESCRIPTION
        "Entry for the cfprBiosVfOSBootWatchdogTimerTimeoutTable table."
    INDEX { cfprBiosVfOSBootWatchdogTimerTimeoutInstanceId }
    ::= { cfprBiosVfOSBootWatchdogTimerTimeoutTable 1 }

CfprBiosVfOSBootWatchdogTimerTimeoutEntry ::= SEQUENCE {
    cfprBiosVfOSBootWatchdogTimerTimeoutInstanceId                   CfprManagedObjectId,
    cfprBiosVfOSBootWatchdogTimerTimeoutDn                           CfprManagedObjectDn,
    cfprBiosVfOSBootWatchdogTimerTimeoutRn                           SnmpAdminString,
    cfprBiosVfOSBootWatchdogTimerTimeoutVpOSBootWatchdogTimerTimeout CfprBiosVfOSBootWatchdogTimerTimeoutVpOSBootWatchdogTimerTimeout,
    cfprBiosVfOSBootWatchdogTimerTimeoutSupportedByDefault           CfprBiosSupportedAction
}

cfprBiosVfOSBootWatchdogTimerTimeoutInstanceId OBJECT-TYPE
    SYNTAX       CfprManagedObjectId
    MAX-ACCESS   not-accessible
    STATUS       current
    DESCRIPTION
        "Instance identifier of the managed object."
    ::= { cfprBiosVfOSBootWatchdogTimerTimeoutEntry 1 }

cfprBiosVfOSBootWatchdogTimerTimeoutDn OBJECT-TYPE
    SYNTAX       CfprManagedObjectDn
    MAX-ACCESS   read-only
    STATUS       current
    DESCRIPTION
        "Cisco Firepower bios:VfOSBootWatchdogTimerTimeout:dn
        managed object property"
    ::= { cfprBiosVfOSBootWatchdogTimerTimeoutEntry 2 }

cfprBiosVfOSBootWatchdogTimerTimeoutRn OBJECT-TYPE
    SYNTAX       SnmpAdminString
    MAX-ACCESS   read-only
    STATUS       current
    DESCRIPTION
        "Cisco Firepower bios:VfOSBootWatchdogTimerTimeout:rn
        managed object property"
    ::= { cfprBiosVfOSBootWatchdogTimerTimeoutEntry 3 }

cfprBiosVfOSBootWatchdogTimerTimeoutVpOSBootWatchdogTimerTimeout OBJECT-TYPE
    SYNTAX       CfprBiosVfOSBootWatchdogTimerTimeoutVpOSBootWatchdogTimerTimeout
    MAX-ACCESS   read-only
    STATUS       current
    DESCRIPTION
        "Cisco Firepower bios:VfOSBootWatchdogTimerTimeout:vpOSBootWatchdo
        gTimerTimeout managed object property"
    ::= { cfprBiosVfOSBootWatchdogTimerTimeoutEntry 4 }

cfprBiosVfOSBootWatchdogTimerTimeoutSupportedByDefault OBJECT-TYPE
    SYNTAX       CfprBiosSupportedAction
    MAX-ACCESS   read-only
    STATUS       current
    DESCRIPTION
        "Cisco Firepower bios:VfOSBootWatchdogTimerTimeout:supportedByDefa
        ult managed object property"
    ::= { cfprBiosVfOSBootWatchdogTimerTimeoutEntry 5 }

cfprBiosVfOnboardSATAControllerTable OBJECT-TYPE
    SYNTAX           SEQUENCE OF CfprBiosVfOnboardSATAControllerEntry
    MAX-ACCESS       not-accessible
    STATUS           current
    DESCRIPTION
        "Cisco Firepower bios:VfOnboardSATAController managed
        object table"
    ::= { cfprBiosObjects 45 }

cfprBiosVfOnboardSATAControllerEntry OBJECT-TYPE
    SYNTAX           CfprBiosVfOnboardSATAControllerEntry
    MAX-ACCESS       not-accessible
    STATUS           current
    DESCRIPTION
        "Entry for the cfprBiosVfOnboardSATAControllerTable table."
    INDEX { cfprBiosVfOnboardSATAControllerInstanceId }
    ::= { cfprBiosVfOnboardSATAControllerTable 1 }

CfprBiosVfOnboardSATAControllerEntry ::= SEQUENCE {
    cfprBiosVfOnboardSATAControllerInstanceId                        CfprManagedObjectId,
    cfprBiosVfOnboardSATAControllerDn                                CfprManagedObjectDn,
    cfprBiosVfOnboardSATAControllerRn                                SnmpAdminString,
    cfprBiosVfOnboardSATAControllerVpOnboardSATAController           CfprBiosVfOnboardSATAControllerVpOnboardSATAController,
    cfprBiosVfOnboardSATAControllerVpSATAMode                        CfprBiosVfOnboardSATAControllerVpSATAMode,
    cfprBiosVfOnboardSATAControllerSupportedByDefault                CfprBiosSupportedAction
}

cfprBiosVfOnboardSATAControllerInstanceId OBJECT-TYPE
    SYNTAX       CfprManagedObjectId
    MAX-ACCESS   not-accessible
    STATUS       current
    DESCRIPTION
        "Instance identifier of the managed object."
    ::= { cfprBiosVfOnboardSATAControllerEntry 1 }

cfprBiosVfOnboardSATAControllerDn OBJECT-TYPE
    SYNTAX       CfprManagedObjectDn
    MAX-ACCESS   read-only
    STATUS       current
    DESCRIPTION
        "Cisco Firepower bios:VfOnboardSATAController:dn
        managed object property"
    ::= { cfprBiosVfOnboardSATAControllerEntry 2 }

cfprBiosVfOnboardSATAControllerRn OBJECT-TYPE
    SYNTAX       SnmpAdminString
    MAX-ACCESS   read-only
    STATUS       current
    DESCRIPTION
        "Cisco Firepower bios:VfOnboardSATAController:rn
        managed object property"
    ::= { cfprBiosVfOnboardSATAControllerEntry 3 }

cfprBiosVfOnboardSATAControllerVpOnboardSATAController OBJECT-TYPE
    SYNTAX       CfprBiosVfOnboardSATAControllerVpOnboardSATAController
    MAX-ACCESS   read-only
    STATUS       current
    DESCRIPTION
        "Cisco Firepower bios:VfOnboardSATAController:vpOnboardSATAControl
        ler managed object property"
    ::= { cfprBiosVfOnboardSATAControllerEntry 4 }

cfprBiosVfOnboardSATAControllerVpSATAMode OBJECT-TYPE
    SYNTAX       CfprBiosVfOnboardSATAControllerVpSATAMode
    MAX-ACCESS   read-only
    STATUS       current
    DESCRIPTION
        "Cisco Firepower bios:VfOnboardSATAController:vpSATAMode
        managed object property"
    ::= { cfprBiosVfOnboardSATAControllerEntry 5 }

cfprBiosVfOnboardSATAControllerSupportedByDefault OBJECT-TYPE
    SYNTAX       CfprBiosSupportedAction
    MAX-ACCESS   read-only
    STATUS       current
    DESCRIPTION
        "Cisco Firepower bios:VfOnboardSATAController:supportedByDefault
        managed object property"
    ::= { cfprBiosVfOnboardSATAControllerEntry 6 }

cfprBiosVfOnboardStorageTable OBJECT-TYPE
    SYNTAX           SEQUENCE OF CfprBiosVfOnboardStorageEntry
    MAX-ACCESS       not-accessible
    STATUS           current
    DESCRIPTION
        "Cisco Firepower bios:VfOnboardStorage managed object table"
    ::= { cfprBiosObjects 46 }

cfprBiosVfOnboardStorageEntry OBJECT-TYPE
    SYNTAX           CfprBiosVfOnboardStorageEntry
    MAX-ACCESS       not-accessible
    STATUS           current
    DESCRIPTION
        "Entry for the cfprBiosVfOnboardStorageTable table."
    INDEX { cfprBiosVfOnboardStorageInstanceId }
    ::= { cfprBiosVfOnboardStorageTable 1 }

CfprBiosVfOnboardStorageEntry ::= SEQUENCE {
    cfprBiosVfOnboardStorageInstanceId                               CfprManagedObjectId,
    cfprBiosVfOnboardStorageDn                                       CfprManagedObjectDn,
    cfprBiosVfOnboardStorageRn                                       SnmpAdminString,
    cfprBiosVfOnboardStorageVpOnboardSCUStorageSupport               CfprBiosVfOnboardStorageVpOnboardSCUStorageSupport,
    cfprBiosVfOnboardStorageSupportedByDefault                       CfprBiosSupportedAction
}

cfprBiosVfOnboardStorageInstanceId OBJECT-TYPE
    SYNTAX       CfprManagedObjectId
    MAX-ACCESS   not-accessible
    STATUS       current
    DESCRIPTION
        "Instance identifier of the managed object."
    ::= { cfprBiosVfOnboardStorageEntry 1 }

cfprBiosVfOnboardStorageDn OBJECT-TYPE
    SYNTAX       CfprManagedObjectDn
    MAX-ACCESS   read-only
    STATUS       current
    DESCRIPTION
        "Cisco Firepower bios:VfOnboardStorage:dn managed object property"
    ::= { cfprBiosVfOnboardStorageEntry 2 }

cfprBiosVfOnboardStorageRn OBJECT-TYPE
    SYNTAX       SnmpAdminString
    MAX-ACCESS   read-only
    STATUS       current
    DESCRIPTION
        "Cisco Firepower bios:VfOnboardStorage:rn managed object property"
    ::= { cfprBiosVfOnboardStorageEntry 3 }

cfprBiosVfOnboardStorageVpOnboardSCUStorageSupport OBJECT-TYPE
    SYNTAX       CfprBiosVfOnboardStorageVpOnboardSCUStorageSupport
    MAX-ACCESS   read-only
    STATUS       current
    DESCRIPTION
        "Cisco Firepower bios:VfOnboardStorage:vpOnboardSCUStorageSupport
        managed object property"
    ::= { cfprBiosVfOnboardStorageEntry 4 }

cfprBiosVfOnboardStorageSupportedByDefault OBJECT-TYPE
    SYNTAX       CfprBiosSupportedAction
    MAX-ACCESS   read-only
    STATUS       current
    DESCRIPTION
        "Cisco Firepower bios:VfOnboardStorage:supportedByDefault
        managed object property"
    ::= { cfprBiosVfOnboardStorageEntry 5 }

cfprBiosVfOptionROMEnableTable OBJECT-TYPE
    SYNTAX           SEQUENCE OF CfprBiosVfOptionROMEnableEntry
    MAX-ACCESS       not-accessible
    STATUS           current
    DESCRIPTION
        "Cisco Firepower bios:VfOptionROMEnable managed object table"
    ::= { cfprBiosObjects 47 }

cfprBiosVfOptionROMEnableEntry OBJECT-TYPE
    SYNTAX           CfprBiosVfOptionROMEnableEntry
    MAX-ACCESS       not-accessible
    STATUS           current
    DESCRIPTION
        "Entry for the cfprBiosVfOptionROMEnableTable table."
    INDEX { cfprBiosVfOptionROMEnableInstanceId }
    ::= { cfprBiosVfOptionROMEnableTable 1 }

CfprBiosVfOptionROMEnableEntry ::= SEQUENCE {
    cfprBiosVfOptionROMEnableInstanceId                              CfprManagedObjectId,
    cfprBiosVfOptionROMEnableDn                                      CfprManagedObjectDn,
    cfprBiosVfOptionROMEnableRn                                      SnmpAdminString,
    cfprBiosVfOptionROMEnableVpState                                 CfprBiosVfOptionROMEnableVpState,
    cfprBiosVfOptionROMEnableSupportedByDefault                      CfprBiosSupportedAction
}

cfprBiosVfOptionROMEnableInstanceId OBJECT-TYPE
    SYNTAX       CfprManagedObjectId
    MAX-ACCESS   not-accessible
    STATUS       current
    DESCRIPTION
        "Instance identifier of the managed object."
    ::= { cfprBiosVfOptionROMEnableEntry 1 }

cfprBiosVfOptionROMEnableDn OBJECT-TYPE
    SYNTAX       CfprManagedObjectDn
    MAX-ACCESS   read-only
    STATUS       current
    DESCRIPTION
        "Cisco Firepower bios:VfOptionROMEnable:dn managed
        object property"
    ::= { cfprBiosVfOptionROMEnableEntry 2 }

cfprBiosVfOptionROMEnableRn OBJECT-TYPE
    SYNTAX       SnmpAdminString
    MAX-ACCESS   read-only
    STATUS       current
    DESCRIPTION
        "Cisco Firepower bios:VfOptionROMEnable:rn managed
        object property"
    ::= { cfprBiosVfOptionROMEnableEntry 3 }

cfprBiosVfOptionROMEnableVpState OBJECT-TYPE
    SYNTAX       CfprBiosVfOptionROMEnableVpState
    MAX-ACCESS   read-only
    STATUS       current
    DESCRIPTION
        "Cisco Firepower bios:VfOptionROMEnable:vpState
        managed object property"
    ::= { cfprBiosVfOptionROMEnableEntry 4 }

cfprBiosVfOptionROMEnableSupportedByDefault OBJECT-TYPE
    SYNTAX       CfprBiosSupportedAction
    MAX-ACCESS   read-only
    STATUS       current
    DESCRIPTION
        "Cisco Firepower bios:VfOptionROMEnable:supportedByDefault
        managed object property"
    ::= { cfprBiosVfOptionROMEnableEntry 5 }

cfprBiosVfOptionROMLoadTable OBJECT-TYPE
    SYNTAX           SEQUENCE OF CfprBiosVfOptionROMLoadEntry
    MAX-ACCESS       not-accessible
    STATUS           current
    DESCRIPTION
        "Cisco Firepower bios:VfOptionROMLoad managed object table"
    ::= { cfprBiosObjects 48 }

cfprBiosVfOptionROMLoadEntry OBJECT-TYPE
    SYNTAX           CfprBiosVfOptionROMLoadEntry
    MAX-ACCESS       not-accessible
    STATUS           current
    DESCRIPTION
        "Entry for the cfprBiosVfOptionROMLoadTable table."
    INDEX { cfprBiosVfOptionROMLoadInstanceId }
    ::= { cfprBiosVfOptionROMLoadTable 1 }

CfprBiosVfOptionROMLoadEntry ::= SEQUENCE {
    cfprBiosVfOptionROMLoadInstanceId                                CfprManagedObjectId,
    cfprBiosVfOptionROMLoadDn                                        CfprManagedObjectDn,
    cfprBiosVfOptionROMLoadRn                                        SnmpAdminString,
    cfprBiosVfOptionROMLoadVpLoad                                    CfprBiosVfOptionROMLoadVpLoad,
    cfprBiosVfOptionROMLoadSupportedByDefault                        CfprBiosSupportedAction
}

cfprBiosVfOptionROMLoadInstanceId OBJECT-TYPE
    SYNTAX       CfprManagedObjectId
    MAX-ACCESS   not-accessible
    STATUS       current
    DESCRIPTION
        "Instance identifier of the managed object."
    ::= { cfprBiosVfOptionROMLoadEntry 1 }

cfprBiosVfOptionROMLoadDn OBJECT-TYPE
    SYNTAX       CfprManagedObjectDn
    MAX-ACCESS   read-only
    STATUS       current
    DESCRIPTION
        "Cisco Firepower bios:VfOptionROMLoad:dn managed object property"
    ::= { cfprBiosVfOptionROMLoadEntry 2 }

cfprBiosVfOptionROMLoadRn OBJECT-TYPE
    SYNTAX       SnmpAdminString
    MAX-ACCESS   read-only
    STATUS       current
    DESCRIPTION
        "Cisco Firepower bios:VfOptionROMLoad:rn managed object property"
    ::= { cfprBiosVfOptionROMLoadEntry 3 }

cfprBiosVfOptionROMLoadVpLoad OBJECT-TYPE
    SYNTAX       CfprBiosVfOptionROMLoadVpLoad
    MAX-ACCESS   read-only
    STATUS       current
    DESCRIPTION
        "Cisco Firepower bios:VfOptionROMLoad:vpLoad managed
        object property"
    ::= { cfprBiosVfOptionROMLoadEntry 4 }

cfprBiosVfOptionROMLoadSupportedByDefault OBJECT-TYPE
    SYNTAX       CfprBiosSupportedAction
    MAX-ACCESS   read-only
    STATUS       current
    DESCRIPTION
        "Cisco Firepower bios:VfOptionROMLoad:supportedByDefault
        managed object property"
    ::= { cfprBiosVfOptionROMLoadEntry 5 }

cfprBiosVfPCISlotLinkSpeedTable OBJECT-TYPE
    SYNTAX           SEQUENCE OF CfprBiosVfPCISlotLinkSpeedEntry
    MAX-ACCESS       not-accessible
    STATUS           current
    DESCRIPTION
        "Cisco Firepower bios:VfPCISlotLinkSpeed managed object table"
    ::= { cfprBiosObjects 49 }

cfprBiosVfPCISlotLinkSpeedEntry OBJECT-TYPE
    SYNTAX           CfprBiosVfPCISlotLinkSpeedEntry
    MAX-ACCESS       not-accessible
    STATUS           current
    DESCRIPTION
        "Entry for the cfprBiosVfPCISlotLinkSpeedTable table."
    INDEX { cfprBiosVfPCISlotLinkSpeedInstanceId }
    ::= { cfprBiosVfPCISlotLinkSpeedTable 1 }

CfprBiosVfPCISlotLinkSpeedEntry ::= SEQUENCE {
    cfprBiosVfPCISlotLinkSpeedInstanceId                             CfprManagedObjectId,
    cfprBiosVfPCISlotLinkSpeedDn                                     CfprManagedObjectDn,
    cfprBiosVfPCISlotLinkSpeedRn                                     SnmpAdminString,
    cfprBiosVfPCISlotLinkSpeedVpPCIeSlot10LinkSpeed                  CfprBiosVfPCISlotLinkSpeedVpPCIeSlot10LinkSpeed,
    cfprBiosVfPCISlotLinkSpeedVpPCIeSlot1LinkSpeed                   CfprBiosVfPCISlotLinkSpeedVpPCIeSlot1LinkSpeed,
    cfprBiosVfPCISlotLinkSpeedVpPCIeSlot2LinkSpeed                   CfprBiosVfPCISlotLinkSpeedVpPCIeSlot2LinkSpeed,
    cfprBiosVfPCISlotLinkSpeedVpPCIeSlot3LinkSpeed                   CfprBiosVfPCISlotLinkSpeedVpPCIeSlot3LinkSpeed,
    cfprBiosVfPCISlotLinkSpeedVpPCIeSlot4LinkSpeed                   CfprBiosVfPCISlotLinkSpeedVpPCIeSlot4LinkSpeed,
    cfprBiosVfPCISlotLinkSpeedVpPCIeSlot5LinkSpeed                   CfprBiosVfPCISlotLinkSpeedVpPCIeSlot5LinkSpeed,
    cfprBiosVfPCISlotLinkSpeedVpPCIeSlot6LinkSpeed                   CfprBiosVfPCISlotLinkSpeedVpPCIeSlot6LinkSpeed,
    cfprBiosVfPCISlotLinkSpeedVpPCIeSlot7LinkSpeed                   CfprBiosVfPCISlotLinkSpeedVpPCIeSlot7LinkSpeed,
    cfprBiosVfPCISlotLinkSpeedVpPCIeSlot8LinkSpeed                   CfprBiosVfPCISlotLinkSpeedVpPCIeSlot8LinkSpeed,
    cfprBiosVfPCISlotLinkSpeedVpPCIeSlot9LinkSpeed                   CfprBiosVfPCISlotLinkSpeedVpPCIeSlot9LinkSpeed,
    cfprBiosVfPCISlotLinkSpeedSupportedByDefault                     CfprBiosSupportedAction
}

cfprBiosVfPCISlotLinkSpeedInstanceId OBJECT-TYPE
    SYNTAX       CfprManagedObjectId
    MAX-ACCESS   not-accessible
    STATUS       current
    DESCRIPTION
        "Instance identifier of the managed object."
    ::= { cfprBiosVfPCISlotLinkSpeedEntry 1 }

cfprBiosVfPCISlotLinkSpeedDn OBJECT-TYPE
    SYNTAX       CfprManagedObjectDn
    MAX-ACCESS   read-only
    STATUS       current
    DESCRIPTION
        "Cisco Firepower bios:VfPCISlotLinkSpeed:dn managed
        object property"
    ::= { cfprBiosVfPCISlotLinkSpeedEntry 2 }

cfprBiosVfPCISlotLinkSpeedRn OBJECT-TYPE
    SYNTAX       SnmpAdminString
    MAX-ACCESS   read-only
    STATUS       current
    DESCRIPTION
        "Cisco Firepower bios:VfPCISlotLinkSpeed:rn managed
        object property"
    ::= { cfprBiosVfPCISlotLinkSpeedEntry 3 }

cfprBiosVfPCISlotLinkSpeedVpPCIeSlot10LinkSpeed OBJECT-TYPE
    SYNTAX       CfprBiosVfPCISlotLinkSpeedVpPCIeSlot10LinkSpeed
    MAX-ACCESS   read-only
    STATUS       current
    DESCRIPTION
        "Cisco Firepower bios:VfPCISlotLinkSpeed:vpPCIeSlot10LinkSpeed
        managed object property"
    ::= { cfprBiosVfPCISlotLinkSpeedEntry 4 }

cfprBiosVfPCISlotLinkSpeedVpPCIeSlot1LinkSpeed OBJECT-TYPE
    SYNTAX       CfprBiosVfPCISlotLinkSpeedVpPCIeSlot1LinkSpeed
    MAX-ACCESS   read-only
    STATUS       current
    DESCRIPTION
        "Cisco Firepower bios:VfPCISlotLinkSpeed:vpPCIeSlot1LinkSpeed
        managed object property"
    ::= { cfprBiosVfPCISlotLinkSpeedEntry 5 }

cfprBiosVfPCISlotLinkSpeedVpPCIeSlot2LinkSpeed OBJECT-TYPE
    SYNTAX       CfprBiosVfPCISlotLinkSpeedVpPCIeSlot2LinkSpeed
    MAX-ACCESS   read-only
    STATUS       current
    DESCRIPTION
        "Cisco Firepower bios:VfPCISlotLinkSpeed:vpPCIeSlot2LinkSpeed
        managed object property"
    ::= { cfprBiosVfPCISlotLinkSpeedEntry 6 }

cfprBiosVfPCISlotLinkSpeedVpPCIeSlot3LinkSpeed OBJECT-TYPE
    SYNTAX       CfprBiosVfPCISlotLinkSpeedVpPCIeSlot3LinkSpeed
    MAX-ACCESS   read-only
    STATUS       current
    DESCRIPTION
        "Cisco Firepower bios:VfPCISlotLinkSpeed:vpPCIeSlot3LinkSpeed
        managed object property"
    ::= { cfprBiosVfPCISlotLinkSpeedEntry 7 }

cfprBiosVfPCISlotLinkSpeedVpPCIeSlot4LinkSpeed OBJECT-TYPE
    SYNTAX       CfprBiosVfPCISlotLinkSpeedVpPCIeSlot4LinkSpeed
    MAX-ACCESS   read-only
    STATUS       current
    DESCRIPTION
        "Cisco Firepower bios:VfPCISlotLinkSpeed:vpPCIeSlot4LinkSpeed
        managed object property"
    ::= { cfprBiosVfPCISlotLinkSpeedEntry 8 }

cfprBiosVfPCISlotLinkSpeedVpPCIeSlot5LinkSpeed OBJECT-TYPE
    SYNTAX       CfprBiosVfPCISlotLinkSpeedVpPCIeSlot5LinkSpeed
    MAX-ACCESS   read-only
    STATUS       current
    DESCRIPTION
        "Cisco Firepower bios:VfPCISlotLinkSpeed:vpPCIeSlot5LinkSpeed
        managed object property"
    ::= { cfprBiosVfPCISlotLinkSpeedEntry 9 }

cfprBiosVfPCISlotLinkSpeedVpPCIeSlot6LinkSpeed OBJECT-TYPE
    SYNTAX       CfprBiosVfPCISlotLinkSpeedVpPCIeSlot6LinkSpeed
    MAX-ACCESS   read-only
    STATUS       current
    DESCRIPTION
        "Cisco Firepower bios:VfPCISlotLinkSpeed:vpPCIeSlot6LinkSpeed
        managed object property"
    ::= { cfprBiosVfPCISlotLinkSpeedEntry 10 }

cfprBiosVfPCISlotLinkSpeedVpPCIeSlot7LinkSpeed OBJECT-TYPE
    SYNTAX       CfprBiosVfPCISlotLinkSpeedVpPCIeSlot7LinkSpeed
    MAX-ACCESS   read-only
    STATUS       current
    DESCRIPTION
        "Cisco Firepower bios:VfPCISlotLinkSpeed:vpPCIeSlot7LinkSpeed
        managed object property"
    ::= { cfprBiosVfPCISlotLinkSpeedEntry 11 }

cfprBiosVfPCISlotLinkSpeedVpPCIeSlot8LinkSpeed OBJECT-TYPE
    SYNTAX       CfprBiosVfPCISlotLinkSpeedVpPCIeSlot8LinkSpeed
    MAX-ACCESS   read-only
    STATUS       current
    DESCRIPTION
        "Cisco Firepower bios:VfPCISlotLinkSpeed:vpPCIeSlot8LinkSpeed
        managed object property"
    ::= { cfprBiosVfPCISlotLinkSpeedEntry 12 }

cfprBiosVfPCISlotLinkSpeedVpPCIeSlot9LinkSpeed OBJECT-TYPE
    SYNTAX       CfprBiosVfPCISlotLinkSpeedVpPCIeSlot9LinkSpeed
    MAX-ACCESS   read-only
    STATUS       current
    DESCRIPTION
        "Cisco Firepower bios:VfPCISlotLinkSpeed:vpPCIeSlot9LinkSpeed
        managed object property"
    ::= { cfprBiosVfPCISlotLinkSpeedEntry 13 }

cfprBiosVfPCISlotLinkSpeedSupportedByDefault OBJECT-TYPE
    SYNTAX       CfprBiosSupportedAction
    MAX-ACCESS   read-only
    STATUS       current
    DESCRIPTION
        "Cisco Firepower bios:VfPCISlotLinkSpeed:supportedByDefault
        managed object property"
    ::= { cfprBiosVfPCISlotLinkSpeedEntry 14 }

cfprBiosVfPCISlotOptionROMEnableTable OBJECT-TYPE
    SYNTAX           SEQUENCE OF CfprBiosVfPCISlotOptionROMEnableEntry
    MAX-ACCESS       not-accessible
    STATUS           current
    DESCRIPTION
        "Cisco Firepower bios:VfPCISlotOptionROMEnable
        managed object table"
    ::= { cfprBiosObjects 50 }

cfprBiosVfPCISlotOptionROMEnableEntry OBJECT-TYPE
    SYNTAX           CfprBiosVfPCISlotOptionROMEnableEntry
    MAX-ACCESS       not-accessible
    STATUS           current
    DESCRIPTION
        "Entry for the cfprBiosVfPCISlotOptionROMEnableTable table."
    INDEX { cfprBiosVfPCISlotOptionROMEnableInstanceId }
    ::= { cfprBiosVfPCISlotOptionROMEnableTable 1 }

CfprBiosVfPCISlotOptionROMEnableEntry ::= SEQUENCE {
    cfprBiosVfPCISlotOptionROMEnableInstanceId                       CfprManagedObjectId,
    cfprBiosVfPCISlotOptionROMEnableDn                               CfprManagedObjectDn,
    cfprBiosVfPCISlotOptionROMEnableRn                               SnmpAdminString,
    cfprBiosVfPCISlotOptionROMEnableVpPCIeSlotHBAOptionROM           CfprBiosVfPCISlotOptionROMEnableVpPCIeSlotHBAOptionROM,
    cfprBiosVfPCISlotOptionROMEnableVpPCIeSlotMLOMOptionROM          CfprBiosVfPCISlotOptionROMEnableVpPCIeSlotMLOMOptionROM,
    cfprBiosVfPCISlotOptionROMEnableVpPCIeSlotN1OptionROM            CfprBiosVfPCISlotOptionROMEnableVpPCIeSlotN1OptionROM,
    cfprBiosVfPCISlotOptionROMEnableVpPCIeSlotN2OptionROM            CfprBiosVfPCISlotOptionROMEnableVpPCIeSlotN2OptionROM,
    cfprBiosVfPCISlotOptionROMEnableVpPCIeSlotSASOptionROM           CfprBiosVfPCISlotOptionROMEnableVpPCIeSlotSASOptionROM,
    cfprBiosVfPCISlotOptionROMEnableVpSlot10State                    CfprBiosVfPCISlotOptionROMEnableVpSlot10State,
    cfprBiosVfPCISlotOptionROMEnableVpSlot1State                     CfprBiosVfPCISlotOptionROMEnableVpSlot1State,
    cfprBiosVfPCISlotOptionROMEnableVpSlot2State                     CfprBiosVfPCISlotOptionROMEnableVpSlot2State,
    cfprBiosVfPCISlotOptionROMEnableVpSlot3State                     CfprBiosVfPCISlotOptionROMEnableVpSlot3State,
    cfprBiosVfPCISlotOptionROMEnableVpSlot4State                     CfprBiosVfPCISlotOptionROMEnableVpSlot4State,
    cfprBiosVfPCISlotOptionROMEnableVpSlot5State                     CfprBiosVfPCISlotOptionROMEnableVpSlot5State,
    cfprBiosVfPCISlotOptionROMEnableVpSlot6State                     CfprBiosVfPCISlotOptionROMEnableVpSlot6State,
    cfprBiosVfPCISlotOptionROMEnableVpSlot7State                     CfprBiosVfPCISlotOptionROMEnableVpSlot7State,
    cfprBiosVfPCISlotOptionROMEnableVpSlot8State                     CfprBiosVfPCISlotOptionROMEnableVpSlot8State,
    cfprBiosVfPCISlotOptionROMEnableVpSlot9State                     CfprBiosVfPCISlotOptionROMEnableVpSlot9State,
    cfprBiosVfPCISlotOptionROMEnableVpSlotMezzState                  CfprBiosVfPCISlotOptionROMEnableVpSlotMezzState,
    cfprBiosVfPCISlotOptionROMEnableSupportedByDefault               CfprBiosSupportedAction
}

cfprBiosVfPCISlotOptionROMEnableInstanceId OBJECT-TYPE
    SYNTAX       CfprManagedObjectId
    MAX-ACCESS   not-accessible
    STATUS       current
    DESCRIPTION
        "Instance identifier of the managed object."
    ::= { cfprBiosVfPCISlotOptionROMEnableEntry 1 }

cfprBiosVfPCISlotOptionROMEnableDn OBJECT-TYPE
    SYNTAX       CfprManagedObjectDn
    MAX-ACCESS   read-only
    STATUS       current
    DESCRIPTION
        "Cisco Firepower bios:VfPCISlotOptionROMEnable:dn
        managed object property"
    ::= { cfprBiosVfPCISlotOptionROMEnableEntry 2 }

cfprBiosVfPCISlotOptionROMEnableRn OBJECT-TYPE
    SYNTAX       SnmpAdminString
    MAX-ACCESS   read-only
    STATUS       current
    DESCRIPTION
        "Cisco Firepower bios:VfPCISlotOptionROMEnable:rn
        managed object property"
    ::= { cfprBiosVfPCISlotOptionROMEnableEntry 3 }

cfprBiosVfPCISlotOptionROMEnableVpPCIeSlotHBAOptionROM OBJECT-TYPE
    SYNTAX       CfprBiosVfPCISlotOptionROMEnableVpPCIeSlotHBAOptionROM
    MAX-ACCESS   read-only
    STATUS       current
    DESCRIPTION
        "Cisco Firepower bios:VfPCISlotOptionROMEnable:vpPCIeSlotHBAOption
        ROM managed object property"
    ::= { cfprBiosVfPCISlotOptionROMEnableEntry 4 }

cfprBiosVfPCISlotOptionROMEnableVpPCIeSlotMLOMOptionROM OBJECT-TYPE
    SYNTAX       CfprBiosVfPCISlotOptionROMEnableVpPCIeSlotMLOMOptionROM
    MAX-ACCESS   read-only
    STATUS       current
    DESCRIPTION
        "Cisco Firepower bios:VfPCISlotOptionROMEnable:vpPCIeSlotMLOMOptio
        nROM managed object property"
    ::= { cfprBiosVfPCISlotOptionROMEnableEntry 5 }

cfprBiosVfPCISlotOptionROMEnableVpPCIeSlotN1OptionROM OBJECT-TYPE
    SYNTAX       CfprBiosVfPCISlotOptionROMEnableVpPCIeSlotN1OptionROM
    MAX-ACCESS   read-only
    STATUS       current
    DESCRIPTION
        "Cisco Firepower bios:VfPCISlotOptionROMEnable:vpPCIeSlotN1OptionR
        OM managed object property"
    ::= { cfprBiosVfPCISlotOptionROMEnableEntry 6 }

cfprBiosVfPCISlotOptionROMEnableVpPCIeSlotN2OptionROM OBJECT-TYPE
    SYNTAX       CfprBiosVfPCISlotOptionROMEnableVpPCIeSlotN2OptionROM
    MAX-ACCESS   read-only
    STATUS       current
    DESCRIPTION
        "Cisco Firepower bios:VfPCISlotOptionROMEnable:vpPCIeSlotN2OptionR
        OM managed object property"
    ::= { cfprBiosVfPCISlotOptionROMEnableEntry 7 }

cfprBiosVfPCISlotOptionROMEnableVpPCIeSlotSASOptionROM OBJECT-TYPE
    SYNTAX       CfprBiosVfPCISlotOptionROMEnableVpPCIeSlotSASOptionROM
    MAX-ACCESS   read-only
    STATUS       current
    DESCRIPTION
        "Cisco Firepower bios:VfPCISlotOptionROMEnable:vpPCIeSlotSASOption
        ROM managed object property"
    ::= { cfprBiosVfPCISlotOptionROMEnableEntry 8 }

cfprBiosVfPCISlotOptionROMEnableVpSlot10State OBJECT-TYPE
    SYNTAX       CfprBiosVfPCISlotOptionROMEnableVpSlot10State
    MAX-ACCESS   read-only
    STATUS       current
    DESCRIPTION
        "Cisco Firepower bios:VfPCISlotOptionROMEnable:vpSlot10State
        managed object property"
    ::= { cfprBiosVfPCISlotOptionROMEnableEntry 9 }

cfprBiosVfPCISlotOptionROMEnableVpSlot1State OBJECT-TYPE
    SYNTAX       CfprBiosVfPCISlotOptionROMEnableVpSlot1State
    MAX-ACCESS   read-only
    STATUS       current
    DESCRIPTION
        "Cisco Firepower bios:VfPCISlotOptionROMEnable:vpSlot1State
        managed object property"
    ::= { cfprBiosVfPCISlotOptionROMEnableEntry 10 }

cfprBiosVfPCISlotOptionROMEnableVpSlot2State OBJECT-TYPE
    SYNTAX       CfprBiosVfPCISlotOptionROMEnableVpSlot2State
    MAX-ACCESS   read-only
    STATUS       current
    DESCRIPTION
        "Cisco Firepower bios:VfPCISlotOptionROMEnable:vpSlot2State
        managed object property"
    ::= { cfprBiosVfPCISlotOptionROMEnableEntry 11 }

cfprBiosVfPCISlotOptionROMEnableVpSlot3State OBJECT-TYPE
    SYNTAX       CfprBiosVfPCISlotOptionROMEnableVpSlot3State
    MAX-ACCESS   read-only
    STATUS       current
    DESCRIPTION
        "Cisco Firepower bios:VfPCISlotOptionROMEnable:vpSlot3State
        managed object property"
    ::= { cfprBiosVfPCISlotOptionROMEnableEntry 12 }

cfprBiosVfPCISlotOptionROMEnableVpSlot4State OBJECT-TYPE
    SYNTAX       CfprBiosVfPCISlotOptionROMEnableVpSlot4State
    MAX-ACCESS   read-only
    STATUS       current
    DESCRIPTION
        "Cisco Firepower bios:VfPCISlotOptionROMEnable:vpSlot4State
        managed object property"
    ::= { cfprBiosVfPCISlotOptionROMEnableEntry 13 }

cfprBiosVfPCISlotOptionROMEnableVpSlot5State OBJECT-TYPE
    SYNTAX       CfprBiosVfPCISlotOptionROMEnableVpSlot5State
    MAX-ACCESS   read-only
    STATUS       current
    DESCRIPTION
        "Cisco Firepower bios:VfPCISlotOptionROMEnable:vpSlot5State
        managed object property"
    ::= { cfprBiosVfPCISlotOptionROMEnableEntry 14 }

cfprBiosVfPCISlotOptionROMEnableVpSlot6State OBJECT-TYPE
    SYNTAX       CfprBiosVfPCISlotOptionROMEnableVpSlot6State
    MAX-ACCESS   read-only
    STATUS       current
    DESCRIPTION
        "Cisco Firepower bios:VfPCISlotOptionROMEnable:vpSlot6State
        managed object property"
    ::= { cfprBiosVfPCISlotOptionROMEnableEntry 15 }

cfprBiosVfPCISlotOptionROMEnableVpSlot7State OBJECT-TYPE
    SYNTAX       CfprBiosVfPCISlotOptionROMEnableVpSlot7State
    MAX-ACCESS   read-only
    STATUS       current
    DESCRIPTION
        "Cisco Firepower bios:VfPCISlotOptionROMEnable:vpSlot7State
        managed object property"
    ::= { cfprBiosVfPCISlotOptionROMEnableEntry 16 }

cfprBiosVfPCISlotOptionROMEnableVpSlot8State OBJECT-TYPE
    SYNTAX       CfprBiosVfPCISlotOptionROMEnableVpSlot8State
    MAX-ACCESS   read-only
    STATUS       current
    DESCRIPTION
        "Cisco Firepower bios:VfPCISlotOptionROMEnable:vpSlot8State
        managed object property"
    ::= { cfprBiosVfPCISlotOptionROMEnableEntry 17 }

cfprBiosVfPCISlotOptionROMEnableVpSlot9State OBJECT-TYPE
    SYNTAX       CfprBiosVfPCISlotOptionROMEnableVpSlot9State
    MAX-ACCESS   read-only
    STATUS       current
    DESCRIPTION
        "Cisco Firepower bios:VfPCISlotOptionROMEnable:vpSlot9State
        managed object property"
    ::= { cfprBiosVfPCISlotOptionROMEnableEntry 18 }

cfprBiosVfPCISlotOptionROMEnableVpSlotMezzState OBJECT-TYPE
    SYNTAX       CfprBiosVfPCISlotOptionROMEnableVpSlotMezzState
    MAX-ACCESS   read-only
    STATUS       current
    DESCRIPTION
        "Cisco Firepower bios:VfPCISlotOptionROMEnable:vpSlotMezzState
        managed object property"
    ::= { cfprBiosVfPCISlotOptionROMEnableEntry 19 }

cfprBiosVfPCISlotOptionROMEnableSupportedByDefault OBJECT-TYPE
    SYNTAX       CfprBiosSupportedAction
    MAX-ACCESS   read-only
    STATUS       current
    DESCRIPTION
        "Cisco Firepower bios:VfPCISlotOptionROMEnable:supportedByDefault
        managed object property"
    ::= { cfprBiosVfPCISlotOptionROMEnableEntry 20 }

cfprBiosVfPOSTErrorPauseTable OBJECT-TYPE
    SYNTAX           SEQUENCE OF CfprBiosVfPOSTErrorPauseEntry
    MAX-ACCESS       not-accessible
    STATUS           current
    DESCRIPTION
        "Cisco Firepower bios:VfPOSTErrorPause managed object table"
    ::= { cfprBiosObjects 51 }

cfprBiosVfPOSTErrorPauseEntry OBJECT-TYPE
    SYNTAX           CfprBiosVfPOSTErrorPauseEntry
    MAX-ACCESS       not-accessible
    STATUS           current
    DESCRIPTION
        "Entry for the cfprBiosVfPOSTErrorPauseTable table."
    INDEX { cfprBiosVfPOSTErrorPauseInstanceId }
    ::= { cfprBiosVfPOSTErrorPauseTable 1 }

CfprBiosVfPOSTErrorPauseEntry ::= SEQUENCE {
    cfprBiosVfPOSTErrorPauseInstanceId                               CfprManagedObjectId,
    cfprBiosVfPOSTErrorPauseDn                                       CfprManagedObjectDn,
    cfprBiosVfPOSTErrorPauseRn                                       SnmpAdminString,
    cfprBiosVfPOSTErrorPauseVpPOSTErrorPause                         CfprBiosVfPOSTErrorPauseVpPOSTErrorPause,
    cfprBiosVfPOSTErrorPauseSupportedByDefault                       CfprBiosSupportedAction
}

cfprBiosVfPOSTErrorPauseInstanceId OBJECT-TYPE
    SYNTAX       CfprManagedObjectId
    MAX-ACCESS   not-accessible
    STATUS       current
    DESCRIPTION
        "Instance identifier of the managed object."
    ::= { cfprBiosVfPOSTErrorPauseEntry 1 }

cfprBiosVfPOSTErrorPauseDn OBJECT-TYPE
    SYNTAX       CfprManagedObjectDn
    MAX-ACCESS   read-only
    STATUS       current
    DESCRIPTION
        "Cisco Firepower bios:VfPOSTErrorPause:dn managed object property"
    ::= { cfprBiosVfPOSTErrorPauseEntry 2 }

cfprBiosVfPOSTErrorPauseRn OBJECT-TYPE
    SYNTAX       SnmpAdminString
    MAX-ACCESS   read-only
    STATUS       current
    DESCRIPTION
        "Cisco Firepower bios:VfPOSTErrorPause:rn managed object property"
    ::= { cfprBiosVfPOSTErrorPauseEntry 3 }

cfprBiosVfPOSTErrorPauseVpPOSTErrorPause OBJECT-TYPE
    SYNTAX       CfprBiosVfPOSTErrorPauseVpPOSTErrorPause
    MAX-ACCESS   read-only
    STATUS       current
    DESCRIPTION
        "Cisco Firepower bios:VfPOSTErrorPause:vpPOSTErrorPause
        managed object property"
    ::= { cfprBiosVfPOSTErrorPauseEntry 4 }

cfprBiosVfPOSTErrorPauseSupportedByDefault OBJECT-TYPE
    SYNTAX       CfprBiosSupportedAction
    MAX-ACCESS   read-only
    STATUS       current
    DESCRIPTION
        "Cisco Firepower bios:VfPOSTErrorPause:supportedByDefault
        managed object property"
    ::= { cfprBiosVfPOSTErrorPauseEntry 5 }

cfprBiosVfPSTATECoordinationTable OBJECT-TYPE
    SYNTAX           SEQUENCE OF CfprBiosVfPSTATECoordinationEntry
    MAX-ACCESS       not-accessible
    STATUS           current
    DESCRIPTION
        "Cisco Firepower bios:VfPSTATECoordination managed object table"
    ::= { cfprBiosObjects 52 }

cfprBiosVfPSTATECoordinationEntry OBJECT-TYPE
    SYNTAX           CfprBiosVfPSTATECoordinationEntry
    MAX-ACCESS       not-accessible
    STATUS           current
    DESCRIPTION
        "Entry for the cfprBiosVfPSTATECoordinationTable table."
    INDEX { cfprBiosVfPSTATECoordinationInstanceId }
    ::= { cfprBiosVfPSTATECoordinationTable 1 }

CfprBiosVfPSTATECoordinationEntry ::= SEQUENCE {
    cfprBiosVfPSTATECoordinationInstanceId                           CfprManagedObjectId,
    cfprBiosVfPSTATECoordinationDn                                   CfprManagedObjectDn,
    cfprBiosVfPSTATECoordinationRn                                   SnmpAdminString,
    cfprBiosVfPSTATECoordinationVpPSTATECoordination                 CfprBiosVfPSTATECoordinationVpPSTATECoordination,
    cfprBiosVfPSTATECoordinationSupportedByDefault                   CfprBiosSupportedAction
}

cfprBiosVfPSTATECoordinationInstanceId OBJECT-TYPE
    SYNTAX       CfprManagedObjectId
    MAX-ACCESS   not-accessible
    STATUS       current
    DESCRIPTION
        "Instance identifier of the managed object."
    ::= { cfprBiosVfPSTATECoordinationEntry 1 }

cfprBiosVfPSTATECoordinationDn OBJECT-TYPE
    SYNTAX       CfprManagedObjectDn
    MAX-ACCESS   read-only
    STATUS       current
    DESCRIPTION
        "Cisco Firepower bios:VfPSTATECoordination:dn managed
        object property"
    ::= { cfprBiosVfPSTATECoordinationEntry 2 }

cfprBiosVfPSTATECoordinationRn OBJECT-TYPE
    SYNTAX       SnmpAdminString
    MAX-ACCESS   read-only
    STATUS       current
    DESCRIPTION
        "Cisco Firepower bios:VfPSTATECoordination:rn managed
        object property"
    ::= { cfprBiosVfPSTATECoordinationEntry 3 }

cfprBiosVfPSTATECoordinationVpPSTATECoordination OBJECT-TYPE
    SYNTAX       CfprBiosVfPSTATECoordinationVpPSTATECoordination
    MAX-ACCESS   read-only
    STATUS       current
    DESCRIPTION
        "Cisco Firepower bios:VfPSTATECoordination:vpPSTATECoordination
        managed object property"
    ::= { cfprBiosVfPSTATECoordinationEntry 4 }

cfprBiosVfPSTATECoordinationSupportedByDefault OBJECT-TYPE
    SYNTAX       CfprBiosSupportedAction
    MAX-ACCESS   read-only
    STATUS       current
    DESCRIPTION
        "Cisco Firepower bios:VfPSTATECoordination:supportedByDefault
        managed object property"
    ::= { cfprBiosVfPSTATECoordinationEntry 5 }

cfprBiosVfPackageCStateLimitTable OBJECT-TYPE
    SYNTAX           SEQUENCE OF CfprBiosVfPackageCStateLimitEntry
    MAX-ACCESS       not-accessible
    STATUS           current
    DESCRIPTION
        "Cisco Firepower bios:VfPackageCStateLimit managed object table"
    ::= { cfprBiosObjects 53 }

cfprBiosVfPackageCStateLimitEntry OBJECT-TYPE
    SYNTAX           CfprBiosVfPackageCStateLimitEntry
    MAX-ACCESS       not-accessible
    STATUS           current
    DESCRIPTION
        "Entry for the cfprBiosVfPackageCStateLimitTable table."
    INDEX { cfprBiosVfPackageCStateLimitInstanceId }
    ::= { cfprBiosVfPackageCStateLimitTable 1 }

CfprBiosVfPackageCStateLimitEntry ::= SEQUENCE {
    cfprBiosVfPackageCStateLimitInstanceId                           CfprManagedObjectId,
    cfprBiosVfPackageCStateLimitDn                                   CfprManagedObjectDn,
    cfprBiosVfPackageCStateLimitRn                                   SnmpAdminString,
    cfprBiosVfPackageCStateLimitVpPackageCStateLimit                 CfprBiosVfPackageCStateLimitVpPackageCStateLimit,
    cfprBiosVfPackageCStateLimitSupportedByDefault                   CfprBiosSupportedAction
}

cfprBiosVfPackageCStateLimitInstanceId OBJECT-TYPE
    SYNTAX       CfprManagedObjectId
    MAX-ACCESS   not-accessible
    STATUS       current
    DESCRIPTION
        "Instance identifier of the managed object."
    ::= { cfprBiosVfPackageCStateLimitEntry 1 }

cfprBiosVfPackageCStateLimitDn OBJECT-TYPE
    SYNTAX       CfprManagedObjectDn
    MAX-ACCESS   read-only
    STATUS       current
    DESCRIPTION
        "Cisco Firepower bios:VfPackageCStateLimit:dn managed
        object property"
    ::= { cfprBiosVfPackageCStateLimitEntry 2 }

cfprBiosVfPackageCStateLimitRn OBJECT-TYPE
    SYNTAX       SnmpAdminString
    MAX-ACCESS   read-only
    STATUS       current
    DESCRIPTION
        "Cisco Firepower bios:VfPackageCStateLimit:rn managed
        object property"
    ::= { cfprBiosVfPackageCStateLimitEntry 3 }

cfprBiosVfPackageCStateLimitVpPackageCStateLimit OBJECT-TYPE
    SYNTAX       CfprBiosVfPackageCStateLimitVpPackageCStateLimit
    MAX-ACCESS   read-only
    STATUS       current
    DESCRIPTION
        "Cisco Firepower bios:VfPackageCStateLimit:vpPackageCStateLimit
        managed object property"
    ::= { cfprBiosVfPackageCStateLimitEntry 4 }

cfprBiosVfPackageCStateLimitSupportedByDefault OBJECT-TYPE
    SYNTAX       CfprBiosSupportedAction
    MAX-ACCESS   read-only
    STATUS       current
    DESCRIPTION
        "Cisco Firepower bios:VfPackageCStateLimit:supportedByDefault
        managed object property"
    ::= { cfprBiosVfPackageCStateLimitEntry 5 }

cfprBiosVfProcessorC1ETable OBJECT-TYPE
    SYNTAX           SEQUENCE OF CfprBiosVfProcessorC1EEntry
    MAX-ACCESS       not-accessible
    STATUS           current
    DESCRIPTION
        "Cisco Firepower bios:VfProcessorC1E managed object table"
    ::= { cfprBiosObjects 54 }

cfprBiosVfProcessorC1EEntry OBJECT-TYPE
    SYNTAX           CfprBiosVfProcessorC1EEntry
    MAX-ACCESS       not-accessible
    STATUS           current
    DESCRIPTION
        "Entry for the cfprBiosVfProcessorC1ETable table."
    INDEX { cfprBiosVfProcessorC1EInstanceId }
    ::= { cfprBiosVfProcessorC1ETable 1 }

CfprBiosVfProcessorC1EEntry ::= SEQUENCE {
    cfprBiosVfProcessorC1EInstanceId                                 CfprManagedObjectId,
    cfprBiosVfProcessorC1EDn                                         CfprManagedObjectDn,
    cfprBiosVfProcessorC1ERn                                         SnmpAdminString,
    cfprBiosVfProcessorC1EVpProcessorC1E                             CfprBiosVfProcessorC1EVpProcessorC1E,
    cfprBiosVfProcessorC1ESupportedByDefault                         CfprBiosSupportedAction
}

cfprBiosVfProcessorC1EInstanceId OBJECT-TYPE
    SYNTAX       CfprManagedObjectId
    MAX-ACCESS   not-accessible
    STATUS       current
    DESCRIPTION
        "Instance identifier of the managed object."
    ::= { cfprBiosVfProcessorC1EEntry 1 }

cfprBiosVfProcessorC1EDn OBJECT-TYPE
    SYNTAX       CfprManagedObjectDn
    MAX-ACCESS   read-only
    STATUS       current
    DESCRIPTION
        "Cisco Firepower bios:VfProcessorC1E:dn managed object property"
    ::= { cfprBiosVfProcessorC1EEntry 2 }

cfprBiosVfProcessorC1ERn OBJECT-TYPE
    SYNTAX       SnmpAdminString
    MAX-ACCESS   read-only
    STATUS       current
    DESCRIPTION
        "Cisco Firepower bios:VfProcessorC1E:rn managed object property"
    ::= { cfprBiosVfProcessorC1EEntry 3 }

cfprBiosVfProcessorC1EVpProcessorC1E OBJECT-TYPE
    SYNTAX       CfprBiosVfProcessorC1EVpProcessorC1E
    MAX-ACCESS   read-only
    STATUS       current
    DESCRIPTION
        "Cisco Firepower bios:VfProcessorC1E:vpProcessorC1E
        managed object property"
    ::= { cfprBiosVfProcessorC1EEntry 4 }

cfprBiosVfProcessorC1ESupportedByDefault OBJECT-TYPE
    SYNTAX       CfprBiosSupportedAction
    MAX-ACCESS   read-only
    STATUS       current
    DESCRIPTION
        "Cisco Firepower bios:VfProcessorC1E:supportedByDefault
        managed object property"
    ::= { cfprBiosVfProcessorC1EEntry 5 }

cfprBiosVfProcessorC3ReportTable OBJECT-TYPE
    SYNTAX           SEQUENCE OF CfprBiosVfProcessorC3ReportEntry
    MAX-ACCESS       not-accessible
    STATUS           current
    DESCRIPTION
        "Cisco Firepower bios:VfProcessorC3Report managed object table"
    ::= { cfprBiosObjects 55 }

cfprBiosVfProcessorC3ReportEntry OBJECT-TYPE
    SYNTAX           CfprBiosVfProcessorC3ReportEntry
    MAX-ACCESS       not-accessible
    STATUS           current
    DESCRIPTION
        "Entry for the cfprBiosVfProcessorC3ReportTable table."
    INDEX { cfprBiosVfProcessorC3ReportInstanceId }
    ::= { cfprBiosVfProcessorC3ReportTable 1 }

CfprBiosVfProcessorC3ReportEntry ::= SEQUENCE {
    cfprBiosVfProcessorC3ReportInstanceId                            CfprManagedObjectId,
    cfprBiosVfProcessorC3ReportDn                                    CfprManagedObjectDn,
    cfprBiosVfProcessorC3ReportRn                                    SnmpAdminString,
    cfprBiosVfProcessorC3ReportVpProcessorC3Report                   CfprBiosVfProcessorC3ReportVpProcessorC3Report,
    cfprBiosVfProcessorC3ReportSupportedByDefault                    CfprBiosSupportedAction
}

cfprBiosVfProcessorC3ReportInstanceId OBJECT-TYPE
    SYNTAX       CfprManagedObjectId
    MAX-ACCESS   not-accessible
    STATUS       current
    DESCRIPTION
        "Instance identifier of the managed object."
    ::= { cfprBiosVfProcessorC3ReportEntry 1 }

cfprBiosVfProcessorC3ReportDn OBJECT-TYPE
    SYNTAX       CfprManagedObjectDn
    MAX-ACCESS   read-only
    STATUS       current
    DESCRIPTION
        "Cisco Firepower bios:VfProcessorC3Report:dn managed
        object property"
    ::= { cfprBiosVfProcessorC3ReportEntry 2 }

cfprBiosVfProcessorC3ReportRn OBJECT-TYPE
    SYNTAX       SnmpAdminString
    MAX-ACCESS   read-only
    STATUS       current
    DESCRIPTION
        "Cisco Firepower bios:VfProcessorC3Report:rn managed
        object property"
    ::= { cfprBiosVfProcessorC3ReportEntry 3 }

cfprBiosVfProcessorC3ReportVpProcessorC3Report OBJECT-TYPE
    SYNTAX       CfprBiosVfProcessorC3ReportVpProcessorC3Report
    MAX-ACCESS   read-only
    STATUS       current
    DESCRIPTION
        "Cisco Firepower bios:VfProcessorC3Report:vpProcessorC3Report
        managed object property"
    ::= { cfprBiosVfProcessorC3ReportEntry 4 }

cfprBiosVfProcessorC3ReportSupportedByDefault OBJECT-TYPE
    SYNTAX       CfprBiosSupportedAction
    MAX-ACCESS   read-only
    STATUS       current
    DESCRIPTION
        "Cisco Firepower bios:VfProcessorC3Report:supportedByDefault
        managed object property"
    ::= { cfprBiosVfProcessorC3ReportEntry 5 }

cfprBiosVfProcessorC6ReportTable OBJECT-TYPE
    SYNTAX           SEQUENCE OF CfprBiosVfProcessorC6ReportEntry
    MAX-ACCESS       not-accessible
    STATUS           current
    DESCRIPTION
        "Cisco Firepower bios:VfProcessorC6Report managed object table"
    ::= { cfprBiosObjects 56 }

cfprBiosVfProcessorC6ReportEntry OBJECT-TYPE
    SYNTAX           CfprBiosVfProcessorC6ReportEntry
    MAX-ACCESS       not-accessible
    STATUS           current
    DESCRIPTION
        "Entry for the cfprBiosVfProcessorC6ReportTable table."
    INDEX { cfprBiosVfProcessorC6ReportInstanceId }
    ::= { cfprBiosVfProcessorC6ReportTable 1 }

CfprBiosVfProcessorC6ReportEntry ::= SEQUENCE {
    cfprBiosVfProcessorC6ReportInstanceId                            CfprManagedObjectId,
    cfprBiosVfProcessorC6ReportDn                                    CfprManagedObjectDn,
    cfprBiosVfProcessorC6ReportRn                                    SnmpAdminString,
    cfprBiosVfProcessorC6ReportVpProcessorC6Report                   CfprBiosVfProcessorC6ReportVpProcessorC6Report,
    cfprBiosVfProcessorC6ReportSupportedByDefault                    CfprBiosSupportedAction
}

cfprBiosVfProcessorC6ReportInstanceId OBJECT-TYPE
    SYNTAX       CfprManagedObjectId
    MAX-ACCESS   not-accessible
    STATUS       current
    DESCRIPTION
        "Instance identifier of the managed object."
    ::= { cfprBiosVfProcessorC6ReportEntry 1 }

cfprBiosVfProcessorC6ReportDn OBJECT-TYPE
    SYNTAX       CfprManagedObjectDn
    MAX-ACCESS   read-only
    STATUS       current
    DESCRIPTION
        "Cisco Firepower bios:VfProcessorC6Report:dn managed
        object property"
    ::= { cfprBiosVfProcessorC6ReportEntry 2 }

cfprBiosVfProcessorC6ReportRn OBJECT-TYPE
    SYNTAX       SnmpAdminString
    MAX-ACCESS   read-only
    STATUS       current
    DESCRIPTION
        "Cisco Firepower bios:VfProcessorC6Report:rn managed
        object property"
    ::= { cfprBiosVfProcessorC6ReportEntry 3 }

cfprBiosVfProcessorC6ReportVpProcessorC6Report OBJECT-TYPE
    SYNTAX       CfprBiosVfProcessorC6ReportVpProcessorC6Report
    MAX-ACCESS   read-only
    STATUS       current
    DESCRIPTION
        "Cisco Firepower bios:VfProcessorC6Report:vpProcessorC6Report
        managed object property"
    ::= { cfprBiosVfProcessorC6ReportEntry 4 }

cfprBiosVfProcessorC6ReportSupportedByDefault OBJECT-TYPE
    SYNTAX       CfprBiosSupportedAction
    MAX-ACCESS   read-only
    STATUS       current
    DESCRIPTION
        "Cisco Firepower bios:VfProcessorC6Report:supportedByDefault
        managed object property"
    ::= { cfprBiosVfProcessorC6ReportEntry 5 }

cfprBiosVfProcessorC7ReportTable OBJECT-TYPE
    SYNTAX           SEQUENCE OF CfprBiosVfProcessorC7ReportEntry
    MAX-ACCESS       not-accessible
    STATUS           current
    DESCRIPTION
        "Cisco Firepower bios:VfProcessorC7Report managed object table"
    ::= { cfprBiosObjects 57 }

cfprBiosVfProcessorC7ReportEntry OBJECT-TYPE
    SYNTAX           CfprBiosVfProcessorC7ReportEntry
    MAX-ACCESS       not-accessible
    STATUS           current
    DESCRIPTION
        "Entry for the cfprBiosVfProcessorC7ReportTable table."
    INDEX { cfprBiosVfProcessorC7ReportInstanceId }
    ::= { cfprBiosVfProcessorC7ReportTable 1 }

CfprBiosVfProcessorC7ReportEntry ::= SEQUENCE {
    cfprBiosVfProcessorC7ReportInstanceId                            CfprManagedObjectId,
    cfprBiosVfProcessorC7ReportDn                                    CfprManagedObjectDn,
    cfprBiosVfProcessorC7ReportRn                                    SnmpAdminString,
    cfprBiosVfProcessorC7ReportVpProcessorC7Report                   CfprBiosVfProcessorC7ReportVpProcessorC7Report,
    cfprBiosVfProcessorC7ReportSupportedByDefault                    CfprBiosSupportedAction
}

cfprBiosVfProcessorC7ReportInstanceId OBJECT-TYPE
    SYNTAX       CfprManagedObjectId
    MAX-ACCESS   not-accessible
    STATUS       current
    DESCRIPTION
        "Instance identifier of the managed object."
    ::= { cfprBiosVfProcessorC7ReportEntry 1 }

cfprBiosVfProcessorC7ReportDn OBJECT-TYPE
    SYNTAX       CfprManagedObjectDn
    MAX-ACCESS   read-only
    STATUS       current
    DESCRIPTION
        "Cisco Firepower bios:VfProcessorC7Report:dn managed
        object property"
    ::= { cfprBiosVfProcessorC7ReportEntry 2 }

cfprBiosVfProcessorC7ReportRn OBJECT-TYPE
    SYNTAX       SnmpAdminString
    MAX-ACCESS   read-only
    STATUS       current
    DESCRIPTION
        "Cisco Firepower bios:VfProcessorC7Report:rn managed
        object property"
    ::= { cfprBiosVfProcessorC7ReportEntry 3 }

cfprBiosVfProcessorC7ReportVpProcessorC7Report OBJECT-TYPE
    SYNTAX       CfprBiosVfProcessorC7ReportVpProcessorC7Report
    MAX-ACCESS   read-only
    STATUS       current
    DESCRIPTION
        "Cisco Firepower bios:VfProcessorC7Report:vpProcessorC7Report
        managed object property"
    ::= { cfprBiosVfProcessorC7ReportEntry 4 }

cfprBiosVfProcessorC7ReportSupportedByDefault OBJECT-TYPE
    SYNTAX       CfprBiosSupportedAction
    MAX-ACCESS   read-only
    STATUS       current
    DESCRIPTION
        "Cisco Firepower bios:VfProcessorC7Report:supportedByDefault
        managed object property"
    ::= { cfprBiosVfProcessorC7ReportEntry 5 }

cfprBiosVfProcessorCStateTable OBJECT-TYPE
    SYNTAX           SEQUENCE OF CfprBiosVfProcessorCStateEntry
    MAX-ACCESS       not-accessible
    STATUS           current
    DESCRIPTION
        "Cisco Firepower bios:VfProcessorCState managed object table"
    ::= { cfprBiosObjects 58 }

cfprBiosVfProcessorCStateEntry OBJECT-TYPE
    SYNTAX           CfprBiosVfProcessorCStateEntry
    MAX-ACCESS       not-accessible
    STATUS           current
    DESCRIPTION
        "Entry for the cfprBiosVfProcessorCStateTable table."
    INDEX { cfprBiosVfProcessorCStateInstanceId }
    ::= { cfprBiosVfProcessorCStateTable 1 }

CfprBiosVfProcessorCStateEntry ::= SEQUENCE {
    cfprBiosVfProcessorCStateInstanceId                              CfprManagedObjectId,
    cfprBiosVfProcessorCStateDn                                      CfprManagedObjectDn,
    cfprBiosVfProcessorCStateRn                                      SnmpAdminString,
    cfprBiosVfProcessorCStateVpProcessorCState                       CfprBiosVfProcessorCStateVpProcessorCState,
    cfprBiosVfProcessorCStateSupportedByDefault                      CfprBiosSupportedAction
}

cfprBiosVfProcessorCStateInstanceId OBJECT-TYPE
    SYNTAX       CfprManagedObjectId
    MAX-ACCESS   not-accessible
    STATUS       current
    DESCRIPTION
        "Instance identifier of the managed object."
    ::= { cfprBiosVfProcessorCStateEntry 1 }

cfprBiosVfProcessorCStateDn OBJECT-TYPE
    SYNTAX       CfprManagedObjectDn
    MAX-ACCESS   read-only
    STATUS       current
    DESCRIPTION
        "Cisco Firepower bios:VfProcessorCState:dn managed
        object property"
    ::= { cfprBiosVfProcessorCStateEntry 2 }

cfprBiosVfProcessorCStateRn OBJECT-TYPE
    SYNTAX       SnmpAdminString
    MAX-ACCESS   read-only
    STATUS       current
    DESCRIPTION
        "Cisco Firepower bios:VfProcessorCState:rn managed
        object property"
    ::= { cfprBiosVfProcessorCStateEntry 3 }

cfprBiosVfProcessorCStateVpProcessorCState OBJECT-TYPE
    SYNTAX       CfprBiosVfProcessorCStateVpProcessorCState
    MAX-ACCESS   read-only
    STATUS       current
    DESCRIPTION
        "Cisco Firepower bios:VfProcessorCState:vpProcessorCState
        managed object property"
    ::= { cfprBiosVfProcessorCStateEntry 4 }

cfprBiosVfProcessorCStateSupportedByDefault OBJECT-TYPE
    SYNTAX       CfprBiosSupportedAction
    MAX-ACCESS   read-only
    STATUS       current
    DESCRIPTION
        "Cisco Firepower bios:VfProcessorCState:supportedByDefault
        managed object property"
    ::= { cfprBiosVfProcessorCStateEntry 5 }

cfprBiosVfProcessorEnergyConfigurationTable OBJECT-TYPE
    SYNTAX           SEQUENCE OF CfprBiosVfProcessorEnergyConfigurationEntry
    MAX-ACCESS       not-accessible
    STATUS           current
    DESCRIPTION
        "Cisco Firepower bios:VfProcessorEnergyConfiguration
        managed object table"
    ::= { cfprBiosObjects 59 }

cfprBiosVfProcessorEnergyConfigurationEntry OBJECT-TYPE
    SYNTAX           CfprBiosVfProcessorEnergyConfigurationEntry
    MAX-ACCESS       not-accessible
    STATUS           current
    DESCRIPTION
        "Entry for the cfprBiosVfProcessorEnergyConfigurationTable table."
    INDEX { cfprBiosVfProcessorEnergyConfigurationInstanceId }
    ::= { cfprBiosVfProcessorEnergyConfigurationTable 1 }

CfprBiosVfProcessorEnergyConfigurationEntry ::= SEQUENCE {
    cfprBiosVfProcessorEnergyConfigurationInstanceId                 CfprManagedObjectId,
    cfprBiosVfProcessorEnergyConfigurationDn                         CfprManagedObjectDn,
    cfprBiosVfProcessorEnergyConfigurationRn                         SnmpAdminString,
    cfprBiosVfProcessorEnergyConfigurationVpEnergyPerformance        CfprBiosVfProcessorEnergyConfigurationVpEnergyPerformance,
    cfprBiosVfProcessorEnergyConfigurationVpPowerTechnology          CfprBiosVfProcessorEnergyConfigurationVpPowerTechnology,
    cfprBiosVfProcessorEnergyConfigurationSupportedByDefault         CfprBiosSupportedAction
}

cfprBiosVfProcessorEnergyConfigurationInstanceId OBJECT-TYPE
    SYNTAX       CfprManagedObjectId
    MAX-ACCESS   not-accessible
    STATUS       current
    DESCRIPTION
        "Instance identifier of the managed object."
    ::= { cfprBiosVfProcessorEnergyConfigurationEntry 1 }

cfprBiosVfProcessorEnergyConfigurationDn OBJECT-TYPE
    SYNTAX       CfprManagedObjectDn
    MAX-ACCESS   read-only
    STATUS       current
    DESCRIPTION
        "Cisco Firepower bios:VfProcessorEnergyConfiguration:dn
        managed object property"
    ::= { cfprBiosVfProcessorEnergyConfigurationEntry 2 }

cfprBiosVfProcessorEnergyConfigurationRn OBJECT-TYPE
    SYNTAX       SnmpAdminString
    MAX-ACCESS   read-only
    STATUS       current
    DESCRIPTION
        "Cisco Firepower bios:VfProcessorEnergyConfiguration:rn
        managed object property"
    ::= { cfprBiosVfProcessorEnergyConfigurationEntry 3 }

cfprBiosVfProcessorEnergyConfigurationVpEnergyPerformance OBJECT-TYPE
    SYNTAX       CfprBiosVfProcessorEnergyConfigurationVpEnergyPerformance
    MAX-ACCESS   read-only
    STATUS       current
    DESCRIPTION
        "Cisco Firepower bios:VfProcessorEnergyConfiguration:vpEnergyPerfo
        rmance managed object property"
    ::= { cfprBiosVfProcessorEnergyConfigurationEntry 4 }

cfprBiosVfProcessorEnergyConfigurationVpPowerTechnology OBJECT-TYPE
    SYNTAX       CfprBiosVfProcessorEnergyConfigurationVpPowerTechnology
    MAX-ACCESS   read-only
    STATUS       current
    DESCRIPTION
        "Cisco Firepower bios:VfProcessorEnergyConfiguration:vpPowerTechno
        logy managed object property"
    ::= { cfprBiosVfProcessorEnergyConfigurationEntry 5 }

cfprBiosVfProcessorEnergyConfigurationSupportedByDefault OBJECT-TYPE
    SYNTAX       CfprBiosSupportedAction
    MAX-ACCESS   read-only
    STATUS       current
    DESCRIPTION
        "Cisco Firepower bios:VfProcessorEnergyConfiguration:supportedByDe
        fault managed object property"
    ::= { cfprBiosVfProcessorEnergyConfigurationEntry 6 }

cfprBiosVfProcessorPrefetchConfigTable OBJECT-TYPE
    SYNTAX           SEQUENCE OF CfprBiosVfProcessorPrefetchConfigEntry
    MAX-ACCESS       not-accessible
    STATUS           current
    DESCRIPTION
        "Cisco Firepower bios:VfProcessorPrefetchConfig
        managed object table"
    ::= { cfprBiosObjects 60 }

cfprBiosVfProcessorPrefetchConfigEntry OBJECT-TYPE
    SYNTAX           CfprBiosVfProcessorPrefetchConfigEntry
    MAX-ACCESS       not-accessible
    STATUS           current
    DESCRIPTION
        "Entry for the cfprBiosVfProcessorPrefetchConfigTable table."
    INDEX { cfprBiosVfProcessorPrefetchConfigInstanceId }
    ::= { cfprBiosVfProcessorPrefetchConfigTable 1 }

CfprBiosVfProcessorPrefetchConfigEntry ::= SEQUENCE {
    cfprBiosVfProcessorPrefetchConfigInstanceId                      CfprManagedObjectId,
    cfprBiosVfProcessorPrefetchConfigDn                              CfprManagedObjectDn,
    cfprBiosVfProcessorPrefetchConfigRn                              SnmpAdminString,
    cfprBiosVfProcessorPrefetchConfigVpAdjacentCacheLinePrefetcher   CfprBiosVfProcessorPrefetchConfigVpAdjacentCacheLinePrefetcher,
    cfprBiosVfProcessorPrefetchConfigVpDCUIPPrefetcher               CfprBiosVfProcessorPrefetchConfigVpDCUIPPrefetcher,
    cfprBiosVfProcessorPrefetchConfigVpDCUStreamerPrefetch           CfprBiosVfProcessorPrefetchConfigVpDCUStreamerPrefetch,
    cfprBiosVfProcessorPrefetchConfigVpHardwarePrefetcher            CfprBiosVfProcessorPrefetchConfigVpHardwarePrefetcher,
    cfprBiosVfProcessorPrefetchConfigSupportedByDefault              CfprBiosSupportedAction
}

cfprBiosVfProcessorPrefetchConfigInstanceId OBJECT-TYPE
    SYNTAX       CfprManagedObjectId
    MAX-ACCESS   not-accessible
    STATUS       current
    DESCRIPTION
        "Instance identifier of the managed object."
    ::= { cfprBiosVfProcessorPrefetchConfigEntry 1 }

cfprBiosVfProcessorPrefetchConfigDn OBJECT-TYPE
    SYNTAX       CfprManagedObjectDn
    MAX-ACCESS   read-only
    STATUS       current
    DESCRIPTION
        "Cisco Firepower bios:VfProcessorPrefetchConfig:dn
        managed object property"
    ::= { cfprBiosVfProcessorPrefetchConfigEntry 2 }

cfprBiosVfProcessorPrefetchConfigRn OBJECT-TYPE
    SYNTAX       SnmpAdminString
    MAX-ACCESS   read-only
    STATUS       current
    DESCRIPTION
        "Cisco Firepower bios:VfProcessorPrefetchConfig:rn
        managed object property"
    ::= { cfprBiosVfProcessorPrefetchConfigEntry 3 }

cfprBiosVfProcessorPrefetchConfigVpAdjacentCacheLinePrefetcher OBJECT-TYPE
    SYNTAX       CfprBiosVfProcessorPrefetchConfigVpAdjacentCacheLinePrefetcher
    MAX-ACCESS   read-only
    STATUS       current
    DESCRIPTION
        "Cisco Firepower bios:VfProcessorPrefetchConfig:vpAdjacentCacheLin
        ePrefetcher managed object property"
    ::= { cfprBiosVfProcessorPrefetchConfigEntry 4 }

cfprBiosVfProcessorPrefetchConfigVpDCUIPPrefetcher OBJECT-TYPE
    SYNTAX       CfprBiosVfProcessorPrefetchConfigVpDCUIPPrefetcher
    MAX-ACCESS   read-only
    STATUS       current
    DESCRIPTION
        "Cisco Firepower bios:VfProcessorPrefetchConfig:vpDCUIPPrefetcher
        managed object property"
    ::= { cfprBiosVfProcessorPrefetchConfigEntry 5 }

cfprBiosVfProcessorPrefetchConfigVpDCUStreamerPrefetch OBJECT-TYPE
    SYNTAX       CfprBiosVfProcessorPrefetchConfigVpDCUStreamerPrefetch
    MAX-ACCESS   read-only
    STATUS       current
    DESCRIPTION
        "Cisco Firepower bios:VfProcessorPrefetchConfig:vpDCUStreamerPrefe
        tch managed object property"
    ::= { cfprBiosVfProcessorPrefetchConfigEntry 6 }

cfprBiosVfProcessorPrefetchConfigVpHardwarePrefetcher OBJECT-TYPE
    SYNTAX       CfprBiosVfProcessorPrefetchConfigVpHardwarePrefetcher
    MAX-ACCESS   read-only
    STATUS       current
    DESCRIPTION
        "Cisco Firepower bios:VfProcessorPrefetchConfig:vpHardwarePrefetch
        er managed object property"
    ::= { cfprBiosVfProcessorPrefetchConfigEntry 7 }

cfprBiosVfProcessorPrefetchConfigSupportedByDefault OBJECT-TYPE
    SYNTAX       CfprBiosSupportedAction
    MAX-ACCESS   read-only
    STATUS       current
    DESCRIPTION
        "Cisco Firepower bios:VfProcessorPrefetchConfig:supportedByDefault
         managed object property"
    ::= { cfprBiosVfProcessorPrefetchConfigEntry 8 }

cfprBiosVfQPILinkFrequencySelectTable OBJECT-TYPE
    SYNTAX           SEQUENCE OF CfprBiosVfQPILinkFrequencySelectEntry
    MAX-ACCESS       not-accessible
    STATUS           current
    DESCRIPTION
        "Cisco Firepower bios:VfQPILinkFrequencySelect
        managed object table"
    ::= { cfprBiosObjects 61 }

cfprBiosVfQPILinkFrequencySelectEntry OBJECT-TYPE
    SYNTAX           CfprBiosVfQPILinkFrequencySelectEntry
    MAX-ACCESS       not-accessible
    STATUS           current
    DESCRIPTION
        "Entry for the cfprBiosVfQPILinkFrequencySelectTable table."
    INDEX { cfprBiosVfQPILinkFrequencySelectInstanceId }
    ::= { cfprBiosVfQPILinkFrequencySelectTable 1 }

CfprBiosVfQPILinkFrequencySelectEntry ::= SEQUENCE {
    cfprBiosVfQPILinkFrequencySelectInstanceId                       CfprManagedObjectId,
    cfprBiosVfQPILinkFrequencySelectDn                               CfprManagedObjectDn,
    cfprBiosVfQPILinkFrequencySelectRn                               SnmpAdminString,
    cfprBiosVfQPILinkFrequencySelectVpQPILinkFrequencySelect         CfprBiosVfQPILinkFrequencySelectVpQPILinkFrequencySelect,
    cfprBiosVfQPILinkFrequencySelectSupportedByDefault               CfprBiosSupportedAction
}

cfprBiosVfQPILinkFrequencySelectInstanceId OBJECT-TYPE
    SYNTAX       CfprManagedObjectId
    MAX-ACCESS   not-accessible
    STATUS       current
    DESCRIPTION
        "Instance identifier of the managed object."
    ::= { cfprBiosVfQPILinkFrequencySelectEntry 1 }

cfprBiosVfQPILinkFrequencySelectDn OBJECT-TYPE
    SYNTAX       CfprManagedObjectDn
    MAX-ACCESS   read-only
    STATUS       current
    DESCRIPTION
        "Cisco Firepower bios:VfQPILinkFrequencySelect:dn
        managed object property"
    ::= { cfprBiosVfQPILinkFrequencySelectEntry 2 }

cfprBiosVfQPILinkFrequencySelectRn OBJECT-TYPE
    SYNTAX       SnmpAdminString
    MAX-ACCESS   read-only
    STATUS       current
    DESCRIPTION
        "Cisco Firepower bios:VfQPILinkFrequencySelect:rn
        managed object property"
    ::= { cfprBiosVfQPILinkFrequencySelectEntry 3 }

cfprBiosVfQPILinkFrequencySelectVpQPILinkFrequencySelect OBJECT-TYPE
    SYNTAX       CfprBiosVfQPILinkFrequencySelectVpQPILinkFrequencySelect
    MAX-ACCESS   read-only
    STATUS       current
    DESCRIPTION
        "Cisco Firepower bios:VfQPILinkFrequencySelect:vpQPILinkFrequencyS
        elect managed object property"
    ::= { cfprBiosVfQPILinkFrequencySelectEntry 4 }

cfprBiosVfQPILinkFrequencySelectSupportedByDefault OBJECT-TYPE
    SYNTAX       CfprBiosSupportedAction
    MAX-ACCESS   read-only
    STATUS       current
    DESCRIPTION
        "Cisco Firepower bios:VfQPILinkFrequencySelect:supportedByDefault
        managed object property"
    ::= { cfprBiosVfQPILinkFrequencySelectEntry 5 }

cfprBiosVfQuietBootTable OBJECT-TYPE
    SYNTAX           SEQUENCE OF CfprBiosVfQuietBootEntry
    MAX-ACCESS       not-accessible
    STATUS           current
    DESCRIPTION
        "Cisco Firepower bios:VfQuietBoot managed object table"
    ::= { cfprBiosObjects 62 }

cfprBiosVfQuietBootEntry OBJECT-TYPE
    SYNTAX           CfprBiosVfQuietBootEntry
    MAX-ACCESS       not-accessible
    STATUS           current
    DESCRIPTION
        "Entry for the cfprBiosVfQuietBootTable table."
    INDEX { cfprBiosVfQuietBootInstanceId }
    ::= { cfprBiosVfQuietBootTable 1 }

CfprBiosVfQuietBootEntry ::= SEQUENCE {
    cfprBiosVfQuietBootInstanceId                                    CfprManagedObjectId,
    cfprBiosVfQuietBootDn                                            CfprManagedObjectDn,
    cfprBiosVfQuietBootRn                                            SnmpAdminString,
    cfprBiosVfQuietBootVpQuietBoot                                   CfprBiosVfQuietBootVpQuietBoot,
    cfprBiosVfQuietBootSupportedByDefault                            CfprBiosSupportedAction
}

cfprBiosVfQuietBootInstanceId OBJECT-TYPE
    SYNTAX       CfprManagedObjectId
    MAX-ACCESS   not-accessible
    STATUS       current
    DESCRIPTION
        "Instance identifier of the managed object."
    ::= { cfprBiosVfQuietBootEntry 1 }

cfprBiosVfQuietBootDn OBJECT-TYPE
    SYNTAX       CfprManagedObjectDn
    MAX-ACCESS   read-only
    STATUS       current
    DESCRIPTION
        "Cisco Firepower bios:VfQuietBoot:dn managed object property"
    ::= { cfprBiosVfQuietBootEntry 2 }

cfprBiosVfQuietBootRn OBJECT-TYPE
    SYNTAX       SnmpAdminString
    MAX-ACCESS   read-only
    STATUS       current
    DESCRIPTION
        "Cisco Firepower bios:VfQuietBoot:rn managed object property"
    ::= { cfprBiosVfQuietBootEntry 3 }

cfprBiosVfQuietBootVpQuietBoot OBJECT-TYPE
    SYNTAX       CfprBiosVfQuietBootVpQuietBoot
    MAX-ACCESS   read-only
    STATUS       current
    DESCRIPTION
        "Cisco Firepower bios:VfQuietBoot:vpQuietBoot managed
        object property"
    ::= { cfprBiosVfQuietBootEntry 4 }

cfprBiosVfQuietBootSupportedByDefault OBJECT-TYPE
    SYNTAX       CfprBiosSupportedAction
    MAX-ACCESS   read-only
    STATUS       current
    DESCRIPTION
        "Cisco Firepower bios:VfQuietBoot:supportedByDefault
        managed object property"
    ::= { cfprBiosVfQuietBootEntry 5 }

cfprBiosVfResumeOnACPowerLossTable OBJECT-TYPE
    SYNTAX           SEQUENCE OF CfprBiosVfResumeOnACPowerLossEntry
    MAX-ACCESS       not-accessible
    STATUS           current
    DESCRIPTION
        "Cisco Firepower bios:VfResumeOnACPowerLoss managed object table"
    ::= { cfprBiosObjects 63 }

cfprBiosVfResumeOnACPowerLossEntry OBJECT-TYPE
    SYNTAX           CfprBiosVfResumeOnACPowerLossEntry
    MAX-ACCESS       not-accessible
    STATUS           current
    DESCRIPTION
        "Entry for the cfprBiosVfResumeOnACPowerLossTable table."
    INDEX { cfprBiosVfResumeOnACPowerLossInstanceId }
    ::= { cfprBiosVfResumeOnACPowerLossTable 1 }

CfprBiosVfResumeOnACPowerLossEntry ::= SEQUENCE {
    cfprBiosVfResumeOnACPowerLossInstanceId                          CfprManagedObjectId,
    cfprBiosVfResumeOnACPowerLossDn                                  CfprManagedObjectDn,
    cfprBiosVfResumeOnACPowerLossRn                                  SnmpAdminString,
    cfprBiosVfResumeOnACPowerLossVpResumeOnACPowerLoss               CfprBiosVfResumeOnACPowerLossVpResumeOnACPowerLoss,
    cfprBiosVfResumeOnACPowerLossSupportedByDefault                  CfprBiosSupportedAction
}

cfprBiosVfResumeOnACPowerLossInstanceId OBJECT-TYPE
    SYNTAX       CfprManagedObjectId
    MAX-ACCESS   not-accessible
    STATUS       current
    DESCRIPTION
        "Instance identifier of the managed object."
    ::= { cfprBiosVfResumeOnACPowerLossEntry 1 }

cfprBiosVfResumeOnACPowerLossDn OBJECT-TYPE
    SYNTAX       CfprManagedObjectDn
    MAX-ACCESS   read-only
    STATUS       current
    DESCRIPTION
        "Cisco Firepower bios:VfResumeOnACPowerLoss:dn
        managed object property"
    ::= { cfprBiosVfResumeOnACPowerLossEntry 2 }

cfprBiosVfResumeOnACPowerLossRn OBJECT-TYPE
    SYNTAX       SnmpAdminString
    MAX-ACCESS   read-only
    STATUS       current
    DESCRIPTION
        "Cisco Firepower bios:VfResumeOnACPowerLoss:rn
        managed object property"
    ::= { cfprBiosVfResumeOnACPowerLossEntry 3 }

cfprBiosVfResumeOnACPowerLossVpResumeOnACPowerLoss OBJECT-TYPE
    SYNTAX       CfprBiosVfResumeOnACPowerLossVpResumeOnACPowerLoss
    MAX-ACCESS   read-only
    STATUS       current
    DESCRIPTION
        "Cisco Firepower bios:VfResumeOnACPowerLoss:vpResumeOnACPowerLoss
        managed object property"
    ::= { cfprBiosVfResumeOnACPowerLossEntry 4 }

cfprBiosVfResumeOnACPowerLossSupportedByDefault OBJECT-TYPE
    SYNTAX       CfprBiosSupportedAction
    MAX-ACCESS   read-only
    STATUS       current
    DESCRIPTION
        "Cisco Firepower bios:VfResumeOnACPowerLoss:supportedByDefault
        managed object property"
    ::= { cfprBiosVfResumeOnACPowerLossEntry 5 }

cfprBiosVfScrubPoliciesTable OBJECT-TYPE
    SYNTAX           SEQUENCE OF CfprBiosVfScrubPoliciesEntry
    MAX-ACCESS       not-accessible
    STATUS           current
    DESCRIPTION
        "Cisco Firepower bios:VfScrubPolicies managed object table"
    ::= { cfprBiosObjects 64 }

cfprBiosVfScrubPoliciesEntry OBJECT-TYPE
    SYNTAX           CfprBiosVfScrubPoliciesEntry
    MAX-ACCESS       not-accessible
    STATUS           current
    DESCRIPTION
        "Entry for the cfprBiosVfScrubPoliciesTable table."
    INDEX { cfprBiosVfScrubPoliciesInstanceId }
    ::= { cfprBiosVfScrubPoliciesTable 1 }

CfprBiosVfScrubPoliciesEntry ::= SEQUENCE {
    cfprBiosVfScrubPoliciesInstanceId                                CfprManagedObjectId,
    cfprBiosVfScrubPoliciesDn                                        CfprManagedObjectDn,
    cfprBiosVfScrubPoliciesRn                                        SnmpAdminString,
    cfprBiosVfScrubPoliciesVpDemandScrub                             CfprBiosVfScrubPoliciesVpDemandScrub,
    cfprBiosVfScrubPoliciesVpPatrolScrub                             CfprBiosVfScrubPoliciesVpPatrolScrub,
    cfprBiosVfScrubPoliciesSupportedByDefault                        CfprBiosSupportedAction
}

cfprBiosVfScrubPoliciesInstanceId OBJECT-TYPE
    SYNTAX       CfprManagedObjectId
    MAX-ACCESS   not-accessible
    STATUS       current
    DESCRIPTION
        "Instance identifier of the managed object."
    ::= { cfprBiosVfScrubPoliciesEntry 1 }

cfprBiosVfScrubPoliciesDn OBJECT-TYPE
    SYNTAX       CfprManagedObjectDn
    MAX-ACCESS   read-only
    STATUS       current
    DESCRIPTION
        "Cisco Firepower bios:VfScrubPolicies:dn managed object property"
    ::= { cfprBiosVfScrubPoliciesEntry 2 }

cfprBiosVfScrubPoliciesRn OBJECT-TYPE
    SYNTAX       SnmpAdminString
    MAX-ACCESS   read-only
    STATUS       current
    DESCRIPTION
        "Cisco Firepower bios:VfScrubPolicies:rn managed object property"
    ::= { cfprBiosVfScrubPoliciesEntry 3 }

cfprBiosVfScrubPoliciesVpDemandScrub OBJECT-TYPE
    SYNTAX       CfprBiosVfScrubPoliciesVpDemandScrub
    MAX-ACCESS   read-only
    STATUS       current
    DESCRIPTION
        "Cisco Firepower bios:VfScrubPolicies:vpDemandScrub
        managed object property"
    ::= { cfprBiosVfScrubPoliciesEntry 4 }

cfprBiosVfScrubPoliciesVpPatrolScrub OBJECT-TYPE
    SYNTAX       CfprBiosVfScrubPoliciesVpPatrolScrub
    MAX-ACCESS   read-only
    STATUS       current
    DESCRIPTION
        "Cisco Firepower bios:VfScrubPolicies:vpPatrolScrub
        managed object property"
    ::= { cfprBiosVfScrubPoliciesEntry 5 }

cfprBiosVfScrubPoliciesSupportedByDefault OBJECT-TYPE
    SYNTAX       CfprBiosSupportedAction
    MAX-ACCESS   read-only
    STATUS       current
    DESCRIPTION
        "Cisco Firepower bios:VfScrubPolicies:supportedByDefault
        managed object property"
    ::= { cfprBiosVfScrubPoliciesEntry 6 }

cfprBiosVfSelectMemoryRASConfigurationTable OBJECT-TYPE
    SYNTAX           SEQUENCE OF CfprBiosVfSelectMemoryRASConfigurationEntry
    MAX-ACCESS       not-accessible
    STATUS           current
    DESCRIPTION
        "Cisco Firepower bios:VfSelectMemoryRASConfiguration
        managed object table"
    ::= { cfprBiosObjects 65 }

cfprBiosVfSelectMemoryRASConfigurationEntry OBJECT-TYPE
    SYNTAX           CfprBiosVfSelectMemoryRASConfigurationEntry
    MAX-ACCESS       not-accessible
    STATUS           current
    DESCRIPTION
        "Entry for the cfprBiosVfSelectMemoryRASConfigurationTable table."
    INDEX { cfprBiosVfSelectMemoryRASConfigurationInstanceId }
    ::= { cfprBiosVfSelectMemoryRASConfigurationTable 1 }

CfprBiosVfSelectMemoryRASConfigurationEntry ::= SEQUENCE {
    cfprBiosVfSelectMemoryRASConfigurationInstanceId                 CfprManagedObjectId,
    cfprBiosVfSelectMemoryRASConfigurationDn                         CfprManagedObjectDn,
    cfprBiosVfSelectMemoryRASConfigurationRn                         SnmpAdminString,
    cfprBiosVfSelectMemoryRASConfigurationVpSelectMemoryRASConfiguration CfprBiosVfSelectMemoryRASConfigurationVpSelectMemoryRASConf,
    cfprBiosVfSelectMemoryRASConfigurationSupportedByDefault         CfprBiosSupportedAction
}

cfprBiosVfSelectMemoryRASConfigurationInstanceId OBJECT-TYPE
    SYNTAX       CfprManagedObjectId
    MAX-ACCESS   not-accessible
    STATUS       current
    DESCRIPTION
        "Instance identifier of the managed object."
    ::= { cfprBiosVfSelectMemoryRASConfigurationEntry 1 }

cfprBiosVfSelectMemoryRASConfigurationDn OBJECT-TYPE
    SYNTAX       CfprManagedObjectDn
    MAX-ACCESS   read-only
    STATUS       current
    DESCRIPTION
        "Cisco Firepower bios:VfSelectMemoryRASConfiguration:dn
        managed object property"
    ::= { cfprBiosVfSelectMemoryRASConfigurationEntry 2 }

cfprBiosVfSelectMemoryRASConfigurationRn OBJECT-TYPE
    SYNTAX       SnmpAdminString
    MAX-ACCESS   read-only
    STATUS       current
    DESCRIPTION
        "Cisco Firepower bios:VfSelectMemoryRASConfiguration:rn
        managed object property"
    ::= { cfprBiosVfSelectMemoryRASConfigurationEntry 3 }

cfprBiosVfSelectMemoryRASConfigurationVpSelectMemoryRASConfiguration OBJECT-TYPE
    SYNTAX       CfprBiosVfSelectMemoryRASConfigurationVpSelectMemoryRASConf
    MAX-ACCESS   read-only
    STATUS       current
    DESCRIPTION
        "Cisco Firepower bios:VfSelectMemoryRASConfiguration:vpSelectMemor
        yRASConfiguration managed object property"
    ::= { cfprBiosVfSelectMemoryRASConfigurationEntry 4 }

cfprBiosVfSelectMemoryRASConfigurationSupportedByDefault OBJECT-TYPE
    SYNTAX       CfprBiosSupportedAction
    MAX-ACCESS   read-only
    STATUS       current
    DESCRIPTION
        "Cisco Firepower bios:VfSelectMemoryRASConfiguration:supportedByDe
        fault managed object property"
    ::= { cfprBiosVfSelectMemoryRASConfigurationEntry 5 }

cfprBiosVfSerialPortAEnableTable OBJECT-TYPE
    SYNTAX           SEQUENCE OF CfprBiosVfSerialPortAEnableEntry
    MAX-ACCESS       not-accessible
    STATUS           current
    DESCRIPTION
        "Cisco Firepower bios:VfSerialPortAEnable managed object table"
    ::= { cfprBiosObjects 66 }

cfprBiosVfSerialPortAEnableEntry OBJECT-TYPE
    SYNTAX           CfprBiosVfSerialPortAEnableEntry
    MAX-ACCESS       not-accessible
    STATUS           current
    DESCRIPTION
        "Entry for the cfprBiosVfSerialPortAEnableTable table."
    INDEX { cfprBiosVfSerialPortAEnableInstanceId }
    ::= { cfprBiosVfSerialPortAEnableTable 1 }

CfprBiosVfSerialPortAEnableEntry ::= SEQUENCE {
    cfprBiosVfSerialPortAEnableInstanceId                            CfprManagedObjectId,
    cfprBiosVfSerialPortAEnableDn                                    CfprManagedObjectDn,
    cfprBiosVfSerialPortAEnableRn                                    SnmpAdminString,
    cfprBiosVfSerialPortAEnableVpSerialPortAEnable                   CfprBiosVfSerialPortAEnableVpSerialPortAEnable,
    cfprBiosVfSerialPortAEnableSupportedByDefault                    CfprBiosSupportedAction
}

cfprBiosVfSerialPortAEnableInstanceId OBJECT-TYPE
    SYNTAX       CfprManagedObjectId
    MAX-ACCESS   not-accessible
    STATUS       current
    DESCRIPTION
        "Instance identifier of the managed object."
    ::= { cfprBiosVfSerialPortAEnableEntry 1 }

cfprBiosVfSerialPortAEnableDn OBJECT-TYPE
    SYNTAX       CfprManagedObjectDn
    MAX-ACCESS   read-only
    STATUS       current
    DESCRIPTION
        "Cisco Firepower bios:VfSerialPortAEnable:dn managed
        object property"
    ::= { cfprBiosVfSerialPortAEnableEntry 2 }

cfprBiosVfSerialPortAEnableRn OBJECT-TYPE
    SYNTAX       SnmpAdminString
    MAX-ACCESS   read-only
    STATUS       current
    DESCRIPTION
        "Cisco Firepower bios:VfSerialPortAEnable:rn managed
        object property"
    ::= { cfprBiosVfSerialPortAEnableEntry 3 }

cfprBiosVfSerialPortAEnableVpSerialPortAEnable OBJECT-TYPE
    SYNTAX       CfprBiosVfSerialPortAEnableVpSerialPortAEnable
    MAX-ACCESS   read-only
    STATUS       current
    DESCRIPTION
        "Cisco Firepower bios:VfSerialPortAEnable:vpSerialPortAEnable
        managed object property"
    ::= { cfprBiosVfSerialPortAEnableEntry 4 }

cfprBiosVfSerialPortAEnableSupportedByDefault OBJECT-TYPE
    SYNTAX       CfprBiosSupportedAction
    MAX-ACCESS   read-only
    STATUS       current
    DESCRIPTION
        "Cisco Firepower bios:VfSerialPortAEnable:supportedByDefault
        managed object property"
    ::= { cfprBiosVfSerialPortAEnableEntry 5 }

cfprBiosVfSparingModeTable OBJECT-TYPE
    SYNTAX           SEQUENCE OF CfprBiosVfSparingModeEntry
    MAX-ACCESS       not-accessible
    STATUS           current
    DESCRIPTION
        "Cisco Firepower bios:VfSparingMode managed object table"
    ::= { cfprBiosObjects 67 }

cfprBiosVfSparingModeEntry OBJECT-TYPE
    SYNTAX           CfprBiosVfSparingModeEntry
    MAX-ACCESS       not-accessible
    STATUS           current
    DESCRIPTION
        "Entry for the cfprBiosVfSparingModeTable table."
    INDEX { cfprBiosVfSparingModeInstanceId }
    ::= { cfprBiosVfSparingModeTable 1 }

CfprBiosVfSparingModeEntry ::= SEQUENCE {
    cfprBiosVfSparingModeInstanceId                                  CfprManagedObjectId,
    cfprBiosVfSparingModeDn                                          CfprManagedObjectDn,
    cfprBiosVfSparingModeRn                                          SnmpAdminString,
    cfprBiosVfSparingModeVpSparingMode                               CfprBiosVfSparingModeVpSparingMode,
    cfprBiosVfSparingModeSupportedByDefault                          CfprBiosSupportedAction
}

cfprBiosVfSparingModeInstanceId OBJECT-TYPE
    SYNTAX       CfprManagedObjectId
    MAX-ACCESS   not-accessible
    STATUS       current
    DESCRIPTION
        "Instance identifier of the managed object."
    ::= { cfprBiosVfSparingModeEntry 1 }

cfprBiosVfSparingModeDn OBJECT-TYPE
    SYNTAX       CfprManagedObjectDn
    MAX-ACCESS   read-only
    STATUS       current
    DESCRIPTION
        "Cisco Firepower bios:VfSparingMode:dn managed object property"
    ::= { cfprBiosVfSparingModeEntry 2 }

cfprBiosVfSparingModeRn OBJECT-TYPE
    SYNTAX       SnmpAdminString
    MAX-ACCESS   read-only
    STATUS       current
    DESCRIPTION
        "Cisco Firepower bios:VfSparingMode:rn managed object property"
    ::= { cfprBiosVfSparingModeEntry 3 }

cfprBiosVfSparingModeVpSparingMode OBJECT-TYPE
    SYNTAX       CfprBiosVfSparingModeVpSparingMode
    MAX-ACCESS   read-only
    STATUS       current
    DESCRIPTION
        "Cisco Firepower bios:VfSparingMode:vpSparingMode
        managed object property"
    ::= { cfprBiosVfSparingModeEntry 4 }

cfprBiosVfSparingModeSupportedByDefault OBJECT-TYPE
    SYNTAX       CfprBiosSupportedAction
    MAX-ACCESS   read-only
    STATUS       current
    DESCRIPTION
        "Cisco Firepower bios:VfSparingMode:supportedByDefault
        managed object property"
    ::= { cfprBiosVfSparingModeEntry 5 }

cfprBiosVfSriovConfigTable OBJECT-TYPE
    SYNTAX           SEQUENCE OF CfprBiosVfSriovConfigEntry
    MAX-ACCESS       not-accessible
    STATUS           current
    DESCRIPTION
        "Cisco Firepower bios:VfSriovConfig managed object table"
    ::= { cfprBiosObjects 68 }

cfprBiosVfSriovConfigEntry OBJECT-TYPE
    SYNTAX           CfprBiosVfSriovConfigEntry
    MAX-ACCESS       not-accessible
    STATUS           current
    DESCRIPTION
        "Entry for the cfprBiosVfSriovConfigTable table."
    INDEX { cfprBiosVfSriovConfigInstanceId }
    ::= { cfprBiosVfSriovConfigTable 1 }

CfprBiosVfSriovConfigEntry ::= SEQUENCE {
    cfprBiosVfSriovConfigInstanceId                                  CfprManagedObjectId,
    cfprBiosVfSriovConfigDn                                          CfprManagedObjectDn,
    cfprBiosVfSriovConfigRn                                          SnmpAdminString,
    cfprBiosVfSriovConfigVpSriov                                     CfprBiosVfSriovConfigVpSriov,
    cfprBiosVfSriovConfigSupportedByDefault                          CfprBiosSupportedAction
}

cfprBiosVfSriovConfigInstanceId OBJECT-TYPE
    SYNTAX       CfprManagedObjectId
    MAX-ACCESS   not-accessible
    STATUS       current
    DESCRIPTION
        "Instance identifier of the managed object."
    ::= { cfprBiosVfSriovConfigEntry 1 }

cfprBiosVfSriovConfigDn OBJECT-TYPE
    SYNTAX       CfprManagedObjectDn
    MAX-ACCESS   read-only
    STATUS       current
    DESCRIPTION
        "Cisco Firepower bios:VfSriovConfig:dn managed object property"
    ::= { cfprBiosVfSriovConfigEntry 2 }

cfprBiosVfSriovConfigRn OBJECT-TYPE
    SYNTAX       SnmpAdminString
    MAX-ACCESS   read-only
    STATUS       current
    DESCRIPTION
        "Cisco Firepower bios:VfSriovConfig:rn managed object property"
    ::= { cfprBiosVfSriovConfigEntry 3 }

cfprBiosVfSriovConfigVpSriov OBJECT-TYPE
    SYNTAX       CfprBiosVfSriovConfigVpSriov
    MAX-ACCESS   read-only
    STATUS       current
    DESCRIPTION
        "Cisco Firepower bios:VfSriovConfig:vpSriov managed
        object property"
    ::= { cfprBiosVfSriovConfigEntry 4 }

cfprBiosVfSriovConfigSupportedByDefault OBJECT-TYPE
    SYNTAX       CfprBiosSupportedAction
    MAX-ACCESS   read-only
    STATUS       current
    DESCRIPTION
        "Cisco Firepower bios:VfSriovConfig:supportedByDefault
        managed object property"
    ::= { cfprBiosVfSriovConfigEntry 5 }

cfprBiosVfTPMSupportTable OBJECT-TYPE
    SYNTAX           SEQUENCE OF CfprBiosVfTPMSupportEntry
    MAX-ACCESS       not-accessible
    STATUS           current
    DESCRIPTION
        "Cisco Firepower bios:VfTPMSupport managed object table"
    ::= { cfprBiosObjects 69 }

cfprBiosVfTPMSupportEntry OBJECT-TYPE
    SYNTAX           CfprBiosVfTPMSupportEntry
    MAX-ACCESS       not-accessible
    STATUS           current
    DESCRIPTION
        "Entry for the cfprBiosVfTPMSupportTable table."
    INDEX { cfprBiosVfTPMSupportInstanceId }
    ::= { cfprBiosVfTPMSupportTable 1 }

CfprBiosVfTPMSupportEntry ::= SEQUENCE {
    cfprBiosVfTPMSupportInstanceId                                   CfprManagedObjectId,
    cfprBiosVfTPMSupportDn                                           CfprManagedObjectDn,
    cfprBiosVfTPMSupportRn                                           SnmpAdminString,
    cfprBiosVfTPMSupportVpTPMSupport                                 CfprBiosVfTPMSupportVpTPMSupport,
    cfprBiosVfTPMSupportSupportedByDefault                           CfprBiosSupportedAction
}

cfprBiosVfTPMSupportInstanceId OBJECT-TYPE
    SYNTAX       CfprManagedObjectId
    MAX-ACCESS   not-accessible
    STATUS       current
    DESCRIPTION
        "Instance identifier of the managed object."
    ::= { cfprBiosVfTPMSupportEntry 1 }

cfprBiosVfTPMSupportDn OBJECT-TYPE
    SYNTAX       CfprManagedObjectDn
    MAX-ACCESS   read-only
    STATUS       current
    DESCRIPTION
        "Cisco Firepower bios:VfTPMSupport:dn managed object property"
    ::= { cfprBiosVfTPMSupportEntry 2 }

cfprBiosVfTPMSupportRn OBJECT-TYPE
    SYNTAX       SnmpAdminString
    MAX-ACCESS   read-only
    STATUS       current
    DESCRIPTION
        "Cisco Firepower bios:VfTPMSupport:rn managed object property"
    ::= { cfprBiosVfTPMSupportEntry 3 }

cfprBiosVfTPMSupportVpTPMSupport OBJECT-TYPE
    SYNTAX       CfprBiosVfTPMSupportVpTPMSupport
    MAX-ACCESS   read-only
    STATUS       current
    DESCRIPTION
        "Cisco Firepower bios:VfTPMSupport:vpTPMSupport
        managed object property"
    ::= { cfprBiosVfTPMSupportEntry 4 }

cfprBiosVfTPMSupportSupportedByDefault OBJECT-TYPE
    SYNTAX       CfprBiosSupportedAction
    MAX-ACCESS   read-only
    STATUS       current
    DESCRIPTION
        "Cisco Firepower bios:VfTPMSupport:supportedByDefault
        managed object property"
    ::= { cfprBiosVfTPMSupportEntry 5 }

cfprBiosVfFPRMBootModeControlTable OBJECT-TYPE
    SYNTAX           SEQUENCE OF CfprBiosVfFPRMBootModeControlEntry
    MAX-ACCESS       not-accessible
    STATUS           current
    DESCRIPTION
        "Cisco Firepower bios:VfFPRMBootModeControl managed object table"
    ::= { cfprBiosObjects 70 }

cfprBiosVfFPRMBootModeControlEntry OBJECT-TYPE
    SYNTAX           CfprBiosVfFPRMBootModeControlEntry
    MAX-ACCESS       not-accessible
    STATUS           current
    DESCRIPTION
        "Entry for the cfprBiosVfFPRMBootModeControlTable table."
    INDEX { cfprBiosVfFPRMBootModeControlInstanceId }
    ::= { cfprBiosVfFPRMBootModeControlTable 1 }

CfprBiosVfFPRMBootModeControlEntry ::= SEQUENCE {
    cfprBiosVfFPRMBootModeControlInstanceId                          CfprManagedObjectId,
    cfprBiosVfFPRMBootModeControlDn                                  CfprManagedObjectDn,
    cfprBiosVfFPRMBootModeControlRn                                  SnmpAdminString,
    cfprBiosVfFPRMBootModeControlVpUEFIBootMode                      CfprBiosVfFPRMBootModeControlVpUEFIBootMode,
    cfprBiosVfFPRMBootModeControlSupportedByDefault                  CfprBiosSupportedAction
}

cfprBiosVfFPRMBootModeControlInstanceId OBJECT-TYPE
    SYNTAX       CfprManagedObjectId
    MAX-ACCESS   not-accessible
    STATUS       current
    DESCRIPTION
        "Instance identifier of the managed object."
    ::= { cfprBiosVfFPRMBootModeControlEntry 1 }

cfprBiosVfFPRMBootModeControlDn OBJECT-TYPE
    SYNTAX       CfprManagedObjectDn
    MAX-ACCESS   read-only
    STATUS       current
    DESCRIPTION
        "Cisco Firepower bios:VfFPRMBootModeControl:dn
        managed object property"
    ::= { cfprBiosVfFPRMBootModeControlEntry 2 }

cfprBiosVfFPRMBootModeControlRn OBJECT-TYPE
    SYNTAX       SnmpAdminString
    MAX-ACCESS   read-only
    STATUS       current
    DESCRIPTION
        "Cisco Firepower bios:VfFPRMBootModeControl:rn
        managed object property"
    ::= { cfprBiosVfFPRMBootModeControlEntry 3 }

cfprBiosVfFPRMBootModeControlVpUEFIBootMode OBJECT-TYPE
    SYNTAX       CfprBiosVfFPRMBootModeControlVpUEFIBootMode
    MAX-ACCESS   read-only
    STATUS       current
    DESCRIPTION
        "Cisco Firepower bios:VfFPRMBootModeControl:vpUEFIBootMode
        managed object property"
    ::= { cfprBiosVfFPRMBootModeControlEntry 4 }

cfprBiosVfFPRMBootModeControlSupportedByDefault OBJECT-TYPE
    SYNTAX       CfprBiosSupportedAction
    MAX-ACCESS   read-only
    STATUS       current
    DESCRIPTION
        "Cisco Firepower bios:VfFPRMBootModeControl:supportedByDefault
        managed object property"
    ::= { cfprBiosVfFPRMBootModeControlEntry 5 }

cfprBiosVfFPRMBootOrderRuleControlTable OBJECT-TYPE
    SYNTAX           SEQUENCE OF CfprBiosVfFPRMBootOrderRuleControlEntry
    MAX-ACCESS       not-accessible
    STATUS           current
    DESCRIPTION
        "Cisco Firepower bios:VfFPRMBootOrderRuleControl
        managed object table"
    ::= { cfprBiosObjects 71 }

cfprBiosVfFPRMBootOrderRuleControlEntry OBJECT-TYPE
    SYNTAX           CfprBiosVfFPRMBootOrderRuleControlEntry
    MAX-ACCESS       not-accessible
    STATUS           current
    DESCRIPTION
        "Entry for the cfprBiosVfFPRMBootOrderRuleControlTable table."
    INDEX { cfprBiosVfFPRMBootOrderRuleControlInstanceId }
    ::= { cfprBiosVfFPRMBootOrderRuleControlTable 1 }

CfprBiosVfFPRMBootOrderRuleControlEntry ::= SEQUENCE {
    cfprBiosVfFPRMBootOrderRuleControlInstanceId                     CfprManagedObjectId,
    cfprBiosVfFPRMBootOrderRuleControlDn                             CfprManagedObjectDn,
    cfprBiosVfFPRMBootOrderRuleControlRn                             SnmpAdminString,
    cfprBiosVfFPRMBootOrderRuleControlVpFPRMBootOrderRule            CfprBiosVfFPRMBootOrderRuleControlVpFPRMBootOrderRule,
    cfprBiosVfFPRMBootOrderRuleControlSupportedByDefault             CfprBiosSupportedAction
}

cfprBiosVfFPRMBootOrderRuleControlInstanceId OBJECT-TYPE
    SYNTAX       CfprManagedObjectId
    MAX-ACCESS   not-accessible
    STATUS       current
    DESCRIPTION
        "Instance identifier of the managed object."
    ::= { cfprBiosVfFPRMBootOrderRuleControlEntry 1 }

cfprBiosVfFPRMBootOrderRuleControlDn OBJECT-TYPE
    SYNTAX       CfprManagedObjectDn
    MAX-ACCESS   read-only
    STATUS       current
    DESCRIPTION
        "Cisco Firepower bios:VfFPRMBootOrderRuleControl:dn
        managed object property"
    ::= { cfprBiosVfFPRMBootOrderRuleControlEntry 2 }

cfprBiosVfFPRMBootOrderRuleControlRn OBJECT-TYPE
    SYNTAX       SnmpAdminString
    MAX-ACCESS   read-only
    STATUS       current
    DESCRIPTION
        "Cisco Firepower bios:VfFPRMBootOrderRuleControl:rn
        managed object property"
    ::= { cfprBiosVfFPRMBootOrderRuleControlEntry 3 }

cfprBiosVfFPRMBootOrderRuleControlVpFPRMBootOrderRule OBJECT-TYPE
    SYNTAX       CfprBiosVfFPRMBootOrderRuleControlVpFPRMBootOrderRule
    MAX-ACCESS   read-only
    STATUS       current
    DESCRIPTION
        "Cisco Firepower bios:VfFPRMBootOrderRuleControl:vpFPRMBootOrderRu
        le managed object property"
    ::= { cfprBiosVfFPRMBootOrderRuleControlEntry 4 }

cfprBiosVfFPRMBootOrderRuleControlSupportedByDefault OBJECT-TYPE
    SYNTAX       CfprBiosSupportedAction
    MAX-ACCESS   read-only
    STATUS       current
    DESCRIPTION
        "Cisco Firepower bios:VfFPRMBootOrderRuleControl:supportedByDefaul
        t managed object property"
    ::= { cfprBiosVfFPRMBootOrderRuleControlEntry 5 }

cfprBiosVfUEFIOSUseLegacyVideoTable OBJECT-TYPE
    SYNTAX           SEQUENCE OF CfprBiosVfUEFIOSUseLegacyVideoEntry
    MAX-ACCESS       not-accessible
    STATUS           current
    DESCRIPTION
        "Cisco Firepower bios:VfUEFIOSUseLegacyVideo managed object table"
    ::= { cfprBiosObjects 72 }

cfprBiosVfUEFIOSUseLegacyVideoEntry OBJECT-TYPE
    SYNTAX           CfprBiosVfUEFIOSUseLegacyVideoEntry
    MAX-ACCESS       not-accessible
    STATUS           current
    DESCRIPTION
        "Entry for the cfprBiosVfUEFIOSUseLegacyVideoTable table."
    INDEX { cfprBiosVfUEFIOSUseLegacyVideoInstanceId }
    ::= { cfprBiosVfUEFIOSUseLegacyVideoTable 1 }

CfprBiosVfUEFIOSUseLegacyVideoEntry ::= SEQUENCE {
    cfprBiosVfUEFIOSUseLegacyVideoInstanceId                         CfprManagedObjectId,
    cfprBiosVfUEFIOSUseLegacyVideoDn                                 CfprManagedObjectDn,
    cfprBiosVfUEFIOSUseLegacyVideoRn                                 SnmpAdminString,
    cfprBiosVfUEFIOSUseLegacyVideoVpUEFIOSUseLegacyVideo             CfprBiosVfUEFIOSUseLegacyVideoVpUEFIOSUseLegacyVideo,
    cfprBiosVfUEFIOSUseLegacyVideoSupportedByDefault                 CfprBiosSupportedAction
}

cfprBiosVfUEFIOSUseLegacyVideoInstanceId OBJECT-TYPE
    SYNTAX       CfprManagedObjectId
    MAX-ACCESS   not-accessible
    STATUS       current
    DESCRIPTION
        "Instance identifier of the managed object."
    ::= { cfprBiosVfUEFIOSUseLegacyVideoEntry 1 }

cfprBiosVfUEFIOSUseLegacyVideoDn OBJECT-TYPE
    SYNTAX       CfprManagedObjectDn
    MAX-ACCESS   read-only
    STATUS       current
    DESCRIPTION
        "Cisco Firepower bios:VfUEFIOSUseLegacyVideo:dn
        managed object property"
    ::= { cfprBiosVfUEFIOSUseLegacyVideoEntry 2 }

cfprBiosVfUEFIOSUseLegacyVideoRn OBJECT-TYPE
    SYNTAX       SnmpAdminString
    MAX-ACCESS   read-only
    STATUS       current
    DESCRIPTION
        "Cisco Firepower bios:VfUEFIOSUseLegacyVideo:rn
        managed object property"
    ::= { cfprBiosVfUEFIOSUseLegacyVideoEntry 3 }

cfprBiosVfUEFIOSUseLegacyVideoVpUEFIOSUseLegacyVideo OBJECT-TYPE
    SYNTAX       CfprBiosVfUEFIOSUseLegacyVideoVpUEFIOSUseLegacyVideo
    MAX-ACCESS   read-only
    STATUS       current
    DESCRIPTION
        "Cisco Firepower bios:VfUEFIOSUseLegacyVideo:vpUEFIOSUseLegacyVide
        o managed object property"
    ::= { cfprBiosVfUEFIOSUseLegacyVideoEntry 4 }

cfprBiosVfUEFIOSUseLegacyVideoSupportedByDefault OBJECT-TYPE
    SYNTAX       CfprBiosSupportedAction
    MAX-ACCESS   read-only
    STATUS       current
    DESCRIPTION
        "Cisco Firepower bios:VfUEFIOSUseLegacyVideo:supportedByDefault
        managed object property"
    ::= { cfprBiosVfUEFIOSUseLegacyVideoEntry 5 }

cfprBiosVfUSBBootConfigTable OBJECT-TYPE
    SYNTAX           SEQUENCE OF CfprBiosVfUSBBootConfigEntry
    MAX-ACCESS       not-accessible
    STATUS           current
    DESCRIPTION
        "Cisco Firepower bios:VfUSBBootConfig managed object table"
    ::= { cfprBiosObjects 73 }

cfprBiosVfUSBBootConfigEntry OBJECT-TYPE
    SYNTAX           CfprBiosVfUSBBootConfigEntry
    MAX-ACCESS       not-accessible
    STATUS           current
    DESCRIPTION
        "Entry for the cfprBiosVfUSBBootConfigTable table."
    INDEX { cfprBiosVfUSBBootConfigInstanceId }
    ::= { cfprBiosVfUSBBootConfigTable 1 }

CfprBiosVfUSBBootConfigEntry ::= SEQUENCE {
    cfprBiosVfUSBBootConfigInstanceId                                CfprManagedObjectId,
    cfprBiosVfUSBBootConfigDn                                        CfprManagedObjectDn,
    cfprBiosVfUSBBootConfigRn                                        SnmpAdminString,
    cfprBiosVfUSBBootConfigVpLegacyUSBSupport                        CfprBiosVfUSBBootConfigVpLegacyUSBSupport,
    cfprBiosVfUSBBootConfigVpMakeDeviceNonBootable                   CfprBiosVfUSBBootConfigVpMakeDeviceNonBootable,
    cfprBiosVfUSBBootConfigSupportedByDefault                        CfprBiosSupportedAction
}

cfprBiosVfUSBBootConfigInstanceId OBJECT-TYPE
    SYNTAX       CfprManagedObjectId
    MAX-ACCESS   not-accessible
    STATUS       current
    DESCRIPTION
        "Instance identifier of the managed object."
    ::= { cfprBiosVfUSBBootConfigEntry 1 }

cfprBiosVfUSBBootConfigDn OBJECT-TYPE
    SYNTAX       CfprManagedObjectDn
    MAX-ACCESS   read-only
    STATUS       current
    DESCRIPTION
        "Cisco Firepower bios:VfUSBBootConfig:dn managed object property"
    ::= { cfprBiosVfUSBBootConfigEntry 2 }

cfprBiosVfUSBBootConfigRn OBJECT-TYPE
    SYNTAX       SnmpAdminString
    MAX-ACCESS   read-only
    STATUS       current
    DESCRIPTION
        "Cisco Firepower bios:VfUSBBootConfig:rn managed object property"
    ::= { cfprBiosVfUSBBootConfigEntry 3 }

cfprBiosVfUSBBootConfigVpLegacyUSBSupport OBJECT-TYPE
    SYNTAX       CfprBiosVfUSBBootConfigVpLegacyUSBSupport
    MAX-ACCESS   read-only
    STATUS       current
    DESCRIPTION
        "Cisco Firepower bios:VfUSBBootConfig:vpLegacyUSBSupport
        managed object property"
    ::= { cfprBiosVfUSBBootConfigEntry 4 }

cfprBiosVfUSBBootConfigVpMakeDeviceNonBootable OBJECT-TYPE
    SYNTAX       CfprBiosVfUSBBootConfigVpMakeDeviceNonBootable
    MAX-ACCESS   read-only
    STATUS       current
    DESCRIPTION
        "Cisco Firepower bios:VfUSBBootConfig:vpMakeDeviceNonBootable
        managed object property"
    ::= { cfprBiosVfUSBBootConfigEntry 5 }

cfprBiosVfUSBBootConfigSupportedByDefault OBJECT-TYPE
    SYNTAX       CfprBiosSupportedAction
    MAX-ACCESS   read-only
    STATUS       current
    DESCRIPTION
        "Cisco Firepower bios:VfUSBBootConfig:supportedByDefault
        managed object property"
    ::= { cfprBiosVfUSBBootConfigEntry 6 }

cfprBiosVfUSBConfigurationTable OBJECT-TYPE
    SYNTAX           SEQUENCE OF CfprBiosVfUSBConfigurationEntry
    MAX-ACCESS       not-accessible
    STATUS           current
    DESCRIPTION
        "Cisco Firepower bios:VfUSBConfiguration managed object table"
    ::= { cfprBiosObjects 74 }

cfprBiosVfUSBConfigurationEntry OBJECT-TYPE
    SYNTAX           CfprBiosVfUSBConfigurationEntry
    MAX-ACCESS       not-accessible
    STATUS           current
    DESCRIPTION
        "Entry for the cfprBiosVfUSBConfigurationTable table."
    INDEX { cfprBiosVfUSBConfigurationInstanceId }
    ::= { cfprBiosVfUSBConfigurationTable 1 }

CfprBiosVfUSBConfigurationEntry ::= SEQUENCE {
    cfprBiosVfUSBConfigurationInstanceId                             CfprManagedObjectId,
    cfprBiosVfUSBConfigurationDn                                     CfprManagedObjectDn,
    cfprBiosVfUSBConfigurationRn                                     SnmpAdminString,
    cfprBiosVfUSBConfigurationVpLegacyUSBSupport                     CfprBiosVfUSBConfigurationVpLegacyUSBSupport,
    cfprBiosVfUSBConfigurationVpXHCIMode                             CfprBiosVfUSBConfigurationVpXHCIMode,
    cfprBiosVfUSBConfigurationSupportedByDefault                     CfprBiosSupportedAction
}

cfprBiosVfUSBConfigurationInstanceId OBJECT-TYPE
    SYNTAX       CfprManagedObjectId
    MAX-ACCESS   not-accessible
    STATUS       current
    DESCRIPTION
        "Instance identifier of the managed object."
    ::= { cfprBiosVfUSBConfigurationEntry 1 }

cfprBiosVfUSBConfigurationDn OBJECT-TYPE
    SYNTAX       CfprManagedObjectDn
    MAX-ACCESS   read-only
    STATUS       current
    DESCRIPTION
        "Cisco Firepower bios:VfUSBConfiguration:dn managed
        object property"
    ::= { cfprBiosVfUSBConfigurationEntry 2 }

cfprBiosVfUSBConfigurationRn OBJECT-TYPE
    SYNTAX       SnmpAdminString
    MAX-ACCESS   read-only
    STATUS       current
    DESCRIPTION
        "Cisco Firepower bios:VfUSBConfiguration:rn managed
        object property"
    ::= { cfprBiosVfUSBConfigurationEntry 3 }

cfprBiosVfUSBConfigurationVpLegacyUSBSupport OBJECT-TYPE
    SYNTAX       CfprBiosVfUSBConfigurationVpLegacyUSBSupport
    MAX-ACCESS   read-only
    STATUS       current
    DESCRIPTION
        "Cisco Firepower bios:VfUSBConfiguration:vpLegacyUSBSupport
        managed object property"
    ::= { cfprBiosVfUSBConfigurationEntry 4 }

cfprBiosVfUSBConfigurationVpXHCIMode OBJECT-TYPE
    SYNTAX       CfprBiosVfUSBConfigurationVpXHCIMode
    MAX-ACCESS   read-only
    STATUS       current
    DESCRIPTION
        "Cisco Firepower bios:VfUSBConfiguration:vpXHCIMode
        managed object property"
    ::= { cfprBiosVfUSBConfigurationEntry 5 }

cfprBiosVfUSBConfigurationSupportedByDefault OBJECT-TYPE
    SYNTAX       CfprBiosSupportedAction
    MAX-ACCESS   read-only
    STATUS       current
    DESCRIPTION
        "Cisco Firepower bios:VfUSBConfiguration:supportedByDefault
        managed object property"
    ::= { cfprBiosVfUSBConfigurationEntry 6 }

cfprBiosVfUSBFrontPanelAccessLockTable OBJECT-TYPE
    SYNTAX           SEQUENCE OF CfprBiosVfUSBFrontPanelAccessLockEntry
    MAX-ACCESS       not-accessible
    STATUS           current
    DESCRIPTION
        "Cisco Firepower bios:VfUSBFrontPanelAccessLock
        managed object table"
    ::= { cfprBiosObjects 75 }

cfprBiosVfUSBFrontPanelAccessLockEntry OBJECT-TYPE
    SYNTAX           CfprBiosVfUSBFrontPanelAccessLockEntry
    MAX-ACCESS       not-accessible
    STATUS           current
    DESCRIPTION
        "Entry for the cfprBiosVfUSBFrontPanelAccessLockTable table."
    INDEX { cfprBiosVfUSBFrontPanelAccessLockInstanceId }
    ::= { cfprBiosVfUSBFrontPanelAccessLockTable 1 }

CfprBiosVfUSBFrontPanelAccessLockEntry ::= SEQUENCE {
    cfprBiosVfUSBFrontPanelAccessLockInstanceId                      CfprManagedObjectId,
    cfprBiosVfUSBFrontPanelAccessLockDn                              CfprManagedObjectDn,
    cfprBiosVfUSBFrontPanelAccessLockRn                              SnmpAdminString,
    cfprBiosVfUSBFrontPanelAccessLockVpUSBFrontPanelLock             CfprBiosVfUSBFrontPanelAccessLockVpUSBFrontPanelLock,
    cfprBiosVfUSBFrontPanelAccessLockSupportedByDefault              CfprBiosSupportedAction
}

cfprBiosVfUSBFrontPanelAccessLockInstanceId OBJECT-TYPE
    SYNTAX       CfprManagedObjectId
    MAX-ACCESS   not-accessible
    STATUS       current
    DESCRIPTION
        "Instance identifier of the managed object."
    ::= { cfprBiosVfUSBFrontPanelAccessLockEntry 1 }

cfprBiosVfUSBFrontPanelAccessLockDn OBJECT-TYPE
    SYNTAX       CfprManagedObjectDn
    MAX-ACCESS   read-only
    STATUS       current
    DESCRIPTION
        "Cisco Firepower bios:VfUSBFrontPanelAccessLock:dn
        managed object property"
    ::= { cfprBiosVfUSBFrontPanelAccessLockEntry 2 }

cfprBiosVfUSBFrontPanelAccessLockRn OBJECT-TYPE
    SYNTAX       SnmpAdminString
    MAX-ACCESS   read-only
    STATUS       current
    DESCRIPTION
        "Cisco Firepower bios:VfUSBFrontPanelAccessLock:rn
        managed object property"
    ::= { cfprBiosVfUSBFrontPanelAccessLockEntry 3 }

cfprBiosVfUSBFrontPanelAccessLockVpUSBFrontPanelLock OBJECT-TYPE
    SYNTAX       CfprBiosVfUSBFrontPanelAccessLockVpUSBFrontPanelLock
    MAX-ACCESS   read-only
    STATUS       current
    DESCRIPTION
        "Cisco Firepower bios:VfUSBFrontPanelAccessLock:vpUSBFrontPanelLoc
        k managed object property"
    ::= { cfprBiosVfUSBFrontPanelAccessLockEntry 4 }

cfprBiosVfUSBFrontPanelAccessLockSupportedByDefault OBJECT-TYPE
    SYNTAX       CfprBiosSupportedAction
    MAX-ACCESS   read-only
    STATUS       current
    DESCRIPTION
        "Cisco Firepower bios:VfUSBFrontPanelAccessLock:supportedByDefault
         managed object property"
    ::= { cfprBiosVfUSBFrontPanelAccessLockEntry 5 }

cfprBiosVfUSBPortConfigurationTable OBJECT-TYPE
    SYNTAX           SEQUENCE OF CfprBiosVfUSBPortConfigurationEntry
    MAX-ACCESS       not-accessible
    STATUS           current
    DESCRIPTION
        "Cisco Firepower bios:VfUSBPortConfiguration managed object table"
    ::= { cfprBiosObjects 76 }

cfprBiosVfUSBPortConfigurationEntry OBJECT-TYPE
    SYNTAX           CfprBiosVfUSBPortConfigurationEntry
    MAX-ACCESS       not-accessible
    STATUS           current
    DESCRIPTION
        "Entry for the cfprBiosVfUSBPortConfigurationTable table."
    INDEX { cfprBiosVfUSBPortConfigurationInstanceId }
    ::= { cfprBiosVfUSBPortConfigurationTable 1 }

CfprBiosVfUSBPortConfigurationEntry ::= SEQUENCE {
    cfprBiosVfUSBPortConfigurationInstanceId                         CfprManagedObjectId,
    cfprBiosVfUSBPortConfigurationDn                                 CfprManagedObjectDn,
    cfprBiosVfUSBPortConfigurationRn                                 SnmpAdminString,
    cfprBiosVfUSBPortConfigurationVpPort6064Emulation                CfprBiosVfUSBPortConfigurationVpPort6064Emulation,
    cfprBiosVfUSBPortConfigurationVpUSBPortFront                     CfprBiosVfUSBPortConfigurationVpUSBPortFront,
    cfprBiosVfUSBPortConfigurationVpUSBPortInternal                  CfprBiosVfUSBPortConfigurationVpUSBPortInternal,
    cfprBiosVfUSBPortConfigurationVpUSBPortKVM                       CfprBiosVfUSBPortConfigurationVpUSBPortKVM,
    cfprBiosVfUSBPortConfigurationVpUSBPortRear                      CfprBiosVfUSBPortConfigurationVpUSBPortRear,
    cfprBiosVfUSBPortConfigurationVpUSBPortSDCard                    CfprBiosVfUSBPortConfigurationVpUSBPortSDCard,
    cfprBiosVfUSBPortConfigurationVpUSBPortVMedia                    CfprBiosVfUSBPortConfigurationVpUSBPortVMedia,
    cfprBiosVfUSBPortConfigurationSupportedByDefault                 CfprBiosSupportedAction
}

cfprBiosVfUSBPortConfigurationInstanceId OBJECT-TYPE
    SYNTAX       CfprManagedObjectId
    MAX-ACCESS   not-accessible
    STATUS       current
    DESCRIPTION
        "Instance identifier of the managed object."
    ::= { cfprBiosVfUSBPortConfigurationEntry 1 }

cfprBiosVfUSBPortConfigurationDn OBJECT-TYPE
    SYNTAX       CfprManagedObjectDn
    MAX-ACCESS   read-only
    STATUS       current
    DESCRIPTION
        "Cisco Firepower bios:VfUSBPortConfiguration:dn
        managed object property"
    ::= { cfprBiosVfUSBPortConfigurationEntry 2 }

cfprBiosVfUSBPortConfigurationRn OBJECT-TYPE
    SYNTAX       SnmpAdminString
    MAX-ACCESS   read-only
    STATUS       current
    DESCRIPTION
        "Cisco Firepower bios:VfUSBPortConfiguration:rn
        managed object property"
    ::= { cfprBiosVfUSBPortConfigurationEntry 3 }

cfprBiosVfUSBPortConfigurationVpPort6064Emulation OBJECT-TYPE
    SYNTAX       CfprBiosVfUSBPortConfigurationVpPort6064Emulation
    MAX-ACCESS   read-only
    STATUS       current
    DESCRIPTION
        "Cisco Firepower bios:VfUSBPortConfiguration:vpPort6064Emulation
        managed object property"
    ::= { cfprBiosVfUSBPortConfigurationEntry 4 }

cfprBiosVfUSBPortConfigurationVpUSBPortFront OBJECT-TYPE
    SYNTAX       CfprBiosVfUSBPortConfigurationVpUSBPortFront
    MAX-ACCESS   read-only
    STATUS       current
    DESCRIPTION
        "Cisco Firepower bios:VfUSBPortConfiguration:vpUSBPortFront
        managed object property"
    ::= { cfprBiosVfUSBPortConfigurationEntry 5 }

cfprBiosVfUSBPortConfigurationVpUSBPortInternal OBJECT-TYPE
    SYNTAX       CfprBiosVfUSBPortConfigurationVpUSBPortInternal
    MAX-ACCESS   read-only
    STATUS       current
    DESCRIPTION
        "Cisco Firepower bios:VfUSBPortConfiguration:vpUSBPortInternal
        managed object property"
    ::= { cfprBiosVfUSBPortConfigurationEntry 6 }

cfprBiosVfUSBPortConfigurationVpUSBPortKVM OBJECT-TYPE
    SYNTAX       CfprBiosVfUSBPortConfigurationVpUSBPortKVM
    MAX-ACCESS   read-only
    STATUS       current
    DESCRIPTION
        "Cisco Firepower bios:VfUSBPortConfiguration:vpUSBPortKVM
        managed object property"
    ::= { cfprBiosVfUSBPortConfigurationEntry 7 }

cfprBiosVfUSBPortConfigurationVpUSBPortRear OBJECT-TYPE
    SYNTAX       CfprBiosVfUSBPortConfigurationVpUSBPortRear
    MAX-ACCESS   read-only
    STATUS       current
    DESCRIPTION
        "Cisco Firepower bios:VfUSBPortConfiguration:vpUSBPortRear
        managed object property"
    ::= { cfprBiosVfUSBPortConfigurationEntry 8 }

cfprBiosVfUSBPortConfigurationVpUSBPortSDCard OBJECT-TYPE
    SYNTAX       CfprBiosVfUSBPortConfigurationVpUSBPortSDCard
    MAX-ACCESS   read-only
    STATUS       current
    DESCRIPTION
        "Cisco Firepower bios:VfUSBPortConfiguration:vpUSBPortSDCard
        managed object property"
    ::= { cfprBiosVfUSBPortConfigurationEntry 9 }

cfprBiosVfUSBPortConfigurationVpUSBPortVMedia OBJECT-TYPE
    SYNTAX       CfprBiosVfUSBPortConfigurationVpUSBPortVMedia
    MAX-ACCESS   read-only
    STATUS       current
    DESCRIPTION
        "Cisco Firepower bios:VfUSBPortConfiguration:vpUSBPortVMedia
        managed object property"
    ::= { cfprBiosVfUSBPortConfigurationEntry 10 }

cfprBiosVfUSBPortConfigurationSupportedByDefault OBJECT-TYPE
    SYNTAX       CfprBiosSupportedAction
    MAX-ACCESS   read-only
    STATUS       current
    DESCRIPTION
        "Cisco Firepower bios:VfUSBPortConfiguration:supportedByDefault
        managed object property"
    ::= { cfprBiosVfUSBPortConfigurationEntry 11 }

cfprBiosVfUSBSystemIdlePowerOptimizingSettingTable OBJECT-TYPE
    SYNTAX           SEQUENCE OF CfprBiosVfUSBSystemIdlePowerOptimizingSettingEntry
    MAX-ACCESS       not-accessible
    STATUS           current
    DESCRIPTION
        "Cisco Firepower bios:VfUSBSystemIdlePowerOptimizingSetting
        managed object table"
    ::= { cfprBiosObjects 77 }

cfprBiosVfUSBSystemIdlePowerOptimizingSettingEntry OBJECT-TYPE
    SYNTAX           CfprBiosVfUSBSystemIdlePowerOptimizingSettingEntry
    MAX-ACCESS       not-accessible
    STATUS           current
    DESCRIPTION
        "Entry for the cfprBiosVfUSBSystemIdlePowerOptimizingSettingTable table."
    INDEX { cfprBiosVfUSBSystemIdlePowerOptimizingSettingInstanceId }
    ::= { cfprBiosVfUSBSystemIdlePowerOptimizingSettingTable 1 }

CfprBiosVfUSBSystemIdlePowerOptimizingSettingEntry ::= SEQUENCE {
    cfprBiosVfUSBSystemIdlePowerOptimizingSettingInstanceId          CfprManagedObjectId,
    cfprBiosVfUSBSystemIdlePowerOptimizingSettingDn                  CfprManagedObjectDn,
    cfprBiosVfUSBSystemIdlePowerOptimizingSettingRn                  SnmpAdminString,
    cfprBiosVfUSBSystemIdlePowerOptimizingSettingVpUSBIdlePowerOptimizing CfprBiosVfUSBSysIdlePowerOptimizingSettingVpUSBIdlePowerOptimize,
    cfprBiosVfUSBSystemIdlePowerOptimizingSettingSupportedByDefault  CfprBiosSupportedAction
}

cfprBiosVfUSBSystemIdlePowerOptimizingSettingInstanceId OBJECT-TYPE
    SYNTAX       CfprManagedObjectId
    MAX-ACCESS   not-accessible
    STATUS       current
    DESCRIPTION
        "Instance identifier of the managed object."
    ::= { cfprBiosVfUSBSystemIdlePowerOptimizingSettingEntry 1 }

cfprBiosVfUSBSystemIdlePowerOptimizingSettingDn OBJECT-TYPE
    SYNTAX       CfprManagedObjectDn
    MAX-ACCESS   read-only
    STATUS       current
    DESCRIPTION
        "Cisco Firepower bios:VfUSBSystemIdlePowerOptimizingSetting:dn
        managed object property"
    ::= { cfprBiosVfUSBSystemIdlePowerOptimizingSettingEntry 2 }

cfprBiosVfUSBSystemIdlePowerOptimizingSettingRn OBJECT-TYPE
    SYNTAX       SnmpAdminString
    MAX-ACCESS   read-only
    STATUS       current
    DESCRIPTION
        "Cisco Firepower bios:VfUSBSystemIdlePowerOptimizingSetting:rn
        managed object property"
    ::= { cfprBiosVfUSBSystemIdlePowerOptimizingSettingEntry 3 }

cfprBiosVfUSBSystemIdlePowerOptimizingSettingVpUSBIdlePowerOptimizing OBJECT-TYPE
    SYNTAX       CfprBiosVfUSBSysIdlePowerOptimizingSettingVpUSBIdlePowerOptimize
    MAX-ACCESS   read-only
    STATUS       current
    DESCRIPTION
        "Cisco Firepower bios:VfUSBSystemIdlePowerOptimizingSetting:vpUSBI
        dlePowerOptimizing managed object property"
    ::= { cfprBiosVfUSBSystemIdlePowerOptimizingSettingEntry 4 }

cfprBiosVfUSBSystemIdlePowerOptimizingSettingSupportedByDefault OBJECT-TYPE
    SYNTAX       CfprBiosSupportedAction
    MAX-ACCESS   read-only
    STATUS       current
    DESCRIPTION
        "Cisco Firepower bios:VfUSBSystemIdlePowerOptimizingSetting:suppor
        tedByDefault managed object property"
    ::= { cfprBiosVfUSBSystemIdlePowerOptimizingSettingEntry 5 }

cfprBiosVfVGAPriorityTable OBJECT-TYPE
    SYNTAX           SEQUENCE OF CfprBiosVfVGAPriorityEntry
    MAX-ACCESS       not-accessible
    STATUS           current
    DESCRIPTION
        "Cisco Firepower bios:VfVGAPriority managed object table"
    ::= { cfprBiosObjects 78 }

cfprBiosVfVGAPriorityEntry OBJECT-TYPE
    SYNTAX           CfprBiosVfVGAPriorityEntry
    MAX-ACCESS       not-accessible
    STATUS           current
    DESCRIPTION
        "Entry for the cfprBiosVfVGAPriorityTable table."
    INDEX { cfprBiosVfVGAPriorityInstanceId }
    ::= { cfprBiosVfVGAPriorityTable 1 }

CfprBiosVfVGAPriorityEntry ::= SEQUENCE {
    cfprBiosVfVGAPriorityInstanceId                                  CfprManagedObjectId,
    cfprBiosVfVGAPriorityDn                                          CfprManagedObjectDn,
    cfprBiosVfVGAPriorityRn                                          SnmpAdminString,
    cfprBiosVfVGAPriorityVpVGAPriority                               CfprBiosVfVGAPriorityVpVGAPriority,
    cfprBiosVfVGAPrioritySupportedByDefault                          CfprBiosSupportedAction
}

cfprBiosVfVGAPriorityInstanceId OBJECT-TYPE
    SYNTAX       CfprManagedObjectId
    MAX-ACCESS   not-accessible
    STATUS       current
    DESCRIPTION
        "Instance identifier of the managed object."
    ::= { cfprBiosVfVGAPriorityEntry 1 }

cfprBiosVfVGAPriorityDn OBJECT-TYPE
    SYNTAX       CfprManagedObjectDn
    MAX-ACCESS   read-only
    STATUS       current
    DESCRIPTION
        "Cisco Firepower bios:VfVGAPriority:dn managed object property"
    ::= { cfprBiosVfVGAPriorityEntry 2 }

cfprBiosVfVGAPriorityRn OBJECT-TYPE
    SYNTAX       SnmpAdminString
    MAX-ACCESS   read-only
    STATUS       current
    DESCRIPTION
        "Cisco Firepower bios:VfVGAPriority:rn managed object property"
    ::= { cfprBiosVfVGAPriorityEntry 3 }

cfprBiosVfVGAPriorityVpVGAPriority OBJECT-TYPE
    SYNTAX       CfprBiosVfVGAPriorityVpVGAPriority
    MAX-ACCESS   read-only
    STATUS       current
    DESCRIPTION
        "Cisco Firepower bios:VfVGAPriority:vpVGAPriority
        managed object property"
    ::= { cfprBiosVfVGAPriorityEntry 4 }

cfprBiosVfVGAPrioritySupportedByDefault OBJECT-TYPE
    SYNTAX       CfprBiosSupportedAction
    MAX-ACCESS   read-only
    STATUS       current
    DESCRIPTION
        "Cisco Firepower bios:VfVGAPriority:supportedByDefault
        managed object property"
    ::= { cfprBiosVfVGAPriorityEntry 5 }

END

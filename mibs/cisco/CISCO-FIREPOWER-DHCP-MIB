-- *********************************************************************
-- CISCO-FIREPOWER-DHCP-MIB.my
-- 
-- MIB representation of the Cisco Firepower
-- DHCP management information model package
-- 
-- Created March 2020 by Charles Bullis
-- 
-- Copyright (c) 2005-2020 Cisco Systems, Inc. All rights reserved.
-- 
-- *********************************************************************

CISCO-FIREPOWER-DHCP-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerMIBObjects,
    CfprManagedObjectId,
    CfprManagedObjectDn
        FROM CISCO-FIREPOWER-MIB;

cfprDhcpObjects MODULE-IDENTITY
    LAST-UPDATED    "202003100000Z"
    ORGANIZATION    "Cisco Systems Inc."
    CONTACT-INFO
        "Cisco Systems
        Customer Service
        
        Postal: 170 W Tasman Drive
        San Jose, CA  95134
        USA
        
        Tel: +1 800 553-NETS
        
        E-mail: firepower-mibs@cisco.com"
    DESCRIPTION
        "MIB representation of the Cisco Firepower
        DHCP management information model package"
    ::= { ciscoFirepowerMIBObjects 15 }

cfprDhcpAcquiredTable OBJECT-TYPE
    SYNTAX           SEQUENCE OF CfprDhcpAcquiredEntry
    MAX-ACCESS       not-accessible
    STATUS           current
    DESCRIPTION
        "Cisco Firepower dhcp:Acquired managed object table"
    ::= { cfprDhcpObjects 1 }

cfprDhcpAcquiredEntry OBJECT-TYPE
    SYNTAX           CfprDhcpAcquiredEntry
    MAX-ACCESS       not-accessible
    STATUS           current
    DESCRIPTION
        "Entry for the cfprDhcpAcquiredTable table."
    INDEX { cfprDhcpAcquiredInstanceId }
    ::= { cfprDhcpAcquiredTable 1 }

CfprDhcpAcquiredEntry ::= SEQUENCE {
    cfprDhcpAcquiredInstanceId                                       CfprManagedObjectId,
    cfprDhcpAcquiredDn                                               CfprManagedObjectDn,
    cfprDhcpAcquiredRn                                               SnmpAdminString,
    cfprDhcpAcquiredAcqts                                            DateAndTime,
    cfprDhcpAcquiredCookie                                           SnmpAdminString,
    cfprDhcpAcquiredEnds                                             DateAndTime,
    cfprDhcpAcquiredIp                                               InetAddressIPv4,
    cfprDhcpAcquiredMac                                              MacAddress,
    cfprDhcpAcquiredSysId                                            SnmpAdminString
}

cfprDhcpAcquiredInstanceId OBJECT-TYPE
    SYNTAX       CfprManagedObjectId
    MAX-ACCESS   not-accessible
    STATUS       current
    DESCRIPTION
        "Instance identifier of the managed object."
    ::= { cfprDhcpAcquiredEntry 1 }

cfprDhcpAcquiredDn OBJECT-TYPE
    SYNTAX       CfprManagedObjectDn
    MAX-ACCESS   read-only
    STATUS       current
    DESCRIPTION
        "Cisco Firepower dhcp:Acquired:dn managed object property"
    ::= { cfprDhcpAcquiredEntry 2 }

cfprDhcpAcquiredRn OBJECT-TYPE
    SYNTAX       SnmpAdminString
    MAX-ACCESS   read-only
    STATUS       current
    DESCRIPTION
        "Cisco Firepower dhcp:Acquired:rn managed object property"
    ::= { cfprDhcpAcquiredEntry 3 }

cfprDhcpAcquiredAcqts OBJECT-TYPE
    SYNTAX       DateAndTime
    MAX-ACCESS   read-only
    STATUS       current
    DESCRIPTION
        "Cisco Firepower dhcp:Acquired:acqts managed object property"
    ::= { cfprDhcpAcquiredEntry 4 }

cfprDhcpAcquiredCookie OBJECT-TYPE
    SYNTAX       SnmpAdminString
    MAX-ACCESS   read-only
    STATUS       current
    DESCRIPTION
        "Cisco Firepower dhcp:Acquired:cookie managed object property"
    ::= { cfprDhcpAcquiredEntry 5 }

cfprDhcpAcquiredEnds OBJECT-TYPE
    SYNTAX       DateAndTime
    MAX-ACCESS   read-only
    STATUS       current
    DESCRIPTION
        "Cisco Firepower dhcp:Acquired:ends managed object property"
    ::= { cfprDhcpAcquiredEntry 6 }

cfprDhcpAcquiredIp OBJECT-TYPE
    SYNTAX       InetAddressIPv4
    MAX-ACCESS   read-only
    STATUS       current
    DESCRIPTION
        "Cisco Firepower dhcp:Acquired:ip managed object property"
    ::= { cfprDhcpAcquiredEntry 7 }

cfprDhcpAcquiredMac OBJECT-TYPE
    SYNTAX       MacAddress
    MAX-ACCESS   read-only
    STATUS       current
    DESCRIPTION
        "Cisco Firepower dhcp:Acquired:mac managed object property"
    ::= { cfprDhcpAcquiredEntry 8 }

cfprDhcpAcquiredSysId OBJECT-TYPE
    SYNTAX       SnmpAdminString
    MAX-ACCESS   read-only
    STATUS       current
    DESCRIPTION
        "Cisco Firepower dhcp:Acquired:sysId managed object property"
    ::= { cfprDhcpAcquiredEntry 9 }

cfprDhcpInstTable OBJECT-TYPE
    SYNTAX           SEQUENCE OF CfprDhcpInstEntry
    MAX-ACCESS       not-accessible
    STATUS           current
    DESCRIPTION
        "Cisco Firepower dhcp:Inst managed object table"
    ::= { cfprDhcpObjects 2 }

cfprDhcpInstEntry OBJECT-TYPE
    SYNTAX           CfprDhcpInstEntry
    MAX-ACCESS       not-accessible
    STATUS           current
    DESCRIPTION
        "Entry for the cfprDhcpInstTable table."
    INDEX { cfprDhcpInstInstanceId }
    ::= { cfprDhcpInstTable 1 }

CfprDhcpInstEntry ::= SEQUENCE {
    cfprDhcpInstInstanceId                                           CfprManagedObjectId,
    cfprDhcpInstDn                                                   CfprManagedObjectDn,
    cfprDhcpInstRn                                                   SnmpAdminString
}

cfprDhcpInstInstanceId OBJECT-TYPE
    SYNTAX       CfprManagedObjectId
    MAX-ACCESS   not-accessible
    STATUS       current
    DESCRIPTION
        "Instance identifier of the managed object."
    ::= { cfprDhcpInstEntry 1 }

cfprDhcpInstDn OBJECT-TYPE
    SYNTAX       CfprManagedObjectDn
    MAX-ACCESS   read-only
    STATUS       current
    DESCRIPTION
        "Cisco Firepower dhcp:Inst:dn managed object property"
    ::= { cfprDhcpInstEntry 2 }

cfprDhcpInstRn OBJECT-TYPE
    SYNTAX       SnmpAdminString
    MAX-ACCESS   read-only
    STATUS       current
    DESCRIPTION
        "Cisco Firepower dhcp:Inst:rn managed object property"
    ::= { cfprDhcpInstEntry 3 }

cfprDhcpLeaseTable OBJECT-TYPE
    SYNTAX           SEQUENCE OF CfprDhcpLeaseEntry
    MAX-ACCESS       not-accessible
    STATUS           current
    DESCRIPTION
        "Cisco Firepower dhcp:Lease managed object table"
    ::= { cfprDhcpObjects 3 }

cfprDhcpLeaseEntry OBJECT-TYPE
    SYNTAX           CfprDhcpLeaseEntry
    MAX-ACCESS       not-accessible
    STATUS           current
    DESCRIPTION
        "Entry for the cfprDhcpLeaseTable table."
    INDEX { cfprDhcpLeaseInstanceId }
    ::= { cfprDhcpLeaseTable 1 }

CfprDhcpLeaseEntry ::= SEQUENCE {
    cfprDhcpLeaseInstanceId                                          CfprManagedObjectId,
    cfprDhcpLeaseDn                                                  CfprManagedObjectDn,
    cfprDhcpLeaseRn                                                  SnmpAdminString,
    cfprDhcpLeaseCliId                                               SnmpAdminString,
    cfprDhcpLeaseCookie                                              SnmpAdminString,
    cfprDhcpLeaseEnds                                                DateAndTime,
    cfprDhcpLeaseHostname                                            SnmpAdminString,
    cfprDhcpLeaseIntf                                                SnmpAdminString,
    cfprDhcpLeaseIp                                                  InetAddressIPv4,
    cfprDhcpLeaseMac                                                 MacAddress,
    cfprDhcpLeaseStarts                                              DateAndTime
}

cfprDhcpLeaseInstanceId OBJECT-TYPE
    SYNTAX       CfprManagedObjectId
    MAX-ACCESS   not-accessible
    STATUS       current
    DESCRIPTION
        "Instance identifier of the managed object."
    ::= { cfprDhcpLeaseEntry 1 }

cfprDhcpLeaseDn OBJECT-TYPE
    SYNTAX       CfprManagedObjectDn
    MAX-ACCESS   read-only
    STATUS       current
    DESCRIPTION
        "Cisco Firepower dhcp:Lease:dn managed object property"
    ::= { cfprDhcpLeaseEntry 2 }

cfprDhcpLeaseRn OBJECT-TYPE
    SYNTAX       SnmpAdminString
    MAX-ACCESS   read-only
    STATUS       current
    DESCRIPTION
        "Cisco Firepower dhcp:Lease:rn managed object property"
    ::= { cfprDhcpLeaseEntry 3 }

cfprDhcpLeaseCliId OBJECT-TYPE
    SYNTAX       SnmpAdminString
    MAX-ACCESS   read-only
    STATUS       current
    DESCRIPTION
        "Cisco Firepower dhcp:Lease:cliId managed object property"
    ::= { cfprDhcpLeaseEntry 4 }

cfprDhcpLeaseCookie OBJECT-TYPE
    SYNTAX       SnmpAdminString
    MAX-ACCESS   read-only
    STATUS       current
    DESCRIPTION
        "Cisco Firepower dhcp:Lease:cookie managed object property"
    ::= { cfprDhcpLeaseEntry 5 }

cfprDhcpLeaseEnds OBJECT-TYPE
    SYNTAX       DateAndTime
    MAX-ACCESS   read-only
    STATUS       current
    DESCRIPTION
        "Cisco Firepower dhcp:Lease:ends managed object property"
    ::= { cfprDhcpLeaseEntry 6 }

cfprDhcpLeaseHostname OBJECT-TYPE
    SYNTAX       SnmpAdminString
    MAX-ACCESS   read-only
    STATUS       current
    DESCRIPTION
        "Cisco Firepower dhcp:Lease:hostname managed object property"
    ::= { cfprDhcpLeaseEntry 7 }

cfprDhcpLeaseIntf OBJECT-TYPE
    SYNTAX       SnmpAdminString
    MAX-ACCESS   read-only
    STATUS       current
    DESCRIPTION
        "Cisco Firepower dhcp:Lease:intf managed object property"
    ::= { cfprDhcpLeaseEntry 8 }

cfprDhcpLeaseIp OBJECT-TYPE
    SYNTAX       InetAddressIPv4
    MAX-ACCESS   read-only
    STATUS       current
    DESCRIPTION
        "Cisco Firepower dhcp:Lease:ip managed object property"
    ::= { cfprDhcpLeaseEntry 9 }

cfprDhcpLeaseMac OBJECT-TYPE
    SYNTAX       MacAddress
    MAX-ACCESS   read-only
    STATUS       current
    DESCRIPTION
        "Cisco Firepower dhcp:Lease:mac managed object property"
    ::= { cfprDhcpLeaseEntry 10 }

cfprDhcpLeaseStarts OBJECT-TYPE
    SYNTAX       DateAndTime
    MAX-ACCESS   read-only
    STATUS       current
    DESCRIPTION
        "Cisco Firepower dhcp:Lease:starts managed object property"
    ::= { cfprDhcpLeaseEntry 11 }

END

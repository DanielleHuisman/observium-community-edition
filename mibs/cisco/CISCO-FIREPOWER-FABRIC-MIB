-- *********************************************************************
-- CISCO-FIREPOWER-FABRIC-MIB.my
-- 
-- MIB representation of the Cisco Firepower
-- FABRIC management information model package
-- 
-- Created March 2020 by Charles Bullis
-- 
-- Copyright (c) 2005-2020 Cisco Systems, Inc. All rights reserved.
-- 
-- *********************************************************************

CISCO-FIREPOWER-FABRIC-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerMIBObjects,
    CfprManagedObjectId,
    CfprManagedObjectDn
        FROM CISCO-FIREPOWER-MIB
    CfprComputeDecommissionState,
    CfprComputeDiscovery,
    CfprConditionRemoteInvRslt,
    CfprEquipmentBoardAggregationRole,
    CfprEquipmentConnectionStatus,
    CfprEquipmentEthPortSpeedCap,
    CfprEquipmentFabricEpType,
    CfprEquipmentSlotStatus,
    CfprFabricADceSwSrvEpTransport,
    CfprFabricAEthEstcEpIfRole,
    CfprFabricAEthEstcEpTransport,
    CfprFabricAEthEstcEpType,
    CfprFabricAEthLanEpTransport,
    CfprFabricAFcEstcEpTransport,
    CfprFabricAFcEstcEpType,
    CfprFabricAFcSanEpTransport,
    CfprFabricAFcoeEstcEpIfRole,
    CfprFabricAFcoeEstcEpTransport,
    CfprFabricAFcoeEstcEpType,
    CfprFabricAFcoeSanEpTransport,
    CfprFabricAVlanAssocPrimaryVlanSwitchId,
    CfprFabricAVlanSharing,
    CfprFabricAVlanTransport,
    CfprFabricAVlanType,
    CfprFabricAVsanTransport,
    CfprFabricAVsanType,
    CfprFabricAccessType,
    CfprFabricAdminState,
    CfprFabricAllowedVlanType,
    CfprFabricBHVlanSwitchId,
    CfprFabricBladeLifeCycle,
    CfprFabricBreakoutPortId,
    CfprFabricBreakoutSlotId,
    CfprFabricBreakoutType,
    CfprFabricCIoEpAdminState,
    CfprFabricCIoEpIfType,
    CfprFabricCdpLinkPolicyAdminState,
    CfprFabricCloudType,
    CfprFabricComputeEpIfRole,
    CfprFabricComputeEpType,
    CfprFabricComputePhEpAdminState,
    CfprFabricComputeSlotEpFsmCurrentFsm,
    CfprFabricComputeSlotEpFsmStageName,
    CfprFabricComputeSlotEpFsmTaskItem,
    CfprFabricComputeSlotEpSlotId,
    CfprFabricConfMode,
    CfprFabricConfState,
    CfprFabricConfigState,
    CfprFabricDceSwSrvEpPortId,
    CfprFabricDceSwSrvEpSlotId,
    CfprFabricDceSwSrvPcAdminState,
    CfprFabricDceSwSrvPcEpPortId,
    CfprFabricDceSwSrvPcEpSlotId,
    CfprFabricDceSwSrvPcPortId,
    CfprFabricDceSwSrvPcTransport,
    CfprFabricDefaultZoningState,
    CfprFabricDirection,
    CfprFabricEpMgrFsmCurrentFsm,
    CfprFabricEpMgrFsmStageName,
    CfprFabricEpMgrFsmTaskFlags,
    CfprFabricEpMgrFsmTaskItem,
    CfprFabricEstcEpIfRole,
    CfprFabricEstcPcIfRole,
    CfprFabricEstcPcType,
    CfprFabricEthCdpPolicyProtocol,
    CfprFabricEthEstcEpPortId,
    CfprFabricEthEstcEpPrio,
    CfprFabricEthEstcEpSlotId,
    CfprFabricEthEstcEpTransport,
    CfprFabricEthEstcEpType,
    CfprFabricEthEstcOperPortMode,
    CfprFabricEthEstcPcEpPortId,
    CfprFabricEthEstcPcEpSlotId,
    CfprFabricEthEstcPcTransport,
    CfprFabricEthEstcPortMode,
    CfprFabricEthEstcTransport,
    CfprFabricEthEstcType,
    CfprFabricEthFlowMonLanTransport,
    CfprFabricEthFlowMonLanType,
    CfprFabricEthFlowMonSourceType,
    CfprFabricEthFlowMonSrcRefType,
    CfprFabricEthLanEpAdminState,
    CfprFabricEthLanEpInlineState,
    CfprFabricEthLanEpVlanStatus,
    CfprFabricEthLanFlowMonCollectorTransport,
    CfprFabricEthLanFlowMonExporterTransport,
    CfprFabricEthLanFlowMonSrcEpTransport,
    CfprFabricEthLanFlowMonTransport,
    CfprFabricEthLanFlowMonitorTransport,
    CfprFabricEthLanFlowMonitoringType,
    CfprFabricEthLanPcAdminState,
    CfprFabricEthLanPcInlineState,
    CfprFabricEthLanPcLacpDetach,
    CfprFabricEthLanPcTransport,
    CfprFabricEthLanPcVlanStatus,
    CfprFabricEthLanTransport,
    CfprFabricEthLinkPolicyType,
    CfprFabricEthMonDestEpAdminSpeed,
    CfprFabricEthMonDestEpIfRole,
    CfprFabricEthMonDestEpPortId,
    CfprFabricEthMonDestEpSlotId,
    CfprFabricEthMonDestEpType,
    CfprFabricEthMonFiltEpType,
    CfprFabricEthMonFiltRefType,
    CfprFabricEthMonLanTransport,
    CfprFabricEthMonLanType,
    CfprFabricEthMonSrcEpType,
    CfprFabricEthMonSrcRefType,
    CfprFabricEthMonTransport,
    CfprFabricEthMonType,
    CfprFabricEthPcProtocol,
    CfprFabricEthSourceType,
    CfprFabricEthTargetEpTransport,
    CfprFabricEthUdldPolicyProtocol,
    CfprFabricEthVlanPcTransport,
    CfprFabricExternalEpAdminState,
    CfprFabricExternalEpLocale,
    CfprFabricExternalLocale,
    CfprFabricExternalPcLocale,
    CfprFabricFcEstcEpPortId,
    CfprFabricFcEstcEpSlotId,
    CfprFabricFcEstcTransport,
    CfprFabricFcEstcType,
    CfprFabricFcMonDestEpAdminSpeed,
    CfprFabricFcMonDestEpIfRole,
    CfprFabricFcMonDestEpPortId,
    CfprFabricFcMonDestEpSlotId,
    CfprFabricFcMonDestEpType,
    CfprFabricFcMonFiltEpType,
    CfprFabricFcMonFiltRefType,
    CfprFabricFcMonSanTransport,
    CfprFabricFcMonSanType,
    CfprFabricFcMonSrcEpType,
    CfprFabricFcMonSrcRefType,
    CfprFabricFcMonTransport,
    CfprFabricFcMonType,
    CfprFabricFcSanEpPortId,
    CfprFabricFcSanEpSlotId,
    CfprFabricFcSanPcEpPortId,
    CfprFabricFcSanPcEpSlotId,
    CfprFabricFcSanPcTransport,
    CfprFabricFcSanTransport,
    CfprFabricFcSanUplinkTrunking,
    CfprFabricFcSourceType,
    CfprFabricFcVsanPcTransport,
    CfprFabricFcVsanPortEpPortId,
    CfprFabricFcVsanPortEpSlotId,
    CfprFabricFcZoneSharingMode,
    CfprFabricFcoeEstcEpPortId,
    CfprFabricFcoeEstcEpSlotId,
    CfprFabricFcoeSanEpPortId,
    CfprFabricFcoeSanEpSlotId,
    CfprFabricFcoeSanPcEpPortId,
    CfprFabricFcoeSanPcEpSlotId,
    CfprFabricFcoeSanPcTransport,
    CfprFabricFcoeVsanPcTransport,
    CfprFabricFcoeVsanPortEpPortId,
    CfprFabricFcoeVsanPortEpSlotId,
    CfprFabricFillPattern,
    CfprFabricFlowMonCollectorLocale,
    CfprFabricFlowMonDefType,
    CfprFabricFlowMonIpv4Keys,
    CfprFabricFlowMonIpv6Keys,
    CfprFabricFlowMonKeyType,
    CfprFabricFlowMonL2Keys,
    CfprFabricFlowMonNonKeys,
    CfprFabricFlowMonitoringCategoryAdminState,
    CfprFabricInternalDceSrvTransport,
    CfprFabricInternalDceSrvType,
    CfprFabricInternalEpAdminState,
    CfprFabricInternalEpLocale,
    CfprFabricInternalLocale,
    CfprFabricInternalPcLocale,
    CfprFabricLacpMode,
    CfprFabricLacpRate,
    CfprFabricLacpSuspend,
    CfprFabricLanCloudFsmCurrentFsm,
    CfprFabricLanCloudFsmStageName,
    CfprFabricLanCloudFsmTaskItem,
    CfprFabricLanCloudVlanCompression,
    CfprFabricLanEpIfRole,
    CfprFabricLanEpType,
    CfprFabricLanFlowMonCollectorType,
    CfprFabricLanFlowMonExporterType,
    CfprFabricLanFlowMonSrcEpType,
    CfprFabricLanFlowMonType,
    CfprFabricLanFlowMonitorType,
    CfprFabricLanPcIfRole,
    CfprFabricLanPcType,
    CfprFabricLanType,
    CfprFabricLifeCycle,
    CfprFabricMemberStatus,
    CfprFabricMembershipStatus,
    CfprFabricMonAdminState,
    CfprFabricMonOperState,
    CfprFabricMonOperStateReason,
    CfprFabricNFExporterVersion,
    CfprFabricNFTransport,
    CfprFabricNetGroupSwitchId,
    CfprFabricNetGroupType,
    CfprFabricNetflowCollectorFlowProtocol,
    CfprFabricNetflowConfigIssues,
    CfprFabricNetflowMonExporterProtocol,
    CfprFabricNetflowMonSessionAdminState,
    CfprFabricNetflowMonSessionProtocol,
    CfprFabricNetflowMonSrcEpProtocol,
    CfprFabricNetflowMonSrcRefProtocol,
    CfprFabricNetflowMonitorFlowMonProtocol,
    CfprFabricOperState,
    CfprFabricOwner,
    CfprFabricPIoEpIfType,
    CfprFabricPIoEpOperState,
    CfprFabricPIoEpPortId,
    CfprFabricPIoEpSlotId,
    CfprFabricPathEpIfType,
    CfprFabricPathEpLocale,
    CfprFabricPcConfigStatus,
    CfprFabricPcMode,
    CfprFabricPcModeState,
    CfprFabricPktCaptureAppSlotId,
    CfprFabricPoolMemberConfigIssues,
    CfprFabricQosPrio,
    CfprFabricQuerierType,
    CfprFabricRecoveryAction,
    CfprFabricReqIssues,
    CfprFabricSSAPortType,
    CfprFabricSSASubPortType,
    CfprFabricSanCloudFsmCurrentFsm,
    CfprFabricSanCloudFsmStageName,
    CfprFabricSanCloudFsmTaskItem,
    CfprFabricSanEpIfRole,
    CfprFabricSanEpType,
    CfprFabricSanPcIfRole,
    CfprFabricSanPcType,
    CfprFabricSanType,
    CfprFabricSlotAdminState,
    CfprFabricSnoopingType,
    CfprFabricSpannedCluster,
    CfprFabricSspEthMonAppendFlag,
    CfprFabricSspEthMonDelAllSessEnabledState,
    CfprFabricSspLanMonCloudDelAllSess,
    CfprFabricSspMonAdminState,
    CfprFabricSspMonDelPcap,
    CfprFabricSspMonOperState,
    CfprFabricSspMonOperStateReason,
    CfprFabricStatus,
    CfprFabricSubGroupAggrPortId,
    CfprFabricSubGroupConfigState,
    CfprFabricSubGroupSlotId,
    CfprFabricSwChEpIfRole,
    CfprFabricSwChEpType,
    CfprFabricSwChPhEpAdminState,
    CfprFabricSwSrvEpIfRole,
    CfprFabricSwSrvEpType,
    CfprFabricSwSrvPcIfRole,
    CfprFabricSwSrvPcType,
    CfprFabricSwSubGroupAggrPortId,
    CfprFabricSwSubGroupConfigState,
    CfprFabricSwSubGroupSlotId,
    CfprFabricSwitchingMode,
    CfprFabricTargetEpType,
    CfprFabricTargetStatus,
    CfprFabricTrafficDirection,
    CfprFabricUdldLinkPolicyAdminState,
    CfprFabricUdldLinkPolicyMode,
    CfprFabricUdldOperState,
    CfprFabricVConInstType,
    CfprFabricVConMappingScheme,
    CfprFabricVConPlacementPref,
    CfprFabricVConSelectPref,
    CfprFabricVConSharePref,
    CfprFabricVConTransportPref,
    CfprFabricVlanAssocPrimaryVlanState,
    CfprFabricVlanCompType,
    CfprFabricVlanConfigIssues,
    CfprFabricVlanOperState,
    CfprFabricVlanOverlapState,
    CfprFabricVlanSwitchId,
    CfprFabricVnetEpIfRole,
    CfprFabricVnetEpLocale,
    CfprFabricVnetEpPolicyOwner,
    CfprFabricVnetEpSyncEpFsmCurrentFsm,
    CfprFabricVnetEpSyncEpFsmStageName,
    CfprFabricVnetEpSyncEpFsmTaskItem,
    CfprFabricVsanOperState,
    CfprFabricVsanSwitchId,
    CfprFabricWarnings,
    CfprFabricZoningState,
    CfprFsmCompletion,
    CfprFsmFlags,
    CfprFsmFsmStageStatus,
    CfprLicenseState,
    CfprLsOperState,
    CfprNetworkConnectionType,
    CfprNetworkLocale,
    CfprNetworkPortOperState,
    CfprNetworkPortRole,
    CfprNetworkSide,
    CfprNetworkSwitchId,
    CfprNetworkTransport,
    CfprNetworkVnetEpIfType,
    CfprNhTpHashType,
    CfprPolicyPolicyOwner,
    CfprPoolPoolAssignmentOrder,
    CfprPortDuplex,
    CfprPortEthAdminSpeed,
    CfprPortEthSpeed,
    CfprPortSpeed,
    CfprQosPriority,
    CfprSwPktCaptureLifeCycle
        FROM CISCO-FIREPOWER-TC-MIB;

cfprFabricObjects MODULE-IDENTITY
    LAST-UPDATED    "202003100000Z"
    ORGANIZATION    "Cisco Systems Inc."
    CONTACT-INFO
        "Cisco Systems
        Customer Service
        
        Postal: 170 W Tasman Drive
        San Jose, CA  95134
        USA
        
        Tel: +1 800 553-NETS
        
        E-mail: firepower-mibs@cisco.com"
    DESCRIPTION
        "MIB representation of the Cisco Firepower
        FABRIC management information model package"
    ::= { ciscoFirepowerMIBObjects 26 }

cfprFabricBHVlanTable OBJECT-TYPE
    SYNTAX           SEQUENCE OF CfprFabricBHVlanEntry
    MAX-ACCESS       not-accessible
    STATUS           current
    DESCRIPTION
        "Cisco Firepower fabric:BHVlan managed object table"
    ::= { cfprFabricObjects 1 }

cfprFabricBHVlanEntry OBJECT-TYPE
    SYNTAX           CfprFabricBHVlanEntry
    MAX-ACCESS       not-accessible
    STATUS           current
    DESCRIPTION
        "Entry for the cfprFabricBHVlanTable table."
    INDEX { cfprFabricBHVlanInstanceId }
    ::= { cfprFabricBHVlanTable 1 }

CfprFabricBHVlanEntry ::= SEQUENCE {
    cfprFabricBHVlanInstanceId                                       CfprManagedObjectId,
    cfprFabricBHVlanDn                                               CfprManagedObjectDn,
    cfprFabricBHVlanRn                                               SnmpAdminString,
    cfprFabricBHVlanAssocPrimaryVlanState                            CfprFabricVlanAssocPrimaryVlanState,
    cfprFabricBHVlanAssocPrimaryVlanSwitchId                         CfprFabricAVlanAssocPrimaryVlanSwitchId,
    cfprFabricBHVlanEpDn                                             SnmpAdminString,
    cfprFabricBHVlanId                                               Gauge32,
    cfprFabricBHVlanIfRole                                           CfprFabricVnetEpIfRole,
    cfprFabricBHVlanIfType                                           CfprNetworkVnetEpIfType,
    cfprFabricBHVlanLocale                                           CfprFabricVnetEpLocale,
    cfprFabricBHVlanName                                             SnmpAdminString,
    cfprFabricBHVlanOperState                                        CfprFabricVlanOperState,
    cfprFabricBHVlanOverlapStateForA                                 CfprFabricVlanOverlapState,
    cfprFabricBHVlanOverlapStateForB                                 CfprFabricVlanOverlapState,
    cfprFabricBHVlanPeerDn                                           SnmpAdminString,
    cfprFabricBHVlanPolicyOwner                                      CfprFabricVnetEpPolicyOwner,
    cfprFabricBHVlanPubNwDn                                          SnmpAdminString,
    cfprFabricBHVlanPubNwId                                          Gauge32,
    cfprFabricBHVlanPubNwName                                        SnmpAdminString,
    cfprFabricBHVlanSharing                                          CfprFabricAVlanSharing,
    cfprFabricBHVlanSwitchId                                         CfprFabricBHVlanSwitchId,
    cfprFabricBHVlanTransport                                        CfprFabricAVlanTransport,
    cfprFabricBHVlanType                                             CfprFabricAVlanType
}

cfprFabricBHVlanInstanceId OBJECT-TYPE
    SYNTAX       CfprManagedObjectId
    MAX-ACCESS   not-accessible
    STATUS       current
    DESCRIPTION
        "Instance identifier of the managed object."
    ::= { cfprFabricBHVlanEntry 1 }

cfprFabricBHVlanDn OBJECT-TYPE
    SYNTAX       CfprManagedObjectDn
    MAX-ACCESS   read-only
    STATUS       current
    DESCRIPTION
        "Cisco Firepower fabric:BHVlan:dn managed object property"
    ::= { cfprFabricBHVlanEntry 2 }

cfprFabricBHVlanRn OBJECT-TYPE
    SYNTAX       SnmpAdminString
    MAX-ACCESS   read-only
    STATUS       current
    DESCRIPTION
        "Cisco Firepower fabric:BHVlan:rn managed object property"
    ::= { cfprFabricBHVlanEntry 3 }

cfprFabricBHVlanAssocPrimaryVlanState OBJECT-TYPE
    SYNTAX       CfprFabricVlanAssocPrimaryVlanState
    MAX-ACCESS   read-only
    STATUS       current
    DESCRIPTION
        "Cisco Firepower fabric:BHVlan:assocPrimaryVlanState
        managed object property"
    ::= { cfprFabricBHVlanEntry 4 }

cfprFabricBHVlanAssocPrimaryVlanSwitchId OBJECT-TYPE
    SYNTAX       CfprFabricAVlanAssocPrimaryVlanSwitchId
    MAX-ACCESS   read-only
    STATUS       current
    DESCRIPTION
        "Cisco Firepower fabric:BHVlan:assocPrimaryVlanSwitchId
        managed object property"
    ::= { cfprFabricBHVlanEntry 5 }

cfprFabricBHVlanEpDn OBJECT-TYPE
    SYNTAX       SnmpAdminString
    MAX-ACCESS   read-only
    STATUS       current
    DESCRIPTION
        "Cisco Firepower fabric:BHVlan:epDn managed object property"
    ::= { cfprFabricBHVlanEntry 6 }

cfprFabricBHVlanId OBJECT-TYPE
    SYNTAX       Gauge32
    MAX-ACCESS   read-only
    STATUS       current
    DESCRIPTION
        "Cisco Firepower fabric:BHVlan:id managed object property"
    ::= { cfprFabricBHVlanEntry 7 }

cfprFabricBHVlanIfRole OBJECT-TYPE
    SYNTAX       CfprFabricVnetEpIfRole
    MAX-ACCESS   read-only
    STATUS       current
    DESCRIPTION
        "Cisco Firepower fabric:BHVlan:ifRole managed object property"
    ::= { cfprFabricBHVlanEntry 8 }

cfprFabricBHVlanIfType OBJECT-TYPE
    SYNTAX       CfprNetworkVnetEpIfType
    MAX-ACCESS   read-only
    STATUS       current
    DESCRIPTION
        "Cisco Firepower fabric:BHVlan:ifType managed object property"
    ::= { cfprFabricBHVlanEntry 9 }

cfprFabricBHVlanLocale OBJECT-TYPE
    SYNTAX       CfprFabricVnetEpLocale
    MAX-ACCESS   read-only
    STATUS       current
    DESCRIPTION
        "Cisco Firepower fabric:BHVlan:locale managed object property"
    ::= { cfprFabricBHVlanEntry 10 }

cfprFabricBHVlanName OBJECT-TYPE
    SYNTAX       SnmpAdminString
    MAX-ACCESS   read-only
    STATUS       current
    DESCRIPTION
        "Cisco Firepower fabric:BHVlan:name managed object property"
    ::= { cfprFabricBHVlanEntry 11 }

cfprFabricBHVlanOperState OBJECT-TYPE
    SYNTAX       CfprFabricVlanOperState
    MAX-ACCESS   read-only
    STATUS       current
    DESCRIPTION
        "Cisco Firepower fabric:BHVlan:operState managed object property"
    ::= { cfprFabricBHVlanEntry 12 }

cfprFabricBHVlanOverlapStateForA OBJECT-TYPE
    SYNTAX       CfprFabricVlanOverlapState
    MAX-ACCESS   read-only
    STATUS       current
    DESCRIPTION
        "Cisco Firepower fabric:BHVlan:overlapStateForA
        managed object property"
    ::= { cfprFabricBHVlanEntry 13 }

cfprFabricBHVlanOverlapStateForB OBJECT-TYPE
    SYNTAX       CfprFabricVlanOverlapState
    MAX-ACCESS   read-only
    STATUS       current
    DESCRIPTION
        "Cisco Firepower fabric:BHVlan:overlapStateForB
        managed object property"
    ::= { cfprFabricBHVlanEntry 14 }

cfprFabricBHVlanPeerDn OBJECT-TYPE
    SYNTAX       SnmpAdminString
    MAX-ACCESS   read-only
    STATUS       current
    DESCRIPTION
        "Cisco Firepower fabric:BHVlan:peerDn managed object property"
    ::= { cfprFabricBHVlanEntry 15 }

cfprFabricBHVlanPolicyOwner OBJECT-TYPE
    SYNTAX       CfprFabricVnetEpPolicyOwner
    MAX-ACCESS   read-only
    STATUS       current
    DESCRIPTION
        "Cisco Firepower fabric:BHVlan:policyOwner managed
        object property"
    ::= { cfprFabricBHVlanEntry 16 }

cfprFabricBHVlanPubNwDn OBJECT-TYPE
    SYNTAX       SnmpAdminString
    MAX-ACCESS   read-only
    STATUS       current
    DESCRIPTION
        "Cisco Firepower fabric:BHVlan:pubNwDn managed object property"
    ::= { cfprFabricBHVlanEntry 17 }

cfprFabricBHVlanPubNwId OBJECT-TYPE
    SYNTAX       Gauge32
    MAX-ACCESS   read-only
    STATUS       current
    DESCRIPTION
        "Cisco Firepower fabric:BHVlan:pubNwId managed object property"
    ::= { cfprFabricBHVlanEntry 18 }

cfprFabricBHVlanPubNwName OBJECT-TYPE
    SYNTAX       SnmpAdminString
    MAX-ACCESS   read-only
    STATUS       current
    DESCRIPTION
        "Cisco Firepower fabric:BHVlan:pubNwName managed object property"
    ::= { cfprFabricBHVlanEntry 19 }

cfprFabricBHVlanSharing OBJECT-TYPE
    SYNTAX       CfprFabricAVlanSharing
    MAX-ACCESS   read-only
    STATUS       current
    DESCRIPTION
        "Cisco Firepower fabric:BHVlan:sharing managed object property"
    ::= { cfprFabricBHVlanEntry 20 }

cfprFabricBHVlanSwitchId OBJECT-TYPE
    SYNTAX       CfprFabricBHVlanSwitchId
    MAX-ACCESS   read-only
    STATUS       current
    DESCRIPTION
        "Cisco Firepower fabric:BHVlan:switchId managed object property"
    ::= { cfprFabricBHVlanEntry 21 }

cfprFabricBHVlanTransport OBJECT-TYPE
    SYNTAX       CfprFabricAVlanTransport
    MAX-ACCESS   read-only
    STATUS       current
    DESCRIPTION
        "Cisco Firepower fabric:BHVlan:transport managed object property"
    ::= { cfprFabricBHVlanEntry 22 }

cfprFabricBHVlanType OBJECT-TYPE
    SYNTAX       CfprFabricAVlanType
    MAX-ACCESS   read-only
    STATUS       current
    DESCRIPTION
        "Cisco Firepower fabric:BHVlan:type managed object property"
    ::= { cfprFabricBHVlanEntry 23 }

cfprFabricBreakoutTable OBJECT-TYPE
    SYNTAX           SEQUENCE OF CfprFabricBreakoutEntry
    MAX-ACCESS       not-accessible
    STATUS           current
    DESCRIPTION
        "Cisco Firepower fabric:Breakout managed object table"
    ::= { cfprFabricObjects 2 }

cfprFabricBreakoutEntry OBJECT-TYPE
    SYNTAX           CfprFabricBreakoutEntry
    MAX-ACCESS       not-accessible
    STATUS           current
    DESCRIPTION
        "Entry for the cfprFabricBreakoutTable table."
    INDEX { cfprFabricBreakoutInstanceId }
    ::= { cfprFabricBreakoutTable 1 }

CfprFabricBreakoutEntry ::= SEQUENCE {
    cfprFabricBreakoutInstanceId                                     CfprManagedObjectId,
    cfprFabricBreakoutDn                                             CfprManagedObjectDn,
    cfprFabricBreakoutRn                                             SnmpAdminString,
    cfprFabricBreakoutBreakoutType                                   CfprFabricBreakoutType,
    cfprFabricBreakoutPortId                                         CfprFabricBreakoutPortId,
    cfprFabricBreakoutSlotId                                         CfprFabricBreakoutSlotId
}

cfprFabricBreakoutInstanceId OBJECT-TYPE
    SYNTAX       CfprManagedObjectId
    MAX-ACCESS   not-accessible
    STATUS       current
    DESCRIPTION
        "Instance identifier of the managed object."
    ::= { cfprFabricBreakoutEntry 1 }

cfprFabricBreakoutDn OBJECT-TYPE
    SYNTAX       CfprManagedObjectDn
    MAX-ACCESS   read-only
    STATUS       current
    DESCRIPTION
        "Cisco Firepower fabric:Breakout:dn managed object property"
    ::= { cfprFabricBreakoutEntry 2 }

cfprFabricBreakoutRn OBJECT-TYPE
    SYNTAX       SnmpAdminString
    MAX-ACCESS   read-only
    STATUS       current
    DESCRIPTION
        "Cisco Firepower fabric:Breakout:rn managed object property"
    ::= { cfprFabricBreakoutEntry 3 }

cfprFabricBreakoutBreakoutType OBJECT-TYPE
    SYNTAX       CfprFabricBreakoutType
    MAX-ACCESS   read-only
    STATUS       current
    DESCRIPTION
        "Cisco Firepower fabric:Breakout:breakoutType managed
        object property"
    ::= { cfprFabricBreakoutEntry 4 }

cfprFabricBreakoutPortId OBJECT-TYPE
    SYNTAX       CfprFabricBreakoutPortId
    MAX-ACCESS   read-only
    STATUS       current
    DESCRIPTION
        "Cisco Firepower fabric:Breakout:portId managed object property"
    ::= { cfprFabricBreakoutEntry 5 }

cfprFabricBreakoutSlotId OBJECT-TYPE
    SYNTAX       CfprFabricBreakoutSlotId
    MAX-ACCESS   read-only
    STATUS       current
    DESCRIPTION
        "Cisco Firepower fabric:Breakout:slotId managed object property"
    ::= { cfprFabricBreakoutEntry 6 }

cfprFabricCablingTable OBJECT-TYPE
    SYNTAX           SEQUENCE OF CfprFabricCablingEntry
    MAX-ACCESS       not-accessible
    STATUS           current
    DESCRIPTION
        "Cisco Firepower fabric:Cabling managed object table"
    ::= { cfprFabricObjects 3 }

cfprFabricCablingEntry OBJECT-TYPE
    SYNTAX           CfprFabricCablingEntry
    MAX-ACCESS       not-accessible
    STATUS           current
    DESCRIPTION
        "Entry for the cfprFabricCablingTable table."
    INDEX { cfprFabricCablingInstanceId }
    ::= { cfprFabricCablingTable 1 }

CfprFabricCablingEntry ::= SEQUENCE {
    cfprFabricCablingInstanceId                                      CfprManagedObjectId,
    cfprFabricCablingDn                                              CfprManagedObjectDn,
    cfprFabricCablingRn                                              SnmpAdminString
}

cfprFabricCablingInstanceId OBJECT-TYPE
    SYNTAX       CfprManagedObjectId
    MAX-ACCESS   not-accessible
    STATUS       current
    DESCRIPTION
        "Instance identifier of the managed object."
    ::= { cfprFabricCablingEntry 1 }

cfprFabricCablingDn OBJECT-TYPE
    SYNTAX       CfprManagedObjectDn
    MAX-ACCESS   read-only
    STATUS       current
    DESCRIPTION
        "Cisco Firepower fabric:Cabling:dn managed object property"
    ::= { cfprFabricCablingEntry 2 }

cfprFabricCablingRn OBJECT-TYPE
    SYNTAX       SnmpAdminString
    MAX-ACCESS   read-only
    STATUS       current
    DESCRIPTION
        "Cisco Firepower fabric:Cabling:rn managed object property"
    ::= { cfprFabricCablingEntry 3 }

cfprFabricCablingSwTable OBJECT-TYPE
    SYNTAX           SEQUENCE OF CfprFabricCablingSwEntry
    MAX-ACCESS       not-accessible
    STATUS           current
    DESCRIPTION
        "Cisco Firepower fabric:CablingSw managed object table"
    ::= { cfprFabricObjects 4 }

cfprFabricCablingSwEntry OBJECT-TYPE
    SYNTAX           CfprFabricCablingSwEntry
    MAX-ACCESS       not-accessible
    STATUS           current
    DESCRIPTION
        "Entry for the cfprFabricCablingSwTable table."
    INDEX { cfprFabricCablingSwInstanceId }
    ::= { cfprFabricCablingSwTable 1 }

CfprFabricCablingSwEntry ::= SEQUENCE {
    cfprFabricCablingSwInstanceId                                    CfprManagedObjectId,
    cfprFabricCablingSwDn                                            CfprManagedObjectDn,
    cfprFabricCablingSwRn                                            SnmpAdminString,
    cfprFabricCablingSwId                                            CfprNetworkSwitchId,
    cfprFabricCablingSwLocale                                        CfprFabricExternalLocale,
    cfprFabricCablingSwName                                          SnmpAdminString,
    cfprFabricCablingSwTransport                                     CfprNetworkTransport,
    cfprFabricCablingSwType                                          CfprNetworkConnectionType
}

cfprFabricCablingSwInstanceId OBJECT-TYPE
    SYNTAX       CfprManagedObjectId
    MAX-ACCESS   not-accessible
    STATUS       current
    DESCRIPTION
        "Instance identifier of the managed object."
    ::= { cfprFabricCablingSwEntry 1 }

cfprFabricCablingSwDn OBJECT-TYPE
    SYNTAX       CfprManagedObjectDn
    MAX-ACCESS   read-only
    STATUS       current
    DESCRIPTION
        "Cisco Firepower fabric:CablingSw:dn managed object property"
    ::= { cfprFabricCablingSwEntry 2 }

cfprFabricCablingSwRn OBJECT-TYPE
    SYNTAX       SnmpAdminString
    MAX-ACCESS   read-only
    STATUS       current
    DESCRIPTION
        "Cisco Firepower fabric:CablingSw:rn managed object property"
    ::= { cfprFabricCablingSwEntry 3 }

cfprFabricCablingSwId OBJECT-TYPE
    SYNTAX       CfprNetworkSwitchId
    MAX-ACCESS   read-only
    STATUS       current
    DESCRIPTION
        "Cisco Firepower fabric:CablingSw:id managed object property"
    ::= { cfprFabricCablingSwEntry 4 }

cfprFabricCablingSwLocale OBJECT-TYPE
    SYNTAX       CfprFabricExternalLocale
    MAX-ACCESS   read-only
    STATUS       current
    DESCRIPTION
        "Cisco Firepower fabric:CablingSw:locale managed object property"
    ::= { cfprFabricCablingSwEntry 5 }

cfprFabricCablingSwName OBJECT-TYPE
    SYNTAX       SnmpAdminString
    MAX-ACCESS   read-only
    STATUS       current
    DESCRIPTION
        "Cisco Firepower fabric:CablingSw:name managed object property"
    ::= { cfprFabricCablingSwEntry 6 }

cfprFabricCablingSwTransport OBJECT-TYPE
    SYNTAX       CfprNetworkTransport
    MAX-ACCESS   read-only
    STATUS       current
    DESCRIPTION
        "Cisco Firepower fabric:CablingSw:transport managed
        object property"
    ::= { cfprFabricCablingSwEntry 7 }

cfprFabricCablingSwType OBJECT-TYPE
    SYNTAX       CfprNetworkConnectionType
    MAX-ACCESS   read-only
    STATUS       current
    DESCRIPTION
        "Cisco Firepower fabric:CablingSw:type managed object property"
    ::= { cfprFabricCablingSwEntry 8 }

cfprFabricCdpLinkPolicyTable OBJECT-TYPE
    SYNTAX           SEQUENCE OF CfprFabricCdpLinkPolicyEntry
    MAX-ACCESS       not-accessible
    STATUS           current
    DESCRIPTION
        "Cisco Firepower fabric:CdpLinkPolicy managed object table"
    ::= { cfprFabricObjects 5 }

cfprFabricCdpLinkPolicyEntry OBJECT-TYPE
    SYNTAX           CfprFabricCdpLinkPolicyEntry
    MAX-ACCESS       not-accessible
    STATUS           current
    DESCRIPTION
        "Entry for the cfprFabricCdpLinkPolicyTable table."
    INDEX { cfprFabricCdpLinkPolicyInstanceId }
    ::= { cfprFabricCdpLinkPolicyTable 1 }

CfprFabricCdpLinkPolicyEntry ::= SEQUENCE {
    cfprFabricCdpLinkPolicyInstanceId                                CfprManagedObjectId,
    cfprFabricCdpLinkPolicyDn                                        CfprManagedObjectDn,
    cfprFabricCdpLinkPolicyRn                                        SnmpAdminString,
    cfprFabricCdpLinkPolicyAdminState                                CfprFabricCdpLinkPolicyAdminState,
    cfprFabricCdpLinkPolicyDescr                                     SnmpAdminString,
    cfprFabricCdpLinkPolicyIntId                                     SnmpAdminString,
    cfprFabricCdpLinkPolicyName                                      SnmpAdminString,
    cfprFabricCdpLinkPolicyPolicyLevel                               Gauge32,
    cfprFabricCdpLinkPolicyPolicyOwner                               CfprPolicyPolicyOwner,
    cfprFabricCdpLinkPolicyProtocol                                  CfprFabricEthCdpPolicyProtocol,
    cfprFabricCdpLinkPolicyType                                      CfprFabricEthLinkPolicyType
}

cfprFabricCdpLinkPolicyInstanceId OBJECT-TYPE
    SYNTAX       CfprManagedObjectId
    MAX-ACCESS   not-accessible
    STATUS       current
    DESCRIPTION
        "Instance identifier of the managed object."
    ::= { cfprFabricCdpLinkPolicyEntry 1 }

cfprFabricCdpLinkPolicyDn OBJECT-TYPE
    SYNTAX       CfprManagedObjectDn
    MAX-ACCESS   read-only
    STATUS       current
    DESCRIPTION
        "Cisco Firepower fabric:CdpLinkPolicy:dn managed object property"
    ::= { cfprFabricCdpLinkPolicyEntry 2 }

cfprFabricCdpLinkPolicyRn OBJECT-TYPE
    SYNTAX       SnmpAdminString
    MAX-ACCESS   read-only
    STATUS       current
    DESCRIPTION
        "Cisco Firepower fabric:CdpLinkPolicy:rn managed object property"
    ::= { cfprFabricCdpLinkPolicyEntry 3 }

cfprFabricCdpLinkPolicyAdminState OBJECT-TYPE
    SYNTAX       CfprFabricCdpLinkPolicyAdminState
    MAX-ACCESS   read-only
    STATUS       current
    DESCRIPTION
        "Cisco Firepower fabric:CdpLinkPolicy:adminState
        managed object property"
    ::= { cfprFabricCdpLinkPolicyEntry 4 }

cfprFabricCdpLinkPolicyDescr OBJECT-TYPE
    SYNTAX       SnmpAdminString
    MAX-ACCESS   read-only
    STATUS       current
    DESCRIPTION
        "Cisco Firepower fabric:CdpLinkPolicy:descr managed
        object property"
    ::= { cfprFabricCdpLinkPolicyEntry 5 }

cfprFabricCdpLinkPolicyIntId OBJECT-TYPE
    SYNTAX       SnmpAdminString
    MAX-ACCESS   read-only
    STATUS       current
    DESCRIPTION
        "Cisco Firepower fabric:CdpLinkPolicy:intId managed
        object property"
    ::= { cfprFabricCdpLinkPolicyEntry 6 }

cfprFabricCdpLinkPolicyName OBJECT-TYPE
    SYNTAX       SnmpAdminString
    MAX-ACCESS   read-only
    STATUS       current
    DESCRIPTION
        "Cisco Firepower fabric:CdpLinkPolicy:name managed
        object property"
    ::= { cfprFabricCdpLinkPolicyEntry 7 }

cfprFabricCdpLinkPolicyPolicyLevel OBJECT-TYPE
    SYNTAX       Gauge32
    MAX-ACCESS   read-only
    STATUS       current
    DESCRIPTION
        "Cisco Firepower fabric:CdpLinkPolicy:policyLevel
        managed object property"
    ::= { cfprFabricCdpLinkPolicyEntry 8 }

cfprFabricCdpLinkPolicyPolicyOwner OBJECT-TYPE
    SYNTAX       CfprPolicyPolicyOwner
    MAX-ACCESS   read-only
    STATUS       current
    DESCRIPTION
        "Cisco Firepower fabric:CdpLinkPolicy:policyOwner
        managed object property"
    ::= { cfprFabricCdpLinkPolicyEntry 9 }

cfprFabricCdpLinkPolicyProtocol OBJECT-TYPE
    SYNTAX       CfprFabricEthCdpPolicyProtocol
    MAX-ACCESS   read-only
    STATUS       current
    DESCRIPTION
        "Cisco Firepower fabric:CdpLinkPolicy:protocol
        managed object property"
    ::= { cfprFabricCdpLinkPolicyEntry 10 }

cfprFabricCdpLinkPolicyType OBJECT-TYPE
    SYNTAX       CfprFabricEthLinkPolicyType
    MAX-ACCESS   read-only
    STATUS       current
    DESCRIPTION
        "Cisco Firepower fabric:CdpLinkPolicy:type managed
        object property"
    ::= { cfprFabricCdpLinkPolicyEntry 11 }

cfprFabricChangedObjectRefTable OBJECT-TYPE
    SYNTAX           SEQUENCE OF CfprFabricChangedObjectRefEntry
    MAX-ACCESS       not-accessible
    STATUS           current
    DESCRIPTION
        "Cisco Firepower fabric:ChangedObjectRef managed object table"
    ::= { cfprFabricObjects 6 }

cfprFabricChangedObjectRefEntry OBJECT-TYPE
    SYNTAX           CfprFabricChangedObjectRefEntry
    MAX-ACCESS       not-accessible
    STATUS           current
    DESCRIPTION
        "Entry for the cfprFabricChangedObjectRefTable table."
    INDEX { cfprFabricChangedObjectRefInstanceId }
    ::= { cfprFabricChangedObjectRefTable 1 }

CfprFabricChangedObjectRefEntry ::= SEQUENCE {
    cfprFabricChangedObjectRefInstanceId                             CfprManagedObjectId,
    cfprFabricChangedObjectRefDn                                     CfprManagedObjectDn,
    cfprFabricChangedObjectRefRn                                     SnmpAdminString,
    cfprFabricChangedObjectRefCentraleVnetEpDn                       SnmpAdminString,
    cfprFabricChangedObjectRefId                                     Gauge32,
    cfprFabricChangedObjectRefOldCentraleVnetEpDn                    SnmpAdminString,
    cfprFabricChangedObjectRefRefObjStatus                           CfprFabricStatus,
    cfprFabricChangedObjectRefFprmVnetEpDn                           SnmpAdminString
}

cfprFabricChangedObjectRefInstanceId OBJECT-TYPE
    SYNTAX       CfprManagedObjectId
    MAX-ACCESS   not-accessible
    STATUS       current
    DESCRIPTION
        "Instance identifier of the managed object."
    ::= { cfprFabricChangedObjectRefEntry 1 }

cfprFabricChangedObjectRefDn OBJECT-TYPE
    SYNTAX       CfprManagedObjectDn
    MAX-ACCESS   read-only
    STATUS       current
    DESCRIPTION
        "Cisco Firepower fabric:ChangedObjectRef:dn managed
        object property"
    ::= { cfprFabricChangedObjectRefEntry 2 }

cfprFabricChangedObjectRefRn OBJECT-TYPE
    SYNTAX       SnmpAdminString
    MAX-ACCESS   read-only
    STATUS       current
    DESCRIPTION
        "Cisco Firepower fabric:ChangedObjectRef:rn managed
        object property"
    ::= { cfprFabricChangedObjectRefEntry 3 }

cfprFabricChangedObjectRefCentraleVnetEpDn OBJECT-TYPE
    SYNTAX       SnmpAdminString
    MAX-ACCESS   read-only
    STATUS       current
    DESCRIPTION
        "Cisco Firepower fabric:ChangedObjectRef:centraleVnetEpDn
        managed object property"
    ::= { cfprFabricChangedObjectRefEntry 4 }

cfprFabricChangedObjectRefId OBJECT-TYPE
    SYNTAX       Gauge32
    MAX-ACCESS   read-only
    STATUS       current
    DESCRIPTION
        "Cisco Firepower fabric:ChangedObjectRef:id managed
        object property"
    ::= { cfprFabricChangedObjectRefEntry 5 }

cfprFabricChangedObjectRefOldCentraleVnetEpDn OBJECT-TYPE
    SYNTAX       SnmpAdminString
    MAX-ACCESS   read-only
    STATUS       current
    DESCRIPTION
        "Cisco Firepower fabric:ChangedObjectRef:oldCentraleVnetEpDn
        managed object property"
    ::= { cfprFabricChangedObjectRefEntry 6 }

cfprFabricChangedObjectRefRefObjStatus OBJECT-TYPE
    SYNTAX       CfprFabricStatus
    MAX-ACCESS   read-only
    STATUS       current
    DESCRIPTION
        "Cisco Firepower fabric:ChangedObjectRef:refObjStatus
        managed object property"
    ::= { cfprFabricChangedObjectRefEntry 7 }

cfprFabricChangedObjectRefFprmVnetEpDn OBJECT-TYPE
    SYNTAX       SnmpAdminString
    MAX-ACCESS   read-only
    STATUS       current
    DESCRIPTION
        "Cisco Firepower fabric:ChangedObjectRef:fprmVnetEpDn
        managed object property"
    ::= { cfprFabricChangedObjectRefEntry 8 }

cfprFabricChassisEpTable OBJECT-TYPE
    SYNTAX           SEQUENCE OF CfprFabricChassisEpEntry
    MAX-ACCESS       not-accessible
    STATUS           current
    DESCRIPTION
        "Cisco Firepower fabric:ChassisEp managed object table"
    ::= { cfprFabricObjects 7 }

cfprFabricChassisEpEntry OBJECT-TYPE
    SYNTAX           CfprFabricChassisEpEntry
    MAX-ACCESS       not-accessible
    STATUS           current
    DESCRIPTION
        "Entry for the cfprFabricChassisEpTable table."
    INDEX { cfprFabricChassisEpInstanceId }
    ::= { cfprFabricChassisEpTable 1 }

CfprFabricChassisEpEntry ::= SEQUENCE {
    cfprFabricChassisEpInstanceId                                    CfprManagedObjectId,
    cfprFabricChassisEpDn                                            CfprManagedObjectDn,
    cfprFabricChassisEpRn                                            SnmpAdminString,
    cfprFabricChassisEpAdminState                                    CfprFabricInternalEpAdminState,
    cfprFabricChassisEpAggrPortId                                    Gauge32,
    cfprFabricChassisEpChassisDn                                     SnmpAdminString,
    cfprFabricChassisEpChassisId                                     Gauge32,
    cfprFabricChassisEpEpDn                                          SnmpAdminString,
    cfprFabricChassisEpFltAggr                                       Unsigned64,
    cfprFabricChassisEpIfRole                                        CfprFabricComputeEpIfRole,
    cfprFabricChassisEpIfType                                        CfprFabricPIoEpIfType,
    cfprFabricChassisEpLicGP                                         Unsigned64,
    cfprFabricChassisEpLicState                                      CfprLicenseState,
    cfprFabricChassisEpLocale                                        CfprFabricInternalEpLocale,
    cfprFabricChassisEpModel                                         SnmpAdminString,
    cfprFabricChassisEpName                                          SnmpAdminString,
    cfprFabricChassisEpOperState                                     CfprFabricPIoEpOperState,
    cfprFabricChassisEpOperStateReason                               SnmpAdminString,
    cfprFabricChassisEpPeerAggrPortId                                Gauge32,
    cfprFabricChassisEpPeerChassisId                                 Gauge32,
    cfprFabricChassisEpPeerDn                                        SnmpAdminString,
    cfprFabricChassisEpPeerPortId                                    Gauge32,
    cfprFabricChassisEpPeerSlotId                                    Gauge32,
    cfprFabricChassisEpPortId                                        CfprFabricPIoEpPortId,
    cfprFabricChassisEpRevision                                      SnmpAdminString,
    cfprFabricChassisEpSerial                                        SnmpAdminString,
    cfprFabricChassisEpSlotId                                        CfprFabricPIoEpSlotId,
    cfprFabricChassisEpSwitchId                                      CfprNetworkSwitchId,
    cfprFabricChassisEpTransport                                     CfprNetworkTransport,
    cfprFabricChassisEpType                                          CfprFabricComputeEpType,
    cfprFabricChassisEpVendor                                        SnmpAdminString
}

cfprFabricChassisEpInstanceId OBJECT-TYPE
    SYNTAX       CfprManagedObjectId
    MAX-ACCESS   not-accessible
    STATUS       current
    DESCRIPTION
        "Instance identifier of the managed object."
    ::= { cfprFabricChassisEpEntry 1 }

cfprFabricChassisEpDn OBJECT-TYPE
    SYNTAX       CfprManagedObjectDn
    MAX-ACCESS   read-only
    STATUS       current
    DESCRIPTION
        "Cisco Firepower fabric:ChassisEp:dn managed object property"
    ::= { cfprFabricChassisEpEntry 2 }

cfprFabricChassisEpRn OBJECT-TYPE
    SYNTAX       SnmpAdminString
    MAX-ACCESS   read-only
    STATUS       current
    DESCRIPTION
        "Cisco Firepower fabric:ChassisEp:rn managed object property"
    ::= { cfprFabricChassisEpEntry 3 }

cfprFabricChassisEpAdminState OBJECT-TYPE
    SYNTAX       CfprFabricInternalEpAdminState
    MAX-ACCESS   read-only
    STATUS       current
    DESCRIPTION
        "Cisco Firepower fabric:ChassisEp:adminState managed
        object property"
    ::= { cfprFabricChassisEpEntry 4 }

cfprFabricChassisEpAggrPortId OBJECT-TYPE
    SYNTAX       Gauge32
    MAX-ACCESS   read-only
    STATUS       current
    DESCRIPTION
        "Cisco Firepower fabric:ChassisEp:aggrPortId managed
        object property"
    ::= { cfprFabricChassisEpEntry 5 }

cfprFabricChassisEpChassisDn OBJECT-TYPE
    SYNTAX       SnmpAdminString
    MAX-ACCESS   read-only
    STATUS       current
    DESCRIPTION
        "Cisco Firepower fabric:ChassisEp:chassisDn managed
        object property"
    ::= { cfprFabricChassisEpEntry 6 }

cfprFabricChassisEpChassisId OBJECT-TYPE
    SYNTAX       Gauge32
    MAX-ACCESS   read-only
    STATUS       current
    DESCRIPTION
        "Cisco Firepower fabric:ChassisEp:chassisId managed
        object property"
    ::= { cfprFabricChassisEpEntry 7 }

cfprFabricChassisEpEpDn OBJECT-TYPE
    SYNTAX       SnmpAdminString
    MAX-ACCESS   read-only
    STATUS       current
    DESCRIPTION
        "Cisco Firepower fabric:ChassisEp:epDn managed object property"
    ::= { cfprFabricChassisEpEntry 8 }

cfprFabricChassisEpFltAggr OBJECT-TYPE
    SYNTAX       Unsigned64
    MAX-ACCESS   read-only
    STATUS       current
    DESCRIPTION
        "Cisco Firepower fabric:ChassisEp:fltAggr managed object property"
    ::= { cfprFabricChassisEpEntry 9 }

cfprFabricChassisEpIfRole OBJECT-TYPE
    SYNTAX       CfprFabricComputeEpIfRole
    MAX-ACCESS   read-only
    STATUS       current
    DESCRIPTION
        "Cisco Firepower fabric:ChassisEp:ifRole managed object property"
    ::= { cfprFabricChassisEpEntry 10 }

cfprFabricChassisEpIfType OBJECT-TYPE
    SYNTAX       CfprFabricPIoEpIfType
    MAX-ACCESS   read-only
    STATUS       current
    DESCRIPTION
        "Cisco Firepower fabric:ChassisEp:ifType managed object property"
    ::= { cfprFabricChassisEpEntry 11 }

cfprFabricChassisEpLicGP OBJECT-TYPE
    SYNTAX       Unsigned64
    MAX-ACCESS   read-only
    STATUS       current
    DESCRIPTION
        "Cisco Firepower fabric:ChassisEp:licGP managed object property"
    ::= { cfprFabricChassisEpEntry 12 }

cfprFabricChassisEpLicState OBJECT-TYPE
    SYNTAX       CfprLicenseState
    MAX-ACCESS   read-only
    STATUS       current
    DESCRIPTION
        "Cisco Firepower fabric:ChassisEp:licState managed
        object property"
    ::= { cfprFabricChassisEpEntry 13 }

cfprFabricChassisEpLocale OBJECT-TYPE
    SYNTAX       CfprFabricInternalEpLocale
    MAX-ACCESS   read-only
    STATUS       current
    DESCRIPTION
        "Cisco Firepower fabric:ChassisEp:locale managed object property"
    ::= { cfprFabricChassisEpEntry 14 }

cfprFabricChassisEpModel OBJECT-TYPE
    SYNTAX       SnmpAdminString
    MAX-ACCESS   read-only
    STATUS       current
    DESCRIPTION
        "Cisco Firepower fabric:ChassisEp:model managed object property"
    ::= { cfprFabricChassisEpEntry 15 }

cfprFabricChassisEpName OBJECT-TYPE
    SYNTAX       SnmpAdminString
    MAX-ACCESS   read-only
    STATUS       current
    DESCRIPTION
        "Cisco Firepower fabric:ChassisEp:name managed object property"
    ::= { cfprFabricChassisEpEntry 16 }

cfprFabricChassisEpOperState OBJECT-TYPE
    SYNTAX       CfprFabricPIoEpOperState
    MAX-ACCESS   read-only
    STATUS       current
    DESCRIPTION
        "Cisco Firepower fabric:ChassisEp:operState managed
        object property"
    ::= { cfprFabricChassisEpEntry 17 }

cfprFabricChassisEpOperStateReason OBJECT-TYPE
    SYNTAX       SnmpAdminString
    MAX-ACCESS   read-only
    STATUS       current
    DESCRIPTION
        "Cisco Firepower fabric:ChassisEp:operStateReason
        managed object property"
    ::= { cfprFabricChassisEpEntry 18 }

cfprFabricChassisEpPeerAggrPortId OBJECT-TYPE
    SYNTAX       Gauge32
    MAX-ACCESS   read-only
    STATUS       current
    DESCRIPTION
        "Cisco Firepower fabric:ChassisEp:peerAggrPortId
        managed object property"
    ::= { cfprFabricChassisEpEntry 19 }

cfprFabricChassisEpPeerChassisId OBJECT-TYPE
    SYNTAX       Gauge32
    MAX-ACCESS   read-only
    STATUS       current
    DESCRIPTION
        "Cisco Firepower fabric:ChassisEp:peerChassisId
        managed object property"
    ::= { cfprFabricChassisEpEntry 20 }

cfprFabricChassisEpPeerDn OBJECT-TYPE
    SYNTAX       SnmpAdminString
    MAX-ACCESS   read-only
    STATUS       current
    DESCRIPTION
        "Cisco Firepower fabric:ChassisEp:peerDn managed object property"
    ::= { cfprFabricChassisEpEntry 21 }

cfprFabricChassisEpPeerPortId OBJECT-TYPE
    SYNTAX       Gauge32
    MAX-ACCESS   read-only
    STATUS       current
    DESCRIPTION
        "Cisco Firepower fabric:ChassisEp:peerPortId managed
        object property"
    ::= { cfprFabricChassisEpEntry 22 }

cfprFabricChassisEpPeerSlotId OBJECT-TYPE
    SYNTAX       Gauge32
    MAX-ACCESS   read-only
    STATUS       current
    DESCRIPTION
        "Cisco Firepower fabric:ChassisEp:peerSlotId managed
        object property"
    ::= { cfprFabricChassisEpEntry 23 }

cfprFabricChassisEpPortId OBJECT-TYPE
    SYNTAX       CfprFabricPIoEpPortId
    MAX-ACCESS   read-only
    STATUS       current
    DESCRIPTION
        "Cisco Firepower fabric:ChassisEp:portId managed object property"
    ::= { cfprFabricChassisEpEntry 24 }

cfprFabricChassisEpRevision OBJECT-TYPE
    SYNTAX       SnmpAdminString
    MAX-ACCESS   read-only
    STATUS       current
    DESCRIPTION
        "Cisco Firepower fabric:ChassisEp:revision managed
        object property"
    ::= { cfprFabricChassisEpEntry 25 }

cfprFabricChassisEpSerial OBJECT-TYPE
    SYNTAX       SnmpAdminString
    MAX-ACCESS   read-only
    STATUS       current
    DESCRIPTION
        "Cisco Firepower fabric:ChassisEp:serial managed object property"
    ::= { cfprFabricChassisEpEntry 26 }

cfprFabricChassisEpSlotId OBJECT-TYPE
    SYNTAX       CfprFabricPIoEpSlotId
    MAX-ACCESS   read-only
    STATUS       current
    DESCRIPTION
        "Cisco Firepower fabric:ChassisEp:slotId managed object property"
    ::= { cfprFabricChassisEpEntry 27 }

cfprFabricChassisEpSwitchId OBJECT-TYPE
    SYNTAX       CfprNetworkSwitchId
    MAX-ACCESS   read-only
    STATUS       current
    DESCRIPTION
        "Cisco Firepower fabric:ChassisEp:switchId managed
        object property"
    ::= { cfprFabricChassisEpEntry 28 }

cfprFabricChassisEpTransport OBJECT-TYPE
    SYNTAX       CfprNetworkTransport
    MAX-ACCESS   read-only
    STATUS       current
    DESCRIPTION
        "Cisco Firepower fabric:ChassisEp:transport managed
        object property"
    ::= { cfprFabricChassisEpEntry 29 }

cfprFabricChassisEpType OBJECT-TYPE
    SYNTAX       CfprFabricComputeEpType
    MAX-ACCESS   read-only
    STATUS       current
    DESCRIPTION
        "Cisco Firepower fabric:ChassisEp:type managed object property"
    ::= { cfprFabricChassisEpEntry 30 }

cfprFabricChassisEpVendor OBJECT-TYPE
    SYNTAX       SnmpAdminString
    MAX-ACCESS   read-only
    STATUS       current
    DESCRIPTION
        "Cisco Firepower fabric:ChassisEp:vendor managed object property"
    ::= { cfprFabricChassisEpEntry 31 }

cfprFabricComputePhEpTable OBJECT-TYPE
    SYNTAX           SEQUENCE OF CfprFabricComputePhEpEntry
    MAX-ACCESS       not-accessible
    STATUS           current
    DESCRIPTION
        "Cisco Firepower fabric:ComputePhEp managed object table"
    ::= { cfprFabricObjects 8 }

cfprFabricComputePhEpEntry OBJECT-TYPE
    SYNTAX           CfprFabricComputePhEpEntry
    MAX-ACCESS       not-accessible
    STATUS           current
    DESCRIPTION
        "Entry for the cfprFabricComputePhEpTable table."
    INDEX { cfprFabricComputePhEpInstanceId }
    ::= { cfprFabricComputePhEpTable 1 }

CfprFabricComputePhEpEntry ::= SEQUENCE {
    cfprFabricComputePhEpInstanceId                                  CfprManagedObjectId,
    cfprFabricComputePhEpDn                                          CfprManagedObjectDn,
    cfprFabricComputePhEpRn                                          SnmpAdminString,
    cfprFabricComputePhEpAdminState                                  CfprFabricComputePhEpAdminState,
    cfprFabricComputePhEpAggrPortId                                  Gauge32,
    cfprFabricComputePhEpBoardAggregationRole                        CfprEquipmentBoardAggregationRole,
    cfprFabricComputePhEpChassisId                                   Gauge32,
    cfprFabricComputePhEpCheckpointTrigTs                            Unsigned64,
    cfprFabricComputePhEpDeepCheckpointTrigTs                        Unsigned64,
    cfprFabricComputePhEpDiscTrigTs                                  Unsigned64,
    cfprFabricComputePhEpEpDn                                        SnmpAdminString,
    cfprFabricComputePhEpEqType                                      CfprEquipmentFabricEpType,
    cfprFabricComputePhEpFltAggr                                     Unsigned64,
    cfprFabricComputePhEpIfRole                                      CfprFabricComputeEpIfRole,
    cfprFabricComputePhEpIfType                                      CfprFabricPIoEpIfType,
    cfprFabricComputePhEpLc                                          CfprFabricBladeLifeCycle,
    cfprFabricComputePhEpLicGP                                       Unsigned64,
    cfprFabricComputePhEpLicState                                    CfprLicenseState,
    cfprFabricComputePhEpLocale                                      CfprFabricInternalEpLocale,
    cfprFabricComputePhEpModel                                       SnmpAdminString,
    cfprFabricComputePhEpName                                        SnmpAdminString,
    cfprFabricComputePhEpOperState                                   CfprFabricPIoEpOperState,
    cfprFabricComputePhEpOperStateReason                             SnmpAdminString,
    cfprFabricComputePhEpPeerAggrPortId                              Gauge32,
    cfprFabricComputePhEpPeerChassisId                               Gauge32,
    cfprFabricComputePhEpPeerDn                                      SnmpAdminString,
    cfprFabricComputePhEpPeerPortId                                  Gauge32,
    cfprFabricComputePhEpPeerSlotId                                  Gauge32,
    cfprFabricComputePhEpPortId                                      CfprFabricPIoEpPortId,
    cfprFabricComputePhEpProfileDn                                   SnmpAdminString,
    cfprFabricComputePhEpRevision                                    SnmpAdminString,
    cfprFabricComputePhEpSerial                                      SnmpAdminString,
    cfprFabricComputePhEpSlotId                                      CfprFabricPIoEpSlotId,
    cfprFabricComputePhEpSwitchId                                    CfprNetworkSwitchId,
    cfprFabricComputePhEpTransport                                   CfprNetworkTransport,
    cfprFabricComputePhEpType                                        CfprFabricComputeEpType,
    cfprFabricComputePhEpVendor                                      SnmpAdminString
}

cfprFabricComputePhEpInstanceId OBJECT-TYPE
    SYNTAX       CfprManagedObjectId
    MAX-ACCESS   not-accessible
    STATUS       current
    DESCRIPTION
        "Instance identifier of the managed object."
    ::= { cfprFabricComputePhEpEntry 1 }

cfprFabricComputePhEpDn OBJECT-TYPE
    SYNTAX       CfprManagedObjectDn
    MAX-ACCESS   read-only
    STATUS       current
    DESCRIPTION
        "Cisco Firepower fabric:ComputePhEp:dn managed object property"
    ::= { cfprFabricComputePhEpEntry 2 }

cfprFabricComputePhEpRn OBJECT-TYPE
    SYNTAX       SnmpAdminString
    MAX-ACCESS   read-only
    STATUS       current
    DESCRIPTION
        "Cisco Firepower fabric:ComputePhEp:rn managed object property"
    ::= { cfprFabricComputePhEpEntry 3 }

cfprFabricComputePhEpAdminState OBJECT-TYPE
    SYNTAX       CfprFabricComputePhEpAdminState
    MAX-ACCESS   read-only
    STATUS       current
    DESCRIPTION
        "Cisco Firepower fabric:ComputePhEp:adminState
        managed object property"
    ::= { cfprFabricComputePhEpEntry 4 }

cfprFabricComputePhEpAggrPortId OBJECT-TYPE
    SYNTAX       Gauge32
    MAX-ACCESS   read-only
    STATUS       current
    DESCRIPTION
        "Cisco Firepower fabric:ComputePhEp:aggrPortId
        managed object property"
    ::= { cfprFabricComputePhEpEntry 5 }

cfprFabricComputePhEpBoardAggregationRole OBJECT-TYPE
    SYNTAX       CfprEquipmentBoardAggregationRole
    MAX-ACCESS   read-only
    STATUS       current
    DESCRIPTION
        "Cisco Firepower fabric:ComputePhEp:boardAggregationRole
        managed object property"
    ::= { cfprFabricComputePhEpEntry 6 }

cfprFabricComputePhEpChassisId OBJECT-TYPE
    SYNTAX       Gauge32
    MAX-ACCESS   read-only
    STATUS       current
    DESCRIPTION
        "Cisco Firepower fabric:ComputePhEp:chassisId managed
        object property"
    ::= { cfprFabricComputePhEpEntry 7 }

cfprFabricComputePhEpCheckpointTrigTs OBJECT-TYPE
    SYNTAX       Unsigned64
    MAX-ACCESS   read-only
    STATUS       current
    DESCRIPTION
        "Cisco Firepower fabric:ComputePhEp:checkpointTrigTs
        managed object property"
    ::= { cfprFabricComputePhEpEntry 8 }

cfprFabricComputePhEpDeepCheckpointTrigTs OBJECT-TYPE
    SYNTAX       Unsigned64
    MAX-ACCESS   read-only
    STATUS       current
    DESCRIPTION
        "Cisco Firepower fabric:ComputePhEp:deepCheckpointTrigTs
        managed object property"
    ::= { cfprFabricComputePhEpEntry 9 }

cfprFabricComputePhEpDiscTrigTs OBJECT-TYPE
    SYNTAX       Unsigned64
    MAX-ACCESS   read-only
    STATUS       current
    DESCRIPTION
        "Cisco Firepower fabric:ComputePhEp:discTrigTs
        managed object property"
    ::= { cfprFabricComputePhEpEntry 10 }

cfprFabricComputePhEpEpDn OBJECT-TYPE
    SYNTAX       SnmpAdminString
    MAX-ACCESS   read-only
    STATUS       current
    DESCRIPTION
        "Cisco Firepower fabric:ComputePhEp:epDn managed object property"
    ::= { cfprFabricComputePhEpEntry 11 }

cfprFabricComputePhEpEqType OBJECT-TYPE
    SYNTAX       CfprEquipmentFabricEpType
    MAX-ACCESS   read-only
    STATUS       current
    DESCRIPTION
        "Cisco Firepower fabric:ComputePhEp:eqType managed
        object property"
    ::= { cfprFabricComputePhEpEntry 12 }

cfprFabricComputePhEpFltAggr OBJECT-TYPE
    SYNTAX       Unsigned64
    MAX-ACCESS   read-only
    STATUS       current
    DESCRIPTION
        "Cisco Firepower fabric:ComputePhEp:fltAggr managed
        object property"
    ::= { cfprFabricComputePhEpEntry 13 }

cfprFabricComputePhEpIfRole OBJECT-TYPE
    SYNTAX       CfprFabricComputeEpIfRole
    MAX-ACCESS   read-only
    STATUS       current
    DESCRIPTION
        "Cisco Firepower fabric:ComputePhEp:ifRole managed
        object property"
    ::= { cfprFabricComputePhEpEntry 14 }

cfprFabricComputePhEpIfType OBJECT-TYPE
    SYNTAX       CfprFabricPIoEpIfType
    MAX-ACCESS   read-only
    STATUS       current
    DESCRIPTION
        "Cisco Firepower fabric:ComputePhEp:ifType managed
        object property"
    ::= { cfprFabricComputePhEpEntry 15 }

cfprFabricComputePhEpLc OBJECT-TYPE
    SYNTAX       CfprFabricBladeLifeCycle
    MAX-ACCESS   read-only
    STATUS       current
    DESCRIPTION
        "Cisco Firepower fabric:ComputePhEp:lc managed object property"
    ::= { cfprFabricComputePhEpEntry 16 }

cfprFabricComputePhEpLicGP OBJECT-TYPE
    SYNTAX       Unsigned64
    MAX-ACCESS   read-only
    STATUS       current
    DESCRIPTION
        "Cisco Firepower fabric:ComputePhEp:licGP managed object property"
    ::= { cfprFabricComputePhEpEntry 17 }

cfprFabricComputePhEpLicState OBJECT-TYPE
    SYNTAX       CfprLicenseState
    MAX-ACCESS   read-only
    STATUS       current
    DESCRIPTION
        "Cisco Firepower fabric:ComputePhEp:licState managed
        object property"
    ::= { cfprFabricComputePhEpEntry 18 }

cfprFabricComputePhEpLocale OBJECT-TYPE
    SYNTAX       CfprFabricInternalEpLocale
    MAX-ACCESS   read-only
    STATUS       current
    DESCRIPTION
        "Cisco Firepower fabric:ComputePhEp:locale managed
        object property"
    ::= { cfprFabricComputePhEpEntry 19 }

cfprFabricComputePhEpModel OBJECT-TYPE
    SYNTAX       SnmpAdminString
    MAX-ACCESS   read-only
    STATUS       current
    DESCRIPTION
        "Cisco Firepower fabric:ComputePhEp:model managed object property"
    ::= { cfprFabricComputePhEpEntry 20 }

cfprFabricComputePhEpName OBJECT-TYPE
    SYNTAX       SnmpAdminString
    MAX-ACCESS   read-only
    STATUS       current
    DESCRIPTION
        "Cisco Firepower fabric:ComputePhEp:name managed object property"
    ::= { cfprFabricComputePhEpEntry 21 }

cfprFabricComputePhEpOperState OBJECT-TYPE
    SYNTAX       CfprFabricPIoEpOperState
    MAX-ACCESS   read-only
    STATUS       current
    DESCRIPTION
        "Cisco Firepower fabric:ComputePhEp:operState managed
        object property"
    ::= { cfprFabricComputePhEpEntry 22 }

cfprFabricComputePhEpOperStateReason OBJECT-TYPE
    SYNTAX       SnmpAdminString
    MAX-ACCESS   read-only
    STATUS       current
    DESCRIPTION
        "Cisco Firepower fabric:ComputePhEp:operStateReason
        managed object property"
    ::= { cfprFabricComputePhEpEntry 23 }

cfprFabricComputePhEpPeerAggrPortId OBJECT-TYPE
    SYNTAX       Gauge32
    MAX-ACCESS   read-only
    STATUS       current
    DESCRIPTION
        "Cisco Firepower fabric:ComputePhEp:peerAggrPortId
        managed object property"
    ::= { cfprFabricComputePhEpEntry 24 }

cfprFabricComputePhEpPeerChassisId OBJECT-TYPE
    SYNTAX       Gauge32
    MAX-ACCESS   read-only
    STATUS       current
    DESCRIPTION
        "Cisco Firepower fabric:ComputePhEp:peerChassisId
        managed object property"
    ::= { cfprFabricComputePhEpEntry 25 }

cfprFabricComputePhEpPeerDn OBJECT-TYPE
    SYNTAX       SnmpAdminString
    MAX-ACCESS   read-only
    STATUS       current
    DESCRIPTION
        "Cisco Firepower fabric:ComputePhEp:peerDn managed
        object property"
    ::= { cfprFabricComputePhEpEntry 26 }

cfprFabricComputePhEpPeerPortId OBJECT-TYPE
    SYNTAX       Gauge32
    MAX-ACCESS   read-only
    STATUS       current
    DESCRIPTION
        "Cisco Firepower fabric:ComputePhEp:peerPortId
        managed object property"
    ::= { cfprFabricComputePhEpEntry 27 }

cfprFabricComputePhEpPeerSlotId OBJECT-TYPE
    SYNTAX       Gauge32
    MAX-ACCESS   read-only
    STATUS       current
    DESCRIPTION
        "Cisco Firepower fabric:ComputePhEp:peerSlotId
        managed object property"
    ::= { cfprFabricComputePhEpEntry 28 }

cfprFabricComputePhEpPortId OBJECT-TYPE
    SYNTAX       CfprFabricPIoEpPortId
    MAX-ACCESS   read-only
    STATUS       current
    DESCRIPTION
        "Cisco Firepower fabric:ComputePhEp:portId managed
        object property"
    ::= { cfprFabricComputePhEpEntry 29 }

cfprFabricComputePhEpProfileDn OBJECT-TYPE
    SYNTAX       SnmpAdminString
    MAX-ACCESS   read-only
    STATUS       current
    DESCRIPTION
        "Cisco Firepower fabric:ComputePhEp:profileDn managed
        object property"
    ::= { cfprFabricComputePhEpEntry 30 }

cfprFabricComputePhEpRevision OBJECT-TYPE
    SYNTAX       SnmpAdminString
    MAX-ACCESS   read-only
    STATUS       current
    DESCRIPTION
        "Cisco Firepower fabric:ComputePhEp:revision managed
        object property"
    ::= { cfprFabricComputePhEpEntry 31 }

cfprFabricComputePhEpSerial OBJECT-TYPE
    SYNTAX       SnmpAdminString
    MAX-ACCESS   read-only
    STATUS       current
    DESCRIPTION
        "Cisco Firepower fabric:ComputePhEp:serial managed
        object property"
    ::= { cfprFabricComputePhEpEntry 32 }

cfprFabricComputePhEpSlotId OBJECT-TYPE
    SYNTAX       CfprFabricPIoEpSlotId
    MAX-ACCESS   read-only
    STATUS       current
    DESCRIPTION
        "Cisco Firepower fabric:ComputePhEp:slotId managed
        object property"
    ::= { cfprFabricComputePhEpEntry 33 }

cfprFabricComputePhEpSwitchId OBJECT-TYPE
    SYNTAX       CfprNetworkSwitchId
    MAX-ACCESS   read-only
    STATUS       current
    DESCRIPTION
        "Cisco Firepower fabric:ComputePhEp:switchId managed
        object property"
    ::= { cfprFabricComputePhEpEntry 34 }

cfprFabricComputePhEpTransport OBJECT-TYPE
    SYNTAX       CfprNetworkTransport
    MAX-ACCESS   read-only
    STATUS       current
    DESCRIPTION
        "Cisco Firepower fabric:ComputePhEp:transport managed
        object property"
    ::= { cfprFabricComputePhEpEntry 35 }

cfprFabricComputePhEpType OBJECT-TYPE
    SYNTAX       CfprFabricComputeEpType
    MAX-ACCESS   read-only
    STATUS       current
    DESCRIPTION
        "Cisco Firepower fabric:ComputePhEp:type managed object property"
    ::= { cfprFabricComputePhEpEntry 36 }

cfprFabricComputePhEpVendor OBJECT-TYPE
    SYNTAX       SnmpAdminString
    MAX-ACCESS   read-only
    STATUS       current
    DESCRIPTION
        "Cisco Firepower fabric:ComputePhEp:vendor managed
        object property"
    ::= { cfprFabricComputePhEpEntry 37 }

cfprFabricComputeSlotEpTable OBJECT-TYPE
    SYNTAX           SEQUENCE OF CfprFabricComputeSlotEpEntry
    MAX-ACCESS       not-accessible
    STATUS           current
    DESCRIPTION
        "Cisco Firepower fabric:ComputeSlotEp managed object table"
    ::= { cfprFabricObjects 9 }

cfprFabricComputeSlotEpEntry OBJECT-TYPE
    SYNTAX           CfprFabricComputeSlotEpEntry
    MAX-ACCESS       not-accessible
    STATUS           current
    DESCRIPTION
        "Entry for the cfprFabricComputeSlotEpTable table."
    INDEX { cfprFabricComputeSlotEpInstanceId }
    ::= { cfprFabricComputeSlotEpTable 1 }

CfprFabricComputeSlotEpEntry ::= SEQUENCE {
    cfprFabricComputeSlotEpInstanceId                                CfprManagedObjectId,
    cfprFabricComputeSlotEpDn                                        CfprManagedObjectDn,
    cfprFabricComputeSlotEpRn                                        SnmpAdminString,
    cfprFabricComputeSlotEpAdminState                                CfprFabricSlotAdminState,
    cfprFabricComputeSlotEpAggrPortId                                Gauge32,
    cfprFabricComputeSlotEpBoardAggregationRole                      CfprEquipmentBoardAggregationRole,
    cfprFabricComputeSlotEpChassisId                                 Gauge32,
    cfprFabricComputeSlotEpConnPath                                  CfprEquipmentConnectionStatus,
    cfprFabricComputeSlotEpConnStatus                                CfprEquipmentConnectionStatus,
    cfprFabricComputeSlotEpDiscovery                                 CfprComputeDiscovery,
    cfprFabricComputeSlotEpEpDn                                      SnmpAdminString,
    cfprFabricComputeSlotEpFactoryResetFlag                          TruthValue,
    cfprFabricComputeSlotEpFltAggr                                   Unsigned64,
    cfprFabricComputeSlotEpFruIdentTrigTs                            Unsigned64,
    cfprFabricComputeSlotEpFsmDescr                                  SnmpAdminString,
    cfprFabricComputeSlotEpFsmPrev                                   SnmpAdminString,
    cfprFabricComputeSlotEpFsmProgr                                  Gauge32,
    cfprFabricComputeSlotEpFsmRmtInvErrCode                          Gauge32,
    cfprFabricComputeSlotEpFsmRmtInvErrDescr                         SnmpAdminString,
    cfprFabricComputeSlotEpFsmRmtInvRslt                             CfprConditionRemoteInvRslt,
    cfprFabricComputeSlotEpFsmStageDescr                             SnmpAdminString,
    cfprFabricComputeSlotEpFsmStamp                                  DateAndTime,
    cfprFabricComputeSlotEpFsmStatus                                 SnmpAdminString,
    cfprFabricComputeSlotEpFsmTry                                    Gauge32,
    cfprFabricComputeSlotEpIfRole                                    CfprFabricComputeEpIfRole,
    cfprFabricComputeSlotEpIfType                                    CfprFabricPIoEpIfType,
    cfprFabricComputeSlotEpLcTs                                      DateAndTime,
    cfprFabricComputeSlotEpLicGP                                     Unsigned64,
    cfprFabricComputeSlotEpLicState                                  CfprLicenseState,
    cfprFabricComputeSlotEpLocale                                    CfprFabricInternalEpLocale,
    cfprFabricComputeSlotEpManagingInst                              CfprNetworkSwitchId,
    cfprFabricComputeSlotEpModel                                     SnmpAdminString,
    cfprFabricComputeSlotEpName                                      SnmpAdminString,
    cfprFabricComputeSlotEpOperState                                 CfprFabricPIoEpOperState,
    cfprFabricComputeSlotEpOperStateReason                           SnmpAdminString,
    cfprFabricComputeSlotEpPeerAggrPortId                            Gauge32,
    cfprFabricComputeSlotEpPeerChassisId                             Gauge32,
    cfprFabricComputeSlotEpPeerDn                                    SnmpAdminString,
    cfprFabricComputeSlotEpPeerPortId                                Gauge32,
    cfprFabricComputeSlotEpPeerSlotEpDn                              SnmpAdminString,
    cfprFabricComputeSlotEpPeerSlotId                                Gauge32,
    cfprFabricComputeSlotEpPortId                                    CfprFabricPIoEpPortId,
    cfprFabricComputeSlotEpPresence                                  CfprEquipmentSlotStatus,
    cfprFabricComputeSlotEpPresencePath                              CfprEquipmentConnectionStatus,
    cfprFabricComputeSlotEpRevision                                  SnmpAdminString,
    cfprFabricComputeSlotEpSerial                                    SnmpAdminString,
    cfprFabricComputeSlotEpSlotId                                    CfprFabricComputeSlotEpSlotId,
    cfprFabricComputeSlotEpSwitchId                                  CfprNetworkSwitchId,
    cfprFabricComputeSlotEpTransport                                 CfprNetworkTransport,
    cfprFabricComputeSlotEpType                                      CfprFabricComputeEpType,
    cfprFabricComputeSlotEpVendor                                    SnmpAdminString,
    cfprFabricComputeSlotEpBladeState                                CfprLsOperState,
    cfprFabricComputeSlotEpDecommissionSecure                        CfprComputeDecommissionState,
    cfprFabricComputeSlotEpFailReason                                SnmpAdminString
}

cfprFabricComputeSlotEpInstanceId OBJECT-TYPE
    SYNTAX       CfprManagedObjectId
    MAX-ACCESS   not-accessible
    STATUS       current
    DESCRIPTION
        "Instance identifier of the managed object."
    ::= { cfprFabricComputeSlotEpEntry 1 }

cfprFabricComputeSlotEpDn OBJECT-TYPE
    SYNTAX       CfprManagedObjectDn
    MAX-ACCESS   read-only
    STATUS       current
    DESCRIPTION
        "Cisco Firepower fabric:ComputeSlotEp:dn managed object property"
    ::= { cfprFabricComputeSlotEpEntry 2 }

cfprFabricComputeSlotEpRn OBJECT-TYPE
    SYNTAX       SnmpAdminString
    MAX-ACCESS   read-only
    STATUS       current
    DESCRIPTION
        "Cisco Firepower fabric:ComputeSlotEp:rn managed object property"
    ::= { cfprFabricComputeSlotEpEntry 3 }

cfprFabricComputeSlotEpAdminState OBJECT-TYPE
    SYNTAX       CfprFabricSlotAdminState
    MAX-ACCESS   read-only
    STATUS       current
    DESCRIPTION
        "Cisco Firepower fabric:ComputeSlotEp:adminState
        managed object property"
    ::= { cfprFabricComputeSlotEpEntry 4 }

cfprFabricComputeSlotEpAggrPortId OBJECT-TYPE
    SYNTAX       Gauge32
    MAX-ACCESS   read-only
    STATUS       current
    DESCRIPTION
        "Cisco Firepower fabric:ComputeSlotEp:aggrPortId
        managed object property"
    ::= { cfprFabricComputeSlotEpEntry 5 }

cfprFabricComputeSlotEpBoardAggregationRole OBJECT-TYPE
    SYNTAX       CfprEquipmentBoardAggregationRole
    MAX-ACCESS   read-only
    STATUS       current
    DESCRIPTION
        "Cisco Firepower fabric:ComputeSlotEp:boardAggregationRole
        managed object property"
    ::= { cfprFabricComputeSlotEpEntry 6 }

cfprFabricComputeSlotEpChassisId OBJECT-TYPE
    SYNTAX       Gauge32
    MAX-ACCESS   read-only
    STATUS       current
    DESCRIPTION
        "Cisco Firepower fabric:ComputeSlotEp:chassisId
        managed object property"
    ::= { cfprFabricComputeSlotEpEntry 7 }

cfprFabricComputeSlotEpConnPath OBJECT-TYPE
    SYNTAX       CfprEquipmentConnectionStatus
    MAX-ACCESS   read-only
    STATUS       current
    DESCRIPTION
        "Cisco Firepower fabric:ComputeSlotEp:connPath
        managed object property"
    ::= { cfprFabricComputeSlotEpEntry 8 }

cfprFabricComputeSlotEpConnStatus OBJECT-TYPE
    SYNTAX       CfprEquipmentConnectionStatus
    MAX-ACCESS   read-only
    STATUS       current
    DESCRIPTION
        "Cisco Firepower fabric:ComputeSlotEp:connStatus
        managed object property"
    ::= { cfprFabricComputeSlotEpEntry 9 }

cfprFabricComputeSlotEpDiscovery OBJECT-TYPE
    SYNTAX       CfprComputeDiscovery
    MAX-ACCESS   read-only
    STATUS       current
    DESCRIPTION
        "Cisco Firepower fabric:ComputeSlotEp:discovery
        managed object property"
    ::= { cfprFabricComputeSlotEpEntry 10 }

cfprFabricComputeSlotEpEpDn OBJECT-TYPE
    SYNTAX       SnmpAdminString
    MAX-ACCESS   read-only
    STATUS       current
    DESCRIPTION
        "Cisco Firepower fabric:ComputeSlotEp:epDn managed
        object property"
    ::= { cfprFabricComputeSlotEpEntry 11 }

cfprFabricComputeSlotEpFactoryResetFlag OBJECT-TYPE
    SYNTAX       TruthValue
    MAX-ACCESS   read-only
    STATUS       current
    DESCRIPTION
        "Cisco Firepower fabric:ComputeSlotEp:factoryResetFlag
        managed object property"
    ::= { cfprFabricComputeSlotEpEntry 12 }

cfprFabricComputeSlotEpFltAggr OBJECT-TYPE
    SYNTAX       Unsigned64
    MAX-ACCESS   read-only
    STATUS       current
    DESCRIPTION
        "Cisco Firepower fabric:ComputeSlotEp:fltAggr managed
        object property"
    ::= { cfprFabricComputeSlotEpEntry 13 }

cfprFabricComputeSlotEpFruIdentTrigTs OBJECT-TYPE
    SYNTAX       Unsigned64
    MAX-ACCESS   read-only
    STATUS       current
    DESCRIPTION
        "Cisco Firepower fabric:ComputeSlotEp:fruIdentTrigTs
        managed object property"
    ::= { cfprFabricComputeSlotEpEntry 14 }

cfprFabricComputeSlotEpFsmDescr OBJECT-TYPE
    SYNTAX       SnmpAdminString
    MAX-ACCESS   read-only
    STATUS       current
    DESCRIPTION
        "Cisco Firepower fabric:ComputeSlotEp:fsmDescr
        managed object property"
    ::= { cfprFabricComputeSlotEpEntry 15 }

cfprFabricComputeSlotEpFsmPrev OBJECT-TYPE
    SYNTAX       SnmpAdminString
    MAX-ACCESS   read-only
    STATUS       current
    DESCRIPTION
        "Cisco Firepower fabric:ComputeSlotEp:fsmPrev managed
        object property"
    ::= { cfprFabricComputeSlotEpEntry 16 }

cfprFabricComputeSlotEpFsmProgr OBJECT-TYPE
    SYNTAX       Gauge32
    MAX-ACCESS   read-only
    STATUS       current
    DESCRIPTION
        "Cisco Firepower fabric:ComputeSlotEp:fsmProgr
        managed object property"
    ::= { cfprFabricComputeSlotEpEntry 17 }

cfprFabricComputeSlotEpFsmRmtInvErrCode OBJECT-TYPE
    SYNTAX       Gauge32
    MAX-ACCESS   read-only
    STATUS       current
    DESCRIPTION
        "Cisco Firepower fabric:ComputeSlotEp:fsmRmtInvErrCode
        managed object property"
    ::= { cfprFabricComputeSlotEpEntry 18 }

cfprFabricComputeSlotEpFsmRmtInvErrDescr OBJECT-TYPE
    SYNTAX       SnmpAdminString
    MAX-ACCESS   read-only
    STATUS       current
    DESCRIPTION
        "Cisco Firepower fabric:ComputeSlotEp:fsmRmtInvErrDescr
        managed object property"
    ::= { cfprFabricComputeSlotEpEntry 19 }

cfprFabricComputeSlotEpFsmRmtInvRslt OBJECT-TYPE
    SYNTAX       CfprConditionRemoteInvRslt
    MAX-ACCESS   read-only
    STATUS       current
    DESCRIPTION
        "Cisco Firepower fabric:ComputeSlotEp:fsmRmtInvRslt
        managed object property"
    ::= { cfprFabricComputeSlotEpEntry 20 }

cfprFabricComputeSlotEpFsmStageDescr OBJECT-TYPE
    SYNTAX       SnmpAdminString
    MAX-ACCESS   read-only
    STATUS       current
    DESCRIPTION
        "Cisco Firepower fabric:ComputeSlotEp:fsmStageDescr
        managed object property"
    ::= { cfprFabricComputeSlotEpEntry 21 }

cfprFabricComputeSlotEpFsmStamp OBJECT-TYPE
    SYNTAX       DateAndTime
    MAX-ACCESS   read-only
    STATUS       current
    DESCRIPTION
        "Cisco Firepower fabric:ComputeSlotEp:fsmStamp
        managed object property"
    ::= { cfprFabricComputeSlotEpEntry 22 }

cfprFabricComputeSlotEpFsmStatus OBJECT-TYPE
    SYNTAX       SnmpAdminString
    MAX-ACCESS   read-only
    STATUS       current
    DESCRIPTION
        "Cisco Firepower fabric:ComputeSlotEp:fsmStatus
        managed object property"
    ::= { cfprFabricComputeSlotEpEntry 23 }

cfprFabricComputeSlotEpFsmTry OBJECT-TYPE
    SYNTAX       Gauge32
    MAX-ACCESS   read-only
    STATUS       current
    DESCRIPTION
        "Cisco Firepower fabric:ComputeSlotEp:fsmTry managed
        object property"
    ::= { cfprFabricComputeSlotEpEntry 24 }

cfprFabricComputeSlotEpIfRole OBJECT-TYPE
    SYNTAX       CfprFabricComputeEpIfRole
    MAX-ACCESS   read-only
    STATUS       current
    DESCRIPTION
        "Cisco Firepower fabric:ComputeSlotEp:ifRole managed
        object property"
    ::= { cfprFabricComputeSlotEpEntry 25 }

cfprFabricComputeSlotEpIfType OBJECT-TYPE
    SYNTAX       CfprFabricPIoEpIfType
    MAX-ACCESS   read-only
    STATUS       current
    DESCRIPTION
        "Cisco Firepower fabric:ComputeSlotEp:ifType managed
        object property"
    ::= { cfprFabricComputeSlotEpEntry 26 }

cfprFabricComputeSlotEpLcTs OBJECT-TYPE
    SYNTAX       DateAndTime
    MAX-ACCESS   read-only
    STATUS       current
    DESCRIPTION
        "Cisco Firepower fabric:ComputeSlotEp:lcTs managed
        object property"
    ::= { cfprFabricComputeSlotEpEntry 27 }

cfprFabricComputeSlotEpLicGP OBJECT-TYPE
    SYNTAX       Unsigned64
    MAX-ACCESS   read-only
    STATUS       current
    DESCRIPTION
        "Cisco Firepower fabric:ComputeSlotEp:licGP managed
        object property"
    ::= { cfprFabricComputeSlotEpEntry 28 }

cfprFabricComputeSlotEpLicState OBJECT-TYPE
    SYNTAX       CfprLicenseState
    MAX-ACCESS   read-only
    STATUS       current
    DESCRIPTION
        "Cisco Firepower fabric:ComputeSlotEp:licState
        managed object property"
    ::= { cfprFabricComputeSlotEpEntry 29 }

cfprFabricComputeSlotEpLocale OBJECT-TYPE
    SYNTAX       CfprFabricInternalEpLocale
    MAX-ACCESS   read-only
    STATUS       current
    DESCRIPTION
        "Cisco Firepower fabric:ComputeSlotEp:locale managed
        object property"
    ::= { cfprFabricComputeSlotEpEntry 30 }

cfprFabricComputeSlotEpManagingInst OBJECT-TYPE
    SYNTAX       CfprNetworkSwitchId
    MAX-ACCESS   read-only
    STATUS       current
    DESCRIPTION
        "Cisco Firepower fabric:ComputeSlotEp:managingInst
        managed object property"
    ::= { cfprFabricComputeSlotEpEntry 31 }

cfprFabricComputeSlotEpModel OBJECT-TYPE
    SYNTAX       SnmpAdminString
    MAX-ACCESS   read-only
    STATUS       current
    DESCRIPTION
        "Cisco Firepower fabric:ComputeSlotEp:model managed
        object property"
    ::= { cfprFabricComputeSlotEpEntry 32 }

cfprFabricComputeSlotEpName OBJECT-TYPE
    SYNTAX       SnmpAdminString
    MAX-ACCESS   read-only
    STATUS       current
    DESCRIPTION
        "Cisco Firepower fabric:ComputeSlotEp:name managed
        object property"
    ::= { cfprFabricComputeSlotEpEntry 33 }

cfprFabricComputeSlotEpOperState OBJECT-TYPE
    SYNTAX       CfprFabricPIoEpOperState
    MAX-ACCESS   read-only
    STATUS       current
    DESCRIPTION
        "Cisco Firepower fabric:ComputeSlotEp:operState
        managed object property"
    ::= { cfprFabricComputeSlotEpEntry 34 }

cfprFabricComputeSlotEpOperStateReason OBJECT-TYPE
    SYNTAX       SnmpAdminString
    MAX-ACCESS   read-only
    STATUS       current
    DESCRIPTION
        "Cisco Firepower fabric:ComputeSlotEp:operStateReason
        managed object property"
    ::= { cfprFabricComputeSlotEpEntry 35 }

cfprFabricComputeSlotEpPeerAggrPortId OBJECT-TYPE
    SYNTAX       Gauge32
    MAX-ACCESS   read-only
    STATUS       current
    DESCRIPTION
        "Cisco Firepower fabric:ComputeSlotEp:peerAggrPortId
        managed object property"
    ::= { cfprFabricComputeSlotEpEntry 36 }

cfprFabricComputeSlotEpPeerChassisId OBJECT-TYPE
    SYNTAX       Gauge32
    MAX-ACCESS   read-only
    STATUS       current
    DESCRIPTION
        "Cisco Firepower fabric:ComputeSlotEp:peerChassisId
        managed object property"
    ::= { cfprFabricComputeSlotEpEntry 37 }

cfprFabricComputeSlotEpPeerDn OBJECT-TYPE
    SYNTAX       SnmpAdminString
    MAX-ACCESS   read-only
    STATUS       current
    DESCRIPTION
        "Cisco Firepower fabric:ComputeSlotEp:peerDn managed
        object property"
    ::= { cfprFabricComputeSlotEpEntry 38 }

cfprFabricComputeSlotEpPeerPortId OBJECT-TYPE
    SYNTAX       Gauge32
    MAX-ACCESS   read-only
    STATUS       current
    DESCRIPTION
        "Cisco Firepower fabric:ComputeSlotEp:peerPortId
        managed object property"
    ::= { cfprFabricComputeSlotEpEntry 39 }

cfprFabricComputeSlotEpPeerSlotEpDn OBJECT-TYPE
    SYNTAX       SnmpAdminString
    MAX-ACCESS   read-only
    STATUS       current
    DESCRIPTION
        "Cisco Firepower fabric:ComputeSlotEp:peerSlotEpDn
        managed object property"
    ::= { cfprFabricComputeSlotEpEntry 40 }

cfprFabricComputeSlotEpPeerSlotId OBJECT-TYPE
    SYNTAX       Gauge32
    MAX-ACCESS   read-only
    STATUS       current
    DESCRIPTION
        "Cisco Firepower fabric:ComputeSlotEp:peerSlotId
        managed object property"
    ::= { cfprFabricComputeSlotEpEntry 41 }

cfprFabricComputeSlotEpPortId OBJECT-TYPE
    SYNTAX       CfprFabricPIoEpPortId
    MAX-ACCESS   read-only
    STATUS       current
    DESCRIPTION
        "Cisco Firepower fabric:ComputeSlotEp:portId managed
        object property"
    ::= { cfprFabricComputeSlotEpEntry 42 }

cfprFabricComputeSlotEpPresence OBJECT-TYPE
    SYNTAX       CfprEquipmentSlotStatus
    MAX-ACCESS   read-only
    STATUS       current
    DESCRIPTION
        "Cisco Firepower fabric:ComputeSlotEp:presence
        managed object property"
    ::= { cfprFabricComputeSlotEpEntry 43 }

cfprFabricComputeSlotEpPresencePath OBJECT-TYPE
    SYNTAX       CfprEquipmentConnectionStatus
    MAX-ACCESS   read-only
    STATUS       current
    DESCRIPTION
        "Cisco Firepower fabric:ComputeSlotEp:presencePath
        managed object property"
    ::= { cfprFabricComputeSlotEpEntry 44 }

cfprFabricComputeSlotEpRevision OBJECT-TYPE
    SYNTAX       SnmpAdminString
    MAX-ACCESS   read-only
    STATUS       current
    DESCRIPTION
        "Cisco Firepower fabric:ComputeSlotEp:revision
        managed object property"
    ::= { cfprFabricComputeSlotEpEntry 45 }

cfprFabricComputeSlotEpSerial OBJECT-TYPE
    SYNTAX       SnmpAdminString
    MAX-ACCESS   read-only
    STATUS       current
    DESCRIPTION
        "Cisco Firepower fabric:ComputeSlotEp:serial managed
        object property"
    ::= { cfprFabricComputeSlotEpEntry 46 }

cfprFabricComputeSlotEpSlotId OBJECT-TYPE
    SYNTAX       CfprFabricComputeSlotEpSlotId
    MAX-ACCESS   read-only
    STATUS       current
    DESCRIPTION
        "Cisco Firepower fabric:ComputeSlotEp:slotId managed
        object property"
    ::= { cfprFabricComputeSlotEpEntry 47 }

cfprFabricComputeSlotEpSwitchId OBJECT-TYPE
    SYNTAX       CfprNetworkSwitchId
    MAX-ACCESS   read-only
    STATUS       current
    DESCRIPTION
        "Cisco Firepower fabric:ComputeSlotEp:switchId
        managed object property"
    ::= { cfprFabricComputeSlotEpEntry 48 }

cfprFabricComputeSlotEpTransport OBJECT-TYPE
    SYNTAX       CfprNetworkTransport
    MAX-ACCESS   read-only
    STATUS       current
    DESCRIPTION
        "Cisco Firepower fabric:ComputeSlotEp:transport
        managed object property"
    ::= { cfprFabricComputeSlotEpEntry 49 }

cfprFabricComputeSlotEpType OBJECT-TYPE
    SYNTAX       CfprFabricComputeEpType
    MAX-ACCESS   read-only
    STATUS       current
    DESCRIPTION
        "Cisco Firepower fabric:ComputeSlotEp:type managed
        object property"
    ::= { cfprFabricComputeSlotEpEntry 50 }

cfprFabricComputeSlotEpVendor OBJECT-TYPE
    SYNTAX       SnmpAdminString
    MAX-ACCESS   read-only
    STATUS       current
    DESCRIPTION
        "Cisco Firepower fabric:ComputeSlotEp:vendor managed
        object property"
    ::= { cfprFabricComputeSlotEpEntry 51 }

cfprFabricComputeSlotEpBladeState OBJECT-TYPE
    SYNTAX       CfprLsOperState
    MAX-ACCESS   read-only
    STATUS       current
    DESCRIPTION
        "Cisco Firepower fabric:ComputeSlotEp:bladeState
        managed object property"
    ::= { cfprFabricComputeSlotEpEntry 52 }

cfprFabricComputeSlotEpDecommissionSecure OBJECT-TYPE
    SYNTAX       CfprComputeDecommissionState
    MAX-ACCESS   read-only
    STATUS       current
    DESCRIPTION
        "Cisco Firepower fabric:ComputeSlotEp:decommissionSecure
        managed object property"
    ::= { cfprFabricComputeSlotEpEntry 53 }

cfprFabricComputeSlotEpFailReason OBJECT-TYPE
    SYNTAX       SnmpAdminString
    MAX-ACCESS   read-only
    STATUS       current
    DESCRIPTION
        "Cisco Firepower fabric:ComputeSlotEp:failReason
        managed object property"
    ::= { cfprFabricComputeSlotEpEntry 54 }

cfprFabricComputeSlotEpFsmTable OBJECT-TYPE
    SYNTAX           SEQUENCE OF CfprFabricComputeSlotEpFsmEntry
    MAX-ACCESS       not-accessible
    STATUS           current
    DESCRIPTION
        "Cisco Firepower fabric:ComputeSlotEpFsm managed object table"
    ::= { cfprFabricObjects 10 }

cfprFabricComputeSlotEpFsmEntry OBJECT-TYPE
    SYNTAX           CfprFabricComputeSlotEpFsmEntry
    MAX-ACCESS       not-accessible
    STATUS           current
    DESCRIPTION
        "Entry for the cfprFabricComputeSlotEpFsmTable table."
    INDEX { cfprFabricComputeSlotEpFsmInstanceId }
    ::= { cfprFabricComputeSlotEpFsmTable 1 }

CfprFabricComputeSlotEpFsmEntry ::= SEQUENCE {
    cfprFabricComputeSlotEpFsmInstanceId                             CfprManagedObjectId,
    cfprFabricComputeSlotEpFsmDn                                     CfprManagedObjectDn,
    cfprFabricComputeSlotEpFsmRn                                     SnmpAdminString,
    cfprFabricComputeSlotEpFsmCompletionTime                         DateAndTime,
    cfprFabricComputeSlotEpFsmCurrentFsm                             CfprFabricComputeSlotEpFsmCurrentFsm,
    cfprFabricComputeSlotEpFsmDescrData                              SnmpAdminString,
    cfprFabricComputeSlotEpFsmFsmStatus                              CfprFsmFsmStageStatus,
    cfprFabricComputeSlotEpFsmProgress                               Gauge32,
    cfprFabricComputeSlotEpFsmRmtErrCode                             Gauge32,
    cfprFabricComputeSlotEpFsmRmtErrDescr                            SnmpAdminString,
    cfprFabricComputeSlotEpFsmRmtRslt                                CfprConditionRemoteInvRslt
}

cfprFabricComputeSlotEpFsmInstanceId OBJECT-TYPE
    SYNTAX       CfprManagedObjectId
    MAX-ACCESS   not-accessible
    STATUS       current
    DESCRIPTION
        "Instance identifier of the managed object."
    ::= { cfprFabricComputeSlotEpFsmEntry 1 }

cfprFabricComputeSlotEpFsmDn OBJECT-TYPE
    SYNTAX       CfprManagedObjectDn
    MAX-ACCESS   read-only
    STATUS       current
    DESCRIPTION
        "Cisco Firepower fabric:ComputeSlotEpFsm:dn managed
        object property"
    ::= { cfprFabricComputeSlotEpFsmEntry 2 }

cfprFabricComputeSlotEpFsmRn OBJECT-TYPE
    SYNTAX       SnmpAdminString
    MAX-ACCESS   read-only
    STATUS       current
    DESCRIPTION
        "Cisco Firepower fabric:ComputeSlotEpFsm:rn managed
        object property"
    ::= { cfprFabricComputeSlotEpFsmEntry 3 }

cfprFabricComputeSlotEpFsmCompletionTime OBJECT-TYPE
    SYNTAX       DateAndTime
    MAX-ACCESS   read-only
    STATUS       current
    DESCRIPTION
        "Cisco Firepower fabric:ComputeSlotEpFsm:completionTime
        managed object property"
    ::= { cfprFabricComputeSlotEpFsmEntry 4 }

cfprFabricComputeSlotEpFsmCurrentFsm OBJECT-TYPE
    SYNTAX       CfprFabricComputeSlotEpFsmCurrentFsm
    MAX-ACCESS   read-only
    STATUS       current
    DESCRIPTION
        "Cisco Firepower fabric:ComputeSlotEpFsm:currentFsm
        managed object property"
    ::= { cfprFabricComputeSlotEpFsmEntry 5 }

cfprFabricComputeSlotEpFsmDescrData OBJECT-TYPE
    SYNTAX       SnmpAdminString
    MAX-ACCESS   read-only
    STATUS       current
    DESCRIPTION
        "Cisco Firepower fabric:ComputeSlotEpFsm:descr
        managed object property"
    ::= { cfprFabricComputeSlotEpFsmEntry 6 }

cfprFabricComputeSlotEpFsmFsmStatus OBJECT-TYPE
    SYNTAX       CfprFsmFsmStageStatus
    MAX-ACCESS   read-only
    STATUS       current
    DESCRIPTION
        "Cisco Firepower fabric:ComputeSlotEpFsm:fsmStatus
        managed object property"
    ::= { cfprFabricComputeSlotEpFsmEntry 7 }

cfprFabricComputeSlotEpFsmProgress OBJECT-TYPE
    SYNTAX       Gauge32
    MAX-ACCESS   read-only
    STATUS       current
    DESCRIPTION
        "Cisco Firepower fabric:ComputeSlotEpFsm:progress
        managed object property"
    ::= { cfprFabricComputeSlotEpFsmEntry 8 }

cfprFabricComputeSlotEpFsmRmtErrCode OBJECT-TYPE
    SYNTAX       Gauge32
    MAX-ACCESS   read-only
    STATUS       current
    DESCRIPTION
        "Cisco Firepower fabric:ComputeSlotEpFsm:rmtErrCode
        managed object property"
    ::= { cfprFabricComputeSlotEpFsmEntry 9 }

cfprFabricComputeSlotEpFsmRmtErrDescr OBJECT-TYPE
    SYNTAX       SnmpAdminString
    MAX-ACCESS   read-only
    STATUS       current
    DESCRIPTION
        "Cisco Firepower fabric:ComputeSlotEpFsm:rmtErrDescr
        managed object property"
    ::= { cfprFabricComputeSlotEpFsmEntry 10 }

cfprFabricComputeSlotEpFsmRmtRslt OBJECT-TYPE
    SYNTAX       CfprConditionRemoteInvRslt
    MAX-ACCESS   read-only
    STATUS       current
    DESCRIPTION
        "Cisco Firepower fabric:ComputeSlotEpFsm:rmtRslt
        managed object property"
    ::= { cfprFabricComputeSlotEpFsmEntry 11 }

cfprFabricComputeSlotEpFsmStageTable OBJECT-TYPE
    SYNTAX           SEQUENCE OF CfprFabricComputeSlotEpFsmStageEntry
    MAX-ACCESS       not-accessible
    STATUS           current
    DESCRIPTION
        "Cisco Firepower fabric:ComputeSlotEpFsmStage managed
        object table"
    ::= { cfprFabricObjects 11 }

cfprFabricComputeSlotEpFsmStageEntry OBJECT-TYPE
    SYNTAX           CfprFabricComputeSlotEpFsmStageEntry
    MAX-ACCESS       not-accessible
    STATUS           current
    DESCRIPTION
        "Entry for the cfprFabricComputeSlotEpFsmStageTable table."
    INDEX { cfprFabricComputeSlotEpFsmStageInstanceId }
    ::= { cfprFabricComputeSlotEpFsmStageTable 1 }

CfprFabricComputeSlotEpFsmStageEntry ::= SEQUENCE {
    cfprFabricComputeSlotEpFsmStageInstanceId                        CfprManagedObjectId,
    cfprFabricComputeSlotEpFsmStageDn                                CfprManagedObjectDn,
    cfprFabricComputeSlotEpFsmStageRn                                SnmpAdminString,
    cfprFabricComputeSlotEpFsmStageDescrData                         SnmpAdminString,
    cfprFabricComputeSlotEpFsmStageLastUpdateTime                    DateAndTime,
    cfprFabricComputeSlotEpFsmStageName                              CfprFabricComputeSlotEpFsmStageName,
    cfprFabricComputeSlotEpFsmStageOrder                             Gauge32,
    cfprFabricComputeSlotEpFsmStageRetry                             Gauge32,
    cfprFabricComputeSlotEpFsmStageStageStatus                       CfprFsmFsmStageStatus
}

cfprFabricComputeSlotEpFsmStageInstanceId OBJECT-TYPE
    SYNTAX       CfprManagedObjectId
    MAX-ACCESS   not-accessible
    STATUS       current
    DESCRIPTION
        "Instance identifier of the managed object."
    ::= { cfprFabricComputeSlotEpFsmStageEntry 1 }

cfprFabricComputeSlotEpFsmStageDn OBJECT-TYPE
    SYNTAX       CfprManagedObjectDn
    MAX-ACCESS   read-only
    STATUS       current
    DESCRIPTION
        "Cisco Firepower fabric:ComputeSlotEpFsmStage:dn
        managed object property"
    ::= { cfprFabricComputeSlotEpFsmStageEntry 2 }

cfprFabricComputeSlotEpFsmStageRn OBJECT-TYPE
    SYNTAX       SnmpAdminString
    MAX-ACCESS   read-only
    STATUS       current
    DESCRIPTION
        "Cisco Firepower fabric:ComputeSlotEpFsmStage:rn
        managed object property"
    ::= { cfprFabricComputeSlotEpFsmStageEntry 3 }

cfprFabricComputeSlotEpFsmStageDescrData OBJECT-TYPE
    SYNTAX       SnmpAdminString
    MAX-ACCESS   read-only
    STATUS       current
    DESCRIPTION
        "Cisco Firepower fabric:ComputeSlotEpFsmStage:descr
        managed object property"
    ::= { cfprFabricComputeSlotEpFsmStageEntry 4 }

cfprFabricComputeSlotEpFsmStageLastUpdateTime OBJECT-TYPE
    SYNTAX       DateAndTime
    MAX-ACCESS   read-only
    STATUS       current
    DESCRIPTION
        "Cisco Firepower fabric:ComputeSlotEpFsmStage:lastUpdateTime
        managed object property"
    ::= { cfprFabricComputeSlotEpFsmStageEntry 5 }

cfprFabricComputeSlotEpFsmStageName OBJECT-TYPE
    SYNTAX       CfprFabricComputeSlotEpFsmStageName
    MAX-ACCESS   read-only
    STATUS       current
    DESCRIPTION
        "Cisco Firepower fabric:ComputeSlotEpFsmStage:name
        managed object property"
    ::= { cfprFabricComputeSlotEpFsmStageEntry 6 }

cfprFabricComputeSlotEpFsmStageOrder OBJECT-TYPE
    SYNTAX       Gauge32
    MAX-ACCESS   read-only
    STATUS       current
    DESCRIPTION
        "Cisco Firepower fabric:ComputeSlotEpFsmStage:order
        managed object property"
    ::= { cfprFabricComputeSlotEpFsmStageEntry 7 }

cfprFabricComputeSlotEpFsmStageRetry OBJECT-TYPE
    SYNTAX       Gauge32
    MAX-ACCESS   read-only
    STATUS       current
    DESCRIPTION
        "Cisco Firepower fabric:ComputeSlotEpFsmStage:retry
        managed object property"
    ::= { cfprFabricComputeSlotEpFsmStageEntry 8 }

cfprFabricComputeSlotEpFsmStageStageStatus OBJECT-TYPE
    SYNTAX       CfprFsmFsmStageStatus
    MAX-ACCESS   read-only
    STATUS       current
    DESCRIPTION
        "Cisco Firepower fabric:ComputeSlotEpFsmStage:stageStatus
        managed object property"
    ::= { cfprFabricComputeSlotEpFsmStageEntry 9 }

cfprFabricComputeSlotEpFsmTaskTable OBJECT-TYPE
    SYNTAX           SEQUENCE OF CfprFabricComputeSlotEpFsmTaskEntry
    MAX-ACCESS       not-accessible
    STATUS           current
    DESCRIPTION
        "Cisco Firepower fabric:ComputeSlotEpFsmTask managed object table"
    ::= { cfprFabricObjects 12 }

cfprFabricComputeSlotEpFsmTaskEntry OBJECT-TYPE
    SYNTAX           CfprFabricComputeSlotEpFsmTaskEntry
    MAX-ACCESS       not-accessible
    STATUS           current
    DESCRIPTION
        "Entry for the cfprFabricComputeSlotEpFsmTaskTable table."
    INDEX { cfprFabricComputeSlotEpFsmTaskInstanceId }
    ::= { cfprFabricComputeSlotEpFsmTaskTable 1 }

CfprFabricComputeSlotEpFsmTaskEntry ::= SEQUENCE {
    cfprFabricComputeSlotEpFsmTaskInstanceId                         CfprManagedObjectId,
    cfprFabricComputeSlotEpFsmTaskDn                                 CfprManagedObjectDn,
    cfprFabricComputeSlotEpFsmTaskRn                                 SnmpAdminString,
    cfprFabricComputeSlotEpFsmTaskCompletion                         CfprFsmCompletion,
    cfprFabricComputeSlotEpFsmTaskFlags                              CfprFsmFlags,
    cfprFabricComputeSlotEpFsmTaskItem                               CfprFabricComputeSlotEpFsmTaskItem,
    cfprFabricComputeSlotEpFsmTaskSeqId                              Gauge32
}

cfprFabricComputeSlotEpFsmTaskInstanceId OBJECT-TYPE
    SYNTAX       CfprManagedObjectId
    MAX-ACCESS   not-accessible
    STATUS       current
    DESCRIPTION
        "Instance identifier of the managed object."
    ::= { cfprFabricComputeSlotEpFsmTaskEntry 1 }

cfprFabricComputeSlotEpFsmTaskDn OBJECT-TYPE
    SYNTAX       CfprManagedObjectDn
    MAX-ACCESS   read-only
    STATUS       current
    DESCRIPTION
        "Cisco Firepower fabric:ComputeSlotEpFsmTask:dn
        managed object property"
    ::= { cfprFabricComputeSlotEpFsmTaskEntry 2 }

cfprFabricComputeSlotEpFsmTaskRn OBJECT-TYPE
    SYNTAX       SnmpAdminString
    MAX-ACCESS   read-only
    STATUS       current
    DESCRIPTION
        "Cisco Firepower fabric:ComputeSlotEpFsmTask:rn
        managed object property"
    ::= { cfprFabricComputeSlotEpFsmTaskEntry 3 }

cfprFabricComputeSlotEpFsmTaskCompletion OBJECT-TYPE
    SYNTAX       CfprFsmCompletion
    MAX-ACCESS   read-only
    STATUS       current
    DESCRIPTION
        "Cisco Firepower fabric:ComputeSlotEpFsmTask:completion
        managed object property"
    ::= { cfprFabricComputeSlotEpFsmTaskEntry 4 }

cfprFabricComputeSlotEpFsmTaskFlags OBJECT-TYPE
    SYNTAX       CfprFsmFlags
    MAX-ACCESS   read-only
    STATUS       current
    DESCRIPTION
        "Cisco Firepower fabric:ComputeSlotEpFsmTask:flags
        managed object property"
    ::= { cfprFabricComputeSlotEpFsmTaskEntry 5 }

cfprFabricComputeSlotEpFsmTaskItem OBJECT-TYPE
    SYNTAX       CfprFabricComputeSlotEpFsmTaskItem
    MAX-ACCESS   read-only
    STATUS       current
    DESCRIPTION
        "Cisco Firepower fabric:ComputeSlotEpFsmTask:item
        managed object property"
    ::= { cfprFabricComputeSlotEpFsmTaskEntry 6 }

cfprFabricComputeSlotEpFsmTaskSeqId OBJECT-TYPE
    SYNTAX       Gauge32
    MAX-ACCESS   read-only
    STATUS       current
    DESCRIPTION
        "Cisco Firepower fabric:ComputeSlotEpFsmTask:seqId
        managed object property"
    ::= { cfprFabricComputeSlotEpFsmTaskEntry 7 }

cfprFabricDceSrvTable OBJECT-TYPE
    SYNTAX           SEQUENCE OF CfprFabricDceSrvEntry
    MAX-ACCESS       not-accessible
    STATUS           current
    DESCRIPTION
        "Cisco Firepower fabric:DceSrv managed object table"
    ::= { cfprFabricObjects 13 }

cfprFabricDceSrvEntry OBJECT-TYPE
    SYNTAX           CfprFabricDceSrvEntry
    MAX-ACCESS       not-accessible
    STATUS           current
    DESCRIPTION
        "Entry for the cfprFabricDceSrvTable table."
    INDEX { cfprFabricDceSrvInstanceId }
    ::= { cfprFabricDceSrvTable 1 }

CfprFabricDceSrvEntry ::= SEQUENCE {
    cfprFabricDceSrvInstanceId                                       CfprManagedObjectId,
    cfprFabricDceSrvDn                                               CfprManagedObjectDn,
    cfprFabricDceSrvRn                                               SnmpAdminString,
    cfprFabricDceSrvId                                               CfprNetworkSwitchId,
    cfprFabricDceSrvLocale                                           CfprFabricInternalLocale,
    cfprFabricDceSrvName                                             SnmpAdminString,
    cfprFabricDceSrvTransport                                        CfprFabricInternalDceSrvTransport,
    cfprFabricDceSrvType                                             CfprFabricInternalDceSrvType
}

cfprFabricDceSrvInstanceId OBJECT-TYPE
    SYNTAX       CfprManagedObjectId
    MAX-ACCESS   not-accessible
    STATUS       current
    DESCRIPTION
        "Instance identifier of the managed object."
    ::= { cfprFabricDceSrvEntry 1 }

cfprFabricDceSrvDn OBJECT-TYPE
    SYNTAX       CfprManagedObjectDn
    MAX-ACCESS   read-only
    STATUS       current
    DESCRIPTION
        "Cisco Firepower fabric:DceSrv:dn managed object property"
    ::= { cfprFabricDceSrvEntry 2 }

cfprFabricDceSrvRn OBJECT-TYPE
    SYNTAX       SnmpAdminString
    MAX-ACCESS   read-only
    STATUS       current
    DESCRIPTION
        "Cisco Firepower fabric:DceSrv:rn managed object property"
    ::= { cfprFabricDceSrvEntry 3 }

cfprFabricDceSrvId OBJECT-TYPE
    SYNTAX       CfprNetworkSwitchId
    MAX-ACCESS   read-only
    STATUS       current
    DESCRIPTION
        "Cisco Firepower fabric:DceSrv:id managed object property"
    ::= { cfprFabricDceSrvEntry 4 }

cfprFabricDceSrvLocale OBJECT-TYPE
    SYNTAX       CfprFabricInternalLocale
    MAX-ACCESS   read-only
    STATUS       current
    DESCRIPTION
        "Cisco Firepower fabric:DceSrv:locale managed object property"
    ::= { cfprFabricDceSrvEntry 5 }

cfprFabricDceSrvName OBJECT-TYPE
    SYNTAX       SnmpAdminString
    MAX-ACCESS   read-only
    STATUS       current
    DESCRIPTION
        "Cisco Firepower fabric:DceSrv:name managed object property"
    ::= { cfprFabricDceSrvEntry 6 }

cfprFabricDceSrvTransport OBJECT-TYPE
    SYNTAX       CfprFabricInternalDceSrvTransport
    MAX-ACCESS   read-only
    STATUS       current
    DESCRIPTION
        "Cisco Firepower fabric:DceSrv:transport managed object property"
    ::= { cfprFabricDceSrvEntry 7 }

cfprFabricDceSrvType OBJECT-TYPE
    SYNTAX       CfprFabricInternalDceSrvType
    MAX-ACCESS   read-only
    STATUS       current
    DESCRIPTION
        "Cisco Firepower fabric:DceSrv:type managed object property"
    ::= { cfprFabricDceSrvEntry 8 }

cfprFabricDceSwSrvTable OBJECT-TYPE
    SYNTAX           SEQUENCE OF CfprFabricDceSwSrvEntry
    MAX-ACCESS       not-accessible
    STATUS           current
    DESCRIPTION
        "Cisco Firepower fabric:DceSwSrv managed object table"
    ::= { cfprFabricObjects 14 }

cfprFabricDceSwSrvEntry OBJECT-TYPE
    SYNTAX           CfprFabricDceSwSrvEntry
    MAX-ACCESS       not-accessible
    STATUS           current
    DESCRIPTION
        "Entry for the cfprFabricDceSwSrvTable table."
    INDEX { cfprFabricDceSwSrvInstanceId }
    ::= { cfprFabricDceSwSrvTable 1 }

CfprFabricDceSwSrvEntry ::= SEQUENCE {
    cfprFabricDceSwSrvInstanceId                                     CfprManagedObjectId,
    cfprFabricDceSwSrvDn                                             CfprManagedObjectDn,
    cfprFabricDceSwSrvRn                                             SnmpAdminString,
    cfprFabricDceSwSrvId                                             CfprNetworkSwitchId,
    cfprFabricDceSwSrvLocale                                         CfprFabricInternalLocale,
    cfprFabricDceSwSrvName                                           SnmpAdminString,
    cfprFabricDceSwSrvTransport                                      CfprFabricInternalDceSrvTransport,
    cfprFabricDceSwSrvType                                           CfprFabricInternalDceSrvType
}

cfprFabricDceSwSrvInstanceId OBJECT-TYPE
    SYNTAX       CfprManagedObjectId
    MAX-ACCESS   not-accessible
    STATUS       current
    DESCRIPTION
        "Instance identifier of the managed object."
    ::= { cfprFabricDceSwSrvEntry 1 }

cfprFabricDceSwSrvDn OBJECT-TYPE
    SYNTAX       CfprManagedObjectDn
    MAX-ACCESS   read-only
    STATUS       current
    DESCRIPTION
        "Cisco Firepower fabric:DceSwSrv:dn managed object property"
    ::= { cfprFabricDceSwSrvEntry 2 }

cfprFabricDceSwSrvRn OBJECT-TYPE
    SYNTAX       SnmpAdminString
    MAX-ACCESS   read-only
    STATUS       current
    DESCRIPTION
        "Cisco Firepower fabric:DceSwSrv:rn managed object property"
    ::= { cfprFabricDceSwSrvEntry 3 }

cfprFabricDceSwSrvId OBJECT-TYPE
    SYNTAX       CfprNetworkSwitchId
    MAX-ACCESS   read-only
    STATUS       current
    DESCRIPTION
        "Cisco Firepower fabric:DceSwSrv:id managed object property"
    ::= { cfprFabricDceSwSrvEntry 4 }

cfprFabricDceSwSrvLocale OBJECT-TYPE
    SYNTAX       CfprFabricInternalLocale
    MAX-ACCESS   read-only
    STATUS       current
    DESCRIPTION
        "Cisco Firepower fabric:DceSwSrv:locale managed object property"
    ::= { cfprFabricDceSwSrvEntry 5 }

cfprFabricDceSwSrvName OBJECT-TYPE
    SYNTAX       SnmpAdminString
    MAX-ACCESS   read-only
    STATUS       current
    DESCRIPTION
        "Cisco Firepower fabric:DceSwSrv:name managed object property"
    ::= { cfprFabricDceSwSrvEntry 6 }

cfprFabricDceSwSrvTransport OBJECT-TYPE
    SYNTAX       CfprFabricInternalDceSrvTransport
    MAX-ACCESS   read-only
    STATUS       current
    DESCRIPTION
        "Cisco Firepower fabric:DceSwSrv:transport managed
        object property"
    ::= { cfprFabricDceSwSrvEntry 7 }

cfprFabricDceSwSrvType OBJECT-TYPE
    SYNTAX       CfprFabricInternalDceSrvType
    MAX-ACCESS   read-only
    STATUS       current
    DESCRIPTION
        "Cisco Firepower fabric:DceSwSrv:type managed object property"
    ::= { cfprFabricDceSwSrvEntry 8 }

cfprFabricDceSwSrvEpTable OBJECT-TYPE
    SYNTAX           SEQUENCE OF CfprFabricDceSwSrvEpEntry
    MAX-ACCESS       not-accessible
    STATUS           current
    DESCRIPTION
        "Cisco Firepower fabric:DceSwSrvEp managed object table"
    ::= { cfprFabricObjects 15 }

cfprFabricDceSwSrvEpEntry OBJECT-TYPE
    SYNTAX           CfprFabricDceSwSrvEpEntry
    MAX-ACCESS       not-accessible
    STATUS           current
    DESCRIPTION
        "Entry for the cfprFabricDceSwSrvEpTable table."
    INDEX { cfprFabricDceSwSrvEpInstanceId }
    ::= { cfprFabricDceSwSrvEpTable 1 }

CfprFabricDceSwSrvEpEntry ::= SEQUENCE {
    cfprFabricDceSwSrvEpInstanceId                                   CfprManagedObjectId,
    cfprFabricDceSwSrvEpDn                                           CfprManagedObjectDn,
    cfprFabricDceSwSrvEpRn                                           SnmpAdminString,
    cfprFabricDceSwSrvEpAdminState                                   CfprFabricInternalEpAdminState,
    cfprFabricDceSwSrvEpAggrPortId                                   Gauge32,
    cfprFabricDceSwSrvEpChassisId                                    Gauge32,
    cfprFabricDceSwSrvEpEpDn                                         SnmpAdminString,
    cfprFabricDceSwSrvEpFltAggr                                      Unsigned64,
    cfprFabricDceSwSrvEpIfRole                                       CfprFabricSwSrvEpIfRole,
    cfprFabricDceSwSrvEpIfType                                       CfprFabricPIoEpIfType,
    cfprFabricDceSwSrvEpLicGP                                        Unsigned64,
    cfprFabricDceSwSrvEpLicState                                     CfprLicenseState,
    cfprFabricDceSwSrvEpLocale                                       CfprFabricInternalEpLocale,
    cfprFabricDceSwSrvEpName                                         SnmpAdminString,
    cfprFabricDceSwSrvEpOperState                                    CfprFabricPIoEpOperState,
    cfprFabricDceSwSrvEpOperStateReason                              SnmpAdminString,
    cfprFabricDceSwSrvEpPeerAggrPortId                               Gauge32,
    cfprFabricDceSwSrvEpPeerChassisId                                Gauge32,
    cfprFabricDceSwSrvEpPeerDn                                       SnmpAdminString,
    cfprFabricDceSwSrvEpPeerPortId                                   Gauge32,
    cfprFabricDceSwSrvEpPeerSlotId                                   Gauge32,
    cfprFabricDceSwSrvEpPortId                                       CfprFabricDceSwSrvEpPortId,
    cfprFabricDceSwSrvEpSlotId                                       CfprFabricDceSwSrvEpSlotId,
    cfprFabricDceSwSrvEpSwitchId                                     CfprNetworkSwitchId,
    cfprFabricDceSwSrvEpTransport                                    CfprFabricADceSwSrvEpTransport,
    cfprFabricDceSwSrvEpType                                         CfprFabricSwSrvEpType,
    cfprFabricDceSwSrvEpUsrLbl                                       SnmpAdminString
}

cfprFabricDceSwSrvEpInstanceId OBJECT-TYPE
    SYNTAX       CfprManagedObjectId
    MAX-ACCESS   not-accessible
    STATUS       current
    DESCRIPTION
        "Instance identifier of the managed object."
    ::= { cfprFabricDceSwSrvEpEntry 1 }

cfprFabricDceSwSrvEpDn OBJECT-TYPE
    SYNTAX       CfprManagedObjectDn
    MAX-ACCESS   read-only
    STATUS       current
    DESCRIPTION
        "Cisco Firepower fabric:DceSwSrvEp:dn managed object property"
    ::= { cfprFabricDceSwSrvEpEntry 2 }

cfprFabricDceSwSrvEpRn OBJECT-TYPE
    SYNTAX       SnmpAdminString
    MAX-ACCESS   read-only
    STATUS       current
    DESCRIPTION
        "Cisco Firepower fabric:DceSwSrvEp:rn managed object property"
    ::= { cfprFabricDceSwSrvEpEntry 3 }

cfprFabricDceSwSrvEpAdminState OBJECT-TYPE
    SYNTAX       CfprFabricInternalEpAdminState
    MAX-ACCESS   read-only
    STATUS       current
    DESCRIPTION
        "Cisco Firepower fabric:DceSwSrvEp:adminState managed
        object property"
    ::= { cfprFabricDceSwSrvEpEntry 4 }

cfprFabricDceSwSrvEpAggrPortId OBJECT-TYPE
    SYNTAX       Gauge32
    MAX-ACCESS   read-only
    STATUS       current
    DESCRIPTION
        "Cisco Firepower fabric:DceSwSrvEp:aggrPortId managed
        object property"
    ::= { cfprFabricDceSwSrvEpEntry 5 }

cfprFabricDceSwSrvEpChassisId OBJECT-TYPE
    SYNTAX       Gauge32
    MAX-ACCESS   read-only
    STATUS       current
    DESCRIPTION
        "Cisco Firepower fabric:DceSwSrvEp:chassisId managed
        object property"
    ::= { cfprFabricDceSwSrvEpEntry 6 }

cfprFabricDceSwSrvEpEpDn OBJECT-TYPE
    SYNTAX       SnmpAdminString
    MAX-ACCESS   read-only
    STATUS       current
    DESCRIPTION
        "Cisco Firepower fabric:DceSwSrvEp:epDn managed object property"
    ::= { cfprFabricDceSwSrvEpEntry 7 }

cfprFabricDceSwSrvEpFltAggr OBJECT-TYPE
    SYNTAX       Unsigned64
    MAX-ACCESS   read-only
    STATUS       current
    DESCRIPTION
        "Cisco Firepower fabric:DceSwSrvEp:fltAggr managed
        object property"
    ::= { cfprFabricDceSwSrvEpEntry 8 }

cfprFabricDceSwSrvEpIfRole OBJECT-TYPE
    SYNTAX       CfprFabricSwSrvEpIfRole
    MAX-ACCESS   read-only
    STATUS       current
    DESCRIPTION
        "Cisco Firepower fabric:DceSwSrvEp:ifRole managed object property"
    ::= { cfprFabricDceSwSrvEpEntry 9 }

cfprFabricDceSwSrvEpIfType OBJECT-TYPE
    SYNTAX       CfprFabricPIoEpIfType
    MAX-ACCESS   read-only
    STATUS       current
    DESCRIPTION
        "Cisco Firepower fabric:DceSwSrvEp:ifType managed object property"
    ::= { cfprFabricDceSwSrvEpEntry 10 }

cfprFabricDceSwSrvEpLicGP OBJECT-TYPE
    SYNTAX       Unsigned64
    MAX-ACCESS   read-only
    STATUS       current
    DESCRIPTION
        "Cisco Firepower fabric:DceSwSrvEp:licGP managed object property"
    ::= { cfprFabricDceSwSrvEpEntry 11 }

cfprFabricDceSwSrvEpLicState OBJECT-TYPE
    SYNTAX       CfprLicenseState
    MAX-ACCESS   read-only
    STATUS       current
    DESCRIPTION
        "Cisco Firepower fabric:DceSwSrvEp:licState managed
        object property"
    ::= { cfprFabricDceSwSrvEpEntry 12 }

cfprFabricDceSwSrvEpLocale OBJECT-TYPE
    SYNTAX       CfprFabricInternalEpLocale
    MAX-ACCESS   read-only
    STATUS       current
    DESCRIPTION
        "Cisco Firepower fabric:DceSwSrvEp:locale managed object property"
    ::= { cfprFabricDceSwSrvEpEntry 13 }

cfprFabricDceSwSrvEpName OBJECT-TYPE
    SYNTAX       SnmpAdminString
    MAX-ACCESS   read-only
    STATUS       current
    DESCRIPTION
        "Cisco Firepower fabric:DceSwSrvEp:name managed object property"
    ::= { cfprFabricDceSwSrvEpEntry 14 }

cfprFabricDceSwSrvEpOperState OBJECT-TYPE
    SYNTAX       CfprFabricPIoEpOperState
    MAX-ACCESS   read-only
    STATUS       current
    DESCRIPTION
        "Cisco Firepower fabric:DceSwSrvEp:operState managed
        object property"
    ::= { cfprFabricDceSwSrvEpEntry 15 }

cfprFabricDceSwSrvEpOperStateReason OBJECT-TYPE
    SYNTAX       SnmpAdminString
    MAX-ACCESS   read-only
    STATUS       current
    DESCRIPTION
        "Cisco Firepower fabric:DceSwSrvEp:operStateReason
        managed object property"
    ::= { cfprFabricDceSwSrvEpEntry 16 }

cfprFabricDceSwSrvEpPeerAggrPortId OBJECT-TYPE
    SYNTAX       Gauge32
    MAX-ACCESS   read-only
    STATUS       current
    DESCRIPTION
        "Cisco Firepower fabric:DceSwSrvEp:peerAggrPortId
        managed object property"
    ::= { cfprFabricDceSwSrvEpEntry 17 }

cfprFabricDceSwSrvEpPeerChassisId OBJECT-TYPE
    SYNTAX       Gauge32
    MAX-ACCESS   read-only
    STATUS       current
    DESCRIPTION
        "Cisco Firepower fabric:DceSwSrvEp:peerChassisId
        managed object property"
    ::= { cfprFabricDceSwSrvEpEntry 18 }

cfprFabricDceSwSrvEpPeerDn OBJECT-TYPE
    SYNTAX       SnmpAdminString
    MAX-ACCESS   read-only
    STATUS       current
    DESCRIPTION
        "Cisco Firepower fabric:DceSwSrvEp:peerDn managed object property"
    ::= { cfprFabricDceSwSrvEpEntry 19 }

cfprFabricDceSwSrvEpPeerPortId OBJECT-TYPE
    SYNTAX       Gauge32
    MAX-ACCESS   read-only
    STATUS       current
    DESCRIPTION
        "Cisco Firepower fabric:DceSwSrvEp:peerPortId managed
        object property"
    ::= { cfprFabricDceSwSrvEpEntry 20 }

cfprFabricDceSwSrvEpPeerSlotId OBJECT-TYPE
    SYNTAX       Gauge32
    MAX-ACCESS   read-only
    STATUS       current
    DESCRIPTION
        "Cisco Firepower fabric:DceSwSrvEp:peerSlotId managed
        object property"
    ::= { cfprFabricDceSwSrvEpEntry 21 }

cfprFabricDceSwSrvEpPortId OBJECT-TYPE
    SYNTAX       CfprFabricDceSwSrvEpPortId
    MAX-ACCESS   read-only
    STATUS       current
    DESCRIPTION
        "Cisco Firepower fabric:DceSwSrvEp:portId managed object property"
    ::= { cfprFabricDceSwSrvEpEntry 22 }

cfprFabricDceSwSrvEpSlotId OBJECT-TYPE
    SYNTAX       CfprFabricDceSwSrvEpSlotId
    MAX-ACCESS   read-only
    STATUS       current
    DESCRIPTION
        "Cisco Firepower fabric:DceSwSrvEp:slotId managed object property"
    ::= { cfprFabricDceSwSrvEpEntry 23 }

cfprFabricDceSwSrvEpSwitchId OBJECT-TYPE
    SYNTAX       CfprNetworkSwitchId
    MAX-ACCESS   read-only
    STATUS       current
    DESCRIPTION
        "Cisco Firepower fabric:DceSwSrvEp:switchId managed
        object property"
    ::= { cfprFabricDceSwSrvEpEntry 24 }

cfprFabricDceSwSrvEpTransport OBJECT-TYPE
    SYNTAX       CfprFabricADceSwSrvEpTransport
    MAX-ACCESS   read-only
    STATUS       current
    DESCRIPTION
        "Cisco Firepower fabric:DceSwSrvEp:transport managed
        object property"
    ::= { cfprFabricDceSwSrvEpEntry 25 }

cfprFabricDceSwSrvEpType OBJECT-TYPE
    SYNTAX       CfprFabricSwSrvEpType
    MAX-ACCESS   read-only
    STATUS       current
    DESCRIPTION
        "Cisco Firepower fabric:DceSwSrvEp:type managed object property"
    ::= { cfprFabricDceSwSrvEpEntry 26 }

cfprFabricDceSwSrvEpUsrLbl OBJECT-TYPE
    SYNTAX       SnmpAdminString
    MAX-ACCESS   read-only
    STATUS       current
    DESCRIPTION
        "Cisco Firepower fabric:DceSwSrvEp:usrLbl managed object property"
    ::= { cfprFabricDceSwSrvEpEntry 27 }

cfprFabricDceSwSrvPcTable OBJECT-TYPE
    SYNTAX           SEQUENCE OF CfprFabricDceSwSrvPcEntry
    MAX-ACCESS       not-accessible
    STATUS           current
    DESCRIPTION
        "Cisco Firepower fabric:DceSwSrvPc managed object table"
    ::= { cfprFabricObjects 16 }

cfprFabricDceSwSrvPcEntry OBJECT-TYPE
    SYNTAX           CfprFabricDceSwSrvPcEntry
    MAX-ACCESS       not-accessible
    STATUS           current
    DESCRIPTION
        "Entry for the cfprFabricDceSwSrvPcTable table."
    INDEX { cfprFabricDceSwSrvPcInstanceId }
    ::= { cfprFabricDceSwSrvPcTable 1 }

CfprFabricDceSwSrvPcEntry ::= SEQUENCE {
    cfprFabricDceSwSrvPcInstanceId                                   CfprManagedObjectId,
    cfprFabricDceSwSrvPcDn                                           CfprManagedObjectDn,
    cfprFabricDceSwSrvPcRn                                           SnmpAdminString,
    cfprFabricDceSwSrvPcAdminState                                   CfprFabricDceSwSrvPcAdminState,
    cfprFabricDceSwSrvPcChassisId                                    Gauge32,
    cfprFabricDceSwSrvPcDescr                                        SnmpAdminString,
    cfprFabricDceSwSrvPcEpDn                                         SnmpAdminString,
    cfprFabricDceSwSrvPcFltAggr                                      Unsigned64,
    cfprFabricDceSwSrvPcIfRole                                       CfprFabricSwSrvPcIfRole,
    cfprFabricDceSwSrvPcIfType                                       CfprFabricCIoEpIfType,
    cfprFabricDceSwSrvPcLocale                                       CfprFabricInternalPcLocale,
    cfprFabricDceSwSrvPcName                                         SnmpAdminString,
    cfprFabricDceSwSrvPcOperSpeed                                    CfprPortEthSpeed,
    cfprFabricDceSwSrvPcOperState                                    CfprNetworkPortOperState,
    cfprFabricDceSwSrvPcPeerDn                                       SnmpAdminString,
    cfprFabricDceSwSrvPcPortId                                       CfprFabricDceSwSrvPcPortId,
    cfprFabricDceSwSrvPcStateQual                                    SnmpAdminString,
    cfprFabricDceSwSrvPcSwitchId                                     CfprNetworkSwitchId,
    cfprFabricDceSwSrvPcTransport                                    CfprFabricDceSwSrvPcTransport,
    cfprFabricDceSwSrvPcType                                         CfprFabricSwSrvPcType
}

cfprFabricDceSwSrvPcInstanceId OBJECT-TYPE
    SYNTAX       CfprManagedObjectId
    MAX-ACCESS   not-accessible
    STATUS       current
    DESCRIPTION
        "Instance identifier of the managed object."
    ::= { cfprFabricDceSwSrvPcEntry 1 }

cfprFabricDceSwSrvPcDn OBJECT-TYPE
    SYNTAX       CfprManagedObjectDn
    MAX-ACCESS   read-only
    STATUS       current
    DESCRIPTION
        "Cisco Firepower fabric:DceSwSrvPc:dn managed object property"
    ::= { cfprFabricDceSwSrvPcEntry 2 }

cfprFabricDceSwSrvPcRn OBJECT-TYPE
    SYNTAX       SnmpAdminString
    MAX-ACCESS   read-only
    STATUS       current
    DESCRIPTION
        "Cisco Firepower fabric:DceSwSrvPc:rn managed object property"
    ::= { cfprFabricDceSwSrvPcEntry 3 }

cfprFabricDceSwSrvPcAdminState OBJECT-TYPE
    SYNTAX       CfprFabricDceSwSrvPcAdminState
    MAX-ACCESS   read-only
    STATUS       current
    DESCRIPTION
        "Cisco Firepower fabric:DceSwSrvPc:adminState managed
        object property"
    ::= { cfprFabricDceSwSrvPcEntry 4 }

cfprFabricDceSwSrvPcChassisId OBJECT-TYPE
    SYNTAX       Gauge32
    MAX-ACCESS   read-only
    STATUS       current
    DESCRIPTION
        "Cisco Firepower fabric:DceSwSrvPc:chassisId managed
        object property"
    ::= { cfprFabricDceSwSrvPcEntry 5 }

cfprFabricDceSwSrvPcDescr OBJECT-TYPE
    SYNTAX       SnmpAdminString
    MAX-ACCESS   read-only
    STATUS       current
    DESCRIPTION
        "Cisco Firepower fabric:DceSwSrvPc:descr managed object property"
    ::= { cfprFabricDceSwSrvPcEntry 6 }

cfprFabricDceSwSrvPcEpDn OBJECT-TYPE
    SYNTAX       SnmpAdminString
    MAX-ACCESS   read-only
    STATUS       current
    DESCRIPTION
        "Cisco Firepower fabric:DceSwSrvPc:epDn managed object property"
    ::= { cfprFabricDceSwSrvPcEntry 7 }

cfprFabricDceSwSrvPcFltAggr OBJECT-TYPE
    SYNTAX       Unsigned64
    MAX-ACCESS   read-only
    STATUS       current
    DESCRIPTION
        "Cisco Firepower fabric:DceSwSrvPc:fltAggr managed
        object property"
    ::= { cfprFabricDceSwSrvPcEntry 8 }

cfprFabricDceSwSrvPcIfRole OBJECT-TYPE
    SYNTAX       CfprFabricSwSrvPcIfRole
    MAX-ACCESS   read-only
    STATUS       current
    DESCRIPTION
        "Cisco Firepower fabric:DceSwSrvPc:ifRole managed object property"
    ::= { cfprFabricDceSwSrvPcEntry 9 }

cfprFabricDceSwSrvPcIfType OBJECT-TYPE
    SYNTAX       CfprFabricCIoEpIfType
    MAX-ACCESS   read-only
    STATUS       current
    DESCRIPTION
        "Cisco Firepower fabric:DceSwSrvPc:ifType managed object property"
    ::= { cfprFabricDceSwSrvPcEntry 10 }

cfprFabricDceSwSrvPcLocale OBJECT-TYPE
    SYNTAX       CfprFabricInternalPcLocale
    MAX-ACCESS   read-only
    STATUS       current
    DESCRIPTION
        "Cisco Firepower fabric:DceSwSrvPc:locale managed object property"
    ::= { cfprFabricDceSwSrvPcEntry 11 }

cfprFabricDceSwSrvPcName OBJECT-TYPE
    SYNTAX       SnmpAdminString
    MAX-ACCESS   read-only
    STATUS       current
    DESCRIPTION
        "Cisco Firepower fabric:DceSwSrvPc:name managed object property"
    ::= { cfprFabricDceSwSrvPcEntry 12 }

cfprFabricDceSwSrvPcOperSpeed OBJECT-TYPE
    SYNTAX       CfprPortEthSpeed
    MAX-ACCESS   read-only
    STATUS       current
    DESCRIPTION
        "Cisco Firepower fabric:DceSwSrvPc:operSpeed managed
        object property"
    ::= { cfprFabricDceSwSrvPcEntry 13 }

cfprFabricDceSwSrvPcOperState OBJECT-TYPE
    SYNTAX       CfprNetworkPortOperState
    MAX-ACCESS   read-only
    STATUS       current
    DESCRIPTION
        "Cisco Firepower fabric:DceSwSrvPc:operState managed
        object property"
    ::= { cfprFabricDceSwSrvPcEntry 14 }

cfprFabricDceSwSrvPcPeerDn OBJECT-TYPE
    SYNTAX       SnmpAdminString
    MAX-ACCESS   read-only
    STATUS       current
    DESCRIPTION
        "Cisco Firepower fabric:DceSwSrvPc:peerDn managed object property"
    ::= { cfprFabricDceSwSrvPcEntry 15 }

cfprFabricDceSwSrvPcPortId OBJECT-TYPE
    SYNTAX       CfprFabricDceSwSrvPcPortId
    MAX-ACCESS   read-only
    STATUS       current
    DESCRIPTION
        "Cisco Firepower fabric:DceSwSrvPc:portId managed object property"
    ::= { cfprFabricDceSwSrvPcEntry 16 }

cfprFabricDceSwSrvPcStateQual OBJECT-TYPE
    SYNTAX       SnmpAdminString
    MAX-ACCESS   read-only
    STATUS       current
    DESCRIPTION
        "Cisco Firepower fabric:DceSwSrvPc:stateQual managed
        object property"
    ::= { cfprFabricDceSwSrvPcEntry 17 }

cfprFabricDceSwSrvPcSwitchId OBJECT-TYPE
    SYNTAX       CfprNetworkSwitchId
    MAX-ACCESS   read-only
    STATUS       current
    DESCRIPTION
        "Cisco Firepower fabric:DceSwSrvPc:switchId managed
        object property"
    ::= { cfprFabricDceSwSrvPcEntry 18 }

cfprFabricDceSwSrvPcTransport OBJECT-TYPE
    SYNTAX       CfprFabricDceSwSrvPcTransport
    MAX-ACCESS   read-only
    STATUS       current
    DESCRIPTION
        "Cisco Firepower fabric:DceSwSrvPc:transport managed
        object property"
    ::= { cfprFabricDceSwSrvPcEntry 19 }

cfprFabricDceSwSrvPcType OBJECT-TYPE
    SYNTAX       CfprFabricSwSrvPcType
    MAX-ACCESS   read-only
    STATUS       current
    DESCRIPTION
        "Cisco Firepower fabric:DceSwSrvPc:type managed object property"
    ::= { cfprFabricDceSwSrvPcEntry 20 }

cfprFabricDceSwSrvPcEpTable OBJECT-TYPE
    SYNTAX           SEQUENCE OF CfprFabricDceSwSrvPcEpEntry
    MAX-ACCESS       not-accessible
    STATUS           current
    DESCRIPTION
        "Cisco Firepower fabric:DceSwSrvPcEp managed object table"
    ::= { cfprFabricObjects 17 }

cfprFabricDceSwSrvPcEpEntry OBJECT-TYPE
    SYNTAX           CfprFabricDceSwSrvPcEpEntry
    MAX-ACCESS       not-accessible
    STATUS           current
    DESCRIPTION
        "Entry for the cfprFabricDceSwSrvPcEpTable table."
    INDEX { cfprFabricDceSwSrvPcEpInstanceId }
    ::= { cfprFabricDceSwSrvPcEpTable 1 }

CfprFabricDceSwSrvPcEpEntry ::= SEQUENCE {
    cfprFabricDceSwSrvPcEpInstanceId                                 CfprManagedObjectId,
    cfprFabricDceSwSrvPcEpDnData                                     CfprManagedObjectDn,
    cfprFabricDceSwSrvPcEpRn                                         SnmpAdminString,
    cfprFabricDceSwSrvPcEpAdminState                                 CfprFabricInternalEpAdminState,
    cfprFabricDceSwSrvPcEpAggrPortId                                 Gauge32,
    cfprFabricDceSwSrvPcEpChassisId                                  Gauge32,
    cfprFabricDceSwSrvPcEpEpDn                                       SnmpAdminString,
    cfprFabricDceSwSrvPcEpFltAggr                                    Unsigned64,
    cfprFabricDceSwSrvPcEpIfRole                                     CfprFabricSwSrvEpIfRole,
    cfprFabricDceSwSrvPcEpIfType                                     CfprFabricPIoEpIfType,
    cfprFabricDceSwSrvPcEpLicGP                                      Unsigned64,
    cfprFabricDceSwSrvPcEpLicState                                   CfprLicenseState,
    cfprFabricDceSwSrvPcEpLocale                                     CfprFabricInternalEpLocale,
    cfprFabricDceSwSrvPcEpMembership                                 CfprFabricMembershipStatus,
    cfprFabricDceSwSrvPcEpName                                       SnmpAdminString,
    cfprFabricDceSwSrvPcEpOperState                                  CfprFabricPIoEpOperState,
    cfprFabricDceSwSrvPcEpOperStateReason                            SnmpAdminString,
    cfprFabricDceSwSrvPcEpPeerAggrPortId                             Gauge32,
    cfprFabricDceSwSrvPcEpPeerChassisId                              Gauge32,
    cfprFabricDceSwSrvPcEpPeerDn                                     SnmpAdminString,
    cfprFabricDceSwSrvPcEpPeerPortId                                 Gauge32,
    cfprFabricDceSwSrvPcEpPeerSlotId                                 Gauge32,
    cfprFabricDceSwSrvPcEpPortId                                     CfprFabricDceSwSrvPcEpPortId,
    cfprFabricDceSwSrvPcEpSlotId                                     CfprFabricDceSwSrvPcEpSlotId,
    cfprFabricDceSwSrvPcEpSwitchId                                   CfprNetworkSwitchId,
    cfprFabricDceSwSrvPcEpTransport                                  CfprFabricADceSwSrvEpTransport,
    cfprFabricDceSwSrvPcEpType                                       CfprFabricSwSrvEpType,
    cfprFabricDceSwSrvPcEpUsrLbl                                     SnmpAdminString
}

cfprFabricDceSwSrvPcEpInstanceId OBJECT-TYPE
    SYNTAX       CfprManagedObjectId
    MAX-ACCESS   not-accessible
    STATUS       current
    DESCRIPTION
        "Instance identifier of the managed object."
    ::= { cfprFabricDceSwSrvPcEpEntry 1 }

cfprFabricDceSwSrvPcEpDnData OBJECT-TYPE
    SYNTAX       CfprManagedObjectDn
    MAX-ACCESS   read-only
    STATUS       current
    DESCRIPTION
        "Cisco Firepower fabric:DceSwSrvPcEp:dn managed object property"
    ::= { cfprFabricDceSwSrvPcEpEntry 2 }

cfprFabricDceSwSrvPcEpRn OBJECT-TYPE
    SYNTAX       SnmpAdminString
    MAX-ACCESS   read-only
    STATUS       current
    DESCRIPTION
        "Cisco Firepower fabric:DceSwSrvPcEp:rn managed object property"
    ::= { cfprFabricDceSwSrvPcEpEntry 3 }

cfprFabricDceSwSrvPcEpAdminState OBJECT-TYPE
    SYNTAX       CfprFabricInternalEpAdminState
    MAX-ACCESS   read-only
    STATUS       current
    DESCRIPTION
        "Cisco Firepower fabric:DceSwSrvPcEp:adminState
        managed object property"
    ::= { cfprFabricDceSwSrvPcEpEntry 4 }

cfprFabricDceSwSrvPcEpAggrPortId OBJECT-TYPE
    SYNTAX       Gauge32
    MAX-ACCESS   read-only
    STATUS       current
    DESCRIPTION
        "Cisco Firepower fabric:DceSwSrvPcEp:aggrPortId
        managed object property"
    ::= { cfprFabricDceSwSrvPcEpEntry 5 }

cfprFabricDceSwSrvPcEpChassisId OBJECT-TYPE
    SYNTAX       Gauge32
    MAX-ACCESS   read-only
    STATUS       current
    DESCRIPTION
        "Cisco Firepower fabric:DceSwSrvPcEp:chassisId
        managed object property"
    ::= { cfprFabricDceSwSrvPcEpEntry 6 }

cfprFabricDceSwSrvPcEpEpDn OBJECT-TYPE
    SYNTAX       SnmpAdminString
    MAX-ACCESS   read-only
    STATUS       current
    DESCRIPTION
        "Cisco Firepower fabric:DceSwSrvPcEp:epDn managed object property"
    ::= { cfprFabricDceSwSrvPcEpEntry 7 }

cfprFabricDceSwSrvPcEpFltAggr OBJECT-TYPE
    SYNTAX       Unsigned64
    MAX-ACCESS   read-only
    STATUS       current
    DESCRIPTION
        "Cisco Firepower fabric:DceSwSrvPcEp:fltAggr managed
        object property"
    ::= { cfprFabricDceSwSrvPcEpEntry 8 }

cfprFabricDceSwSrvPcEpIfRole OBJECT-TYPE
    SYNTAX       CfprFabricSwSrvEpIfRole
    MAX-ACCESS   read-only
    STATUS       current
    DESCRIPTION
        "Cisco Firepower fabric:DceSwSrvPcEp:ifRole managed
        object property"
    ::= { cfprFabricDceSwSrvPcEpEntry 9 }

cfprFabricDceSwSrvPcEpIfType OBJECT-TYPE
    SYNTAX       CfprFabricPIoEpIfType
    MAX-ACCESS   read-only
    STATUS       current
    DESCRIPTION
        "Cisco Firepower fabric:DceSwSrvPcEp:ifType managed
        object property"
    ::= { cfprFabricDceSwSrvPcEpEntry 10 }

cfprFabricDceSwSrvPcEpLicGP OBJECT-TYPE
    SYNTAX       Unsigned64
    MAX-ACCESS   read-only
    STATUS       current
    DESCRIPTION
        "Cisco Firepower fabric:DceSwSrvPcEp:licGP managed
        object property"
    ::= { cfprFabricDceSwSrvPcEpEntry 11 }

cfprFabricDceSwSrvPcEpLicState OBJECT-TYPE
    SYNTAX       CfprLicenseState
    MAX-ACCESS   read-only
    STATUS       current
    DESCRIPTION
        "Cisco Firepower fabric:DceSwSrvPcEp:licState managed
        object property"
    ::= { cfprFabricDceSwSrvPcEpEntry 12 }

cfprFabricDceSwSrvPcEpLocale OBJECT-TYPE
    SYNTAX       CfprFabricInternalEpLocale
    MAX-ACCESS   read-only
    STATUS       current
    DESCRIPTION
        "Cisco Firepower fabric:DceSwSrvPcEp:locale managed
        object property"
    ::= { cfprFabricDceSwSrvPcEpEntry 13 }

cfprFabricDceSwSrvPcEpMembership OBJECT-TYPE
    SYNTAX       CfprFabricMembershipStatus
    MAX-ACCESS   read-only
    STATUS       current
    DESCRIPTION
        "Cisco Firepower fabric:DceSwSrvPcEp:membership
        managed object property"
    ::= { cfprFabricDceSwSrvPcEpEntry 14 }

cfprFabricDceSwSrvPcEpName OBJECT-TYPE
    SYNTAX       SnmpAdminString
    MAX-ACCESS   read-only
    STATUS       current
    DESCRIPTION
        "Cisco Firepower fabric:DceSwSrvPcEp:name managed object property"
    ::= { cfprFabricDceSwSrvPcEpEntry 15 }

cfprFabricDceSwSrvPcEpOperState OBJECT-TYPE
    SYNTAX       CfprFabricPIoEpOperState
    MAX-ACCESS   read-only
    STATUS       current
    DESCRIPTION
        "Cisco Firepower fabric:DceSwSrvPcEp:operState
        managed object property"
    ::= { cfprFabricDceSwSrvPcEpEntry 16 }

cfprFabricDceSwSrvPcEpOperStateReason OBJECT-TYPE
    SYNTAX       SnmpAdminString
    MAX-ACCESS   read-only
    STATUS       current
    DESCRIPTION
        "Cisco Firepower fabric:DceSwSrvPcEp:operStateReason
        managed object property"
    ::= { cfprFabricDceSwSrvPcEpEntry 17 }

cfprFabricDceSwSrvPcEpPeerAggrPortId OBJECT-TYPE
    SYNTAX       Gauge32
    MAX-ACCESS   read-only
    STATUS       current
    DESCRIPTION
        "Cisco Firepower fabric:DceSwSrvPcEp:peerAggrPortId
        managed object property"
    ::= { cfprFabricDceSwSrvPcEpEntry 18 }

cfprFabricDceSwSrvPcEpPeerChassisId OBJECT-TYPE
    SYNTAX       Gauge32
    MAX-ACCESS   read-only
    STATUS       current
    DESCRIPTION
        "Cisco Firepower fabric:DceSwSrvPcEp:peerChassisId
        managed object property"
    ::= { cfprFabricDceSwSrvPcEpEntry 19 }

cfprFabricDceSwSrvPcEpPeerDn OBJECT-TYPE
    SYNTAX       SnmpAdminString
    MAX-ACCESS   read-only
    STATUS       current
    DESCRIPTION
        "Cisco Firepower fabric:DceSwSrvPcEp:peerDn managed
        object property"
    ::= { cfprFabricDceSwSrvPcEpEntry 20 }

cfprFabricDceSwSrvPcEpPeerPortId OBJECT-TYPE
    SYNTAX       Gauge32
    MAX-ACCESS   read-only
    STATUS       current
    DESCRIPTION
        "Cisco Firepower fabric:DceSwSrvPcEp:peerPortId
        managed object property"
    ::= { cfprFabricDceSwSrvPcEpEntry 21 }

cfprFabricDceSwSrvPcEpPeerSlotId OBJECT-TYPE
    SYNTAX       Gauge32
    MAX-ACCESS   read-only
    STATUS       current
    DESCRIPTION
        "Cisco Firepower fabric:DceSwSrvPcEp:peerSlotId
        managed object property"
    ::= { cfprFabricDceSwSrvPcEpEntry 22 }

cfprFabricDceSwSrvPcEpPortId OBJECT-TYPE
    SYNTAX       CfprFabricDceSwSrvPcEpPortId
    MAX-ACCESS   read-only
    STATUS       current
    DESCRIPTION
        "Cisco Firepower fabric:DceSwSrvPcEp:portId managed
        object property"
    ::= { cfprFabricDceSwSrvPcEpEntry 23 }

cfprFabricDceSwSrvPcEpSlotId OBJECT-TYPE
    SYNTAX       CfprFabricDceSwSrvPcEpSlotId
    MAX-ACCESS   read-only
    STATUS       current
    DESCRIPTION
        "Cisco Firepower fabric:DceSwSrvPcEp:slotId managed
        object property"
    ::= { cfprFabricDceSwSrvPcEpEntry 24 }

cfprFabricDceSwSrvPcEpSwitchId OBJECT-TYPE
    SYNTAX       CfprNetworkSwitchId
    MAX-ACCESS   read-only
    STATUS       current
    DESCRIPTION
        "Cisco Firepower fabric:DceSwSrvPcEp:switchId managed
        object property"
    ::= { cfprFabricDceSwSrvPcEpEntry 25 }

cfprFabricDceSwSrvPcEpTransport OBJECT-TYPE
    SYNTAX       CfprFabricADceSwSrvEpTransport
    MAX-ACCESS   read-only
    STATUS       current
    DESCRIPTION
        "Cisco Firepower fabric:DceSwSrvPcEp:transport
        managed object property"
    ::= { cfprFabricDceSwSrvPcEpEntry 26 }

cfprFabricDceSwSrvPcEpType OBJECT-TYPE
    SYNTAX       CfprFabricSwSrvEpType
    MAX-ACCESS   read-only
    STATUS       current
    DESCRIPTION
        "Cisco Firepower fabric:DceSwSrvPcEp:type managed object property"
    ::= { cfprFabricDceSwSrvPcEpEntry 27 }

cfprFabricDceSwSrvPcEpUsrLbl OBJECT-TYPE
    SYNTAX       SnmpAdminString
    MAX-ACCESS   read-only
    STATUS       current
    DESCRIPTION
        "Cisco Firepower fabric:DceSwSrvPcEp:usrLbl managed
        object property"
    ::= { cfprFabricDceSwSrvPcEpEntry 28 }

cfprFabricEpTable OBJECT-TYPE
    SYNTAX           SEQUENCE OF CfprFabricEpEntry
    MAX-ACCESS       not-accessible
    STATUS           current
    DESCRIPTION
        "Cisco Firepower fabric:Ep managed object table"
    ::= { cfprFabricObjects 18 }

cfprFabricEpEntry OBJECT-TYPE
    SYNTAX           CfprFabricEpEntry
    MAX-ACCESS       not-accessible
    STATUS           current
    DESCRIPTION
        "Entry for the cfprFabricEpTable table."
    INDEX { cfprFabricEpInstanceId }
    ::= { cfprFabricEpTable 1 }

CfprFabricEpEntry ::= SEQUENCE {
    cfprFabricEpInstanceId                                           CfprManagedObjectId,
    cfprFabricEpDn                                                   CfprManagedObjectDn,
    cfprFabricEpRn                                                   SnmpAdminString
}

cfprFabricEpInstanceId OBJECT-TYPE
    SYNTAX       CfprManagedObjectId
    MAX-ACCESS   not-accessible
    STATUS       current
    DESCRIPTION
        "Instance identifier of the managed object."
    ::= { cfprFabricEpEntry 1 }

cfprFabricEpDn OBJECT-TYPE
    SYNTAX       CfprManagedObjectDn
    MAX-ACCESS   read-only
    STATUS       current
    DESCRIPTION
        "Cisco Firepower fabric:Ep:dn managed object property"
    ::= { cfprFabricEpEntry 2 }

cfprFabricEpRn OBJECT-TYPE
    SYNTAX       SnmpAdminString
    MAX-ACCESS   read-only
    STATUS       current
    DESCRIPTION
        "Cisco Firepower fabric:Ep:rn managed object property"
    ::= { cfprFabricEpEntry 3 }

cfprFabricEpMgrTable OBJECT-TYPE
    SYNTAX           SEQUENCE OF CfprFabricEpMgrEntry
    MAX-ACCESS       not-accessible
    STATUS           current
    DESCRIPTION
        "Cisco Firepower fabric:EpMgr managed object table"
    ::= { cfprFabricObjects 19 }

cfprFabricEpMgrEntry OBJECT-TYPE
    SYNTAX           CfprFabricEpMgrEntry
    MAX-ACCESS       not-accessible
    STATUS           current
    DESCRIPTION
        "Entry for the cfprFabricEpMgrTable table."
    INDEX { cfprFabricEpMgrInstanceId }
    ::= { cfprFabricEpMgrTable 1 }

CfprFabricEpMgrEntry ::= SEQUENCE {
    cfprFabricEpMgrInstanceId                                        CfprManagedObjectId,
    cfprFabricEpMgrDn                                                CfprManagedObjectDn,
    cfprFabricEpMgrRn                                                SnmpAdminString,
    cfprFabricEpMgrConfMode                                          CfprFabricConfMode,
    cfprFabricEpMgrConfQual                                          SnmpAdminString,
    cfprFabricEpMgrConfState                                         CfprFabricConfState,
    cfprFabricEpMgrFltAggr                                           Unsigned64,
    cfprFabricEpMgrFsmDescr                                          SnmpAdminString,
    cfprFabricEpMgrFsmFlags                                          SnmpAdminString,
    cfprFabricEpMgrFsmPrev                                           SnmpAdminString,
    cfprFabricEpMgrFsmProgr                                          Gauge32,
    cfprFabricEpMgrFsmRmtInvErrCode                                  Gauge32,
    cfprFabricEpMgrFsmRmtInvErrDescr                                 SnmpAdminString,
    cfprFabricEpMgrFsmRmtInvRslt                                     CfprConditionRemoteInvRslt,
    cfprFabricEpMgrFsmStageDescr                                     SnmpAdminString,
    cfprFabricEpMgrFsmStamp                                          DateAndTime,
    cfprFabricEpMgrFsmStatus                                         SnmpAdminString,
    cfprFabricEpMgrFsmTry                                            Gauge32,
    cfprFabricEpMgrId                                                CfprNetworkSwitchId
}

cfprFabricEpMgrInstanceId OBJECT-TYPE
    SYNTAX       CfprManagedObjectId
    MAX-ACCESS   not-accessible
    STATUS       current
    DESCRIPTION
        "Instance identifier of the managed object."
    ::= { cfprFabricEpMgrEntry 1 }

cfprFabricEpMgrDn OBJECT-TYPE
    SYNTAX       CfprManagedObjectDn
    MAX-ACCESS   read-only
    STATUS       current
    DESCRIPTION
        "Cisco Firepower fabric:EpMgr:dn managed object property"
    ::= { cfprFabricEpMgrEntry 2 }

cfprFabricEpMgrRn OBJECT-TYPE
    SYNTAX       SnmpAdminString
    MAX-ACCESS   read-only
    STATUS       current
    DESCRIPTION
        "Cisco Firepower fabric:EpMgr:rn managed object property"
    ::= { cfprFabricEpMgrEntry 3 }

cfprFabricEpMgrConfMode OBJECT-TYPE
    SYNTAX       CfprFabricConfMode
    MAX-ACCESS   read-only
    STATUS       current
    DESCRIPTION
        "Cisco Firepower fabric:EpMgr:confMode managed object property"
    ::= { cfprFabricEpMgrEntry 4 }

cfprFabricEpMgrConfQual OBJECT-TYPE
    SYNTAX       SnmpAdminString
    MAX-ACCESS   read-only
    STATUS       current
    DESCRIPTION
        "Cisco Firepower fabric:EpMgr:confQual managed object property"
    ::= { cfprFabricEpMgrEntry 5 }

cfprFabricEpMgrConfState OBJECT-TYPE
    SYNTAX       CfprFabricConfState
    MAX-ACCESS   read-only
    STATUS       current
    DESCRIPTION
        "Cisco Firepower fabric:EpMgr:confState managed object property"
    ::= { cfprFabricEpMgrEntry 6 }

cfprFabricEpMgrFltAggr OBJECT-TYPE
    SYNTAX       Unsigned64
    MAX-ACCESS   read-only
    STATUS       current
    DESCRIPTION
        "Cisco Firepower fabric:EpMgr:fltAggr managed object property"
    ::= { cfprFabricEpMgrEntry 7 }

cfprFabricEpMgrFsmDescr OBJECT-TYPE
    SYNTAX       SnmpAdminString
    MAX-ACCESS   read-only
    STATUS       current
    DESCRIPTION
        "Cisco Firepower fabric:EpMgr:fsmDescr managed object property"
    ::= { cfprFabricEpMgrEntry 8 }

cfprFabricEpMgrFsmFlags OBJECT-TYPE
    SYNTAX       SnmpAdminString
    MAX-ACCESS   read-only
    STATUS       current
    DESCRIPTION
        "Cisco Firepower fabric:EpMgr:fsmFlags managed object property"
    ::= { cfprFabricEpMgrEntry 9 }

cfprFabricEpMgrFsmPrev OBJECT-TYPE
    SYNTAX       SnmpAdminString
    MAX-ACCESS   read-only
    STATUS       current
    DESCRIPTION
        "Cisco Firepower fabric:EpMgr:fsmPrev managed object property"
    ::= { cfprFabricEpMgrEntry 10 }

cfprFabricEpMgrFsmProgr OBJECT-TYPE
    SYNTAX       Gauge32
    MAX-ACCESS   read-only
    STATUS       current
    DESCRIPTION
        "Cisco Firepower fabric:EpMgr:fsmProgr managed object property"
    ::= { cfprFabricEpMgrEntry 11 }

cfprFabricEpMgrFsmRmtInvErrCode OBJECT-TYPE
    SYNTAX       Gauge32
    MAX-ACCESS   read-only
    STATUS       current
    DESCRIPTION
        "Cisco Firepower fabric:EpMgr:fsmRmtInvErrCode
        managed object property"
    ::= { cfprFabricEpMgrEntry 12 }

cfprFabricEpMgrFsmRmtInvErrDescr OBJECT-TYPE
    SYNTAX       SnmpAdminString
    MAX-ACCESS   read-only
    STATUS       current
    DESCRIPTION
        "Cisco Firepower fabric:EpMgr:fsmRmtInvErrDescr
        managed object property"
    ::= { cfprFabricEpMgrEntry 13 }

cfprFabricEpMgrFsmRmtInvRslt OBJECT-TYPE
    SYNTAX       CfprConditionRemoteInvRslt
    MAX-ACCESS   read-only
    STATUS       current
    DESCRIPTION
        "Cisco Firepower fabric:EpMgr:fsmRmtInvRslt managed
        object property"
    ::= { cfprFabricEpMgrEntry 14 }

cfprFabricEpMgrFsmStageDescr OBJECT-TYPE
    SYNTAX       SnmpAdminString
    MAX-ACCESS   read-only
    STATUS       current
    DESCRIPTION
        "Cisco Firepower fabric:EpMgr:fsmStageDescr managed
        object property"
    ::= { cfprFabricEpMgrEntry 15 }

cfprFabricEpMgrFsmStamp OBJECT-TYPE
    SYNTAX       DateAndTime
    MAX-ACCESS   read-only
    STATUS       current
    DESCRIPTION
        "Cisco Firepower fabric:EpMgr:fsmStamp managed object property"
    ::= { cfprFabricEpMgrEntry 16 }

cfprFabricEpMgrFsmStatus OBJECT-TYPE
    SYNTAX       SnmpAdminString
    MAX-ACCESS   read-only
    STATUS       current
    DESCRIPTION
        "Cisco Firepower fabric:EpMgr:fsmStatus managed object property"
    ::= { cfprFabricEpMgrEntry 17 }

cfprFabricEpMgrFsmTry OBJECT-TYPE
    SYNTAX       Gauge32
    MAX-ACCESS   read-only
    STATUS       current
    DESCRIPTION
        "Cisco Firepower fabric:EpMgr:fsmTry managed object property"
    ::= { cfprFabricEpMgrEntry 18 }

cfprFabricEpMgrId OBJECT-TYPE
    SYNTAX       CfprNetworkSwitchId
    MAX-ACCESS   read-only
    STATUS       current
    DESCRIPTION
        "Cisco Firepower fabric:EpMgr:id managed object property"
    ::= { cfprFabricEpMgrEntry 19 }

cfprFabricEpMgrFsmTable OBJECT-TYPE
    SYNTAX           SEQUENCE OF CfprFabricEpMgrFsmEntry
    MAX-ACCESS       not-accessible
    STATUS           current
    DESCRIPTION
        "Cisco Firepower fabric:EpMgrFsm managed object table"
    ::= { cfprFabricObjects 20 }

cfprFabricEpMgrFsmEntry OBJECT-TYPE
    SYNTAX           CfprFabricEpMgrFsmEntry
    MAX-ACCESS       not-accessible
    STATUS           current
    DESCRIPTION
        "Entry for the cfprFabricEpMgrFsmTable table."
    INDEX { cfprFabricEpMgrFsmInstanceId }
    ::= { cfprFabricEpMgrFsmTable 1 }

CfprFabricEpMgrFsmEntry ::= SEQUENCE {
    cfprFabricEpMgrFsmInstanceId                                     CfprManagedObjectId,
    cfprFabricEpMgrFsmDn                                             CfprManagedObjectDn,
    cfprFabricEpMgrFsmRn                                             SnmpAdminString,
    cfprFabricEpMgrFsmCompletionTime                                 DateAndTime,
    cfprFabricEpMgrFsmCurrentFsm                                     CfprFabricEpMgrFsmCurrentFsm,
    cfprFabricEpMgrFsmDescrData                                      SnmpAdminString,
    cfprFabricEpMgrFsmFsmStatus                                      CfprFsmFsmStageStatus,
    cfprFabricEpMgrFsmProgress                                       Gauge32,
    cfprFabricEpMgrFsmRmtErrCode                                     Gauge32,
    cfprFabricEpMgrFsmRmtErrDescr                                    SnmpAdminString,
    cfprFabricEpMgrFsmRmtRslt                                        CfprConditionRemoteInvRslt
}

cfprFabricEpMgrFsmInstanceId OBJECT-TYPE
    SYNTAX       CfprManagedObjectId
    MAX-ACCESS   not-accessible
    STATUS       current
    DESCRIPTION
        "Instance identifier of the managed object."
    ::= { cfprFabricEpMgrFsmEntry 1 }

cfprFabricEpMgrFsmDn OBJECT-TYPE
    SYNTAX       CfprManagedObjectDn
    MAX-ACCESS   read-only
    STATUS       current
    DESCRIPTION
        "Cisco Firepower fabric:EpMgrFsm:dn managed object property"
    ::= { cfprFabricEpMgrFsmEntry 2 }

cfprFabricEpMgrFsmRn OBJECT-TYPE
    SYNTAX       SnmpAdminString
    MAX-ACCESS   read-only
    STATUS       current
    DESCRIPTION
        "Cisco Firepower fabric:EpMgrFsm:rn managed object property"
    ::= { cfprFabricEpMgrFsmEntry 3 }

cfprFabricEpMgrFsmCompletionTime OBJECT-TYPE
    SYNTAX       DateAndTime
    MAX-ACCESS   read-only
    STATUS       current
    DESCRIPTION
        "Cisco Firepower fabric:EpMgrFsm:completionTime
        managed object property"
    ::= { cfprFabricEpMgrFsmEntry 4 }

cfprFabricEpMgrFsmCurrentFsm OBJECT-TYPE
    SYNTAX       CfprFabricEpMgrFsmCurrentFsm
    MAX-ACCESS   read-only
    STATUS       current
    DESCRIPTION
        "Cisco Firepower fabric:EpMgrFsm:currentFsm managed
        object property"
    ::= { cfprFabricEpMgrFsmEntry 5 }

cfprFabricEpMgrFsmDescrData OBJECT-TYPE
    SYNTAX       SnmpAdminString
    MAX-ACCESS   read-only
    STATUS       current
    DESCRIPTION
        "Cisco Firepower fabric:EpMgrFsm:descr managed object property"
    ::= { cfprFabricEpMgrFsmEntry 6 }

cfprFabricEpMgrFsmFsmStatus OBJECT-TYPE
    SYNTAX       CfprFsmFsmStageStatus
    MAX-ACCESS   read-only
    STATUS       current
    DESCRIPTION
        "Cisco Firepower fabric:EpMgrFsm:fsmStatus managed
        object property"
    ::= { cfprFabricEpMgrFsmEntry 7 }

cfprFabricEpMgrFsmProgress OBJECT-TYPE
    SYNTAX       Gauge32
    MAX-ACCESS   read-only
    STATUS       current
    DESCRIPTION
        "Cisco Firepower fabric:EpMgrFsm:progress managed object property"
    ::= { cfprFabricEpMgrFsmEntry 8 }

cfprFabricEpMgrFsmRmtErrCode OBJECT-TYPE
    SYNTAX       Gauge32
    MAX-ACCESS   read-only
    STATUS       current
    DESCRIPTION
        "Cisco Firepower fabric:EpMgrFsm:rmtErrCode managed
        object property"
    ::= { cfprFabricEpMgrFsmEntry 9 }

cfprFabricEpMgrFsmRmtErrDescr OBJECT-TYPE
    SYNTAX       SnmpAdminString
    MAX-ACCESS   read-only
    STATUS       current
    DESCRIPTION
        "Cisco Firepower fabric:EpMgrFsm:rmtErrDescr managed
        object property"
    ::= { cfprFabricEpMgrFsmEntry 10 }

cfprFabricEpMgrFsmRmtRslt OBJECT-TYPE
    SYNTAX       CfprConditionRemoteInvRslt
    MAX-ACCESS   read-only
    STATUS       current
    DESCRIPTION
        "Cisco Firepower fabric:EpMgrFsm:rmtRslt managed object property"
    ::= { cfprFabricEpMgrFsmEntry 11 }

cfprFabricEpMgrFsmStageTable OBJECT-TYPE
    SYNTAX           SEQUENCE OF CfprFabricEpMgrFsmStageEntry
    MAX-ACCESS       not-accessible
    STATUS           current
    DESCRIPTION
        "Cisco Firepower fabric:EpMgrFsmStage managed object table"
    ::= { cfprFabricObjects 21 }

cfprFabricEpMgrFsmStageEntry OBJECT-TYPE
    SYNTAX           CfprFabricEpMgrFsmStageEntry
    MAX-ACCESS       not-accessible
    STATUS           current
    DESCRIPTION
        "Entry for the cfprFabricEpMgrFsmStageTable table."
    INDEX { cfprFabricEpMgrFsmStageInstanceId }
    ::= { cfprFabricEpMgrFsmStageTable 1 }

CfprFabricEpMgrFsmStageEntry ::= SEQUENCE {
    cfprFabricEpMgrFsmStageInstanceId                                CfprManagedObjectId,
    cfprFabricEpMgrFsmStageDn                                        CfprManagedObjectDn,
    cfprFabricEpMgrFsmStageRn                                        SnmpAdminString,
    cfprFabricEpMgrFsmStageDescrData                                 SnmpAdminString,
    cfprFabricEpMgrFsmStageLastUpdateTime                            DateAndTime,
    cfprFabricEpMgrFsmStageName                                      CfprFabricEpMgrFsmStageName,
    cfprFabricEpMgrFsmStageOrder                                     Gauge32,
    cfprFabricEpMgrFsmStageRetry                                     Gauge32,
    cfprFabricEpMgrFsmStageStageStatus                               CfprFsmFsmStageStatus
}

cfprFabricEpMgrFsmStageInstanceId OBJECT-TYPE
    SYNTAX       CfprManagedObjectId
    MAX-ACCESS   not-accessible
    STATUS       current
    DESCRIPTION
        "Instance identifier of the managed object."
    ::= { cfprFabricEpMgrFsmStageEntry 1 }

cfprFabricEpMgrFsmStageDn OBJECT-TYPE
    SYNTAX       CfprManagedObjectDn
    MAX-ACCESS   read-only
    STATUS       current
    DESCRIPTION
        "Cisco Firepower fabric:EpMgrFsmStage:dn managed object property"
    ::= { cfprFabricEpMgrFsmStageEntry 2 }

cfprFabricEpMgrFsmStageRn OBJECT-TYPE
    SYNTAX       SnmpAdminString
    MAX-ACCESS   read-only
    STATUS       current
    DESCRIPTION
        "Cisco Firepower fabric:EpMgrFsmStage:rn managed object property"
    ::= { cfprFabricEpMgrFsmStageEntry 3 }

cfprFabricEpMgrFsmStageDescrData OBJECT-TYPE
    SYNTAX       SnmpAdminString
    MAX-ACCESS   read-only
    STATUS       current
    DESCRIPTION
        "Cisco Firepower fabric:EpMgrFsmStage:descr managed
        object property"
    ::= { cfprFabricEpMgrFsmStageEntry 4 }

cfprFabricEpMgrFsmStageLastUpdateTime OBJECT-TYPE
    SYNTAX       DateAndTime
    MAX-ACCESS   read-only
    STATUS       current
    DESCRIPTION
        "Cisco Firepower fabric:EpMgrFsmStage:lastUpdateTime
        managed object property"
    ::= { cfprFabricEpMgrFsmStageEntry 5 }

cfprFabricEpMgrFsmStageName OBJECT-TYPE
    SYNTAX       CfprFabricEpMgrFsmStageName
    MAX-ACCESS   read-only
    STATUS       current
    DESCRIPTION
        "Cisco Firepower fabric:EpMgrFsmStage:name managed
        object property"
    ::= { cfprFabricEpMgrFsmStageEntry 6 }

cfprFabricEpMgrFsmStageOrder OBJECT-TYPE
    SYNTAX       Gauge32
    MAX-ACCESS   read-only
    STATUS       current
    DESCRIPTION
        "Cisco Firepower fabric:EpMgrFsmStage:order managed
        object property"
    ::= { cfprFabricEpMgrFsmStageEntry 7 }

cfprFabricEpMgrFsmStageRetry OBJECT-TYPE
    SYNTAX       Gauge32
    MAX-ACCESS   read-only
    STATUS       current
    DESCRIPTION
        "Cisco Firepower fabric:EpMgrFsmStage:retry managed
        object property"
    ::= { cfprFabricEpMgrFsmStageEntry 8 }

cfprFabricEpMgrFsmStageStageStatus OBJECT-TYPE
    SYNTAX       CfprFsmFsmStageStatus
    MAX-ACCESS   read-only
    STATUS       current
    DESCRIPTION
        "Cisco Firepower fabric:EpMgrFsmStage:stageStatus
        managed object property"
    ::= { cfprFabricEpMgrFsmStageEntry 9 }

cfprFabricEpMgrFsmTaskTable OBJECT-TYPE
    SYNTAX           SEQUENCE OF CfprFabricEpMgrFsmTaskEntry
    MAX-ACCESS       not-accessible
    STATUS           current
    DESCRIPTION
        "Cisco Firepower fabric:EpMgrFsmTask managed object table"
    ::= { cfprFabricObjects 22 }

cfprFabricEpMgrFsmTaskEntry OBJECT-TYPE
    SYNTAX           CfprFabricEpMgrFsmTaskEntry
    MAX-ACCESS       not-accessible
    STATUS           current
    DESCRIPTION
        "Entry for the cfprFabricEpMgrFsmTaskTable table."
    INDEX { cfprFabricEpMgrFsmTaskInstanceId }
    ::= { cfprFabricEpMgrFsmTaskTable 1 }

CfprFabricEpMgrFsmTaskEntry ::= SEQUENCE {
    cfprFabricEpMgrFsmTaskInstanceId                                 CfprManagedObjectId,
    cfprFabricEpMgrFsmTaskDn                                         CfprManagedObjectDn,
    cfprFabricEpMgrFsmTaskRn                                         SnmpAdminString,
    cfprFabricEpMgrFsmTaskCompletion                                 CfprFsmCompletion,
    cfprFabricEpMgrFsmTaskFlags                                      CfprFabricEpMgrFsmTaskFlags,
    cfprFabricEpMgrFsmTaskItem                                       CfprFabricEpMgrFsmTaskItem,
    cfprFabricEpMgrFsmTaskSeqId                                      Gauge32
}

cfprFabricEpMgrFsmTaskInstanceId OBJECT-TYPE
    SYNTAX       CfprManagedObjectId
    MAX-ACCESS   not-accessible
    STATUS       current
    DESCRIPTION
        "Instance identifier of the managed object."
    ::= { cfprFabricEpMgrFsmTaskEntry 1 }

cfprFabricEpMgrFsmTaskDn OBJECT-TYPE
    SYNTAX       CfprManagedObjectDn
    MAX-ACCESS   read-only
    STATUS       current
    DESCRIPTION
        "Cisco Firepower fabric:EpMgrFsmTask:dn managed object property"
    ::= { cfprFabricEpMgrFsmTaskEntry 2 }

cfprFabricEpMgrFsmTaskRn OBJECT-TYPE
    SYNTAX       SnmpAdminString
    MAX-ACCESS   read-only
    STATUS       current
    DESCRIPTION
        "Cisco Firepower fabric:EpMgrFsmTask:rn managed object property"
    ::= { cfprFabricEpMgrFsmTaskEntry 3 }

cfprFabricEpMgrFsmTaskCompletion OBJECT-TYPE
    SYNTAX       CfprFsmCompletion
    MAX-ACCESS   read-only
    STATUS       current
    DESCRIPTION
        "Cisco Firepower fabric:EpMgrFsmTask:completion
        managed object property"
    ::= { cfprFabricEpMgrFsmTaskEntry 4 }

cfprFabricEpMgrFsmTaskFlags OBJECT-TYPE
    SYNTAX       CfprFabricEpMgrFsmTaskFlags
    MAX-ACCESS   read-only
    STATUS       current
    DESCRIPTION
        "Cisco Firepower fabric:EpMgrFsmTask:flags managed
        object property"
    ::= { cfprFabricEpMgrFsmTaskEntry 5 }

cfprFabricEpMgrFsmTaskItem OBJECT-TYPE
    SYNTAX       CfprFabricEpMgrFsmTaskItem
    MAX-ACCESS   read-only
    STATUS       current
    DESCRIPTION
        "Cisco Firepower fabric:EpMgrFsmTask:item managed object property"
    ::= { cfprFabricEpMgrFsmTaskEntry 6 }

cfprFabricEpMgrFsmTaskSeqId OBJECT-TYPE
    SYNTAX       Gauge32
    MAX-ACCESS   read-only
    STATUS       current
    DESCRIPTION
        "Cisco Firepower fabric:EpMgrFsmTask:seqId managed
        object property"
    ::= { cfprFabricEpMgrFsmTaskEntry 7 }

cfprFabricEthEstcTable OBJECT-TYPE
    SYNTAX           SEQUENCE OF CfprFabricEthEstcEntry
    MAX-ACCESS       not-accessible
    STATUS           current
    DESCRIPTION
        "Cisco Firepower fabric:EthEstc managed object table"
    ::= { cfprFabricObjects 23 }

cfprFabricEthEstcEntry OBJECT-TYPE
    SYNTAX           CfprFabricEthEstcEntry
    MAX-ACCESS       not-accessible
    STATUS           current
    DESCRIPTION
        "Entry for the cfprFabricEthEstcTable table."
    INDEX { cfprFabricEthEstcInstanceId }
    ::= { cfprFabricEthEstcTable 1 }

CfprFabricEthEstcEntry ::= SEQUENCE {
    cfprFabricEthEstcInstanceId                                      CfprManagedObjectId,
    cfprFabricEthEstcDn                                              CfprManagedObjectDn,
    cfprFabricEthEstcRn                                              SnmpAdminString,
    cfprFabricEthEstcId                                              CfprNetworkSwitchId,
    cfprFabricEthEstcLocale                                          CfprFabricExternalLocale,
    cfprFabricEthEstcName                                            SnmpAdminString,
    cfprFabricEthEstcTransport                                       CfprFabricEthEstcTransport,
    cfprFabricEthEstcType                                            CfprFabricEthEstcType
}

cfprFabricEthEstcInstanceId OBJECT-TYPE
    SYNTAX       CfprManagedObjectId
    MAX-ACCESS   not-accessible
    STATUS       current
    DESCRIPTION
        "Instance identifier of the managed object."
    ::= { cfprFabricEthEstcEntry 1 }

cfprFabricEthEstcDn OBJECT-TYPE
    SYNTAX       CfprManagedObjectDn
    MAX-ACCESS   read-only
    STATUS       current
    DESCRIPTION
        "Cisco Firepower fabric:EthEstc:dn managed object property"
    ::= { cfprFabricEthEstcEntry 2 }

cfprFabricEthEstcRn OBJECT-TYPE
    SYNTAX       SnmpAdminString
    MAX-ACCESS   read-only
    STATUS       current
    DESCRIPTION
        "Cisco Firepower fabric:EthEstc:rn managed object property"
    ::= { cfprFabricEthEstcEntry 3 }

cfprFabricEthEstcId OBJECT-TYPE
    SYNTAX       CfprNetworkSwitchId
    MAX-ACCESS   read-only
    STATUS       current
    DESCRIPTION
        "Cisco Firepower fabric:EthEstc:id managed object property"
    ::= { cfprFabricEthEstcEntry 4 }

cfprFabricEthEstcLocale OBJECT-TYPE
    SYNTAX       CfprFabricExternalLocale
    MAX-ACCESS   read-only
    STATUS       current
    DESCRIPTION
        "Cisco Firepower fabric:EthEstc:locale managed object property"
    ::= { cfprFabricEthEstcEntry 5 }

cfprFabricEthEstcName OBJECT-TYPE
    SYNTAX       SnmpAdminString
    MAX-ACCESS   read-only
    STATUS       current
    DESCRIPTION
        "Cisco Firepower fabric:EthEstc:name managed object property"
    ::= { cfprFabricEthEstcEntry 6 }

cfprFabricEthEstcTransport OBJECT-TYPE
    SYNTAX       CfprFabricEthEstcTransport
    MAX-ACCESS   read-only
    STATUS       current
    DESCRIPTION
        "Cisco Firepower fabric:EthEstc:transport managed object property"
    ::= { cfprFabricEthEstcEntry 7 }

cfprFabricEthEstcType OBJECT-TYPE
    SYNTAX       CfprFabricEthEstcType
    MAX-ACCESS   read-only
    STATUS       current
    DESCRIPTION
        "Cisco Firepower fabric:EthEstc:type managed object property"
    ::= { cfprFabricEthEstcEntry 8 }

cfprFabricEthEstcCloudTable OBJECT-TYPE
    SYNTAX           SEQUENCE OF CfprFabricEthEstcCloudEntry
    MAX-ACCESS       not-accessible
    STATUS           current
    DESCRIPTION
        "Cisco Firepower fabric:EthEstcCloud managed object table"
    ::= { cfprFabricObjects 24 }

cfprFabricEthEstcCloudEntry OBJECT-TYPE
    SYNTAX           CfprFabricEthEstcCloudEntry
    MAX-ACCESS       not-accessible
    STATUS           current
    DESCRIPTION
        "Entry for the cfprFabricEthEstcCloudTable table."
    INDEX { cfprFabricEthEstcCloudInstanceId }
    ::= { cfprFabricEthEstcCloudTable 1 }

CfprFabricEthEstcCloudEntry ::= SEQUENCE {
    cfprFabricEthEstcCloudInstanceId                                 CfprManagedObjectId,
    cfprFabricEthEstcCloudDn                                         CfprManagedObjectDn,
    cfprFabricEthEstcCloudRn                                         SnmpAdminString
}

cfprFabricEthEstcCloudInstanceId OBJECT-TYPE
    SYNTAX       CfprManagedObjectId
    MAX-ACCESS   not-accessible
    STATUS       current
    DESCRIPTION
        "Instance identifier of the managed object."
    ::= { cfprFabricEthEstcCloudEntry 1 }

cfprFabricEthEstcCloudDn OBJECT-TYPE
    SYNTAX       CfprManagedObjectDn
    MAX-ACCESS   read-only
    STATUS       current
    DESCRIPTION
        "Cisco Firepower fabric:EthEstcCloud:dn managed object property"
    ::= { cfprFabricEthEstcCloudEntry 2 }

cfprFabricEthEstcCloudRn OBJECT-TYPE
    SYNTAX       SnmpAdminString
    MAX-ACCESS   read-only
    STATUS       current
    DESCRIPTION
        "Cisco Firepower fabric:EthEstcCloud:rn managed object property"
    ::= { cfprFabricEthEstcCloudEntry 3 }

cfprFabricEthEstcEpTable OBJECT-TYPE
    SYNTAX           SEQUENCE OF CfprFabricEthEstcEpEntry
    MAX-ACCESS       not-accessible
    STATUS           current
    DESCRIPTION
        "Cisco Firepower fabric:EthEstcEp managed object table"
    ::= { cfprFabricObjects 25 }

cfprFabricEthEstcEpEntry OBJECT-TYPE
    SYNTAX           CfprFabricEthEstcEpEntry
    MAX-ACCESS       not-accessible
    STATUS           current
    DESCRIPTION
        "Entry for the cfprFabricEthEstcEpTable table."
    INDEX { cfprFabricEthEstcEpInstanceId }
    ::= { cfprFabricEthEstcEpTable 1 }

CfprFabricEthEstcEpEntry ::= SEQUENCE {
    cfprFabricEthEstcEpInstanceId                                    CfprManagedObjectId,
    cfprFabricEthEstcEpDn                                            CfprManagedObjectDn,
    cfprFabricEthEstcEpRn                                            SnmpAdminString,
    cfprFabricEthEstcEpAdminSpeed                                    CfprPortEthSpeed,
    cfprFabricEthEstcEpAdminState                                    CfprFabricExternalEpAdminState,
    cfprFabricEthEstcEpAggrPortId                                    Gauge32,
    cfprFabricEthEstcEpChassisId                                     Gauge32,
    cfprFabricEthEstcEpConfigState                                   CfprFabricConfigState,
    cfprFabricEthEstcEpEpDn                                          SnmpAdminString,
    cfprFabricEthEstcEpFlowCtrlPolicy                                SnmpAdminString,
    cfprFabricEthEstcEpFltAggr                                       Unsigned64,
    cfprFabricEthEstcEpIfRole                                        CfprFabricAEthEstcEpIfRole,
    cfprFabricEthEstcEpIfType                                        CfprFabricPIoEpIfType,
    cfprFabricEthEstcEpLicGP                                         Unsigned64,
    cfprFabricEthEstcEpLicState                                      CfprLicenseState,
    cfprFabricEthEstcEpLocale                                        CfprFabricExternalEpLocale,
    cfprFabricEthEstcEpName                                          SnmpAdminString,
    cfprFabricEthEstcEpNwCtrlPolicyName                              SnmpAdminString,
    cfprFabricEthEstcEpOperNwCtrlPolicyName                          SnmpAdminString,
    cfprFabricEthEstcEpOperPortMode                                  CfprFabricEthEstcOperPortMode,
    cfprFabricEthEstcEpOperState                                     CfprFabricPIoEpOperState,
    cfprFabricEthEstcEpOperStateReason                               SnmpAdminString,
    cfprFabricEthEstcEpPeerAggrPortId                                Gauge32,
    cfprFabricEthEstcEpPeerChassisId                                 Gauge32,
    cfprFabricEthEstcEpPeerDn                                        SnmpAdminString,
    cfprFabricEthEstcEpPeerPortId                                    Gauge32,
    cfprFabricEthEstcEpPeerSlotId                                    Gauge32,
    cfprFabricEthEstcEpPinGroupName                                  SnmpAdminString,
    cfprFabricEthEstcEpPortId                                        CfprFabricEthEstcEpPortId,
    cfprFabricEthEstcEpPortMode                                      CfprFabricEthEstcPortMode,
    cfprFabricEthEstcEpPrio                                          CfprFabricEthEstcEpPrio,
    cfprFabricEthEstcEpSlotId                                        CfprFabricEthEstcEpSlotId,
    cfprFabricEthEstcEpSwitchId                                      CfprNetworkSwitchId,
    cfprFabricEthEstcEpTransport                                     CfprFabricEthEstcEpTransport,
    cfprFabricEthEstcEpType                                          CfprFabricEthEstcEpType,
    cfprFabricEthEstcEpUsrLbl                                        SnmpAdminString,
    cfprFabricEthEstcEpWarnings                                      CfprFabricWarnings
}

cfprFabricEthEstcEpInstanceId OBJECT-TYPE
    SYNTAX       CfprManagedObjectId
    MAX-ACCESS   not-accessible
    STATUS       current
    DESCRIPTION
        "Instance identifier of the managed object."
    ::= { cfprFabricEthEstcEpEntry 1 }

cfprFabricEthEstcEpDn OBJECT-TYPE
    SYNTAX       CfprManagedObjectDn
    MAX-ACCESS   read-only
    STATUS       current
    DESCRIPTION
        "Cisco Firepower fabric:EthEstcEp:dn managed object property"
    ::= { cfprFabricEthEstcEpEntry 2 }

cfprFabricEthEstcEpRn OBJECT-TYPE
    SYNTAX       SnmpAdminString
    MAX-ACCESS   read-only
    STATUS       current
    DESCRIPTION
        "Cisco Firepower fabric:EthEstcEp:rn managed object property"
    ::= { cfprFabricEthEstcEpEntry 3 }

cfprFabricEthEstcEpAdminSpeed OBJECT-TYPE
    SYNTAX       CfprPortEthSpeed
    MAX-ACCESS   read-only
    STATUS       current
    DESCRIPTION
        "Cisco Firepower fabric:EthEstcEp:adminSpeed managed
        object property"
    ::= { cfprFabricEthEstcEpEntry 4 }

cfprFabricEthEstcEpAdminState OBJECT-TYPE
    SYNTAX       CfprFabricExternalEpAdminState
    MAX-ACCESS   read-only
    STATUS       current
    DESCRIPTION
        "Cisco Firepower fabric:EthEstcEp:adminState managed
        object property"
    ::= { cfprFabricEthEstcEpEntry 5 }

cfprFabricEthEstcEpAggrPortId OBJECT-TYPE
    SYNTAX       Gauge32
    MAX-ACCESS   read-only
    STATUS       current
    DESCRIPTION
        "Cisco Firepower fabric:EthEstcEp:aggrPortId managed
        object property"
    ::= { cfprFabricEthEstcEpEntry 6 }

cfprFabricEthEstcEpChassisId OBJECT-TYPE
    SYNTAX       Gauge32
    MAX-ACCESS   read-only
    STATUS       current
    DESCRIPTION
        "Cisco Firepower fabric:EthEstcEp:chassisId managed
        object property"
    ::= { cfprFabricEthEstcEpEntry 7 }

cfprFabricEthEstcEpConfigState OBJECT-TYPE
    SYNTAX       CfprFabricConfigState
    MAX-ACCESS   read-only
    STATUS       current
    DESCRIPTION
        "Cisco Firepower fabric:EthEstcEp:configState managed
        object property"
    ::= { cfprFabricEthEstcEpEntry 8 }

cfprFabricEthEstcEpEpDn OBJECT-TYPE
    SYNTAX       SnmpAdminString
    MAX-ACCESS   read-only
    STATUS       current
    DESCRIPTION
        "Cisco Firepower fabric:EthEstcEp:epDn managed object property"
    ::= { cfprFabricEthEstcEpEntry 9 }

cfprFabricEthEstcEpFlowCtrlPolicy OBJECT-TYPE
    SYNTAX       SnmpAdminString
    MAX-ACCESS   read-only
    STATUS       current
    DESCRIPTION
        "Cisco Firepower fabric:EthEstcEp:flowCtrlPolicy
        managed object property"
    ::= { cfprFabricEthEstcEpEntry 10 }

cfprFabricEthEstcEpFltAggr OBJECT-TYPE
    SYNTAX       Unsigned64
    MAX-ACCESS   read-only
    STATUS       current
    DESCRIPTION
        "Cisco Firepower fabric:EthEstcEp:fltAggr managed object property"
    ::= { cfprFabricEthEstcEpEntry 11 }

cfprFabricEthEstcEpIfRole OBJECT-TYPE
    SYNTAX       CfprFabricAEthEstcEpIfRole
    MAX-ACCESS   read-only
    STATUS       current
    DESCRIPTION
        "Cisco Firepower fabric:EthEstcEp:ifRole managed object property"
    ::= { cfprFabricEthEstcEpEntry 12 }

cfprFabricEthEstcEpIfType OBJECT-TYPE
    SYNTAX       CfprFabricPIoEpIfType
    MAX-ACCESS   read-only
    STATUS       current
    DESCRIPTION
        "Cisco Firepower fabric:EthEstcEp:ifType managed object property"
    ::= { cfprFabricEthEstcEpEntry 13 }

cfprFabricEthEstcEpLicGP OBJECT-TYPE
    SYNTAX       Unsigned64
    MAX-ACCESS   read-only
    STATUS       current
    DESCRIPTION
        "Cisco Firepower fabric:EthEstcEp:licGP managed object property"
    ::= { cfprFabricEthEstcEpEntry 14 }

cfprFabricEthEstcEpLicState OBJECT-TYPE
    SYNTAX       CfprLicenseState
    MAX-ACCESS   read-only
    STATUS       current
    DESCRIPTION
        "Cisco Firepower fabric:EthEstcEp:licState managed
        object property"
    ::= { cfprFabricEthEstcEpEntry 15 }

cfprFabricEthEstcEpLocale OBJECT-TYPE
    SYNTAX       CfprFabricExternalEpLocale
    MAX-ACCESS   read-only
    STATUS       current
    DESCRIPTION
        "Cisco Firepower fabric:EthEstcEp:locale managed object property"
    ::= { cfprFabricEthEstcEpEntry 16 }

cfprFabricEthEstcEpName OBJECT-TYPE
    SYNTAX       SnmpAdminString
    MAX-ACCESS   read-only
    STATUS       current
    DESCRIPTION
        "Cisco Firepower fabric:EthEstcEp:name managed object property"
    ::= { cfprFabricEthEstcEpEntry 17 }

cfprFabricEthEstcEpNwCtrlPolicyName OBJECT-TYPE
    SYNTAX       SnmpAdminString
    MAX-ACCESS   read-only
    STATUS       current
    DESCRIPTION
        "Cisco Firepower fabric:EthEstcEp:nwCtrlPolicyName
        managed object property"
    ::= { cfprFabricEthEstcEpEntry 18 }

cfprFabricEthEstcEpOperNwCtrlPolicyName OBJECT-TYPE
    SYNTAX       SnmpAdminString
    MAX-ACCESS   read-only
    STATUS       current
    DESCRIPTION
        "Cisco Firepower fabric:EthEstcEp:operNwCtrlPolicyName
        managed object property"
    ::= { cfprFabricEthEstcEpEntry 19 }

cfprFabricEthEstcEpOperPortMode OBJECT-TYPE
    SYNTAX       CfprFabricEthEstcOperPortMode
    MAX-ACCESS   read-only
    STATUS       current
    DESCRIPTION
        "Cisco Firepower fabric:EthEstcEp:operPortMode
        managed object property"
    ::= { cfprFabricEthEstcEpEntry 20 }

cfprFabricEthEstcEpOperState OBJECT-TYPE
    SYNTAX       CfprFabricPIoEpOperState
    MAX-ACCESS   read-only
    STATUS       current
    DESCRIPTION
        "Cisco Firepower fabric:EthEstcEp:operState managed
        object property"
    ::= { cfprFabricEthEstcEpEntry 21 }

cfprFabricEthEstcEpOperStateReason OBJECT-TYPE
    SYNTAX       SnmpAdminString
    MAX-ACCESS   read-only
    STATUS       current
    DESCRIPTION
        "Cisco Firepower fabric:EthEstcEp:operStateReason
        managed object property"
    ::= { cfprFabricEthEstcEpEntry 22 }

cfprFabricEthEstcEpPeerAggrPortId OBJECT-TYPE
    SYNTAX       Gauge32
    MAX-ACCESS   read-only
    STATUS       current
    DESCRIPTION
        "Cisco Firepower fabric:EthEstcEp:peerAggrPortId
        managed object property"
    ::= { cfprFabricEthEstcEpEntry 23 }

cfprFabricEthEstcEpPeerChassisId OBJECT-TYPE
    SYNTAX       Gauge32
    MAX-ACCESS   read-only
    STATUS       current
    DESCRIPTION
        "Cisco Firepower fabric:EthEstcEp:peerChassisId
        managed object property"
    ::= { cfprFabricEthEstcEpEntry 24 }

cfprFabricEthEstcEpPeerDn OBJECT-TYPE
    SYNTAX       SnmpAdminString
    MAX-ACCESS   read-only
    STATUS       current
    DESCRIPTION
        "Cisco Firepower fabric:EthEstcEp:peerDn managed object property"
    ::= { cfprFabricEthEstcEpEntry 25 }

cfprFabricEthEstcEpPeerPortId OBJECT-TYPE
    SYNTAX       Gauge32
    MAX-ACCESS   read-only
    STATUS       current
    DESCRIPTION
        "Cisco Firepower fabric:EthEstcEp:peerPortId managed
        object property"
    ::= { cfprFabricEthEstcEpEntry 26 }

cfprFabricEthEstcEpPeerSlotId OBJECT-TYPE
    SYNTAX       Gauge32
    MAX-ACCESS   read-only
    STATUS       current
    DESCRIPTION
        "Cisco Firepower fabric:EthEstcEp:peerSlotId managed
        object property"
    ::= { cfprFabricEthEstcEpEntry 27 }

cfprFabricEthEstcEpPinGroupName OBJECT-TYPE
    SYNTAX       SnmpAdminString
    MAX-ACCESS   read-only
    STATUS       current
    DESCRIPTION
        "Cisco Firepower fabric:EthEstcEp:pinGroupName
        managed object property"
    ::= { cfprFabricEthEstcEpEntry 28 }

cfprFabricEthEstcEpPortId OBJECT-TYPE
    SYNTAX       CfprFabricEthEstcEpPortId
    MAX-ACCESS   read-only
    STATUS       current
    DESCRIPTION
        "Cisco Firepower fabric:EthEstcEp:portId managed object property"
    ::= { cfprFabricEthEstcEpEntry 29 }

cfprFabricEthEstcEpPortMode OBJECT-TYPE
    SYNTAX       CfprFabricEthEstcPortMode
    MAX-ACCESS   read-only
    STATUS       current
    DESCRIPTION
        "Cisco Firepower fabric:EthEstcEp:portMode managed
        object property"
    ::= { cfprFabricEthEstcEpEntry 30 }

cfprFabricEthEstcEpPrio OBJECT-TYPE
    SYNTAX       CfprFabricEthEstcEpPrio
    MAX-ACCESS   read-only
    STATUS       current
    DESCRIPTION
        "Cisco Firepower fabric:EthEstcEp:prio managed object property"
    ::= { cfprFabricEthEstcEpEntry 31 }

cfprFabricEthEstcEpSlotId OBJECT-TYPE
    SYNTAX       CfprFabricEthEstcEpSlotId
    MAX-ACCESS   read-only
    STATUS       current
    DESCRIPTION
        "Cisco Firepower fabric:EthEstcEp:slotId managed object property"
    ::= { cfprFabricEthEstcEpEntry 32 }

cfprFabricEthEstcEpSwitchId OBJECT-TYPE
    SYNTAX       CfprNetworkSwitchId
    MAX-ACCESS   read-only
    STATUS       current
    DESCRIPTION
        "Cisco Firepower fabric:EthEstcEp:switchId managed
        object property"
    ::= { cfprFabricEthEstcEpEntry 33 }

cfprFabricEthEstcEpTransport OBJECT-TYPE
    SYNTAX       CfprFabricEthEstcEpTransport
    MAX-ACCESS   read-only
    STATUS       current
    DESCRIPTION
        "Cisco Firepower fabric:EthEstcEp:transport managed
        object property"
    ::= { cfprFabricEthEstcEpEntry 34 }

cfprFabricEthEstcEpType OBJECT-TYPE
    SYNTAX       CfprFabricEthEstcEpType
    MAX-ACCESS   read-only
    STATUS       current
    DESCRIPTION
        "Cisco Firepower fabric:EthEstcEp:type managed object property"
    ::= { cfprFabricEthEstcEpEntry 35 }

cfprFabricEthEstcEpUsrLbl OBJECT-TYPE
    SYNTAX       SnmpAdminString
    MAX-ACCESS   read-only
    STATUS       current
    DESCRIPTION
        "Cisco Firepower fabric:EthEstcEp:usrLbl managed object property"
    ::= { cfprFabricEthEstcEpEntry 36 }

cfprFabricEthEstcEpWarnings OBJECT-TYPE
    SYNTAX       CfprFabricWarnings
    MAX-ACCESS   read-only
    STATUS       current
    DESCRIPTION
        "Cisco Firepower fabric:EthEstcEp:warnings managed
        object property"
    ::= { cfprFabricEthEstcEpEntry 37 }

cfprFabricEthEstcPcTable OBJECT-TYPE
    SYNTAX           SEQUENCE OF CfprFabricEthEstcPcEntry
    MAX-ACCESS       not-accessible
    STATUS           current
    DESCRIPTION
        "Cisco Firepower fabric:EthEstcPc managed object table"
    ::= { cfprFabricObjects 26 }

cfprFabricEthEstcPcEntry OBJECT-TYPE
    SYNTAX           CfprFabricEthEstcPcEntry
    MAX-ACCESS       not-accessible
    STATUS           current
    DESCRIPTION
        "Entry for the cfprFabricEthEstcPcTable table."
    INDEX { cfprFabricEthEstcPcInstanceId }
    ::= { cfprFabricEthEstcPcTable 1 }

CfprFabricEthEstcPcEntry ::= SEQUENCE {
    cfprFabricEthEstcPcInstanceId                                    CfprManagedObjectId,
    cfprFabricEthEstcPcDn                                            CfprManagedObjectDn,
    cfprFabricEthEstcPcRn                                            SnmpAdminString,
    cfprFabricEthEstcPcAdminSpeed                                    CfprPortEthAdminSpeed,
    cfprFabricEthEstcPcAdminState                                    CfprFabricCIoEpAdminState,
    cfprFabricEthEstcPcDescr                                         SnmpAdminString,
    cfprFabricEthEstcPcEpDn                                          SnmpAdminString,
    cfprFabricEthEstcPcFlowCtrlPolicy                                SnmpAdminString,
    cfprFabricEthEstcPcFltAggr                                       Unsigned64,
    cfprFabricEthEstcPcIfRole                                        CfprFabricEstcPcIfRole,
    cfprFabricEthEstcPcIfType                                        CfprFabricCIoEpIfType,
    cfprFabricEthEstcPcLacpPolicyName                                SnmpAdminString,
    cfprFabricEthEstcPcLocale                                        CfprFabricExternalPcLocale,
    cfprFabricEthEstcPcName                                          SnmpAdminString,
    cfprFabricEthEstcPcNwCtrlPolicyName                              SnmpAdminString,
    cfprFabricEthEstcPcOperLacpPolicyName                            SnmpAdminString,
    cfprFabricEthEstcPcOperNwCtrlPolicyName                          SnmpAdminString,
    cfprFabricEthEstcPcOperSpeed                                     CfprPortEthSpeed,
    cfprFabricEthEstcPcOperState                                     CfprNetworkPortOperState,
    cfprFabricEthEstcPcPeerDn                                        SnmpAdminString,
    cfprFabricEthEstcPcPinGroupName                                  SnmpAdminString,
    cfprFabricEthEstcPcPortId                                        Gauge32,
    cfprFabricEthEstcPcPortMode                                      CfprFabricEthEstcPortMode,
    cfprFabricEthEstcPcPrio                                          CfprQosPriority,
    cfprFabricEthEstcPcProtocol                                      CfprFabricEthPcProtocol,
    cfprFabricEthEstcPcStateQual                                     SnmpAdminString,
    cfprFabricEthEstcPcSwitchId                                      CfprNetworkSwitchId,
    cfprFabricEthEstcPcTransport                                     CfprFabricEthEstcPcTransport,
    cfprFabricEthEstcPcType                                          CfprFabricEstcPcType,
    cfprFabricEthEstcPcWarnings                                      CfprFabricWarnings
}

cfprFabricEthEstcPcInstanceId OBJECT-TYPE
    SYNTAX       CfprManagedObjectId
    MAX-ACCESS   not-accessible
    STATUS       current
    DESCRIPTION
        "Instance identifier of the managed object."
    ::= { cfprFabricEthEstcPcEntry 1 }

cfprFabricEthEstcPcDn OBJECT-TYPE
    SYNTAX       CfprManagedObjectDn
    MAX-ACCESS   read-only
    STATUS       current
    DESCRIPTION
        "Cisco Firepower fabric:EthEstcPc:dn managed object property"
    ::= { cfprFabricEthEstcPcEntry 2 }

cfprFabricEthEstcPcRn OBJECT-TYPE
    SYNTAX       SnmpAdminString
    MAX-ACCESS   read-only
    STATUS       current
    DESCRIPTION
        "Cisco Firepower fabric:EthEstcPc:rn managed object property"
    ::= { cfprFabricEthEstcPcEntry 3 }

cfprFabricEthEstcPcAdminSpeed OBJECT-TYPE
    SYNTAX       CfprPortEthAdminSpeed
    MAX-ACCESS   read-only
    STATUS       current
    DESCRIPTION
        "Cisco Firepower fabric:EthEstcPc:adminSpeed managed
        object property"
    ::= { cfprFabricEthEstcPcEntry 4 }

cfprFabricEthEstcPcAdminState OBJECT-TYPE
    SYNTAX       CfprFabricCIoEpAdminState
    MAX-ACCESS   read-only
    STATUS       current
    DESCRIPTION
        "Cisco Firepower fabric:EthEstcPc:adminState managed
        object property"
    ::= { cfprFabricEthEstcPcEntry 5 }

cfprFabricEthEstcPcDescr OBJECT-TYPE
    SYNTAX       SnmpAdminString
    MAX-ACCESS   read-only
    STATUS       current
    DESCRIPTION
        "Cisco Firepower fabric:EthEstcPc:descr managed object property"
    ::= { cfprFabricEthEstcPcEntry 6 }

cfprFabricEthEstcPcEpDn OBJECT-TYPE
    SYNTAX       SnmpAdminString
    MAX-ACCESS   read-only
    STATUS       current
    DESCRIPTION
        "Cisco Firepower fabric:EthEstcPc:epDn managed object property"
    ::= { cfprFabricEthEstcPcEntry 7 }

cfprFabricEthEstcPcFlowCtrlPolicy OBJECT-TYPE
    SYNTAX       SnmpAdminString
    MAX-ACCESS   read-only
    STATUS       current
    DESCRIPTION
        "Cisco Firepower fabric:EthEstcPc:flowCtrlPolicy
        managed object property"
    ::= { cfprFabricEthEstcPcEntry 8 }

cfprFabricEthEstcPcFltAggr OBJECT-TYPE
    SYNTAX       Unsigned64
    MAX-ACCESS   read-only
    STATUS       current
    DESCRIPTION
        "Cisco Firepower fabric:EthEstcPc:fltAggr managed object property"
    ::= { cfprFabricEthEstcPcEntry 9 }

cfprFabricEthEstcPcIfRole OBJECT-TYPE
    SYNTAX       CfprFabricEstcPcIfRole
    MAX-ACCESS   read-only
    STATUS       current
    DESCRIPTION
        "Cisco Firepower fabric:EthEstcPc:ifRole managed object property"
    ::= { cfprFabricEthEstcPcEntry 10 }

cfprFabricEthEstcPcIfType OBJECT-TYPE
    SYNTAX       CfprFabricCIoEpIfType
    MAX-ACCESS   read-only
    STATUS       current
    DESCRIPTION
        "Cisco Firepower fabric:EthEstcPc:ifType managed object property"
    ::= { cfprFabricEthEstcPcEntry 11 }

cfprFabricEthEstcPcLacpPolicyName OBJECT-TYPE
    SYNTAX       SnmpAdminString
    MAX-ACCESS   read-only
    STATUS       current
    DESCRIPTION
        "Cisco Firepower fabric:EthEstcPc:lacpPolicyName
        managed object property"
    ::= { cfprFabricEthEstcPcEntry 12 }

cfprFabricEthEstcPcLocale OBJECT-TYPE
    SYNTAX       CfprFabricExternalPcLocale
    MAX-ACCESS   read-only
    STATUS       current
    DESCRIPTION
        "Cisco Firepower fabric:EthEstcPc:locale managed object property"
    ::= { cfprFabricEthEstcPcEntry 13 }

cfprFabricEthEstcPcName OBJECT-TYPE
    SYNTAX       SnmpAdminString
    MAX-ACCESS   read-only
    STATUS       current
    DESCRIPTION
        "Cisco Firepower fabric:EthEstcPc:name managed object property"
    ::= { cfprFabricEthEstcPcEntry 14 }

cfprFabricEthEstcPcNwCtrlPolicyName OBJECT-TYPE
    SYNTAX       SnmpAdminString
    MAX-ACCESS   read-only
    STATUS       current
    DESCRIPTION
        "Cisco Firepower fabric:EthEstcPc:nwCtrlPolicyName
        managed object property"
    ::= { cfprFabricEthEstcPcEntry 15 }

cfprFabricEthEstcPcOperLacpPolicyName OBJECT-TYPE
    SYNTAX       SnmpAdminString
    MAX-ACCESS   read-only
    STATUS       current
    DESCRIPTION
        "Cisco Firepower fabric:EthEstcPc:operLacpPolicyName
        managed object property"
    ::= { cfprFabricEthEstcPcEntry 16 }

cfprFabricEthEstcPcOperNwCtrlPolicyName OBJECT-TYPE
    SYNTAX       SnmpAdminString
    MAX-ACCESS   read-only
    STATUS       current
    DESCRIPTION
        "Cisco Firepower fabric:EthEstcPc:operNwCtrlPolicyName
        managed object property"
    ::= { cfprFabricEthEstcPcEntry 17 }

cfprFabricEthEstcPcOperSpeed OBJECT-TYPE
    SYNTAX       CfprPortEthSpeed
    MAX-ACCESS   read-only
    STATUS       current
    DESCRIPTION
        "Cisco Firepower fabric:EthEstcPc:operSpeed managed
        object property"
    ::= { cfprFabricEthEstcPcEntry 18 }

cfprFabricEthEstcPcOperState OBJECT-TYPE
    SYNTAX       CfprNetworkPortOperState
    MAX-ACCESS   read-only
    STATUS       current
    DESCRIPTION
        "Cisco Firepower fabric:EthEstcPc:operState managed
        object property"
    ::= { cfprFabricEthEstcPcEntry 19 }

cfprFabricEthEstcPcPeerDn OBJECT-TYPE
    SYNTAX       SnmpAdminString
    MAX-ACCESS   read-only
    STATUS       current
    DESCRIPTION
        "Cisco Firepower fabric:EthEstcPc:peerDn managed object property"
    ::= { cfprFabricEthEstcPcEntry 20 }

cfprFabricEthEstcPcPinGroupName OBJECT-TYPE
    SYNTAX       SnmpAdminString
    MAX-ACCESS   read-only
    STATUS       current
    DESCRIPTION
        "Cisco Firepower fabric:EthEstcPc:pinGroupName
        managed object property"
    ::= { cfprFabricEthEstcPcEntry 21 }

cfprFabricEthEstcPcPortId OBJECT-TYPE
    SYNTAX       Gauge32
    MAX-ACCESS   read-only
    STATUS       current
    DESCRIPTION
        "Cisco Firepower fabric:EthEstcPc:portId managed object property"
    ::= { cfprFabricEthEstcPcEntry 22 }

cfprFabricEthEstcPcPortMode OBJECT-TYPE
    SYNTAX       CfprFabricEthEstcPortMode
    MAX-ACCESS   read-only
    STATUS       current
    DESCRIPTION
        "Cisco Firepower fabric:EthEstcPc:portMode managed
        object property"
    ::= { cfprFabricEthEstcPcEntry 23 }

cfprFabricEthEstcPcPrio OBJECT-TYPE
    SYNTAX       CfprQosPriority
    MAX-ACCESS   read-only
    STATUS       current
    DESCRIPTION
        "Cisco Firepower fabric:EthEstcPc:prio managed object property"
    ::= { cfprFabricEthEstcPcEntry 24 }

cfprFabricEthEstcPcProtocol OBJECT-TYPE
    SYNTAX       CfprFabricEthPcProtocol
    MAX-ACCESS   read-only
    STATUS       current
    DESCRIPTION
        "Cisco Firepower fabric:EthEstcPc:protocol managed
        object property"
    ::= { cfprFabricEthEstcPcEntry 25 }

cfprFabricEthEstcPcStateQual OBJECT-TYPE
    SYNTAX       SnmpAdminString
    MAX-ACCESS   read-only
    STATUS       current
    DESCRIPTION
        "Cisco Firepower fabric:EthEstcPc:stateQual managed
        object property"
    ::= { cfprFabricEthEstcPcEntry 26 }

cfprFabricEthEstcPcSwitchId OBJECT-TYPE
    SYNTAX       CfprNetworkSwitchId
    MAX-ACCESS   read-only
    STATUS       current
    DESCRIPTION
        "Cisco Firepower fabric:EthEstcPc:switchId managed
        object property"
    ::= { cfprFabricEthEstcPcEntry 27 }

cfprFabricEthEstcPcTransport OBJECT-TYPE
    SYNTAX       CfprFabricEthEstcPcTransport
    MAX-ACCESS   read-only
    STATUS       current
    DESCRIPTION
        "Cisco Firepower fabric:EthEstcPc:transport managed
        object property"
    ::= { cfprFabricEthEstcPcEntry 28 }

cfprFabricEthEstcPcType OBJECT-TYPE
    SYNTAX       CfprFabricEstcPcType
    MAX-ACCESS   read-only
    STATUS       current
    DESCRIPTION
        "Cisco Firepower fabric:EthEstcPc:type managed object property"
    ::= { cfprFabricEthEstcPcEntry 29 }

cfprFabricEthEstcPcWarnings OBJECT-TYPE
    SYNTAX       CfprFabricWarnings
    MAX-ACCESS   read-only
    STATUS       current
    DESCRIPTION
        "Cisco Firepower fabric:EthEstcPc:warnings managed
        object property"
    ::= { cfprFabricEthEstcPcEntry 30 }

cfprFabricEthEstcPcEpTable OBJECT-TYPE
    SYNTAX           SEQUENCE OF CfprFabricEthEstcPcEpEntry
    MAX-ACCESS       not-accessible
    STATUS           current
    DESCRIPTION
        "Cisco Firepower fabric:EthEstcPcEp managed object table"
    ::= { cfprFabricObjects 27 }

cfprFabricEthEstcPcEpEntry OBJECT-TYPE
    SYNTAX           CfprFabricEthEstcPcEpEntry
    MAX-ACCESS       not-accessible
    STATUS           current
    DESCRIPTION
        "Entry for the cfprFabricEthEstcPcEpTable table."
    INDEX { cfprFabricEthEstcPcEpInstanceId }
    ::= { cfprFabricEthEstcPcEpTable 1 }

CfprFabricEthEstcPcEpEntry ::= SEQUENCE {
    cfprFabricEthEstcPcEpInstanceId                                  CfprManagedObjectId,
    cfprFabricEthEstcPcEpDnData                                      CfprManagedObjectDn,
    cfprFabricEthEstcPcEpRn                                          SnmpAdminString,
    cfprFabricEthEstcPcEpAdminSpeed                                  CfprPortSpeed,
    cfprFabricEthEstcPcEpAdminState                                  CfprFabricExternalEpAdminState,
    cfprFabricEthEstcPcEpAggrPortId                                  Gauge32,
    cfprFabricEthEstcPcEpChassisId                                   Gauge32,
    cfprFabricEthEstcPcEpConfigState                                 CfprFabricConfigState,
    cfprFabricEthEstcPcEpEpDn                                        SnmpAdminString,
    cfprFabricEthEstcPcEpFltAggr                                     Unsigned64,
    cfprFabricEthEstcPcEpIfRole                                      CfprFabricAEthEstcEpIfRole,
    cfprFabricEthEstcPcEpIfType                                      CfprFabricPIoEpIfType,
    cfprFabricEthEstcPcEpLicGP                                       Unsigned64,
    cfprFabricEthEstcPcEpLicState                                    CfprLicenseState,
    cfprFabricEthEstcPcEpLocale                                      CfprFabricExternalEpLocale,
    cfprFabricEthEstcPcEpMembership                                  CfprFabricMembershipStatus,
    cfprFabricEthEstcPcEpName                                        SnmpAdminString,
    cfprFabricEthEstcPcEpOperState                                   CfprFabricPIoEpOperState,
    cfprFabricEthEstcPcEpOperStateReason                             SnmpAdminString,
    cfprFabricEthEstcPcEpPeerAggrPortId                              Gauge32,
    cfprFabricEthEstcPcEpPeerChassisId                               Gauge32,
    cfprFabricEthEstcPcEpPeerDn                                      SnmpAdminString,
    cfprFabricEthEstcPcEpPeerPortId                                  Gauge32,
    cfprFabricEthEstcPcEpPeerSlotId                                  Gauge32,
    cfprFabricEthEstcPcEpPortId                                      CfprFabricEthEstcPcEpPortId,
    cfprFabricEthEstcPcEpSlotId                                      CfprFabricEthEstcPcEpSlotId,
    cfprFabricEthEstcPcEpSwitchId                                    CfprNetworkSwitchId,
    cfprFabricEthEstcPcEpTransport                                   CfprFabricAEthEstcEpTransport,
    cfprFabricEthEstcPcEpType                                        CfprFabricAEthEstcEpType,
    cfprFabricEthEstcPcEpUsrLbl                                      SnmpAdminString,
    cfprFabricEthEstcPcEpWarnings                                    CfprFabricWarnings
}

cfprFabricEthEstcPcEpInstanceId OBJECT-TYPE
    SYNTAX       CfprManagedObjectId
    MAX-ACCESS   not-accessible
    STATUS       current
    DESCRIPTION
        "Instance identifier of the managed object."
    ::= { cfprFabricEthEstcPcEpEntry 1 }

cfprFabricEthEstcPcEpDnData OBJECT-TYPE
    SYNTAX       CfprManagedObjectDn
    MAX-ACCESS   read-only
    STATUS       current
    DESCRIPTION
        "Cisco Firepower fabric:EthEstcPcEp:dn managed object property"
    ::= { cfprFabricEthEstcPcEpEntry 2 }

cfprFabricEthEstcPcEpRn OBJECT-TYPE
    SYNTAX       SnmpAdminString
    MAX-ACCESS   read-only
    STATUS       current
    DESCRIPTION
        "Cisco Firepower fabric:EthEstcPcEp:rn managed object property"
    ::= { cfprFabricEthEstcPcEpEntry 3 }

cfprFabricEthEstcPcEpAdminSpeed OBJECT-TYPE
    SYNTAX       CfprPortSpeed
    MAX-ACCESS   read-only
    STATUS       current
    DESCRIPTION
        "Cisco Firepower fabric:EthEstcPcEp:adminSpeed
        managed object property"
    ::= { cfprFabricEthEstcPcEpEntry 4 }

cfprFabricEthEstcPcEpAdminState OBJECT-TYPE
    SYNTAX       CfprFabricExternalEpAdminState
    MAX-ACCESS   read-only
    STATUS       current
    DESCRIPTION
        "Cisco Firepower fabric:EthEstcPcEp:adminState
        managed object property"
    ::= { cfprFabricEthEstcPcEpEntry 5 }

cfprFabricEthEstcPcEpAggrPortId OBJECT-TYPE
    SYNTAX       Gauge32
    MAX-ACCESS   read-only
    STATUS       current
    DESCRIPTION
        "Cisco Firepower fabric:EthEstcPcEp:aggrPortId
        managed object property"
    ::= { cfprFabricEthEstcPcEpEntry 6 }

cfprFabricEthEstcPcEpChassisId OBJECT-TYPE
    SYNTAX       Gauge32
    MAX-ACCESS   read-only
    STATUS       current
    DESCRIPTION
        "Cisco Firepower fabric:EthEstcPcEp:chassisId managed
        object property"
    ::= { cfprFabricEthEstcPcEpEntry 7 }

cfprFabricEthEstcPcEpConfigState OBJECT-TYPE
    SYNTAX       CfprFabricConfigState
    MAX-ACCESS   read-only
    STATUS       current
    DESCRIPTION
        "Cisco Firepower fabric:EthEstcPcEp:configState
        managed object property"
    ::= { cfprFabricEthEstcPcEpEntry 8 }

cfprFabricEthEstcPcEpEpDn OBJECT-TYPE
    SYNTAX       SnmpAdminString
    MAX-ACCESS   read-only
    STATUS       current
    DESCRIPTION
        "Cisco Firepower fabric:EthEstcPcEp:epDn managed object property"
    ::= { cfprFabricEthEstcPcEpEntry 9 }

cfprFabricEthEstcPcEpFltAggr OBJECT-TYPE
    SYNTAX       Unsigned64
    MAX-ACCESS   read-only
    STATUS       current
    DESCRIPTION
        "Cisco Firepower fabric:EthEstcPcEp:fltAggr managed
        object property"
    ::= { cfprFabricEthEstcPcEpEntry 10 }

cfprFabricEthEstcPcEpIfRole OBJECT-TYPE
    SYNTAX       CfprFabricAEthEstcEpIfRole
    MAX-ACCESS   read-only
    STATUS       current
    DESCRIPTION
        "Cisco Firepower fabric:EthEstcPcEp:ifRole managed
        object property"
    ::= { cfprFabricEthEstcPcEpEntry 11 }

cfprFabricEthEstcPcEpIfType OBJECT-TYPE
    SYNTAX       CfprFabricPIoEpIfType
    MAX-ACCESS   read-only
    STATUS       current
    DESCRIPTION
        "Cisco Firepower fabric:EthEstcPcEp:ifType managed
        object property"
    ::= { cfprFabricEthEstcPcEpEntry 12 }

cfprFabricEthEstcPcEpLicGP OBJECT-TYPE
    SYNTAX       Unsigned64
    MAX-ACCESS   read-only
    STATUS       current
    DESCRIPTION
        "Cisco Firepower fabric:EthEstcPcEp:licGP managed object property"
    ::= { cfprFabricEthEstcPcEpEntry 13 }

cfprFabricEthEstcPcEpLicState OBJECT-TYPE
    SYNTAX       CfprLicenseState
    MAX-ACCESS   read-only
    STATUS       current
    DESCRIPTION
        "Cisco Firepower fabric:EthEstcPcEp:licState managed
        object property"
    ::= { cfprFabricEthEstcPcEpEntry 14 }

cfprFabricEthEstcPcEpLocale OBJECT-TYPE
    SYNTAX       CfprFabricExternalEpLocale
    MAX-ACCESS   read-only
    STATUS       current
    DESCRIPTION
        "Cisco Firepower fabric:EthEstcPcEp:locale managed
        object property"
    ::= { cfprFabricEthEstcPcEpEntry 15 }

cfprFabricEthEstcPcEpMembership OBJECT-TYPE
    SYNTAX       CfprFabricMembershipStatus
    MAX-ACCESS   read-only
    STATUS       current
    DESCRIPTION
        "Cisco Firepower fabric:EthEstcPcEp:membership
        managed object property"
    ::= { cfprFabricEthEstcPcEpEntry 16 }

cfprFabricEthEstcPcEpName OBJECT-TYPE
    SYNTAX       SnmpAdminString
    MAX-ACCESS   read-only
    STATUS       current
    DESCRIPTION
        "Cisco Firepower fabric:EthEstcPcEp:name managed object property"
    ::= { cfprFabricEthEstcPcEpEntry 17 }

cfprFabricEthEstcPcEpOperState OBJECT-TYPE
    SYNTAX       CfprFabricPIoEpOperState
    MAX-ACCESS   read-only
    STATUS       current
    DESCRIPTION
        "Cisco Firepower fabric:EthEstcPcEp:operState managed
        object property"
    ::= { cfprFabricEthEstcPcEpEntry 18 }

cfprFabricEthEstcPcEpOperStateReason OBJECT-TYPE
    SYNTAX       SnmpAdminString
    MAX-ACCESS   read-only
    STATUS       current
    DESCRIPTION
        "Cisco Firepower fabric:EthEstcPcEp:operStateReason
        managed object property"
    ::= { cfprFabricEthEstcPcEpEntry 19 }

cfprFabricEthEstcPcEpPeerAggrPortId OBJECT-TYPE
    SYNTAX       Gauge32
    MAX-ACCESS   read-only
    STATUS       current
    DESCRIPTION
        "Cisco Firepower fabric:EthEstcPcEp:peerAggrPortId
        managed object property"
    ::= { cfprFabricEthEstcPcEpEntry 20 }

cfprFabricEthEstcPcEpPeerChassisId OBJECT-TYPE
    SYNTAX       Gauge32
    MAX-ACCESS   read-only
    STATUS       current
    DESCRIPTION
        "Cisco Firepower fabric:EthEstcPcEp:peerChassisId
        managed object property"
    ::= { cfprFabricEthEstcPcEpEntry 21 }

cfprFabricEthEstcPcEpPeerDn OBJECT-TYPE
    SYNTAX       SnmpAdminString
    MAX-ACCESS   read-only
    STATUS       current
    DESCRIPTION
        "Cisco Firepower fabric:EthEstcPcEp:peerDn managed
        object property"
    ::= { cfprFabricEthEstcPcEpEntry 22 }

cfprFabricEthEstcPcEpPeerPortId OBJECT-TYPE
    SYNTAX       Gauge32
    MAX-ACCESS   read-only
    STATUS       current
    DESCRIPTION
        "Cisco Firepower fabric:EthEstcPcEp:peerPortId
        managed object property"
    ::= { cfprFabricEthEstcPcEpEntry 23 }

cfprFabricEthEstcPcEpPeerSlotId OBJECT-TYPE
    SYNTAX       Gauge32
    MAX-ACCESS   read-only
    STATUS       current
    DESCRIPTION
        "Cisco Firepower fabric:EthEstcPcEp:peerSlotId
        managed object property"
    ::= { cfprFabricEthEstcPcEpEntry 24 }

cfprFabricEthEstcPcEpPortId OBJECT-TYPE
    SYNTAX       CfprFabricEthEstcPcEpPortId
    MAX-ACCESS   read-only
    STATUS       current
    DESCRIPTION
        "Cisco Firepower fabric:EthEstcPcEp:portId managed
        object property"
    ::= { cfprFabricEthEstcPcEpEntry 25 }

cfprFabricEthEstcPcEpSlotId OBJECT-TYPE
    SYNTAX       CfprFabricEthEstcPcEpSlotId
    MAX-ACCESS   read-only
    STATUS       current
    DESCRIPTION
        "Cisco Firepower fabric:EthEstcPcEp:slotId managed
        object property"
    ::= { cfprFabricEthEstcPcEpEntry 26 }

cfprFabricEthEstcPcEpSwitchId OBJECT-TYPE
    SYNTAX       CfprNetworkSwitchId
    MAX-ACCESS   read-only
    STATUS       current
    DESCRIPTION
        "Cisco Firepower fabric:EthEstcPcEp:switchId managed
        object property"
    ::= { cfprFabricEthEstcPcEpEntry 27 }

cfprFabricEthEstcPcEpTransport OBJECT-TYPE
    SYNTAX       CfprFabricAEthEstcEpTransport
    MAX-ACCESS   read-only
    STATUS       current
    DESCRIPTION
        "Cisco Firepower fabric:EthEstcPcEp:transport managed
        object property"
    ::= { cfprFabricEthEstcPcEpEntry 28 }

cfprFabricEthEstcPcEpType OBJECT-TYPE
    SYNTAX       CfprFabricAEthEstcEpType
    MAX-ACCESS   read-only
    STATUS       current
    DESCRIPTION
        "Cisco Firepower fabric:EthEstcPcEp:type managed object property"
    ::= { cfprFabricEthEstcPcEpEntry 29 }

cfprFabricEthEstcPcEpUsrLbl OBJECT-TYPE
    SYNTAX       SnmpAdminString
    MAX-ACCESS   read-only
    STATUS       current
    DESCRIPTION
        "Cisco Firepower fabric:EthEstcPcEp:usrLbl managed
        object property"
    ::= { cfprFabricEthEstcPcEpEntry 30 }

cfprFabricEthEstcPcEpWarnings OBJECT-TYPE
    SYNTAX       CfprFabricWarnings
    MAX-ACCESS   read-only
    STATUS       current
    DESCRIPTION
        "Cisco Firepower fabric:EthEstcPcEp:warnings managed
        object property"
    ::= { cfprFabricEthEstcPcEpEntry 31 }

cfprFabricEthFlowMonLanTable OBJECT-TYPE
    SYNTAX           SEQUENCE OF CfprFabricEthFlowMonLanEntry
    MAX-ACCESS       not-accessible
    STATUS           current
    DESCRIPTION
        "Cisco Firepower fabric:EthFlowMonLan managed object table"
    ::= { cfprFabricObjects 28 }

cfprFabricEthFlowMonLanEntry OBJECT-TYPE
    SYNTAX           CfprFabricEthFlowMonLanEntry
    MAX-ACCESS       not-accessible
    STATUS           current
    DESCRIPTION
        "Entry for the cfprFabricEthFlowMonLanTable table."
    INDEX { cfprFabricEthFlowMonLanInstanceId }
    ::= { cfprFabricEthFlowMonLanTable 1 }

CfprFabricEthFlowMonLanEntry ::= SEQUENCE {
    cfprFabricEthFlowMonLanInstanceId                                CfprManagedObjectId,
    cfprFabricEthFlowMonLanDn                                        CfprManagedObjectDn,
    cfprFabricEthFlowMonLanRn                                        SnmpAdminString,
    cfprFabricEthFlowMonLanExporterSourceMac                         MacAddress,
    cfprFabricEthFlowMonLanId                                        CfprNetworkSwitchId,
    cfprFabricEthFlowMonLanLocale                                    CfprFabricExternalLocale,
    cfprFabricEthFlowMonLanName                                      SnmpAdminString,
    cfprFabricEthFlowMonLanTransport                                 CfprFabricEthFlowMonLanTransport,
    cfprFabricEthFlowMonLanType                                      CfprFabricEthFlowMonLanType
}

cfprFabricEthFlowMonLanInstanceId OBJECT-TYPE
    SYNTAX       CfprManagedObjectId
    MAX-ACCESS   not-accessible
    STATUS       current
    DESCRIPTION
        "Instance identifier of the managed object."
    ::= { cfprFabricEthFlowMonLanEntry 1 }

cfprFabricEthFlowMonLanDn OBJECT-TYPE
    SYNTAX       CfprManagedObjectDn
    MAX-ACCESS   read-only
    STATUS       current
    DESCRIPTION
        "Cisco Firepower fabric:EthFlowMonLan:dn managed object property"
    ::= { cfprFabricEthFlowMonLanEntry 2 }

cfprFabricEthFlowMonLanRn OBJECT-TYPE
    SYNTAX       SnmpAdminString
    MAX-ACCESS   read-only
    STATUS       current
    DESCRIPTION
        "Cisco Firepower fabric:EthFlowMonLan:rn managed object property"
    ::= { cfprFabricEthFlowMonLanEntry 3 }

cfprFabricEthFlowMonLanExporterSourceMac OBJECT-TYPE
    SYNTAX       MacAddress
    MAX-ACCESS   read-only
    STATUS       current
    DESCRIPTION
        "Cisco Firepower fabric:EthFlowMonLan:exporterSourceMac
        managed object property"
    ::= { cfprFabricEthFlowMonLanEntry 4 }

cfprFabricEthFlowMonLanId OBJECT-TYPE
    SYNTAX       CfprNetworkSwitchId
    MAX-ACCESS   read-only
    STATUS       current
    DESCRIPTION
        "Cisco Firepower fabric:EthFlowMonLan:id managed object property"
    ::= { cfprFabricEthFlowMonLanEntry 5 }

cfprFabricEthFlowMonLanLocale OBJECT-TYPE
    SYNTAX       CfprFabricExternalLocale
    MAX-ACCESS   read-only
    STATUS       current
    DESCRIPTION
        "Cisco Firepower fabric:EthFlowMonLan:locale managed
        object property"
    ::= { cfprFabricEthFlowMonLanEntry 6 }

cfprFabricEthFlowMonLanName OBJECT-TYPE
    SYNTAX       SnmpAdminString
    MAX-ACCESS   read-only
    STATUS       current
    DESCRIPTION
        "Cisco Firepower fabric:EthFlowMonLan:name managed
        object property"
    ::= { cfprFabricEthFlowMonLanEntry 7 }

cfprFabricEthFlowMonLanTransport OBJECT-TYPE
    SYNTAX       CfprFabricEthFlowMonLanTransport
    MAX-ACCESS   read-only
    STATUS       current
    DESCRIPTION
        "Cisco Firepower fabric:EthFlowMonLan:transport
        managed object property"
    ::= { cfprFabricEthFlowMonLanEntry 8 }

cfprFabricEthFlowMonLanType OBJECT-TYPE
    SYNTAX       CfprFabricEthFlowMonLanType
    MAX-ACCESS   read-only
    STATUS       current
    DESCRIPTION
        "Cisco Firepower fabric:EthFlowMonLan:type managed
        object property"
    ::= { cfprFabricEthFlowMonLanEntry 9 }

cfprFabricEthLanTable OBJECT-TYPE
    SYNTAX           SEQUENCE OF CfprFabricEthLanEntry
    MAX-ACCESS       not-accessible
    STATUS           current
    DESCRIPTION
        "Cisco Firepower fabric:EthLan managed object table"
    ::= { cfprFabricObjects 29 }

cfprFabricEthLanEntry OBJECT-TYPE
    SYNTAX           CfprFabricEthLanEntry
    MAX-ACCESS       not-accessible
    STATUS           current
    DESCRIPTION
        "Entry for the cfprFabricEthLanTable table."
    INDEX { cfprFabricEthLanInstanceId }
    ::= { cfprFabricEthLanTable 1 }

CfprFabricEthLanEntry ::= SEQUENCE {
    cfprFabricEthLanInstanceId                                       CfprManagedObjectId,
    cfprFabricEthLanDn                                               CfprManagedObjectDn,
    cfprFabricEthLanRn                                               SnmpAdminString,
    cfprFabricEthLanId                                               CfprNetworkSwitchId,
    cfprFabricEthLanLocale                                           CfprFabricExternalLocale,
    cfprFabricEthLanName                                             SnmpAdminString,
    cfprFabricEthLanTransport                                        CfprFabricEthLanTransport,
    cfprFabricEthLanType                                             CfprFabricLanType
}

cfprFabricEthLanInstanceId OBJECT-TYPE
    SYNTAX       CfprManagedObjectId
    MAX-ACCESS   not-accessible
    STATUS       current
    DESCRIPTION
        "Instance identifier of the managed object."
    ::= { cfprFabricEthLanEntry 1 }

cfprFabricEthLanDn OBJECT-TYPE
    SYNTAX       CfprManagedObjectDn
    MAX-ACCESS   read-only
    STATUS       current
    DESCRIPTION
        "Cisco Firepower fabric:EthLan:dn managed object property"
    ::= { cfprFabricEthLanEntry 2 }

cfprFabricEthLanRn OBJECT-TYPE
    SYNTAX       SnmpAdminString
    MAX-ACCESS   read-only
    STATUS       current
    DESCRIPTION
        "Cisco Firepower fabric:EthLan:rn managed object property"
    ::= { cfprFabricEthLanEntry 3 }

cfprFabricEthLanId OBJECT-TYPE
    SYNTAX       CfprNetworkSwitchId
    MAX-ACCESS   read-only
    STATUS       current
    DESCRIPTION
        "Cisco Firepower fabric:EthLan:id managed object property"
    ::= { cfprFabricEthLanEntry 4 }

cfprFabricEthLanLocale OBJECT-TYPE
    SYNTAX       CfprFabricExternalLocale
    MAX-ACCESS   read-only
    STATUS       current
    DESCRIPTION
        "Cisco Firepower fabric:EthLan:locale managed object property"
    ::= { cfprFabricEthLanEntry 5 }

cfprFabricEthLanName OBJECT-TYPE
    SYNTAX       SnmpAdminString
    MAX-ACCESS   read-only
    STATUS       current
    DESCRIPTION
        "Cisco Firepower fabric:EthLan:name managed object property"
    ::= { cfprFabricEthLanEntry 6 }

cfprFabricEthLanTransport OBJECT-TYPE
    SYNTAX       CfprFabricEthLanTransport
    MAX-ACCESS   read-only
    STATUS       current
    DESCRIPTION
        "Cisco Firepower fabric:EthLan:transport managed object property"
    ::= { cfprFabricEthLanEntry 7 }

cfprFabricEthLanType OBJECT-TYPE
    SYNTAX       CfprFabricLanType
    MAX-ACCESS   read-only
    STATUS       current
    DESCRIPTION
        "Cisco Firepower fabric:EthLan:type managed object property"
    ::= { cfprFabricEthLanEntry 8 }

cfprFabricEthLanEpTable OBJECT-TYPE
    SYNTAX           SEQUENCE OF CfprFabricEthLanEpEntry
    MAX-ACCESS       not-accessible
    STATUS           current
    DESCRIPTION
        "Cisco Firepower fabric:EthLanEp managed object table"
    ::= { cfprFabricObjects 30 }

cfprFabricEthLanEpEntry OBJECT-TYPE
    SYNTAX           CfprFabricEthLanEpEntry
    MAX-ACCESS       not-accessible
    STATUS           current
    DESCRIPTION
        "Entry for the cfprFabricEthLanEpTable table."
    INDEX { cfprFabricEthLanEpInstanceId }
    ::= { cfprFabricEthLanEpTable 1 }

CfprFabricEthLanEpEntry ::= SEQUENCE {
    cfprFabricEthLanEpInstanceId                                     CfprManagedObjectId,
    cfprFabricEthLanEpDn                                             CfprManagedObjectDn,
    cfprFabricEthLanEpRn                                             SnmpAdminString,
    cfprFabricEthLanEpAdminSpeed                                     CfprPortEthSpeed,
    cfprFabricEthLanEpAdminState                                     CfprFabricEthLanEpAdminState,
    cfprFabricEthLanEpAggrPortId                                     Gauge32,
    cfprFabricEthLanEpChassisId                                      Gauge32,
    cfprFabricEthLanEpDtagVlan                                       Gauge32,
    cfprFabricEthLanEpEpDn                                           SnmpAdminString,
    cfprFabricEthLanEpEthLinkProfileName                             SnmpAdminString,
    cfprFabricEthLanEpFlowCtrlPolicy                                 SnmpAdminString,
    cfprFabricEthLanEpFltAggr                                        Unsigned64,
    cfprFabricEthLanEpIfRole                                         CfprFabricLanEpIfRole,
    cfprFabricEthLanEpIfType                                         CfprFabricPIoEpIfType,
    cfprFabricEthLanEpLicGP                                          Unsigned64,
    cfprFabricEthLanEpLicState                                       CfprLicenseState,
    cfprFabricEthLanEpLocale                                         CfprFabricExternalEpLocale,
    cfprFabricEthLanEpName                                           SnmpAdminString,
    cfprFabricEthLanEpOperEthLinkProfileName                         SnmpAdminString,
    cfprFabricEthLanEpOperState                                      CfprFabricPIoEpOperState,
    cfprFabricEthLanEpOperStateReason                                SnmpAdminString,
    cfprFabricEthLanEpOverlappingVlans                               SnmpAdminString,
    cfprFabricEthLanEpPeerAggrPortId                                 Gauge32,
    cfprFabricEthLanEpPeerChassisId                                  Gauge32,
    cfprFabricEthLanEpPeerDn                                         SnmpAdminString,
    cfprFabricEthLanEpPeerPortId                                     Gauge32,
    cfprFabricEthLanEpPeerSlotId                                     Gauge32,
    cfprFabricEthLanEpPortId                                         Gauge32,
    cfprFabricEthLanEpSlotId                                         Gauge32,
    cfprFabricEthLanEpSsaPortType                                    CfprFabricSSAPortType,
    cfprFabricEthLanEpSsaVlanId                                      Gauge32,
    cfprFabricEthLanEpSwitchId                                       CfprNetworkSwitchId,
    cfprFabricEthLanEpTransport                                      CfprFabricAEthLanEpTransport,
    cfprFabricEthLanEpType                                           CfprFabricLanEpType,
    cfprFabricEthLanEpUdldOperState                                  CfprFabricUdldOperState,
    cfprFabricEthLanEpUsrLbl                                         SnmpAdminString,
    cfprFabricEthLanEpVlanStatus                                     CfprFabricEthLanEpVlanStatus,
    cfprFabricEthLanEpWarnings                                       CfprFabricWarnings,
    cfprFabricEthLanEpAdminDuplex                                    CfprPortDuplex,
    cfprFabricEthLanEpAllowSharing                                   TruthValue,
    cfprFabricEthLanEpAllowedVlan                                    CfprFabricAllowedVlanType,
    cfprFabricEthLanEpAutoNeg                                        TruthValue,
    cfprFabricEthLanEpDescr                                          SnmpAdminString,
    cfprFabricEthLanEpHashAlg                                        CfprNhTpHashType,
    cfprFabricEthLanEpInlinePeerDn                                   SnmpAdminString,
    cfprFabricEthLanEpInlinePeerName                                 SnmpAdminString,
    cfprFabricEthLanEpInlineState                                    CfprFabricEthLanEpInlineState,
    cfprFabricEthLanEpQosPrio                                        CfprFabricQosPrio,
    cfprFabricEthLanEpSpeedCap                                       CfprEquipmentEthPortSpeedCap,
    cfprFabricEthLanEpNwCtrlPolicyName                               SnmpAdminString,
    cfprFabricEthLanEpOperNwCtrlPolicyName                           SnmpAdminString,
    cfprFabricEthLanEpAllowAneg                                      TruthValue
}

cfprFabricEthLanEpInstanceId OBJECT-TYPE
    SYNTAX       CfprManagedObjectId
    MAX-ACCESS   not-accessible
    STATUS       current
    DESCRIPTION
        "Instance identifier of the managed object."
    ::= { cfprFabricEthLanEpEntry 1 }

cfprFabricEthLanEpDn OBJECT-TYPE
    SYNTAX       CfprManagedObjectDn
    MAX-ACCESS   read-only
    STATUS       current
    DESCRIPTION
        "Cisco Firepower fabric:EthLanEp:dn managed object property"
    ::= { cfprFabricEthLanEpEntry 2 }

cfprFabricEthLanEpRn OBJECT-TYPE
    SYNTAX       SnmpAdminString
    MAX-ACCESS   read-only
    STATUS       current
    DESCRIPTION
        "Cisco Firepower fabric:EthLanEp:rn managed object property"
    ::= { cfprFabricEthLanEpEntry 3 }

cfprFabricEthLanEpAdminSpeed OBJECT-TYPE
    SYNTAX       CfprPortEthSpeed
    MAX-ACCESS   read-only
    STATUS       current
    DESCRIPTION
        "Cisco Firepower fabric:EthLanEp:adminSpeed managed
        object property"
    ::= { cfprFabricEthLanEpEntry 4 }

cfprFabricEthLanEpAdminState OBJECT-TYPE
    SYNTAX       CfprFabricEthLanEpAdminState
    MAX-ACCESS   read-only
    STATUS       current
    DESCRIPTION
        "Cisco Firepower fabric:EthLanEp:adminState managed
        object property"
    ::= { cfprFabricEthLanEpEntry 5 }

cfprFabricEthLanEpAggrPortId OBJECT-TYPE
    SYNTAX       Gauge32
    MAX-ACCESS   read-only
    STATUS       current
    DESCRIPTION
        "Cisco Firepower fabric:EthLanEp:aggrPortId managed
        object property"
    ::= { cfprFabricEthLanEpEntry 6 }

cfprFabricEthLanEpChassisId OBJECT-TYPE
    SYNTAX       Gauge32
    MAX-ACCESS   read-only
    STATUS       current
    DESCRIPTION
        "Cisco Firepower fabric:EthLanEp:chassisId managed
        object property"
    ::= { cfprFabricEthLanEpEntry 7 }

cfprFabricEthLanEpDtagVlan OBJECT-TYPE
    SYNTAX       Gauge32
    MAX-ACCESS   read-only
    STATUS       current
    DESCRIPTION
        "Cisco Firepower fabric:EthLanEp:dtagVlan managed object property"
    ::= { cfprFabricEthLanEpEntry 8 }

cfprFabricEthLanEpEpDn OBJECT-TYPE
    SYNTAX       SnmpAdminString
    MAX-ACCESS   read-only
    STATUS       current
    DESCRIPTION
        "Cisco Firepower fabric:EthLanEp:epDn managed object property"
    ::= { cfprFabricEthLanEpEntry 9 }

cfprFabricEthLanEpEthLinkProfileName OBJECT-TYPE
    SYNTAX       SnmpAdminString
    MAX-ACCESS   read-only
    STATUS       current
    DESCRIPTION
        "Cisco Firepower fabric:EthLanEp:ethLinkProfileName
        managed object property"
    ::= { cfprFabricEthLanEpEntry 10 }

cfprFabricEthLanEpFlowCtrlPolicy OBJECT-TYPE
    SYNTAX       SnmpAdminString
    MAX-ACCESS   read-only
    STATUS       current
    DESCRIPTION
        "Cisco Firepower fabric:EthLanEp:flowCtrlPolicy
        managed object property"
    ::= { cfprFabricEthLanEpEntry 11 }

cfprFabricEthLanEpFltAggr OBJECT-TYPE
    SYNTAX       Unsigned64
    MAX-ACCESS   read-only
    STATUS       current
    DESCRIPTION
        "Cisco Firepower fabric:EthLanEp:fltAggr managed object property"
    ::= { cfprFabricEthLanEpEntry 12 }

cfprFabricEthLanEpIfRole OBJECT-TYPE
    SYNTAX       CfprFabricLanEpIfRole
    MAX-ACCESS   read-only
    STATUS       current
    DESCRIPTION
        "Cisco Firepower fabric:EthLanEp:ifRole managed object property"
    ::= { cfprFabricEthLanEpEntry 13 }

cfprFabricEthLanEpIfType OBJECT-TYPE
    SYNTAX       CfprFabricPIoEpIfType
    MAX-ACCESS   read-only
    STATUS       current
    DESCRIPTION
        "Cisco Firepower fabric:EthLanEp:ifType managed object property"
    ::= { cfprFabricEthLanEpEntry 14 }

cfprFabricEthLanEpLicGP OBJECT-TYPE
    SYNTAX       Unsigned64
    MAX-ACCESS   read-only
    STATUS       current
    DESCRIPTION
        "Cisco Firepower fabric:EthLanEp:licGP managed object property"
    ::= { cfprFabricEthLanEpEntry 15 }

cfprFabricEthLanEpLicState OBJECT-TYPE
    SYNTAX       CfprLicenseState
    MAX-ACCESS   read-only
    STATUS       current
    DESCRIPTION
        "Cisco Firepower fabric:EthLanEp:licState managed object property"
    ::= { cfprFabricEthLanEpEntry 16 }

cfprFabricEthLanEpLocale OBJECT-TYPE
    SYNTAX       CfprFabricExternalEpLocale
    MAX-ACCESS   read-only
    STATUS       current
    DESCRIPTION
        "Cisco Firepower fabric:EthLanEp:locale managed object property"
    ::= { cfprFabricEthLanEpEntry 17 }

cfprFabricEthLanEpName OBJECT-TYPE
    SYNTAX       SnmpAdminString
    MAX-ACCESS   read-only
    STATUS       current
    DESCRIPTION
        "Cisco Firepower fabric:EthLanEp:name managed object property"
    ::= { cfprFabricEthLanEpEntry 19 }

cfprFabricEthLanEpOperEthLinkProfileName OBJECT-TYPE
    SYNTAX       SnmpAdminString
    MAX-ACCESS   read-only
    STATUS       current
    DESCRIPTION
        "Cisco Firepower fabric:EthLanEp:operEthLinkProfileName
        managed object property"
    ::= { cfprFabricEthLanEpEntry 20 }

cfprFabricEthLanEpOperState OBJECT-TYPE
    SYNTAX       CfprFabricPIoEpOperState
    MAX-ACCESS   read-only
    STATUS       current
    DESCRIPTION
        "Cisco Firepower fabric:EthLanEp:operState managed
        object property"
    ::= { cfprFabricEthLanEpEntry 21 }

cfprFabricEthLanEpOperStateReason OBJECT-TYPE
    SYNTAX       SnmpAdminString
    MAX-ACCESS   read-only
    STATUS       current
    DESCRIPTION
        "Cisco Firepower fabric:EthLanEp:operStateReason
        managed object property"
    ::= { cfprFabricEthLanEpEntry 22 }

cfprFabricEthLanEpOverlappingVlans OBJECT-TYPE
    SYNTAX       SnmpAdminString
    MAX-ACCESS   read-only
    STATUS       current
    DESCRIPTION
        "Cisco Firepower fabric:EthLanEp:overlappingVlans
        managed object property"
    ::= { cfprFabricEthLanEpEntry 23 }

cfprFabricEthLanEpPeerAggrPortId OBJECT-TYPE
    SYNTAX       Gauge32
    MAX-ACCESS   read-only
    STATUS       current
    DESCRIPTION
        "Cisco Firepower fabric:EthLanEp:peerAggrPortId
        managed object property"
    ::= { cfprFabricEthLanEpEntry 24 }

cfprFabricEthLanEpPeerChassisId OBJECT-TYPE
    SYNTAX       Gauge32
    MAX-ACCESS   read-only
    STATUS       current
    DESCRIPTION
        "Cisco Firepower fabric:EthLanEp:peerChassisId
        managed object property"
    ::= { cfprFabricEthLanEpEntry 25 }

cfprFabricEthLanEpPeerDn OBJECT-TYPE
    SYNTAX       SnmpAdminString
    MAX-ACCESS   read-only
    STATUS       current
    DESCRIPTION
        "Cisco Firepower fabric:EthLanEp:peerDn managed object property"
    ::= { cfprFabricEthLanEpEntry 26 }

cfprFabricEthLanEpPeerPortId OBJECT-TYPE
    SYNTAX       Gauge32
    MAX-ACCESS   read-only
    STATUS       current
    DESCRIPTION
        "Cisco Firepower fabric:EthLanEp:peerPortId managed
        object property"
    ::= { cfprFabricEthLanEpEntry 27 }

cfprFabricEthLanEpPeerSlotId OBJECT-TYPE
    SYNTAX       Gauge32
    MAX-ACCESS   read-only
    STATUS       current
    DESCRIPTION
        "Cisco Firepower fabric:EthLanEp:peerSlotId managed
        object property"
    ::= { cfprFabricEthLanEpEntry 28 }

cfprFabricEthLanEpPortId OBJECT-TYPE
    SYNTAX       Gauge32
    MAX-ACCESS   read-only
    STATUS       current
    DESCRIPTION
        "Cisco Firepower fabric:EthLanEp:portId managed object property"
    ::= { cfprFabricEthLanEpEntry 29 }

cfprFabricEthLanEpSlotId OBJECT-TYPE
    SYNTAX       Gauge32
    MAX-ACCESS   read-only
    STATUS       current
    DESCRIPTION
        "Cisco Firepower fabric:EthLanEp:slotId managed object property"
    ::= { cfprFabricEthLanEpEntry 30 }

cfprFabricEthLanEpSsaPortType OBJECT-TYPE
    SYNTAX       CfprFabricSSAPortType
    MAX-ACCESS   read-only
    STATUS       current
    DESCRIPTION
        "Cisco Firepower fabric:EthLanEp:ssaPortType managed
        object property"
    ::= { cfprFabricEthLanEpEntry 31 }

cfprFabricEthLanEpSsaVlanId OBJECT-TYPE
    SYNTAX       Gauge32
    MAX-ACCESS   read-only
    STATUS       current
    DESCRIPTION
        "Cisco Firepower fabric:EthLanEp:ssaVlanId managed
        object property"
    ::= { cfprFabricEthLanEpEntry 32 }

cfprFabricEthLanEpSwitchId OBJECT-TYPE
    SYNTAX       CfprNetworkSwitchId
    MAX-ACCESS   read-only
    STATUS       current
    DESCRIPTION
        "Cisco Firepower fabric:EthLanEp:switchId managed object property"
    ::= { cfprFabricEthLanEpEntry 33 }

cfprFabricEthLanEpTransport OBJECT-TYPE
    SYNTAX       CfprFabricAEthLanEpTransport
    MAX-ACCESS   read-only
    STATUS       current
    DESCRIPTION
        "Cisco Firepower fabric:EthLanEp:transport managed
        object property"
    ::= { cfprFabricEthLanEpEntry 34 }

cfprFabricEthLanEpType OBJECT-TYPE
    SYNTAX       CfprFabricLanEpType
    MAX-ACCESS   read-only
    STATUS       current
    DESCRIPTION
        "Cisco Firepower fabric:EthLanEp:type managed object property"
    ::= { cfprFabricEthLanEpEntry 35 }

cfprFabricEthLanEpUdldOperState OBJECT-TYPE
    SYNTAX       CfprFabricUdldOperState
    MAX-ACCESS   read-only
    STATUS       current
    DESCRIPTION
        "Cisco Firepower fabric:EthLanEp:udldOperState
        managed object property"
    ::= { cfprFabricEthLanEpEntry 36 }

cfprFabricEthLanEpUsrLbl OBJECT-TYPE
    SYNTAX       SnmpAdminString
    MAX-ACCESS   read-only
    STATUS       current
    DESCRIPTION
        "Cisco Firepower fabric:EthLanEp:usrLbl managed object property"
    ::= { cfprFabricEthLanEpEntry 37 }

cfprFabricEthLanEpVlanStatus OBJECT-TYPE
    SYNTAX       CfprFabricEthLanEpVlanStatus
    MAX-ACCESS   read-only
    STATUS       current
    DESCRIPTION
        "Cisco Firepower fabric:EthLanEp:vlanStatus managed
        object property"
    ::= { cfprFabricEthLanEpEntry 38 }

cfprFabricEthLanEpWarnings OBJECT-TYPE
    SYNTAX       CfprFabricWarnings
    MAX-ACCESS   read-only
    STATUS       current
    DESCRIPTION
        "Cisco Firepower fabric:EthLanEp:warnings managed object property"
    ::= { cfprFabricEthLanEpEntry 39 }

cfprFabricEthLanEpAdminDuplex OBJECT-TYPE
    SYNTAX       CfprPortDuplex
    MAX-ACCESS   read-only
    STATUS       current
    DESCRIPTION
        "Cisco Firepower fabric:EthLanEp:adminDuplex managed
        object property"
    ::= { cfprFabricEthLanEpEntry 40 }

cfprFabricEthLanEpAllowSharing OBJECT-TYPE
    SYNTAX       TruthValue
    MAX-ACCESS   read-only
    STATUS       current
    DESCRIPTION
        "Cisco Firepower fabric:EthLanEp:allowSharing managed
        object property"
    ::= { cfprFabricEthLanEpEntry 41 }

cfprFabricEthLanEpAllowedVlan OBJECT-TYPE
    SYNTAX       CfprFabricAllowedVlanType
    MAX-ACCESS   read-only
    STATUS       current
    DESCRIPTION
        "Cisco Firepower fabric:EthLanEp:allowedVlan managed
        object property"
    ::= { cfprFabricEthLanEpEntry 42 }

cfprFabricEthLanEpAutoNeg OBJECT-TYPE
    SYNTAX       TruthValue
    MAX-ACCESS   read-only
    STATUS       current
    DESCRIPTION
        "Cisco Firepower fabric:EthLanEp:autoNeg managed object property"
    ::= { cfprFabricEthLanEpEntry 43 }

cfprFabricEthLanEpDescr OBJECT-TYPE
    SYNTAX       SnmpAdminString
    MAX-ACCESS   read-only
    STATUS       current
    DESCRIPTION
        "Cisco Firepower fabric:EthLanEp:descr managed object property"
    ::= { cfprFabricEthLanEpEntry 44 }

cfprFabricEthLanEpHashAlg OBJECT-TYPE
    SYNTAX       CfprNhTpHashType
    MAX-ACCESS   read-only
    STATUS       current
    DESCRIPTION
        "Cisco Firepower fabric:EthLanEp:hashAlg managed object property"
    ::= { cfprFabricEthLanEpEntry 45 }

cfprFabricEthLanEpInlinePeerDn OBJECT-TYPE
    SYNTAX       SnmpAdminString
    MAX-ACCESS   read-only
    STATUS       current
    DESCRIPTION
        "Cisco Firepower fabric:EthLanEp:inlinePeerDn managed
        object property"
    ::= { cfprFabricEthLanEpEntry 46 }

cfprFabricEthLanEpInlinePeerName OBJECT-TYPE
    SYNTAX       SnmpAdminString
    MAX-ACCESS   read-only
    STATUS       current
    DESCRIPTION
        "Cisco Firepower fabric:EthLanEp:inlinePeerName
        managed object property"
    ::= { cfprFabricEthLanEpEntry 47 }

cfprFabricEthLanEpInlineState OBJECT-TYPE
    SYNTAX       CfprFabricEthLanEpInlineState
    MAX-ACCESS   read-only
    STATUS       current
    DESCRIPTION
        "Cisco Firepower fabric:EthLanEp:inlineState managed
        object property"
    ::= { cfprFabricEthLanEpEntry 48 }

cfprFabricEthLanEpQosPrio OBJECT-TYPE
    SYNTAX       CfprFabricQosPrio
    MAX-ACCESS   read-only
    STATUS       current
    DESCRIPTION
        "Cisco Firepower fabric:EthLanEp:qosPrio managed object property"
    ::= { cfprFabricEthLanEpEntry 49 }

cfprFabricEthLanEpSpeedCap OBJECT-TYPE
    SYNTAX       CfprEquipmentEthPortSpeedCap
    MAX-ACCESS   read-only
    STATUS       current
    DESCRIPTION
        "Cisco Firepower fabric:EthLanEp:speedCap managed object property"
    ::= { cfprFabricEthLanEpEntry 50 }

cfprFabricEthLanEpNwCtrlPolicyName OBJECT-TYPE
    SYNTAX       SnmpAdminString
    MAX-ACCESS   read-only
    STATUS       current
    DESCRIPTION
        "Cisco Firepower fabric:EthLanEp:nwCtrlPolicyName
        managed object property"
    ::= { cfprFabricEthLanEpEntry 51 }

cfprFabricEthLanEpOperNwCtrlPolicyName OBJECT-TYPE
    SYNTAX       SnmpAdminString
    MAX-ACCESS   read-only
    STATUS       current
    DESCRIPTION
        "Cisco Firepower fabric:EthLanEp:operNwCtrlPolicyName
        managed object property"
    ::= { cfprFabricEthLanEpEntry 52 }

cfprFabricEthLanEpAllowAneg OBJECT-TYPE
    SYNTAX       TruthValue
    MAX-ACCESS   read-only
    STATUS       current
    DESCRIPTION
        "Cisco Firepower fabric:EthLanEp:allowAneg managed
        object property"
    ::= { cfprFabricEthLanEpEntry 53 }

cfprFabricEthLanFlowMonitoringTable OBJECT-TYPE
    SYNTAX           SEQUENCE OF CfprFabricEthLanFlowMonitoringEntry
    MAX-ACCESS       not-accessible
    STATUS           current
    DESCRIPTION
        "Cisco Firepower fabric:EthLanFlowMonitoring managed object table"
    ::= { cfprFabricObjects 31 }

cfprFabricEthLanFlowMonitoringEntry OBJECT-TYPE
    SYNTAX           CfprFabricEthLanFlowMonitoringEntry
    MAX-ACCESS       not-accessible
    STATUS           current
    DESCRIPTION
        "Entry for the cfprFabricEthLanFlowMonitoringTable table."
    INDEX { cfprFabricEthLanFlowMonitoringInstanceId }
    ::= { cfprFabricEthLanFlowMonitoringTable 1 }

CfprFabricEthLanFlowMonitoringEntry ::= SEQUENCE {
    cfprFabricEthLanFlowMonitoringInstanceId                         CfprManagedObjectId,
    cfprFabricEthLanFlowMonitoringDn                                 CfprManagedObjectDn,
    cfprFabricEthLanFlowMonitoringRn                                 SnmpAdminString,
    cfprFabricEthLanFlowMonitoringAdminState                         CfprFabricFlowMonitoringCategoryAdminState,
    cfprFabricEthLanFlowMonitoringType                               CfprFabricEthLanFlowMonitoringType
}

cfprFabricEthLanFlowMonitoringInstanceId OBJECT-TYPE
    SYNTAX       CfprManagedObjectId
    MAX-ACCESS   not-accessible
    STATUS       current
    DESCRIPTION
        "Instance identifier of the managed object."
    ::= { cfprFabricEthLanFlowMonitoringEntry 1 }

cfprFabricEthLanFlowMonitoringDn OBJECT-TYPE
    SYNTAX       CfprManagedObjectDn
    MAX-ACCESS   read-only
    STATUS       current
    DESCRIPTION
        "Cisco Firepower fabric:EthLanFlowMonitoring:dn
        managed object property"
    ::= { cfprFabricEthLanFlowMonitoringEntry 2 }

cfprFabricEthLanFlowMonitoringRn OBJECT-TYPE
    SYNTAX       SnmpAdminString
    MAX-ACCESS   read-only
    STATUS       current
    DESCRIPTION
        "Cisco Firepower fabric:EthLanFlowMonitoring:rn
        managed object property"
    ::= { cfprFabricEthLanFlowMonitoringEntry 3 }

cfprFabricEthLanFlowMonitoringAdminState OBJECT-TYPE
    SYNTAX       CfprFabricFlowMonitoringCategoryAdminState
    MAX-ACCESS   read-only
    STATUS       current
    DESCRIPTION
        "Cisco Firepower fabric:EthLanFlowMonitoring:adminState
        managed object property"
    ::= { cfprFabricEthLanFlowMonitoringEntry 4 }

cfprFabricEthLanFlowMonitoringType OBJECT-TYPE
    SYNTAX       CfprFabricEthLanFlowMonitoringType
    MAX-ACCESS   read-only
    STATUS       current
    DESCRIPTION
        "Cisco Firepower fabric:EthLanFlowMonitoring:type
        managed object property"
    ::= { cfprFabricEthLanFlowMonitoringEntry 5 }

cfprFabricEthLanPcTable OBJECT-TYPE
    SYNTAX           SEQUENCE OF CfprFabricEthLanPcEntry
    MAX-ACCESS       not-accessible
    STATUS           current
    DESCRIPTION
        "Cisco Firepower fabric:EthLanPc managed object table"
    ::= { cfprFabricObjects 32 }

cfprFabricEthLanPcEntry OBJECT-TYPE
    SYNTAX           CfprFabricEthLanPcEntry
    MAX-ACCESS       not-accessible
    STATUS           current
    DESCRIPTION
        "Entry for the cfprFabricEthLanPcTable table."
    INDEX { cfprFabricEthLanPcInstanceId }
    ::= { cfprFabricEthLanPcTable 1 }

CfprFabricEthLanPcEntry ::= SEQUENCE {
    cfprFabricEthLanPcInstanceId                                     CfprManagedObjectId,
    cfprFabricEthLanPcDn                                             CfprManagedObjectDn,
    cfprFabricEthLanPcRn                                             SnmpAdminString,
    cfprFabricEthLanPcAdminSpeed                                     CfprPortEthSpeed,
    cfprFabricEthLanPcAdminState                                     CfprFabricEthLanPcAdminState,
    cfprFabricEthLanPcBandwidth                                      Gauge32,
    cfprFabricEthLanPcClusterName                                    SnmpAdminString,
    cfprFabricEthLanPcDescr                                          SnmpAdminString,
    cfprFabricEthLanPcDtagVlan                                       Gauge32,
    cfprFabricEthLanPcEpDn                                           SnmpAdminString,
    cfprFabricEthLanPcFlowCtrlPolicy                                 SnmpAdminString,
    cfprFabricEthLanPcFltAggr                                        Unsigned64,
    cfprFabricEthLanPcIfRole                                         CfprFabricLanPcIfRole,
    cfprFabricEthLanPcIfType                                         CfprFabricCIoEpIfType,
    cfprFabricEthLanPcLacpPolicyName                                 SnmpAdminString,
    cfprFabricEthLanPcLocale                                         CfprFabricExternalPcLocale,
    cfprFabricEthLanPcName                                           SnmpAdminString,
    cfprFabricEthLanPcOperLacpPolicyName                             SnmpAdminString,
    cfprFabricEthLanPcOperSpeed                                      CfprPortEthSpeed,
    cfprFabricEthLanPcOperState                                      CfprNetworkPortOperState,
    cfprFabricEthLanPcOverlappingVlans                               SnmpAdminString,
    cfprFabricEthLanPcPeerDn                                         SnmpAdminString,
    cfprFabricEthLanPcPortId                                         Gauge32,
    cfprFabricEthLanPcSpannedCluster                                 CfprFabricSpannedCluster,
    cfprFabricEthLanPcSsaPortType                                    CfprFabricSSAPortType,
    cfprFabricEthLanPcSsaVlanId                                      Gauge32,
    cfprFabricEthLanPcStateQual                                      SnmpAdminString,
    cfprFabricEthLanPcSwitchId                                       CfprNetworkSwitchId,
    cfprFabricEthLanPcTransport                                      CfprFabricEthLanPcTransport,
    cfprFabricEthLanPcType                                           CfprFabricLanPcType,
    cfprFabricEthLanPcVlanStatus                                     CfprFabricEthLanPcVlanStatus,
    cfprFabricEthLanPcWarnings                                       CfprFabricWarnings,
    cfprFabricEthLanPcCluChassisId                                   Gauge32,
    cfprFabricEthLanPcLacpDetach                                     CfprFabricEthLanPcLacpDetach,
    cfprFabricEthLanPcAdminDuplex                                    CfprPortDuplex,
    cfprFabricEthLanPcAllowSharing                                   TruthValue,
    cfprFabricEthLanPcAllowedVlan                                    CfprFabricAllowedVlanType,
    cfprFabricEthLanPcAutoNeg                                        TruthValue,
    cfprFabricEthLanPcHashAlg                                        CfprNhTpHashType,
    cfprFabricEthLanPcInlinePeerDn                                   SnmpAdminString,
    cfprFabricEthLanPcInlinePeerName                                 SnmpAdminString,
    cfprFabricEthLanPcInlineState                                    CfprFabricEthLanPcInlineState,
    cfprFabricEthLanPcLacpMode                                       CfprFabricLacpMode,
    cfprFabricEthLanPcPcMode                                         CfprFabricPcMode,
    cfprFabricEthLanPcPcModeState                                    CfprFabricPcModeState,
    cfprFabricEthLanPcQosPrio                                        CfprFabricQosPrio,
    cfprFabricEthLanPcSpeedCap                                       CfprEquipmentEthPortSpeedCap,
    cfprFabricEthLanPcNwCtrlPolicyName                               SnmpAdminString,
    cfprFabricEthLanPcOperNwCtrlPolicyName                           SnmpAdminString
}

cfprFabricEthLanPcInstanceId OBJECT-TYPE
    SYNTAX       CfprManagedObjectId
    MAX-ACCESS   not-accessible
    STATUS       current
    DESCRIPTION
        "Instance identifier of the managed object."
    ::= { cfprFabricEthLanPcEntry 1 }

cfprFabricEthLanPcDn OBJECT-TYPE
    SYNTAX       CfprManagedObjectDn
    MAX-ACCESS   read-only
    STATUS       current
    DESCRIPTION
        "Cisco Firepower fabric:EthLanPc:dn managed object property"
    ::= { cfprFabricEthLanPcEntry 2 }

cfprFabricEthLanPcRn OBJECT-TYPE
    SYNTAX       SnmpAdminString
    MAX-ACCESS   read-only
    STATUS       current
    DESCRIPTION
        "Cisco Firepower fabric:EthLanPc:rn managed object property"
    ::= { cfprFabricEthLanPcEntry 3 }

cfprFabricEthLanPcAdminSpeed OBJECT-TYPE
    SYNTAX       CfprPortEthSpeed
    MAX-ACCESS   read-only
    STATUS       current
    DESCRIPTION
        "Cisco Firepower fabric:EthLanPc:adminSpeed managed
        object property"
    ::= { cfprFabricEthLanPcEntry 4 }

cfprFabricEthLanPcAdminState OBJECT-TYPE
    SYNTAX       CfprFabricEthLanPcAdminState
    MAX-ACCESS   read-only
    STATUS       current
    DESCRIPTION
        "Cisco Firepower fabric:EthLanPc:adminState managed
        object property"
    ::= { cfprFabricEthLanPcEntry 5 }

cfprFabricEthLanPcBandwidth OBJECT-TYPE
    SYNTAX       Gauge32
    MAX-ACCESS   read-only
    STATUS       current
    DESCRIPTION
        "Cisco Firepower fabric:EthLanPc:bandwidth managed
        object property"
    ::= { cfprFabricEthLanPcEntry 6 }

cfprFabricEthLanPcClusterName OBJECT-TYPE
    SYNTAX       SnmpAdminString
    MAX-ACCESS   read-only
    STATUS       current
    DESCRIPTION
        "Cisco Firepower fabric:EthLanPc:clusterName managed
        object property"
    ::= { cfprFabricEthLanPcEntry 7 }

cfprFabricEthLanPcDescr OBJECT-TYPE
    SYNTAX       SnmpAdminString
    MAX-ACCESS   read-only
    STATUS       current
    DESCRIPTION
        "Cisco Firepower fabric:EthLanPc:descr managed object property"
    ::= { cfprFabricEthLanPcEntry 8 }

cfprFabricEthLanPcDtagVlan OBJECT-TYPE
    SYNTAX       Gauge32
    MAX-ACCESS   read-only
    STATUS       current
    DESCRIPTION
        "Cisco Firepower fabric:EthLanPc:dtagVlan managed object property"
    ::= { cfprFabricEthLanPcEntry 9 }

cfprFabricEthLanPcEpDn OBJECT-TYPE
    SYNTAX       SnmpAdminString
    MAX-ACCESS   read-only
    STATUS       current
    DESCRIPTION
        "Cisco Firepower fabric:EthLanPc:epDn managed object property"
    ::= { cfprFabricEthLanPcEntry 10 }

cfprFabricEthLanPcFlowCtrlPolicy OBJECT-TYPE
    SYNTAX       SnmpAdminString
    MAX-ACCESS   read-only
    STATUS       current
    DESCRIPTION
        "Cisco Firepower fabric:EthLanPc:flowCtrlPolicy
        managed object property"
    ::= { cfprFabricEthLanPcEntry 11 }

cfprFabricEthLanPcFltAggr OBJECT-TYPE
    SYNTAX       Unsigned64
    MAX-ACCESS   read-only
    STATUS       current
    DESCRIPTION
        "Cisco Firepower fabric:EthLanPc:fltAggr managed object property"
    ::= { cfprFabricEthLanPcEntry 12 }

cfprFabricEthLanPcIfRole OBJECT-TYPE
    SYNTAX       CfprFabricLanPcIfRole
    MAX-ACCESS   read-only
    STATUS       current
    DESCRIPTION
        "Cisco Firepower fabric:EthLanPc:ifRole managed object property"
    ::= { cfprFabricEthLanPcEntry 13 }

cfprFabricEthLanPcIfType OBJECT-TYPE
    SYNTAX       CfprFabricCIoEpIfType
    MAX-ACCESS   read-only
    STATUS       current
    DESCRIPTION
        "Cisco Firepower fabric:EthLanPc:ifType managed object property"
    ::= { cfprFabricEthLanPcEntry 14 }

cfprFabricEthLanPcLacpPolicyName OBJECT-TYPE
    SYNTAX       SnmpAdminString
    MAX-ACCESS   read-only
    STATUS       current
    DESCRIPTION
        "Cisco Firepower fabric:EthLanPc:lacpPolicyName
        managed object property"
    ::= { cfprFabricEthLanPcEntry 15 }

cfprFabricEthLanPcLocale OBJECT-TYPE
    SYNTAX       CfprFabricExternalPcLocale
    MAX-ACCESS   read-only
    STATUS       current
    DESCRIPTION
        "Cisco Firepower fabric:EthLanPc:locale managed object property"
    ::= { cfprFabricEthLanPcEntry 16 }

cfprFabricEthLanPcName OBJECT-TYPE
    SYNTAX       SnmpAdminString
    MAX-ACCESS   read-only
    STATUS       current
    DESCRIPTION
        "Cisco Firepower fabric:EthLanPc:name managed object property"
    ::= { cfprFabricEthLanPcEntry 18 }

cfprFabricEthLanPcOperLacpPolicyName OBJECT-TYPE
    SYNTAX       SnmpAdminString
    MAX-ACCESS   read-only
    STATUS       current
    DESCRIPTION
        "Cisco Firepower fabric:EthLanPc:operLacpPolicyName
        managed object property"
    ::= { cfprFabricEthLanPcEntry 19 }

cfprFabricEthLanPcOperSpeed OBJECT-TYPE
    SYNTAX       CfprPortEthSpeed
    MAX-ACCESS   read-only
    STATUS       current
    DESCRIPTION
        "Cisco Firepower fabric:EthLanPc:operSpeed managed
        object property"
    ::= { cfprFabricEthLanPcEntry 20 }

cfprFabricEthLanPcOperState OBJECT-TYPE
    SYNTAX       CfprNetworkPortOperState
    MAX-ACCESS   read-only
    STATUS       current
    DESCRIPTION
        "Cisco Firepower fabric:EthLanPc:operState managed
        object property"
    ::= { cfprFabricEthLanPcEntry 21 }

cfprFabricEthLanPcOverlappingVlans OBJECT-TYPE
    SYNTAX       SnmpAdminString
    MAX-ACCESS   read-only
    STATUS       current
    DESCRIPTION
        "Cisco Firepower fabric:EthLanPc:overlappingVlans
        managed object property"
    ::= { cfprFabricEthLanPcEntry 22 }

cfprFabricEthLanPcPeerDn OBJECT-TYPE
    SYNTAX       SnmpAdminString
    MAX-ACCESS   read-only
    STATUS       current
    DESCRIPTION
        "Cisco Firepower fabric:EthLanPc:peerDn managed object property"
    ::= { cfprFabricEthLanPcEntry 23 }

cfprFabricEthLanPcPortId OBJECT-TYPE
    SYNTAX       Gauge32
    MAX-ACCESS   read-only
    STATUS       current
    DESCRIPTION
        "Cisco Firepower fabric:EthLanPc:portId managed object property"
    ::= { cfprFabricEthLanPcEntry 24 }

cfprFabricEthLanPcSpannedCluster OBJECT-TYPE
    SYNTAX       CfprFabricSpannedCluster
    MAX-ACCESS   read-only
    STATUS       current
    DESCRIPTION
        "Cisco Firepower fabric:EthLanPc:spannedCluster
        managed object property"
    ::= { cfprFabricEthLanPcEntry 25 }

cfprFabricEthLanPcSsaPortType OBJECT-TYPE
    SYNTAX       CfprFabricSSAPortType
    MAX-ACCESS   read-only
    STATUS       current
    DESCRIPTION
        "Cisco Firepower fabric:EthLanPc:ssaPortType managed
        object property"
    ::= { cfprFabricEthLanPcEntry 26 }

cfprFabricEthLanPcSsaVlanId OBJECT-TYPE
    SYNTAX       Gauge32
    MAX-ACCESS   read-only
    STATUS       current
    DESCRIPTION
        "Cisco Firepower fabric:EthLanPc:ssaVlanId managed
        object property"
    ::= { cfprFabricEthLanPcEntry 27 }

cfprFabricEthLanPcStateQual OBJECT-TYPE
    SYNTAX       SnmpAdminString
    MAX-ACCESS   read-only
    STATUS       current
    DESCRIPTION
        "Cisco Firepower fabric:EthLanPc:stateQual managed
        object property"
    ::= { cfprFabricEthLanPcEntry 28 }

cfprFabricEthLanPcSwitchId OBJECT-TYPE
    SYNTAX       CfprNetworkSwitchId
    MAX-ACCESS   read-only
    STATUS       current
    DESCRIPTION
        "Cisco Firepower fabric:EthLanPc:switchId managed object property"
    ::= { cfprFabricEthLanPcEntry 29 }

cfprFabricEthLanPcTransport OBJECT-TYPE
    SYNTAX       CfprFabricEthLanPcTransport
    MAX-ACCESS   read-only
    STATUS       current
    DESCRIPTION
        "Cisco Firepower fabric:EthLanPc:transport managed
        object property"
    ::= { cfprFabricEthLanPcEntry 30 }

cfprFabricEthLanPcType OBJECT-TYPE
    SYNTAX       CfprFabricLanPcType
    MAX-ACCESS   read-only
    STATUS       current
    DESCRIPTION
        "Cisco Firepower fabric:EthLanPc:type managed object property"
    ::= { cfprFabricEthLanPcEntry 31 }

cfprFabricEthLanPcVlanStatus OBJECT-TYPE
    SYNTAX       CfprFabricEthLanPcVlanStatus
    MAX-ACCESS   read-only
    STATUS       current
    DESCRIPTION
        "Cisco Firepower fabric:EthLanPc:vlanStatus managed
        object property"
    ::= { cfprFabricEthLanPcEntry 32 }

cfprFabricEthLanPcWarnings OBJECT-TYPE
    SYNTAX       CfprFabricWarnings
    MAX-ACCESS   read-only
    STATUS       current
    DESCRIPTION
        "Cisco Firepower fabric:EthLanPc:warnings managed object property"
    ::= { cfprFabricEthLanPcEntry 33 }

cfprFabricEthLanPcCluChassisId OBJECT-TYPE
    SYNTAX       Gauge32
    MAX-ACCESS   read-only
    STATUS       current
    DESCRIPTION
        "Cisco Firepower fabric:EthLanPc:cluChassisId managed
        object property"
    ::= { cfprFabricEthLanPcEntry 34 }

cfprFabricEthLanPcLacpDetach OBJECT-TYPE
    SYNTAX       CfprFabricEthLanPcLacpDetach
    MAX-ACCESS   read-only
    STATUS       current
    DESCRIPTION
        "Cisco Firepower fabric:EthLanPc:lacpDetach managed
        object property"
    ::= { cfprFabricEthLanPcEntry 35 }

cfprFabricEthLanPcAdminDuplex OBJECT-TYPE
    SYNTAX       CfprPortDuplex
    MAX-ACCESS   read-only
    STATUS       current
    DESCRIPTION
        "Cisco Firepower fabric:EthLanPc:adminDuplex managed
        object property"
    ::= { cfprFabricEthLanPcEntry 36 }

cfprFabricEthLanPcAllowSharing OBJECT-TYPE
    SYNTAX       TruthValue
    MAX-ACCESS   read-only
    STATUS       current
    DESCRIPTION
        "Cisco Firepower fabric:EthLanPc:allowSharing managed
        object property"
    ::= { cfprFabricEthLanPcEntry 37 }

cfprFabricEthLanPcAllowedVlan OBJECT-TYPE
    SYNTAX       CfprFabricAllowedVlanType
    MAX-ACCESS   read-only
    STATUS       current
    DESCRIPTION
        "Cisco Firepower fabric:EthLanPc:allowedVlan managed
        object property"
    ::= { cfprFabricEthLanPcEntry 38 }

cfprFabricEthLanPcAutoNeg OBJECT-TYPE
    SYNTAX       TruthValue
    MAX-ACCESS   read-only
    STATUS       current
    DESCRIPTION
        "Cisco Firepower fabric:EthLanPc:autoNeg managed object property"
    ::= { cfprFabricEthLanPcEntry 39 }

cfprFabricEthLanPcHashAlg OBJECT-TYPE
    SYNTAX       CfprNhTpHashType
    MAX-ACCESS   read-only
    STATUS       current
    DESCRIPTION
        "Cisco Firepower fabric:EthLanPc:hashAlg managed object property"
    ::= { cfprFabricEthLanPcEntry 40 }

cfprFabricEthLanPcInlinePeerDn OBJECT-TYPE
    SYNTAX       SnmpAdminString
    MAX-ACCESS   read-only
    STATUS       current
    DESCRIPTION
        "Cisco Firepower fabric:EthLanPc:inlinePeerDn managed
        object property"
    ::= { cfprFabricEthLanPcEntry 41 }

cfprFabricEthLanPcInlinePeerName OBJECT-TYPE
    SYNTAX       SnmpAdminString
    MAX-ACCESS   read-only
    STATUS       current
    DESCRIPTION
        "Cisco Firepower fabric:EthLanPc:inlinePeerName
        managed object property"
    ::= { cfprFabricEthLanPcEntry 42 }

cfprFabricEthLanPcInlineState OBJECT-TYPE
    SYNTAX       CfprFabricEthLanPcInlineState
    MAX-ACCESS   read-only
    STATUS       current
    DESCRIPTION
        "Cisco Firepower fabric:EthLanPc:inlineState managed
        object property"
    ::= { cfprFabricEthLanPcEntry 43 }

cfprFabricEthLanPcLacpMode OBJECT-TYPE
    SYNTAX       CfprFabricLacpMode
    MAX-ACCESS   read-only
    STATUS       current
    DESCRIPTION
        "Cisco Firepower fabric:EthLanPc:lacpMode managed object property"
    ::= { cfprFabricEthLanPcEntry 44 }

cfprFabricEthLanPcPcMode OBJECT-TYPE
    SYNTAX       CfprFabricPcMode
    MAX-ACCESS   read-only
    STATUS       current
    DESCRIPTION
        "Cisco Firepower fabric:EthLanPc:pcMode managed object property"
    ::= { cfprFabricEthLanPcEntry 45 }

cfprFabricEthLanPcPcModeState OBJECT-TYPE
    SYNTAX       CfprFabricPcModeState
    MAX-ACCESS   read-only
    STATUS       current
    DESCRIPTION
        "Cisco Firepower fabric:EthLanPc:pcModeState managed
        object property"
    ::= { cfprFabricEthLanPcEntry 46 }

cfprFabricEthLanPcQosPrio OBJECT-TYPE
    SYNTAX       CfprFabricQosPrio
    MAX-ACCESS   read-only
    STATUS       current
    DESCRIPTION
        "Cisco Firepower fabric:EthLanPc:qosPrio managed object property"
    ::= { cfprFabricEthLanPcEntry 47 }

cfprFabricEthLanPcSpeedCap OBJECT-TYPE
    SYNTAX       CfprEquipmentEthPortSpeedCap
    MAX-ACCESS   read-only
    STATUS       current
    DESCRIPTION
        "Cisco Firepower fabric:EthLanPc:speedCap managed object property"
    ::= { cfprFabricEthLanPcEntry 48 }

cfprFabricEthLanPcNwCtrlPolicyName OBJECT-TYPE
    SYNTAX       SnmpAdminString
    MAX-ACCESS   read-only
    STATUS       current
    DESCRIPTION
        "Cisco Firepower fabric:EthLanPc:nwCtrlPolicyName
        managed object property"
    ::= { cfprFabricEthLanPcEntry 49 }

cfprFabricEthLanPcOperNwCtrlPolicyName OBJECT-TYPE
    SYNTAX       SnmpAdminString
    MAX-ACCESS   read-only
    STATUS       current
    DESCRIPTION
        "Cisco Firepower fabric:EthLanPc:operNwCtrlPolicyName
        managed object property"
    ::= { cfprFabricEthLanPcEntry 50 }

cfprFabricEthLanPcEpTable OBJECT-TYPE
    SYNTAX           SEQUENCE OF CfprFabricEthLanPcEpEntry
    MAX-ACCESS       not-accessible
    STATUS           current
    DESCRIPTION
        "Cisco Firepower fabric:EthLanPcEp managed object table"
    ::= { cfprFabricObjects 33 }

cfprFabricEthLanPcEpEntry OBJECT-TYPE
    SYNTAX           CfprFabricEthLanPcEpEntry
    MAX-ACCESS       not-accessible
    STATUS           current
    DESCRIPTION
        "Entry for the cfprFabricEthLanPcEpTable table."
    INDEX { cfprFabricEthLanPcEpInstanceId }
    ::= { cfprFabricEthLanPcEpTable 1 }

CfprFabricEthLanPcEpEntry ::= SEQUENCE {
    cfprFabricEthLanPcEpInstanceId                                   CfprManagedObjectId,
    cfprFabricEthLanPcEpDnData                                       CfprManagedObjectDn,
    cfprFabricEthLanPcEpRn                                           SnmpAdminString,
    cfprFabricEthLanPcEpAdminState                                   CfprFabricExternalEpAdminState,
    cfprFabricEthLanPcEpAggrPortId                                   Gauge32,
    cfprFabricEthLanPcEpChassisId                                    Gauge32,
    cfprFabricEthLanPcEpEpDn                                         SnmpAdminString,
    cfprFabricEthLanPcEpEthLinkProfileName                           SnmpAdminString,
    cfprFabricEthLanPcEpFltAggr                                      Unsigned64,
    cfprFabricEthLanPcEpIfRole                                       CfprFabricLanEpIfRole,
    cfprFabricEthLanPcEpIfType                                       CfprFabricPIoEpIfType,
    cfprFabricEthLanPcEpLicGP                                        Unsigned64,
    cfprFabricEthLanPcEpLicState                                     CfprLicenseState,
    cfprFabricEthLanPcEpLocale                                       CfprFabricExternalEpLocale,
    cfprFabricEthLanPcEpMembership                                   CfprFabricMembershipStatus,
    cfprFabricEthLanPcEpName                                         SnmpAdminString,
    cfprFabricEthLanPcEpOperEthLinkProfileName                       SnmpAdminString,
    cfprFabricEthLanPcEpOperState                                    CfprFabricPIoEpOperState,
    cfprFabricEthLanPcEpOperStateReason                              SnmpAdminString,
    cfprFabricEthLanPcEpPeerAggrPortId                               Gauge32,
    cfprFabricEthLanPcEpPeerChassisId                                Gauge32,
    cfprFabricEthLanPcEpPeerDn                                       SnmpAdminString,
    cfprFabricEthLanPcEpPeerPortId                                   Gauge32,
    cfprFabricEthLanPcEpPeerSlotId                                   Gauge32,
    cfprFabricEthLanPcEpPortId                                       Gauge32,
    cfprFabricEthLanPcEpSlotId                                       Gauge32,
    cfprFabricEthLanPcEpSwitchId                                     CfprNetworkSwitchId,
    cfprFabricEthLanPcEpTransport                                    CfprFabricAEthLanEpTransport,
    cfprFabricEthLanPcEpType                                         CfprFabricLanEpType,
    cfprFabricEthLanPcEpUdldOperState                                CfprFabricUdldOperState,
    cfprFabricEthLanPcEpWarnings                                     CfprFabricWarnings,
    cfprFabricEthLanPcEpDescr                                        SnmpAdminString,
    cfprFabricEthLanPcEpSpeedCap                                     CfprEquipmentEthPortSpeedCap
}

cfprFabricEthLanPcEpInstanceId OBJECT-TYPE
    SYNTAX       CfprManagedObjectId
    MAX-ACCESS   not-accessible
    STATUS       current
    DESCRIPTION
        "Instance identifier of the managed object."
    ::= { cfprFabricEthLanPcEpEntry 1 }

cfprFabricEthLanPcEpDnData OBJECT-TYPE
    SYNTAX       CfprManagedObjectDn
    MAX-ACCESS   read-only
    STATUS       current
    DESCRIPTION
        "Cisco Firepower fabric:EthLanPcEp:dn managed object property"
    ::= { cfprFabricEthLanPcEpEntry 2 }

cfprFabricEthLanPcEpRn OBJECT-TYPE
    SYNTAX       SnmpAdminString
    MAX-ACCESS   read-only
    STATUS       current
    DESCRIPTION
        "Cisco Firepower fabric:EthLanPcEp:rn managed object property"
    ::= { cfprFabricEthLanPcEpEntry 3 }

cfprFabricEthLanPcEpAdminState OBJECT-TYPE
    SYNTAX       CfprFabricExternalEpAdminState
    MAX-ACCESS   read-only
    STATUS       current
    DESCRIPTION
        "Cisco Firepower fabric:EthLanPcEp:adminState managed
        object property"
    ::= { cfprFabricEthLanPcEpEntry 4 }

cfprFabricEthLanPcEpAggrPortId OBJECT-TYPE
    SYNTAX       Gauge32
    MAX-ACCESS   read-only
    STATUS       current
    DESCRIPTION
        "Cisco Firepower fabric:EthLanPcEp:aggrPortId managed
        object property"
    ::= { cfprFabricEthLanPcEpEntry 5 }

cfprFabricEthLanPcEpChassisId OBJECT-TYPE
    SYNTAX       Gauge32
    MAX-ACCESS   read-only
    STATUS       current
    DESCRIPTION
        "Cisco Firepower fabric:EthLanPcEp:chassisId managed
        object property"
    ::= { cfprFabricEthLanPcEpEntry 6 }

cfprFabricEthLanPcEpEpDn OBJECT-TYPE
    SYNTAX       SnmpAdminString
    MAX-ACCESS   read-only
    STATUS       current
    DESCRIPTION
        "Cisco Firepower fabric:EthLanPcEp:epDn managed object property"
    ::= { cfprFabricEthLanPcEpEntry 7 }

cfprFabricEthLanPcEpEthLinkProfileName OBJECT-TYPE
    SYNTAX       SnmpAdminString
    MAX-ACCESS   read-only
    STATUS       current
    DESCRIPTION
        "Cisco Firepower fabric:EthLanPcEp:ethLinkProfileName
        managed object property"
    ::= { cfprFabricEthLanPcEpEntry 8 }

cfprFabricEthLanPcEpFltAggr OBJECT-TYPE
    SYNTAX       Unsigned64
    MAX-ACCESS   read-only
    STATUS       current
    DESCRIPTION
        "Cisco Firepower fabric:EthLanPcEp:fltAggr managed
        object property"
    ::= { cfprFabricEthLanPcEpEntry 9 }

cfprFabricEthLanPcEpIfRole OBJECT-TYPE
    SYNTAX       CfprFabricLanEpIfRole
    MAX-ACCESS   read-only
    STATUS       current
    DESCRIPTION
        "Cisco Firepower fabric:EthLanPcEp:ifRole managed object property"
    ::= { cfprFabricEthLanPcEpEntry 10 }

cfprFabricEthLanPcEpIfType OBJECT-TYPE
    SYNTAX       CfprFabricPIoEpIfType
    MAX-ACCESS   read-only
    STATUS       current
    DESCRIPTION
        "Cisco Firepower fabric:EthLanPcEp:ifType managed object property"
    ::= { cfprFabricEthLanPcEpEntry 11 }

cfprFabricEthLanPcEpLicGP OBJECT-TYPE
    SYNTAX       Unsigned64
    MAX-ACCESS   read-only
    STATUS       current
    DESCRIPTION
        "Cisco Firepower fabric:EthLanPcEp:licGP managed object property"
    ::= { cfprFabricEthLanPcEpEntry 12 }

cfprFabricEthLanPcEpLicState OBJECT-TYPE
    SYNTAX       CfprLicenseState
    MAX-ACCESS   read-only
    STATUS       current
    DESCRIPTION
        "Cisco Firepower fabric:EthLanPcEp:licState managed
        object property"
    ::= { cfprFabricEthLanPcEpEntry 13 }

cfprFabricEthLanPcEpLocale OBJECT-TYPE
    SYNTAX       CfprFabricExternalEpLocale
    MAX-ACCESS   read-only
    STATUS       current
    DESCRIPTION
        "Cisco Firepower fabric:EthLanPcEp:locale managed object property"
    ::= { cfprFabricEthLanPcEpEntry 14 }

cfprFabricEthLanPcEpMembership OBJECT-TYPE
    SYNTAX       CfprFabricMembershipStatus
    MAX-ACCESS   read-only
    STATUS       current
    DESCRIPTION
        "Cisco Firepower fabric:EthLanPcEp:membership managed
        object property"
    ::= { cfprFabricEthLanPcEpEntry 15 }

cfprFabricEthLanPcEpName OBJECT-TYPE
    SYNTAX       SnmpAdminString
    MAX-ACCESS   read-only
    STATUS       current
    DESCRIPTION
        "Cisco Firepower fabric:EthLanPcEp:name managed object property"
    ::= { cfprFabricEthLanPcEpEntry 16 }

cfprFabricEthLanPcEpOperEthLinkProfileName OBJECT-TYPE
    SYNTAX       SnmpAdminString
    MAX-ACCESS   read-only
    STATUS       current
    DESCRIPTION
        "Cisco Firepower fabric:EthLanPcEp:operEthLinkProfileName
        managed object property"
    ::= { cfprFabricEthLanPcEpEntry 17 }

cfprFabricEthLanPcEpOperState OBJECT-TYPE
    SYNTAX       CfprFabricPIoEpOperState
    MAX-ACCESS   read-only
    STATUS       current
    DESCRIPTION
        "Cisco Firepower fabric:EthLanPcEp:operState managed
        object property"
    ::= { cfprFabricEthLanPcEpEntry 18 }

cfprFabricEthLanPcEpOperStateReason OBJECT-TYPE
    SYNTAX       SnmpAdminString
    MAX-ACCESS   read-only
    STATUS       current
    DESCRIPTION
        "Cisco Firepower fabric:EthLanPcEp:operStateReason
        managed object property"
    ::= { cfprFabricEthLanPcEpEntry 19 }

cfprFabricEthLanPcEpPeerAggrPortId OBJECT-TYPE
    SYNTAX       Gauge32
    MAX-ACCESS   read-only
    STATUS       current
    DESCRIPTION
        "Cisco Firepower fabric:EthLanPcEp:peerAggrPortId
        managed object property"
    ::= { cfprFabricEthLanPcEpEntry 20 }

cfprFabricEthLanPcEpPeerChassisId OBJECT-TYPE
    SYNTAX       Gauge32
    MAX-ACCESS   read-only
    STATUS       current
    DESCRIPTION
        "Cisco Firepower fabric:EthLanPcEp:peerChassisId
        managed object property"
    ::= { cfprFabricEthLanPcEpEntry 21 }

cfprFabricEthLanPcEpPeerDn OBJECT-TYPE
    SYNTAX       SnmpAdminString
    MAX-ACCESS   read-only
    STATUS       current
    DESCRIPTION
        "Cisco Firepower fabric:EthLanPcEp:peerDn managed object property"
    ::= { cfprFabricEthLanPcEpEntry 22 }

cfprFabricEthLanPcEpPeerPortId OBJECT-TYPE
    SYNTAX       Gauge32
    MAX-ACCESS   read-only
    STATUS       current
    DESCRIPTION
        "Cisco Firepower fabric:EthLanPcEp:peerPortId managed
        object property"
    ::= { cfprFabricEthLanPcEpEntry 23 }

cfprFabricEthLanPcEpPeerSlotId OBJECT-TYPE
    SYNTAX       Gauge32
    MAX-ACCESS   read-only
    STATUS       current
    DESCRIPTION
        "Cisco Firepower fabric:EthLanPcEp:peerSlotId managed
        object property"
    ::= { cfprFabricEthLanPcEpEntry 24 }

cfprFabricEthLanPcEpPortId OBJECT-TYPE
    SYNTAX       Gauge32
    MAX-ACCESS   read-only
    STATUS       current
    DESCRIPTION
        "Cisco Firepower fabric:EthLanPcEp:portId managed object property"
    ::= { cfprFabricEthLanPcEpEntry 25 }

cfprFabricEthLanPcEpSlotId OBJECT-TYPE
    SYNTAX       Gauge32
    MAX-ACCESS   read-only
    STATUS       current
    DESCRIPTION
        "Cisco Firepower fabric:EthLanPcEp:slotId managed object property"
    ::= { cfprFabricEthLanPcEpEntry 26 }

cfprFabricEthLanPcEpSwitchId OBJECT-TYPE
    SYNTAX       CfprNetworkSwitchId
    MAX-ACCESS   read-only
    STATUS       current
    DESCRIPTION
        "Cisco Firepower fabric:EthLanPcEp:switchId managed
        object property"
    ::= { cfprFabricEthLanPcEpEntry 27 }

cfprFabricEthLanPcEpTransport OBJECT-TYPE
    SYNTAX       CfprFabricAEthLanEpTransport
    MAX-ACCESS   read-only
    STATUS       current
    DESCRIPTION
        "Cisco Firepower fabric:EthLanPcEp:transport managed
        object property"
    ::= { cfprFabricEthLanPcEpEntry 28 }

cfprFabricEthLanPcEpType OBJECT-TYPE
    SYNTAX       CfprFabricLanEpType
    MAX-ACCESS   read-only
    STATUS       current
    DESCRIPTION
        "Cisco Firepower fabric:EthLanPcEp:type managed object property"
    ::= { cfprFabricEthLanPcEpEntry 29 }

cfprFabricEthLanPcEpUdldOperState OBJECT-TYPE
    SYNTAX       CfprFabricUdldOperState
    MAX-ACCESS   read-only
    STATUS       current
    DESCRIPTION
        "Cisco Firepower fabric:EthLanPcEp:udldOperState
        managed object property"
    ::= { cfprFabricEthLanPcEpEntry 30 }

cfprFabricEthLanPcEpWarnings OBJECT-TYPE
    SYNTAX       CfprFabricWarnings
    MAX-ACCESS   read-only
    STATUS       current
    DESCRIPTION
        "Cisco Firepower fabric:EthLanPcEp:warnings managed
        object property"
    ::= { cfprFabricEthLanPcEpEntry 31 }

cfprFabricEthLanPcEpDescr OBJECT-TYPE
    SYNTAX       SnmpAdminString
    MAX-ACCESS   read-only
    STATUS       current
    DESCRIPTION
        "Cisco Firepower fabric:EthLanPcEp:descr managed object property"
    ::= { cfprFabricEthLanPcEpEntry 32 }

cfprFabricEthLanPcEpSpeedCap OBJECT-TYPE
    SYNTAX       CfprEquipmentEthPortSpeedCap
    MAX-ACCESS   read-only
    STATUS       current
    DESCRIPTION
        "Cisco Firepower fabric:EthLanPcEp:speedCap managed
        object property"
    ::= { cfprFabricEthLanPcEpEntry 33 }

cfprFabricEthLinkProfileTable OBJECT-TYPE
    SYNTAX           SEQUENCE OF CfprFabricEthLinkProfileEntry
    MAX-ACCESS       not-accessible
    STATUS           current
    DESCRIPTION
        "Cisco Firepower fabric:EthLinkProfile managed object table"
    ::= { cfprFabricObjects 34 }

cfprFabricEthLinkProfileEntry OBJECT-TYPE
    SYNTAX           CfprFabricEthLinkProfileEntry
    MAX-ACCESS       not-accessible
    STATUS           current
    DESCRIPTION
        "Entry for the cfprFabricEthLinkProfileTable table."
    INDEX { cfprFabricEthLinkProfileInstanceId }
    ::= { cfprFabricEthLinkProfileTable 1 }

CfprFabricEthLinkProfileEntry ::= SEQUENCE {
    cfprFabricEthLinkProfileInstanceId                               CfprManagedObjectId,
    cfprFabricEthLinkProfileDn                                       CfprManagedObjectDn,
    cfprFabricEthLinkProfileRn                                       SnmpAdminString,
    cfprFabricEthLinkProfileCdpLinkPolicyName                        SnmpAdminString,
    cfprFabricEthLinkProfileDescr                                    SnmpAdminString,
    cfprFabricEthLinkProfileIntId                                    SnmpAdminString,
    cfprFabricEthLinkProfileName                                     SnmpAdminString,
    cfprFabricEthLinkProfileOperCdpLinkPolicyName                    SnmpAdminString,
    cfprFabricEthLinkProfileOperUdldLinkPolicyName                   SnmpAdminString,
    cfprFabricEthLinkProfilePolicyLevel                              Gauge32,
    cfprFabricEthLinkProfilePolicyOwner                              CfprPolicyPolicyOwner,
    cfprFabricEthLinkProfileUdldLinkPolicyName                       SnmpAdminString
}

cfprFabricEthLinkProfileInstanceId OBJECT-TYPE
    SYNTAX       CfprManagedObjectId
    MAX-ACCESS   not-accessible
    STATUS       current
    DESCRIPTION
        "Instance identifier of the managed object."
    ::= { cfprFabricEthLinkProfileEntry 1 }

cfprFabricEthLinkProfileDn OBJECT-TYPE
    SYNTAX       CfprManagedObjectDn
    MAX-ACCESS   read-only
    STATUS       current
    DESCRIPTION
        "Cisco Firepower fabric:EthLinkProfile:dn managed object property"
    ::= { cfprFabricEthLinkProfileEntry 2 }

cfprFabricEthLinkProfileRn OBJECT-TYPE
    SYNTAX       SnmpAdminString
    MAX-ACCESS   read-only
    STATUS       current
    DESCRIPTION
        "Cisco Firepower fabric:EthLinkProfile:rn managed object property"
    ::= { cfprFabricEthLinkProfileEntry 3 }

cfprFabricEthLinkProfileCdpLinkPolicyName OBJECT-TYPE
    SYNTAX       SnmpAdminString
    MAX-ACCESS   read-only
    STATUS       current
    DESCRIPTION
        "Cisco Firepower fabric:EthLinkProfile:cdpLinkPolicyName
        managed object property"
    ::= { cfprFabricEthLinkProfileEntry 4 }

cfprFabricEthLinkProfileDescr OBJECT-TYPE
    SYNTAX       SnmpAdminString
    MAX-ACCESS   read-only
    STATUS       current
    DESCRIPTION
        "Cisco Firepower fabric:EthLinkProfile:descr managed
        object property"
    ::= { cfprFabricEthLinkProfileEntry 5 }

cfprFabricEthLinkProfileIntId OBJECT-TYPE
    SYNTAX       SnmpAdminString
    MAX-ACCESS   read-only
    STATUS       current
    DESCRIPTION
        "Cisco Firepower fabric:EthLinkProfile:intId managed
        object property"
    ::= { cfprFabricEthLinkProfileEntry 6 }

cfprFabricEthLinkProfileName OBJECT-TYPE
    SYNTAX       SnmpAdminString
    MAX-ACCESS   read-only
    STATUS       current
    DESCRIPTION
        "Cisco Firepower fabric:EthLinkProfile:name managed
        object property"
    ::= { cfprFabricEthLinkProfileEntry 7 }

cfprFabricEthLinkProfileOperCdpLinkPolicyName OBJECT-TYPE
    SYNTAX       SnmpAdminString
    MAX-ACCESS   read-only
    STATUS       current
    DESCRIPTION
        "Cisco Firepower fabric:EthLinkProfile:operCdpLinkPolicyName
        managed object property"
    ::= { cfprFabricEthLinkProfileEntry 8 }

cfprFabricEthLinkProfileOperUdldLinkPolicyName OBJECT-TYPE
    SYNTAX       SnmpAdminString
    MAX-ACCESS   read-only
    STATUS       current
    DESCRIPTION
        "Cisco Firepower fabric:EthLinkProfile:operUdldLinkPolicyName
        managed object property"
    ::= { cfprFabricEthLinkProfileEntry 9 }

cfprFabricEthLinkProfilePolicyLevel OBJECT-TYPE
    SYNTAX       Gauge32
    MAX-ACCESS   read-only
    STATUS       current
    DESCRIPTION
        "Cisco Firepower fabric:EthLinkProfile:policyLevel
        managed object property"
    ::= { cfprFabricEthLinkProfileEntry 10 }

cfprFabricEthLinkProfilePolicyOwner OBJECT-TYPE
    SYNTAX       CfprPolicyPolicyOwner
    MAX-ACCESS   read-only
    STATUS       current
    DESCRIPTION
        "Cisco Firepower fabric:EthLinkProfile:policyOwner
        managed object property"
    ::= { cfprFabricEthLinkProfileEntry 11 }

cfprFabricEthLinkProfileUdldLinkPolicyName OBJECT-TYPE
    SYNTAX       SnmpAdminString
    MAX-ACCESS   read-only
    STATUS       current
    DESCRIPTION
        "Cisco Firepower fabric:EthLinkProfile:udldLinkPolicyName
        managed object property"
    ::= { cfprFabricEthLinkProfileEntry 12 }

cfprFabricEthMonTable OBJECT-TYPE
    SYNTAX           SEQUENCE OF CfprFabricEthMonEntry
    MAX-ACCESS       not-accessible
    STATUS           current
    DESCRIPTION
        "Cisco Firepower fabric:EthMon managed object table"
    ::= { cfprFabricObjects 35 }

cfprFabricEthMonEntry OBJECT-TYPE
    SYNTAX           CfprFabricEthMonEntry
    MAX-ACCESS       not-accessible
    STATUS           current
    DESCRIPTION
        "Entry for the cfprFabricEthMonTable table."
    INDEX { cfprFabricEthMonInstanceId }
    ::= { cfprFabricEthMonTable 1 }

CfprFabricEthMonEntry ::= SEQUENCE {
    cfprFabricEthMonInstanceId                                       CfprManagedObjectId,
    cfprFabricEthMonDn                                               CfprManagedObjectDn,
    cfprFabricEthMonRn                                               SnmpAdminString,
    cfprFabricEthMonAdminState                                       CfprFabricMonAdminState,
    cfprFabricEthMonConfigFailReason                                 SnmpAdminString,
    cfprFabricEthMonId                                               CfprNetworkSwitchId,
    cfprFabricEthMonIsConfigSuccess                                  TruthValue,
    cfprFabricEthMonLocale                                           CfprFabricExternalLocale,
    cfprFabricEthMonName                                             SnmpAdminString,
    cfprFabricEthMonOperState                                        CfprFabricMonOperState,
    cfprFabricEthMonOperStateReason                                  CfprFabricMonOperStateReason,
    cfprFabricEthMonPeerDn                                           SnmpAdminString,
    cfprFabricEthMonSession                                          Gauge32,
    cfprFabricEthMonTransport                                        CfprFabricEthMonTransport,
    cfprFabricEthMonType                                             CfprFabricEthMonType
}

cfprFabricEthMonInstanceId OBJECT-TYPE
    SYNTAX       CfprManagedObjectId
    MAX-ACCESS   not-accessible
    STATUS       current
    DESCRIPTION
        "Instance identifier of the managed object."
    ::= { cfprFabricEthMonEntry 1 }

cfprFabricEthMonDn OBJECT-TYPE
    SYNTAX       CfprManagedObjectDn
    MAX-ACCESS   read-only
    STATUS       current
    DESCRIPTION
        "Cisco Firepower fabric:EthMon:dn managed object property"
    ::= { cfprFabricEthMonEntry 2 }

cfprFabricEthMonRn OBJECT-TYPE
    SYNTAX       SnmpAdminString
    MAX-ACCESS   read-only
    STATUS       current
    DESCRIPTION
        "Cisco Firepower fabric:EthMon:rn managed object property"
    ::= { cfprFabricEthMonEntry 3 }

cfprFabricEthMonAdminState OBJECT-TYPE
    SYNTAX       CfprFabricMonAdminState
    MAX-ACCESS   read-only
    STATUS       current
    DESCRIPTION
        "Cisco Firepower fabric:EthMon:adminState managed object property"
    ::= { cfprFabricEthMonEntry 4 }

cfprFabricEthMonConfigFailReason OBJECT-TYPE
    SYNTAX       SnmpAdminString
    MAX-ACCESS   read-only
    STATUS       current
    DESCRIPTION
        "Cisco Firepower fabric:EthMon:configFailReason
        managed object property"
    ::= { cfprFabricEthMonEntry 5 }

cfprFabricEthMonId OBJECT-TYPE
    SYNTAX       CfprNetworkSwitchId
    MAX-ACCESS   read-only
    STATUS       current
    DESCRIPTION
        "Cisco Firepower fabric:EthMon:id managed object property"
    ::= { cfprFabricEthMonEntry 6 }

cfprFabricEthMonIsConfigSuccess OBJECT-TYPE
    SYNTAX       TruthValue
    MAX-ACCESS   read-only
    STATUS       current
    DESCRIPTION
        "Cisco Firepower fabric:EthMon:isConfigSuccess
        managed object property"
    ::= { cfprFabricEthMonEntry 7 }

cfprFabricEthMonLocale OBJECT-TYPE
    SYNTAX       CfprFabricExternalLocale
    MAX-ACCESS   read-only
    STATUS       current
    DESCRIPTION
        "Cisco Firepower fabric:EthMon:locale managed object property"
    ::= { cfprFabricEthMonEntry 8 }

cfprFabricEthMonName OBJECT-TYPE
    SYNTAX       SnmpAdminString
    MAX-ACCESS   read-only
    STATUS       current
    DESCRIPTION
        "Cisco Firepower fabric:EthMon:name managed object property"
    ::= { cfprFabricEthMonEntry 9 }

cfprFabricEthMonOperState OBJECT-TYPE
    SYNTAX       CfprFabricMonOperState
    MAX-ACCESS   read-only
    STATUS       current
    DESCRIPTION
        "Cisco Firepower fabric:EthMon:operState managed object property"
    ::= { cfprFabricEthMonEntry 10 }

cfprFabricEthMonOperStateReason OBJECT-TYPE
    SYNTAX       CfprFabricMonOperStateReason
    MAX-ACCESS   read-only
    STATUS       current
    DESCRIPTION
        "Cisco Firepower fabric:EthMon:operStateReason
        managed object property"
    ::= { cfprFabricEthMonEntry 11 }

cfprFabricEthMonPeerDn OBJECT-TYPE
    SYNTAX       SnmpAdminString
    MAX-ACCESS   read-only
    STATUS       current
    DESCRIPTION
        "Cisco Firepower fabric:EthMon:peerDn managed object property"
    ::= { cfprFabricEthMonEntry 12 }

cfprFabricEthMonSession OBJECT-TYPE
    SYNTAX       Gauge32
    MAX-ACCESS   read-only
    STATUS       current
    DESCRIPTION
        "Cisco Firepower fabric:EthMon:session managed object property"
    ::= { cfprFabricEthMonEntry 13 }

cfprFabricEthMonTransport OBJECT-TYPE
    SYNTAX       CfprFabricEthMonTransport
    MAX-ACCESS   read-only
    STATUS       current
    DESCRIPTION
        "Cisco Firepower fabric:EthMon:transport managed object property"
    ::= { cfprFabricEthMonEntry 14 }

cfprFabricEthMonType OBJECT-TYPE
    SYNTAX       CfprFabricEthMonType
    MAX-ACCESS   read-only
    STATUS       current
    DESCRIPTION
        "Cisco Firepower fabric:EthMon:type managed object property"
    ::= { cfprFabricEthMonEntry 15 }

cfprFabricEthMonDestEpTable OBJECT-TYPE
    SYNTAX           SEQUENCE OF CfprFabricEthMonDestEpEntry
    MAX-ACCESS       not-accessible
    STATUS           current
    DESCRIPTION
        "Cisco Firepower fabric:EthMonDestEp managed object table"
    ::= { cfprFabricObjects 36 }

cfprFabricEthMonDestEpEntry OBJECT-TYPE
    SYNTAX           CfprFabricEthMonDestEpEntry
    MAX-ACCESS       not-accessible
    STATUS           current
    DESCRIPTION
        "Entry for the cfprFabricEthMonDestEpTable table."
    INDEX { cfprFabricEthMonDestEpInstanceId }
    ::= { cfprFabricEthMonDestEpTable 1 }

CfprFabricEthMonDestEpEntry ::= SEQUENCE {
    cfprFabricEthMonDestEpInstanceId                                 CfprManagedObjectId,
    cfprFabricEthMonDestEpDn                                         CfprManagedObjectDn,
    cfprFabricEthMonDestEpRn                                         SnmpAdminString,
    cfprFabricEthMonDestEpAdminSpeed                                 CfprFabricEthMonDestEpAdminSpeed,
    cfprFabricEthMonDestEpAdminState                                 CfprFabricExternalEpAdminState,
    cfprFabricEthMonDestEpAggrPortId                                 Gauge32,
    cfprFabricEthMonDestEpChassisId                                  Gauge32,
    cfprFabricEthMonDestEpEpDn                                       SnmpAdminString,
    cfprFabricEthMonDestEpFltAggr                                    Unsigned64,
    cfprFabricEthMonDestEpIfRole                                     CfprFabricEthMonDestEpIfRole,
    cfprFabricEthMonDestEpIfType                                     CfprFabricPIoEpIfType,
    cfprFabricEthMonDestEpLicGP                                      Unsigned64,
    cfprFabricEthMonDestEpLicState                                   CfprLicenseState,
    cfprFabricEthMonDestEpLocale                                     CfprFabricExternalEpLocale,
    cfprFabricEthMonDestEpName                                       SnmpAdminString,
    cfprFabricEthMonDestEpOperState                                  CfprFabricPIoEpOperState,
    cfprFabricEthMonDestEpOperStateReason                            SnmpAdminString,
    cfprFabricEthMonDestEpPeerAggrPortId                             Gauge32,
    cfprFabricEthMonDestEpPeerChassisId                              Gauge32,
    cfprFabricEthMonDestEpPeerDn                                     SnmpAdminString,
    cfprFabricEthMonDestEpPeerPortId                                 Gauge32,
    cfprFabricEthMonDestEpPeerSlotId                                 Gauge32,
    cfprFabricEthMonDestEpPortId                                     CfprFabricEthMonDestEpPortId,
    cfprFabricEthMonDestEpSlotId                                     CfprFabricEthMonDestEpSlotId,
    cfprFabricEthMonDestEpSwitchId                                   CfprNetworkSwitchId,
    cfprFabricEthMonDestEpTransport                                  CfprNetworkTransport,
    cfprFabricEthMonDestEpType                                       CfprFabricEthMonDestEpType,
    cfprFabricEthMonDestEpWarnings                                   CfprFabricWarnings
}

cfprFabricEthMonDestEpInstanceId OBJECT-TYPE
    SYNTAX       CfprManagedObjectId
    MAX-ACCESS   not-accessible
    STATUS       current
    DESCRIPTION
        "Instance identifier of the managed object."
    ::= { cfprFabricEthMonDestEpEntry 1 }

cfprFabricEthMonDestEpDn OBJECT-TYPE
    SYNTAX       CfprManagedObjectDn
    MAX-ACCESS   read-only
    STATUS       current
    DESCRIPTION
        "Cisco Firepower fabric:EthMonDestEp:dn managed object property"
    ::= { cfprFabricEthMonDestEpEntry 2 }

cfprFabricEthMonDestEpRn OBJECT-TYPE
    SYNTAX       SnmpAdminString
    MAX-ACCESS   read-only
    STATUS       current
    DESCRIPTION
        "Cisco Firepower fabric:EthMonDestEp:rn managed object property"
    ::= { cfprFabricEthMonDestEpEntry 3 }

cfprFabricEthMonDestEpAdminSpeed OBJECT-TYPE
    SYNTAX       CfprFabricEthMonDestEpAdminSpeed
    MAX-ACCESS   read-only
    STATUS       current
    DESCRIPTION
        "Cisco Firepower fabric:EthMonDestEp:adminSpeed
        managed object property"
    ::= { cfprFabricEthMonDestEpEntry 4 }

cfprFabricEthMonDestEpAdminState OBJECT-TYPE
    SYNTAX       CfprFabricExternalEpAdminState
    MAX-ACCESS   read-only
    STATUS       current
    DESCRIPTION
        "Cisco Firepower fabric:EthMonDestEp:adminState
        managed object property"
    ::= { cfprFabricEthMonDestEpEntry 5 }

cfprFabricEthMonDestEpAggrPortId OBJECT-TYPE
    SYNTAX       Gauge32
    MAX-ACCESS   read-only
    STATUS       current
    DESCRIPTION
        "Cisco Firepower fabric:EthMonDestEp:aggrPortId
        managed object property"
    ::= { cfprFabricEthMonDestEpEntry 6 }

cfprFabricEthMonDestEpChassisId OBJECT-TYPE
    SYNTAX       Gauge32
    MAX-ACCESS   read-only
    STATUS       current
    DESCRIPTION
        "Cisco Firepower fabric:EthMonDestEp:chassisId
        managed object property"
    ::= { cfprFabricEthMonDestEpEntry 7 }

cfprFabricEthMonDestEpEpDn OBJECT-TYPE
    SYNTAX       SnmpAdminString
    MAX-ACCESS   read-only
    STATUS       current
    DESCRIPTION
        "Cisco Firepower fabric:EthMonDestEp:epDn managed object property"
    ::= { cfprFabricEthMonDestEpEntry 8 }

cfprFabricEthMonDestEpFltAggr OBJECT-TYPE
    SYNTAX       Unsigned64
    MAX-ACCESS   read-only
    STATUS       current
    DESCRIPTION
        "Cisco Firepower fabric:EthMonDestEp:fltAggr managed
        object property"
    ::= { cfprFabricEthMonDestEpEntry 9 }

cfprFabricEthMonDestEpIfRole OBJECT-TYPE
    SYNTAX       CfprFabricEthMonDestEpIfRole
    MAX-ACCESS   read-only
    STATUS       current
    DESCRIPTION
        "Cisco Firepower fabric:EthMonDestEp:ifRole managed
        object property"
    ::= { cfprFabricEthMonDestEpEntry 10 }

cfprFabricEthMonDestEpIfType OBJECT-TYPE
    SYNTAX       CfprFabricPIoEpIfType
    MAX-ACCESS   read-only
    STATUS       current
    DESCRIPTION
        "Cisco Firepower fabric:EthMonDestEp:ifType managed
        object property"
    ::= { cfprFabricEthMonDestEpEntry 11 }

cfprFabricEthMonDestEpLicGP OBJECT-TYPE
    SYNTAX       Unsigned64
    MAX-ACCESS   read-only
    STATUS       current
    DESCRIPTION
        "Cisco Firepower fabric:EthMonDestEp:licGP managed
        object property"
    ::= { cfprFabricEthMonDestEpEntry 12 }

cfprFabricEthMonDestEpLicState OBJECT-TYPE
    SYNTAX       CfprLicenseState
    MAX-ACCESS   read-only
    STATUS       current
    DESCRIPTION
        "Cisco Firepower fabric:EthMonDestEp:licState managed
        object property"
    ::= { cfprFabricEthMonDestEpEntry 13 }

cfprFabricEthMonDestEpLocale OBJECT-TYPE
    SYNTAX       CfprFabricExternalEpLocale
    MAX-ACCESS   read-only
    STATUS       current
    DESCRIPTION
        "Cisco Firepower fabric:EthMonDestEp:locale managed
        object property"
    ::= { cfprFabricEthMonDestEpEntry 14 }

cfprFabricEthMonDestEpName OBJECT-TYPE
    SYNTAX       SnmpAdminString
    MAX-ACCESS   read-only
    STATUS       current
    DESCRIPTION
        "Cisco Firepower fabric:EthMonDestEp:name managed object property"
    ::= { cfprFabricEthMonDestEpEntry 15 }

cfprFabricEthMonDestEpOperState OBJECT-TYPE
    SYNTAX       CfprFabricPIoEpOperState
    MAX-ACCESS   read-only
    STATUS       current
    DESCRIPTION
        "Cisco Firepower fabric:EthMonDestEp:operState
        managed object property"
    ::= { cfprFabricEthMonDestEpEntry 16 }

cfprFabricEthMonDestEpOperStateReason OBJECT-TYPE
    SYNTAX       SnmpAdminString
    MAX-ACCESS   read-only
    STATUS       current
    DESCRIPTION
        "Cisco Firepower fabric:EthMonDestEp:operStateReason
        managed object property"
    ::= { cfprFabricEthMonDestEpEntry 17 }

cfprFabricEthMonDestEpPeerAggrPortId OBJECT-TYPE
    SYNTAX       Gauge32
    MAX-ACCESS   read-only
    STATUS       current
    DESCRIPTION
        "Cisco Firepower fabric:EthMonDestEp:peerAggrPortId
        managed object property"
    ::= { cfprFabricEthMonDestEpEntry 18 }

cfprFabricEthMonDestEpPeerChassisId OBJECT-TYPE
    SYNTAX       Gauge32
    MAX-ACCESS   read-only
    STATUS       current
    DESCRIPTION
        "Cisco Firepower fabric:EthMonDestEp:peerChassisId
        managed object property"
    ::= { cfprFabricEthMonDestEpEntry 19 }

cfprFabricEthMonDestEpPeerDn OBJECT-TYPE
    SYNTAX       SnmpAdminString
    MAX-ACCESS   read-only
    STATUS       current
    DESCRIPTION
        "Cisco Firepower fabric:EthMonDestEp:peerDn managed
        object property"
    ::= { cfprFabricEthMonDestEpEntry 20 }

cfprFabricEthMonDestEpPeerPortId OBJECT-TYPE
    SYNTAX       Gauge32
    MAX-ACCESS   read-only
    STATUS       current
    DESCRIPTION
        "Cisco Firepower fabric:EthMonDestEp:peerPortId
        managed object property"
    ::= { cfprFabricEthMonDestEpEntry 21 }

cfprFabricEthMonDestEpPeerSlotId OBJECT-TYPE
    SYNTAX       Gauge32
    MAX-ACCESS   read-only
    STATUS       current
    DESCRIPTION
        "Cisco Firepower fabric:EthMonDestEp:peerSlotId
        managed object property"
    ::= { cfprFabricEthMonDestEpEntry 22 }

cfprFabricEthMonDestEpPortId OBJECT-TYPE
    SYNTAX       CfprFabricEthMonDestEpPortId
    MAX-ACCESS   read-only
    STATUS       current
    DESCRIPTION
        "Cisco Firepower fabric:EthMonDestEp:portId managed
        object property"
    ::= { cfprFabricEthMonDestEpEntry 23 }

cfprFabricEthMonDestEpSlotId OBJECT-TYPE
    SYNTAX       CfprFabricEthMonDestEpSlotId
    MAX-ACCESS   read-only
    STATUS       current
    DESCRIPTION
        "Cisco Firepower fabric:EthMonDestEp:slotId managed
        object property"
    ::= { cfprFabricEthMonDestEpEntry 24 }

cfprFabricEthMonDestEpSwitchId OBJECT-TYPE
    SYNTAX       CfprNetworkSwitchId
    MAX-ACCESS   read-only
    STATUS       current
    DESCRIPTION
        "Cisco Firepower fabric:EthMonDestEp:switchId managed
        object property"
    ::= { cfprFabricEthMonDestEpEntry 25 }

cfprFabricEthMonDestEpTransport OBJECT-TYPE
    SYNTAX       CfprNetworkTransport
    MAX-ACCESS   read-only
    STATUS       current
    DESCRIPTION
        "Cisco Firepower fabric:EthMonDestEp:transport
        managed object property"
    ::= { cfprFabricEthMonDestEpEntry 26 }

cfprFabricEthMonDestEpType OBJECT-TYPE
    SYNTAX       CfprFabricEthMonDestEpType
    MAX-ACCESS   read-only
    STATUS       current
    DESCRIPTION
        "Cisco Firepower fabric:EthMonDestEp:type managed object property"
    ::= { cfprFabricEthMonDestEpEntry 27 }

cfprFabricEthMonDestEpWarnings OBJECT-TYPE
    SYNTAX       CfprFabricWarnings
    MAX-ACCESS   read-only
    STATUS       current
    DESCRIPTION
        "Cisco Firepower fabric:EthMonDestEp:warnings managed
        object property"
    ::= { cfprFabricEthMonDestEpEntry 28 }

cfprFabricEthMonFiltEpTable OBJECT-TYPE
    SYNTAX           SEQUENCE OF CfprFabricEthMonFiltEpEntry
    MAX-ACCESS       not-accessible
    STATUS           current
    DESCRIPTION
        "Cisco Firepower fabric:EthMonFiltEp managed object table"
    ::= { cfprFabricObjects 37 }

cfprFabricEthMonFiltEpEntry OBJECT-TYPE
    SYNTAX           CfprFabricEthMonFiltEpEntry
    MAX-ACCESS       not-accessible
    STATUS           current
    DESCRIPTION
        "Entry for the cfprFabricEthMonFiltEpTable table."
    INDEX { cfprFabricEthMonFiltEpInstanceId }
    ::= { cfprFabricEthMonFiltEpTable 1 }

CfprFabricEthMonFiltEpEntry ::= SEQUENCE {
    cfprFabricEthMonFiltEpInstanceId                                 CfprManagedObjectId,
    cfprFabricEthMonFiltEpDn                                         CfprManagedObjectDn,
    cfprFabricEthMonFiltEpRn                                         SnmpAdminString,
    cfprFabricEthMonFiltEpName                                       SnmpAdminString,
    cfprFabricEthMonFiltEpSession                                    Gauge32,
    cfprFabricEthMonFiltEpType                                       CfprFabricEthMonFiltEpType
}

cfprFabricEthMonFiltEpInstanceId OBJECT-TYPE
    SYNTAX       CfprManagedObjectId
    MAX-ACCESS   not-accessible
    STATUS       current
    DESCRIPTION
        "Instance identifier of the managed object."
    ::= { cfprFabricEthMonFiltEpEntry 1 }

cfprFabricEthMonFiltEpDn OBJECT-TYPE
    SYNTAX       CfprManagedObjectDn
    MAX-ACCESS   read-only
    STATUS       current
    DESCRIPTION
        "Cisco Firepower fabric:EthMonFiltEp:dn managed object property"
    ::= { cfprFabricEthMonFiltEpEntry 2 }

cfprFabricEthMonFiltEpRn OBJECT-TYPE
    SYNTAX       SnmpAdminString
    MAX-ACCESS   read-only
    STATUS       current
    DESCRIPTION
        "Cisco Firepower fabric:EthMonFiltEp:rn managed object property"
    ::= { cfprFabricEthMonFiltEpEntry 3 }

cfprFabricEthMonFiltEpName OBJECT-TYPE
    SYNTAX       SnmpAdminString
    MAX-ACCESS   read-only
    STATUS       current
    DESCRIPTION
        "Cisco Firepower fabric:EthMonFiltEp:name managed object property"
    ::= { cfprFabricEthMonFiltEpEntry 4 }

cfprFabricEthMonFiltEpSession OBJECT-TYPE
    SYNTAX       Gauge32
    MAX-ACCESS   read-only
    STATUS       current
    DESCRIPTION
        "Cisco Firepower fabric:EthMonFiltEp:session managed
        object property"
    ::= { cfprFabricEthMonFiltEpEntry 5 }

cfprFabricEthMonFiltEpType OBJECT-TYPE
    SYNTAX       CfprFabricEthMonFiltEpType
    MAX-ACCESS   read-only
    STATUS       current
    DESCRIPTION
        "Cisco Firepower fabric:EthMonFiltEp:type managed object property"
    ::= { cfprFabricEthMonFiltEpEntry 6 }

cfprFabricEthMonFiltRefTable OBJECT-TYPE
    SYNTAX           SEQUENCE OF CfprFabricEthMonFiltRefEntry
    MAX-ACCESS       not-accessible
    STATUS           current
    DESCRIPTION
        "Cisco Firepower fabric:EthMonFiltRef managed object table"
    ::= { cfprFabricObjects 38 }

cfprFabricEthMonFiltRefEntry OBJECT-TYPE
    SYNTAX           CfprFabricEthMonFiltRefEntry
    MAX-ACCESS       not-accessible
    STATUS           current
    DESCRIPTION
        "Entry for the cfprFabricEthMonFiltRefTable table."
    INDEX { cfprFabricEthMonFiltRefInstanceId }
    ::= { cfprFabricEthMonFiltRefTable 1 }

CfprFabricEthMonFiltRefEntry ::= SEQUENCE {
    cfprFabricEthMonFiltRefInstanceId                                CfprManagedObjectId,
    cfprFabricEthMonFiltRefDn                                        CfprManagedObjectDn,
    cfprFabricEthMonFiltRefRn                                        SnmpAdminString,
    cfprFabricEthMonFiltRefSrcFiltDn                                 SnmpAdminString,
    cfprFabricEthMonFiltRefType                                      CfprFabricEthMonFiltRefType
}

cfprFabricEthMonFiltRefInstanceId OBJECT-TYPE
    SYNTAX       CfprManagedObjectId
    MAX-ACCESS   not-accessible
    STATUS       current
    DESCRIPTION
        "Instance identifier of the managed object."
    ::= { cfprFabricEthMonFiltRefEntry 1 }

cfprFabricEthMonFiltRefDn OBJECT-TYPE
    SYNTAX       CfprManagedObjectDn
    MAX-ACCESS   read-only
    STATUS       current
    DESCRIPTION
        "Cisco Firepower fabric:EthMonFiltRef:dn managed object property"
    ::= { cfprFabricEthMonFiltRefEntry 2 }

cfprFabricEthMonFiltRefRn OBJECT-TYPE
    SYNTAX       SnmpAdminString
    MAX-ACCESS   read-only
    STATUS       current
    DESCRIPTION
        "Cisco Firepower fabric:EthMonFiltRef:rn managed object property"
    ::= { cfprFabricEthMonFiltRefEntry 3 }

cfprFabricEthMonFiltRefSrcFiltDn OBJECT-TYPE
    SYNTAX       SnmpAdminString
    MAX-ACCESS   read-only
    STATUS       current
    DESCRIPTION
        "Cisco Firepower fabric:EthMonFiltRef:srcFiltDn
        managed object property"
    ::= { cfprFabricEthMonFiltRefEntry 4 }

cfprFabricEthMonFiltRefType OBJECT-TYPE
    SYNTAX       CfprFabricEthMonFiltRefType
    MAX-ACCESS   read-only
    STATUS       current
    DESCRIPTION
        "Cisco Firepower fabric:EthMonFiltRef:type managed
        object property"
    ::= { cfprFabricEthMonFiltRefEntry 5 }

cfprFabricEthMonLanTable OBJECT-TYPE
    SYNTAX           SEQUENCE OF CfprFabricEthMonLanEntry
    MAX-ACCESS       not-accessible
    STATUS           current
    DESCRIPTION
        "Cisco Firepower fabric:EthMonLan managed object table"
    ::= { cfprFabricObjects 39 }

cfprFabricEthMonLanEntry OBJECT-TYPE
    SYNTAX           CfprFabricEthMonLanEntry
    MAX-ACCESS       not-accessible
    STATUS           current
    DESCRIPTION
        "Entry for the cfprFabricEthMonLanTable table."
    INDEX { cfprFabricEthMonLanInstanceId }
    ::= { cfprFabricEthMonLanTable 1 }

CfprFabricEthMonLanEntry ::= SEQUENCE {
    cfprFabricEthMonLanInstanceId                                    CfprManagedObjectId,
    cfprFabricEthMonLanDn                                            CfprManagedObjectDn,
    cfprFabricEthMonLanRn                                            SnmpAdminString,
    cfprFabricEthMonLanId                                            CfprNetworkSwitchId,
    cfprFabricEthMonLanLocale                                        CfprFabricExternalLocale,
    cfprFabricEthMonLanName                                          SnmpAdminString,
    cfprFabricEthMonLanTransport                                     CfprFabricEthMonLanTransport,
    cfprFabricEthMonLanType                                          CfprFabricEthMonLanType
}

cfprFabricEthMonLanInstanceId OBJECT-TYPE
    SYNTAX       CfprManagedObjectId
    MAX-ACCESS   not-accessible
    STATUS       current
    DESCRIPTION
        "Instance identifier of the managed object."
    ::= { cfprFabricEthMonLanEntry 1 }

cfprFabricEthMonLanDn OBJECT-TYPE
    SYNTAX       CfprManagedObjectDn
    MAX-ACCESS   read-only
    STATUS       current
    DESCRIPTION
        "Cisco Firepower fabric:EthMonLan:dn managed object property"
    ::= { cfprFabricEthMonLanEntry 2 }

cfprFabricEthMonLanRn OBJECT-TYPE
    SYNTAX       SnmpAdminString
    MAX-ACCESS   read-only
    STATUS       current
    DESCRIPTION
        "Cisco Firepower fabric:EthMonLan:rn managed object property"
    ::= { cfprFabricEthMonLanEntry 3 }

cfprFabricEthMonLanId OBJECT-TYPE
    SYNTAX       CfprNetworkSwitchId
    MAX-ACCESS   read-only
    STATUS       current
    DESCRIPTION
        "Cisco Firepower fabric:EthMonLan:id managed object property"
    ::= { cfprFabricEthMonLanEntry 4 }

cfprFabricEthMonLanLocale OBJECT-TYPE
    SYNTAX       CfprFabricExternalLocale
    MAX-ACCESS   read-only
    STATUS       current
    DESCRIPTION
        "Cisco Firepower fabric:EthMonLan:locale managed object property"
    ::= { cfprFabricEthMonLanEntry 5 }

cfprFabricEthMonLanName OBJECT-TYPE
    SYNTAX       SnmpAdminString
    MAX-ACCESS   read-only
    STATUS       current
    DESCRIPTION
        "Cisco Firepower fabric:EthMonLan:name managed object property"
    ::= { cfprFabricEthMonLanEntry 6 }

cfprFabricEthMonLanTransport OBJECT-TYPE
    SYNTAX       CfprFabricEthMonLanTransport
    MAX-ACCESS   read-only
    STATUS       current
    DESCRIPTION
        "Cisco Firepower fabric:EthMonLan:transport managed
        object property"
    ::= { cfprFabricEthMonLanEntry 7 }

cfprFabricEthMonLanType OBJECT-TYPE
    SYNTAX       CfprFabricEthMonLanType
    MAX-ACCESS   read-only
    STATUS       current
    DESCRIPTION
        "Cisco Firepower fabric:EthMonLan:type managed object property"
    ::= { cfprFabricEthMonLanEntry 8 }

cfprFabricEthMonSrcEpTable OBJECT-TYPE
    SYNTAX           SEQUENCE OF CfprFabricEthMonSrcEpEntry
    MAX-ACCESS       not-accessible
    STATUS           current
    DESCRIPTION
        "Cisco Firepower fabric:EthMonSrcEp managed object table"
    ::= { cfprFabricObjects 40 }

cfprFabricEthMonSrcEpEntry OBJECT-TYPE
    SYNTAX           CfprFabricEthMonSrcEpEntry
    MAX-ACCESS       not-accessible
    STATUS           current
    DESCRIPTION
        "Entry for the cfprFabricEthMonSrcEpTable table."
    INDEX { cfprFabricEthMonSrcEpInstanceId }
    ::= { cfprFabricEthMonSrcEpTable 1 }

CfprFabricEthMonSrcEpEntry ::= SEQUENCE {
    cfprFabricEthMonSrcEpInstanceId                                  CfprManagedObjectId,
    cfprFabricEthMonSrcEpDn                                          CfprManagedObjectDn,
    cfprFabricEthMonSrcEpRn                                          SnmpAdminString,
    cfprFabricEthMonSrcEpDirection                                   CfprFabricTrafficDirection,
    cfprFabricEthMonSrcEpName                                        SnmpAdminString,
    cfprFabricEthMonSrcEpSession                                     Gauge32,
    cfprFabricEthMonSrcEpTransport                                   CfprNetworkTransport,
    cfprFabricEthMonSrcEpType                                        CfprFabricEthMonSrcEpType
}

cfprFabricEthMonSrcEpInstanceId OBJECT-TYPE
    SYNTAX       CfprManagedObjectId
    MAX-ACCESS   not-accessible
    STATUS       current
    DESCRIPTION
        "Instance identifier of the managed object."
    ::= { cfprFabricEthMonSrcEpEntry 1 }

cfprFabricEthMonSrcEpDn OBJECT-TYPE
    SYNTAX       CfprManagedObjectDn
    MAX-ACCESS   read-only
    STATUS       current
    DESCRIPTION
        "Cisco Firepower fabric:EthMonSrcEp:dn managed object property"
    ::= { cfprFabricEthMonSrcEpEntry 2 }

cfprFabricEthMonSrcEpRn OBJECT-TYPE
    SYNTAX       SnmpAdminString
    MAX-ACCESS   read-only
    STATUS       current
    DESCRIPTION
        "Cisco Firepower fabric:EthMonSrcEp:rn managed object property"
    ::= { cfprFabricEthMonSrcEpEntry 3 }

cfprFabricEthMonSrcEpDirection OBJECT-TYPE
    SYNTAX       CfprFabricTrafficDirection
    MAX-ACCESS   read-only
    STATUS       current
    DESCRIPTION
        "Cisco Firepower fabric:EthMonSrcEp:direction managed
        object property"
    ::= { cfprFabricEthMonSrcEpEntry 4 }

cfprFabricEthMonSrcEpName OBJECT-TYPE
    SYNTAX       SnmpAdminString
    MAX-ACCESS   read-only
    STATUS       current
    DESCRIPTION
        "Cisco Firepower fabric:EthMonSrcEp:name managed object property"
    ::= { cfprFabricEthMonSrcEpEntry 5 }

cfprFabricEthMonSrcEpSession OBJECT-TYPE
    SYNTAX       Gauge32
    MAX-ACCESS   read-only
    STATUS       current
    DESCRIPTION
        "Cisco Firepower fabric:EthMonSrcEp:session managed
        object property"
    ::= { cfprFabricEthMonSrcEpEntry 6 }

cfprFabricEthMonSrcEpTransport OBJECT-TYPE
    SYNTAX       CfprNetworkTransport
    MAX-ACCESS   read-only
    STATUS       current
    DESCRIPTION
        "Cisco Firepower fabric:EthMonSrcEp:transport managed
        object property"
    ::= { cfprFabricEthMonSrcEpEntry 7 }

cfprFabricEthMonSrcEpType OBJECT-TYPE
    SYNTAX       CfprFabricEthMonSrcEpType
    MAX-ACCESS   read-only
    STATUS       current
    DESCRIPTION
        "Cisco Firepower fabric:EthMonSrcEp:type managed object property"
    ::= { cfprFabricEthMonSrcEpEntry 8 }

cfprFabricEthMonSrcRefTable OBJECT-TYPE
    SYNTAX           SEQUENCE OF CfprFabricEthMonSrcRefEntry
    MAX-ACCESS       not-accessible
    STATUS           current
    DESCRIPTION
        "Cisco Firepower fabric:EthMonSrcRef managed object table"
    ::= { cfprFabricObjects 41 }

cfprFabricEthMonSrcRefEntry OBJECT-TYPE
    SYNTAX           CfprFabricEthMonSrcRefEntry
    MAX-ACCESS       not-accessible
    STATUS           current
    DESCRIPTION
        "Entry for the cfprFabricEthMonSrcRefTable table."
    INDEX { cfprFabricEthMonSrcRefInstanceId }
    ::= { cfprFabricEthMonSrcRefTable 1 }

CfprFabricEthMonSrcRefEntry ::= SEQUENCE {
    cfprFabricEthMonSrcRefInstanceId                                 CfprManagedObjectId,
    cfprFabricEthMonSrcRefDn                                         CfprManagedObjectDn,
    cfprFabricEthMonSrcRefRn                                         SnmpAdminString,
    cfprFabricEthMonSrcRefId                                         Unsigned64,
    cfprFabricEthMonSrcRefSourceDn                                   SnmpAdminString,
    cfprFabricEthMonSrcRefSourceType                                 CfprFabricEthSourceType,
    cfprFabricEthMonSrcRefType                                       CfprFabricEthMonSrcRefType
}

cfprFabricEthMonSrcRefInstanceId OBJECT-TYPE
    SYNTAX       CfprManagedObjectId
    MAX-ACCESS   not-accessible
    STATUS       current
    DESCRIPTION
        "Instance identifier of the managed object."
    ::= { cfprFabricEthMonSrcRefEntry 1 }

cfprFabricEthMonSrcRefDn OBJECT-TYPE
    SYNTAX       CfprManagedObjectDn
    MAX-ACCESS   read-only
    STATUS       current
    DESCRIPTION
        "Cisco Firepower fabric:EthMonSrcRef:dn managed object property"
    ::= { cfprFabricEthMonSrcRefEntry 2 }

cfprFabricEthMonSrcRefRn OBJECT-TYPE
    SYNTAX       SnmpAdminString
    MAX-ACCESS   read-only
    STATUS       current
    DESCRIPTION
        "Cisco Firepower fabric:EthMonSrcRef:rn managed object property"
    ::= { cfprFabricEthMonSrcRefEntry 3 }

cfprFabricEthMonSrcRefId OBJECT-TYPE
    SYNTAX       Unsigned64
    MAX-ACCESS   read-only
    STATUS       current
    DESCRIPTION
        "Cisco Firepower fabric:EthMonSrcRef:id managed object property"
    ::= { cfprFabricEthMonSrcRefEntry 4 }

cfprFabricEthMonSrcRefSourceDn OBJECT-TYPE
    SYNTAX       SnmpAdminString
    MAX-ACCESS   read-only
    STATUS       current
    DESCRIPTION
        "Cisco Firepower fabric:EthMonSrcRef:sourceDn managed
        object property"
    ::= { cfprFabricEthMonSrcRefEntry 5 }

cfprFabricEthMonSrcRefSourceType OBJECT-TYPE
    SYNTAX       CfprFabricEthSourceType
    MAX-ACCESS   read-only
    STATUS       current
    DESCRIPTION
        "Cisco Firepower fabric:EthMonSrcRef:sourceType
        managed object property"
    ::= { cfprFabricEthMonSrcRefEntry 6 }

cfprFabricEthMonSrcRefType OBJECT-TYPE
    SYNTAX       CfprFabricEthMonSrcRefType
    MAX-ACCESS   read-only
    STATUS       current
    DESCRIPTION
        "Cisco Firepower fabric:EthMonSrcRef:type managed object property"
    ::= { cfprFabricEthMonSrcRefEntry 7 }

cfprFabricEthTargetEpTable OBJECT-TYPE
    SYNTAX           SEQUENCE OF CfprFabricEthTargetEpEntry
    MAX-ACCESS       not-accessible
    STATUS           current
    DESCRIPTION
        "Cisco Firepower fabric:EthTargetEp managed object table"
    ::= { cfprFabricObjects 42 }

cfprFabricEthTargetEpEntry OBJECT-TYPE
    SYNTAX           CfprFabricEthTargetEpEntry
    MAX-ACCESS       not-accessible
    STATUS           current
    DESCRIPTION
        "Entry for the cfprFabricEthTargetEpTable table."
    INDEX { cfprFabricEthTargetEpInstanceId }
    ::= { cfprFabricEthTargetEpTable 1 }

CfprFabricEthTargetEpEntry ::= SEQUENCE {
    cfprFabricEthTargetEpInstanceId                                  CfprManagedObjectId,
    cfprFabricEthTargetEpDn                                          CfprManagedObjectDn,
    cfprFabricEthTargetEpRn                                          SnmpAdminString,
    cfprFabricEthTargetEpAdminState                                  CfprFabricExternalEpAdminState,
    cfprFabricEthTargetEpAggrPortId                                  Gauge32,
    cfprFabricEthTargetEpChassisId                                   Gauge32,
    cfprFabricEthTargetEpEpDn                                        SnmpAdminString,
    cfprFabricEthTargetEpFltAggr                                     Unsigned64,
    cfprFabricEthTargetEpIfRole                                      CfprNetworkPortRole,
    cfprFabricEthTargetEpIfType                                      CfprFabricPIoEpIfType,
    cfprFabricEthTargetEpLicGP                                       Unsigned64,
    cfprFabricEthTargetEpLicState                                    CfprLicenseState,
    cfprFabricEthTargetEpLocale                                      CfprFabricExternalEpLocale,
    cfprFabricEthTargetEpMacAddress                                  MacAddress,
    cfprFabricEthTargetEpName                                        SnmpAdminString,
    cfprFabricEthTargetEpOperState                                   CfprFabricPIoEpOperState,
    cfprFabricEthTargetEpOperStateReason                             SnmpAdminString,
    cfprFabricEthTargetEpPeerAggrPortId                              Gauge32,
    cfprFabricEthTargetEpPeerChassisId                               Gauge32,
    cfprFabricEthTargetEpPeerDn                                      SnmpAdminString,
    cfprFabricEthTargetEpPeerPortId                                  Gauge32,
    cfprFabricEthTargetEpPeerSlotId                                  Gauge32,
    cfprFabricEthTargetEpPortId                                      CfprFabricPIoEpPortId,
    cfprFabricEthTargetEpSlotId                                      CfprFabricPIoEpSlotId,
    cfprFabricEthTargetEpSwitchId                                    CfprNetworkSwitchId,
    cfprFabricEthTargetEpTransport                                   CfprFabricEthTargetEpTransport,
    cfprFabricEthTargetEpType                                        CfprFabricTargetEpType,
    cfprFabricEthTargetEpWarnings                                    CfprFabricWarnings
}

cfprFabricEthTargetEpInstanceId OBJECT-TYPE
    SYNTAX       CfprManagedObjectId
    MAX-ACCESS   not-accessible
    STATUS       current
    DESCRIPTION
        "Instance identifier of the managed object."
    ::= { cfprFabricEthTargetEpEntry 1 }

cfprFabricEthTargetEpDn OBJECT-TYPE
    SYNTAX       CfprManagedObjectDn
    MAX-ACCESS   read-only
    STATUS       current
    DESCRIPTION
        "Cisco Firepower fabric:EthTargetEp:dn managed object property"
    ::= { cfprFabricEthTargetEpEntry 2 }

cfprFabricEthTargetEpRn OBJECT-TYPE
    SYNTAX       SnmpAdminString
    MAX-ACCESS   read-only
    STATUS       current
    DESCRIPTION
        "Cisco Firepower fabric:EthTargetEp:rn managed object property"
    ::= { cfprFabricEthTargetEpEntry 3 }

cfprFabricEthTargetEpAdminState OBJECT-TYPE
    SYNTAX       CfprFabricExternalEpAdminState
    MAX-ACCESS   read-only
    STATUS       current
    DESCRIPTION
        "Cisco Firepower fabric:EthTargetEp:adminState
        managed object property"
    ::= { cfprFabricEthTargetEpEntry 4 }

cfprFabricEthTargetEpAggrPortId OBJECT-TYPE
    SYNTAX       Gauge32
    MAX-ACCESS   read-only
    STATUS       current
    DESCRIPTION
        "Cisco Firepower fabric:EthTargetEp:aggrPortId
        managed object property"
    ::= { cfprFabricEthTargetEpEntry 5 }

cfprFabricEthTargetEpChassisId OBJECT-TYPE
    SYNTAX       Gauge32
    MAX-ACCESS   read-only
    STATUS       current
    DESCRIPTION
        "Cisco Firepower fabric:EthTargetEp:chassisId managed
        object property"
    ::= { cfprFabricEthTargetEpEntry 6 }

cfprFabricEthTargetEpEpDn OBJECT-TYPE
    SYNTAX       SnmpAdminString
    MAX-ACCESS   read-only
    STATUS       current
    DESCRIPTION
        "Cisco Firepower fabric:EthTargetEp:epDn managed object property"
    ::= { cfprFabricEthTargetEpEntry 7 }

cfprFabricEthTargetEpFltAggr OBJECT-TYPE
    SYNTAX       Unsigned64
    MAX-ACCESS   read-only
    STATUS       current
    DESCRIPTION
        "Cisco Firepower fabric:EthTargetEp:fltAggr managed
        object property"
    ::= { cfprFabricEthTargetEpEntry 8 }

cfprFabricEthTargetEpIfRole OBJECT-TYPE
    SYNTAX       CfprNetworkPortRole
    MAX-ACCESS   read-only
    STATUS       current
    DESCRIPTION
        "Cisco Firepower fabric:EthTargetEp:ifRole managed
        object property"
    ::= { cfprFabricEthTargetEpEntry 9 }

cfprFabricEthTargetEpIfType OBJECT-TYPE
    SYNTAX       CfprFabricPIoEpIfType
    MAX-ACCESS   read-only
    STATUS       current
    DESCRIPTION
        "Cisco Firepower fabric:EthTargetEp:ifType managed
        object property"
    ::= { cfprFabricEthTargetEpEntry 10 }

cfprFabricEthTargetEpLicGP OBJECT-TYPE
    SYNTAX       Unsigned64
    MAX-ACCESS   read-only
    STATUS       current
    DESCRIPTION
        "Cisco Firepower fabric:EthTargetEp:licGP managed object property"
    ::= { cfprFabricEthTargetEpEntry 11 }

cfprFabricEthTargetEpLicState OBJECT-TYPE
    SYNTAX       CfprLicenseState
    MAX-ACCESS   read-only
    STATUS       current
    DESCRIPTION
        "Cisco Firepower fabric:EthTargetEp:licState managed
        object property"
    ::= { cfprFabricEthTargetEpEntry 12 }

cfprFabricEthTargetEpLocale OBJECT-TYPE
    SYNTAX       CfprFabricExternalEpLocale
    MAX-ACCESS   read-only
    STATUS       current
    DESCRIPTION
        "Cisco Firepower fabric:EthTargetEp:locale managed
        object property"
    ::= { cfprFabricEthTargetEpEntry 13 }

cfprFabricEthTargetEpMacAddress OBJECT-TYPE
    SYNTAX       MacAddress
    MAX-ACCESS   read-only
    STATUS       current
    DESCRIPTION
        "Cisco Firepower fabric:EthTargetEp:macAddress
        managed object property"
    ::= { cfprFabricEthTargetEpEntry 14 }

cfprFabricEthTargetEpName OBJECT-TYPE
    SYNTAX       SnmpAdminString
    MAX-ACCESS   read-only
    STATUS       current
    DESCRIPTION
        "Cisco Firepower fabric:EthTargetEp:name managed object property"
    ::= { cfprFabricEthTargetEpEntry 15 }

cfprFabricEthTargetEpOperState OBJECT-TYPE
    SYNTAX       CfprFabricPIoEpOperState
    MAX-ACCESS   read-only
    STATUS       current
    DESCRIPTION
        "Cisco Firepower fabric:EthTargetEp:operState managed
        object property"
    ::= { cfprFabricEthTargetEpEntry 16 }

cfprFabricEthTargetEpOperStateReason OBJECT-TYPE
    SYNTAX       SnmpAdminString
    MAX-ACCESS   read-only
    STATUS       current
    DESCRIPTION
        "Cisco Firepower fabric:EthTargetEp:operStateReason
        managed object property"
    ::= { cfprFabricEthTargetEpEntry 17 }

cfprFabricEthTargetEpPeerAggrPortId OBJECT-TYPE
    SYNTAX       Gauge32
    MAX-ACCESS   read-only
    STATUS       current
    DESCRIPTION
        "Cisco Firepower fabric:EthTargetEp:peerAggrPortId
        managed object property"
    ::= { cfprFabricEthTargetEpEntry 18 }

cfprFabricEthTargetEpPeerChassisId OBJECT-TYPE
    SYNTAX       Gauge32
    MAX-ACCESS   read-only
    STATUS       current
    DESCRIPTION
        "Cisco Firepower fabric:EthTargetEp:peerChassisId
        managed object property"
    ::= { cfprFabricEthTargetEpEntry 19 }

cfprFabricEthTargetEpPeerDn OBJECT-TYPE
    SYNTAX       SnmpAdminString
    MAX-ACCESS   read-only
    STATUS       current
    DESCRIPTION
        "Cisco Firepower fabric:EthTargetEp:peerDn managed
        object property"
    ::= { cfprFabricEthTargetEpEntry 20 }

cfprFabricEthTargetEpPeerPortId OBJECT-TYPE
    SYNTAX       Gauge32
    MAX-ACCESS   read-only
    STATUS       current
    DESCRIPTION
        "Cisco Firepower fabric:EthTargetEp:peerPortId
        managed object property"
    ::= { cfprFabricEthTargetEpEntry 21 }

cfprFabricEthTargetEpPeerSlotId OBJECT-TYPE
    SYNTAX       Gauge32
    MAX-ACCESS   read-only
    STATUS       current
    DESCRIPTION
        "Cisco Firepower fabric:EthTargetEp:peerSlotId
        managed object property"
    ::= { cfprFabricEthTargetEpEntry 22 }

cfprFabricEthTargetEpPortId OBJECT-TYPE
    SYNTAX       CfprFabricPIoEpPortId
    MAX-ACCESS   read-only
    STATUS       current
    DESCRIPTION
        "Cisco Firepower fabric:EthTargetEp:portId managed
        object property"
    ::= { cfprFabricEthTargetEpEntry 23 }

cfprFabricEthTargetEpSlotId OBJECT-TYPE
    SYNTAX       CfprFabricPIoEpSlotId
    MAX-ACCESS   read-only
    STATUS       current
    DESCRIPTION
        "Cisco Firepower fabric:EthTargetEp:slotId managed
        object property"
    ::= { cfprFabricEthTargetEpEntry 24 }

cfprFabricEthTargetEpSwitchId OBJECT-TYPE
    SYNTAX       CfprNetworkSwitchId
    MAX-ACCESS   read-only
    STATUS       current
    DESCRIPTION
        "Cisco Firepower fabric:EthTargetEp:switchId managed
        object property"
    ::= { cfprFabricEthTargetEpEntry 25 }

cfprFabricEthTargetEpTransport OBJECT-TYPE
    SYNTAX       CfprFabricEthTargetEpTransport
    MAX-ACCESS   read-only
    STATUS       current
    DESCRIPTION
        "Cisco Firepower fabric:EthTargetEp:transport managed
        object property"
    ::= { cfprFabricEthTargetEpEntry 26 }

cfprFabricEthTargetEpType OBJECT-TYPE
    SYNTAX       CfprFabricTargetEpType
    MAX-ACCESS   read-only
    STATUS       current
    DESCRIPTION
        "Cisco Firepower fabric:EthTargetEp:type managed object property"
    ::= { cfprFabricEthTargetEpEntry 27 }

cfprFabricEthTargetEpWarnings OBJECT-TYPE
    SYNTAX       CfprFabricWarnings
    MAX-ACCESS   read-only
    STATUS       current
    DESCRIPTION
        "Cisco Firepower fabric:EthTargetEp:warnings managed
        object property"
    ::= { cfprFabricEthTargetEpEntry 28 }

cfprFabricEthVlanPcTable OBJECT-TYPE
    SYNTAX           SEQUENCE OF CfprFabricEthVlanPcEntry
    MAX-ACCESS       not-accessible
    STATUS           current
    DESCRIPTION
        "Cisco Firepower fabric:EthVlanPc managed object table"
    ::= { cfprFabricObjects 43 }

cfprFabricEthVlanPcEntry OBJECT-TYPE
    SYNTAX           CfprFabricEthVlanPcEntry
    MAX-ACCESS       not-accessible
    STATUS           current
    DESCRIPTION
        "Entry for the cfprFabricEthVlanPcTable table."
    INDEX { cfprFabricEthVlanPcInstanceId }
    ::= { cfprFabricEthVlanPcTable 1 }

CfprFabricEthVlanPcEntry ::= SEQUENCE {
    cfprFabricEthVlanPcInstanceId                                    CfprManagedObjectId,
    cfprFabricEthVlanPcDn                                            CfprManagedObjectDn,
    cfprFabricEthVlanPcRn                                            SnmpAdminString,
    cfprFabricEthVlanPcAdminSpeed                                    CfprPortEthAdminSpeed,
    cfprFabricEthVlanPcAdminState                                    CfprFabricCIoEpAdminState,
    cfprFabricEthVlanPcDescr                                         SnmpAdminString,
    cfprFabricEthVlanPcEpDn                                          SnmpAdminString,
    cfprFabricEthVlanPcFltAggr                                       Unsigned64,
    cfprFabricEthVlanPcIfRole                                        CfprFabricEstcPcIfRole,
    cfprFabricEthVlanPcIfType                                        CfprFabricCIoEpIfType,
    cfprFabricEthVlanPcIsNative                                      TruthValue,
    cfprFabricEthVlanPcLocale                                        CfprFabricExternalPcLocale,
    cfprFabricEthVlanPcName                                          SnmpAdminString,
    cfprFabricEthVlanPcOperSpeed                                     CfprPortEthSpeed,
    cfprFabricEthVlanPcOperState                                     CfprNetworkPortOperState,
    cfprFabricEthVlanPcPeerDn                                        SnmpAdminString,
    cfprFabricEthVlanPcPortId                                        Gauge32,
    cfprFabricEthVlanPcStateQual                                     SnmpAdminString,
    cfprFabricEthVlanPcSwitchId                                      CfprNetworkSwitchId,
    cfprFabricEthVlanPcTransport                                     CfprFabricEthVlanPcTransport,
    cfprFabricEthVlanPcType                                          CfprFabricEstcPcType,
    cfprFabricEthVlanPcWarnings                                      CfprFabricWarnings
}

cfprFabricEthVlanPcInstanceId OBJECT-TYPE
    SYNTAX       CfprManagedObjectId
    MAX-ACCESS   not-accessible
    STATUS       current
    DESCRIPTION
        "Instance identifier of the managed object."
    ::= { cfprFabricEthVlanPcEntry 1 }

cfprFabricEthVlanPcDn OBJECT-TYPE
    SYNTAX       CfprManagedObjectDn
    MAX-ACCESS   read-only
    STATUS       current
    DESCRIPTION
        "Cisco Firepower fabric:EthVlanPc:dn managed object property"
    ::= { cfprFabricEthVlanPcEntry 2 }

cfprFabricEthVlanPcRn OBJECT-TYPE
    SYNTAX       SnmpAdminString
    MAX-ACCESS   read-only
    STATUS       current
    DESCRIPTION
        "Cisco Firepower fabric:EthVlanPc:rn managed object property"
    ::= { cfprFabricEthVlanPcEntry 3 }

cfprFabricEthVlanPcAdminSpeed OBJECT-TYPE
    SYNTAX       CfprPortEthAdminSpeed
    MAX-ACCESS   read-only
    STATUS       current
    DESCRIPTION
        "Cisco Firepower fabric:EthVlanPc:adminSpeed managed
        object property"
    ::= { cfprFabricEthVlanPcEntry 4 }

cfprFabricEthVlanPcAdminState OBJECT-TYPE
    SYNTAX       CfprFabricCIoEpAdminState
    MAX-ACCESS   read-only
    STATUS       current
    DESCRIPTION
        "Cisco Firepower fabric:EthVlanPc:adminState managed
        object property"
    ::= { cfprFabricEthVlanPcEntry 5 }

cfprFabricEthVlanPcDescr OBJECT-TYPE
    SYNTAX       SnmpAdminString
    MAX-ACCESS   read-only
    STATUS       current
    DESCRIPTION
        "Cisco Firepower fabric:EthVlanPc:descr managed object property"
    ::= { cfprFabricEthVlanPcEntry 6 }

cfprFabricEthVlanPcEpDn OBJECT-TYPE
    SYNTAX       SnmpAdminString
    MAX-ACCESS   read-only
    STATUS       current
    DESCRIPTION
        "Cisco Firepower fabric:EthVlanPc:epDn managed object property"
    ::= { cfprFabricEthVlanPcEntry 7 }

cfprFabricEthVlanPcFltAggr OBJECT-TYPE
    SYNTAX       Unsigned64
    MAX-ACCESS   read-only
    STATUS       current
    DESCRIPTION
        "Cisco Firepower fabric:EthVlanPc:fltAggr managed object property"
    ::= { cfprFabricEthVlanPcEntry 8 }

cfprFabricEthVlanPcIfRole OBJECT-TYPE
    SYNTAX       CfprFabricEstcPcIfRole
    MAX-ACCESS   read-only
    STATUS       current
    DESCRIPTION
        "Cisco Firepower fabric:EthVlanPc:ifRole managed object property"
    ::= { cfprFabricEthVlanPcEntry 9 }

cfprFabricEthVlanPcIfType OBJECT-TYPE
    SYNTAX       CfprFabricCIoEpIfType
    MAX-ACCESS   read-only
    STATUS       current
    DESCRIPTION
        "Cisco Firepower fabric:EthVlanPc:ifType managed object property"
    ::= { cfprFabricEthVlanPcEntry 10 }

cfprFabricEthVlanPcIsNative OBJECT-TYPE
    SYNTAX       TruthValue
    MAX-ACCESS   read-only
    STATUS       current
    DESCRIPTION
        "Cisco Firepower fabric:EthVlanPc:isNative managed
        object property"
    ::= { cfprFabricEthVlanPcEntry 11 }

cfprFabricEthVlanPcLocale OBJECT-TYPE
    SYNTAX       CfprFabricExternalPcLocale
    MAX-ACCESS   read-only
    STATUS       current
    DESCRIPTION
        "Cisco Firepower fabric:EthVlanPc:locale managed object property"
    ::= { cfprFabricEthVlanPcEntry 12 }

cfprFabricEthVlanPcName OBJECT-TYPE
    SYNTAX       SnmpAdminString
    MAX-ACCESS   read-only
    STATUS       current
    DESCRIPTION
        "Cisco Firepower fabric:EthVlanPc:name managed object property"
    ::= { cfprFabricEthVlanPcEntry 13 }

cfprFabricEthVlanPcOperSpeed OBJECT-TYPE
    SYNTAX       CfprPortEthSpeed
    MAX-ACCESS   read-only
    STATUS       current
    DESCRIPTION
        "Cisco Firepower fabric:EthVlanPc:operSpeed managed
        object property"
    ::= { cfprFabricEthVlanPcEntry 14 }

cfprFabricEthVlanPcOperState OBJECT-TYPE
    SYNTAX       CfprNetworkPortOperState
    MAX-ACCESS   read-only
    STATUS       current
    DESCRIPTION
        "Cisco Firepower fabric:EthVlanPc:operState managed
        object property"
    ::= { cfprFabricEthVlanPcEntry 15 }

cfprFabricEthVlanPcPeerDn OBJECT-TYPE
    SYNTAX       SnmpAdminString
    MAX-ACCESS   read-only
    STATUS       current
    DESCRIPTION
        "Cisco Firepower fabric:EthVlanPc:peerDn managed object property"
    ::= { cfprFabricEthVlanPcEntry 16 }

cfprFabricEthVlanPcPortId OBJECT-TYPE
    SYNTAX       Gauge32
    MAX-ACCESS   read-only
    STATUS       current
    DESCRIPTION
        "Cisco Firepower fabric:EthVlanPc:portId managed object property"
    ::= { cfprFabricEthVlanPcEntry 17 }

cfprFabricEthVlanPcStateQual OBJECT-TYPE
    SYNTAX       SnmpAdminString
    MAX-ACCESS   read-only
    STATUS       current
    DESCRIPTION
        "Cisco Firepower fabric:EthVlanPc:stateQual managed
        object property"
    ::= { cfprFabricEthVlanPcEntry 18 }

cfprFabricEthVlanPcSwitchId OBJECT-TYPE
    SYNTAX       CfprNetworkSwitchId
    MAX-ACCESS   read-only
    STATUS       current
    DESCRIPTION
        "Cisco Firepower fabric:EthVlanPc:switchId managed
        object property"
    ::= { cfprFabricEthVlanPcEntry 19 }

cfprFabricEthVlanPcTransport OBJECT-TYPE
    SYNTAX       CfprFabricEthVlanPcTransport
    MAX-ACCESS   read-only
    STATUS       current
    DESCRIPTION
        "Cisco Firepower fabric:EthVlanPc:transport managed
        object property"
    ::= { cfprFabricEthVlanPcEntry 20 }

cfprFabricEthVlanPcType OBJECT-TYPE
    SYNTAX       CfprFabricEstcPcType
    MAX-ACCESS   read-only
    STATUS       current
    DESCRIPTION
        "Cisco Firepower fabric:EthVlanPc:type managed object property"
    ::= { cfprFabricEthVlanPcEntry 21 }

cfprFabricEthVlanPcWarnings OBJECT-TYPE
    SYNTAX       CfprFabricWarnings
    MAX-ACCESS   read-only
    STATUS       current
    DESCRIPTION
        "Cisco Firepower fabric:EthVlanPc:warnings managed
        object property"
    ::= { cfprFabricEthVlanPcEntry 22 }

cfprFabricEthVlanPortEpTable OBJECT-TYPE
    SYNTAX           SEQUENCE OF CfprFabricEthVlanPortEpEntry
    MAX-ACCESS       not-accessible
    STATUS           current
    DESCRIPTION
        "Cisco Firepower fabric:EthVlanPortEp managed object table"
    ::= { cfprFabricObjects 44 }

cfprFabricEthVlanPortEpEntry OBJECT-TYPE
    SYNTAX           CfprFabricEthVlanPortEpEntry
    MAX-ACCESS       not-accessible
    STATUS           current
    DESCRIPTION
        "Entry for the cfprFabricEthVlanPortEpTable table."
    INDEX { cfprFabricEthVlanPortEpInstanceId }
    ::= { cfprFabricEthVlanPortEpTable 1 }

CfprFabricEthVlanPortEpEntry ::= SEQUENCE {
    cfprFabricEthVlanPortEpInstanceId                                CfprManagedObjectId,
    cfprFabricEthVlanPortEpDn                                        CfprManagedObjectDn,
    cfprFabricEthVlanPortEpRn                                        SnmpAdminString,
    cfprFabricEthVlanPortEpAdminState                                CfprFabricExternalEpAdminState,
    cfprFabricEthVlanPortEpAggrPortId                                Gauge32,
    cfprFabricEthVlanPortEpChassisId                                 Gauge32,
    cfprFabricEthVlanPortEpEpDn                                      SnmpAdminString,
    cfprFabricEthVlanPortEpFltAggr                                   Unsigned64,
    cfprFabricEthVlanPortEpIfRole                                    CfprFabricLanEpIfRole,
    cfprFabricEthVlanPortEpIfType                                    CfprFabricPIoEpIfType,
    cfprFabricEthVlanPortEpIsNative                                  TruthValue,
    cfprFabricEthVlanPortEpLicGP                                     Unsigned64,
    cfprFabricEthVlanPortEpLicState                                  CfprLicenseState,
    cfprFabricEthVlanPortEpLocale                                    CfprFabricExternalEpLocale,
    cfprFabricEthVlanPortEpName                                      SnmpAdminString,
    cfprFabricEthVlanPortEpOperState                                 CfprFabricPIoEpOperState,
    cfprFabricEthVlanPortEpOperStateReason                           SnmpAdminString,
    cfprFabricEthVlanPortEpPeerAggrPortId                            Gauge32,
    cfprFabricEthVlanPortEpPeerChassisId                             Gauge32,
    cfprFabricEthVlanPortEpPeerDn                                    SnmpAdminString,
    cfprFabricEthVlanPortEpPeerPortId                                Gauge32,
    cfprFabricEthVlanPortEpPeerSlotId                                Gauge32,
    cfprFabricEthVlanPortEpPortId                                    Gauge32,
    cfprFabricEthVlanPortEpSlotId                                    Gauge32,
    cfprFabricEthVlanPortEpSwitchId                                  CfprNetworkSwitchId,
    cfprFabricEthVlanPortEpTransport                                 CfprFabricAEthLanEpTransport,
    cfprFabricEthVlanPortEpType                                      CfprFabricLanEpType,
    cfprFabricEthVlanPortEpWarnings                                  CfprFabricWarnings
}

cfprFabricEthVlanPortEpInstanceId OBJECT-TYPE
    SYNTAX       CfprManagedObjectId
    MAX-ACCESS   not-accessible
    STATUS       current
    DESCRIPTION
        "Instance identifier of the managed object."
    ::= { cfprFabricEthVlanPortEpEntry 1 }

cfprFabricEthVlanPortEpDn OBJECT-TYPE
    SYNTAX       CfprManagedObjectDn
    MAX-ACCESS   read-only
    STATUS       current
    DESCRIPTION
        "Cisco Firepower fabric:EthVlanPortEp:dn managed object property"
    ::= { cfprFabricEthVlanPortEpEntry 2 }

cfprFabricEthVlanPortEpRn OBJECT-TYPE
    SYNTAX       SnmpAdminString
    MAX-ACCESS   read-only
    STATUS       current
    DESCRIPTION
        "Cisco Firepower fabric:EthVlanPortEp:rn managed object property"
    ::= { cfprFabricEthVlanPortEpEntry 3 }

cfprFabricEthVlanPortEpAdminState OBJECT-TYPE
    SYNTAX       CfprFabricExternalEpAdminState
    MAX-ACCESS   read-only
    STATUS       current
    DESCRIPTION
        "Cisco Firepower fabric:EthVlanPortEp:adminState
        managed object property"
    ::= { cfprFabricEthVlanPortEpEntry 4 }

cfprFabricEthVlanPortEpAggrPortId OBJECT-TYPE
    SYNTAX       Gauge32
    MAX-ACCESS   read-only
    STATUS       current
    DESCRIPTION
        "Cisco Firepower fabric:EthVlanPortEp:aggrPortId
        managed object property"
    ::= { cfprFabricEthVlanPortEpEntry 5 }

cfprFabricEthVlanPortEpChassisId OBJECT-TYPE
    SYNTAX       Gauge32
    MAX-ACCESS   read-only
    STATUS       current
    DESCRIPTION
        "Cisco Firepower fabric:EthVlanPortEp:chassisId
        managed object property"
    ::= { cfprFabricEthVlanPortEpEntry 6 }

cfprFabricEthVlanPortEpEpDn OBJECT-TYPE
    SYNTAX       SnmpAdminString
    MAX-ACCESS   read-only
    STATUS       current
    DESCRIPTION
        "Cisco Firepower fabric:EthVlanPortEp:epDn managed
        object property"
    ::= { cfprFabricEthVlanPortEpEntry 7 }

cfprFabricEthVlanPortEpFltAggr OBJECT-TYPE
    SYNTAX       Unsigned64
    MAX-ACCESS   read-only
    STATUS       current
    DESCRIPTION
        "Cisco Firepower fabric:EthVlanPortEp:fltAggr managed
        object property"
    ::= { cfprFabricEthVlanPortEpEntry 8 }

cfprFabricEthVlanPortEpIfRole OBJECT-TYPE
    SYNTAX       CfprFabricLanEpIfRole
    MAX-ACCESS   read-only
    STATUS       current
    DESCRIPTION
        "Cisco Firepower fabric:EthVlanPortEp:ifRole managed
        object property"
    ::= { cfprFabricEthVlanPortEpEntry 9 }

cfprFabricEthVlanPortEpIfType OBJECT-TYPE
    SYNTAX       CfprFabricPIoEpIfType
    MAX-ACCESS   read-only
    STATUS       current
    DESCRIPTION
        "Cisco Firepower fabric:EthVlanPortEp:ifType managed
        object property"
    ::= { cfprFabricEthVlanPortEpEntry 10 }

cfprFabricEthVlanPortEpIsNative OBJECT-TYPE
    SYNTAX       TruthValue
    MAX-ACCESS   read-only
    STATUS       current
    DESCRIPTION
        "Cisco Firepower fabric:EthVlanPortEp:isNative
        managed object property"
    ::= { cfprFabricEthVlanPortEpEntry 11 }

cfprFabricEthVlanPortEpLicGP OBJECT-TYPE
    SYNTAX       Unsigned64
    MAX-ACCESS   read-only
    STATUS       current
    DESCRIPTION
        "Cisco Firepower fabric:EthVlanPortEp:licGP managed
        object property"
    ::= { cfprFabricEthVlanPortEpEntry 12 }

cfprFabricEthVlanPortEpLicState OBJECT-TYPE
    SYNTAX       CfprLicenseState
    MAX-ACCESS   read-only
    STATUS       current
    DESCRIPTION
        "Cisco Firepower fabric:EthVlanPortEp:licState
        managed object property"
    ::= { cfprFabricEthVlanPortEpEntry 13 }

cfprFabricEthVlanPortEpLocale OBJECT-TYPE
    SYNTAX       CfprFabricExternalEpLocale
    MAX-ACCESS   read-only
    STATUS       current
    DESCRIPTION
        "Cisco Firepower fabric:EthVlanPortEp:locale managed
        object property"
    ::= { cfprFabricEthVlanPortEpEntry 14 }

cfprFabricEthVlanPortEpName OBJECT-TYPE
    SYNTAX       SnmpAdminString
    MAX-ACCESS   read-only
    STATUS       current
    DESCRIPTION
        "Cisco Firepower fabric:EthVlanPortEp:name managed
        object property"
    ::= { cfprFabricEthVlanPortEpEntry 15 }

cfprFabricEthVlanPortEpOperState OBJECT-TYPE
    SYNTAX       CfprFabricPIoEpOperState
    MAX-ACCESS   read-only
    STATUS       current
    DESCRIPTION
        "Cisco Firepower fabric:EthVlanPortEp:operState
        managed object property"
    ::= { cfprFabricEthVlanPortEpEntry 16 }

cfprFabricEthVlanPortEpOperStateReason OBJECT-TYPE
    SYNTAX       SnmpAdminString
    MAX-ACCESS   read-only
    STATUS       current
    DESCRIPTION
        "Cisco Firepower fabric:EthVlanPortEp:operStateReason
        managed object property"
    ::= { cfprFabricEthVlanPortEpEntry 17 }

cfprFabricEthVlanPortEpPeerAggrPortId OBJECT-TYPE
    SYNTAX       Gauge32
    MAX-ACCESS   read-only
    STATUS       current
    DESCRIPTION
        "Cisco Firepower fabric:EthVlanPortEp:peerAggrPortId
        managed object property"
    ::= { cfprFabricEthVlanPortEpEntry 18 }

cfprFabricEthVlanPortEpPeerChassisId OBJECT-TYPE
    SYNTAX       Gauge32
    MAX-ACCESS   read-only
    STATUS       current
    DESCRIPTION
        "Cisco Firepower fabric:EthVlanPortEp:peerChassisId
        managed object property"
    ::= { cfprFabricEthVlanPortEpEntry 19 }

cfprFabricEthVlanPortEpPeerDn OBJECT-TYPE
    SYNTAX       SnmpAdminString
    MAX-ACCESS   read-only
    STATUS       current
    DESCRIPTION
        "Cisco Firepower fabric:EthVlanPortEp:peerDn managed
        object property"
    ::= { cfprFabricEthVlanPortEpEntry 20 }

cfprFabricEthVlanPortEpPeerPortId OBJECT-TYPE
    SYNTAX       Gauge32
    MAX-ACCESS   read-only
    STATUS       current
    DESCRIPTION
        "Cisco Firepower fabric:EthVlanPortEp:peerPortId
        managed object property"
    ::= { cfprFabricEthVlanPortEpEntry 21 }

cfprFabricEthVlanPortEpPeerSlotId OBJECT-TYPE
    SYNTAX       Gauge32
    MAX-ACCESS   read-only
    STATUS       current
    DESCRIPTION
        "Cisco Firepower fabric:EthVlanPortEp:peerSlotId
        managed object property"
    ::= { cfprFabricEthVlanPortEpEntry 22 }

cfprFabricEthVlanPortEpPortId OBJECT-TYPE
    SYNTAX       Gauge32
    MAX-ACCESS   read-only
    STATUS       current
    DESCRIPTION
        "Cisco Firepower fabric:EthVlanPortEp:portId managed
        object property"
    ::= { cfprFabricEthVlanPortEpEntry 23 }

cfprFabricEthVlanPortEpSlotId OBJECT-TYPE
    SYNTAX       Gauge32
    MAX-ACCESS   read-only
    STATUS       current
    DESCRIPTION
        "Cisco Firepower fabric:EthVlanPortEp:slotId managed
        object property"
    ::= { cfprFabricEthVlanPortEpEntry 24 }

cfprFabricEthVlanPortEpSwitchId OBJECT-TYPE
    SYNTAX       CfprNetworkSwitchId
    MAX-ACCESS   read-only
    STATUS       current
    DESCRIPTION
        "Cisco Firepower fabric:EthVlanPortEp:switchId
        managed object property"
    ::= { cfprFabricEthVlanPortEpEntry 25 }

cfprFabricEthVlanPortEpTransport OBJECT-TYPE
    SYNTAX       CfprFabricAEthLanEpTransport
    MAX-ACCESS   read-only
    STATUS       current
    DESCRIPTION
        "Cisco Firepower fabric:EthVlanPortEp:transport
        managed object property"
    ::= { cfprFabricEthVlanPortEpEntry 26 }

cfprFabricEthVlanPortEpType OBJECT-TYPE
    SYNTAX       CfprFabricLanEpType
    MAX-ACCESS   read-only
    STATUS       current
    DESCRIPTION
        "Cisco Firepower fabric:EthVlanPortEp:type managed
        object property"
    ::= { cfprFabricEthVlanPortEpEntry 27 }

cfprFabricEthVlanPortEpWarnings OBJECT-TYPE
    SYNTAX       CfprFabricWarnings
    MAX-ACCESS   read-only
    STATUS       current
    DESCRIPTION
        "Cisco Firepower fabric:EthVlanPortEp:warnings
        managed object property"
    ::= { cfprFabricEthVlanPortEpEntry 28 }

cfprFabricFcEstcTable OBJECT-TYPE
    SYNTAX           SEQUENCE OF CfprFabricFcEstcEntry
    MAX-ACCESS       not-accessible
    STATUS           current
    DESCRIPTION
        "Cisco Firepower fabric:FcEstc managed object table"
    ::= { cfprFabricObjects 45 }

cfprFabricFcEstcEntry OBJECT-TYPE
    SYNTAX           CfprFabricFcEstcEntry
    MAX-ACCESS       not-accessible
    STATUS           current
    DESCRIPTION
        "Entry for the cfprFabricFcEstcTable table."
    INDEX { cfprFabricFcEstcInstanceId }
    ::= { cfprFabricFcEstcTable 1 }

CfprFabricFcEstcEntry ::= SEQUENCE {
    cfprFabricFcEstcInstanceId                                       CfprManagedObjectId,
    cfprFabricFcEstcDn                                               CfprManagedObjectDn,
    cfprFabricFcEstcRn                                               SnmpAdminString,
    cfprFabricFcEstcId                                               CfprNetworkSwitchId,
    cfprFabricFcEstcLocale                                           CfprFabricExternalLocale,
    cfprFabricFcEstcName                                             SnmpAdminString,
    cfprFabricFcEstcTransport                                        CfprFabricFcEstcTransport,
    cfprFabricFcEstcType                                             CfprFabricFcEstcType
}

cfprFabricFcEstcInstanceId OBJECT-TYPE
    SYNTAX       CfprManagedObjectId
    MAX-ACCESS   not-accessible
    STATUS       current
    DESCRIPTION
        "Instance identifier of the managed object."
    ::= { cfprFabricFcEstcEntry 1 }

cfprFabricFcEstcDn OBJECT-TYPE
    SYNTAX       CfprManagedObjectDn
    MAX-ACCESS   read-only
    STATUS       current
    DESCRIPTION
        "Cisco Firepower fabric:FcEstc:dn managed object property"
    ::= { cfprFabricFcEstcEntry 2 }

cfprFabricFcEstcRn OBJECT-TYPE
    SYNTAX       SnmpAdminString
    MAX-ACCESS   read-only
    STATUS       current
    DESCRIPTION
        "Cisco Firepower fabric:FcEstc:rn managed object property"
    ::= { cfprFabricFcEstcEntry 3 }

cfprFabricFcEstcId OBJECT-TYPE
    SYNTAX       CfprNetworkSwitchId
    MAX-ACCESS   read-only
    STATUS       current
    DESCRIPTION
        "Cisco Firepower fabric:FcEstc:id managed object property"
    ::= { cfprFabricFcEstcEntry 4 }

cfprFabricFcEstcLocale OBJECT-TYPE
    SYNTAX       CfprFabricExternalLocale
    MAX-ACCESS   read-only
    STATUS       current
    DESCRIPTION
        "Cisco Firepower fabric:FcEstc:locale managed object property"
    ::= { cfprFabricFcEstcEntry 5 }

cfprFabricFcEstcName OBJECT-TYPE
    SYNTAX       SnmpAdminString
    MAX-ACCESS   read-only
    STATUS       current
    DESCRIPTION
        "Cisco Firepower fabric:FcEstc:name managed object property"
    ::= { cfprFabricFcEstcEntry 6 }

cfprFabricFcEstcTransport OBJECT-TYPE
    SYNTAX       CfprFabricFcEstcTransport
    MAX-ACCESS   read-only
    STATUS       current
    DESCRIPTION
        "Cisco Firepower fabric:FcEstc:transport managed object property"
    ::= { cfprFabricFcEstcEntry 7 }

cfprFabricFcEstcType OBJECT-TYPE
    SYNTAX       CfprFabricFcEstcType
    MAX-ACCESS   read-only
    STATUS       current
    DESCRIPTION
        "Cisco Firepower fabric:FcEstc:type managed object property"
    ::= { cfprFabricFcEstcEntry 8 }

cfprFabricFcEstcCloudTable OBJECT-TYPE
    SYNTAX           SEQUENCE OF CfprFabricFcEstcCloudEntry
    MAX-ACCESS       not-accessible
    STATUS           current
    DESCRIPTION
        "Cisco Firepower fabric:FcEstcCloud managed object table"
    ::= { cfprFabricObjects 46 }

cfprFabricFcEstcCloudEntry OBJECT-TYPE
    SYNTAX           CfprFabricFcEstcCloudEntry
    MAX-ACCESS       not-accessible
    STATUS           current
    DESCRIPTION
        "Entry for the cfprFabricFcEstcCloudTable table."
    INDEX { cfprFabricFcEstcCloudInstanceId }
    ::= { cfprFabricFcEstcCloudTable 1 }

CfprFabricFcEstcCloudEntry ::= SEQUENCE {
    cfprFabricFcEstcCloudInstanceId                                  CfprManagedObjectId,
    cfprFabricFcEstcCloudDn                                          CfprManagedObjectDn,
    cfprFabricFcEstcCloudRn                                          SnmpAdminString
}

cfprFabricFcEstcCloudInstanceId OBJECT-TYPE
    SYNTAX       CfprManagedObjectId
    MAX-ACCESS   not-accessible
    STATUS       current
    DESCRIPTION
        "Instance identifier of the managed object."
    ::= { cfprFabricFcEstcCloudEntry 1 }

cfprFabricFcEstcCloudDn OBJECT-TYPE
    SYNTAX       CfprManagedObjectDn
    MAX-ACCESS   read-only
    STATUS       current
    DESCRIPTION
        "Cisco Firepower fabric:FcEstcCloud:dn managed object property"
    ::= { cfprFabricFcEstcCloudEntry 2 }

cfprFabricFcEstcCloudRn OBJECT-TYPE
    SYNTAX       SnmpAdminString
    MAX-ACCESS   read-only
    STATUS       current
    DESCRIPTION
        "Cisco Firepower fabric:FcEstcCloud:rn managed object property"
    ::= { cfprFabricFcEstcCloudEntry 3 }

cfprFabricFcEstcEpTable OBJECT-TYPE
    SYNTAX           SEQUENCE OF CfprFabricFcEstcEpEntry
    MAX-ACCESS       not-accessible
    STATUS           current
    DESCRIPTION
        "Cisco Firepower fabric:FcEstcEp managed object table"
    ::= { cfprFabricObjects 47 }

cfprFabricFcEstcEpEntry OBJECT-TYPE
    SYNTAX           CfprFabricFcEstcEpEntry
    MAX-ACCESS       not-accessible
    STATUS           current
    DESCRIPTION
        "Entry for the cfprFabricFcEstcEpTable table."
    INDEX { cfprFabricFcEstcEpInstanceId }
    ::= { cfprFabricFcEstcEpTable 1 }

CfprFabricFcEstcEpEntry ::= SEQUENCE {
    cfprFabricFcEstcEpInstanceId                                     CfprManagedObjectId,
    cfprFabricFcEstcEpDn                                             CfprManagedObjectDn,
    cfprFabricFcEstcEpRn                                             SnmpAdminString,
    cfprFabricFcEstcEpAdminState                                     CfprFabricExternalEpAdminState,
    cfprFabricFcEstcEpAggrPortId                                     Gauge32,
    cfprFabricFcEstcEpChassisId                                      Gauge32,
    cfprFabricFcEstcEpConfigState                                    CfprFabricConfigState,
    cfprFabricFcEstcEpEpDn                                           SnmpAdminString,
    cfprFabricFcEstcEpFillPattern                                    CfprFabricFillPattern,
    cfprFabricFcEstcEpFltAggr                                        Unsigned64,
    cfprFabricFcEstcEpIfRole                                         CfprFabricEstcEpIfRole,
    cfprFabricFcEstcEpIfType                                         CfprFabricPIoEpIfType,
    cfprFabricFcEstcEpLicGP                                          Unsigned64,
    cfprFabricFcEstcEpLicState                                       CfprLicenseState,
    cfprFabricFcEstcEpLocale                                         CfprFabricExternalEpLocale,
    cfprFabricFcEstcEpName                                           SnmpAdminString,
    cfprFabricFcEstcEpOperState                                      CfprFabricPIoEpOperState,
    cfprFabricFcEstcEpOperStateReason                                SnmpAdminString,
    cfprFabricFcEstcEpPeerAggrPortId                                 Gauge32,
    cfprFabricFcEstcEpPeerChassisId                                  Gauge32,
    cfprFabricFcEstcEpPeerDn                                         SnmpAdminString,
    cfprFabricFcEstcEpPeerPortId                                     Gauge32,
    cfprFabricFcEstcEpPeerSlotId                                     Gauge32,
    cfprFabricFcEstcEpPortId                                         CfprFabricFcEstcEpPortId,
    cfprFabricFcEstcEpSlotId                                         CfprFabricFcEstcEpSlotId,
    cfprFabricFcEstcEpSwitchId                                       CfprNetworkSwitchId,
    cfprFabricFcEstcEpTransport                                      CfprFabricAFcEstcEpTransport,
    cfprFabricFcEstcEpType                                           CfprFabricAFcEstcEpType,
    cfprFabricFcEstcEpUsrLbl                                         SnmpAdminString,
    cfprFabricFcEstcEpWarnings                                       CfprFabricWarnings
}

cfprFabricFcEstcEpInstanceId OBJECT-TYPE
    SYNTAX       CfprManagedObjectId
    MAX-ACCESS   not-accessible
    STATUS       current
    DESCRIPTION
        "Instance identifier of the managed object."
    ::= { cfprFabricFcEstcEpEntry 1 }

cfprFabricFcEstcEpDn OBJECT-TYPE
    SYNTAX       CfprManagedObjectDn
    MAX-ACCESS   read-only
    STATUS       current
    DESCRIPTION
        "Cisco Firepower fabric:FcEstcEp:dn managed object property"
    ::= { cfprFabricFcEstcEpEntry 2 }

cfprFabricFcEstcEpRn OBJECT-TYPE
    SYNTAX       SnmpAdminString
    MAX-ACCESS   read-only
    STATUS       current
    DESCRIPTION
        "Cisco Firepower fabric:FcEstcEp:rn managed object property"
    ::= { cfprFabricFcEstcEpEntry 3 }

cfprFabricFcEstcEpAdminState OBJECT-TYPE
    SYNTAX       CfprFabricExternalEpAdminState
    MAX-ACCESS   read-only
    STATUS       current
    DESCRIPTION
        "Cisco Firepower fabric:FcEstcEp:adminState managed
        object property"
    ::= { cfprFabricFcEstcEpEntry 4 }

cfprFabricFcEstcEpAggrPortId OBJECT-TYPE
    SYNTAX       Gauge32
    MAX-ACCESS   read-only
    STATUS       current
    DESCRIPTION
        "Cisco Firepower fabric:FcEstcEp:aggrPortId managed
        object property"
    ::= { cfprFabricFcEstcEpEntry 5 }

cfprFabricFcEstcEpChassisId OBJECT-TYPE
    SYNTAX       Gauge32
    MAX-ACCESS   read-only
    STATUS       current
    DESCRIPTION
        "Cisco Firepower fabric:FcEstcEp:chassisId managed
        object property"
    ::= { cfprFabricFcEstcEpEntry 6 }

cfprFabricFcEstcEpConfigState OBJECT-TYPE
    SYNTAX       CfprFabricConfigState
    MAX-ACCESS   read-only
    STATUS       current
    DESCRIPTION
        "Cisco Firepower fabric:FcEstcEp:configState managed
        object property"
    ::= { cfprFabricFcEstcEpEntry 7 }

cfprFabricFcEstcEpEpDn OBJECT-TYPE
    SYNTAX       SnmpAdminString
    MAX-ACCESS   read-only
    STATUS       current
    DESCRIPTION
        "Cisco Firepower fabric:FcEstcEp:epDn managed object property"
    ::= { cfprFabricFcEstcEpEntry 8 }

cfprFabricFcEstcEpFillPattern OBJECT-TYPE
    SYNTAX       CfprFabricFillPattern
    MAX-ACCESS   read-only
    STATUS       current
    DESCRIPTION
        "Cisco Firepower fabric:FcEstcEp:fillPattern managed
        object property"
    ::= { cfprFabricFcEstcEpEntry 9 }

cfprFabricFcEstcEpFltAggr OBJECT-TYPE
    SYNTAX       Unsigned64
    MAX-ACCESS   read-only
    STATUS       current
    DESCRIPTION
        "Cisco Firepower fabric:FcEstcEp:fltAggr managed object property"
    ::= { cfprFabricFcEstcEpEntry 10 }

cfprFabricFcEstcEpIfRole OBJECT-TYPE
    SYNTAX       CfprFabricEstcEpIfRole
    MAX-ACCESS   read-only
    STATUS       current
    DESCRIPTION
        "Cisco Firepower fabric:FcEstcEp:ifRole managed object property"
    ::= { cfprFabricFcEstcEpEntry 11 }

cfprFabricFcEstcEpIfType OBJECT-TYPE
    SYNTAX       CfprFabricPIoEpIfType
    MAX-ACCESS   read-only
    STATUS       current
    DESCRIPTION
        "Cisco Firepower fabric:FcEstcEp:ifType managed object property"
    ::= { cfprFabricFcEstcEpEntry 12 }

cfprFabricFcEstcEpLicGP OBJECT-TYPE
    SYNTAX       Unsigned64
    MAX-ACCESS   read-only
    STATUS       current
    DESCRIPTION
        "Cisco Firepower fabric:FcEstcEp:licGP managed object property"
    ::= { cfprFabricFcEstcEpEntry 13 }

cfprFabricFcEstcEpLicState OBJECT-TYPE
    SYNTAX       CfprLicenseState
    MAX-ACCESS   read-only
    STATUS       current
    DESCRIPTION
        "Cisco Firepower fabric:FcEstcEp:licState managed object property"
    ::= { cfprFabricFcEstcEpEntry 14 }

cfprFabricFcEstcEpLocale OBJECT-TYPE
    SYNTAX       CfprFabricExternalEpLocale
    MAX-ACCESS   read-only
    STATUS       current
    DESCRIPTION
        "Cisco Firepower fabric:FcEstcEp:locale managed object property"
    ::= { cfprFabricFcEstcEpEntry 15 }

cfprFabricFcEstcEpName OBJECT-TYPE
    SYNTAX       SnmpAdminString
    MAX-ACCESS   read-only
    STATUS       current
    DESCRIPTION
        "Cisco Firepower fabric:FcEstcEp:name managed object property"
    ::= { cfprFabricFcEstcEpEntry 16 }

cfprFabricFcEstcEpOperState OBJECT-TYPE
    SYNTAX       CfprFabricPIoEpOperState
    MAX-ACCESS   read-only
    STATUS       current
    DESCRIPTION
        "Cisco Firepower fabric:FcEstcEp:operState managed
        object property"
    ::= { cfprFabricFcEstcEpEntry 17 }

cfprFabricFcEstcEpOperStateReason OBJECT-TYPE
    SYNTAX       SnmpAdminString
    MAX-ACCESS   read-only
    STATUS       current
    DESCRIPTION
        "Cisco Firepower fabric:FcEstcEp:operStateReason
        managed object property"
    ::= { cfprFabricFcEstcEpEntry 18 }

cfprFabricFcEstcEpPeerAggrPortId OBJECT-TYPE
    SYNTAX       Gauge32
    MAX-ACCESS   read-only
    STATUS       current
    DESCRIPTION
        "Cisco Firepower fabric:FcEstcEp:peerAggrPortId
        managed object property"
    ::= { cfprFabricFcEstcEpEntry 19 }

cfprFabricFcEstcEpPeerChassisId OBJECT-TYPE
    SYNTAX       Gauge32
    MAX-ACCESS   read-only
    STATUS       current
    DESCRIPTION
        "Cisco Firepower fabric:FcEstcEp:peerChassisId
        managed object property"
    ::= { cfprFabricFcEstcEpEntry 20 }

cfprFabricFcEstcEpPeerDn OBJECT-TYPE
    SYNTAX       SnmpAdminString
    MAX-ACCESS   read-only
    STATUS       current
    DESCRIPTION
        "Cisco Firepower fabric:FcEstcEp:peerDn managed object property"
    ::= { cfprFabricFcEstcEpEntry 21 }

cfprFabricFcEstcEpPeerPortId OBJECT-TYPE
    SYNTAX       Gauge32
    MAX-ACCESS   read-only
    STATUS       current
    DESCRIPTION
        "Cisco Firepower fabric:FcEstcEp:peerPortId managed
        object property"
    ::= { cfprFabricFcEstcEpEntry 22 }

cfprFabricFcEstcEpPeerSlotId OBJECT-TYPE
    SYNTAX       Gauge32
    MAX-ACCESS   read-only
    STATUS       current
    DESCRIPTION
        "Cisco Firepower fabric:FcEstcEp:peerSlotId managed
        object property"
    ::= { cfprFabricFcEstcEpEntry 23 }

cfprFabricFcEstcEpPortId OBJECT-TYPE
    SYNTAX       CfprFabricFcEstcEpPortId
    MAX-ACCESS   read-only
    STATUS       current
    DESCRIPTION
        "Cisco Firepower fabric:FcEstcEp:portId managed object property"
    ::= { cfprFabricFcEstcEpEntry 24 }

cfprFabricFcEstcEpSlotId OBJECT-TYPE
    SYNTAX       CfprFabricFcEstcEpSlotId
    MAX-ACCESS   read-only
    STATUS       current
    DESCRIPTION
        "Cisco Firepower fabric:FcEstcEp:slotId managed object property"
    ::= { cfprFabricFcEstcEpEntry 25 }

cfprFabricFcEstcEpSwitchId OBJECT-TYPE
    SYNTAX       CfprNetworkSwitchId
    MAX-ACCESS   read-only
    STATUS       current
    DESCRIPTION
        "Cisco Firepower fabric:FcEstcEp:switchId managed object property"
    ::= { cfprFabricFcEstcEpEntry 26 }

cfprFabricFcEstcEpTransport OBJECT-TYPE
    SYNTAX       CfprFabricAFcEstcEpTransport
    MAX-ACCESS   read-only
    STATUS       current
    DESCRIPTION
        "Cisco Firepower fabric:FcEstcEp:transport managed
        object property"
    ::= { cfprFabricFcEstcEpEntry 27 }

cfprFabricFcEstcEpType OBJECT-TYPE
    SYNTAX       CfprFabricAFcEstcEpType
    MAX-ACCESS   read-only
    STATUS       current
    DESCRIPTION
        "Cisco Firepower fabric:FcEstcEp:type managed object property"
    ::= { cfprFabricFcEstcEpEntry 28 }

cfprFabricFcEstcEpUsrLbl OBJECT-TYPE
    SYNTAX       SnmpAdminString
    MAX-ACCESS   read-only
    STATUS       current
    DESCRIPTION
        "Cisco Firepower fabric:FcEstcEp:usrLbl managed object property"
    ::= { cfprFabricFcEstcEpEntry 29 }

cfprFabricFcEstcEpWarnings OBJECT-TYPE
    SYNTAX       CfprFabricWarnings
    MAX-ACCESS   read-only
    STATUS       current
    DESCRIPTION
        "Cisco Firepower fabric:FcEstcEp:warnings managed object property"
    ::= { cfprFabricFcEstcEpEntry 30 }

cfprFabricFcMonTable OBJECT-TYPE
    SYNTAX           SEQUENCE OF CfprFabricFcMonEntry
    MAX-ACCESS       not-accessible
    STATUS           current
    DESCRIPTION
        "Cisco Firepower fabric:FcMon managed object table"
    ::= { cfprFabricObjects 48 }

cfprFabricFcMonEntry OBJECT-TYPE
    SYNTAX           CfprFabricFcMonEntry
    MAX-ACCESS       not-accessible
    STATUS           current
    DESCRIPTION
        "Entry for the cfprFabricFcMonTable table."
    INDEX { cfprFabricFcMonInstanceId }
    ::= { cfprFabricFcMonTable 1 }

CfprFabricFcMonEntry ::= SEQUENCE {
    cfprFabricFcMonInstanceId                                        CfprManagedObjectId,
    cfprFabricFcMonDn                                                CfprManagedObjectDn,
    cfprFabricFcMonRn                                                SnmpAdminString,
    cfprFabricFcMonAdminState                                        CfprFabricMonAdminState,
    cfprFabricFcMonConfigFailReason                                  SnmpAdminString,
    cfprFabricFcMonId                                                CfprNetworkSwitchId,
    cfprFabricFcMonIsConfigSuccess                                   TruthValue,
    cfprFabricFcMonLocale                                            CfprFabricExternalLocale,
    cfprFabricFcMonName                                              SnmpAdminString,
    cfprFabricFcMonOperState                                         CfprFabricMonOperState,
    cfprFabricFcMonOperStateReason                                   CfprFabricMonOperStateReason,
    cfprFabricFcMonPeerDn                                            SnmpAdminString,
    cfprFabricFcMonSession                                           Gauge32,
    cfprFabricFcMonTransport                                         CfprFabricFcMonTransport,
    cfprFabricFcMonType                                              CfprFabricFcMonType
}

cfprFabricFcMonInstanceId OBJECT-TYPE
    SYNTAX       CfprManagedObjectId
    MAX-ACCESS   not-accessible
    STATUS       current
    DESCRIPTION
        "Instance identifier of the managed object."
    ::= { cfprFabricFcMonEntry 1 }

cfprFabricFcMonDn OBJECT-TYPE
    SYNTAX       CfprManagedObjectDn
    MAX-ACCESS   read-only
    STATUS       current
    DESCRIPTION
        "Cisco Firepower fabric:FcMon:dn managed object property"
    ::= { cfprFabricFcMonEntry 2 }

cfprFabricFcMonRn OBJECT-TYPE
    SYNTAX       SnmpAdminString
    MAX-ACCESS   read-only
    STATUS       current
    DESCRIPTION
        "Cisco Firepower fabric:FcMon:rn managed object property"
    ::= { cfprFabricFcMonEntry 3 }

cfprFabricFcMonAdminState OBJECT-TYPE
    SYNTAX       CfprFabricMonAdminState
    MAX-ACCESS   read-only
    STATUS       current
    DESCRIPTION
        "Cisco Firepower fabric:FcMon:adminState managed object property"
    ::= { cfprFabricFcMonEntry 4 }

cfprFabricFcMonConfigFailReason OBJECT-TYPE
    SYNTAX       SnmpAdminString
    MAX-ACCESS   read-only
    STATUS       current
    DESCRIPTION
        "Cisco Firepower fabric:FcMon:configFailReason
        managed object property"
    ::= { cfprFabricFcMonEntry 5 }

cfprFabricFcMonId OBJECT-TYPE
    SYNTAX       CfprNetworkSwitchId
    MAX-ACCESS   read-only
    STATUS       current
    DESCRIPTION
        "Cisco Firepower fabric:FcMon:id managed object property"
    ::= { cfprFabricFcMonEntry 6 }

cfprFabricFcMonIsConfigSuccess OBJECT-TYPE
    SYNTAX       TruthValue
    MAX-ACCESS   read-only
    STATUS       current
    DESCRIPTION
        "Cisco Firepower fabric:FcMon:isConfigSuccess managed
        object property"
    ::= { cfprFabricFcMonEntry 7 }

cfprFabricFcMonLocale OBJECT-TYPE
    SYNTAX       CfprFabricExternalLocale
    MAX-ACCESS   read-only
    STATUS       current
    DESCRIPTION
        "Cisco Firepower fabric:FcMon:locale managed object property"
    ::= { cfprFabricFcMonEntry 8 }

cfprFabricFcMonName OBJECT-TYPE
    SYNTAX       SnmpAdminString
    MAX-ACCESS   read-only
    STATUS       current
    DESCRIPTION
        "Cisco Firepower fabric:FcMon:name managed object property"
    ::= { cfprFabricFcMonEntry 9 }

cfprFabricFcMonOperState OBJECT-TYPE
    SYNTAX       CfprFabricMonOperState
    MAX-ACCESS   read-only
    STATUS       current
    DESCRIPTION
        "Cisco Firepower fabric:FcMon:operState managed object property"
    ::= { cfprFabricFcMonEntry 10 }

cfprFabricFcMonOperStateReason OBJECT-TYPE
    SYNTAX       CfprFabricMonOperStateReason
    MAX-ACCESS   read-only
    STATUS       current
    DESCRIPTION
        "Cisco Firepower fabric:FcMon:operStateReason managed
        object property"
    ::= { cfprFabricFcMonEntry 11 }

cfprFabricFcMonPeerDn OBJECT-TYPE
    SYNTAX       SnmpAdminString
    MAX-ACCESS   read-only
    STATUS       current
    DESCRIPTION
        "Cisco Firepower fabric:FcMon:peerDn managed object property"
    ::= { cfprFabricFcMonEntry 12 }

cfprFabricFcMonSession OBJECT-TYPE
    SYNTAX       Gauge32
    MAX-ACCESS   read-only
    STATUS       current
    DESCRIPTION
        "Cisco Firepower fabric:FcMon:session managed object property"
    ::= { cfprFabricFcMonEntry 13 }

cfprFabricFcMonTransport OBJECT-TYPE
    SYNTAX       CfprFabricFcMonTransport
    MAX-ACCESS   read-only
    STATUS       current
    DESCRIPTION
        "Cisco Firepower fabric:FcMon:transport managed object property"
    ::= { cfprFabricFcMonEntry 14 }

cfprFabricFcMonType OBJECT-TYPE
    SYNTAX       CfprFabricFcMonType
    MAX-ACCESS   read-only
    STATUS       current
    DESCRIPTION
        "Cisco Firepower fabric:FcMon:type managed object property"
    ::= { cfprFabricFcMonEntry 15 }

cfprFabricFcMonDestEpTable OBJECT-TYPE
    SYNTAX           SEQUENCE OF CfprFabricFcMonDestEpEntry
    MAX-ACCESS       not-accessible
    STATUS           current
    DESCRIPTION
        "Cisco Firepower fabric:FcMonDestEp managed object table"
    ::= { cfprFabricObjects 49 }

cfprFabricFcMonDestEpEntry OBJECT-TYPE
    SYNTAX           CfprFabricFcMonDestEpEntry
    MAX-ACCESS       not-accessible
    STATUS           current
    DESCRIPTION
        "Entry for the cfprFabricFcMonDestEpTable table."
    INDEX { cfprFabricFcMonDestEpInstanceId }
    ::= { cfprFabricFcMonDestEpTable 1 }

CfprFabricFcMonDestEpEntry ::= SEQUENCE {
    cfprFabricFcMonDestEpInstanceId                                  CfprManagedObjectId,
    cfprFabricFcMonDestEpDn                                          CfprManagedObjectDn,
    cfprFabricFcMonDestEpRn                                          SnmpAdminString,
    cfprFabricFcMonDestEpAdminSpeed                                  CfprFabricFcMonDestEpAdminSpeed,
    cfprFabricFcMonDestEpAdminState                                  CfprFabricExternalEpAdminState,
    cfprFabricFcMonDestEpAggrPortId                                  Gauge32,
    cfprFabricFcMonDestEpChassisId                                   Gauge32,
    cfprFabricFcMonDestEpEpDn                                        SnmpAdminString,
    cfprFabricFcMonDestEpFltAggr                                     Unsigned64,
    cfprFabricFcMonDestEpIfRole                                      CfprFabricFcMonDestEpIfRole,
    cfprFabricFcMonDestEpIfType                                      CfprFabricPIoEpIfType,
    cfprFabricFcMonDestEpLicGP                                       Unsigned64,
    cfprFabricFcMonDestEpLicState                                    CfprLicenseState,
    cfprFabricFcMonDestEpLocale                                      CfprFabricExternalEpLocale,
    cfprFabricFcMonDestEpName                                        SnmpAdminString,
    cfprFabricFcMonDestEpOperState                                   CfprFabricPIoEpOperState,
    cfprFabricFcMonDestEpOperStateReason                             SnmpAdminString,
    cfprFabricFcMonDestEpPeerAggrPortId                              Gauge32,
    cfprFabricFcMonDestEpPeerChassisId                               Gauge32,
    cfprFabricFcMonDestEpPeerDn                                      SnmpAdminString,
    cfprFabricFcMonDestEpPeerPortId                                  Gauge32,
    cfprFabricFcMonDestEpPeerSlotId                                  Gauge32,
    cfprFabricFcMonDestEpPortId                                      CfprFabricFcMonDestEpPortId,
    cfprFabricFcMonDestEpSlotId                                      CfprFabricFcMonDestEpSlotId,
    cfprFabricFcMonDestEpSwitchId                                    CfprNetworkSwitchId,
    cfprFabricFcMonDestEpTransport                                   CfprNetworkTransport,
    cfprFabricFcMonDestEpType                                        CfprFabricFcMonDestEpType,
    cfprFabricFcMonDestEpWarnings                                    CfprFabricWarnings
}

cfprFabricFcMonDestEpInstanceId OBJECT-TYPE
    SYNTAX       CfprManagedObjectId
    MAX-ACCESS   not-accessible
    STATUS       current
    DESCRIPTION
        "Instance identifier of the managed object."
    ::= { cfprFabricFcMonDestEpEntry 1 }

cfprFabricFcMonDestEpDn OBJECT-TYPE
    SYNTAX       CfprManagedObjectDn
    MAX-ACCESS   read-only
    STATUS       current
    DESCRIPTION
        "Cisco Firepower fabric:FcMonDestEp:dn managed object property"
    ::= { cfprFabricFcMonDestEpEntry 2 }

cfprFabricFcMonDestEpRn OBJECT-TYPE
    SYNTAX       SnmpAdminString
    MAX-ACCESS   read-only
    STATUS       current
    DESCRIPTION
        "Cisco Firepower fabric:FcMonDestEp:rn managed object property"
    ::= { cfprFabricFcMonDestEpEntry 3 }

cfprFabricFcMonDestEpAdminSpeed OBJECT-TYPE
    SYNTAX       CfprFabricFcMonDestEpAdminSpeed
    MAX-ACCESS   read-only
    STATUS       current
    DESCRIPTION
        "Cisco Firepower fabric:FcMonDestEp:adminSpeed
        managed object property"
    ::= { cfprFabricFcMonDestEpEntry 4 }

cfprFabricFcMonDestEpAdminState OBJECT-TYPE
    SYNTAX       CfprFabricExternalEpAdminState
    MAX-ACCESS   read-only
    STATUS       current
    DESCRIPTION
        "Cisco Firepower fabric:FcMonDestEp:adminState
        managed object property"
    ::= { cfprFabricFcMonDestEpEntry 5 }

cfprFabricFcMonDestEpAggrPortId OBJECT-TYPE
    SYNTAX       Gauge32
    MAX-ACCESS   read-only
    STATUS       current
    DESCRIPTION
        "Cisco Firepower fabric:FcMonDestEp:aggrPortId
        managed object property"
    ::= { cfprFabricFcMonDestEpEntry 6 }

cfprFabricFcMonDestEpChassisId OBJECT-TYPE
    SYNTAX       Gauge32
    MAX-ACCESS   read-only
    STATUS       current
    DESCRIPTION
        "Cisco Firepower fabric:FcMonDestEp:chassisId managed
        object property"
    ::= { cfprFabricFcMonDestEpEntry 7 }

cfprFabricFcMonDestEpEpDn OBJECT-TYPE
    SYNTAX       SnmpAdminString
    MAX-ACCESS   read-only
    STATUS       current
    DESCRIPTION
        "Cisco Firepower fabric:FcMonDestEp:epDn managed object property"
    ::= { cfprFabricFcMonDestEpEntry 8 }

cfprFabricFcMonDestEpFltAggr OBJECT-TYPE
    SYNTAX       Unsigned64
    MAX-ACCESS   read-only
    STATUS       current
    DESCRIPTION
        "Cisco Firepower fabric:FcMonDestEp:fltAggr managed
        object property"
    ::= { cfprFabricFcMonDestEpEntry 9 }

cfprFabricFcMonDestEpIfRole OBJECT-TYPE
    SYNTAX       CfprFabricFcMonDestEpIfRole
    MAX-ACCESS   read-only
    STATUS       current
    DESCRIPTION
        "Cisco Firepower fabric:FcMonDestEp:ifRole managed
        object property"
    ::= { cfprFabricFcMonDestEpEntry 10 }

cfprFabricFcMonDestEpIfType OBJECT-TYPE
    SYNTAX       CfprFabricPIoEpIfType
    MAX-ACCESS   read-only
    STATUS       current
    DESCRIPTION
        "Cisco Firepower fabric:FcMonDestEp:ifType managed
        object property"
    ::= { cfprFabricFcMonDestEpEntry 11 }

cfprFabricFcMonDestEpLicGP OBJECT-TYPE
    SYNTAX       Unsigned64
    MAX-ACCESS   read-only
    STATUS       current
    DESCRIPTION
        "Cisco Firepower fabric:FcMonDestEp:licGP managed object property"
    ::= { cfprFabricFcMonDestEpEntry 12 }

cfprFabricFcMonDestEpLicState OBJECT-TYPE
    SYNTAX       CfprLicenseState
    MAX-ACCESS   read-only
    STATUS       current
    DESCRIPTION
        "Cisco Firepower fabric:FcMonDestEp:licState managed
        object property"
    ::= { cfprFabricFcMonDestEpEntry 13 }

cfprFabricFcMonDestEpLocale OBJECT-TYPE
    SYNTAX       CfprFabricExternalEpLocale
    MAX-ACCESS   read-only
    STATUS       current
    DESCRIPTION
        "Cisco Firepower fabric:FcMonDestEp:locale managed
        object property"
    ::= { cfprFabricFcMonDestEpEntry 14 }

cfprFabricFcMonDestEpName OBJECT-TYPE
    SYNTAX       SnmpAdminString
    MAX-ACCESS   read-only
    STATUS       current
    DESCRIPTION
        "Cisco Firepower fabric:FcMonDestEp:name managed object property"
    ::= { cfprFabricFcMonDestEpEntry 15 }

cfprFabricFcMonDestEpOperState OBJECT-TYPE
    SYNTAX       CfprFabricPIoEpOperState
    MAX-ACCESS   read-only
    STATUS       current
    DESCRIPTION
        "Cisco Firepower fabric:FcMonDestEp:operState managed
        object property"
    ::= { cfprFabricFcMonDestEpEntry 16 }

cfprFabricFcMonDestEpOperStateReason OBJECT-TYPE
    SYNTAX       SnmpAdminString
    MAX-ACCESS   read-only
    STATUS       current
    DESCRIPTION
        "Cisco Firepower fabric:FcMonDestEp:operStateReason
        managed object property"
    ::= { cfprFabricFcMonDestEpEntry 17 }

cfprFabricFcMonDestEpPeerAggrPortId OBJECT-TYPE
    SYNTAX       Gauge32
    MAX-ACCESS   read-only
    STATUS       current
    DESCRIPTION
        "Cisco Firepower fabric:FcMonDestEp:peerAggrPortId
        managed object property"
    ::= { cfprFabricFcMonDestEpEntry 18 }

cfprFabricFcMonDestEpPeerChassisId OBJECT-TYPE
    SYNTAX       Gauge32
    MAX-ACCESS   read-only
    STATUS       current
    DESCRIPTION
        "Cisco Firepower fabric:FcMonDestEp:peerChassisId
        managed object property"
    ::= { cfprFabricFcMonDestEpEntry 19 }

cfprFabricFcMonDestEpPeerDn OBJECT-TYPE
    SYNTAX       SnmpAdminString
    MAX-ACCESS   read-only
    STATUS       current
    DESCRIPTION
        "Cisco Firepower fabric:FcMonDestEp:peerDn managed
        object property"
    ::= { cfprFabricFcMonDestEpEntry 20 }

cfprFabricFcMonDestEpPeerPortId OBJECT-TYPE
    SYNTAX       Gauge32
    MAX-ACCESS   read-only
    STATUS       current
    DESCRIPTION
        "Cisco Firepower fabric:FcMonDestEp:peerPortId
        managed object property"
    ::= { cfprFabricFcMonDestEpEntry 21 }

cfprFabricFcMonDestEpPeerSlotId OBJECT-TYPE
    SYNTAX       Gauge32
    MAX-ACCESS   read-only
    STATUS       current
    DESCRIPTION
        "Cisco Firepower fabric:FcMonDestEp:peerSlotId
        managed object property"
    ::= { cfprFabricFcMonDestEpEntry 22 }

cfprFabricFcMonDestEpPortId OBJECT-TYPE
    SYNTAX       CfprFabricFcMonDestEpPortId
    MAX-ACCESS   read-only
    STATUS       current
    DESCRIPTION
        "Cisco Firepower fabric:FcMonDestEp:portId managed
        object property"
    ::= { cfprFabricFcMonDestEpEntry 23 }

cfprFabricFcMonDestEpSlotId OBJECT-TYPE
    SYNTAX       CfprFabricFcMonDestEpSlotId
    MAX-ACCESS   read-only
    STATUS       current
    DESCRIPTION
        "Cisco Firepower fabric:FcMonDestEp:slotId managed
        object property"
    ::= { cfprFabricFcMonDestEpEntry 24 }

cfprFabricFcMonDestEpSwitchId OBJECT-TYPE
    SYNTAX       CfprNetworkSwitchId
    MAX-ACCESS   read-only
    STATUS       current
    DESCRIPTION
        "Cisco Firepower fabric:FcMonDestEp:switchId managed
        object property"
    ::= { cfprFabricFcMonDestEpEntry 25 }

cfprFabricFcMonDestEpTransport OBJECT-TYPE
    SYNTAX       CfprNetworkTransport
    MAX-ACCESS   read-only
    STATUS       current
    DESCRIPTION
        "Cisco Firepower fabric:FcMonDestEp:transport managed
        object property"
    ::= { cfprFabricFcMonDestEpEntry 26 }

cfprFabricFcMonDestEpType OBJECT-TYPE
    SYNTAX       CfprFabricFcMonDestEpType
    MAX-ACCESS   read-only
    STATUS       current
    DESCRIPTION
        "Cisco Firepower fabric:FcMonDestEp:type managed object property"
    ::= { cfprFabricFcMonDestEpEntry 27 }

cfprFabricFcMonDestEpWarnings OBJECT-TYPE
    SYNTAX       CfprFabricWarnings
    MAX-ACCESS   read-only
    STATUS       current
    DESCRIPTION
        "Cisco Firepower fabric:FcMonDestEp:warnings managed
        object property"
    ::= { cfprFabricFcMonDestEpEntry 28 }

cfprFabricFcMonFiltEpTable OBJECT-TYPE
    SYNTAX           SEQUENCE OF CfprFabricFcMonFiltEpEntry
    MAX-ACCESS       not-accessible
    STATUS           current
    DESCRIPTION
        "Cisco Firepower fabric:FcMonFiltEp managed object table"
    ::= { cfprFabricObjects 50 }

cfprFabricFcMonFiltEpEntry OBJECT-TYPE
    SYNTAX           CfprFabricFcMonFiltEpEntry
    MAX-ACCESS       not-accessible
    STATUS           current
    DESCRIPTION
        "Entry for the cfprFabricFcMonFiltEpTable table."
    INDEX { cfprFabricFcMonFiltEpInstanceId }
    ::= { cfprFabricFcMonFiltEpTable 1 }

CfprFabricFcMonFiltEpEntry ::= SEQUENCE {
    cfprFabricFcMonFiltEpInstanceId                                  CfprManagedObjectId,
    cfprFabricFcMonFiltEpDn                                          CfprManagedObjectDn,
    cfprFabricFcMonFiltEpRn                                          SnmpAdminString,
    cfprFabricFcMonFiltEpName                                        SnmpAdminString,
    cfprFabricFcMonFiltEpSession                                     Gauge32,
    cfprFabricFcMonFiltEpType                                        CfprFabricFcMonFiltEpType
}

cfprFabricFcMonFiltEpInstanceId OBJECT-TYPE
    SYNTAX       CfprManagedObjectId
    MAX-ACCESS   not-accessible
    STATUS       current
    DESCRIPTION
        "Instance identifier of the managed object."
    ::= { cfprFabricFcMonFiltEpEntry 1 }

cfprFabricFcMonFiltEpDn OBJECT-TYPE
    SYNTAX       CfprManagedObjectDn
    MAX-ACCESS   read-only
    STATUS       current
    DESCRIPTION
        "Cisco Firepower fabric:FcMonFiltEp:dn managed object property"
    ::= { cfprFabricFcMonFiltEpEntry 2 }

cfprFabricFcMonFiltEpRn OBJECT-TYPE
    SYNTAX       SnmpAdminString
    MAX-ACCESS   read-only
    STATUS       current
    DESCRIPTION
        "Cisco Firepower fabric:FcMonFiltEp:rn managed object property"
    ::= { cfprFabricFcMonFiltEpEntry 3 }

cfprFabricFcMonFiltEpName OBJECT-TYPE
    SYNTAX       SnmpAdminString
    MAX-ACCESS   read-only
    STATUS       current
    DESCRIPTION
        "Cisco Firepower fabric:FcMonFiltEp:name managed object property"
    ::= { cfprFabricFcMonFiltEpEntry 4 }

cfprFabricFcMonFiltEpSession OBJECT-TYPE
    SYNTAX       Gauge32
    MAX-ACCESS   read-only
    STATUS       current
    DESCRIPTION
        "Cisco Firepower fabric:FcMonFiltEp:session managed
        object property"
    ::= { cfprFabricFcMonFiltEpEntry 5 }

cfprFabricFcMonFiltEpType OBJECT-TYPE
    SYNTAX       CfprFabricFcMonFiltEpType
    MAX-ACCESS   read-only
    STATUS       current
    DESCRIPTION
        "Cisco Firepower fabric:FcMonFiltEp:type managed object property"
    ::= { cfprFabricFcMonFiltEpEntry 6 }

cfprFabricFcMonFiltRefTable OBJECT-TYPE
    SYNTAX           SEQUENCE OF CfprFabricFcMonFiltRefEntry
    MAX-ACCESS       not-accessible
    STATUS           current
    DESCRIPTION
        "Cisco Firepower fabric:FcMonFiltRef managed object table"
    ::= { cfprFabricObjects 51 }

cfprFabricFcMonFiltRefEntry OBJECT-TYPE
    SYNTAX           CfprFabricFcMonFiltRefEntry
    MAX-ACCESS       not-accessible
    STATUS           current
    DESCRIPTION
        "Entry for the cfprFabricFcMonFiltRefTable table."
    INDEX { cfprFabricFcMonFiltRefInstanceId }
    ::= { cfprFabricFcMonFiltRefTable 1 }

CfprFabricFcMonFiltRefEntry ::= SEQUENCE {
    cfprFabricFcMonFiltRefInstanceId                                 CfprManagedObjectId,
    cfprFabricFcMonFiltRefDn                                         CfprManagedObjectDn,
    cfprFabricFcMonFiltRefRn                                         SnmpAdminString,
    cfprFabricFcMonFiltRefSrcFiltDn                                  SnmpAdminString,
    cfprFabricFcMonFiltRefType                                       CfprFabricFcMonFiltRefType
}

cfprFabricFcMonFiltRefInstanceId OBJECT-TYPE
    SYNTAX       CfprManagedObjectId
    MAX-ACCESS   not-accessible
    STATUS       current
    DESCRIPTION
        "Instance identifier of the managed object."
    ::= { cfprFabricFcMonFiltRefEntry 1 }

cfprFabricFcMonFiltRefDn OBJECT-TYPE
    SYNTAX       CfprManagedObjectDn
    MAX-ACCESS   read-only
    STATUS       current
    DESCRIPTION
        "Cisco Firepower fabric:FcMonFiltRef:dn managed object property"
    ::= { cfprFabricFcMonFiltRefEntry 2 }

cfprFabricFcMonFiltRefRn OBJECT-TYPE
    SYNTAX       SnmpAdminString
    MAX-ACCESS   read-only
    STATUS       current
    DESCRIPTION
        "Cisco Firepower fabric:FcMonFiltRef:rn managed object property"
    ::= { cfprFabricFcMonFiltRefEntry 3 }

cfprFabricFcMonFiltRefSrcFiltDn OBJECT-TYPE
    SYNTAX       SnmpAdminString
    MAX-ACCESS   read-only
    STATUS       current
    DESCRIPTION
        "Cisco Firepower fabric:FcMonFiltRef:srcFiltDn
        managed object property"
    ::= { cfprFabricFcMonFiltRefEntry 4 }

cfprFabricFcMonFiltRefType OBJECT-TYPE
    SYNTAX       CfprFabricFcMonFiltRefType
    MAX-ACCESS   read-only
    STATUS       current
    DESCRIPTION
        "Cisco Firepower fabric:FcMonFiltRef:type managed object property"
    ::= { cfprFabricFcMonFiltRefEntry 5 }

cfprFabricFcMonSanTable OBJECT-TYPE
    SYNTAX           SEQUENCE OF CfprFabricFcMonSanEntry
    MAX-ACCESS       not-accessible
    STATUS           current
    DESCRIPTION
        "Cisco Firepower fabric:FcMonSan managed object table"
    ::= { cfprFabricObjects 52 }

cfprFabricFcMonSanEntry OBJECT-TYPE
    SYNTAX           CfprFabricFcMonSanEntry
    MAX-ACCESS       not-accessible
    STATUS           current
    DESCRIPTION
        "Entry for the cfprFabricFcMonSanTable table."
    INDEX { cfprFabricFcMonSanInstanceId }
    ::= { cfprFabricFcMonSanTable 1 }

CfprFabricFcMonSanEntry ::= SEQUENCE {
    cfprFabricFcMonSanInstanceId                                     CfprManagedObjectId,
    cfprFabricFcMonSanDn                                             CfprManagedObjectDn,
    cfprFabricFcMonSanRn                                             SnmpAdminString,
    cfprFabricFcMonSanId                                             CfprNetworkSwitchId,
    cfprFabricFcMonSanLocale                                         CfprFabricExternalLocale,
    cfprFabricFcMonSanName                                           SnmpAdminString,
    cfprFabricFcMonSanTransport                                      CfprFabricFcMonSanTransport,
    cfprFabricFcMonSanType                                           CfprFabricFcMonSanType
}

cfprFabricFcMonSanInstanceId OBJECT-TYPE
    SYNTAX       CfprManagedObjectId
    MAX-ACCESS   not-accessible
    STATUS       current
    DESCRIPTION
        "Instance identifier of the managed object."
    ::= { cfprFabricFcMonSanEntry 1 }

cfprFabricFcMonSanDn OBJECT-TYPE
    SYNTAX       CfprManagedObjectDn
    MAX-ACCESS   read-only
    STATUS       current
    DESCRIPTION
        "Cisco Firepower fabric:FcMonSan:dn managed object property"
    ::= { cfprFabricFcMonSanEntry 2 }

cfprFabricFcMonSanRn OBJECT-TYPE
    SYNTAX       SnmpAdminString
    MAX-ACCESS   read-only
    STATUS       current
    DESCRIPTION
        "Cisco Firepower fabric:FcMonSan:rn managed object property"
    ::= { cfprFabricFcMonSanEntry 3 }

cfprFabricFcMonSanId OBJECT-TYPE
    SYNTAX       CfprNetworkSwitchId
    MAX-ACCESS   read-only
    STATUS       current
    DESCRIPTION
        "Cisco Firepower fabric:FcMonSan:id managed object property"
    ::= { cfprFabricFcMonSanEntry 4 }

cfprFabricFcMonSanLocale OBJECT-TYPE
    SYNTAX       CfprFabricExternalLocale
    MAX-ACCESS   read-only
    STATUS       current
    DESCRIPTION
        "Cisco Firepower fabric:FcMonSan:locale managed object property"
    ::= { cfprFabricFcMonSanEntry 5 }

cfprFabricFcMonSanName OBJECT-TYPE
    SYNTAX       SnmpAdminString
    MAX-ACCESS   read-only
    STATUS       current
    DESCRIPTION
        "Cisco Firepower fabric:FcMonSan:name managed object property"
    ::= { cfprFabricFcMonSanEntry 6 }

cfprFabricFcMonSanTransport OBJECT-TYPE
    SYNTAX       CfprFabricFcMonSanTransport
    MAX-ACCESS   read-only
    STATUS       current
    DESCRIPTION
        "Cisco Firepower fabric:FcMonSan:transport managed
        object property"
    ::= { cfprFabricFcMonSanEntry 7 }

cfprFabricFcMonSanType OBJECT-TYPE
    SYNTAX       CfprFabricFcMonSanType
    MAX-ACCESS   read-only
    STATUS       current
    DESCRIPTION
        "Cisco Firepower fabric:FcMonSan:type managed object property"
    ::= { cfprFabricFcMonSanEntry 8 }

cfprFabricFcMonSrcEpTable OBJECT-TYPE
    SYNTAX           SEQUENCE OF CfprFabricFcMonSrcEpEntry
    MAX-ACCESS       not-accessible
    STATUS           current
    DESCRIPTION
        "Cisco Firepower fabric:FcMonSrcEp managed object table"
    ::= { cfprFabricObjects 53 }

cfprFabricFcMonSrcEpEntry OBJECT-TYPE
    SYNTAX           CfprFabricFcMonSrcEpEntry
    MAX-ACCESS       not-accessible
    STATUS           current
    DESCRIPTION
        "Entry for the cfprFabricFcMonSrcEpTable table."
    INDEX { cfprFabricFcMonSrcEpInstanceId }
    ::= { cfprFabricFcMonSrcEpTable 1 }

CfprFabricFcMonSrcEpEntry ::= SEQUENCE {
    cfprFabricFcMonSrcEpInstanceId                                   CfprManagedObjectId,
    cfprFabricFcMonSrcEpDn                                           CfprManagedObjectDn,
    cfprFabricFcMonSrcEpRn                                           SnmpAdminString,
    cfprFabricFcMonSrcEpDirection                                    CfprFabricTrafficDirection,
    cfprFabricFcMonSrcEpName                                         SnmpAdminString,
    cfprFabricFcMonSrcEpSession                                      Gauge32,
    cfprFabricFcMonSrcEpTransport                                    CfprNetworkTransport,
    cfprFabricFcMonSrcEpType                                         CfprFabricFcMonSrcEpType
}

cfprFabricFcMonSrcEpInstanceId OBJECT-TYPE
    SYNTAX       CfprManagedObjectId
    MAX-ACCESS   not-accessible
    STATUS       current
    DESCRIPTION
        "Instance identifier of the managed object."
    ::= { cfprFabricFcMonSrcEpEntry 1 }

cfprFabricFcMonSrcEpDn OBJECT-TYPE
    SYNTAX       CfprManagedObjectDn
    MAX-ACCESS   read-only
    STATUS       current
    DESCRIPTION
        "Cisco Firepower fabric:FcMonSrcEp:dn managed object property"
    ::= { cfprFabricFcMonSrcEpEntry 2 }

cfprFabricFcMonSrcEpRn OBJECT-TYPE
    SYNTAX       SnmpAdminString
    MAX-ACCESS   read-only
    STATUS       current
    DESCRIPTION
        "Cisco Firepower fabric:FcMonSrcEp:rn managed object property"
    ::= { cfprFabricFcMonSrcEpEntry 3 }

cfprFabricFcMonSrcEpDirection OBJECT-TYPE
    SYNTAX       CfprFabricTrafficDirection
    MAX-ACCESS   read-only
    STATUS       current
    DESCRIPTION
        "Cisco Firepower fabric:FcMonSrcEp:direction managed
        object property"
    ::= { cfprFabricFcMonSrcEpEntry 4 }

cfprFabricFcMonSrcEpName OBJECT-TYPE
    SYNTAX       SnmpAdminString
    MAX-ACCESS   read-only
    STATUS       current
    DESCRIPTION
        "Cisco Firepower fabric:FcMonSrcEp:name managed object property"
    ::= { cfprFabricFcMonSrcEpEntry 5 }

cfprFabricFcMonSrcEpSession OBJECT-TYPE
    SYNTAX       Gauge32
    MAX-ACCESS   read-only
    STATUS       current
    DESCRIPTION
        "Cisco Firepower fabric:FcMonSrcEp:session managed
        object property"
    ::= { cfprFabricFcMonSrcEpEntry 6 }

cfprFabricFcMonSrcEpTransport OBJECT-TYPE
    SYNTAX       CfprNetworkTransport
    MAX-ACCESS   read-only
    STATUS       current
    DESCRIPTION
        "Cisco Firepower fabric:FcMonSrcEp:transport managed
        object property"
    ::= { cfprFabricFcMonSrcEpEntry 7 }

cfprFabricFcMonSrcEpType OBJECT-TYPE
    SYNTAX       CfprFabricFcMonSrcEpType
    MAX-ACCESS   read-only
    STATUS       current
    DESCRIPTION
        "Cisco Firepower fabric:FcMonSrcEp:type managed object property"
    ::= { cfprFabricFcMonSrcEpEntry 8 }

cfprFabricFcMonSrcRefTable OBJECT-TYPE
    SYNTAX           SEQUENCE OF CfprFabricFcMonSrcRefEntry
    MAX-ACCESS       not-accessible
    STATUS           current
    DESCRIPTION
        "Cisco Firepower fabric:FcMonSrcRef managed object table"
    ::= { cfprFabricObjects 54 }

cfprFabricFcMonSrcRefEntry OBJECT-TYPE
    SYNTAX           CfprFabricFcMonSrcRefEntry
    MAX-ACCESS       not-accessible
    STATUS           current
    DESCRIPTION
        "Entry for the cfprFabricFcMonSrcRefTable table."
    INDEX { cfprFabricFcMonSrcRefInstanceId }
    ::= { cfprFabricFcMonSrcRefTable 1 }

CfprFabricFcMonSrcRefEntry ::= SEQUENCE {
    cfprFabricFcMonSrcRefInstanceId                                  CfprManagedObjectId,
    cfprFabricFcMonSrcRefDn                                          CfprManagedObjectDn,
    cfprFabricFcMonSrcRefRn                                          SnmpAdminString,
    cfprFabricFcMonSrcRefId                                          Unsigned64,
    cfprFabricFcMonSrcRefSourceDn                                    SnmpAdminString,
    cfprFabricFcMonSrcRefSourceType                                  CfprFabricFcSourceType,
    cfprFabricFcMonSrcRefType                                        CfprFabricFcMonSrcRefType
}

cfprFabricFcMonSrcRefInstanceId OBJECT-TYPE
    SYNTAX       CfprManagedObjectId
    MAX-ACCESS   not-accessible
    STATUS       current
    DESCRIPTION
        "Instance identifier of the managed object."
    ::= { cfprFabricFcMonSrcRefEntry 1 }

cfprFabricFcMonSrcRefDn OBJECT-TYPE
    SYNTAX       CfprManagedObjectDn
    MAX-ACCESS   read-only
    STATUS       current
    DESCRIPTION
        "Cisco Firepower fabric:FcMonSrcRef:dn managed object property"
    ::= { cfprFabricFcMonSrcRefEntry 2 }

cfprFabricFcMonSrcRefRn OBJECT-TYPE
    SYNTAX       SnmpAdminString
    MAX-ACCESS   read-only
    STATUS       current
    DESCRIPTION
        "Cisco Firepower fabric:FcMonSrcRef:rn managed object property"
    ::= { cfprFabricFcMonSrcRefEntry 3 }

cfprFabricFcMonSrcRefId OBJECT-TYPE
    SYNTAX       Unsigned64
    MAX-ACCESS   read-only
    STATUS       current
    DESCRIPTION
        "Cisco Firepower fabric:FcMonSrcRef:id managed object property"
    ::= { cfprFabricFcMonSrcRefEntry 4 }

cfprFabricFcMonSrcRefSourceDn OBJECT-TYPE
    SYNTAX       SnmpAdminString
    MAX-ACCESS   read-only
    STATUS       current
    DESCRIPTION
        "Cisco Firepower fabric:FcMonSrcRef:sourceDn managed
        object property"
    ::= { cfprFabricFcMonSrcRefEntry 5 }

cfprFabricFcMonSrcRefSourceType OBJECT-TYPE
    SYNTAX       CfprFabricFcSourceType
    MAX-ACCESS   read-only
    STATUS       current
    DESCRIPTION
        "Cisco Firepower fabric:FcMonSrcRef:sourceType
        managed object property"
    ::= { cfprFabricFcMonSrcRefEntry 6 }

cfprFabricFcMonSrcRefType OBJECT-TYPE
    SYNTAX       CfprFabricFcMonSrcRefType
    MAX-ACCESS   read-only
    STATUS       current
    DESCRIPTION
        "Cisco Firepower fabric:FcMonSrcRef:type managed object property"
    ::= { cfprFabricFcMonSrcRefEntry 7 }

cfprFabricFcSanTable OBJECT-TYPE
    SYNTAX           SEQUENCE OF CfprFabricFcSanEntry
    MAX-ACCESS       not-accessible
    STATUS           current
    DESCRIPTION
        "Cisco Firepower fabric:FcSan managed object table"
    ::= { cfprFabricObjects 55 }

cfprFabricFcSanEntry OBJECT-TYPE
    SYNTAX           CfprFabricFcSanEntry
    MAX-ACCESS       not-accessible
    STATUS           current
    DESCRIPTION
        "Entry for the cfprFabricFcSanTable table."
    INDEX { cfprFabricFcSanInstanceId }
    ::= { cfprFabricFcSanTable 1 }

CfprFabricFcSanEntry ::= SEQUENCE {
    cfprFabricFcSanInstanceId                                        CfprManagedObjectId,
    cfprFabricFcSanDn                                                CfprManagedObjectDn,
    cfprFabricFcSanRn                                                SnmpAdminString,
    cfprFabricFcSanId                                                CfprNetworkSwitchId,
    cfprFabricFcSanLocale                                            CfprFabricExternalLocale,
    cfprFabricFcSanName                                              SnmpAdminString,
    cfprFabricFcSanTransport                                         CfprFabricFcSanTransport,
    cfprFabricFcSanType                                              CfprFabricSanType,
    cfprFabricFcSanUplinkTrunking                                    CfprFabricFcSanUplinkTrunking
}

cfprFabricFcSanInstanceId OBJECT-TYPE
    SYNTAX       CfprManagedObjectId
    MAX-ACCESS   not-accessible
    STATUS       current
    DESCRIPTION
        "Instance identifier of the managed object."
    ::= { cfprFabricFcSanEntry 1 }

cfprFabricFcSanDn OBJECT-TYPE
    SYNTAX       CfprManagedObjectDn
    MAX-ACCESS   read-only
    STATUS       current
    DESCRIPTION
        "Cisco Firepower fabric:FcSan:dn managed object property"
    ::= { cfprFabricFcSanEntry 2 }

cfprFabricFcSanRn OBJECT-TYPE
    SYNTAX       SnmpAdminString
    MAX-ACCESS   read-only
    STATUS       current
    DESCRIPTION
        "Cisco Firepower fabric:FcSan:rn managed object property"
    ::= { cfprFabricFcSanEntry 3 }

cfprFabricFcSanId OBJECT-TYPE
    SYNTAX       CfprNetworkSwitchId
    MAX-ACCESS   read-only
    STATUS       current
    DESCRIPTION
        "Cisco Firepower fabric:FcSan:id managed object property"
    ::= { cfprFabricFcSanEntry 4 }

cfprFabricFcSanLocale OBJECT-TYPE
    SYNTAX       CfprFabricExternalLocale
    MAX-ACCESS   read-only
    STATUS       current
    DESCRIPTION
        "Cisco Firepower fabric:FcSan:locale managed object property"
    ::= { cfprFabricFcSanEntry 5 }

cfprFabricFcSanName OBJECT-TYPE
    SYNTAX       SnmpAdminString
    MAX-ACCESS   read-only
    STATUS       current
    DESCRIPTION
        "Cisco Firepower fabric:FcSan:name managed object property"
    ::= { cfprFabricFcSanEntry 6 }

cfprFabricFcSanTransport OBJECT-TYPE
    SYNTAX       CfprFabricFcSanTransport
    MAX-ACCESS   read-only
    STATUS       current
    DESCRIPTION
        "Cisco Firepower fabric:FcSan:transport managed object property"
    ::= { cfprFabricFcSanEntry 7 }

cfprFabricFcSanType OBJECT-TYPE
    SYNTAX       CfprFabricSanType
    MAX-ACCESS   read-only
    STATUS       current
    DESCRIPTION
        "Cisco Firepower fabric:FcSan:type managed object property"
    ::= { cfprFabricFcSanEntry 8 }

cfprFabricFcSanUplinkTrunking OBJECT-TYPE
    SYNTAX       CfprFabricFcSanUplinkTrunking
    MAX-ACCESS   read-only
    STATUS       current
    DESCRIPTION
        "Cisco Firepower fabric:FcSan:uplinkTrunking managed
        object property"
    ::= { cfprFabricFcSanEntry 9 }

cfprFabricFcSanEpTable OBJECT-TYPE
    SYNTAX           SEQUENCE OF CfprFabricFcSanEpEntry
    MAX-ACCESS       not-accessible
    STATUS           current
    DESCRIPTION
        "Cisco Firepower fabric:FcSanEp managed object table"
    ::= { cfprFabricObjects 56 }

cfprFabricFcSanEpEntry OBJECT-TYPE
    SYNTAX           CfprFabricFcSanEpEntry
    MAX-ACCESS       not-accessible
    STATUS           current
    DESCRIPTION
        "Entry for the cfprFabricFcSanEpTable table."
    INDEX { cfprFabricFcSanEpInstanceId }
    ::= { cfprFabricFcSanEpTable 1 }

CfprFabricFcSanEpEntry ::= SEQUENCE {
    cfprFabricFcSanEpInstanceId                                      CfprManagedObjectId,
    cfprFabricFcSanEpDn                                              CfprManagedObjectDn,
    cfprFabricFcSanEpRn                                              SnmpAdminString,
    cfprFabricFcSanEpAdminState                                      CfprFabricExternalEpAdminState,
    cfprFabricFcSanEpAggrPortId                                      Gauge32,
    cfprFabricFcSanEpChassisId                                       Gauge32,
    cfprFabricFcSanEpEpDn                                            SnmpAdminString,
    cfprFabricFcSanEpFillPattern                                     CfprFabricFillPattern,
    cfprFabricFcSanEpFltAggr                                         Unsigned64,
    cfprFabricFcSanEpIfRole                                          CfprFabricSanEpIfRole,
    cfprFabricFcSanEpIfType                                          CfprFabricPIoEpIfType,
    cfprFabricFcSanEpLicGP                                           Unsigned64,
    cfprFabricFcSanEpLicState                                        CfprLicenseState,
    cfprFabricFcSanEpLocale                                          CfprFabricExternalEpLocale,
    cfprFabricFcSanEpName                                            SnmpAdminString,
    cfprFabricFcSanEpOperState                                       CfprFabricPIoEpOperState,
    cfprFabricFcSanEpOperStateReason                                 SnmpAdminString,
    cfprFabricFcSanEpPeerAggrPortId                                  Gauge32,
    cfprFabricFcSanEpPeerChassisId                                   Gauge32,
    cfprFabricFcSanEpPeerDn                                          SnmpAdminString,
    cfprFabricFcSanEpPeerPortId                                      Gauge32,
    cfprFabricFcSanEpPeerSlotId                                      Gauge32,
    cfprFabricFcSanEpPortId                                          CfprFabricFcSanEpPortId,
    cfprFabricFcSanEpSlotId                                          CfprFabricFcSanEpSlotId,
    cfprFabricFcSanEpSwitchId                                        CfprNetworkSwitchId,
    cfprFabricFcSanEpTransport                                       CfprFabricAFcSanEpTransport,
    cfprFabricFcSanEpType                                            CfprFabricSanEpType,
    cfprFabricFcSanEpUsrLbl                                          SnmpAdminString,
    cfprFabricFcSanEpWarnings                                        CfprFabricWarnings
}

cfprFabricFcSanEpInstanceId OBJECT-TYPE
    SYNTAX       CfprManagedObjectId
    MAX-ACCESS   not-accessible
    STATUS       current
    DESCRIPTION
        "Instance identifier of the managed object."
    ::= { cfprFabricFcSanEpEntry 1 }

cfprFabricFcSanEpDn OBJECT-TYPE
    SYNTAX       CfprManagedObjectDn
    MAX-ACCESS   read-only
    STATUS       current
    DESCRIPTION
        "Cisco Firepower fabric:FcSanEp:dn managed object property"
    ::= { cfprFabricFcSanEpEntry 2 }

cfprFabricFcSanEpRn OBJECT-TYPE
    SYNTAX       SnmpAdminString
    MAX-ACCESS   read-only
    STATUS       current
    DESCRIPTION
        "Cisco Firepower fabric:FcSanEp:rn managed object property"
    ::= { cfprFabricFcSanEpEntry 3 }

cfprFabricFcSanEpAdminState OBJECT-TYPE
    SYNTAX       CfprFabricExternalEpAdminState
    MAX-ACCESS   read-only
    STATUS       current
    DESCRIPTION
        "Cisco Firepower fabric:FcSanEp:adminState managed
        object property"
    ::= { cfprFabricFcSanEpEntry 4 }

cfprFabricFcSanEpAggrPortId OBJECT-TYPE
    SYNTAX       Gauge32
    MAX-ACCESS   read-only
    STATUS       current
    DESCRIPTION
        "Cisco Firepower fabric:FcSanEp:aggrPortId managed
        object property"
    ::= { cfprFabricFcSanEpEntry 5 }

cfprFabricFcSanEpChassisId OBJECT-TYPE
    SYNTAX       Gauge32
    MAX-ACCESS   read-only
    STATUS       current
    DESCRIPTION
        "Cisco Firepower fabric:FcSanEp:chassisId managed object property"
    ::= { cfprFabricFcSanEpEntry 6 }

cfprFabricFcSanEpEpDn OBJECT-TYPE
    SYNTAX       SnmpAdminString
    MAX-ACCESS   read-only
    STATUS       current
    DESCRIPTION
        "Cisco Firepower fabric:FcSanEp:epDn managed object property"
    ::= { cfprFabricFcSanEpEntry 7 }

cfprFabricFcSanEpFillPattern OBJECT-TYPE
    SYNTAX       CfprFabricFillPattern
    MAX-ACCESS   read-only
    STATUS       current
    DESCRIPTION
        "Cisco Firepower fabric:FcSanEp:fillPattern managed
        object property"
    ::= { cfprFabricFcSanEpEntry 8 }

cfprFabricFcSanEpFltAggr OBJECT-TYPE
    SYNTAX       Unsigned64
    MAX-ACCESS   read-only
    STATUS       current
    DESCRIPTION
        "Cisco Firepower fabric:FcSanEp:fltAggr managed object property"
    ::= { cfprFabricFcSanEpEntry 9 }

cfprFabricFcSanEpIfRole OBJECT-TYPE
    SYNTAX       CfprFabricSanEpIfRole
    MAX-ACCESS   read-only
    STATUS       current
    DESCRIPTION
        "Cisco Firepower fabric:FcSanEp:ifRole managed object property"
    ::= { cfprFabricFcSanEpEntry 10 }

cfprFabricFcSanEpIfType OBJECT-TYPE
    SYNTAX       CfprFabricPIoEpIfType
    MAX-ACCESS   read-only
    STATUS       current
    DESCRIPTION
        "Cisco Firepower fabric:FcSanEp:ifType managed object property"
    ::= { cfprFabricFcSanEpEntry 11 }

cfprFabricFcSanEpLicGP OBJECT-TYPE
    SYNTAX       Unsigned64
    MAX-ACCESS   read-only
    STATUS       current
    DESCRIPTION
        "Cisco Firepower fabric:FcSanEp:licGP managed object property"
    ::= { cfprFabricFcSanEpEntry 12 }

cfprFabricFcSanEpLicState OBJECT-TYPE
    SYNTAX       CfprLicenseState
    MAX-ACCESS   read-only
    STATUS       current
    DESCRIPTION
        "Cisco Firepower fabric:FcSanEp:licState managed object property"
    ::= { cfprFabricFcSanEpEntry 13 }

cfprFabricFcSanEpLocale OBJECT-TYPE
    SYNTAX       CfprFabricExternalEpLocale
    MAX-ACCESS   read-only
    STATUS       current
    DESCRIPTION
        "Cisco Firepower fabric:FcSanEp:locale managed object property"
    ::= { cfprFabricFcSanEpEntry 14 }

cfprFabricFcSanEpName OBJECT-TYPE
    SYNTAX       SnmpAdminString
    MAX-ACCESS   read-only
    STATUS       current
    DESCRIPTION
        "Cisco Firepower fabric:FcSanEp:name managed object property"
    ::= { cfprFabricFcSanEpEntry 15 }

cfprFabricFcSanEpOperState OBJECT-TYPE
    SYNTAX       CfprFabricPIoEpOperState
    MAX-ACCESS   read-only
    STATUS       current
    DESCRIPTION
        "Cisco Firepower fabric:FcSanEp:operState managed object property"
    ::= { cfprFabricFcSanEpEntry 16 }

cfprFabricFcSanEpOperStateReason OBJECT-TYPE
    SYNTAX       SnmpAdminString
    MAX-ACCESS   read-only
    STATUS       current
    DESCRIPTION
        "Cisco Firepower fabric:FcSanEp:operStateReason
        managed object property"
    ::= { cfprFabricFcSanEpEntry 17 }

cfprFabricFcSanEpPeerAggrPortId OBJECT-TYPE
    SYNTAX       Gauge32
    MAX-ACCESS   read-only
    STATUS       current
    DESCRIPTION
        "Cisco Firepower fabric:FcSanEp:peerAggrPortId
        managed object property"
    ::= { cfprFabricFcSanEpEntry 18 }

cfprFabricFcSanEpPeerChassisId OBJECT-TYPE
    SYNTAX       Gauge32
    MAX-ACCESS   read-only
    STATUS       current
    DESCRIPTION
        "Cisco Firepower fabric:FcSanEp:peerChassisId managed
        object property"
    ::= { cfprFabricFcSanEpEntry 19 }

cfprFabricFcSanEpPeerDn OBJECT-TYPE
    SYNTAX       SnmpAdminString
    MAX-ACCESS   read-only
    STATUS       current
    DESCRIPTION
        "Cisco Firepower fabric:FcSanEp:peerDn managed object property"
    ::= { cfprFabricFcSanEpEntry 20 }

cfprFabricFcSanEpPeerPortId OBJECT-TYPE
    SYNTAX       Gauge32
    MAX-ACCESS   read-only
    STATUS       current
    DESCRIPTION
        "Cisco Firepower fabric:FcSanEp:peerPortId managed
        object property"
    ::= { cfprFabricFcSanEpEntry 21 }

cfprFabricFcSanEpPeerSlotId OBJECT-TYPE
    SYNTAX       Gauge32
    MAX-ACCESS   read-only
    STATUS       current
    DESCRIPTION
        "Cisco Firepower fabric:FcSanEp:peerSlotId managed
        object property"
    ::= { cfprFabricFcSanEpEntry 22 }

cfprFabricFcSanEpPortId OBJECT-TYPE
    SYNTAX       CfprFabricFcSanEpPortId
    MAX-ACCESS   read-only
    STATUS       current
    DESCRIPTION
        "Cisco Firepower fabric:FcSanEp:portId managed object property"
    ::= { cfprFabricFcSanEpEntry 23 }

cfprFabricFcSanEpSlotId OBJECT-TYPE
    SYNTAX       CfprFabricFcSanEpSlotId
    MAX-ACCESS   read-only
    STATUS       current
    DESCRIPTION
        "Cisco Firepower fabric:FcSanEp:slotId managed object property"
    ::= { cfprFabricFcSanEpEntry 24 }

cfprFabricFcSanEpSwitchId OBJECT-TYPE
    SYNTAX       CfprNetworkSwitchId
    MAX-ACCESS   read-only
    STATUS       current
    DESCRIPTION
        "Cisco Firepower fabric:FcSanEp:switchId managed object property"
    ::= { cfprFabricFcSanEpEntry 25 }

cfprFabricFcSanEpTransport OBJECT-TYPE
    SYNTAX       CfprFabricAFcSanEpTransport
    MAX-ACCESS   read-only
    STATUS       current
    DESCRIPTION
        "Cisco Firepower fabric:FcSanEp:transport managed object property"
    ::= { cfprFabricFcSanEpEntry 26 }

cfprFabricFcSanEpType OBJECT-TYPE
    SYNTAX       CfprFabricSanEpType
    MAX-ACCESS   read-only
    STATUS       current
    DESCRIPTION
        "Cisco Firepower fabric:FcSanEp:type managed object property"
    ::= { cfprFabricFcSanEpEntry 27 }

cfprFabricFcSanEpUsrLbl OBJECT-TYPE
    SYNTAX       SnmpAdminString
    MAX-ACCESS   read-only
    STATUS       current
    DESCRIPTION
        "Cisco Firepower fabric:FcSanEp:usrLbl managed object property"
    ::= { cfprFabricFcSanEpEntry 28 }

cfprFabricFcSanEpWarnings OBJECT-TYPE
    SYNTAX       CfprFabricWarnings
    MAX-ACCESS   read-only
    STATUS       current
    DESCRIPTION
        "Cisco Firepower fabric:FcSanEp:warnings managed object property"
    ::= { cfprFabricFcSanEpEntry 29 }

cfprFabricFcSanPcTable OBJECT-TYPE
    SYNTAX           SEQUENCE OF CfprFabricFcSanPcEntry
    MAX-ACCESS       not-accessible
    STATUS           current
    DESCRIPTION
        "Cisco Firepower fabric:FcSanPc managed object table"
    ::= { cfprFabricObjects 57 }

cfprFabricFcSanPcEntry OBJECT-TYPE
    SYNTAX           CfprFabricFcSanPcEntry
    MAX-ACCESS       not-accessible
    STATUS           current
    DESCRIPTION
        "Entry for the cfprFabricFcSanPcTable table."
    INDEX { cfprFabricFcSanPcInstanceId }
    ::= { cfprFabricFcSanPcTable 1 }

CfprFabricFcSanPcEntry ::= SEQUENCE {
    cfprFabricFcSanPcInstanceId                                      CfprManagedObjectId,
    cfprFabricFcSanPcDn                                              CfprManagedObjectDn,
    cfprFabricFcSanPcRn                                              SnmpAdminString,
    cfprFabricFcSanPcAdminSpeed                                      CfprPortSpeed,
    cfprFabricFcSanPcAdminState                                      CfprFabricCIoEpAdminState,
    cfprFabricFcSanPcConfigState                                     CfprFabricConfigState,
    cfprFabricFcSanPcConfigStatus                                    CfprFabricPcConfigStatus,
    cfprFabricFcSanPcDescr                                           SnmpAdminString,
    cfprFabricFcSanPcEpDn                                            SnmpAdminString,
    cfprFabricFcSanPcFltAggr                                         Unsigned64,
    cfprFabricFcSanPcIfRole                                          CfprFabricSanPcIfRole,
    cfprFabricFcSanPcIfType                                          CfprFabricCIoEpIfType,
    cfprFabricFcSanPcLocale                                          CfprFabricExternalPcLocale,
    cfprFabricFcSanPcName                                            SnmpAdminString,
    cfprFabricFcSanPcOperSpeed                                       Gauge32,
    cfprFabricFcSanPcOperState                                       CfprNetworkPortOperState,
    cfprFabricFcSanPcPeerDn                                          SnmpAdminString,
    cfprFabricFcSanPcPortId                                          Gauge32,
    cfprFabricFcSanPcStateQual                                       SnmpAdminString,
    cfprFabricFcSanPcSwitchId                                        CfprNetworkSwitchId,
    cfprFabricFcSanPcTransport                                       CfprFabricFcSanPcTransport,
    cfprFabricFcSanPcType                                            CfprFabricSanPcType,
    cfprFabricFcSanPcWarnings                                        CfprFabricWarnings
}

cfprFabricFcSanPcInstanceId OBJECT-TYPE
    SYNTAX       CfprManagedObjectId
    MAX-ACCESS   not-accessible
    STATUS       current
    DESCRIPTION
        "Instance identifier of the managed object."
    ::= { cfprFabricFcSanPcEntry 1 }

cfprFabricFcSanPcDn OBJECT-TYPE
    SYNTAX       CfprManagedObjectDn
    MAX-ACCESS   read-only
    STATUS       current
    DESCRIPTION
        "Cisco Firepower fabric:FcSanPc:dn managed object property"
    ::= { cfprFabricFcSanPcEntry 2 }

cfprFabricFcSanPcRn OBJECT-TYPE
    SYNTAX       SnmpAdminString
    MAX-ACCESS   read-only
    STATUS       current
    DESCRIPTION
        "Cisco Firepower fabric:FcSanPc:rn managed object property"
    ::= { cfprFabricFcSanPcEntry 3 }

cfprFabricFcSanPcAdminSpeed OBJECT-TYPE
    SYNTAX       CfprPortSpeed
    MAX-ACCESS   read-only
    STATUS       current
    DESCRIPTION
        "Cisco Firepower fabric:FcSanPc:adminSpeed managed
        object property"
    ::= { cfprFabricFcSanPcEntry 4 }

cfprFabricFcSanPcAdminState OBJECT-TYPE
    SYNTAX       CfprFabricCIoEpAdminState
    MAX-ACCESS   read-only
    STATUS       current
    DESCRIPTION
        "Cisco Firepower fabric:FcSanPc:adminState managed
        object property"
    ::= { cfprFabricFcSanPcEntry 5 }

cfprFabricFcSanPcConfigState OBJECT-TYPE
    SYNTAX       CfprFabricConfigState
    MAX-ACCESS   read-only
    STATUS       current
    DESCRIPTION
        "Cisco Firepower fabric:FcSanPc:configState managed
        object property"
    ::= { cfprFabricFcSanPcEntry 6 }

cfprFabricFcSanPcConfigStatus OBJECT-TYPE
    SYNTAX       CfprFabricPcConfigStatus
    MAX-ACCESS   read-only
    STATUS       current
    DESCRIPTION
        "Cisco Firepower fabric:FcSanPc:configStatus managed
        object property"
    ::= { cfprFabricFcSanPcEntry 7 }

cfprFabricFcSanPcDescr OBJECT-TYPE
    SYNTAX       SnmpAdminString
    MAX-ACCESS   read-only
    STATUS       current
    DESCRIPTION
        "Cisco Firepower fabric:FcSanPc:descr managed object property"
    ::= { cfprFabricFcSanPcEntry 8 }

cfprFabricFcSanPcEpDn OBJECT-TYPE
    SYNTAX       SnmpAdminString
    MAX-ACCESS   read-only
    STATUS       current
    DESCRIPTION
        "Cisco Firepower fabric:FcSanPc:epDn managed object property"
    ::= { cfprFabricFcSanPcEntry 9 }

cfprFabricFcSanPcFltAggr OBJECT-TYPE
    SYNTAX       Unsigned64
    MAX-ACCESS   read-only
    STATUS       current
    DESCRIPTION
        "Cisco Firepower fabric:FcSanPc:fltAggr managed object property"
    ::= { cfprFabricFcSanPcEntry 10 }

cfprFabricFcSanPcIfRole OBJECT-TYPE
    SYNTAX       CfprFabricSanPcIfRole
    MAX-ACCESS   read-only
    STATUS       current
    DESCRIPTION
        "Cisco Firepower fabric:FcSanPc:ifRole managed object property"
    ::= { cfprFabricFcSanPcEntry 11 }

cfprFabricFcSanPcIfType OBJECT-TYPE
    SYNTAX       CfprFabricCIoEpIfType
    MAX-ACCESS   read-only
    STATUS       current
    DESCRIPTION
        "Cisco Firepower fabric:FcSanPc:ifType managed object property"
    ::= { cfprFabricFcSanPcEntry 12 }

cfprFabricFcSanPcLocale OBJECT-TYPE
    SYNTAX       CfprFabricExternalPcLocale
    MAX-ACCESS   read-only
    STATUS       current
    DESCRIPTION
        "Cisco Firepower fabric:FcSanPc:locale managed object property"
    ::= { cfprFabricFcSanPcEntry 13 }

cfprFabricFcSanPcName OBJECT-TYPE
    SYNTAX       SnmpAdminString
    MAX-ACCESS   read-only
    STATUS       current
    DESCRIPTION
        "Cisco Firepower fabric:FcSanPc:name managed object property"
    ::= { cfprFabricFcSanPcEntry 14 }

cfprFabricFcSanPcOperSpeed OBJECT-TYPE
    SYNTAX       Gauge32
    MAX-ACCESS   read-only
    STATUS       current
    DESCRIPTION
        "Cisco Firepower fabric:FcSanPc:operSpeed managed object property"
    ::= { cfprFabricFcSanPcEntry 15 }

cfprFabricFcSanPcOperState OBJECT-TYPE
    SYNTAX       CfprNetworkPortOperState
    MAX-ACCESS   read-only
    STATUS       current
    DESCRIPTION
        "Cisco Firepower fabric:FcSanPc:operState managed object property"
    ::= { cfprFabricFcSanPcEntry 16 }

cfprFabricFcSanPcPeerDn OBJECT-TYPE
    SYNTAX       SnmpAdminString
    MAX-ACCESS   read-only
    STATUS       current
    DESCRIPTION
        "Cisco Firepower fabric:FcSanPc:peerDn managed object property"
    ::= { cfprFabricFcSanPcEntry 17 }

cfprFabricFcSanPcPortId OBJECT-TYPE
    SYNTAX       Gauge32
    MAX-ACCESS   read-only
    STATUS       current
    DESCRIPTION
        "Cisco Firepower fabric:FcSanPc:portId managed object property"
    ::= { cfprFabricFcSanPcEntry 18 }

cfprFabricFcSanPcStateQual OBJECT-TYPE
    SYNTAX       SnmpAdminString
    MAX-ACCESS   read-only
    STATUS       current
    DESCRIPTION
        "Cisco Firepower fabric:FcSanPc:stateQual managed object property"
    ::= { cfprFabricFcSanPcEntry 19 }

cfprFabricFcSanPcSwitchId OBJECT-TYPE
    SYNTAX       CfprNetworkSwitchId
    MAX-ACCESS   read-only
    STATUS       current
    DESCRIPTION
        "Cisco Firepower fabric:FcSanPc:switchId managed object property"
    ::= { cfprFabricFcSanPcEntry 20 }

cfprFabricFcSanPcTransport OBJECT-TYPE
    SYNTAX       CfprFabricFcSanPcTransport
    MAX-ACCESS   read-only
    STATUS       current
    DESCRIPTION
        "Cisco Firepower fabric:FcSanPc:transport managed object property"
    ::= { cfprFabricFcSanPcEntry 21 }

cfprFabricFcSanPcType OBJECT-TYPE
    SYNTAX       CfprFabricSanPcType
    MAX-ACCESS   read-only
    STATUS       current
    DESCRIPTION
        "Cisco Firepower fabric:FcSanPc:type managed object property"
    ::= { cfprFabricFcSanPcEntry 22 }

cfprFabricFcSanPcWarnings OBJECT-TYPE
    SYNTAX       CfprFabricWarnings
    MAX-ACCESS   read-only
    STATUS       current
    DESCRIPTION
        "Cisco Firepower fabric:FcSanPc:warnings managed object property"
    ::= { cfprFabricFcSanPcEntry 23 }

cfprFabricFcSanPcEpTable OBJECT-TYPE
    SYNTAX           SEQUENCE OF CfprFabricFcSanPcEpEntry
    MAX-ACCESS       not-accessible
    STATUS           current
    DESCRIPTION
        "Cisco Firepower fabric:FcSanPcEp managed object table"
    ::= { cfprFabricObjects 58 }

cfprFabricFcSanPcEpEntry OBJECT-TYPE
    SYNTAX           CfprFabricFcSanPcEpEntry
    MAX-ACCESS       not-accessible
    STATUS           current
    DESCRIPTION
        "Entry for the cfprFabricFcSanPcEpTable table."
    INDEX { cfprFabricFcSanPcEpInstanceId }
    ::= { cfprFabricFcSanPcEpTable 1 }

CfprFabricFcSanPcEpEntry ::= SEQUENCE {
    cfprFabricFcSanPcEpInstanceId                                    CfprManagedObjectId,
    cfprFabricFcSanPcEpDnData                                        CfprManagedObjectDn,
    cfprFabricFcSanPcEpRn                                            SnmpAdminString,
    cfprFabricFcSanPcEpAdminSpeed                                    CfprPortSpeed,
    cfprFabricFcSanPcEpAdminState                                    CfprFabricExternalEpAdminState,
    cfprFabricFcSanPcEpAggrPortId                                    Gauge32,
    cfprFabricFcSanPcEpChassisId                                     Gauge32,
    cfprFabricFcSanPcEpEpDn                                          SnmpAdminString,
    cfprFabricFcSanPcEpFillPattern                                   CfprFabricFillPattern,
    cfprFabricFcSanPcEpFltAggr                                       Unsigned64,
    cfprFabricFcSanPcEpIfRole                                        CfprFabricSanEpIfRole,
    cfprFabricFcSanPcEpIfType                                        CfprFabricPIoEpIfType,
    cfprFabricFcSanPcEpLicGP                                         Unsigned64,
    cfprFabricFcSanPcEpLicState                                      CfprLicenseState,
    cfprFabricFcSanPcEpLocale                                        CfprFabricExternalEpLocale,
    cfprFabricFcSanPcEpMembership                                    CfprFabricMembershipStatus,
    cfprFabricFcSanPcEpName                                          SnmpAdminString,
    cfprFabricFcSanPcEpOperState                                     CfprFabricPIoEpOperState,
    cfprFabricFcSanPcEpOperStateReason                               SnmpAdminString,
    cfprFabricFcSanPcEpPeerAggrPortId                                Gauge32,
    cfprFabricFcSanPcEpPeerChassisId                                 Gauge32,
    cfprFabricFcSanPcEpPeerDn                                        SnmpAdminString,
    cfprFabricFcSanPcEpPeerPortId                                    Gauge32,
    cfprFabricFcSanPcEpPeerSlotId                                    Gauge32,
    cfprFabricFcSanPcEpPortId                                        CfprFabricFcSanPcEpPortId,
    cfprFabricFcSanPcEpSlotId                                        CfprFabricFcSanPcEpSlotId,
    cfprFabricFcSanPcEpSwitchId                                      CfprNetworkSwitchId,
    cfprFabricFcSanPcEpTransport                                     CfprFabricAFcSanEpTransport,
    cfprFabricFcSanPcEpType                                          CfprFabricSanEpType,
    cfprFabricFcSanPcEpWarnings                                      CfprFabricWarnings
}

cfprFabricFcSanPcEpInstanceId OBJECT-TYPE
    SYNTAX       CfprManagedObjectId
    MAX-ACCESS   not-accessible
    STATUS       current
    DESCRIPTION
        "Instance identifier of the managed object."
    ::= { cfprFabricFcSanPcEpEntry 1 }

cfprFabricFcSanPcEpDnData OBJECT-TYPE
    SYNTAX       CfprManagedObjectDn
    MAX-ACCESS   read-only
    STATUS       current
    DESCRIPTION
        "Cisco Firepower fabric:FcSanPcEp:dn managed object property"
    ::= { cfprFabricFcSanPcEpEntry 2 }

cfprFabricFcSanPcEpRn OBJECT-TYPE
    SYNTAX       SnmpAdminString
    MAX-ACCESS   read-only
    STATUS       current
    DESCRIPTION
        "Cisco Firepower fabric:FcSanPcEp:rn managed object property"
    ::= { cfprFabricFcSanPcEpEntry 3 }

cfprFabricFcSanPcEpAdminSpeed OBJECT-TYPE
    SYNTAX       CfprPortSpeed
    MAX-ACCESS   read-only
    STATUS       current
    DESCRIPTION
        "Cisco Firepower fabric:FcSanPcEp:adminSpeed managed
        object property"
    ::= { cfprFabricFcSanPcEpEntry 4 }

cfprFabricFcSanPcEpAdminState OBJECT-TYPE
    SYNTAX       CfprFabricExternalEpAdminState
    MAX-ACCESS   read-only
    STATUS       current
    DESCRIPTION
        "Cisco Firepower fabric:FcSanPcEp:adminState managed
        object property"
    ::= { cfprFabricFcSanPcEpEntry 5 }

cfprFabricFcSanPcEpAggrPortId OBJECT-TYPE
    SYNTAX       Gauge32
    MAX-ACCESS   read-only
    STATUS       current
    DESCRIPTION
        "Cisco Firepower fabric:FcSanPcEp:aggrPortId managed
        object property"
    ::= { cfprFabricFcSanPcEpEntry 6 }

cfprFabricFcSanPcEpChassisId OBJECT-TYPE
    SYNTAX       Gauge32
    MAX-ACCESS   read-only
    STATUS       current
    DESCRIPTION
        "Cisco Firepower fabric:FcSanPcEp:chassisId managed
        object property"
    ::= { cfprFabricFcSanPcEpEntry 7 }

cfprFabricFcSanPcEpEpDn OBJECT-TYPE
    SYNTAX       SnmpAdminString
    MAX-ACCESS   read-only
    STATUS       current
    DESCRIPTION
        "Cisco Firepower fabric:FcSanPcEp:epDn managed object property"
    ::= { cfprFabricFcSanPcEpEntry 8 }

cfprFabricFcSanPcEpFillPattern OBJECT-TYPE
    SYNTAX       CfprFabricFillPattern
    MAX-ACCESS   read-only
    STATUS       current
    DESCRIPTION
        "Cisco Firepower fabric:FcSanPcEp:fillPattern managed
        object property"
    ::= { cfprFabricFcSanPcEpEntry 9 }

cfprFabricFcSanPcEpFltAggr OBJECT-TYPE
    SYNTAX       Unsigned64
    MAX-ACCESS   read-only
    STATUS       current
    DESCRIPTION
        "Cisco Firepower fabric:FcSanPcEp:fltAggr managed object property"
    ::= { cfprFabricFcSanPcEpEntry 10 }

cfprFabricFcSanPcEpIfRole OBJECT-TYPE
    SYNTAX       CfprFabricSanEpIfRole
    MAX-ACCESS   read-only
    STATUS       current
    DESCRIPTION
        "Cisco Firepower fabric:FcSanPcEp:ifRole managed object property"
    ::= { cfprFabricFcSanPcEpEntry 11 }

cfprFabricFcSanPcEpIfType OBJECT-TYPE
    SYNTAX       CfprFabricPIoEpIfType
    MAX-ACCESS   read-only
    STATUS       current
    DESCRIPTION
        "Cisco Firepower fabric:FcSanPcEp:ifType managed object property"
    ::= { cfprFabricFcSanPcEpEntry 12 }

cfprFabricFcSanPcEpLicGP OBJECT-TYPE
    SYNTAX       Unsigned64
    MAX-ACCESS   read-only
    STATUS       current
    DESCRIPTION
        "Cisco Firepower fabric:FcSanPcEp:licGP managed object property"
    ::= { cfprFabricFcSanPcEpEntry 13 }

cfprFabricFcSanPcEpLicState OBJECT-TYPE
    SYNTAX       CfprLicenseState
    MAX-ACCESS   read-only
    STATUS       current
    DESCRIPTION
        "Cisco Firepower fabric:FcSanPcEp:licState managed
        object property"
    ::= { cfprFabricFcSanPcEpEntry 14 }

cfprFabricFcSanPcEpLocale OBJECT-TYPE
    SYNTAX       CfprFabricExternalEpLocale
    MAX-ACCESS   read-only
    STATUS       current
    DESCRIPTION
        "Cisco Firepower fabric:FcSanPcEp:locale managed object property"
    ::= { cfprFabricFcSanPcEpEntry 15 }

cfprFabricFcSanPcEpMembership OBJECT-TYPE
    SYNTAX       CfprFabricMembershipStatus
    MAX-ACCESS   read-only
    STATUS       current
    DESCRIPTION
        "Cisco Firepower fabric:FcSanPcEp:membership managed
        object property"
    ::= { cfprFabricFcSanPcEpEntry 16 }

cfprFabricFcSanPcEpName OBJECT-TYPE
    SYNTAX       SnmpAdminString
    MAX-ACCESS   read-only
    STATUS       current
    DESCRIPTION
        "Cisco Firepower fabric:FcSanPcEp:name managed object property"
    ::= { cfprFabricFcSanPcEpEntry 17 }

cfprFabricFcSanPcEpOperState OBJECT-TYPE
    SYNTAX       CfprFabricPIoEpOperState
    MAX-ACCESS   read-only
    STATUS       current
    DESCRIPTION
        "Cisco Firepower fabric:FcSanPcEp:operState managed
        object property"
    ::= { cfprFabricFcSanPcEpEntry 18 }

cfprFabricFcSanPcEpOperStateReason OBJECT-TYPE
    SYNTAX       SnmpAdminString
    MAX-ACCESS   read-only
    STATUS       current
    DESCRIPTION
        "Cisco Firepower fabric:FcSanPcEp:operStateReason
        managed object property"
    ::= { cfprFabricFcSanPcEpEntry 19 }

cfprFabricFcSanPcEpPeerAggrPortId OBJECT-TYPE
    SYNTAX       Gauge32
    MAX-ACCESS   read-only
    STATUS       current
    DESCRIPTION
        "Cisco Firepower fabric:FcSanPcEp:peerAggrPortId
        managed object property"
    ::= { cfprFabricFcSanPcEpEntry 20 }

cfprFabricFcSanPcEpPeerChassisId OBJECT-TYPE
    SYNTAX       Gauge32
    MAX-ACCESS   read-only
    STATUS       current
    DESCRIPTION
        "Cisco Firepower fabric:FcSanPcEp:peerChassisId
        managed object property"
    ::= { cfprFabricFcSanPcEpEntry 21 }

cfprFabricFcSanPcEpPeerDn OBJECT-TYPE
    SYNTAX       SnmpAdminString
    MAX-ACCESS   read-only
    STATUS       current
    DESCRIPTION
        "Cisco Firepower fabric:FcSanPcEp:peerDn managed object property"
    ::= { cfprFabricFcSanPcEpEntry 22 }

cfprFabricFcSanPcEpPeerPortId OBJECT-TYPE
    SYNTAX       Gauge32
    MAX-ACCESS   read-only
    STATUS       current
    DESCRIPTION
        "Cisco Firepower fabric:FcSanPcEp:peerPortId managed
        object property"
    ::= { cfprFabricFcSanPcEpEntry 23 }

cfprFabricFcSanPcEpPeerSlotId OBJECT-TYPE
    SYNTAX       Gauge32
    MAX-ACCESS   read-only
    STATUS       current
    DESCRIPTION
        "Cisco Firepower fabric:FcSanPcEp:peerSlotId managed
        object property"
    ::= { cfprFabricFcSanPcEpEntry 24 }

cfprFabricFcSanPcEpPortId OBJECT-TYPE
    SYNTAX       CfprFabricFcSanPcEpPortId
    MAX-ACCESS   read-only
    STATUS       current
    DESCRIPTION
        "Cisco Firepower fabric:FcSanPcEp:portId managed object property"
    ::= { cfprFabricFcSanPcEpEntry 25 }

cfprFabricFcSanPcEpSlotId OBJECT-TYPE
    SYNTAX       CfprFabricFcSanPcEpSlotId
    MAX-ACCESS   read-only
    STATUS       current
    DESCRIPTION
        "Cisco Firepower fabric:FcSanPcEp:slotId managed object property"
    ::= { cfprFabricFcSanPcEpEntry 26 }

cfprFabricFcSanPcEpSwitchId OBJECT-TYPE
    SYNTAX       CfprNetworkSwitchId
    MAX-ACCESS   read-only
    STATUS       current
    DESCRIPTION
        "Cisco Firepower fabric:FcSanPcEp:switchId managed
        object property"
    ::= { cfprFabricFcSanPcEpEntry 27 }

cfprFabricFcSanPcEpTransport OBJECT-TYPE
    SYNTAX       CfprFabricAFcSanEpTransport
    MAX-ACCESS   read-only
    STATUS       current
    DESCRIPTION
        "Cisco Firepower fabric:FcSanPcEp:transport managed
        object property"
    ::= { cfprFabricFcSanPcEpEntry 28 }

cfprFabricFcSanPcEpType OBJECT-TYPE
    SYNTAX       CfprFabricSanEpType
    MAX-ACCESS   read-only
    STATUS       current
    DESCRIPTION
        "Cisco Firepower fabric:FcSanPcEp:type managed object property"
    ::= { cfprFabricFcSanPcEpEntry 29 }

cfprFabricFcSanPcEpWarnings OBJECT-TYPE
    SYNTAX       CfprFabricWarnings
    MAX-ACCESS   read-only
    STATUS       current
    DESCRIPTION
        "Cisco Firepower fabric:FcSanPcEp:warnings managed
        object property"
    ::= { cfprFabricFcSanPcEpEntry 30 }

cfprFabricFcVsanPcTable OBJECT-TYPE
    SYNTAX           SEQUENCE OF CfprFabricFcVsanPcEntry
    MAX-ACCESS       not-accessible
    STATUS           current
    DESCRIPTION
        "Cisco Firepower fabric:FcVsanPc managed object table"
    ::= { cfprFabricObjects 59 }

cfprFabricFcVsanPcEntry OBJECT-TYPE
    SYNTAX           CfprFabricFcVsanPcEntry
    MAX-ACCESS       not-accessible
    STATUS           current
    DESCRIPTION
        "Entry for the cfprFabricFcVsanPcTable table."
    INDEX { cfprFabricFcVsanPcInstanceId }
    ::= { cfprFabricFcVsanPcTable 1 }

CfprFabricFcVsanPcEntry ::= SEQUENCE {
    cfprFabricFcVsanPcInstanceId                                     CfprManagedObjectId,
    cfprFabricFcVsanPcDn                                             CfprManagedObjectDn,
    cfprFabricFcVsanPcRn                                             SnmpAdminString,
    cfprFabricFcVsanPcAdminState                                     CfprFabricCIoEpAdminState,
    cfprFabricFcVsanPcDescr                                          SnmpAdminString,
    cfprFabricFcVsanPcEpDn                                           SnmpAdminString,
    cfprFabricFcVsanPcFltAggr                                        Unsigned64,
    cfprFabricFcVsanPcIfRole                                         CfprFabricSanPcIfRole,
    cfprFabricFcVsanPcIfType                                         CfprFabricCIoEpIfType,
    cfprFabricFcVsanPcLocale                                         CfprFabricExternalPcLocale,
    cfprFabricFcVsanPcName                                           SnmpAdminString,
    cfprFabricFcVsanPcOperState                                      CfprNetworkPortOperState,
    cfprFabricFcVsanPcPeerDn                                         SnmpAdminString,
    cfprFabricFcVsanPcPortId                                         Gauge32,
    cfprFabricFcVsanPcStateQual                                      SnmpAdminString,
    cfprFabricFcVsanPcSwitchId                                       CfprNetworkSwitchId,
    cfprFabricFcVsanPcTransport                                      CfprFabricFcVsanPcTransport,
    cfprFabricFcVsanPcType                                           CfprFabricSanPcType,
    cfprFabricFcVsanPcWarnings                                       CfprFabricWarnings
}

cfprFabricFcVsanPcInstanceId OBJECT-TYPE
    SYNTAX       CfprManagedObjectId
    MAX-ACCESS   not-accessible
    STATUS       current
    DESCRIPTION
        "Instance identifier of the managed object."
    ::= { cfprFabricFcVsanPcEntry 1 }

cfprFabricFcVsanPcDn OBJECT-TYPE
    SYNTAX       CfprManagedObjectDn
    MAX-ACCESS   read-only
    STATUS       current
    DESCRIPTION
        "Cisco Firepower fabric:FcVsanPc:dn managed object property"
    ::= { cfprFabricFcVsanPcEntry 2 }

cfprFabricFcVsanPcRn OBJECT-TYPE
    SYNTAX       SnmpAdminString
    MAX-ACCESS   read-only
    STATUS       current
    DESCRIPTION
        "Cisco Firepower fabric:FcVsanPc:rn managed object property"
    ::= { cfprFabricFcVsanPcEntry 3 }

cfprFabricFcVsanPcAdminState OBJECT-TYPE
    SYNTAX       CfprFabricCIoEpAdminState
    MAX-ACCESS   read-only
    STATUS       current
    DESCRIPTION
        "Cisco Firepower fabric:FcVsanPc:adminState managed
        object property"
    ::= { cfprFabricFcVsanPcEntry 4 }

cfprFabricFcVsanPcDescr OBJECT-TYPE
    SYNTAX       SnmpAdminString
    MAX-ACCESS   read-only
    STATUS       current
    DESCRIPTION
        "Cisco Firepower fabric:FcVsanPc:descr managed object property"
    ::= { cfprFabricFcVsanPcEntry 5 }

cfprFabricFcVsanPcEpDn OBJECT-TYPE
    SYNTAX       SnmpAdminString
    MAX-ACCESS   read-only
    STATUS       current
    DESCRIPTION
        "Cisco Firepower fabric:FcVsanPc:epDn managed object property"
    ::= { cfprFabricFcVsanPcEntry 6 }

cfprFabricFcVsanPcFltAggr OBJECT-TYPE
    SYNTAX       Unsigned64
    MAX-ACCESS   read-only
    STATUS       current
    DESCRIPTION
        "Cisco Firepower fabric:FcVsanPc:fltAggr managed object property"
    ::= { cfprFabricFcVsanPcEntry 7 }

cfprFabricFcVsanPcIfRole OBJECT-TYPE
    SYNTAX       CfprFabricSanPcIfRole
    MAX-ACCESS   read-only
    STATUS       current
    DESCRIPTION
        "Cisco Firepower fabric:FcVsanPc:ifRole managed object property"
    ::= { cfprFabricFcVsanPcEntry 8 }

cfprFabricFcVsanPcIfType OBJECT-TYPE
    SYNTAX       CfprFabricCIoEpIfType
    MAX-ACCESS   read-only
    STATUS       current
    DESCRIPTION
        "Cisco Firepower fabric:FcVsanPc:ifType managed object property"
    ::= { cfprFabricFcVsanPcEntry 9 }

cfprFabricFcVsanPcLocale OBJECT-TYPE
    SYNTAX       CfprFabricExternalPcLocale
    MAX-ACCESS   read-only
    STATUS       current
    DESCRIPTION
        "Cisco Firepower fabric:FcVsanPc:locale managed object property"
    ::= { cfprFabricFcVsanPcEntry 10 }

cfprFabricFcVsanPcName OBJECT-TYPE
    SYNTAX       SnmpAdminString
    MAX-ACCESS   read-only
    STATUS       current
    DESCRIPTION
        "Cisco Firepower fabric:FcVsanPc:name managed object property"
    ::= { cfprFabricFcVsanPcEntry 11 }

cfprFabricFcVsanPcOperState OBJECT-TYPE
    SYNTAX       CfprNetworkPortOperState
    MAX-ACCESS   read-only
    STATUS       current
    DESCRIPTION
        "Cisco Firepower fabric:FcVsanPc:operState managed
        object property"
    ::= { cfprFabricFcVsanPcEntry 12 }

cfprFabricFcVsanPcPeerDn OBJECT-TYPE
    SYNTAX       SnmpAdminString
    MAX-ACCESS   read-only
    STATUS       current
    DESCRIPTION
        "Cisco Firepower fabric:FcVsanPc:peerDn managed object property"
    ::= { cfprFabricFcVsanPcEntry 13 }

cfprFabricFcVsanPcPortId OBJECT-TYPE
    SYNTAX       Gauge32
    MAX-ACCESS   read-only
    STATUS       current
    DESCRIPTION
        "Cisco Firepower fabric:FcVsanPc:portId managed object property"
    ::= { cfprFabricFcVsanPcEntry 14 }

cfprFabricFcVsanPcStateQual OBJECT-TYPE
    SYNTAX       SnmpAdminString
    MAX-ACCESS   read-only
    STATUS       current
    DESCRIPTION
        "Cisco Firepower fabric:FcVsanPc:stateQual managed
        object property"
    ::= { cfprFabricFcVsanPcEntry 15 }

cfprFabricFcVsanPcSwitchId OBJECT-TYPE
    SYNTAX       CfprNetworkSwitchId
    MAX-ACCESS   read-only
    STATUS       current
    DESCRIPTION
        "Cisco Firepower fabric:FcVsanPc:switchId managed object property"
    ::= { cfprFabricFcVsanPcEntry 16 }

cfprFabricFcVsanPcTransport OBJECT-TYPE
    SYNTAX       CfprFabricFcVsanPcTransport
    MAX-ACCESS   read-only
    STATUS       current
    DESCRIPTION
        "Cisco Firepower fabric:FcVsanPc:transport managed
        object property"
    ::= { cfprFabricFcVsanPcEntry 17 }

cfprFabricFcVsanPcType OBJECT-TYPE
    SYNTAX       CfprFabricSanPcType
    MAX-ACCESS   read-only
    STATUS       current
    DESCRIPTION
        "Cisco Firepower fabric:FcVsanPc:type managed object property"
    ::= { cfprFabricFcVsanPcEntry 18 }

cfprFabricFcVsanPcWarnings OBJECT-TYPE
    SYNTAX       CfprFabricWarnings
    MAX-ACCESS   read-only
    STATUS       current
    DESCRIPTION
        "Cisco Firepower fabric:FcVsanPc:warnings managed object property"
    ::= { cfprFabricFcVsanPcEntry 19 }

cfprFabricFcVsanPortEpTable OBJECT-TYPE
    SYNTAX           SEQUENCE OF CfprFabricFcVsanPortEpEntry
    MAX-ACCESS       not-accessible
    STATUS           current
    DESCRIPTION
        "Cisco Firepower fabric:FcVsanPortEp managed object table"
    ::= { cfprFabricObjects 60 }

cfprFabricFcVsanPortEpEntry OBJECT-TYPE
    SYNTAX           CfprFabricFcVsanPortEpEntry
    MAX-ACCESS       not-accessible
    STATUS           current
    DESCRIPTION
        "Entry for the cfprFabricFcVsanPortEpTable table."
    INDEX { cfprFabricFcVsanPortEpInstanceId }
    ::= { cfprFabricFcVsanPortEpTable 1 }

CfprFabricFcVsanPortEpEntry ::= SEQUENCE {
    cfprFabricFcVsanPortEpInstanceId                                 CfprManagedObjectId,
    cfprFabricFcVsanPortEpDn                                         CfprManagedObjectDn,
    cfprFabricFcVsanPortEpRn                                         SnmpAdminString,
    cfprFabricFcVsanPortEpAdminState                                 CfprFabricExternalEpAdminState,
    cfprFabricFcVsanPortEpAggrPortId                                 Gauge32,
    cfprFabricFcVsanPortEpChassisId                                  Gauge32,
    cfprFabricFcVsanPortEpEpDn                                       SnmpAdminString,
    cfprFabricFcVsanPortEpFltAggr                                    Unsigned64,
    cfprFabricFcVsanPortEpIfRole                                     CfprFabricSanEpIfRole,
    cfprFabricFcVsanPortEpIfType                                     CfprFabricPIoEpIfType,
    cfprFabricFcVsanPortEpLicGP                                      Unsigned64,
    cfprFabricFcVsanPortEpLicState                                   CfprLicenseState,
    cfprFabricFcVsanPortEpLocale                                     CfprFabricExternalEpLocale,
    cfprFabricFcVsanPortEpName                                       SnmpAdminString,
    cfprFabricFcVsanPortEpOperState                                  CfprFabricPIoEpOperState,
    cfprFabricFcVsanPortEpOperStateReason                            SnmpAdminString,
    cfprFabricFcVsanPortEpPeerAggrPortId                             Gauge32,
    cfprFabricFcVsanPortEpPeerChassisId                              Gauge32,
    cfprFabricFcVsanPortEpPeerDn                                     SnmpAdminString,
    cfprFabricFcVsanPortEpPeerPortId                                 Gauge32,
    cfprFabricFcVsanPortEpPeerSlotId                                 Gauge32,
    cfprFabricFcVsanPortEpPortId                                     CfprFabricFcVsanPortEpPortId,
    cfprFabricFcVsanPortEpSlotId                                     CfprFabricFcVsanPortEpSlotId,
    cfprFabricFcVsanPortEpSwitchId                                   CfprNetworkSwitchId,
    cfprFabricFcVsanPortEpTransport                                  CfprFabricAFcSanEpTransport,
    cfprFabricFcVsanPortEpType                                       CfprFabricSanEpType,
    cfprFabricFcVsanPortEpWarnings                                   CfprFabricWarnings
}

cfprFabricFcVsanPortEpInstanceId OBJECT-TYPE
    SYNTAX       CfprManagedObjectId
    MAX-ACCESS   not-accessible
    STATUS       current
    DESCRIPTION
        "Instance identifier of the managed object."
    ::= { cfprFabricFcVsanPortEpEntry 1 }

cfprFabricFcVsanPortEpDn OBJECT-TYPE
    SYNTAX       CfprManagedObjectDn
    MAX-ACCESS   read-only
    STATUS       current
    DESCRIPTION
        "Cisco Firepower fabric:FcVsanPortEp:dn managed object property"
    ::= { cfprFabricFcVsanPortEpEntry 2 }

cfprFabricFcVsanPortEpRn OBJECT-TYPE
    SYNTAX       SnmpAdminString
    MAX-ACCESS   read-only
    STATUS       current
    DESCRIPTION
        "Cisco Firepower fabric:FcVsanPortEp:rn managed object property"
    ::= { cfprFabricFcVsanPortEpEntry 3 }

cfprFabricFcVsanPortEpAdminState OBJECT-TYPE
    SYNTAX       CfprFabricExternalEpAdminState
    MAX-ACCESS   read-only
    STATUS       current
    DESCRIPTION
        "Cisco Firepower fabric:FcVsanPortEp:adminState
        managed object property"
    ::= { cfprFabricFcVsanPortEpEntry 4 }

cfprFabricFcVsanPortEpAggrPortId OBJECT-TYPE
    SYNTAX       Gauge32
    MAX-ACCESS   read-only
    STATUS       current
    DESCRIPTION
        "Cisco Firepower fabric:FcVsanPortEp:aggrPortId
        managed object property"
    ::= { cfprFabricFcVsanPortEpEntry 5 }

cfprFabricFcVsanPortEpChassisId OBJECT-TYPE
    SYNTAX       Gauge32
    MAX-ACCESS   read-only
    STATUS       current
    DESCRIPTION
        "Cisco Firepower fabric:FcVsanPortEp:chassisId
        managed object property"
    ::= { cfprFabricFcVsanPortEpEntry 6 }

cfprFabricFcVsanPortEpEpDn OBJECT-TYPE
    SYNTAX       SnmpAdminString
    MAX-ACCESS   read-only
    STATUS       current
    DESCRIPTION
        "Cisco Firepower fabric:FcVsanPortEp:epDn managed object property"
    ::= { cfprFabricFcVsanPortEpEntry 7 }

cfprFabricFcVsanPortEpFltAggr OBJECT-TYPE
    SYNTAX       Unsigned64
    MAX-ACCESS   read-only
    STATUS       current
    DESCRIPTION
        "Cisco Firepower fabric:FcVsanPortEp:fltAggr managed
        object property"
    ::= { cfprFabricFcVsanPortEpEntry 8 }

cfprFabricFcVsanPortEpIfRole OBJECT-TYPE
    SYNTAX       CfprFabricSanEpIfRole
    MAX-ACCESS   read-only
    STATUS       current
    DESCRIPTION
        "Cisco Firepower fabric:FcVsanPortEp:ifRole managed
        object property"
    ::= { cfprFabricFcVsanPortEpEntry 9 }

cfprFabricFcVsanPortEpIfType OBJECT-TYPE
    SYNTAX       CfprFabricPIoEpIfType
    MAX-ACCESS   read-only
    STATUS       current
    DESCRIPTION
        "Cisco Firepower fabric:FcVsanPortEp:ifType managed
        object property"
    ::= { cfprFabricFcVsanPortEpEntry 10 }

cfprFabricFcVsanPortEpLicGP OBJECT-TYPE
    SYNTAX       Unsigned64
    MAX-ACCESS   read-only
    STATUS       current
    DESCRIPTION
        "Cisco Firepower fabric:FcVsanPortEp:licGP managed
        object property"
    ::= { cfprFabricFcVsanPortEpEntry 11 }

cfprFabricFcVsanPortEpLicState OBJECT-TYPE
    SYNTAX       CfprLicenseState
    MAX-ACCESS   read-only
    STATUS       current
    DESCRIPTION
        "Cisco Firepower fabric:FcVsanPortEp:licState managed
        object property"
    ::= { cfprFabricFcVsanPortEpEntry 12 }

cfprFabricFcVsanPortEpLocale OBJECT-TYPE
    SYNTAX       CfprFabricExternalEpLocale
    MAX-ACCESS   read-only
    STATUS       current
    DESCRIPTION
        "Cisco Firepower fabric:FcVsanPortEp:locale managed
        object property"
    ::= { cfprFabricFcVsanPortEpEntry 13 }

cfprFabricFcVsanPortEpName OBJECT-TYPE
    SYNTAX       SnmpAdminString
    MAX-ACCESS   read-only
    STATUS       current
    DESCRIPTION
        "Cisco Firepower fabric:FcVsanPortEp:name managed object property"
    ::= { cfprFabricFcVsanPortEpEntry 14 }

cfprFabricFcVsanPortEpOperState OBJECT-TYPE
    SYNTAX       CfprFabricPIoEpOperState
    MAX-ACCESS   read-only
    STATUS       current
    DESCRIPTION
        "Cisco Firepower fabric:FcVsanPortEp:operState
        managed object property"
    ::= { cfprFabricFcVsanPortEpEntry 15 }

cfprFabricFcVsanPortEpOperStateReason OBJECT-TYPE
    SYNTAX       SnmpAdminString
    MAX-ACCESS   read-only
    STATUS       current
    DESCRIPTION
        "Cisco Firepower fabric:FcVsanPortEp:operStateReason
        managed object property"
    ::= { cfprFabricFcVsanPortEpEntry 16 }

cfprFabricFcVsanPortEpPeerAggrPortId OBJECT-TYPE
    SYNTAX       Gauge32
    MAX-ACCESS   read-only
    STATUS       current
    DESCRIPTION
        "Cisco Firepower fabric:FcVsanPortEp:peerAggrPortId
        managed object property"
    ::= { cfprFabricFcVsanPortEpEntry 17 }

cfprFabricFcVsanPortEpPeerChassisId OBJECT-TYPE
    SYNTAX       Gauge32
    MAX-ACCESS   read-only
    STATUS       current
    DESCRIPTION
        "Cisco Firepower fabric:FcVsanPortEp:peerChassisId
        managed object property"
    ::= { cfprFabricFcVsanPortEpEntry 18 }

cfprFabricFcVsanPortEpPeerDn OBJECT-TYPE
    SYNTAX       SnmpAdminString
    MAX-ACCESS   read-only
    STATUS       current
    DESCRIPTION
        "Cisco Firepower fabric:FcVsanPortEp:peerDn managed
        object property"
    ::= { cfprFabricFcVsanPortEpEntry 19 }

cfprFabricFcVsanPortEpPeerPortId OBJECT-TYPE
    SYNTAX       Gauge32
    MAX-ACCESS   read-only
    STATUS       current
    DESCRIPTION
        "Cisco Firepower fabric:FcVsanPortEp:peerPortId
        managed object property"
    ::= { cfprFabricFcVsanPortEpEntry 20 }

cfprFabricFcVsanPortEpPeerSlotId OBJECT-TYPE
    SYNTAX       Gauge32
    MAX-ACCESS   read-only
    STATUS       current
    DESCRIPTION
        "Cisco Firepower fabric:FcVsanPortEp:peerSlotId
        managed object property"
    ::= { cfprFabricFcVsanPortEpEntry 21 }

cfprFabricFcVsanPortEpPortId OBJECT-TYPE
    SYNTAX       CfprFabricFcVsanPortEpPortId
    MAX-ACCESS   read-only
    STATUS       current
    DESCRIPTION
        "Cisco Firepower fabric:FcVsanPortEp:portId managed
        object property"
    ::= { cfprFabricFcVsanPortEpEntry 22 }

cfprFabricFcVsanPortEpSlotId OBJECT-TYPE
    SYNTAX       CfprFabricFcVsanPortEpSlotId
    MAX-ACCESS   read-only
    STATUS       current
    DESCRIPTION
        "Cisco Firepower fabric:FcVsanPortEp:slotId managed
        object property"
    ::= { cfprFabricFcVsanPortEpEntry 23 }

cfprFabricFcVsanPortEpSwitchId OBJECT-TYPE
    SYNTAX       CfprNetworkSwitchId
    MAX-ACCESS   read-only
    STATUS       current
    DESCRIPTION
        "Cisco Firepower fabric:FcVsanPortEp:switchId managed
        object property"
    ::= { cfprFabricFcVsanPortEpEntry 24 }

cfprFabricFcVsanPortEpTransport OBJECT-TYPE
    SYNTAX       CfprFabricAFcSanEpTransport
    MAX-ACCESS   read-only
    STATUS       current
    DESCRIPTION
        "Cisco Firepower fabric:FcVsanPortEp:transport
        managed object property"
    ::= { cfprFabricFcVsanPortEpEntry 25 }

cfprFabricFcVsanPortEpType OBJECT-TYPE
    SYNTAX       CfprFabricSanEpType
    MAX-ACCESS   read-only
    STATUS       current
    DESCRIPTION
        "Cisco Firepower fabric:FcVsanPortEp:type managed object property"
    ::= { cfprFabricFcVsanPortEpEntry 26 }

cfprFabricFcVsanPortEpWarnings OBJECT-TYPE
    SYNTAX       CfprFabricWarnings
    MAX-ACCESS   read-only
    STATUS       current
    DESCRIPTION
        "Cisco Firepower fabric:FcVsanPortEp:warnings managed
        object property"
    ::= { cfprFabricFcVsanPortEpEntry 27 }

cfprFabricFcoeEstcEpTable OBJECT-TYPE
    SYNTAX           SEQUENCE OF CfprFabricFcoeEstcEpEntry
    MAX-ACCESS       not-accessible
    STATUS           current
    DESCRIPTION
        "Cisco Firepower fabric:FcoeEstcEp managed object table"
    ::= { cfprFabricObjects 61 }

cfprFabricFcoeEstcEpEntry OBJECT-TYPE
    SYNTAX           CfprFabricFcoeEstcEpEntry
    MAX-ACCESS       not-accessible
    STATUS           current
    DESCRIPTION
        "Entry for the cfprFabricFcoeEstcEpTable table."
    INDEX { cfprFabricFcoeEstcEpInstanceId }
    ::= { cfprFabricFcoeEstcEpTable 1 }

CfprFabricFcoeEstcEpEntry ::= SEQUENCE {
    cfprFabricFcoeEstcEpInstanceId                                   CfprManagedObjectId,
    cfprFabricFcoeEstcEpDn                                           CfprManagedObjectDn,
    cfprFabricFcoeEstcEpRn                                           SnmpAdminString,
    cfprFabricFcoeEstcEpAdminState                                   CfprFabricExternalEpAdminState,
    cfprFabricFcoeEstcEpAggrPortId                                   Gauge32,
    cfprFabricFcoeEstcEpChassisId                                    Gauge32,
    cfprFabricFcoeEstcEpConfigState                                  CfprFabricConfigState,
    cfprFabricFcoeEstcEpEpDn                                         SnmpAdminString,
    cfprFabricFcoeEstcEpFcoeState                                    CfprFabricOperState,
    cfprFabricFcoeEstcEpFcoeStateReason                              SnmpAdminString,
    cfprFabricFcoeEstcEpFltAggr                                      Unsigned64,
    cfprFabricFcoeEstcEpIfRole                                       CfprFabricAFcoeEstcEpIfRole,
    cfprFabricFcoeEstcEpIfType                                       CfprFabricPIoEpIfType,
    cfprFabricFcoeEstcEpLicGP                                        Unsigned64,
    cfprFabricFcoeEstcEpLicState                                     CfprLicenseState,
    cfprFabricFcoeEstcEpLocale                                       CfprFabricExternalEpLocale,
    cfprFabricFcoeEstcEpName                                         SnmpAdminString,
    cfprFabricFcoeEstcEpOperState                                    CfprFabricPIoEpOperState,
    cfprFabricFcoeEstcEpOperStateReason                              SnmpAdminString,
    cfprFabricFcoeEstcEpPeerAggrPortId                               Gauge32,
    cfprFabricFcoeEstcEpPeerChassisId                                Gauge32,
    cfprFabricFcoeEstcEpPeerDn                                       SnmpAdminString,
    cfprFabricFcoeEstcEpPeerPortId                                   Gauge32,
    cfprFabricFcoeEstcEpPeerSlotId                                   Gauge32,
    cfprFabricFcoeEstcEpPortId                                       CfprFabricFcoeEstcEpPortId,
    cfprFabricFcoeEstcEpSlotId                                       CfprFabricFcoeEstcEpSlotId,
    cfprFabricFcoeEstcEpSwitchId                                     CfprNetworkSwitchId,
    cfprFabricFcoeEstcEpTransport                                    CfprFabricAFcoeEstcEpTransport,
    cfprFabricFcoeEstcEpType                                         CfprFabricAFcoeEstcEpType,
    cfprFabricFcoeEstcEpUsrLbl                                       SnmpAdminString,
    cfprFabricFcoeEstcEpWarnings                                     CfprFabricWarnings
}

cfprFabricFcoeEstcEpInstanceId OBJECT-TYPE
    SYNTAX       CfprManagedObjectId
    MAX-ACCESS   not-accessible
    STATUS       current
    DESCRIPTION
        "Instance identifier of the managed object."
    ::= { cfprFabricFcoeEstcEpEntry 1 }

cfprFabricFcoeEstcEpDn OBJECT-TYPE
    SYNTAX       CfprManagedObjectDn
    MAX-ACCESS   read-only
    STATUS       current
    DESCRIPTION
        "Cisco Firepower fabric:FcoeEstcEp:dn managed object property"
    ::= { cfprFabricFcoeEstcEpEntry 2 }

cfprFabricFcoeEstcEpRn OBJECT-TYPE
    SYNTAX       SnmpAdminString
    MAX-ACCESS   read-only
    STATUS       current
    DESCRIPTION
        "Cisco Firepower fabric:FcoeEstcEp:rn managed object property"
    ::= { cfprFabricFcoeEstcEpEntry 3 }

cfprFabricFcoeEstcEpAdminState OBJECT-TYPE
    SYNTAX       CfprFabricExternalEpAdminState
    MAX-ACCESS   read-only
    STATUS       current
    DESCRIPTION
        "Cisco Firepower fabric:FcoeEstcEp:adminState managed
        object property"
    ::= { cfprFabricFcoeEstcEpEntry 4 }

cfprFabricFcoeEstcEpAggrPortId OBJECT-TYPE
    SYNTAX       Gauge32
    MAX-ACCESS   read-only
    STATUS       current
    DESCRIPTION
        "Cisco Firepower fabric:FcoeEstcEp:aggrPortId managed
        object property"
    ::= { cfprFabricFcoeEstcEpEntry 5 }

cfprFabricFcoeEstcEpChassisId OBJECT-TYPE
    SYNTAX       Gauge32
    MAX-ACCESS   read-only
    STATUS       current
    DESCRIPTION
        "Cisco Firepower fabric:FcoeEstcEp:chassisId managed
        object property"
    ::= { cfprFabricFcoeEstcEpEntry 6 }

cfprFabricFcoeEstcEpConfigState OBJECT-TYPE
    SYNTAX       CfprFabricConfigState
    MAX-ACCESS   read-only
    STATUS       current
    DESCRIPTION
        "Cisco Firepower fabric:FcoeEstcEp:configState
        managed object property"
    ::= { cfprFabricFcoeEstcEpEntry 7 }

cfprFabricFcoeEstcEpEpDn OBJECT-TYPE
    SYNTAX       SnmpAdminString
    MAX-ACCESS   read-only
    STATUS       current
    DESCRIPTION
        "Cisco Firepower fabric:FcoeEstcEp:epDn managed object property"
    ::= { cfprFabricFcoeEstcEpEntry 8 }

cfprFabricFcoeEstcEpFcoeState OBJECT-TYPE
    SYNTAX       CfprFabricOperState
    MAX-ACCESS   read-only
    STATUS       current
    DESCRIPTION
        "Cisco Firepower fabric:FcoeEstcEp:fcoeState managed
        object property"
    ::= { cfprFabricFcoeEstcEpEntry 9 }

cfprFabricFcoeEstcEpFcoeStateReason OBJECT-TYPE
    SYNTAX       SnmpAdminString
    MAX-ACCESS   read-only
    STATUS       current
    DESCRIPTION
        "Cisco Firepower fabric:FcoeEstcEp:fcoeStateReason
        managed object property"
    ::= { cfprFabricFcoeEstcEpEntry 10 }

cfprFabricFcoeEstcEpFltAggr OBJECT-TYPE
    SYNTAX       Unsigned64
    MAX-ACCESS   read-only
    STATUS       current
    DESCRIPTION
        "Cisco Firepower fabric:FcoeEstcEp:fltAggr managed
        object property"
    ::= { cfprFabricFcoeEstcEpEntry 11 }

cfprFabricFcoeEstcEpIfRole OBJECT-TYPE
    SYNTAX       CfprFabricAFcoeEstcEpIfRole
    MAX-ACCESS   read-only
    STATUS       current
    DESCRIPTION
        "Cisco Firepower fabric:FcoeEstcEp:ifRole managed object property"
    ::= { cfprFabricFcoeEstcEpEntry 12 }

cfprFabricFcoeEstcEpIfType OBJECT-TYPE
    SYNTAX       CfprFabricPIoEpIfType
    MAX-ACCESS   read-only
    STATUS       current
    DESCRIPTION
        "Cisco Firepower fabric:FcoeEstcEp:ifType managed object property"
    ::= { cfprFabricFcoeEstcEpEntry 13 }

cfprFabricFcoeEstcEpLicGP OBJECT-TYPE
    SYNTAX       Unsigned64
    MAX-ACCESS   read-only
    STATUS       current
    DESCRIPTION
        "Cisco Firepower fabric:FcoeEstcEp:licGP managed object property"
    ::= { cfprFabricFcoeEstcEpEntry 14 }

cfprFabricFcoeEstcEpLicState OBJECT-TYPE
    SYNTAX       CfprLicenseState
    MAX-ACCESS   read-only
    STATUS       current
    DESCRIPTION
        "Cisco Firepower fabric:FcoeEstcEp:licState managed
        object property"
    ::= { cfprFabricFcoeEstcEpEntry 15 }

cfprFabricFcoeEstcEpLocale OBJECT-TYPE
    SYNTAX       CfprFabricExternalEpLocale
    MAX-ACCESS   read-only
    STATUS       current
    DESCRIPTION
        "Cisco Firepower fabric:FcoeEstcEp:locale managed object property"
    ::= { cfprFabricFcoeEstcEpEntry 16 }

cfprFabricFcoeEstcEpName OBJECT-TYPE
    SYNTAX       SnmpAdminString
    MAX-ACCESS   read-only
    STATUS       current
    DESCRIPTION
        "Cisco Firepower fabric:FcoeEstcEp:name managed object property"
    ::= { cfprFabricFcoeEstcEpEntry 17 }

cfprFabricFcoeEstcEpOperState OBJECT-TYPE
    SYNTAX       CfprFabricPIoEpOperState
    MAX-ACCESS   read-only
    STATUS       current
    DESCRIPTION
        "Cisco Firepower fabric:FcoeEstcEp:operState managed
        object property"
    ::= { cfprFabricFcoeEstcEpEntry 18 }

cfprFabricFcoeEstcEpOperStateReason OBJECT-TYPE
    SYNTAX       SnmpAdminString
    MAX-ACCESS   read-only
    STATUS       current
    DESCRIPTION
        "Cisco Firepower fabric:FcoeEstcEp:operStateReason
        managed object property"
    ::= { cfprFabricFcoeEstcEpEntry 19 }

cfprFabricFcoeEstcEpPeerAggrPortId OBJECT-TYPE
    SYNTAX       Gauge32
    MAX-ACCESS   read-only
    STATUS       current
    DESCRIPTION
        "Cisco Firepower fabric:FcoeEstcEp:peerAggrPortId
        managed object property"
    ::= { cfprFabricFcoeEstcEpEntry 20 }

cfprFabricFcoeEstcEpPeerChassisId OBJECT-TYPE
    SYNTAX       Gauge32
    MAX-ACCESS   read-only
    STATUS       current
    DESCRIPTION
        "Cisco Firepower fabric:FcoeEstcEp:peerChassisId
        managed object property"
    ::= { cfprFabricFcoeEstcEpEntry 21 }

cfprFabricFcoeEstcEpPeerDn OBJECT-TYPE
    SYNTAX       SnmpAdminString
    MAX-ACCESS   read-only
    STATUS       current
    DESCRIPTION
        "Cisco Firepower fabric:FcoeEstcEp:peerDn managed object property"
    ::= { cfprFabricFcoeEstcEpEntry 22 }

cfprFabricFcoeEstcEpPeerPortId OBJECT-TYPE
    SYNTAX       Gauge32
    MAX-ACCESS   read-only
    STATUS       current
    DESCRIPTION
        "Cisco Firepower fabric:FcoeEstcEp:peerPortId managed
        object property"
    ::= { cfprFabricFcoeEstcEpEntry 23 }

cfprFabricFcoeEstcEpPeerSlotId OBJECT-TYPE
    SYNTAX       Gauge32
    MAX-ACCESS   read-only
    STATUS       current
    DESCRIPTION
        "Cisco Firepower fabric:FcoeEstcEp:peerSlotId managed
        object property"
    ::= { cfprFabricFcoeEstcEpEntry 24 }

cfprFabricFcoeEstcEpPortId OBJECT-TYPE
    SYNTAX       CfprFabricFcoeEstcEpPortId
    MAX-ACCESS   read-only
    STATUS       current
    DESCRIPTION
        "Cisco Firepower fabric:FcoeEstcEp:portId managed object property"
    ::= { cfprFabricFcoeEstcEpEntry 25 }

cfprFabricFcoeEstcEpSlotId OBJECT-TYPE
    SYNTAX       CfprFabricFcoeEstcEpSlotId
    MAX-ACCESS   read-only
    STATUS       current
    DESCRIPTION
        "Cisco Firepower fabric:FcoeEstcEp:slotId managed object property"
    ::= { cfprFabricFcoeEstcEpEntry 26 }

cfprFabricFcoeEstcEpSwitchId OBJECT-TYPE
    SYNTAX       CfprNetworkSwitchId
    MAX-ACCESS   read-only
    STATUS       current
    DESCRIPTION
        "Cisco Firepower fabric:FcoeEstcEp:switchId managed
        object property"
    ::= { cfprFabricFcoeEstcEpEntry 27 }

cfprFabricFcoeEstcEpTransport OBJECT-TYPE
    SYNTAX       CfprFabricAFcoeEstcEpTransport
    MAX-ACCESS   read-only
    STATUS       current
    DESCRIPTION
        "Cisco Firepower fabric:FcoeEstcEp:transport managed
        object property"
    ::= { cfprFabricFcoeEstcEpEntry 28 }

cfprFabricFcoeEstcEpType OBJECT-TYPE
    SYNTAX       CfprFabricAFcoeEstcEpType
    MAX-ACCESS   read-only
    STATUS       current
    DESCRIPTION
        "Cisco Firepower fabric:FcoeEstcEp:type managed object property"
    ::= { cfprFabricFcoeEstcEpEntry 29 }

cfprFabricFcoeEstcEpUsrLbl OBJECT-TYPE
    SYNTAX       SnmpAdminString
    MAX-ACCESS   read-only
    STATUS       current
    DESCRIPTION
        "Cisco Firepower fabric:FcoeEstcEp:usrLbl managed object property"
    ::= { cfprFabricFcoeEstcEpEntry 30 }

cfprFabricFcoeEstcEpWarnings OBJECT-TYPE
    SYNTAX       CfprFabricWarnings
    MAX-ACCESS   read-only
    STATUS       current
    DESCRIPTION
        "Cisco Firepower fabric:FcoeEstcEp:warnings managed
        object property"
    ::= { cfprFabricFcoeEstcEpEntry 31 }

cfprFabricFcoeSanEpTable OBJECT-TYPE
    SYNTAX           SEQUENCE OF CfprFabricFcoeSanEpEntry
    MAX-ACCESS       not-accessible
    STATUS           current
    DESCRIPTION
        "Cisco Firepower fabric:FcoeSanEp managed object table"
    ::= { cfprFabricObjects 62 }

cfprFabricFcoeSanEpEntry OBJECT-TYPE
    SYNTAX           CfprFabricFcoeSanEpEntry
    MAX-ACCESS       not-accessible
    STATUS           current
    DESCRIPTION
        "Entry for the cfprFabricFcoeSanEpTable table."
    INDEX { cfprFabricFcoeSanEpInstanceId }
    ::= { cfprFabricFcoeSanEpTable 1 }

CfprFabricFcoeSanEpEntry ::= SEQUENCE {
    cfprFabricFcoeSanEpInstanceId                                    CfprManagedObjectId,
    cfprFabricFcoeSanEpDn                                            CfprManagedObjectDn,
    cfprFabricFcoeSanEpRn                                            SnmpAdminString,
    cfprFabricFcoeSanEpAdminState                                    CfprFabricExternalEpAdminState,
    cfprFabricFcoeSanEpAggrPortId                                    Gauge32,
    cfprFabricFcoeSanEpChassisId                                     Gauge32,
    cfprFabricFcoeSanEpConfigState                                   CfprFabricConfigState,
    cfprFabricFcoeSanEpEpDn                                          SnmpAdminString,
    cfprFabricFcoeSanEpEthLinkProfileName                            SnmpAdminString,
    cfprFabricFcoeSanEpFcoeState                                     CfprNetworkPortOperState,
    cfprFabricFcoeSanEpFcoeStateReason                               SnmpAdminString,
    cfprFabricFcoeSanEpFltAggr                                       Unsigned64,
    cfprFabricFcoeSanEpIfRole                                        CfprFabricSanEpIfRole,
    cfprFabricFcoeSanEpIfType                                        CfprFabricPIoEpIfType,
    cfprFabricFcoeSanEpLicGP                                         Unsigned64,
    cfprFabricFcoeSanEpLicState                                      CfprLicenseState,
    cfprFabricFcoeSanEpLocale                                        CfprFabricExternalEpLocale,
    cfprFabricFcoeSanEpName                                          SnmpAdminString,
    cfprFabricFcoeSanEpOperEthLinkProfileName                        SnmpAdminString,
    cfprFabricFcoeSanEpOperState                                     CfprFabricPIoEpOperState,
    cfprFabricFcoeSanEpOperStateReason                               SnmpAdminString,
    cfprFabricFcoeSanEpPeerAggrPortId                                Gauge32,
    cfprFabricFcoeSanEpPeerChassisId                                 Gauge32,
    cfprFabricFcoeSanEpPeerDn                                        SnmpAdminString,
    cfprFabricFcoeSanEpPeerPortId                                    Gauge32,
    cfprFabricFcoeSanEpPeerSlotId                                    Gauge32,
    cfprFabricFcoeSanEpPortId                                        CfprFabricFcoeSanEpPortId,
    cfprFabricFcoeSanEpSlotId                                        CfprFabricFcoeSanEpSlotId,
    cfprFabricFcoeSanEpSwitchId                                      CfprNetworkSwitchId,
    cfprFabricFcoeSanEpTransport                                     CfprFabricAFcoeSanEpTransport,
    cfprFabricFcoeSanEpType                                          CfprFabricSanEpType,
    cfprFabricFcoeSanEpUdldOperState                                 CfprFabricUdldOperState,
    cfprFabricFcoeSanEpUsrLbl                                        SnmpAdminString,
    cfprFabricFcoeSanEpWarnings                                      CfprFabricWarnings
}

cfprFabricFcoeSanEpInstanceId OBJECT-TYPE
    SYNTAX       CfprManagedObjectId
    MAX-ACCESS   not-accessible
    STATUS       current
    DESCRIPTION
        "Instance identifier of the managed object."
    ::= { cfprFabricFcoeSanEpEntry 1 }

cfprFabricFcoeSanEpDn OBJECT-TYPE
    SYNTAX       CfprManagedObjectDn
    MAX-ACCESS   read-only
    STATUS       current
    DESCRIPTION
        "Cisco Firepower fabric:FcoeSanEp:dn managed object property"
    ::= { cfprFabricFcoeSanEpEntry 2 }

cfprFabricFcoeSanEpRn OBJECT-TYPE
    SYNTAX       SnmpAdminString
    MAX-ACCESS   read-only
    STATUS       current
    DESCRIPTION
        "Cisco Firepower fabric:FcoeSanEp:rn managed object property"
    ::= { cfprFabricFcoeSanEpEntry 3 }

cfprFabricFcoeSanEpAdminState OBJECT-TYPE
    SYNTAX       CfprFabricExternalEpAdminState
    MAX-ACCESS   read-only
    STATUS       current
    DESCRIPTION
        "Cisco Firepower fabric:FcoeSanEp:adminState managed
        object property"
    ::= { cfprFabricFcoeSanEpEntry 4 }

cfprFabricFcoeSanEpAggrPortId OBJECT-TYPE
    SYNTAX       Gauge32
    MAX-ACCESS   read-only
    STATUS       current
    DESCRIPTION
        "Cisco Firepower fabric:FcoeSanEp:aggrPortId managed
        object property"
    ::= { cfprFabricFcoeSanEpEntry 5 }

cfprFabricFcoeSanEpChassisId OBJECT-TYPE
    SYNTAX       Gauge32
    MAX-ACCESS   read-only
    STATUS       current
    DESCRIPTION
        "Cisco Firepower fabric:FcoeSanEp:chassisId managed
        object property"
    ::= { cfprFabricFcoeSanEpEntry 6 }

cfprFabricFcoeSanEpConfigState OBJECT-TYPE
    SYNTAX       CfprFabricConfigState
    MAX-ACCESS   read-only
    STATUS       current
    DESCRIPTION
        "Cisco Firepower fabric:FcoeSanEp:configState managed
        object property"
    ::= { cfprFabricFcoeSanEpEntry 7 }

cfprFabricFcoeSanEpEpDn OBJECT-TYPE
    SYNTAX       SnmpAdminString
    MAX-ACCESS   read-only
    STATUS       current
    DESCRIPTION
        "Cisco Firepower fabric:FcoeSanEp:epDn managed object property"
    ::= { cfprFabricFcoeSanEpEntry 8 }

cfprFabricFcoeSanEpEthLinkProfileName OBJECT-TYPE
    SYNTAX       SnmpAdminString
    MAX-ACCESS   read-only
    STATUS       current
    DESCRIPTION
        "Cisco Firepower fabric:FcoeSanEp:ethLinkProfileName
        managed object property"
    ::= { cfprFabricFcoeSanEpEntry 9 }

cfprFabricFcoeSanEpFcoeState OBJECT-TYPE
    SYNTAX       CfprNetworkPortOperState
    MAX-ACCESS   read-only
    STATUS       current
    DESCRIPTION
        "Cisco Firepower fabric:FcoeSanEp:fcoeState managed
        object property"
    ::= { cfprFabricFcoeSanEpEntry 10 }

cfprFabricFcoeSanEpFcoeStateReason OBJECT-TYPE
    SYNTAX       SnmpAdminString
    MAX-ACCESS   read-only
    STATUS       current
    DESCRIPTION
        "Cisco Firepower fabric:FcoeSanEp:fcoeStateReason
        managed object property"
    ::= { cfprFabricFcoeSanEpEntry 11 }

cfprFabricFcoeSanEpFltAggr OBJECT-TYPE
    SYNTAX       Unsigned64
    MAX-ACCESS   read-only
    STATUS       current
    DESCRIPTION
        "Cisco Firepower fabric:FcoeSanEp:fltAggr managed object property"
    ::= { cfprFabricFcoeSanEpEntry 12 }

cfprFabricFcoeSanEpIfRole OBJECT-TYPE
    SYNTAX       CfprFabricSanEpIfRole
    MAX-ACCESS   read-only
    STATUS       current
    DESCRIPTION
        "Cisco Firepower fabric:FcoeSanEp:ifRole managed object property"
    ::= { cfprFabricFcoeSanEpEntry 13 }

cfprFabricFcoeSanEpIfType OBJECT-TYPE
    SYNTAX       CfprFabricPIoEpIfType
    MAX-ACCESS   read-only
    STATUS       current
    DESCRIPTION
        "Cisco Firepower fabric:FcoeSanEp:ifType managed object property"
    ::= { cfprFabricFcoeSanEpEntry 14 }

cfprFabricFcoeSanEpLicGP OBJECT-TYPE
    SYNTAX       Unsigned64
    MAX-ACCESS   read-only
    STATUS       current
    DESCRIPTION
        "Cisco Firepower fabric:FcoeSanEp:licGP managed object property"
    ::= { cfprFabricFcoeSanEpEntry 15 }

cfprFabricFcoeSanEpLicState OBJECT-TYPE
    SYNTAX       CfprLicenseState
    MAX-ACCESS   read-only
    STATUS       current
    DESCRIPTION
        "Cisco Firepower fabric:FcoeSanEp:licState managed
        object property"
    ::= { cfprFabricFcoeSanEpEntry 16 }

cfprFabricFcoeSanEpLocale OBJECT-TYPE
    SYNTAX       CfprFabricExternalEpLocale
    MAX-ACCESS   read-only
    STATUS       current
    DESCRIPTION
        "Cisco Firepower fabric:FcoeSanEp:locale managed object property"
    ::= { cfprFabricFcoeSanEpEntry 17 }

cfprFabricFcoeSanEpName OBJECT-TYPE
    SYNTAX       SnmpAdminString
    MAX-ACCESS   read-only
    STATUS       current
    DESCRIPTION
        "Cisco Firepower fabric:FcoeSanEp:name managed object property"
    ::= { cfprFabricFcoeSanEpEntry 18 }

cfprFabricFcoeSanEpOperEthLinkProfileName OBJECT-TYPE
    SYNTAX       SnmpAdminString
    MAX-ACCESS   read-only
    STATUS       current
    DESCRIPTION
        "Cisco Firepower fabric:FcoeSanEp:operEthLinkProfileName
        managed object property"
    ::= { cfprFabricFcoeSanEpEntry 19 }

cfprFabricFcoeSanEpOperState OBJECT-TYPE
    SYNTAX       CfprFabricPIoEpOperState
    MAX-ACCESS   read-only
    STATUS       current
    DESCRIPTION
        "Cisco Firepower fabric:FcoeSanEp:operState managed
        object property"
    ::= { cfprFabricFcoeSanEpEntry 20 }

cfprFabricFcoeSanEpOperStateReason OBJECT-TYPE
    SYNTAX       SnmpAdminString
    MAX-ACCESS   read-only
    STATUS       current
    DESCRIPTION
        "Cisco Firepower fabric:FcoeSanEp:operStateReason
        managed object property"
    ::= { cfprFabricFcoeSanEpEntry 21 }

cfprFabricFcoeSanEpPeerAggrPortId OBJECT-TYPE
    SYNTAX       Gauge32
    MAX-ACCESS   read-only
    STATUS       current
    DESCRIPTION
        "Cisco Firepower fabric:FcoeSanEp:peerAggrPortId
        managed object property"
    ::= { cfprFabricFcoeSanEpEntry 22 }

cfprFabricFcoeSanEpPeerChassisId OBJECT-TYPE
    SYNTAX       Gauge32
    MAX-ACCESS   read-only
    STATUS       current
    DESCRIPTION
        "Cisco Firepower fabric:FcoeSanEp:peerChassisId
        managed object property"
    ::= { cfprFabricFcoeSanEpEntry 23 }

cfprFabricFcoeSanEpPeerDn OBJECT-TYPE
    SYNTAX       SnmpAdminString
    MAX-ACCESS   read-only
    STATUS       current
    DESCRIPTION
        "Cisco Firepower fabric:FcoeSanEp:peerDn managed object property"
    ::= { cfprFabricFcoeSanEpEntry 24 }

cfprFabricFcoeSanEpPeerPortId OBJECT-TYPE
    SYNTAX       Gauge32
    MAX-ACCESS   read-only
    STATUS       current
    DESCRIPTION
        "Cisco Firepower fabric:FcoeSanEp:peerPortId managed
        object property"
    ::= { cfprFabricFcoeSanEpEntry 25 }

cfprFabricFcoeSanEpPeerSlotId OBJECT-TYPE
    SYNTAX       Gauge32
    MAX-ACCESS   read-only
    STATUS       current
    DESCRIPTION
        "Cisco Firepower fabric:FcoeSanEp:peerSlotId managed
        object property"
    ::= { cfprFabricFcoeSanEpEntry 26 }

cfprFabricFcoeSanEpPortId OBJECT-TYPE
    SYNTAX       CfprFabricFcoeSanEpPortId
    MAX-ACCESS   read-only
    STATUS       current
    DESCRIPTION
        "Cisco Firepower fabric:FcoeSanEp:portId managed object property"
    ::= { cfprFabricFcoeSanEpEntry 27 }

cfprFabricFcoeSanEpSlotId OBJECT-TYPE
    SYNTAX       CfprFabricFcoeSanEpSlotId
    MAX-ACCESS   read-only
    STATUS       current
    DESCRIPTION
        "Cisco Firepower fabric:FcoeSanEp:slotId managed object property"
    ::= { cfprFabricFcoeSanEpEntry 28 }

cfprFabricFcoeSanEpSwitchId OBJECT-TYPE
    SYNTAX       CfprNetworkSwitchId
    MAX-ACCESS   read-only
    STATUS       current
    DESCRIPTION
        "Cisco Firepower fabric:FcoeSanEp:switchId managed
        object property"
    ::= { cfprFabricFcoeSanEpEntry 29 }

cfprFabricFcoeSanEpTransport OBJECT-TYPE
    SYNTAX       CfprFabricAFcoeSanEpTransport
    MAX-ACCESS   read-only
    STATUS       current
    DESCRIPTION
        "Cisco Firepower fabric:FcoeSanEp:transport managed
        object property"
    ::= { cfprFabricFcoeSanEpEntry 30 }

cfprFabricFcoeSanEpType OBJECT-TYPE
    SYNTAX       CfprFabricSanEpType
    MAX-ACCESS   read-only
    STATUS       current
    DESCRIPTION
        "Cisco Firepower fabric:FcoeSanEp:type managed object property"
    ::= { cfprFabricFcoeSanEpEntry 31 }

cfprFabricFcoeSanEpUdldOperState OBJECT-TYPE
    SYNTAX       CfprFabricUdldOperState
    MAX-ACCESS   read-only
    STATUS       current
    DESCRIPTION
        "Cisco Firepower fabric:FcoeSanEp:udldOperState
        managed object property"
    ::= { cfprFabricFcoeSanEpEntry 32 }

cfprFabricFcoeSanEpUsrLbl OBJECT-TYPE
    SYNTAX       SnmpAdminString
    MAX-ACCESS   read-only
    STATUS       current
    DESCRIPTION
        "Cisco Firepower fabric:FcoeSanEp:usrLbl managed object property"
    ::= { cfprFabricFcoeSanEpEntry 33 }

cfprFabricFcoeSanEpWarnings OBJECT-TYPE
    SYNTAX       CfprFabricWarnings
    MAX-ACCESS   read-only
    STATUS       current
    DESCRIPTION
        "Cisco Firepower fabric:FcoeSanEp:warnings managed
        object property"
    ::= { cfprFabricFcoeSanEpEntry 34 }

cfprFabricFcoeSanPcTable OBJECT-TYPE
    SYNTAX           SEQUENCE OF CfprFabricFcoeSanPcEntry
    MAX-ACCESS       not-accessible
    STATUS           current
    DESCRIPTION
        "Cisco Firepower fabric:FcoeSanPc managed object table"
    ::= { cfprFabricObjects 63 }

cfprFabricFcoeSanPcEntry OBJECT-TYPE
    SYNTAX           CfprFabricFcoeSanPcEntry
    MAX-ACCESS       not-accessible
    STATUS           current
    DESCRIPTION
        "Entry for the cfprFabricFcoeSanPcTable table."
    INDEX { cfprFabricFcoeSanPcInstanceId }
    ::= { cfprFabricFcoeSanPcTable 1 }

CfprFabricFcoeSanPcEntry ::= SEQUENCE {
    cfprFabricFcoeSanPcInstanceId                                    CfprManagedObjectId,
    cfprFabricFcoeSanPcDn                                            CfprManagedObjectDn,
    cfprFabricFcoeSanPcRn                                            SnmpAdminString,
    cfprFabricFcoeSanPcAdminState                                    CfprFabricCIoEpAdminState,
    cfprFabricFcoeSanPcConfigState                                   CfprFabricConfigState,
    cfprFabricFcoeSanPcDescr                                         SnmpAdminString,
    cfprFabricFcoeSanPcEpDn                                          SnmpAdminString,
    cfprFabricFcoeSanPcFcoeState                                     CfprNetworkPortOperState,
    cfprFabricFcoeSanPcFcoeStateReason                               SnmpAdminString,
    cfprFabricFcoeSanPcFltAggr                                       Unsigned64,
    cfprFabricFcoeSanPcIfRole                                        CfprFabricSanPcIfRole,
    cfprFabricFcoeSanPcIfType                                        CfprFabricCIoEpIfType,
    cfprFabricFcoeSanPcLacpPolicyName                                SnmpAdminString,
    cfprFabricFcoeSanPcLocale                                        CfprFabricExternalPcLocale,
    cfprFabricFcoeSanPcName                                          SnmpAdminString,
    cfprFabricFcoeSanPcOperLacpPolicyName                            SnmpAdminString,
    cfprFabricFcoeSanPcOperState                                     CfprNetworkPortOperState,
    cfprFabricFcoeSanPcPeerDn                                        SnmpAdminString,
    cfprFabricFcoeSanPcPortId                                        Gauge32,
    cfprFabricFcoeSanPcStateQual                                     SnmpAdminString,
    cfprFabricFcoeSanPcSwitchId                                      CfprNetworkSwitchId,
    cfprFabricFcoeSanPcTransport                                     CfprFabricFcoeSanPcTransport,
    cfprFabricFcoeSanPcType                                          CfprFabricSanPcType,
    cfprFabricFcoeSanPcWarnings                                      CfprFabricWarnings
}

cfprFabricFcoeSanPcInstanceId OBJECT-TYPE
    SYNTAX       CfprManagedObjectId
    MAX-ACCESS   not-accessible
    STATUS       current
    DESCRIPTION
        "Instance identifier of the managed object."
    ::= { cfprFabricFcoeSanPcEntry 1 }

cfprFabricFcoeSanPcDn OBJECT-TYPE
    SYNTAX       CfprManagedObjectDn
    MAX-ACCESS   read-only
    STATUS       current
    DESCRIPTION
        "Cisco Firepower fabric:FcoeSanPc:dn managed object property"
    ::= { cfprFabricFcoeSanPcEntry 2 }

cfprFabricFcoeSanPcRn OBJECT-TYPE
    SYNTAX       SnmpAdminString
    MAX-ACCESS   read-only
    STATUS       current
    DESCRIPTION
        "Cisco Firepower fabric:FcoeSanPc:rn managed object property"
    ::= { cfprFabricFcoeSanPcEntry 3 }

cfprFabricFcoeSanPcAdminState OBJECT-TYPE
    SYNTAX       CfprFabricCIoEpAdminState
    MAX-ACCESS   read-only
    STATUS       current
    DESCRIPTION
        "Cisco Firepower fabric:FcoeSanPc:adminState managed
        object property"
    ::= { cfprFabricFcoeSanPcEntry 4 }

cfprFabricFcoeSanPcConfigState OBJECT-TYPE
    SYNTAX       CfprFabricConfigState
    MAX-ACCESS   read-only
    STATUS       current
    DESCRIPTION
        "Cisco Firepower fabric:FcoeSanPc:configState managed
        object property"
    ::= { cfprFabricFcoeSanPcEntry 5 }

cfprFabricFcoeSanPcDescr OBJECT-TYPE
    SYNTAX       SnmpAdminString
    MAX-ACCESS   read-only
    STATUS       current
    DESCRIPTION
        "Cisco Firepower fabric:FcoeSanPc:descr managed object property"
    ::= { cfprFabricFcoeSanPcEntry 6 }

cfprFabricFcoeSanPcEpDn OBJECT-TYPE
    SYNTAX       SnmpAdminString
    MAX-ACCESS   read-only
    STATUS       current
    DESCRIPTION
        "Cisco Firepower fabric:FcoeSanPc:epDn managed object property"
    ::= { cfprFabricFcoeSanPcEntry 7 }

cfprFabricFcoeSanPcFcoeState OBJECT-TYPE
    SYNTAX       CfprNetworkPortOperState
    MAX-ACCESS   read-only
    STATUS       current
    DESCRIPTION
        "Cisco Firepower fabric:FcoeSanPc:fcoeState managed
        object property"
    ::= { cfprFabricFcoeSanPcEntry 8 }

cfprFabricFcoeSanPcFcoeStateReason OBJECT-TYPE
    SYNTAX       SnmpAdminString
    MAX-ACCESS   read-only
    STATUS       current
    DESCRIPTION
        "Cisco Firepower fabric:FcoeSanPc:fcoeStateReason
        managed object property"
    ::= { cfprFabricFcoeSanPcEntry 9 }

cfprFabricFcoeSanPcFltAggr OBJECT-TYPE
    SYNTAX       Unsigned64
    MAX-ACCESS   read-only
    STATUS       current
    DESCRIPTION
        "Cisco Firepower fabric:FcoeSanPc:fltAggr managed object property"
    ::= { cfprFabricFcoeSanPcEntry 10 }

cfprFabricFcoeSanPcIfRole OBJECT-TYPE
    SYNTAX       CfprFabricSanPcIfRole
    MAX-ACCESS   read-only
    STATUS       current
    DESCRIPTION
        "Cisco Firepower fabric:FcoeSanPc:ifRole managed object property"
    ::= { cfprFabricFcoeSanPcEntry 11 }

cfprFabricFcoeSanPcIfType OBJECT-TYPE
    SYNTAX       CfprFabricCIoEpIfType
    MAX-ACCESS   read-only
    STATUS       current
    DESCRIPTION
        "Cisco Firepower fabric:FcoeSanPc:ifType managed object property"
    ::= { cfprFabricFcoeSanPcEntry 12 }

cfprFabricFcoeSanPcLacpPolicyName OBJECT-TYPE
    SYNTAX       SnmpAdminString
    MAX-ACCESS   read-only
    STATUS       current
    DESCRIPTION
        "Cisco Firepower fabric:FcoeSanPc:lacpPolicyName
        managed object property"
    ::= { cfprFabricFcoeSanPcEntry 13 }

cfprFabricFcoeSanPcLocale OBJECT-TYPE
    SYNTAX       CfprFabricExternalPcLocale
    MAX-ACCESS   read-only
    STATUS       current
    DESCRIPTION
        "Cisco Firepower fabric:FcoeSanPc:locale managed object property"
    ::= { cfprFabricFcoeSanPcEntry 14 }

cfprFabricFcoeSanPcName OBJECT-TYPE
    SYNTAX       SnmpAdminString
    MAX-ACCESS   read-only
    STATUS       current
    DESCRIPTION
        "Cisco Firepower fabric:FcoeSanPc:name managed object property"
    ::= { cfprFabricFcoeSanPcEntry 15 }

cfprFabricFcoeSanPcOperLacpPolicyName OBJECT-TYPE
    SYNTAX       SnmpAdminString
    MAX-ACCESS   read-only
    STATUS       current
    DESCRIPTION
        "Cisco Firepower fabric:FcoeSanPc:operLacpPolicyName
        managed object property"
    ::= { cfprFabricFcoeSanPcEntry 16 }

cfprFabricFcoeSanPcOperState OBJECT-TYPE
    SYNTAX       CfprNetworkPortOperState
    MAX-ACCESS   read-only
    STATUS       current
    DESCRIPTION
        "Cisco Firepower fabric:FcoeSanPc:operState managed
        object property"
    ::= { cfprFabricFcoeSanPcEntry 17 }

cfprFabricFcoeSanPcPeerDn OBJECT-TYPE
    SYNTAX       SnmpAdminString
    MAX-ACCESS   read-only
    STATUS       current
    DESCRIPTION
        "Cisco Firepower fabric:FcoeSanPc:peerDn managed object property"
    ::= { cfprFabricFcoeSanPcEntry 18 }

cfprFabricFcoeSanPcPortId OBJECT-TYPE
    SYNTAX       Gauge32
    MAX-ACCESS   read-only
    STATUS       current
    DESCRIPTION
        "Cisco Firepower fabric:FcoeSanPc:portId managed object property"
    ::= { cfprFabricFcoeSanPcEntry 19 }

cfprFabricFcoeSanPcStateQual OBJECT-TYPE
    SYNTAX       SnmpAdminString
    MAX-ACCESS   read-only
    STATUS       current
    DESCRIPTION
        "Cisco Firepower fabric:FcoeSanPc:stateQual managed
        object property"
    ::= { cfprFabricFcoeSanPcEntry 20 }

cfprFabricFcoeSanPcSwitchId OBJECT-TYPE
    SYNTAX       CfprNetworkSwitchId
    MAX-ACCESS   read-only
    STATUS       current
    DESCRIPTION
        "Cisco Firepower fabric:FcoeSanPc:switchId managed
        object property"
    ::= { cfprFabricFcoeSanPcEntry 21 }

cfprFabricFcoeSanPcTransport OBJECT-TYPE
    SYNTAX       CfprFabricFcoeSanPcTransport
    MAX-ACCESS   read-only
    STATUS       current
    DESCRIPTION
        "Cisco Firepower fabric:FcoeSanPc:transport managed
        object property"
    ::= { cfprFabricFcoeSanPcEntry 22 }

cfprFabricFcoeSanPcType OBJECT-TYPE
    SYNTAX       CfprFabricSanPcType
    MAX-ACCESS   read-only
    STATUS       current
    DESCRIPTION
        "Cisco Firepower fabric:FcoeSanPc:type managed object property"
    ::= { cfprFabricFcoeSanPcEntry 23 }

cfprFabricFcoeSanPcWarnings OBJECT-TYPE
    SYNTAX       CfprFabricWarnings
    MAX-ACCESS   read-only
    STATUS       current
    DESCRIPTION
        "Cisco Firepower fabric:FcoeSanPc:warnings managed
        object property"
    ::= { cfprFabricFcoeSanPcEntry 24 }

cfprFabricFcoeSanPcEpTable OBJECT-TYPE
    SYNTAX           SEQUENCE OF CfprFabricFcoeSanPcEpEntry
    MAX-ACCESS       not-accessible
    STATUS           current
    DESCRIPTION
        "Cisco Firepower fabric:FcoeSanPcEp managed object table"
    ::= { cfprFabricObjects 64 }

cfprFabricFcoeSanPcEpEntry OBJECT-TYPE
    SYNTAX           CfprFabricFcoeSanPcEpEntry
    MAX-ACCESS       not-accessible
    STATUS           current
    DESCRIPTION
        "Entry for the cfprFabricFcoeSanPcEpTable table."
    INDEX { cfprFabricFcoeSanPcEpInstanceId }
    ::= { cfprFabricFcoeSanPcEpTable 1 }

CfprFabricFcoeSanPcEpEntry ::= SEQUENCE {
    cfprFabricFcoeSanPcEpInstanceId                                  CfprManagedObjectId,
    cfprFabricFcoeSanPcEpDnData                                      CfprManagedObjectDn,
    cfprFabricFcoeSanPcEpRn                                          SnmpAdminString,
    cfprFabricFcoeSanPcEpAdminState                                  CfprFabricExternalEpAdminState,
    cfprFabricFcoeSanPcEpAggrPortId                                  Gauge32,
    cfprFabricFcoeSanPcEpChassisId                                   Gauge32,
    cfprFabricFcoeSanPcEpEpDn                                        SnmpAdminString,
    cfprFabricFcoeSanPcEpEthLinkProfileName                          SnmpAdminString,
    cfprFabricFcoeSanPcEpFltAggr                                     Unsigned64,
    cfprFabricFcoeSanPcEpIfRole                                      CfprFabricSanEpIfRole,
    cfprFabricFcoeSanPcEpIfType                                      CfprFabricPIoEpIfType,
    cfprFabricFcoeSanPcEpLicGP                                       Unsigned64,
    cfprFabricFcoeSanPcEpLicState                                    CfprLicenseState,
    cfprFabricFcoeSanPcEpLocale                                      CfprFabricExternalEpLocale,
    cfprFabricFcoeSanPcEpMembership                                  CfprFabricMembershipStatus,
    cfprFabricFcoeSanPcEpName                                        SnmpAdminString,
    cfprFabricFcoeSanPcEpOperEthLinkProfileName                      SnmpAdminString,
    cfprFabricFcoeSanPcEpOperState                                   CfprFabricPIoEpOperState,
    cfprFabricFcoeSanPcEpOperStateReason                             SnmpAdminString,
    cfprFabricFcoeSanPcEpPeerAggrPortId                              Gauge32,
    cfprFabricFcoeSanPcEpPeerChassisId                               Gauge32,
    cfprFabricFcoeSanPcEpPeerDn                                      SnmpAdminString,
    cfprFabricFcoeSanPcEpPeerPortId                                  Gauge32,
    cfprFabricFcoeSanPcEpPeerSlotId                                  Gauge32,
    cfprFabricFcoeSanPcEpPortId                                      CfprFabricFcoeSanPcEpPortId,
    cfprFabricFcoeSanPcEpSlotId                                      CfprFabricFcoeSanPcEpSlotId,
    cfprFabricFcoeSanPcEpSwitchId                                    CfprNetworkSwitchId,
    cfprFabricFcoeSanPcEpTransport                                   CfprFabricAFcoeSanEpTransport,
    cfprFabricFcoeSanPcEpType                                        CfprFabricSanEpType,
    cfprFabricFcoeSanPcEpUdldOperState                               CfprFabricUdldOperState,
    cfprFabricFcoeSanPcEpWarnings                                    CfprFabricWarnings
}

cfprFabricFcoeSanPcEpInstanceId OBJECT-TYPE
    SYNTAX       CfprManagedObjectId
    MAX-ACCESS   not-accessible
    STATUS       current
    DESCRIPTION
        "Instance identifier of the managed object."
    ::= { cfprFabricFcoeSanPcEpEntry 1 }

cfprFabricFcoeSanPcEpDnData OBJECT-TYPE
    SYNTAX       CfprManagedObjectDn
    MAX-ACCESS   read-only
    STATUS       current
    DESCRIPTION
        "Cisco Firepower fabric:FcoeSanPcEp:dn managed object property"
    ::= { cfprFabricFcoeSanPcEpEntry 2 }

cfprFabricFcoeSanPcEpRn OBJECT-TYPE
    SYNTAX       SnmpAdminString
    MAX-ACCESS   read-only
    STATUS       current
    DESCRIPTION
        "Cisco Firepower fabric:FcoeSanPcEp:rn managed object property"
    ::= { cfprFabricFcoeSanPcEpEntry 3 }

cfprFabricFcoeSanPcEpAdminState OBJECT-TYPE
    SYNTAX       CfprFabricExternalEpAdminState
    MAX-ACCESS   read-only
    STATUS       current
    DESCRIPTION
        "Cisco Firepower fabric:FcoeSanPcEp:adminState
        managed object property"
    ::= { cfprFabricFcoeSanPcEpEntry 4 }

cfprFabricFcoeSanPcEpAggrPortId OBJECT-TYPE
    SYNTAX       Gauge32
    MAX-ACCESS   read-only
    STATUS       current
    DESCRIPTION
        "Cisco Firepower fabric:FcoeSanPcEp:aggrPortId
        managed object property"
    ::= { cfprFabricFcoeSanPcEpEntry 5 }

cfprFabricFcoeSanPcEpChassisId OBJECT-TYPE
    SYNTAX       Gauge32
    MAX-ACCESS   read-only
    STATUS       current
    DESCRIPTION
        "Cisco Firepower fabric:FcoeSanPcEp:chassisId managed
        object property"
    ::= { cfprFabricFcoeSanPcEpEntry 6 }

cfprFabricFcoeSanPcEpEpDn OBJECT-TYPE
    SYNTAX       SnmpAdminString
    MAX-ACCESS   read-only
    STATUS       current
    DESCRIPTION
        "Cisco Firepower fabric:FcoeSanPcEp:epDn managed object property"
    ::= { cfprFabricFcoeSanPcEpEntry 7 }

cfprFabricFcoeSanPcEpEthLinkProfileName OBJECT-TYPE
    SYNTAX       SnmpAdminString
    MAX-ACCESS   read-only
    STATUS       current
    DESCRIPTION
        "Cisco Firepower fabric:FcoeSanPcEp:ethLinkProfileName
        managed object property"
    ::= { cfprFabricFcoeSanPcEpEntry 8 }

cfprFabricFcoeSanPcEpFltAggr OBJECT-TYPE
    SYNTAX       Unsigned64
    MAX-ACCESS   read-only
    STATUS       current
    DESCRIPTION
        "Cisco Firepower fabric:FcoeSanPcEp:fltAggr managed
        object property"
    ::= { cfprFabricFcoeSanPcEpEntry 9 }

cfprFabricFcoeSanPcEpIfRole OBJECT-TYPE
    SYNTAX       CfprFabricSanEpIfRole
    MAX-ACCESS   read-only
    STATUS       current
    DESCRIPTION
        "Cisco Firepower fabric:FcoeSanPcEp:ifRole managed
        object property"
    ::= { cfprFabricFcoeSanPcEpEntry 10 }

cfprFabricFcoeSanPcEpIfType OBJECT-TYPE
    SYNTAX       CfprFabricPIoEpIfType
    MAX-ACCESS   read-only
    STATUS       current
    DESCRIPTION
        "Cisco Firepower fabric:FcoeSanPcEp:ifType managed
        object property"
    ::= { cfprFabricFcoeSanPcEpEntry 11 }

cfprFabricFcoeSanPcEpLicGP OBJECT-TYPE
    SYNTAX       Unsigned64
    MAX-ACCESS   read-only
    STATUS       current
    DESCRIPTION
        "Cisco Firepower fabric:FcoeSanPcEp:licGP managed object property"
    ::= { cfprFabricFcoeSanPcEpEntry 12 }

cfprFabricFcoeSanPcEpLicState OBJECT-TYPE
    SYNTAX       CfprLicenseState
    MAX-ACCESS   read-only
    STATUS       current
    DESCRIPTION
        "Cisco Firepower fabric:FcoeSanPcEp:licState managed
        object property"
    ::= { cfprFabricFcoeSanPcEpEntry 13 }

cfprFabricFcoeSanPcEpLocale OBJECT-TYPE
    SYNTAX       CfprFabricExternalEpLocale
    MAX-ACCESS   read-only
    STATUS       current
    DESCRIPTION
        "Cisco Firepower fabric:FcoeSanPcEp:locale managed
        object property"
    ::= { cfprFabricFcoeSanPcEpEntry 14 }

cfprFabricFcoeSanPcEpMembership OBJECT-TYPE
    SYNTAX       CfprFabricMembershipStatus
    MAX-ACCESS   read-only
    STATUS       current
    DESCRIPTION
        "Cisco Firepower fabric:FcoeSanPcEp:membership
        managed object property"
    ::= { cfprFabricFcoeSanPcEpEntry 15 }

cfprFabricFcoeSanPcEpName OBJECT-TYPE
    SYNTAX       SnmpAdminString
    MAX-ACCESS   read-only
    STATUS       current
    DESCRIPTION
        "Cisco Firepower fabric:FcoeSanPcEp:name managed object property"
    ::= { cfprFabricFcoeSanPcEpEntry 16 }

cfprFabricFcoeSanPcEpOperEthLinkProfileName OBJECT-TYPE
    SYNTAX       SnmpAdminString
    MAX-ACCESS   read-only
    STATUS       current
    DESCRIPTION
        "Cisco Firepower fabric:FcoeSanPcEp:operEthLinkProfileName
        managed object property"
    ::= { cfprFabricFcoeSanPcEpEntry 17 }

cfprFabricFcoeSanPcEpOperState OBJECT-TYPE
    SYNTAX       CfprFabricPIoEpOperState
    MAX-ACCESS   read-only
    STATUS       current
    DESCRIPTION
        "Cisco Firepower fabric:FcoeSanPcEp:operState managed
        object property"
    ::= { cfprFabricFcoeSanPcEpEntry 18 }

cfprFabricFcoeSanPcEpOperStateReason OBJECT-TYPE
    SYNTAX       SnmpAdminString
    MAX-ACCESS   read-only
    STATUS       current
    DESCRIPTION
        "Cisco Firepower fabric:FcoeSanPcEp:operStateReason
        managed object property"
    ::= { cfprFabricFcoeSanPcEpEntry 19 }

cfprFabricFcoeSanPcEpPeerAggrPortId OBJECT-TYPE
    SYNTAX       Gauge32
    MAX-ACCESS   read-only
    STATUS       current
    DESCRIPTION
        "Cisco Firepower fabric:FcoeSanPcEp:peerAggrPortId
        managed object property"
    ::= { cfprFabricFcoeSanPcEpEntry 20 }

cfprFabricFcoeSanPcEpPeerChassisId OBJECT-TYPE
    SYNTAX       Gauge32
    MAX-ACCESS   read-only
    STATUS       current
    DESCRIPTION
        "Cisco Firepower fabric:FcoeSanPcEp:peerChassisId
        managed object property"
    ::= { cfprFabricFcoeSanPcEpEntry 21 }

cfprFabricFcoeSanPcEpPeerDn OBJECT-TYPE
    SYNTAX       SnmpAdminString
    MAX-ACCESS   read-only
    STATUS       current
    DESCRIPTION
        "Cisco Firepower fabric:FcoeSanPcEp:peerDn managed
        object property"
    ::= { cfprFabricFcoeSanPcEpEntry 22 }

cfprFabricFcoeSanPcEpPeerPortId OBJECT-TYPE
    SYNTAX       Gauge32
    MAX-ACCESS   read-only
    STATUS       current
    DESCRIPTION
        "Cisco Firepower fabric:FcoeSanPcEp:peerPortId
        managed object property"
    ::= { cfprFabricFcoeSanPcEpEntry 23 }

cfprFabricFcoeSanPcEpPeerSlotId OBJECT-TYPE
    SYNTAX       Gauge32
    MAX-ACCESS   read-only
    STATUS       current
    DESCRIPTION
        "Cisco Firepower fabric:FcoeSanPcEp:peerSlotId
        managed object property"
    ::= { cfprFabricFcoeSanPcEpEntry 24 }

cfprFabricFcoeSanPcEpPortId OBJECT-TYPE
    SYNTAX       CfprFabricFcoeSanPcEpPortId
    MAX-ACCESS   read-only
    STATUS       current
    DESCRIPTION
        "Cisco Firepower fabric:FcoeSanPcEp:portId managed
        object property"
    ::= { cfprFabricFcoeSanPcEpEntry 25 }

cfprFabricFcoeSanPcEpSlotId OBJECT-TYPE
    SYNTAX       CfprFabricFcoeSanPcEpSlotId
    MAX-ACCESS   read-only
    STATUS       current
    DESCRIPTION
        "Cisco Firepower fabric:FcoeSanPcEp:slotId managed
        object property"
    ::= { cfprFabricFcoeSanPcEpEntry 26 }

cfprFabricFcoeSanPcEpSwitchId OBJECT-TYPE
    SYNTAX       CfprNetworkSwitchId
    MAX-ACCESS   read-only
    STATUS       current
    DESCRIPTION
        "Cisco Firepower fabric:FcoeSanPcEp:switchId managed
        object property"
    ::= { cfprFabricFcoeSanPcEpEntry 27 }

cfprFabricFcoeSanPcEpTransport OBJECT-TYPE
    SYNTAX       CfprFabricAFcoeSanEpTransport
    MAX-ACCESS   read-only
    STATUS       current
    DESCRIPTION
        "Cisco Firepower fabric:FcoeSanPcEp:transport managed
        object property"
    ::= { cfprFabricFcoeSanPcEpEntry 28 }

cfprFabricFcoeSanPcEpType OBJECT-TYPE
    SYNTAX       CfprFabricSanEpType
    MAX-ACCESS   read-only
    STATUS       current
    DESCRIPTION
        "Cisco Firepower fabric:FcoeSanPcEp:type managed object property"
    ::= { cfprFabricFcoeSanPcEpEntry 29 }

cfprFabricFcoeSanPcEpUdldOperState OBJECT-TYPE
    SYNTAX       CfprFabricUdldOperState
    MAX-ACCESS   read-only
    STATUS       current
    DESCRIPTION
        "Cisco Firepower fabric:FcoeSanPcEp:udldOperState
        managed object property"
    ::= { cfprFabricFcoeSanPcEpEntry 30 }

cfprFabricFcoeSanPcEpWarnings OBJECT-TYPE
    SYNTAX       CfprFabricWarnings
    MAX-ACCESS   read-only
    STATUS       current
    DESCRIPTION
        "Cisco Firepower fabric:FcoeSanPcEp:warnings managed
        object property"
    ::= { cfprFabricFcoeSanPcEpEntry 31 }

cfprFabricFcoeVsanPcTable OBJECT-TYPE
    SYNTAX           SEQUENCE OF CfprFabricFcoeVsanPcEntry
    MAX-ACCESS       not-accessible
    STATUS           current
    DESCRIPTION
        "Cisco Firepower fabric:FcoeVsanPc managed object table"
    ::= { cfprFabricObjects 65 }

cfprFabricFcoeVsanPcEntry OBJECT-TYPE
    SYNTAX           CfprFabricFcoeVsanPcEntry
    MAX-ACCESS       not-accessible
    STATUS           current
    DESCRIPTION
        "Entry for the cfprFabricFcoeVsanPcTable table."
    INDEX { cfprFabricFcoeVsanPcInstanceId }
    ::= { cfprFabricFcoeVsanPcTable 1 }

CfprFabricFcoeVsanPcEntry ::= SEQUENCE {
    cfprFabricFcoeVsanPcInstanceId                                   CfprManagedObjectId,
    cfprFabricFcoeVsanPcDn                                           CfprManagedObjectDn,
    cfprFabricFcoeVsanPcRn                                           SnmpAdminString,
    cfprFabricFcoeVsanPcAdminState                                   CfprFabricCIoEpAdminState,
    cfprFabricFcoeVsanPcDescr                                        SnmpAdminString,
    cfprFabricFcoeVsanPcEpDn                                         SnmpAdminString,
    cfprFabricFcoeVsanPcFltAggr                                      Unsigned64,
    cfprFabricFcoeVsanPcIfRole                                       CfprFabricSanPcIfRole,
    cfprFabricFcoeVsanPcIfType                                       CfprFabricCIoEpIfType,
    cfprFabricFcoeVsanPcLocale                                       CfprFabricExternalPcLocale,
    cfprFabricFcoeVsanPcName                                         SnmpAdminString,
    cfprFabricFcoeVsanPcOperState                                    CfprNetworkPortOperState,
    cfprFabricFcoeVsanPcPeerDn                                       SnmpAdminString,
    cfprFabricFcoeVsanPcPortId                                       Gauge32,
    cfprFabricFcoeVsanPcStateQual                                    SnmpAdminString,
    cfprFabricFcoeVsanPcSwitchId                                     CfprNetworkSwitchId,
    cfprFabricFcoeVsanPcTransport                                    CfprFabricFcoeVsanPcTransport,
    cfprFabricFcoeVsanPcType                                         CfprFabricSanPcType,
    cfprFabricFcoeVsanPcWarnings                                     CfprFabricWarnings
}

cfprFabricFcoeVsanPcInstanceId OBJECT-TYPE
    SYNTAX       CfprManagedObjectId
    MAX-ACCESS   not-accessible
    STATUS       current
    DESCRIPTION
        "Instance identifier of the managed object."
    ::= { cfprFabricFcoeVsanPcEntry 1 }

cfprFabricFcoeVsanPcDn OBJECT-TYPE
    SYNTAX       CfprManagedObjectDn
    MAX-ACCESS   read-only
    STATUS       current
    DESCRIPTION
        "Cisco Firepower fabric:FcoeVsanPc:dn managed object property"
    ::= { cfprFabricFcoeVsanPcEntry 2 }

cfprFabricFcoeVsanPcRn OBJECT-TYPE
    SYNTAX       SnmpAdminString
    MAX-ACCESS   read-only
    STATUS       current
    DESCRIPTION
        "Cisco Firepower fabric:FcoeVsanPc:rn managed object property"
    ::= { cfprFabricFcoeVsanPcEntry 3 }

cfprFabricFcoeVsanPcAdminState OBJECT-TYPE
    SYNTAX       CfprFabricCIoEpAdminState
    MAX-ACCESS   read-only
    STATUS       current
    DESCRIPTION
        "Cisco Firepower fabric:FcoeVsanPc:adminState managed
        object property"
    ::= { cfprFabricFcoeVsanPcEntry 4 }

cfprFabricFcoeVsanPcDescr OBJECT-TYPE
    SYNTAX       SnmpAdminString
    MAX-ACCESS   read-only
    STATUS       current
    DESCRIPTION
        "Cisco Firepower fabric:FcoeVsanPc:descr managed object property"
    ::= { cfprFabricFcoeVsanPcEntry 5 }

cfprFabricFcoeVsanPcEpDn OBJECT-TYPE
    SYNTAX       SnmpAdminString
    MAX-ACCESS   read-only
    STATUS       current
    DESCRIPTION
        "Cisco Firepower fabric:FcoeVsanPc:epDn managed object property"
    ::= { cfprFabricFcoeVsanPcEntry 6 }

cfprFabricFcoeVsanPcFltAggr OBJECT-TYPE
    SYNTAX       Unsigned64
    MAX-ACCESS   read-only
    STATUS       current
    DESCRIPTION
        "Cisco Firepower fabric:FcoeVsanPc:fltAggr managed
        object property"
    ::= { cfprFabricFcoeVsanPcEntry 7 }

cfprFabricFcoeVsanPcIfRole OBJECT-TYPE
    SYNTAX       CfprFabricSanPcIfRole
    MAX-ACCESS   read-only
    STATUS       current
    DESCRIPTION
        "Cisco Firepower fabric:FcoeVsanPc:ifRole managed object property"
    ::= { cfprFabricFcoeVsanPcEntry 8 }

cfprFabricFcoeVsanPcIfType OBJECT-TYPE
    SYNTAX       CfprFabricCIoEpIfType
    MAX-ACCESS   read-only
    STATUS       current
    DESCRIPTION
        "Cisco Firepower fabric:FcoeVsanPc:ifType managed object property"
    ::= { cfprFabricFcoeVsanPcEntry 9 }

cfprFabricFcoeVsanPcLocale OBJECT-TYPE
    SYNTAX       CfprFabricExternalPcLocale
    MAX-ACCESS   read-only
    STATUS       current
    DESCRIPTION
        "Cisco Firepower fabric:FcoeVsanPc:locale managed object property"
    ::= { cfprFabricFcoeVsanPcEntry 10 }

cfprFabricFcoeVsanPcName OBJECT-TYPE
    SYNTAX       SnmpAdminString
    MAX-ACCESS   read-only
    STATUS       current
    DESCRIPTION
        "Cisco Firepower fabric:FcoeVsanPc:name managed object property"
    ::= { cfprFabricFcoeVsanPcEntry 11 }

cfprFabricFcoeVsanPcOperState OBJECT-TYPE
    SYNTAX       CfprNetworkPortOperState
    MAX-ACCESS   read-only
    STATUS       current
    DESCRIPTION
        "Cisco Firepower fabric:FcoeVsanPc:operState managed
        object property"
    ::= { cfprFabricFcoeVsanPcEntry 12 }

cfprFabricFcoeVsanPcPeerDn OBJECT-TYPE
    SYNTAX       SnmpAdminString
    MAX-ACCESS   read-only
    STATUS       current
    DESCRIPTION
        "Cisco Firepower fabric:FcoeVsanPc:peerDn managed object property"
    ::= { cfprFabricFcoeVsanPcEntry 13 }

cfprFabricFcoeVsanPcPortId OBJECT-TYPE
    SYNTAX       Gauge32
    MAX-ACCESS   read-only
    STATUS       current
    DESCRIPTION
        "Cisco Firepower fabric:FcoeVsanPc:portId managed object property"
    ::= { cfprFabricFcoeVsanPcEntry 14 }

cfprFabricFcoeVsanPcStateQual OBJECT-TYPE
    SYNTAX       SnmpAdminString
    MAX-ACCESS   read-only
    STATUS       current
    DESCRIPTION
        "Cisco Firepower fabric:FcoeVsanPc:stateQual managed
        object property"
    ::= { cfprFabricFcoeVsanPcEntry 15 }

cfprFabricFcoeVsanPcSwitchId OBJECT-TYPE
    SYNTAX       CfprNetworkSwitchId
    MAX-ACCESS   read-only
    STATUS       current
    DESCRIPTION
        "Cisco Firepower fabric:FcoeVsanPc:switchId managed
        object property"
    ::= { cfprFabricFcoeVsanPcEntry 16 }

cfprFabricFcoeVsanPcTransport OBJECT-TYPE
    SYNTAX       CfprFabricFcoeVsanPcTransport
    MAX-ACCESS   read-only
    STATUS       current
    DESCRIPTION
        "Cisco Firepower fabric:FcoeVsanPc:transport managed
        object property"
    ::= { cfprFabricFcoeVsanPcEntry 17 }

cfprFabricFcoeVsanPcType OBJECT-TYPE
    SYNTAX       CfprFabricSanPcType
    MAX-ACCESS   read-only
    STATUS       current
    DESCRIPTION
        "Cisco Firepower fabric:FcoeVsanPc:type managed object property"
    ::= { cfprFabricFcoeVsanPcEntry 18 }

cfprFabricFcoeVsanPcWarnings OBJECT-TYPE
    SYNTAX       CfprFabricWarnings
    MAX-ACCESS   read-only
    STATUS       current
    DESCRIPTION
        "Cisco Firepower fabric:FcoeVsanPc:warnings managed
        object property"
    ::= { cfprFabricFcoeVsanPcEntry 19 }

cfprFabricFcoeVsanPortEpTable OBJECT-TYPE
    SYNTAX           SEQUENCE OF CfprFabricFcoeVsanPortEpEntry
    MAX-ACCESS       not-accessible
    STATUS           current
    DESCRIPTION
        "Cisco Firepower fabric:FcoeVsanPortEp managed object table"
    ::= { cfprFabricObjects 66 }

cfprFabricFcoeVsanPortEpEntry OBJECT-TYPE
    SYNTAX           CfprFabricFcoeVsanPortEpEntry
    MAX-ACCESS       not-accessible
    STATUS           current
    DESCRIPTION
        "Entry for the cfprFabricFcoeVsanPortEpTable table."
    INDEX { cfprFabricFcoeVsanPortEpInstanceId }
    ::= { cfprFabricFcoeVsanPortEpTable 1 }

CfprFabricFcoeVsanPortEpEntry ::= SEQUENCE {
    cfprFabricFcoeVsanPortEpInstanceId                               CfprManagedObjectId,
    cfprFabricFcoeVsanPortEpDn                                       CfprManagedObjectDn,
    cfprFabricFcoeVsanPortEpRn                                       SnmpAdminString,
    cfprFabricFcoeVsanPortEpAdminState                               CfprFabricExternalEpAdminState,
    cfprFabricFcoeVsanPortEpAggrPortId                               Gauge32,
    cfprFabricFcoeVsanPortEpChassisId                                Gauge32,
    cfprFabricFcoeVsanPortEpEpDn                                     SnmpAdminString,
    cfprFabricFcoeVsanPortEpFltAggr                                  Unsigned64,
    cfprFabricFcoeVsanPortEpIfRole                                   CfprFabricSanEpIfRole,
    cfprFabricFcoeVsanPortEpIfType                                   CfprFabricPIoEpIfType,
    cfprFabricFcoeVsanPortEpLicGP                                    Unsigned64,
    cfprFabricFcoeVsanPortEpLicState                                 CfprLicenseState,
    cfprFabricFcoeVsanPortEpLocale                                   CfprFabricExternalEpLocale,
    cfprFabricFcoeVsanPortEpName                                     SnmpAdminString,
    cfprFabricFcoeVsanPortEpOperState                                CfprFabricPIoEpOperState,
    cfprFabricFcoeVsanPortEpOperStateReason                          SnmpAdminString,
    cfprFabricFcoeVsanPortEpPeerAggrPortId                           Gauge32,
    cfprFabricFcoeVsanPortEpPeerChassisId                            Gauge32,
    cfprFabricFcoeVsanPortEpPeerDn                                   SnmpAdminString,
    cfprFabricFcoeVsanPortEpPeerPortId                               Gauge32,
    cfprFabricFcoeVsanPortEpPeerSlotId                               Gauge32,
    cfprFabricFcoeVsanPortEpPortId                                   CfprFabricFcoeVsanPortEpPortId,
    cfprFabricFcoeVsanPortEpSlotId                                   CfprFabricFcoeVsanPortEpSlotId,
    cfprFabricFcoeVsanPortEpSwitchId                                 CfprNetworkSwitchId,
    cfprFabricFcoeVsanPortEpTransport                                CfprFabricAFcSanEpTransport,
    cfprFabricFcoeVsanPortEpType                                     CfprFabricSanEpType,
    cfprFabricFcoeVsanPortEpWarnings                                 CfprFabricWarnings
}

cfprFabricFcoeVsanPortEpInstanceId OBJECT-TYPE
    SYNTAX       CfprManagedObjectId
    MAX-ACCESS   not-accessible
    STATUS       current
    DESCRIPTION
        "Instance identifier of the managed object."
    ::= { cfprFabricFcoeVsanPortEpEntry 1 }

cfprFabricFcoeVsanPortEpDn OBJECT-TYPE
    SYNTAX       CfprManagedObjectDn
    MAX-ACCESS   read-only
    STATUS       current
    DESCRIPTION
        "Cisco Firepower fabric:FcoeVsanPortEp:dn managed object property"
    ::= { cfprFabricFcoeVsanPortEpEntry 2 }

cfprFabricFcoeVsanPortEpRn OBJECT-TYPE
    SYNTAX       SnmpAdminString
    MAX-ACCESS   read-only
    STATUS       current
    DESCRIPTION
        "Cisco Firepower fabric:FcoeVsanPortEp:rn managed object property"
    ::= { cfprFabricFcoeVsanPortEpEntry 3 }

cfprFabricFcoeVsanPortEpAdminState OBJECT-TYPE
    SYNTAX       CfprFabricExternalEpAdminState
    MAX-ACCESS   read-only
    STATUS       current
    DESCRIPTION
        "Cisco Firepower fabric:FcoeVsanPortEp:adminState
        managed object property"
    ::= { cfprFabricFcoeVsanPortEpEntry 4 }

cfprFabricFcoeVsanPortEpAggrPortId OBJECT-TYPE
    SYNTAX       Gauge32
    MAX-ACCESS   read-only
    STATUS       current
    DESCRIPTION
        "Cisco Firepower fabric:FcoeVsanPortEp:aggrPortId
        managed object property"
    ::= { cfprFabricFcoeVsanPortEpEntry 5 }

cfprFabricFcoeVsanPortEpChassisId OBJECT-TYPE
    SYNTAX       Gauge32
    MAX-ACCESS   read-only
    STATUS       current
    DESCRIPTION
        "Cisco Firepower fabric:FcoeVsanPortEp:chassisId
        managed object property"
    ::= { cfprFabricFcoeVsanPortEpEntry 6 }

cfprFabricFcoeVsanPortEpEpDn OBJECT-TYPE
    SYNTAX       SnmpAdminString
    MAX-ACCESS   read-only
    STATUS       current
    DESCRIPTION
        "Cisco Firepower fabric:FcoeVsanPortEp:epDn managed
        object property"
    ::= { cfprFabricFcoeVsanPortEpEntry 7 }

cfprFabricFcoeVsanPortEpFltAggr OBJECT-TYPE
    SYNTAX       Unsigned64
    MAX-ACCESS   read-only
    STATUS       current
    DESCRIPTION
        "Cisco Firepower fabric:FcoeVsanPortEp:fltAggr
        managed object property"
    ::= { cfprFabricFcoeVsanPortEpEntry 8 }

cfprFabricFcoeVsanPortEpIfRole OBJECT-TYPE
    SYNTAX       CfprFabricSanEpIfRole
    MAX-ACCESS   read-only
    STATUS       current
    DESCRIPTION
        "Cisco Firepower fabric:FcoeVsanPortEp:ifRole managed
        object property"
    ::= { cfprFabricFcoeVsanPortEpEntry 9 }

cfprFabricFcoeVsanPortEpIfType OBJECT-TYPE
    SYNTAX       CfprFabricPIoEpIfType
    MAX-ACCESS   read-only
    STATUS       current
    DESCRIPTION
        "Cisco Firepower fabric:FcoeVsanPortEp:ifType managed
        object property"
    ::= { cfprFabricFcoeVsanPortEpEntry 10 }

cfprFabricFcoeVsanPortEpLicGP OBJECT-TYPE
    SYNTAX       Unsigned64
    MAX-ACCESS   read-only
    STATUS       current
    DESCRIPTION
        "Cisco Firepower fabric:FcoeVsanPortEp:licGP managed
        object property"
    ::= { cfprFabricFcoeVsanPortEpEntry 11 }

cfprFabricFcoeVsanPortEpLicState OBJECT-TYPE
    SYNTAX       CfprLicenseState
    MAX-ACCESS   read-only
    STATUS       current
    DESCRIPTION
        "Cisco Firepower fabric:FcoeVsanPortEp:licState
        managed object property"
    ::= { cfprFabricFcoeVsanPortEpEntry 12 }

cfprFabricFcoeVsanPortEpLocale OBJECT-TYPE
    SYNTAX       CfprFabricExternalEpLocale
    MAX-ACCESS   read-only
    STATUS       current
    DESCRIPTION
        "Cisco Firepower fabric:FcoeVsanPortEp:locale managed
        object property"
    ::= { cfprFabricFcoeVsanPortEpEntry 13 }

cfprFabricFcoeVsanPortEpName OBJECT-TYPE
    SYNTAX       SnmpAdminString
    MAX-ACCESS   read-only
    STATUS       current
    DESCRIPTION
        "Cisco Firepower fabric:FcoeVsanPortEp:name managed
        object property"
    ::= { cfprFabricFcoeVsanPortEpEntry 14 }

cfprFabricFcoeVsanPortEpOperState OBJECT-TYPE
    SYNTAX       CfprFabricPIoEpOperState
    MAX-ACCESS   read-only
    STATUS       current
    DESCRIPTION
        "Cisco Firepower fabric:FcoeVsanPortEp:operState
        managed object property"
    ::= { cfprFabricFcoeVsanPortEpEntry 15 }

cfprFabricFcoeVsanPortEpOperStateReason OBJECT-TYPE
    SYNTAX       SnmpAdminString
    MAX-ACCESS   read-only
    STATUS       current
    DESCRIPTION
        "Cisco Firepower fabric:FcoeVsanPortEp:operStateReason
        managed object property"
    ::= { cfprFabricFcoeVsanPortEpEntry 16 }

cfprFabricFcoeVsanPortEpPeerAggrPortId OBJECT-TYPE
    SYNTAX       Gauge32
    MAX-ACCESS   read-only
    STATUS       current
    DESCRIPTION
        "Cisco Firepower fabric:FcoeVsanPortEp:peerAggrPortId
        managed object property"
    ::= { cfprFabricFcoeVsanPortEpEntry 17 }

cfprFabricFcoeVsanPortEpPeerChassisId OBJECT-TYPE
    SYNTAX       Gauge32
    MAX-ACCESS   read-only
    STATUS       current
    DESCRIPTION
        "Cisco Firepower fabric:FcoeVsanPortEp:peerChassisId
        managed object property"
    ::= { cfprFabricFcoeVsanPortEpEntry 18 }

cfprFabricFcoeVsanPortEpPeerDn OBJECT-TYPE
    SYNTAX       SnmpAdminString
    MAX-ACCESS   read-only
    STATUS       current
    DESCRIPTION
        "Cisco Firepower fabric:FcoeVsanPortEp:peerDn managed
        object property"
    ::= { cfprFabricFcoeVsanPortEpEntry 19 }

cfprFabricFcoeVsanPortEpPeerPortId OBJECT-TYPE
    SYNTAX       Gauge32
    MAX-ACCESS   read-only
    STATUS       current
    DESCRIPTION
        "Cisco Firepower fabric:FcoeVsanPortEp:peerPortId
        managed object property"
    ::= { cfprFabricFcoeVsanPortEpEntry 20 }

cfprFabricFcoeVsanPortEpPeerSlotId OBJECT-TYPE
    SYNTAX       Gauge32
    MAX-ACCESS   read-only
    STATUS       current
    DESCRIPTION
        "Cisco Firepower fabric:FcoeVsanPortEp:peerSlotId
        managed object property"
    ::= { cfprFabricFcoeVsanPortEpEntry 21 }

cfprFabricFcoeVsanPortEpPortId OBJECT-TYPE
    SYNTAX       CfprFabricFcoeVsanPortEpPortId
    MAX-ACCESS   read-only
    STATUS       current
    DESCRIPTION
        "Cisco Firepower fabric:FcoeVsanPortEp:portId managed
        object property"
    ::= { cfprFabricFcoeVsanPortEpEntry 22 }

cfprFabricFcoeVsanPortEpSlotId OBJECT-TYPE
    SYNTAX       CfprFabricFcoeVsanPortEpSlotId
    MAX-ACCESS   read-only
    STATUS       current
    DESCRIPTION
        "Cisco Firepower fabric:FcoeVsanPortEp:slotId managed
        object property"
    ::= { cfprFabricFcoeVsanPortEpEntry 23 }

cfprFabricFcoeVsanPortEpSwitchId OBJECT-TYPE
    SYNTAX       CfprNetworkSwitchId
    MAX-ACCESS   read-only
    STATUS       current
    DESCRIPTION
        "Cisco Firepower fabric:FcoeVsanPortEp:switchId
        managed object property"
    ::= { cfprFabricFcoeVsanPortEpEntry 24 }

cfprFabricFcoeVsanPortEpTransport OBJECT-TYPE
    SYNTAX       CfprFabricAFcSanEpTransport
    MAX-ACCESS   read-only
    STATUS       current
    DESCRIPTION
        "Cisco Firepower fabric:FcoeVsanPortEp:transport
        managed object property"
    ::= { cfprFabricFcoeVsanPortEpEntry 25 }

cfprFabricFcoeVsanPortEpType OBJECT-TYPE
    SYNTAX       CfprFabricSanEpType
    MAX-ACCESS   read-only
    STATUS       current
    DESCRIPTION
        "Cisco Firepower fabric:FcoeVsanPortEp:type managed
        object property"
    ::= { cfprFabricFcoeVsanPortEpEntry 26 }

cfprFabricFcoeVsanPortEpWarnings OBJECT-TYPE
    SYNTAX       CfprFabricWarnings
    MAX-ACCESS   read-only
    STATUS       current
    DESCRIPTION
        "Cisco Firepower fabric:FcoeVsanPortEp:warnings
        managed object property"
    ::= { cfprFabricFcoeVsanPortEpEntry 27 }

cfprFabricFlowMonDefinitionTable OBJECT-TYPE
    SYNTAX           SEQUENCE OF CfprFabricFlowMonDefinitionEntry
    MAX-ACCESS       not-accessible
    STATUS           current
    DESCRIPTION
        "Cisco Firepower fabric:FlowMonDefinition managed object table"
    ::= { cfprFabricObjects 67 }

cfprFabricFlowMonDefinitionEntry OBJECT-TYPE
    SYNTAX           CfprFabricFlowMonDefinitionEntry
    MAX-ACCESS       not-accessible
    STATUS           current
    DESCRIPTION
        "Entry for the cfprFabricFlowMonDefinitionTable table."
    INDEX { cfprFabricFlowMonDefinitionInstanceId }
    ::= { cfprFabricFlowMonDefinitionTable 1 }

CfprFabricFlowMonDefinitionEntry ::= SEQUENCE {
    cfprFabricFlowMonDefinitionInstanceId                            CfprManagedObjectId,
    cfprFabricFlowMonDefinitionDn                                    CfprManagedObjectDn,
    cfprFabricFlowMonDefinitionRn                                    SnmpAdminString,
    cfprFabricFlowMonDefinitionDescr                                 SnmpAdminString,
    cfprFabricFlowMonDefinitionIntId                                 SnmpAdminString,
    cfprFabricFlowMonDefinitionIpv4keys                              CfprFabricFlowMonIpv4Keys,
    cfprFabricFlowMonDefinitionIpv6keys                              CfprFabricFlowMonIpv6Keys,
    cfprFabricFlowMonDefinitionKeyType                               CfprFabricFlowMonKeyType,
    cfprFabricFlowMonDefinitionL2keys                                CfprFabricFlowMonL2Keys,
    cfprFabricFlowMonDefinitionName                                  SnmpAdminString,
    cfprFabricFlowMonDefinitionNonkeys                               CfprFabricFlowMonNonKeys,
    cfprFabricFlowMonDefinitionPolicyLevel                           Gauge32,
    cfprFabricFlowMonDefinitionPolicyOwner                           CfprPolicyPolicyOwner,
    cfprFabricFlowMonDefinitionRecordType                            CfprFabricFlowMonDefType
}

cfprFabricFlowMonDefinitionInstanceId OBJECT-TYPE
    SYNTAX       CfprManagedObjectId
    MAX-ACCESS   not-accessible
    STATUS       current
    DESCRIPTION
        "Instance identifier of the managed object."
    ::= { cfprFabricFlowMonDefinitionEntry 1 }

cfprFabricFlowMonDefinitionDn OBJECT-TYPE
    SYNTAX       CfprManagedObjectDn
    MAX-ACCESS   read-only
    STATUS       current
    DESCRIPTION
        "Cisco Firepower fabric:FlowMonDefinition:dn managed
        object property"
    ::= { cfprFabricFlowMonDefinitionEntry 2 }

cfprFabricFlowMonDefinitionRn OBJECT-TYPE
    SYNTAX       SnmpAdminString
    MAX-ACCESS   read-only
    STATUS       current
    DESCRIPTION
        "Cisco Firepower fabric:FlowMonDefinition:rn managed
        object property"
    ::= { cfprFabricFlowMonDefinitionEntry 3 }

cfprFabricFlowMonDefinitionDescr OBJECT-TYPE
    SYNTAX       SnmpAdminString
    MAX-ACCESS   read-only
    STATUS       current
    DESCRIPTION
        "Cisco Firepower fabric:FlowMonDefinition:descr
        managed object property"
    ::= { cfprFabricFlowMonDefinitionEntry 4 }

cfprFabricFlowMonDefinitionIntId OBJECT-TYPE
    SYNTAX       SnmpAdminString
    MAX-ACCESS   read-only
    STATUS       current
    DESCRIPTION
        "Cisco Firepower fabric:FlowMonDefinition:intId
        managed object property"
    ::= { cfprFabricFlowMonDefinitionEntry 5 }

cfprFabricFlowMonDefinitionIpv4keys OBJECT-TYPE
    SYNTAX       CfprFabricFlowMonIpv4Keys
    MAX-ACCESS   read-only
    STATUS       current
    DESCRIPTION
        "Cisco Firepower fabric:FlowMonDefinition:ipv4keys
        managed object property"
    ::= { cfprFabricFlowMonDefinitionEntry 6 }

cfprFabricFlowMonDefinitionIpv6keys OBJECT-TYPE
    SYNTAX       CfprFabricFlowMonIpv6Keys
    MAX-ACCESS   read-only
    STATUS       current
    DESCRIPTION
        "Cisco Firepower fabric:FlowMonDefinition:ipv6keys
        managed object property"
    ::= { cfprFabricFlowMonDefinitionEntry 7 }

cfprFabricFlowMonDefinitionKeyType OBJECT-TYPE
    SYNTAX       CfprFabricFlowMonKeyType
    MAX-ACCESS   read-only
    STATUS       current
    DESCRIPTION
        "Cisco Firepower fabric:FlowMonDefinition:keyType
        managed object property"
    ::= { cfprFabricFlowMonDefinitionEntry 8 }

cfprFabricFlowMonDefinitionL2keys OBJECT-TYPE
    SYNTAX       CfprFabricFlowMonL2Keys
    MAX-ACCESS   read-only
    STATUS       current
    DESCRIPTION
        "Cisco Firepower fabric:FlowMonDefinition:l2keys
        managed object property"
    ::= { cfprFabricFlowMonDefinitionEntry 9 }

cfprFabricFlowMonDefinitionName OBJECT-TYPE
    SYNTAX       SnmpAdminString
    MAX-ACCESS   read-only
    STATUS       current
    DESCRIPTION
        "Cisco Firepower fabric:FlowMonDefinition:name
        managed object property"
    ::= { cfprFabricFlowMonDefinitionEntry 10 }

cfprFabricFlowMonDefinitionNonkeys OBJECT-TYPE
    SYNTAX       CfprFabricFlowMonNonKeys
    MAX-ACCESS   read-only
    STATUS       current
    DESCRIPTION
        "Cisco Firepower fabric:FlowMonDefinition:nonkeys
        managed object property"
    ::= { cfprFabricFlowMonDefinitionEntry 11 }

cfprFabricFlowMonDefinitionPolicyLevel OBJECT-TYPE
    SYNTAX       Gauge32
    MAX-ACCESS   read-only
    STATUS       current
    DESCRIPTION
        "Cisco Firepower fabric:FlowMonDefinition:policyLevel
        managed object property"
    ::= { cfprFabricFlowMonDefinitionEntry 12 }

cfprFabricFlowMonDefinitionPolicyOwner OBJECT-TYPE
    SYNTAX       CfprPolicyPolicyOwner
    MAX-ACCESS   read-only
    STATUS       current
    DESCRIPTION
        "Cisco Firepower fabric:FlowMonDefinition:policyOwner
        managed object property"
    ::= { cfprFabricFlowMonDefinitionEntry 13 }

cfprFabricFlowMonDefinitionRecordType OBJECT-TYPE
    SYNTAX       CfprFabricFlowMonDefType
    MAX-ACCESS   read-only
    STATUS       current
    DESCRIPTION
        "Cisco Firepower fabric:FlowMonDefinition:recordType
        managed object property"
    ::= { cfprFabricFlowMonDefinitionEntry 14 }

cfprFabricFlowMonExporterProfileTable OBJECT-TYPE
    SYNTAX           SEQUENCE OF CfprFabricFlowMonExporterProfileEntry
    MAX-ACCESS       not-accessible
    STATUS           current
    DESCRIPTION
        "Cisco Firepower fabric:FlowMonExporterProfile
        managed object table"
    ::= { cfprFabricObjects 68 }

cfprFabricFlowMonExporterProfileEntry OBJECT-TYPE
    SYNTAX           CfprFabricFlowMonExporterProfileEntry
    MAX-ACCESS       not-accessible
    STATUS           current
    DESCRIPTION
        "Entry for the cfprFabricFlowMonExporterProfileTable table."
    INDEX { cfprFabricFlowMonExporterProfileInstanceId }
    ::= { cfprFabricFlowMonExporterProfileTable 1 }

CfprFabricFlowMonExporterProfileEntry ::= SEQUENCE {
    cfprFabricFlowMonExporterProfileInstanceId                       CfprManagedObjectId,
    cfprFabricFlowMonExporterProfileDn                               CfprManagedObjectDn,
    cfprFabricFlowMonExporterProfileRn                               SnmpAdminString,
    cfprFabricFlowMonExporterProfileDescr                            SnmpAdminString,
    cfprFabricFlowMonExporterProfileIntId                            SnmpAdminString,
    cfprFabricFlowMonExporterProfileName                             SnmpAdminString,
    cfprFabricFlowMonExporterProfilePolicyLevel                      Gauge32,
    cfprFabricFlowMonExporterProfilePolicyOwner                      CfprPolicyPolicyOwner
}

cfprFabricFlowMonExporterProfileInstanceId OBJECT-TYPE
    SYNTAX       CfprManagedObjectId
    MAX-ACCESS   not-accessible
    STATUS       current
    DESCRIPTION
        "Instance identifier of the managed object."
    ::= { cfprFabricFlowMonExporterProfileEntry 1 }

cfprFabricFlowMonExporterProfileDn OBJECT-TYPE
    SYNTAX       CfprManagedObjectDn
    MAX-ACCESS   read-only
    STATUS       current
    DESCRIPTION
        "Cisco Firepower fabric:FlowMonExporterProfile:dn
        managed object property"
    ::= { cfprFabricFlowMonExporterProfileEntry 2 }

cfprFabricFlowMonExporterProfileRn OBJECT-TYPE
    SYNTAX       SnmpAdminString
    MAX-ACCESS   read-only
    STATUS       current
    DESCRIPTION
        "Cisco Firepower fabric:FlowMonExporterProfile:rn
        managed object property"
    ::= { cfprFabricFlowMonExporterProfileEntry 3 }

cfprFabricFlowMonExporterProfileDescr OBJECT-TYPE
    SYNTAX       SnmpAdminString
    MAX-ACCESS   read-only
    STATUS       current
    DESCRIPTION
        "Cisco Firepower fabric:FlowMonExporterProfile:descr
        managed object property"
    ::= { cfprFabricFlowMonExporterProfileEntry 4 }

cfprFabricFlowMonExporterProfileIntId OBJECT-TYPE
    SYNTAX       SnmpAdminString
    MAX-ACCESS   read-only
    STATUS       current
    DESCRIPTION
        "Cisco Firepower fabric:FlowMonExporterProfile:intId
        managed object property"
    ::= { cfprFabricFlowMonExporterProfileEntry 5 }

cfprFabricFlowMonExporterProfileName OBJECT-TYPE
    SYNTAX       SnmpAdminString
    MAX-ACCESS   read-only
    STATUS       current
    DESCRIPTION
        "Cisco Firepower fabric:FlowMonExporterProfile:name
        managed object property"
    ::= { cfprFabricFlowMonExporterProfileEntry 6 }

cfprFabricFlowMonExporterProfilePolicyLevel OBJECT-TYPE
    SYNTAX       Gauge32
    MAX-ACCESS   read-only
    STATUS       current
    DESCRIPTION
        "Cisco Firepower fabric:FlowMonExporterProfile:policyLevel
        managed object property"
    ::= { cfprFabricFlowMonExporterProfileEntry 7 }

cfprFabricFlowMonExporterProfilePolicyOwner OBJECT-TYPE
    SYNTAX       CfprPolicyPolicyOwner
    MAX-ACCESS   read-only
    STATUS       current
    DESCRIPTION
        "Cisco Firepower fabric:FlowMonExporterProfile:policyOwner
        managed object property"
    ::= { cfprFabricFlowMonExporterProfileEntry 8 }

cfprFabricIfTable OBJECT-TYPE
    SYNTAX           SEQUENCE OF CfprFabricIfEntry
    MAX-ACCESS       not-accessible
    STATUS           current
    DESCRIPTION
        "Cisco Firepower fabric:If managed object table"
    ::= { cfprFabricObjects 69 }

cfprFabricIfEntry OBJECT-TYPE
    SYNTAX           CfprFabricIfEntry
    MAX-ACCESS       not-accessible
    STATUS           current
    DESCRIPTION
        "Entry for the cfprFabricIfTable table."
    INDEX { cfprFabricIfInstanceId }
    ::= { cfprFabricIfTable 1 }

CfprFabricIfEntry ::= SEQUENCE {
    cfprFabricIfInstanceId                                           CfprManagedObjectId,
    cfprFabricIfDn                                                   CfprManagedObjectDn,
    cfprFabricIfRn                                                   SnmpAdminString,
    cfprFabricIfAddr                                                 InetAddressIPv4,
    cfprFabricIfId                                                   CfprNetworkSwitchId
}

cfprFabricIfInstanceId OBJECT-TYPE
    SYNTAX       CfprManagedObjectId
    MAX-ACCESS   not-accessible
    STATUS       current
    DESCRIPTION
        "Instance identifier of the managed object."
    ::= { cfprFabricIfEntry 1 }

cfprFabricIfDn OBJECT-TYPE
    SYNTAX       CfprManagedObjectDn
    MAX-ACCESS   read-only
    STATUS       current
    DESCRIPTION
        "Cisco Firepower fabric:If:dn managed object property"
    ::= { cfprFabricIfEntry 2 }

cfprFabricIfRn OBJECT-TYPE
    SYNTAX       SnmpAdminString
    MAX-ACCESS   read-only
    STATUS       current
    DESCRIPTION
        "Cisco Firepower fabric:If:rn managed object property"
    ::= { cfprFabricIfEntry 3 }

cfprFabricIfAddr OBJECT-TYPE
    SYNTAX       InetAddressIPv4
    MAX-ACCESS   read-only
    STATUS       current
    DESCRIPTION
        "Cisco Firepower fabric:If:addr managed object property"
    ::= { cfprFabricIfEntry 4 }

cfprFabricIfId OBJECT-TYPE
    SYNTAX       CfprNetworkSwitchId
    MAX-ACCESS   read-only
    STATUS       current
    DESCRIPTION
        "Cisco Firepower fabric:If:id managed object property"
    ::= { cfprFabricIfEntry 5 }

cfprFabricInnerVlanMgrTable OBJECT-TYPE
    SYNTAX           SEQUENCE OF CfprFabricInnerVlanMgrEntry
    MAX-ACCESS       not-accessible
    STATUS           current
    DESCRIPTION
        "Cisco Firepower fabric:InnerVlanMgr managed object table"
    ::= { cfprFabricObjects 133 }

cfprFabricInnerVlanMgrEntry OBJECT-TYPE
    SYNTAX           CfprFabricInnerVlanMgrEntry
    MAX-ACCESS       not-accessible
    STATUS           current
    DESCRIPTION
        "Entry for the cfprFabricInnerVlanMgrTable table."
    INDEX { cfprFabricInnerVlanMgrInstanceId }
    ::= { cfprFabricInnerVlanMgrTable 1 }

CfprFabricInnerVlanMgrEntry ::= SEQUENCE {
    cfprFabricInnerVlanMgrInstanceId                                 CfprManagedObjectId,
    cfprFabricInnerVlanMgrDn                                         CfprManagedObjectDn,
    cfprFabricInnerVlanMgrRn                                         SnmpAdminString,
    cfprFabricInnerVlanMgrFltAggr                                    Unsigned64,
    cfprFabricInnerVlanMgrId                                         CfprNetworkSwitchId
}

cfprFabricInnerVlanMgrInstanceId OBJECT-TYPE
    SYNTAX       CfprManagedObjectId
    MAX-ACCESS   not-accessible
    STATUS       current
    DESCRIPTION
        "Instance identifier of the managed object."
    ::= { cfprFabricInnerVlanMgrEntry 1 }

cfprFabricInnerVlanMgrDn OBJECT-TYPE
    SYNTAX       CfprManagedObjectDn
    MAX-ACCESS   read-only
    STATUS       current
    DESCRIPTION
        "Cisco Firepower fabric:InnerVlanMgr:dn managed object property"
    ::= { cfprFabricInnerVlanMgrEntry 2 }

cfprFabricInnerVlanMgrRn OBJECT-TYPE
    SYNTAX       SnmpAdminString
    MAX-ACCESS   read-only
    STATUS       current
    DESCRIPTION
        "Cisco Firepower fabric:InnerVlanMgr:rn managed object property"
    ::= { cfprFabricInnerVlanMgrEntry 3 }

cfprFabricInnerVlanMgrFltAggr OBJECT-TYPE
    SYNTAX       Unsigned64
    MAX-ACCESS   read-only
    STATUS       current
    DESCRIPTION
        "Cisco Firepower fabric:InnerVlanMgr:fltAggr managed
        object property"
    ::= { cfprFabricInnerVlanMgrEntry 4 }

cfprFabricInnerVlanMgrId OBJECT-TYPE
    SYNTAX       CfprNetworkSwitchId
    MAX-ACCESS   read-only
    STATUS       current
    DESCRIPTION
        "Cisco Firepower fabric:InnerVlanMgr:id managed object property"
    ::= { cfprFabricInnerVlanMgrEntry 5 }

cfprFabricLacpPolicyTable OBJECT-TYPE
    SYNTAX           SEQUENCE OF CfprFabricLacpPolicyEntry
    MAX-ACCESS       not-accessible
    STATUS           current
    DESCRIPTION
        "Cisco Firepower fabric:LacpPolicy managed object table"
    ::= { cfprFabricObjects 70 }

cfprFabricLacpPolicyEntry OBJECT-TYPE
    SYNTAX           CfprFabricLacpPolicyEntry
    MAX-ACCESS       not-accessible
    STATUS           current
    DESCRIPTION
        "Entry for the cfprFabricLacpPolicyTable table."
    INDEX { cfprFabricLacpPolicyInstanceId }
    ::= { cfprFabricLacpPolicyTable 1 }

CfprFabricLacpPolicyEntry ::= SEQUENCE {
    cfprFabricLacpPolicyInstanceId                                   CfprManagedObjectId,
    cfprFabricLacpPolicyDn                                           CfprManagedObjectDn,
    cfprFabricLacpPolicyRn                                           SnmpAdminString,
    cfprFabricLacpPolicyDescr                                        SnmpAdminString,
    cfprFabricLacpPolicyFastTimer                                    CfprFabricLacpRate,
    cfprFabricLacpPolicyIntId                                        SnmpAdminString,
    cfprFabricLacpPolicyName                                         SnmpAdminString,
    cfprFabricLacpPolicyPolicyLevel                                  Gauge32,
    cfprFabricLacpPolicyPolicyOwner                                  CfprPolicyPolicyOwner,
    cfprFabricLacpPolicySuspendIndividual                            CfprFabricLacpSuspend
}

cfprFabricLacpPolicyInstanceId OBJECT-TYPE
    SYNTAX       CfprManagedObjectId
    MAX-ACCESS   not-accessible
    STATUS       current
    DESCRIPTION
        "Instance identifier of the managed object."
    ::= { cfprFabricLacpPolicyEntry 1 }

cfprFabricLacpPolicyDn OBJECT-TYPE
    SYNTAX       CfprManagedObjectDn
    MAX-ACCESS   read-only
    STATUS       current
    DESCRIPTION
        "Cisco Firepower fabric:LacpPolicy:dn managed object property"
    ::= { cfprFabricLacpPolicyEntry 2 }

cfprFabricLacpPolicyRn OBJECT-TYPE
    SYNTAX       SnmpAdminString
    MAX-ACCESS   read-only
    STATUS       current
    DESCRIPTION
        "Cisco Firepower fabric:LacpPolicy:rn managed object property"
    ::= { cfprFabricLacpPolicyEntry 3 }

cfprFabricLacpPolicyDescr OBJECT-TYPE
    SYNTAX       SnmpAdminString
    MAX-ACCESS   read-only
    STATUS       current
    DESCRIPTION
        "Cisco Firepower fabric:LacpPolicy:descr managed object property"
    ::= { cfprFabricLacpPolicyEntry 4 }

cfprFabricLacpPolicyFastTimer OBJECT-TYPE
    SYNTAX       CfprFabricLacpRate
    MAX-ACCESS   read-only
    STATUS       current
    DESCRIPTION
        "Cisco Firepower fabric:LacpPolicy:fastTimer managed
        object property"
    ::= { cfprFabricLacpPolicyEntry 5 }

cfprFabricLacpPolicyIntId OBJECT-TYPE
    SYNTAX       SnmpAdminString
    MAX-ACCESS   read-only
    STATUS       current
    DESCRIPTION
        "Cisco Firepower fabric:LacpPolicy:intId managed object property"
    ::= { cfprFabricLacpPolicyEntry 6 }

cfprFabricLacpPolicyName OBJECT-TYPE
    SYNTAX       SnmpAdminString
    MAX-ACCESS   read-only
    STATUS       current
    DESCRIPTION
        "Cisco Firepower fabric:LacpPolicy:name managed object property"
    ::= { cfprFabricLacpPolicyEntry 7 }

cfprFabricLacpPolicyPolicyLevel OBJECT-TYPE
    SYNTAX       Gauge32
    MAX-ACCESS   read-only
    STATUS       current
    DESCRIPTION
        "Cisco Firepower fabric:LacpPolicy:policyLevel
        managed object property"
    ::= { cfprFabricLacpPolicyEntry 8 }

cfprFabricLacpPolicyPolicyOwner OBJECT-TYPE
    SYNTAX       CfprPolicyPolicyOwner
    MAX-ACCESS   read-only
    STATUS       current
    DESCRIPTION
        "Cisco Firepower fabric:LacpPolicy:policyOwner
        managed object property"
    ::= { cfprFabricLacpPolicyEntry 9 }

cfprFabricLacpPolicySuspendIndividual OBJECT-TYPE
    SYNTAX       CfprFabricLacpSuspend
    MAX-ACCESS   read-only
    STATUS       current
    DESCRIPTION
        "Cisco Firepower fabric:LacpPolicy:suspendIndividual
        managed object property"
    ::= { cfprFabricLacpPolicyEntry 10 }

cfprFabricLanAccessMgrTable OBJECT-TYPE
    SYNTAX           SEQUENCE OF CfprFabricLanAccessMgrEntry
    MAX-ACCESS       not-accessible
    STATUS           current
    DESCRIPTION
        "Cisco Firepower fabric:LanAccessMgr managed object table"
    ::= { cfprFabricObjects 71 }

cfprFabricLanAccessMgrEntry OBJECT-TYPE
    SYNTAX           CfprFabricLanAccessMgrEntry
    MAX-ACCESS       not-accessible
    STATUS           current
    DESCRIPTION
        "Entry for the cfprFabricLanAccessMgrTable table."
    INDEX { cfprFabricLanAccessMgrInstanceId }
    ::= { cfprFabricLanAccessMgrTable 1 }

CfprFabricLanAccessMgrEntry ::= SEQUENCE {
    cfprFabricLanAccessMgrInstanceId                                 CfprManagedObjectId,
    cfprFabricLanAccessMgrDn                                         CfprManagedObjectDn,
    cfprFabricLanAccessMgrRn                                         SnmpAdminString
}

cfprFabricLanAccessMgrInstanceId OBJECT-TYPE
    SYNTAX       CfprManagedObjectId
    MAX-ACCESS   not-accessible
    STATUS       current
    DESCRIPTION
        "Instance identifier of the managed object."
    ::= { cfprFabricLanAccessMgrEntry 1 }

cfprFabricLanAccessMgrDn OBJECT-TYPE
    SYNTAX       CfprManagedObjectDn
    MAX-ACCESS   read-only
    STATUS       current
    DESCRIPTION
        "Cisco Firepower fabric:LanAccessMgr:dn managed object property"
    ::= { cfprFabricLanAccessMgrEntry 2 }

cfprFabricLanAccessMgrRn OBJECT-TYPE
    SYNTAX       SnmpAdminString
    MAX-ACCESS   read-only
    STATUS       current
    DESCRIPTION
        "Cisco Firepower fabric:LanAccessMgr:rn managed object property"
    ::= { cfprFabricLanAccessMgrEntry 3 }

cfprFabricLanCloudTable OBJECT-TYPE
    SYNTAX           SEQUENCE OF CfprFabricLanCloudEntry
    MAX-ACCESS       not-accessible
    STATUS           current
    DESCRIPTION
        "Cisco Firepower fabric:LanCloud managed object table"
    ::= { cfprFabricObjects 72 }

cfprFabricLanCloudEntry OBJECT-TYPE
    SYNTAX           CfprFabricLanCloudEntry
    MAX-ACCESS       not-accessible
    STATUS           current
    DESCRIPTION
        "Entry for the cfprFabricLanCloudTable table."
    INDEX { cfprFabricLanCloudInstanceId }
    ::= { cfprFabricLanCloudTable 1 }

CfprFabricLanCloudEntry ::= SEQUENCE {
    cfprFabricLanCloudInstanceId                                     CfprManagedObjectId,
    cfprFabricLanCloudDn                                             CfprManagedObjectDn,
    cfprFabricLanCloudRn                                             SnmpAdminString,
    cfprFabricLanCloudFsmDescr                                       SnmpAdminString,
    cfprFabricLanCloudFsmPrev                                        SnmpAdminString,
    cfprFabricLanCloudFsmProgr                                       Gauge32,
    cfprFabricLanCloudFsmRmtInvErrCode                               Gauge32,
    cfprFabricLanCloudFsmRmtInvErrDescr                              SnmpAdminString,
    cfprFabricLanCloudFsmRmtInvRslt                                  CfprConditionRemoteInvRslt,
    cfprFabricLanCloudFsmStageDescr                                  SnmpAdminString,
    cfprFabricLanCloudFsmStamp                                       DateAndTime,
    cfprFabricLanCloudFsmStatus                                      SnmpAdminString,
    cfprFabricLanCloudFsmTry                                         Gauge32,
    cfprFabricLanCloudMacAging                                       TimeIntervalSec,
    cfprFabricLanCloudMode                                           CfprFabricSwitchingMode,
    cfprFabricLanCloudVlanCompression                                CfprFabricLanCloudVlanCompression
}

cfprFabricLanCloudInstanceId OBJECT-TYPE
    SYNTAX       CfprManagedObjectId
    MAX-ACCESS   not-accessible
    STATUS       current
    DESCRIPTION
        "Instance identifier of the managed object."
    ::= { cfprFabricLanCloudEntry 1 }

cfprFabricLanCloudDn OBJECT-TYPE
    SYNTAX       CfprManagedObjectDn
    MAX-ACCESS   read-only
    STATUS       current
    DESCRIPTION
        "Cisco Firepower fabric:LanCloud:dn managed object property"
    ::= { cfprFabricLanCloudEntry 2 }

cfprFabricLanCloudRn OBJECT-TYPE
    SYNTAX       SnmpAdminString
    MAX-ACCESS   read-only
    STATUS       current
    DESCRIPTION
        "Cisco Firepower fabric:LanCloud:rn managed object property"
    ::= { cfprFabricLanCloudEntry 3 }

cfprFabricLanCloudFsmDescr OBJECT-TYPE
    SYNTAX       SnmpAdminString
    MAX-ACCESS   read-only
    STATUS       current
    DESCRIPTION
        "Cisco Firepower fabric:LanCloud:fsmDescr managed object property"
    ::= { cfprFabricLanCloudEntry 4 }

cfprFabricLanCloudFsmPrev OBJECT-TYPE
    SYNTAX       SnmpAdminString
    MAX-ACCESS   read-only
    STATUS       current
    DESCRIPTION
        "Cisco Firepower fabric:LanCloud:fsmPrev managed object property"
    ::= { cfprFabricLanCloudEntry 5 }

cfprFabricLanCloudFsmProgr OBJECT-TYPE
    SYNTAX       Gauge32
    MAX-ACCESS   read-only
    STATUS       current
    DESCRIPTION
        "Cisco Firepower fabric:LanCloud:fsmProgr managed object property"
    ::= { cfprFabricLanCloudEntry 6 }

cfprFabricLanCloudFsmRmtInvErrCode OBJECT-TYPE
    SYNTAX       Gauge32
    MAX-ACCESS   read-only
    STATUS       current
    DESCRIPTION
        "Cisco Firepower fabric:LanCloud:fsmRmtInvErrCode
        managed object property"
    ::= { cfprFabricLanCloudEntry 7 }

cfprFabricLanCloudFsmRmtInvErrDescr OBJECT-TYPE
    SYNTAX       SnmpAdminString
    MAX-ACCESS   read-only
    STATUS       current
    DESCRIPTION
        "Cisco Firepower fabric:LanCloud:fsmRmtInvErrDescr
        managed object property"
    ::= { cfprFabricLanCloudEntry 8 }

cfprFabricLanCloudFsmRmtInvRslt OBJECT-TYPE
    SYNTAX       CfprConditionRemoteInvRslt
    MAX-ACCESS   read-only
    STATUS       current
    DESCRIPTION
        "Cisco Firepower fabric:LanCloud:fsmRmtInvRslt
        managed object property"
    ::= { cfprFabricLanCloudEntry 9 }

cfprFabricLanCloudFsmStageDescr OBJECT-TYPE
    SYNTAX       SnmpAdminString
    MAX-ACCESS   read-only
    STATUS       current
    DESCRIPTION
        "Cisco Firepower fabric:LanCloud:fsmStageDescr
        managed object property"
    ::= { cfprFabricLanCloudEntry 10 }

cfprFabricLanCloudFsmStamp OBJECT-TYPE
    SYNTAX       DateAndTime
    MAX-ACCESS   read-only
    STATUS       current
    DESCRIPTION
        "Cisco Firepower fabric:LanCloud:fsmStamp managed object property"
    ::= { cfprFabricLanCloudEntry 11 }

cfprFabricLanCloudFsmStatus OBJECT-TYPE
    SYNTAX       SnmpAdminString
    MAX-ACCESS   read-only
    STATUS       current
    DESCRIPTION
        "Cisco Firepower fabric:LanCloud:fsmStatus managed
        object property"
    ::= { cfprFabricLanCloudEntry 12 }

cfprFabricLanCloudFsmTry OBJECT-TYPE
    SYNTAX       Gauge32
    MAX-ACCESS   read-only
    STATUS       current
    DESCRIPTION
        "Cisco Firepower fabric:LanCloud:fsmTry managed object property"
    ::= { cfprFabricLanCloudEntry 13 }

cfprFabricLanCloudMacAging OBJECT-TYPE
    SYNTAX       TimeIntervalSec
    MAX-ACCESS   read-only
    STATUS       current
    DESCRIPTION
        "Cisco Firepower fabric:LanCloud:macAging managed object property"
    ::= { cfprFabricLanCloudEntry 14 }

cfprFabricLanCloudMode OBJECT-TYPE
    SYNTAX       CfprFabricSwitchingMode
    MAX-ACCESS   read-only
    STATUS       current
    DESCRIPTION
        "Cisco Firepower fabric:LanCloud:mode managed object property"
    ::= { cfprFabricLanCloudEntry 15 }

cfprFabricLanCloudVlanCompression OBJECT-TYPE
    SYNTAX       CfprFabricLanCloudVlanCompression
    MAX-ACCESS   read-only
    STATUS       current
    DESCRIPTION
        "Cisco Firepower fabric:LanCloud:vlanCompression
        managed object property"
    ::= { cfprFabricLanCloudEntry 16 }

cfprFabricLanCloudFsmTable OBJECT-TYPE
    SYNTAX           SEQUENCE OF CfprFabricLanCloudFsmEntry
    MAX-ACCESS       not-accessible
    STATUS           current
    DESCRIPTION
        "Cisco Firepower fabric:LanCloudFsm managed object table"
    ::= { cfprFabricObjects 73 }

cfprFabricLanCloudFsmEntry OBJECT-TYPE
    SYNTAX           CfprFabricLanCloudFsmEntry
    MAX-ACCESS       not-accessible
    STATUS           current
    DESCRIPTION
        "Entry for the cfprFabricLanCloudFsmTable table."
    INDEX { cfprFabricLanCloudFsmInstanceId }
    ::= { cfprFabricLanCloudFsmTable 1 }

CfprFabricLanCloudFsmEntry ::= SEQUENCE {
    cfprFabricLanCloudFsmInstanceId                                  CfprManagedObjectId,
    cfprFabricLanCloudFsmDn                                          CfprManagedObjectDn,
    cfprFabricLanCloudFsmRn                                          SnmpAdminString,
    cfprFabricLanCloudFsmCompletionTime                              DateAndTime,
    cfprFabricLanCloudFsmCurrentFsm                                  CfprFabricLanCloudFsmCurrentFsm,
    cfprFabricLanCloudFsmDescrData                                   SnmpAdminString,
    cfprFabricLanCloudFsmFsmStatus                                   CfprFsmFsmStageStatus,
    cfprFabricLanCloudFsmProgress                                    Gauge32,
    cfprFabricLanCloudFsmRmtErrCode                                  Gauge32,
    cfprFabricLanCloudFsmRmtErrDescr                                 SnmpAdminString,
    cfprFabricLanCloudFsmRmtRslt                                     CfprConditionRemoteInvRslt
}

cfprFabricLanCloudFsmInstanceId OBJECT-TYPE
    SYNTAX       CfprManagedObjectId
    MAX-ACCESS   not-accessible
    STATUS       current
    DESCRIPTION
        "Instance identifier of the managed object."
    ::= { cfprFabricLanCloudFsmEntry 1 }

cfprFabricLanCloudFsmDn OBJECT-TYPE
    SYNTAX       CfprManagedObjectDn
    MAX-ACCESS   read-only
    STATUS       current
    DESCRIPTION
        "Cisco Firepower fabric:LanCloudFsm:dn managed object property"
    ::= { cfprFabricLanCloudFsmEntry 2 }

cfprFabricLanCloudFsmRn OBJECT-TYPE
    SYNTAX       SnmpAdminString
    MAX-ACCESS   read-only
    STATUS       current
    DESCRIPTION
        "Cisco Firepower fabric:LanCloudFsm:rn managed object property"
    ::= { cfprFabricLanCloudFsmEntry 3 }

cfprFabricLanCloudFsmCompletionTime OBJECT-TYPE
    SYNTAX       DateAndTime
    MAX-ACCESS   read-only
    STATUS       current
    DESCRIPTION
        "Cisco Firepower fabric:LanCloudFsm:completionTime
        managed object property"
    ::= { cfprFabricLanCloudFsmEntry 4 }

cfprFabricLanCloudFsmCurrentFsm OBJECT-TYPE
    SYNTAX       CfprFabricLanCloudFsmCurrentFsm
    MAX-ACCESS   read-only
    STATUS       current
    DESCRIPTION
        "Cisco Firepower fabric:LanCloudFsm:currentFsm
        managed object property"
    ::= { cfprFabricLanCloudFsmEntry 5 }

cfprFabricLanCloudFsmDescrData OBJECT-TYPE
    SYNTAX       SnmpAdminString
    MAX-ACCESS   read-only
    STATUS       current
    DESCRIPTION
        "Cisco Firepower fabric:LanCloudFsm:descr managed object property"
    ::= { cfprFabricLanCloudFsmEntry 6 }

cfprFabricLanCloudFsmFsmStatus OBJECT-TYPE
    SYNTAX       CfprFsmFsmStageStatus
    MAX-ACCESS   read-only
    STATUS       current
    DESCRIPTION
        "Cisco Firepower fabric:LanCloudFsm:fsmStatus managed
        object property"
    ::= { cfprFabricLanCloudFsmEntry 7 }

cfprFabricLanCloudFsmProgress OBJECT-TYPE
    SYNTAX       Gauge32
    MAX-ACCESS   read-only
    STATUS       current
    DESCRIPTION
        "Cisco Firepower fabric:LanCloudFsm:progress managed
        object property"
    ::= { cfprFabricLanCloudFsmEntry 8 }

cfprFabricLanCloudFsmRmtErrCode OBJECT-TYPE
    SYNTAX       Gauge32
    MAX-ACCESS   read-only
    STATUS       current
    DESCRIPTION
        "Cisco Firepower fabric:LanCloudFsm:rmtErrCode
        managed object property"
    ::= { cfprFabricLanCloudFsmEntry 9 }

cfprFabricLanCloudFsmRmtErrDescr OBJECT-TYPE
    SYNTAX       SnmpAdminString
    MAX-ACCESS   read-only
    STATUS       current
    DESCRIPTION
        "Cisco Firepower fabric:LanCloudFsm:rmtErrDescr
        managed object property"
    ::= { cfprFabricLanCloudFsmEntry 10 }

cfprFabricLanCloudFsmRmtRslt OBJECT-TYPE
    SYNTAX       CfprConditionRemoteInvRslt
    MAX-ACCESS   read-only
    STATUS       current
    DESCRIPTION
        "Cisco Firepower fabric:LanCloudFsm:rmtRslt managed
        object property"
    ::= { cfprFabricLanCloudFsmEntry 11 }

cfprFabricLanCloudFsmStageTable OBJECT-TYPE
    SYNTAX           SEQUENCE OF CfprFabricLanCloudFsmStageEntry
    MAX-ACCESS       not-accessible
    STATUS           current
    DESCRIPTION
        "Cisco Firepower fabric:LanCloudFsmStage managed object table"
    ::= { cfprFabricObjects 74 }

cfprFabricLanCloudFsmStageEntry OBJECT-TYPE
    SYNTAX           CfprFabricLanCloudFsmStageEntry
    MAX-ACCESS       not-accessible
    STATUS           current
    DESCRIPTION
        "Entry for the cfprFabricLanCloudFsmStageTable table."
    INDEX { cfprFabricLanCloudFsmStageInstanceId }
    ::= { cfprFabricLanCloudFsmStageTable 1 }

CfprFabricLanCloudFsmStageEntry ::= SEQUENCE {
    cfprFabricLanCloudFsmStageInstanceId                             CfprManagedObjectId,
    cfprFabricLanCloudFsmStageDn                                     CfprManagedObjectDn,
    cfprFabricLanCloudFsmStageRn                                     SnmpAdminString,
    cfprFabricLanCloudFsmStageDescrData                              SnmpAdminString,
    cfprFabricLanCloudFsmStageLastUpdateTime                         DateAndTime,
    cfprFabricLanCloudFsmStageName                                   CfprFabricLanCloudFsmStageName,
    cfprFabricLanCloudFsmStageOrder                                  Gauge32,
    cfprFabricLanCloudFsmStageRetry                                  Gauge32,
    cfprFabricLanCloudFsmStageStageStatus                            CfprFsmFsmStageStatus
}

cfprFabricLanCloudFsmStageInstanceId OBJECT-TYPE
    SYNTAX       CfprManagedObjectId
    MAX-ACCESS   not-accessible
    STATUS       current
    DESCRIPTION
        "Instance identifier of the managed object."
    ::= { cfprFabricLanCloudFsmStageEntry 1 }

cfprFabricLanCloudFsmStageDn OBJECT-TYPE
    SYNTAX       CfprManagedObjectDn
    MAX-ACCESS   read-only
    STATUS       current
    DESCRIPTION
        "Cisco Firepower fabric:LanCloudFsmStage:dn managed
        object property"
    ::= { cfprFabricLanCloudFsmStageEntry 2 }

cfprFabricLanCloudFsmStageRn OBJECT-TYPE
    SYNTAX       SnmpAdminString
    MAX-ACCESS   read-only
    STATUS       current
    DESCRIPTION
        "Cisco Firepower fabric:LanCloudFsmStage:rn managed
        object property"
    ::= { cfprFabricLanCloudFsmStageEntry 3 }

cfprFabricLanCloudFsmStageDescrData OBJECT-TYPE
    SYNTAX       SnmpAdminString
    MAX-ACCESS   read-only
    STATUS       current
    DESCRIPTION
        "Cisco Firepower fabric:LanCloudFsmStage:descr
        managed object property"
    ::= { cfprFabricLanCloudFsmStageEntry 4 }

cfprFabricLanCloudFsmStageLastUpdateTime OBJECT-TYPE
    SYNTAX       DateAndTime
    MAX-ACCESS   read-only
    STATUS       current
    DESCRIPTION
        "Cisco Firepower fabric:LanCloudFsmStage:lastUpdateTime
        managed object property"
    ::= { cfprFabricLanCloudFsmStageEntry 5 }

cfprFabricLanCloudFsmStageName OBJECT-TYPE
    SYNTAX       CfprFabricLanCloudFsmStageName
    MAX-ACCESS   read-only
    STATUS       current
    DESCRIPTION
        "Cisco Firepower fabric:LanCloudFsmStage:name managed
        object property"
    ::= { cfprFabricLanCloudFsmStageEntry 6 }

cfprFabricLanCloudFsmStageOrder OBJECT-TYPE
    SYNTAX       Gauge32
    MAX-ACCESS   read-only
    STATUS       current
    DESCRIPTION
        "Cisco Firepower fabric:LanCloudFsmStage:order
        managed object property"
    ::= { cfprFabricLanCloudFsmStageEntry 7 }

cfprFabricLanCloudFsmStageRetry OBJECT-TYPE
    SYNTAX       Gauge32
    MAX-ACCESS   read-only
    STATUS       current
    DESCRIPTION
        "Cisco Firepower fabric:LanCloudFsmStage:retry
        managed object property"
    ::= { cfprFabricLanCloudFsmStageEntry 8 }

cfprFabricLanCloudFsmStageStageStatus OBJECT-TYPE
    SYNTAX       CfprFsmFsmStageStatus
    MAX-ACCESS   read-only
    STATUS       current
    DESCRIPTION
        "Cisco Firepower fabric:LanCloudFsmStage:stageStatus
        managed object property"
    ::= { cfprFabricLanCloudFsmStageEntry 9 }

cfprFabricLanCloudFsmTaskTable OBJECT-TYPE
    SYNTAX           SEQUENCE OF CfprFabricLanCloudFsmTaskEntry
    MAX-ACCESS       not-accessible
    STATUS           current
    DESCRIPTION
        "Cisco Firepower fabric:LanCloudFsmTask managed object table"
    ::= { cfprFabricObjects 75 }

cfprFabricLanCloudFsmTaskEntry OBJECT-TYPE
    SYNTAX           CfprFabricLanCloudFsmTaskEntry
    MAX-ACCESS       not-accessible
    STATUS           current
    DESCRIPTION
        "Entry for the cfprFabricLanCloudFsmTaskTable table."
    INDEX { cfprFabricLanCloudFsmTaskInstanceId }
    ::= { cfprFabricLanCloudFsmTaskTable 1 }

CfprFabricLanCloudFsmTaskEntry ::= SEQUENCE {
    cfprFabricLanCloudFsmTaskInstanceId                              CfprManagedObjectId,
    cfprFabricLanCloudFsmTaskDn                                      CfprManagedObjectDn,
    cfprFabricLanCloudFsmTaskRn                                      SnmpAdminString,
    cfprFabricLanCloudFsmTaskCompletion                              CfprFsmCompletion,
    cfprFabricLanCloudFsmTaskFlags                                   CfprFsmFlags,
    cfprFabricLanCloudFsmTaskItem                                    CfprFabricLanCloudFsmTaskItem,
    cfprFabricLanCloudFsmTaskSeqId                                   Gauge32
}

cfprFabricLanCloudFsmTaskInstanceId OBJECT-TYPE
    SYNTAX       CfprManagedObjectId
    MAX-ACCESS   not-accessible
    STATUS       current
    DESCRIPTION
        "Instance identifier of the managed object."
    ::= { cfprFabricLanCloudFsmTaskEntry 1 }

cfprFabricLanCloudFsmTaskDn OBJECT-TYPE
    SYNTAX       CfprManagedObjectDn
    MAX-ACCESS   read-only
    STATUS       current
    DESCRIPTION
        "Cisco Firepower fabric:LanCloudFsmTask:dn managed
        object property"
    ::= { cfprFabricLanCloudFsmTaskEntry 2 }

cfprFabricLanCloudFsmTaskRn OBJECT-TYPE
    SYNTAX       SnmpAdminString
    MAX-ACCESS   read-only
    STATUS       current
    DESCRIPTION
        "Cisco Firepower fabric:LanCloudFsmTask:rn managed
        object property"
    ::= { cfprFabricLanCloudFsmTaskEntry 3 }

cfprFabricLanCloudFsmTaskCompletion OBJECT-TYPE
    SYNTAX       CfprFsmCompletion
    MAX-ACCESS   read-only
    STATUS       current
    DESCRIPTION
        "Cisco Firepower fabric:LanCloudFsmTask:completion
        managed object property"
    ::= { cfprFabricLanCloudFsmTaskEntry 4 }

cfprFabricLanCloudFsmTaskFlags OBJECT-TYPE
    SYNTAX       CfprFsmFlags
    MAX-ACCESS   read-only
    STATUS       current
    DESCRIPTION
        "Cisco Firepower fabric:LanCloudFsmTask:flags managed
        object property"
    ::= { cfprFabricLanCloudFsmTaskEntry 5 }

cfprFabricLanCloudFsmTaskItem OBJECT-TYPE
    SYNTAX       CfprFabricLanCloudFsmTaskItem
    MAX-ACCESS   read-only
    STATUS       current
    DESCRIPTION
        "Cisco Firepower fabric:LanCloudFsmTask:item managed
        object property"
    ::= { cfprFabricLanCloudFsmTaskEntry 6 }

cfprFabricLanCloudFsmTaskSeqId OBJECT-TYPE
    SYNTAX       Gauge32
    MAX-ACCESS   read-only
    STATUS       current
    DESCRIPTION
        "Cisco Firepower fabric:LanCloudFsmTask:seqId managed
        object property"
    ::= { cfprFabricLanCloudFsmTaskEntry 7 }

cfprFabricLanMonCloudTable OBJECT-TYPE
    SYNTAX           SEQUENCE OF CfprFabricLanMonCloudEntry
    MAX-ACCESS       not-accessible
    STATUS           current
    DESCRIPTION
        "Cisco Firepower fabric:LanMonCloud managed object table"
    ::= { cfprFabricObjects 76 }

cfprFabricLanMonCloudEntry OBJECT-TYPE
    SYNTAX           CfprFabricLanMonCloudEntry
    MAX-ACCESS       not-accessible
    STATUS           current
    DESCRIPTION
        "Entry for the cfprFabricLanMonCloudTable table."
    INDEX { cfprFabricLanMonCloudInstanceId }
    ::= { cfprFabricLanMonCloudTable 1 }

CfprFabricLanMonCloudEntry ::= SEQUENCE {
    cfprFabricLanMonCloudInstanceId                                  CfprManagedObjectId,
    cfprFabricLanMonCloudDn                                          CfprManagedObjectDn,
    cfprFabricLanMonCloudRn                                          SnmpAdminString,
    cfprFabricLanMonCloudMode                                        CfprFabricSwitchingMode
}

cfprFabricLanMonCloudInstanceId OBJECT-TYPE
    SYNTAX       CfprManagedObjectId
    MAX-ACCESS   not-accessible
    STATUS       current
    DESCRIPTION
        "Instance identifier of the managed object."
    ::= { cfprFabricLanMonCloudEntry 1 }

cfprFabricLanMonCloudDn OBJECT-TYPE
    SYNTAX       CfprManagedObjectDn
    MAX-ACCESS   read-only
    STATUS       current
    DESCRIPTION
        "Cisco Firepower fabric:LanMonCloud:dn managed object property"
    ::= { cfprFabricLanMonCloudEntry 2 }

cfprFabricLanMonCloudRn OBJECT-TYPE
    SYNTAX       SnmpAdminString
    MAX-ACCESS   read-only
    STATUS       current
    DESCRIPTION
        "Cisco Firepower fabric:LanMonCloud:rn managed object property"
    ::= { cfprFabricLanMonCloudEntry 3 }

cfprFabricLanMonCloudMode OBJECT-TYPE
    SYNTAX       CfprFabricSwitchingMode
    MAX-ACCESS   read-only
    STATUS       current
    DESCRIPTION
        "Cisco Firepower fabric:LanMonCloud:mode managed object property"
    ::= { cfprFabricLanMonCloudEntry 4 }

cfprFabricLanPinGroupTable OBJECT-TYPE
    SYNTAX           SEQUENCE OF CfprFabricLanPinGroupEntry
    MAX-ACCESS       not-accessible
    STATUS           current
    DESCRIPTION
        "Cisco Firepower fabric:LanPinGroup managed object table"
    ::= { cfprFabricObjects 77 }

cfprFabricLanPinGroupEntry OBJECT-TYPE
    SYNTAX           CfprFabricLanPinGroupEntry
    MAX-ACCESS       not-accessible
    STATUS           current
    DESCRIPTION
        "Entry for the cfprFabricLanPinGroupTable table."
    INDEX { cfprFabricLanPinGroupInstanceId }
    ::= { cfprFabricLanPinGroupTable 1 }

CfprFabricLanPinGroupEntry ::= SEQUENCE {
    cfprFabricLanPinGroupInstanceId                                  CfprManagedObjectId,
    cfprFabricLanPinGroupDn                                          CfprManagedObjectDn,
    cfprFabricLanPinGroupRn                                          SnmpAdminString,
    cfprFabricLanPinGroupDescr                                       SnmpAdminString,
    cfprFabricLanPinGroupIntId                                       SnmpAdminString,
    cfprFabricLanPinGroupName                                        SnmpAdminString,
    cfprFabricLanPinGroupPolicyLevel                                 Gauge32,
    cfprFabricLanPinGroupPolicyOwner                                 CfprPolicyPolicyOwner,
    cfprFabricLanPinGroupSize                                        Gauge32
}

cfprFabricLanPinGroupInstanceId OBJECT-TYPE
    SYNTAX       CfprManagedObjectId
    MAX-ACCESS   not-accessible
    STATUS       current
    DESCRIPTION
        "Instance identifier of the managed object."
    ::= { cfprFabricLanPinGroupEntry 1 }

cfprFabricLanPinGroupDn OBJECT-TYPE
    SYNTAX       CfprManagedObjectDn
    MAX-ACCESS   read-only
    STATUS       current
    DESCRIPTION
        "Cisco Firepower fabric:LanPinGroup:dn managed object property"
    ::= { cfprFabricLanPinGroupEntry 2 }

cfprFabricLanPinGroupRn OBJECT-TYPE
    SYNTAX       SnmpAdminString
    MAX-ACCESS   read-only
    STATUS       current
    DESCRIPTION
        "Cisco Firepower fabric:LanPinGroup:rn managed object property"
    ::= { cfprFabricLanPinGroupEntry 3 }

cfprFabricLanPinGroupDescr OBJECT-TYPE
    SYNTAX       SnmpAdminString
    MAX-ACCESS   read-only
    STATUS       current
    DESCRIPTION
        "Cisco Firepower fabric:LanPinGroup:descr managed object property"
    ::= { cfprFabricLanPinGroupEntry 4 }

cfprFabricLanPinGroupIntId OBJECT-TYPE
    SYNTAX       SnmpAdminString
    MAX-ACCESS   read-only
    STATUS       current
    DESCRIPTION
        "Cisco Firepower fabric:LanPinGroup:intId managed object property"
    ::= { cfprFabricLanPinGroupEntry 5 }

cfprFabricLanPinGroupName OBJECT-TYPE
    SYNTAX       SnmpAdminString
    MAX-ACCESS   read-only
    STATUS       current
    DESCRIPTION
        "Cisco Firepower fabric:LanPinGroup:name managed object property"
    ::= { cfprFabricLanPinGroupEntry 6 }

cfprFabricLanPinGroupPolicyLevel OBJECT-TYPE
    SYNTAX       Gauge32
    MAX-ACCESS   read-only
    STATUS       current
    DESCRIPTION
        "Cisco Firepower fabric:LanPinGroup:policyLevel
        managed object property"
    ::= { cfprFabricLanPinGroupEntry 7 }

cfprFabricLanPinGroupPolicyOwner OBJECT-TYPE
    SYNTAX       CfprPolicyPolicyOwner
    MAX-ACCESS   read-only
    STATUS       current
    DESCRIPTION
        "Cisco Firepower fabric:LanPinGroup:policyOwner
        managed object property"
    ::= { cfprFabricLanPinGroupEntry 8 }

cfprFabricLanPinGroupSize OBJECT-TYPE
    SYNTAX       Gauge32
    MAX-ACCESS   read-only
    STATUS       current
    DESCRIPTION
        "Cisco Firepower fabric:LanPinGroup:size managed object property"
    ::= { cfprFabricLanPinGroupEntry 9 }

cfprFabricLanPinTargetTable OBJECT-TYPE
    SYNTAX           SEQUENCE OF CfprFabricLanPinTargetEntry
    MAX-ACCESS       not-accessible
    STATUS           current
    DESCRIPTION
        "Cisco Firepower fabric:LanPinTarget managed object table"
    ::= { cfprFabricObjects 78 }

cfprFabricLanPinTargetEntry OBJECT-TYPE
    SYNTAX           CfprFabricLanPinTargetEntry
    MAX-ACCESS       not-accessible
    STATUS           current
    DESCRIPTION
        "Entry for the cfprFabricLanPinTargetTable table."
    INDEX { cfprFabricLanPinTargetInstanceId }
    ::= { cfprFabricLanPinTargetTable 1 }

CfprFabricLanPinTargetEntry ::= SEQUENCE {
    cfprFabricLanPinTargetInstanceId                                 CfprManagedObjectId,
    cfprFabricLanPinTargetDn                                         CfprManagedObjectDn,
    cfprFabricLanPinTargetRn                                         SnmpAdminString,
    cfprFabricLanPinTargetEpDn                                       SnmpAdminString,
    cfprFabricLanPinTargetFabricId                                   SnmpAdminString,
    cfprFabricLanPinTargetTargetStatus                               CfprFabricTargetStatus
}

cfprFabricLanPinTargetInstanceId OBJECT-TYPE
    SYNTAX       CfprManagedObjectId
    MAX-ACCESS   not-accessible
    STATUS       current
    DESCRIPTION
        "Instance identifier of the managed object."
    ::= { cfprFabricLanPinTargetEntry 1 }

cfprFabricLanPinTargetDn OBJECT-TYPE
    SYNTAX       CfprManagedObjectDn
    MAX-ACCESS   read-only
    STATUS       current
    DESCRIPTION
        "Cisco Firepower fabric:LanPinTarget:dn managed object property"
    ::= { cfprFabricLanPinTargetEntry 2 }

cfprFabricLanPinTargetRn OBJECT-TYPE
    SYNTAX       SnmpAdminString
    MAX-ACCESS   read-only
    STATUS       current
    DESCRIPTION
        "Cisco Firepower fabric:LanPinTarget:rn managed object property"
    ::= { cfprFabricLanPinTargetEntry 3 }

cfprFabricLanPinTargetEpDn OBJECT-TYPE
    SYNTAX       SnmpAdminString
    MAX-ACCESS   read-only
    STATUS       current
    DESCRIPTION
        "Cisco Firepower fabric:LanPinTarget:epDn managed object property"
    ::= { cfprFabricLanPinTargetEntry 4 }

cfprFabricLanPinTargetFabricId OBJECT-TYPE
    SYNTAX       SnmpAdminString
    MAX-ACCESS   read-only
    STATUS       current
    DESCRIPTION
        "Cisco Firepower fabric:LanPinTarget:fabricId managed
        object property"
    ::= { cfprFabricLanPinTargetEntry 5 }

cfprFabricLanPinTargetTargetStatus OBJECT-TYPE
    SYNTAX       CfprFabricTargetStatus
    MAX-ACCESS   read-only
    STATUS       current
    DESCRIPTION
        "Cisco Firepower fabric:LanPinTarget:targetStatus
        managed object property"
    ::= { cfprFabricLanPinTargetEntry 6 }

cfprFabricLastAckedSlotTable OBJECT-TYPE
    SYNTAX           SEQUENCE OF CfprFabricLastAckedSlotEntry
    MAX-ACCESS       not-accessible
    STATUS           current
    DESCRIPTION
        "Cisco Firepower fabric:LastAckedSlot managed object table"
    ::= { cfprFabricObjects 79 }

cfprFabricLastAckedSlotEntry OBJECT-TYPE
    SYNTAX           CfprFabricLastAckedSlotEntry
    MAX-ACCESS       not-accessible
    STATUS           current
    DESCRIPTION
        "Entry for the cfprFabricLastAckedSlotTable table."
    INDEX { cfprFabricLastAckedSlotInstanceId }
    ::= { cfprFabricLastAckedSlotTable 1 }

CfprFabricLastAckedSlotEntry ::= SEQUENCE {
    cfprFabricLastAckedSlotInstanceId                                CfprManagedObjectId,
    cfprFabricLastAckedSlotDn                                        CfprManagedObjectDn,
    cfprFabricLastAckedSlotRn                                        SnmpAdminString,
    cfprFabricLastAckedSlotBoardAggregationRole                      CfprEquipmentBoardAggregationRole,
    cfprFabricLastAckedSlotChassisId                                 Gauge32,
    cfprFabricLastAckedSlotSlotId                                    Gauge32,
    cfprFabricLastAckedSlotSwitchId                                  CfprNetworkSwitchId
}

cfprFabricLastAckedSlotInstanceId OBJECT-TYPE
    SYNTAX       CfprManagedObjectId
    MAX-ACCESS   not-accessible
    STATUS       current
    DESCRIPTION
        "Instance identifier of the managed object."
    ::= { cfprFabricLastAckedSlotEntry 1 }

cfprFabricLastAckedSlotDn OBJECT-TYPE
    SYNTAX       CfprManagedObjectDn
    MAX-ACCESS   read-only
    STATUS       current
    DESCRIPTION
        "Cisco Firepower fabric:LastAckedSlot:dn managed object property"
    ::= { cfprFabricLastAckedSlotEntry 2 }

cfprFabricLastAckedSlotRn OBJECT-TYPE
    SYNTAX       SnmpAdminString
    MAX-ACCESS   read-only
    STATUS       current
    DESCRIPTION
        "Cisco Firepower fabric:LastAckedSlot:rn managed object property"
    ::= { cfprFabricLastAckedSlotEntry 3 }

cfprFabricLastAckedSlotBoardAggregationRole OBJECT-TYPE
    SYNTAX       CfprEquipmentBoardAggregationRole
    MAX-ACCESS   read-only
    STATUS       current
    DESCRIPTION
        "Cisco Firepower fabric:LastAckedSlot:boardAggregationRole
        managed object property"
    ::= { cfprFabricLastAckedSlotEntry 4 }

cfprFabricLastAckedSlotChassisId OBJECT-TYPE
    SYNTAX       Gauge32
    MAX-ACCESS   read-only
    STATUS       current
    DESCRIPTION
        "Cisco Firepower fabric:LastAckedSlot:chassisId
        managed object property"
    ::= { cfprFabricLastAckedSlotEntry 5 }

cfprFabricLastAckedSlotSlotId OBJECT-TYPE
    SYNTAX       Gauge32
    MAX-ACCESS   read-only
    STATUS       current
    DESCRIPTION
        "Cisco Firepower fabric:LastAckedSlot:slotId managed
        object property"
    ::= { cfprFabricLastAckedSlotEntry 6 }

cfprFabricLastAckedSlotSwitchId OBJECT-TYPE
    SYNTAX       CfprNetworkSwitchId
    MAX-ACCESS   read-only
    STATUS       current
    DESCRIPTION
        "Cisco Firepower fabric:LastAckedSlot:switchId
        managed object property"
    ::= { cfprFabricLastAckedSlotEntry 7 }

cfprFabricLocaleTable OBJECT-TYPE
    SYNTAX           SEQUENCE OF CfprFabricLocaleEntry
    MAX-ACCESS       not-accessible
    STATUS           current
    DESCRIPTION
        "Cisco Firepower fabric:Locale managed object table"
    ::= { cfprFabricObjects 80 }

cfprFabricLocaleEntry OBJECT-TYPE
    SYNTAX           CfprFabricLocaleEntry
    MAX-ACCESS       not-accessible
    STATUS           current
    DESCRIPTION
        "Entry for the cfprFabricLocaleTable table."
    INDEX { cfprFabricLocaleInstanceId }
    ::= { cfprFabricLocaleTable 1 }

CfprFabricLocaleEntry ::= SEQUENCE {
    cfprFabricLocaleInstanceId                                       CfprManagedObjectId,
    cfprFabricLocaleDn                                               CfprManagedObjectDn,
    cfprFabricLocaleRn                                               SnmpAdminString,
    cfprFabricLocaleCType                                            Gauge32,
    cfprFabricLocaleChassisId                                        Gauge32,
    cfprFabricLocaleLocale                                           CfprNetworkLocale,
    cfprFabricLocaleName                                             SnmpAdminString,
    cfprFabricLocaleSide                                             CfprNetworkSide,
    cfprFabricLocaleSlotId                                           Gauge32,
    cfprFabricLocaleSwitchId                                         CfprNetworkSwitchId,
    cfprFabricLocaleTransport                                        CfprNetworkTransport,
    cfprFabricLocaleType                                             CfprNetworkConnectionType
}

cfprFabricLocaleInstanceId OBJECT-TYPE
    SYNTAX       CfprManagedObjectId
    MAX-ACCESS   not-accessible
    STATUS       current
    DESCRIPTION
        "Instance identifier of the managed object."
    ::= { cfprFabricLocaleEntry 1 }

cfprFabricLocaleDn OBJECT-TYPE
    SYNTAX       CfprManagedObjectDn
    MAX-ACCESS   read-only
    STATUS       current
    DESCRIPTION
        "Cisco Firepower fabric:Locale:dn managed object property"
    ::= { cfprFabricLocaleEntry 2 }

cfprFabricLocaleRn OBJECT-TYPE
    SYNTAX       SnmpAdminString
    MAX-ACCESS   read-only
    STATUS       current
    DESCRIPTION
        "Cisco Firepower fabric:Locale:rn managed object property"
    ::= { cfprFabricLocaleEntry 3 }

cfprFabricLocaleCType OBJECT-TYPE
    SYNTAX       Gauge32
    MAX-ACCESS   read-only
    STATUS       current
    DESCRIPTION
        "Cisco Firepower fabric:Locale:cType managed object property"
    ::= { cfprFabricLocaleEntry 4 }

cfprFabricLocaleChassisId OBJECT-TYPE
    SYNTAX       Gauge32
    MAX-ACCESS   read-only
    STATUS       current
    DESCRIPTION
        "Cisco Firepower fabric:Locale:chassisId managed object property"
    ::= { cfprFabricLocaleEntry 5 }

cfprFabricLocaleLocale OBJECT-TYPE
    SYNTAX       CfprNetworkLocale
    MAX-ACCESS   read-only
    STATUS       current
    DESCRIPTION
        "Cisco Firepower fabric:Locale:locale managed object property"
    ::= { cfprFabricLocaleEntry 6 }

cfprFabricLocaleName OBJECT-TYPE
    SYNTAX       SnmpAdminString
    MAX-ACCESS   read-only
    STATUS       current
    DESCRIPTION
        "Cisco Firepower fabric:Locale:name managed object property"
    ::= { cfprFabricLocaleEntry 7 }

cfprFabricLocaleSide OBJECT-TYPE
    SYNTAX       CfprNetworkSide
    MAX-ACCESS   read-only
    STATUS       current
    DESCRIPTION
        "Cisco Firepower fabric:Locale:side managed object property"
    ::= { cfprFabricLocaleEntry 8 }

cfprFabricLocaleSlotId OBJECT-TYPE
    SYNTAX       Gauge32
    MAX-ACCESS   read-only
    STATUS       current
    DESCRIPTION
        "Cisco Firepower fabric:Locale:slotId managed object property"
    ::= { cfprFabricLocaleEntry 9 }

cfprFabricLocaleSwitchId OBJECT-TYPE
    SYNTAX       CfprNetworkSwitchId
    MAX-ACCESS   read-only
    STATUS       current
    DESCRIPTION
        "Cisco Firepower fabric:Locale:switchId managed object property"
    ::= { cfprFabricLocaleEntry 10 }

cfprFabricLocaleTransport OBJECT-TYPE
    SYNTAX       CfprNetworkTransport
    MAX-ACCESS   read-only
    STATUS       current
    DESCRIPTION
        "Cisco Firepower fabric:Locale:transport managed object property"
    ::= { cfprFabricLocaleEntry 11 }

cfprFabricLocaleType OBJECT-TYPE
    SYNTAX       CfprNetworkConnectionType
    MAX-ACCESS   read-only
    STATUS       current
    DESCRIPTION
        "Cisco Firepower fabric:Locale:type managed object property"
    ::= { cfprFabricLocaleEntry 12 }

cfprFabricMulticastPolicyTable OBJECT-TYPE
    SYNTAX           SEQUENCE OF CfprFabricMulticastPolicyEntry
    MAX-ACCESS       not-accessible
    STATUS           current
    DESCRIPTION
        "Cisco Firepower fabric:MulticastPolicy managed object table"
    ::= { cfprFabricObjects 81 }

cfprFabricMulticastPolicyEntry OBJECT-TYPE
    SYNTAX           CfprFabricMulticastPolicyEntry
    MAX-ACCESS       not-accessible
    STATUS           current
    DESCRIPTION
        "Entry for the cfprFabricMulticastPolicyTable table."
    INDEX { cfprFabricMulticastPolicyInstanceId }
    ::= { cfprFabricMulticastPolicyTable 1 }

CfprFabricMulticastPolicyEntry ::= SEQUENCE {
    cfprFabricMulticastPolicyInstanceId                              CfprManagedObjectId,
    cfprFabricMulticastPolicyDn                                      CfprManagedObjectDn,
    cfprFabricMulticastPolicyRn                                      SnmpAdminString,
    cfprFabricMulticastPolicyDescr                                   SnmpAdminString,
    cfprFabricMulticastPolicyIntId                                   SnmpAdminString,
    cfprFabricMulticastPolicyName                                    SnmpAdminString,
    cfprFabricMulticastPolicyPolicyLevel                             Gauge32,
    cfprFabricMulticastPolicyPolicyOwner                             CfprPolicyPolicyOwner,
    cfprFabricMulticastPolicyQuerierIpAddr                           InetAddressIPv4,
    cfprFabricMulticastPolicyQuerierState                            CfprFabricQuerierType,
    cfprFabricMulticastPolicySnoopingState                           CfprFabricSnoopingType
}

cfprFabricMulticastPolicyInstanceId OBJECT-TYPE
    SYNTAX       CfprManagedObjectId
    MAX-ACCESS   not-accessible
    STATUS       current
    DESCRIPTION
        "Instance identifier of the managed object."
    ::= { cfprFabricMulticastPolicyEntry 1 }

cfprFabricMulticastPolicyDn OBJECT-TYPE
    SYNTAX       CfprManagedObjectDn
    MAX-ACCESS   read-only
    STATUS       current
    DESCRIPTION
        "Cisco Firepower fabric:MulticastPolicy:dn managed
        object property"
    ::= { cfprFabricMulticastPolicyEntry 2 }

cfprFabricMulticastPolicyRn OBJECT-TYPE
    SYNTAX       SnmpAdminString
    MAX-ACCESS   read-only
    STATUS       current
    DESCRIPTION
        "Cisco Firepower fabric:MulticastPolicy:rn managed
        object property"
    ::= { cfprFabricMulticastPolicyEntry 3 }

cfprFabricMulticastPolicyDescr OBJECT-TYPE
    SYNTAX       SnmpAdminString
    MAX-ACCESS   read-only
    STATUS       current
    DESCRIPTION
        "Cisco Firepower fabric:MulticastPolicy:descr managed
        object property"
    ::= { cfprFabricMulticastPolicyEntry 4 }

cfprFabricMulticastPolicyIntId OBJECT-TYPE
    SYNTAX       SnmpAdminString
    MAX-ACCESS   read-only
    STATUS       current
    DESCRIPTION
        "Cisco Firepower fabric:MulticastPolicy:intId managed
        object property"
    ::= { cfprFabricMulticastPolicyEntry 5 }

cfprFabricMulticastPolicyName OBJECT-TYPE
    SYNTAX       SnmpAdminString
    MAX-ACCESS   read-only
    STATUS       current
    DESCRIPTION
        "Cisco Firepower fabric:MulticastPolicy:name managed
        object property"
    ::= { cfprFabricMulticastPolicyEntry 6 }

cfprFabricMulticastPolicyPolicyLevel OBJECT-TYPE
    SYNTAX       Gauge32
    MAX-ACCESS   read-only
    STATUS       current
    DESCRIPTION
        "Cisco Firepower fabric:MulticastPolicy:policyLevel
        managed object property"
    ::= { cfprFabricMulticastPolicyEntry 7 }

cfprFabricMulticastPolicyPolicyOwner OBJECT-TYPE
    SYNTAX       CfprPolicyPolicyOwner
    MAX-ACCESS   read-only
    STATUS       current
    DESCRIPTION
        "Cisco Firepower fabric:MulticastPolicy:policyOwner
        managed object property"
    ::= { cfprFabricMulticastPolicyEntry 8 }

cfprFabricMulticastPolicyQuerierIpAddr OBJECT-TYPE
    SYNTAX       InetAddressIPv4
    MAX-ACCESS   read-only
    STATUS       current
    DESCRIPTION
        "Cisco Firepower fabric:MulticastPolicy:querierIpAddr
        managed object property"
    ::= { cfprFabricMulticastPolicyEntry 9 }

cfprFabricMulticastPolicyQuerierState OBJECT-TYPE
    SYNTAX       CfprFabricQuerierType
    MAX-ACCESS   read-only
    STATUS       current
    DESCRIPTION
        "Cisco Firepower fabric:MulticastPolicy:querierState
        managed object property"
    ::= { cfprFabricMulticastPolicyEntry 10 }

cfprFabricMulticastPolicySnoopingState OBJECT-TYPE
    SYNTAX       CfprFabricSnoopingType
    MAX-ACCESS   read-only
    STATUS       current
    DESCRIPTION
        "Cisco Firepower fabric:MulticastPolicy:snoopingState
        managed object property"
    ::= { cfprFabricMulticastPolicyEntry 11 }

cfprFabricNetGroupTable OBJECT-TYPE
    SYNTAX           SEQUENCE OF CfprFabricNetGroupEntry
    MAX-ACCESS       not-accessible
    STATUS           current
    DESCRIPTION
        "Cisco Firepower fabric:NetGroup managed object table"
    ::= { cfprFabricObjects 82 }

cfprFabricNetGroupEntry OBJECT-TYPE
    SYNTAX           CfprFabricNetGroupEntry
    MAX-ACCESS       not-accessible
    STATUS           current
    DESCRIPTION
        "Entry for the cfprFabricNetGroupTable table."
    INDEX { cfprFabricNetGroupInstanceId }
    ::= { cfprFabricNetGroupTable 1 }

CfprFabricNetGroupEntry ::= SEQUENCE {
    cfprFabricNetGroupInstanceId                                     CfprManagedObjectId,
    cfprFabricNetGroupDn                                             CfprManagedObjectDn,
    cfprFabricNetGroupRn                                             SnmpAdminString,
    cfprFabricNetGroupAssigned                                       Gauge32,
    cfprFabricNetGroupAssignmentOrder                                CfprPoolPoolAssignmentOrder,
    cfprFabricNetGroupDescr                                          SnmpAdminString,
    cfprFabricNetGroupId                                             Gauge32,
    cfprFabricNetGroupIntId                                          SnmpAdminString,
    cfprFabricNetGroupName                                           SnmpAdminString,
    cfprFabricNetGroupNativeNet                                      SnmpAdminString,
    cfprFabricNetGroupNativeNetDn                                    SnmpAdminString,
    cfprFabricNetGroupOwner                                          CfprFabricOwner,
    cfprFabricNetGroupPeerDn                                         SnmpAdminString,
    cfprFabricNetGroupPolicyLevel                                    Gauge32,
    cfprFabricNetGroupPolicyOwner                                    CfprPolicyPolicyOwner,
    cfprFabricNetGroupSize                                           Gauge32,
    cfprFabricNetGroupSwitchId                                       CfprFabricNetGroupSwitchId,
    cfprFabricNetGroupType                                           CfprFabricNetGroupType
}

cfprFabricNetGroupInstanceId OBJECT-TYPE
    SYNTAX       CfprManagedObjectId
    MAX-ACCESS   not-accessible
    STATUS       current
    DESCRIPTION
        "Instance identifier of the managed object."
    ::= { cfprFabricNetGroupEntry 1 }

cfprFabricNetGroupDn OBJECT-TYPE
    SYNTAX       CfprManagedObjectDn
    MAX-ACCESS   read-only
    STATUS       current
    DESCRIPTION
        "Cisco Firepower fabric:NetGroup:dn managed object property"
    ::= { cfprFabricNetGroupEntry 2 }

cfprFabricNetGroupRn OBJECT-TYPE
    SYNTAX       SnmpAdminString
    MAX-ACCESS   read-only
    STATUS       current
    DESCRIPTION
        "Cisco Firepower fabric:NetGroup:rn managed object property"
    ::= { cfprFabricNetGroupEntry 3 }

cfprFabricNetGroupAssigned OBJECT-TYPE
    SYNTAX       Gauge32
    MAX-ACCESS   read-only
    STATUS       current
    DESCRIPTION
        "Cisco Firepower fabric:NetGroup:assigned managed object property"
    ::= { cfprFabricNetGroupEntry 4 }

cfprFabricNetGroupAssignmentOrder OBJECT-TYPE
    SYNTAX       CfprPoolPoolAssignmentOrder
    MAX-ACCESS   read-only
    STATUS       current
    DESCRIPTION
        "Cisco Firepower fabric:NetGroup:assignmentOrder
        managed object property"
    ::= { cfprFabricNetGroupEntry 5 }

cfprFabricNetGroupDescr OBJECT-TYPE
    SYNTAX       SnmpAdminString
    MAX-ACCESS   read-only
    STATUS       current
    DESCRIPTION
        "Cisco Firepower fabric:NetGroup:descr managed object property"
    ::= { cfprFabricNetGroupEntry 6 }

cfprFabricNetGroupId OBJECT-TYPE
    SYNTAX       Gauge32
    MAX-ACCESS   read-only
    STATUS       current
    DESCRIPTION
        "Cisco Firepower fabric:NetGroup:id managed object property"
    ::= { cfprFabricNetGroupEntry 7 }

cfprFabricNetGroupIntId OBJECT-TYPE
    SYNTAX       SnmpAdminString
    MAX-ACCESS   read-only
    STATUS       current
    DESCRIPTION
        "Cisco Firepower fabric:NetGroup:intId managed object property"
    ::= { cfprFabricNetGroupEntry 8 }

cfprFabricNetGroupName OBJECT-TYPE
    SYNTAX       SnmpAdminString
    MAX-ACCESS   read-only
    STATUS       current
    DESCRIPTION
        "Cisco Firepower fabric:NetGroup:name managed object property"
    ::= { cfprFabricNetGroupEntry 9 }

cfprFabricNetGroupNativeNet OBJECT-TYPE
    SYNTAX       SnmpAdminString
    MAX-ACCESS   read-only
    STATUS       current
    DESCRIPTION
        "Cisco Firepower fabric:NetGroup:nativeNet managed
        object property"
    ::= { cfprFabricNetGroupEntry 10 }

cfprFabricNetGroupNativeNetDn OBJECT-TYPE
    SYNTAX       SnmpAdminString
    MAX-ACCESS   read-only
    STATUS       current
    DESCRIPTION
        "Cisco Firepower fabric:NetGroup:nativeNetDn managed
        object property"
    ::= { cfprFabricNetGroupEntry 11 }

cfprFabricNetGroupOwner OBJECT-TYPE
    SYNTAX       CfprFabricOwner
    MAX-ACCESS   read-only
    STATUS       current
    DESCRIPTION
        "Cisco Firepower fabric:NetGroup:owner managed object property"
    ::= { cfprFabricNetGroupEntry 12 }

cfprFabricNetGroupPeerDn OBJECT-TYPE
    SYNTAX       SnmpAdminString
    MAX-ACCESS   read-only
    STATUS       current
    DESCRIPTION
        "Cisco Firepower fabric:NetGroup:peerDn managed object property"
    ::= { cfprFabricNetGroupEntry 13 }

cfprFabricNetGroupPolicyLevel OBJECT-TYPE
    SYNTAX       Gauge32
    MAX-ACCESS   read-only
    STATUS       current
    DESCRIPTION
        "Cisco Firepower fabric:NetGroup:policyLevel managed
        object property"
    ::= { cfprFabricNetGroupEntry 14 }

cfprFabricNetGroupPolicyOwner OBJECT-TYPE
    SYNTAX       CfprPolicyPolicyOwner
    MAX-ACCESS   read-only
    STATUS       current
    DESCRIPTION
        "Cisco Firepower fabric:NetGroup:policyOwner managed
        object property"
    ::= { cfprFabricNetGroupEntry 15 }

cfprFabricNetGroupSize OBJECT-TYPE
    SYNTAX       Gauge32
    MAX-ACCESS   read-only
    STATUS       current
    DESCRIPTION
        "Cisco Firepower fabric:NetGroup:size managed object property"
    ::= { cfprFabricNetGroupEntry 16 }

cfprFabricNetGroupSwitchId OBJECT-TYPE
    SYNTAX       CfprFabricNetGroupSwitchId
    MAX-ACCESS   read-only
    STATUS       current
    DESCRIPTION
        "Cisco Firepower fabric:NetGroup:switchId managed object property"
    ::= { cfprFabricNetGroupEntry 17 }

cfprFabricNetGroupType OBJECT-TYPE
    SYNTAX       CfprFabricNetGroupType
    MAX-ACCESS   read-only
    STATUS       current
    DESCRIPTION
        "Cisco Firepower fabric:NetGroup:type managed object property"
    ::= { cfprFabricNetGroupEntry 18 }

cfprFabricNetflowCollectorTable OBJECT-TYPE
    SYNTAX           SEQUENCE OF CfprFabricNetflowCollectorEntry
    MAX-ACCESS       not-accessible
    STATUS           current
    DESCRIPTION
        "Cisco Firepower fabric:NetflowCollector managed object table"
    ::= { cfprFabricObjects 83 }

cfprFabricNetflowCollectorEntry OBJECT-TYPE
    SYNTAX           CfprFabricNetflowCollectorEntry
    MAX-ACCESS       not-accessible
    STATUS           current
    DESCRIPTION
        "Entry for the cfprFabricNetflowCollectorTable table."
    INDEX { cfprFabricNetflowCollectorInstanceId }
    ::= { cfprFabricNetflowCollectorTable 1 }

CfprFabricNetflowCollectorEntry ::= SEQUENCE {
    cfprFabricNetflowCollectorInstanceId                             CfprManagedObjectId,
    cfprFabricNetflowCollectorDn                                     CfprManagedObjectDn,
    cfprFabricNetflowCollectorRn                                     SnmpAdminString,
    cfprFabricNetflowCollectorDescr                                  SnmpAdminString,
    cfprFabricNetflowCollectorFlowProtocol                           CfprFabricNetflowCollectorFlowProtocol,
    cfprFabricNetflowCollectorId                                     CfprNetworkSwitchId,
    cfprFabricNetflowCollectorLocale                                 CfprFabricFlowMonCollectorLocale,
    cfprFabricNetflowCollectorName                                   SnmpAdminString,
    cfprFabricNetflowCollectorPort                                   Gauge32,
    cfprFabricNetflowCollectorSourceVlan                             SnmpAdminString,
    cfprFabricNetflowCollectorSourceVlanDn                           SnmpAdminString,
    cfprFabricNetflowCollectorTransport                              CfprFabricEthLanFlowMonCollectorTransport,
    cfprFabricNetflowCollectorType                                   CfprFabricLanFlowMonCollectorType
}

cfprFabricNetflowCollectorInstanceId OBJECT-TYPE
    SYNTAX       CfprManagedObjectId
    MAX-ACCESS   not-accessible
    STATUS       current
    DESCRIPTION
        "Instance identifier of the managed object."
    ::= { cfprFabricNetflowCollectorEntry 1 }

cfprFabricNetflowCollectorDn OBJECT-TYPE
    SYNTAX       CfprManagedObjectDn
    MAX-ACCESS   read-only
    STATUS       current
    DESCRIPTION
        "Cisco Firepower fabric:NetflowCollector:dn managed
        object property"
    ::= { cfprFabricNetflowCollectorEntry 2 }

cfprFabricNetflowCollectorRn OBJECT-TYPE
    SYNTAX       SnmpAdminString
    MAX-ACCESS   read-only
    STATUS       current
    DESCRIPTION
        "Cisco Firepower fabric:NetflowCollector:rn managed
        object property"
    ::= { cfprFabricNetflowCollectorEntry 3 }

cfprFabricNetflowCollectorDescr OBJECT-TYPE
    SYNTAX       SnmpAdminString
    MAX-ACCESS   read-only
    STATUS       current
    DESCRIPTION
        "Cisco Firepower fabric:NetflowCollector:descr
        managed object property"
    ::= { cfprFabricNetflowCollectorEntry 4 }

cfprFabricNetflowCollectorFlowProtocol OBJECT-TYPE
    SYNTAX       CfprFabricNetflowCollectorFlowProtocol
    MAX-ACCESS   read-only
    STATUS       current
    DESCRIPTION
        "Cisco Firepower fabric:NetflowCollector:flowProtocol
        managed object property"
    ::= { cfprFabricNetflowCollectorEntry 5 }

cfprFabricNetflowCollectorId OBJECT-TYPE
    SYNTAX       CfprNetworkSwitchId
    MAX-ACCESS   read-only
    STATUS       current
    DESCRIPTION
        "Cisco Firepower fabric:NetflowCollector:id managed
        object property"
    ::= { cfprFabricNetflowCollectorEntry 6 }

cfprFabricNetflowCollectorLocale OBJECT-TYPE
    SYNTAX       CfprFabricFlowMonCollectorLocale
    MAX-ACCESS   read-only
    STATUS       current
    DESCRIPTION
        "Cisco Firepower fabric:NetflowCollector:locale
        managed object property"
    ::= { cfprFabricNetflowCollectorEntry 7 }

cfprFabricNetflowCollectorName OBJECT-TYPE
    SYNTAX       SnmpAdminString
    MAX-ACCESS   read-only
    STATUS       current
    DESCRIPTION
        "Cisco Firepower fabric:NetflowCollector:name managed
        object property"
    ::= { cfprFabricNetflowCollectorEntry 8 }

cfprFabricNetflowCollectorPort OBJECT-TYPE
    SYNTAX       Gauge32
    MAX-ACCESS   read-only
    STATUS       current
    DESCRIPTION
        "Cisco Firepower fabric:NetflowCollector:port managed
        object property"
    ::= { cfprFabricNetflowCollectorEntry 9 }

cfprFabricNetflowCollectorSourceVlan OBJECT-TYPE
    SYNTAX       SnmpAdminString
    MAX-ACCESS   read-only
    STATUS       current
    DESCRIPTION
        "Cisco Firepower fabric:NetflowCollector:sourceVlan
        managed object property"
    ::= { cfprFabricNetflowCollectorEntry 10 }

cfprFabricNetflowCollectorSourceVlanDn OBJECT-TYPE
    SYNTAX       SnmpAdminString
    MAX-ACCESS   read-only
    STATUS       current
    DESCRIPTION
        "Cisco Firepower fabric:NetflowCollector:sourceVlanDn
        managed object property"
    ::= { cfprFabricNetflowCollectorEntry 11 }

cfprFabricNetflowCollectorTransport OBJECT-TYPE
    SYNTAX       CfprFabricEthLanFlowMonCollectorTransport
    MAX-ACCESS   read-only
    STATUS       current
    DESCRIPTION
        "Cisco Firepower fabric:NetflowCollector:transport
        managed object property"
    ::= { cfprFabricNetflowCollectorEntry 12 }

cfprFabricNetflowCollectorType OBJECT-TYPE
    SYNTAX       CfprFabricLanFlowMonCollectorType
    MAX-ACCESS   read-only
    STATUS       current
    DESCRIPTION
        "Cisco Firepower fabric:NetflowCollector:type managed
        object property"
    ::= { cfprFabricNetflowCollectorEntry 13 }

cfprFabricNetflowIPv4AddrTable OBJECT-TYPE
    SYNTAX           SEQUENCE OF CfprFabricNetflowIPv4AddrEntry
    MAX-ACCESS       not-accessible
    STATUS           current
    DESCRIPTION
        "Cisco Firepower fabric:NetflowIPv4Addr managed object table"
    ::= { cfprFabricObjects 84 }

cfprFabricNetflowIPv4AddrEntry OBJECT-TYPE
    SYNTAX           CfprFabricNetflowIPv4AddrEntry
    MAX-ACCESS       not-accessible
    STATUS           current
    DESCRIPTION
        "Entry for the cfprFabricNetflowIPv4AddrTable table."
    INDEX { cfprFabricNetflowIPv4AddrInstanceId }
    ::= { cfprFabricNetflowIPv4AddrTable 1 }

CfprFabricNetflowIPv4AddrEntry ::= SEQUENCE {
    cfprFabricNetflowIPv4AddrInstanceId                              CfprManagedObjectId,
    cfprFabricNetflowIPv4AddrDn                                      CfprManagedObjectDn,
    cfprFabricNetflowIPv4AddrRn                                      SnmpAdminString,
    cfprFabricNetflowIPv4AddrAddr                                    InetAddressIPv4,
    cfprFabricNetflowIPv4AddrDefGw                                   InetAddressIPv4,
    cfprFabricNetflowIPv4AddrFabricId                                CfprNetworkSwitchId,
    cfprFabricNetflowIPv4AddrSubnet                                  InetAddressIPv4
}

cfprFabricNetflowIPv4AddrInstanceId OBJECT-TYPE
    SYNTAX       CfprManagedObjectId
    MAX-ACCESS   not-accessible
    STATUS       current
    DESCRIPTION
        "Instance identifier of the managed object."
    ::= { cfprFabricNetflowIPv4AddrEntry 1 }

cfprFabricNetflowIPv4AddrDn OBJECT-TYPE
    SYNTAX       CfprManagedObjectDn
    MAX-ACCESS   read-only
    STATUS       current
    DESCRIPTION
        "Cisco Firepower fabric:NetflowIPv4Addr:dn managed
        object property"
    ::= { cfprFabricNetflowIPv4AddrEntry 2 }

cfprFabricNetflowIPv4AddrRn OBJECT-TYPE
    SYNTAX       SnmpAdminString
    MAX-ACCESS   read-only
    STATUS       current
    DESCRIPTION
        "Cisco Firepower fabric:NetflowIPv4Addr:rn managed
        object property"
    ::= { cfprFabricNetflowIPv4AddrEntry 3 }

cfprFabricNetflowIPv4AddrAddr OBJECT-TYPE
    SYNTAX       InetAddressIPv4
    MAX-ACCESS   read-only
    STATUS       current
    DESCRIPTION
        "Cisco Firepower fabric:NetflowIPv4Addr:addr managed
        object property"
    ::= { cfprFabricNetflowIPv4AddrEntry 4 }

cfprFabricNetflowIPv4AddrDefGw OBJECT-TYPE
    SYNTAX       InetAddressIPv4
    MAX-ACCESS   read-only
    STATUS       current
    DESCRIPTION
        "Cisco Firepower fabric:NetflowIPv4Addr:defGw managed
        object property"
    ::= { cfprFabricNetflowIPv4AddrEntry 5 }

cfprFabricNetflowIPv4AddrFabricId OBJECT-TYPE
    SYNTAX       CfprNetworkSwitchId
    MAX-ACCESS   read-only
    STATUS       current
    DESCRIPTION
        "Cisco Firepower fabric:NetflowIPv4Addr:fabricId
        managed object property"
    ::= { cfprFabricNetflowIPv4AddrEntry 6 }

cfprFabricNetflowIPv4AddrSubnet OBJECT-TYPE
    SYNTAX       InetAddressIPv4
    MAX-ACCESS   read-only
    STATUS       current
    DESCRIPTION
        "Cisco Firepower fabric:NetflowIPv4Addr:subnet
        managed object property"
    ::= { cfprFabricNetflowIPv4AddrEntry 7 }

cfprFabricNetflowMonExporterTable OBJECT-TYPE
    SYNTAX           SEQUENCE OF CfprFabricNetflowMonExporterEntry
    MAX-ACCESS       not-accessible
    STATUS           current
    DESCRIPTION
        "Cisco Firepower fabric:NetflowMonExporter managed object table"
    ::= { cfprFabricObjects 85 }

cfprFabricNetflowMonExporterEntry OBJECT-TYPE
    SYNTAX           CfprFabricNetflowMonExporterEntry
    MAX-ACCESS       not-accessible
    STATUS           current
    DESCRIPTION
        "Entry for the cfprFabricNetflowMonExporterTable table."
    INDEX { cfprFabricNetflowMonExporterInstanceId }
    ::= { cfprFabricNetflowMonExporterTable 1 }

CfprFabricNetflowMonExporterEntry ::= SEQUENCE {
    cfprFabricNetflowMonExporterInstanceId                           CfprManagedObjectId,
    cfprFabricNetflowMonExporterDn                                   CfprManagedObjectDn,
    cfprFabricNetflowMonExporterRn                                   SnmpAdminString,
    cfprFabricNetflowMonExporterDescr                                SnmpAdminString,
    cfprFabricNetflowMonExporterDscp                                 Gauge32,
    cfprFabricNetflowMonExporterExportInternal                       Gauge32,
    cfprFabricNetflowMonExporterExporterStatsTimeout                 Gauge32,
    cfprFabricNetflowMonExporterFlowExpProfile                       SnmpAdminString,
    cfprFabricNetflowMonExporterFlowMonCollector                     SnmpAdminString,
    cfprFabricNetflowMonExporterIntId                                SnmpAdminString,
    cfprFabricNetflowMonExporterInterfaceTableTimeout                Gauge32,
    cfprFabricNetflowMonExporterName                                 SnmpAdminString,
    cfprFabricNetflowMonExporterOperFlowExpProfile                   SnmpAdminString,
    cfprFabricNetflowMonExporterPolicyLevel                          Gauge32,
    cfprFabricNetflowMonExporterPolicyOwner                          CfprPolicyPolicyOwner,
    cfprFabricNetflowMonExporterProtocol                             CfprFabricNetflowMonExporterProtocol,
    cfprFabricNetflowMonExporterTemplateDataTimeout                  Gauge32,
    cfprFabricNetflowMonExporterTransport                            CfprFabricEthLanFlowMonExporterTransport,
    cfprFabricNetflowMonExporterTransportProtocol                    CfprFabricNFTransport,
    cfprFabricNetflowMonExporterType                                 CfprFabricLanFlowMonExporterType,
    cfprFabricNetflowMonExporterVersion                              CfprFabricNFExporterVersion
}

cfprFabricNetflowMonExporterInstanceId OBJECT-TYPE
    SYNTAX       CfprManagedObjectId
    MAX-ACCESS   not-accessible
    STATUS       current
    DESCRIPTION
        "Instance identifier of the managed object."
    ::= { cfprFabricNetflowMonExporterEntry 1 }

cfprFabricNetflowMonExporterDn OBJECT-TYPE
    SYNTAX       CfprManagedObjectDn
    MAX-ACCESS   read-only
    STATUS       current
    DESCRIPTION
        "Cisco Firepower fabric:NetflowMonExporter:dn managed
        object property"
    ::= { cfprFabricNetflowMonExporterEntry 2 }

cfprFabricNetflowMonExporterRn OBJECT-TYPE
    SYNTAX       SnmpAdminString
    MAX-ACCESS   read-only
    STATUS       current
    DESCRIPTION
        "Cisco Firepower fabric:NetflowMonExporter:rn managed
        object property"
    ::= { cfprFabricNetflowMonExporterEntry 3 }

cfprFabricNetflowMonExporterDescr OBJECT-TYPE
    SYNTAX       SnmpAdminString
    MAX-ACCESS   read-only
    STATUS       current
    DESCRIPTION
        "Cisco Firepower fabric:NetflowMonExporter:descr
        managed object property"
    ::= { cfprFabricNetflowMonExporterEntry 4 }

cfprFabricNetflowMonExporterDscp OBJECT-TYPE
    SYNTAX       Gauge32
    MAX-ACCESS   read-only
    STATUS       current
    DESCRIPTION
        "Cisco Firepower fabric:NetflowMonExporter:dscp
        managed object property"
    ::= { cfprFabricNetflowMonExporterEntry 5 }

cfprFabricNetflowMonExporterExportInternal OBJECT-TYPE
    SYNTAX       Gauge32
    MAX-ACCESS   read-only
    STATUS       current
    DESCRIPTION
        "Cisco Firepower fabric:NetflowMonExporter:exportInternal
        managed object property"
    ::= { cfprFabricNetflowMonExporterEntry 6 }

cfprFabricNetflowMonExporterExporterStatsTimeout OBJECT-TYPE
    SYNTAX       Gauge32
    MAX-ACCESS   read-only
    STATUS       current
    DESCRIPTION
        "Cisco Firepower fabric:NetflowMonExporter:exporterStatsTimeout
        managed object property"
    ::= { cfprFabricNetflowMonExporterEntry 7 }

cfprFabricNetflowMonExporterFlowExpProfile OBJECT-TYPE
    SYNTAX       SnmpAdminString
    MAX-ACCESS   read-only
    STATUS       current
    DESCRIPTION
        "Cisco Firepower fabric:NetflowMonExporter:flowExpProfile
        managed object property"
    ::= { cfprFabricNetflowMonExporterEntry 8 }

cfprFabricNetflowMonExporterFlowMonCollector OBJECT-TYPE
    SYNTAX       SnmpAdminString
    MAX-ACCESS   read-only
    STATUS       current
    DESCRIPTION
        "Cisco Firepower fabric:NetflowMonExporter:flowMonCollector
        managed object property"
    ::= { cfprFabricNetflowMonExporterEntry 9 }

cfprFabricNetflowMonExporterIntId OBJECT-TYPE
    SYNTAX       SnmpAdminString
    MAX-ACCESS   read-only
    STATUS       current
    DESCRIPTION
        "Cisco Firepower fabric:NetflowMonExporter:intId
        managed object property"
    ::= { cfprFabricNetflowMonExporterEntry 10 }

cfprFabricNetflowMonExporterInterfaceTableTimeout OBJECT-TYPE
    SYNTAX       Gauge32
    MAX-ACCESS   read-only
    STATUS       current
    DESCRIPTION
        "Cisco Firepower fabric:NetflowMonExporter:interfaceTableTimeout
        managed object property"
    ::= { cfprFabricNetflowMonExporterEntry 11 }

cfprFabricNetflowMonExporterName OBJECT-TYPE
    SYNTAX       SnmpAdminString
    MAX-ACCESS   read-only
    STATUS       current
    DESCRIPTION
        "Cisco Firepower fabric:NetflowMonExporter:name
        managed object property"
    ::= { cfprFabricNetflowMonExporterEntry 12 }

cfprFabricNetflowMonExporterOperFlowExpProfile OBJECT-TYPE
    SYNTAX       SnmpAdminString
    MAX-ACCESS   read-only
    STATUS       current
    DESCRIPTION
        "Cisco Firepower fabric:NetflowMonExporter:operFlowExpProfile
        managed object property"
    ::= { cfprFabricNetflowMonExporterEntry 13 }

cfprFabricNetflowMonExporterPolicyLevel OBJECT-TYPE
    SYNTAX       Gauge32
    MAX-ACCESS   read-only
    STATUS       current
    DESCRIPTION
        "Cisco Firepower fabric:NetflowMonExporter:policyLevel
        managed object property"
    ::= { cfprFabricNetflowMonExporterEntry 14 }

cfprFabricNetflowMonExporterPolicyOwner OBJECT-TYPE
    SYNTAX       CfprPolicyPolicyOwner
    MAX-ACCESS   read-only
    STATUS       current
    DESCRIPTION
        "Cisco Firepower fabric:NetflowMonExporter:policyOwner
        managed object property"
    ::= { cfprFabricNetflowMonExporterEntry 15 }

cfprFabricNetflowMonExporterProtocol OBJECT-TYPE
    SYNTAX       CfprFabricNetflowMonExporterProtocol
    MAX-ACCESS   read-only
    STATUS       current
    DESCRIPTION
        "Cisco Firepower fabric:NetflowMonExporter:protocol
        managed object property"
    ::= { cfprFabricNetflowMonExporterEntry 16 }

cfprFabricNetflowMonExporterTemplateDataTimeout OBJECT-TYPE
    SYNTAX       Gauge32
    MAX-ACCESS   read-only
    STATUS       current
    DESCRIPTION
        "Cisco Firepower fabric:NetflowMonExporter:templateDataTimeout
        managed object property"
    ::= { cfprFabricNetflowMonExporterEntry 17 }

cfprFabricNetflowMonExporterTransport OBJECT-TYPE
    SYNTAX       CfprFabricEthLanFlowMonExporterTransport
    MAX-ACCESS   read-only
    STATUS       current
    DESCRIPTION
        "Cisco Firepower fabric:NetflowMonExporter:transport
        managed object property"
    ::= { cfprFabricNetflowMonExporterEntry 18 }

cfprFabricNetflowMonExporterTransportProtocol OBJECT-TYPE
    SYNTAX       CfprFabricNFTransport
    MAX-ACCESS   read-only
    STATUS       current
    DESCRIPTION
        "Cisco Firepower fabric:NetflowMonExporter:transportProtocol
        managed object property"
    ::= { cfprFabricNetflowMonExporterEntry 19 }

cfprFabricNetflowMonExporterType OBJECT-TYPE
    SYNTAX       CfprFabricLanFlowMonExporterType
    MAX-ACCESS   read-only
    STATUS       current
    DESCRIPTION
        "Cisco Firepower fabric:NetflowMonExporter:type
        managed object property"
    ::= { cfprFabricNetflowMonExporterEntry 20 }

cfprFabricNetflowMonExporterVersion OBJECT-TYPE
    SYNTAX       CfprFabricNFExporterVersion
    MAX-ACCESS   read-only
    STATUS       current
    DESCRIPTION
        "Cisco Firepower fabric:NetflowMonExporter:version
        managed object property"
    ::= { cfprFabricNetflowMonExporterEntry 21 }

cfprFabricNetflowMonExporterRefTable OBJECT-TYPE
    SYNTAX           SEQUENCE OF CfprFabricNetflowMonExporterRefEntry
    MAX-ACCESS       not-accessible
    STATUS           current
    DESCRIPTION
        "Cisco Firepower fabric:NetflowMonExporterRef managed
        object table"
    ::= { cfprFabricObjects 86 }

cfprFabricNetflowMonExporterRefEntry OBJECT-TYPE
    SYNTAX           CfprFabricNetflowMonExporterRefEntry
    MAX-ACCESS       not-accessible
    STATUS           current
    DESCRIPTION
        "Entry for the cfprFabricNetflowMonExporterRefTable table."
    INDEX { cfprFabricNetflowMonExporterRefInstanceId }
    ::= { cfprFabricNetflowMonExporterRefTable 1 }

CfprFabricNetflowMonExporterRefEntry ::= SEQUENCE {
    cfprFabricNetflowMonExporterRefInstanceId                        CfprManagedObjectId,
    cfprFabricNetflowMonExporterRefDn                                CfprManagedObjectDn,
    cfprFabricNetflowMonExporterRefRn                                SnmpAdminString,
    cfprFabricNetflowMonExporterRefIndex                             Gauge32,
    cfprFabricNetflowMonExporterRefNfMonExporterName                 SnmpAdminString,
    cfprFabricNetflowMonExporterRefOperNfMonExporterName             SnmpAdminString,
    cfprFabricNetflowMonExporterRefSwitchId                          CfprNetworkSwitchId
}

cfprFabricNetflowMonExporterRefInstanceId OBJECT-TYPE
    SYNTAX       CfprManagedObjectId
    MAX-ACCESS   not-accessible
    STATUS       current
    DESCRIPTION
        "Instance identifier of the managed object."
    ::= { cfprFabricNetflowMonExporterRefEntry 1 }

cfprFabricNetflowMonExporterRefDn OBJECT-TYPE
    SYNTAX       CfprManagedObjectDn
    MAX-ACCESS   read-only
    STATUS       current
    DESCRIPTION
        "Cisco Firepower fabric:NetflowMonExporterRef:dn
        managed object property"
    ::= { cfprFabricNetflowMonExporterRefEntry 2 }

cfprFabricNetflowMonExporterRefRn OBJECT-TYPE
    SYNTAX       SnmpAdminString
    MAX-ACCESS   read-only
    STATUS       current
    DESCRIPTION
        "Cisco Firepower fabric:NetflowMonExporterRef:rn
        managed object property"
    ::= { cfprFabricNetflowMonExporterRefEntry 3 }

cfprFabricNetflowMonExporterRefIndex OBJECT-TYPE
    SYNTAX       Gauge32
    MAX-ACCESS   read-only
    STATUS       current
    DESCRIPTION
        "Cisco Firepower fabric:NetflowMonExporterRef:index
        managed object property"
    ::= { cfprFabricNetflowMonExporterRefEntry 4 }

cfprFabricNetflowMonExporterRefNfMonExporterName OBJECT-TYPE
    SYNTAX       SnmpAdminString
    MAX-ACCESS   read-only
    STATUS       current
    DESCRIPTION
        "Cisco Firepower fabric:NetflowMonExporterRef:nfMonExporterName
        managed object property"
    ::= { cfprFabricNetflowMonExporterRefEntry 5 }

cfprFabricNetflowMonExporterRefOperNfMonExporterName OBJECT-TYPE
    SYNTAX       SnmpAdminString
    MAX-ACCESS   read-only
    STATUS       current
    DESCRIPTION
        "Cisco Firepower fabric:NetflowMonExporterRef:operNfMonExporterNam
        e managed object property"
    ::= { cfprFabricNetflowMonExporterRefEntry 6 }

cfprFabricNetflowMonExporterRefSwitchId OBJECT-TYPE
    SYNTAX       CfprNetworkSwitchId
    MAX-ACCESS   read-only
    STATUS       current
    DESCRIPTION
        "Cisco Firepower fabric:NetflowMonExporterRef:switchId
        managed object property"
    ::= { cfprFabricNetflowMonExporterRefEntry 7 }

cfprFabricNetflowMonSessionTable OBJECT-TYPE
    SYNTAX           SEQUENCE OF CfprFabricNetflowMonSessionEntry
    MAX-ACCESS       not-accessible
    STATUS           current
    DESCRIPTION
        "Cisco Firepower fabric:NetflowMonSession managed object table"
    ::= { cfprFabricObjects 87 }

cfprFabricNetflowMonSessionEntry OBJECT-TYPE
    SYNTAX           CfprFabricNetflowMonSessionEntry
    MAX-ACCESS       not-accessible
    STATUS           current
    DESCRIPTION
        "Entry for the cfprFabricNetflowMonSessionTable table."
    INDEX { cfprFabricNetflowMonSessionInstanceId }
    ::= { cfprFabricNetflowMonSessionTable 1 }

CfprFabricNetflowMonSessionEntry ::= SEQUENCE {
    cfprFabricNetflowMonSessionInstanceId                            CfprManagedObjectId,
    cfprFabricNetflowMonSessionDn                                    CfprManagedObjectDn,
    cfprFabricNetflowMonSessionRn                                    SnmpAdminString,
    cfprFabricNetflowMonSessionAdminState                            CfprFabricNetflowMonSessionAdminState,
    cfprFabricNetflowMonSessionConfigFailReason                      SnmpAdminString,
    cfprFabricNetflowMonSessionConfigQualifier                       CfprFabricNetflowConfigIssues,
    cfprFabricNetflowMonSessionDescr                                 SnmpAdminString,
    cfprFabricNetflowMonSessionId                                    CfprNetworkSwitchId,
    cfprFabricNetflowMonSessionIsConfigSuccess                       TruthValue,
    cfprFabricNetflowMonSessionLocale                                CfprFabricExternalLocale,
    cfprFabricNetflowMonSessionName                                  SnmpAdminString,
    cfprFabricNetflowMonSessionProtocol                              CfprFabricNetflowMonSessionProtocol,
    cfprFabricNetflowMonSessionSession                               Gauge32,
    cfprFabricNetflowMonSessionTransport                             CfprFabricEthLanFlowMonTransport,
    cfprFabricNetflowMonSessionType                                  CfprFabricLanFlowMonType
}

cfprFabricNetflowMonSessionInstanceId OBJECT-TYPE
    SYNTAX       CfprManagedObjectId
    MAX-ACCESS   not-accessible
    STATUS       current
    DESCRIPTION
        "Instance identifier of the managed object."
    ::= { cfprFabricNetflowMonSessionEntry 1 }

cfprFabricNetflowMonSessionDn OBJECT-TYPE
    SYNTAX       CfprManagedObjectDn
    MAX-ACCESS   read-only
    STATUS       current
    DESCRIPTION
        "Cisco Firepower fabric:NetflowMonSession:dn managed
        object property"
    ::= { cfprFabricNetflowMonSessionEntry 2 }

cfprFabricNetflowMonSessionRn OBJECT-TYPE
    SYNTAX       SnmpAdminString
    MAX-ACCESS   read-only
    STATUS       current
    DESCRIPTION
        "Cisco Firepower fabric:NetflowMonSession:rn managed
        object property"
    ::= { cfprFabricNetflowMonSessionEntry 3 }

cfprFabricNetflowMonSessionAdminState OBJECT-TYPE
    SYNTAX       CfprFabricNetflowMonSessionAdminState
    MAX-ACCESS   read-only
    STATUS       current
    DESCRIPTION
        "Cisco Firepower fabric:NetflowMonSession:adminState
        managed object property"
    ::= { cfprFabricNetflowMonSessionEntry 4 }

cfprFabricNetflowMonSessionConfigFailReason OBJECT-TYPE
    SYNTAX       SnmpAdminString
    MAX-ACCESS   read-only
    STATUS       current
    DESCRIPTION
        "Cisco Firepower fabric:NetflowMonSession:configFailReason
        managed object property"
    ::= { cfprFabricNetflowMonSessionEntry 5 }

cfprFabricNetflowMonSessionConfigQualifier OBJECT-TYPE
    SYNTAX       CfprFabricNetflowConfigIssues
    MAX-ACCESS   read-only
    STATUS       current
    DESCRIPTION
        "Cisco Firepower fabric:NetflowMonSession:configQualifier
        managed object property"
    ::= { cfprFabricNetflowMonSessionEntry 6 }

cfprFabricNetflowMonSessionDescr OBJECT-TYPE
    SYNTAX       SnmpAdminString
    MAX-ACCESS   read-only
    STATUS       current
    DESCRIPTION
        "Cisco Firepower fabric:NetflowMonSession:descr
        managed object property"
    ::= { cfprFabricNetflowMonSessionEntry 7 }

cfprFabricNetflowMonSessionId OBJECT-TYPE
    SYNTAX       CfprNetworkSwitchId
    MAX-ACCESS   read-only
    STATUS       current
    DESCRIPTION
        "Cisco Firepower fabric:NetflowMonSession:id managed
        object property"
    ::= { cfprFabricNetflowMonSessionEntry 8 }

cfprFabricNetflowMonSessionIsConfigSuccess OBJECT-TYPE
    SYNTAX       TruthValue
    MAX-ACCESS   read-only
    STATUS       current
    DESCRIPTION
        "Cisco Firepower fabric:NetflowMonSession:isConfigSuccess
        managed object property"
    ::= { cfprFabricNetflowMonSessionEntry 9 }

cfprFabricNetflowMonSessionLocale OBJECT-TYPE
    SYNTAX       CfprFabricExternalLocale
    MAX-ACCESS   read-only
    STATUS       current
    DESCRIPTION
        "Cisco Firepower fabric:NetflowMonSession:locale
        managed object property"
    ::= { cfprFabricNetflowMonSessionEntry 10 }

cfprFabricNetflowMonSessionName OBJECT-TYPE
    SYNTAX       SnmpAdminString
    MAX-ACCESS   read-only
    STATUS       current
    DESCRIPTION
        "Cisco Firepower fabric:NetflowMonSession:name
        managed object property"
    ::= { cfprFabricNetflowMonSessionEntry 11 }

cfprFabricNetflowMonSessionProtocol OBJECT-TYPE
    SYNTAX       CfprFabricNetflowMonSessionProtocol
    MAX-ACCESS   read-only
    STATUS       current
    DESCRIPTION
        "Cisco Firepower fabric:NetflowMonSession:protocol
        managed object property"
    ::= { cfprFabricNetflowMonSessionEntry 12 }

cfprFabricNetflowMonSessionSession OBJECT-TYPE
    SYNTAX       Gauge32
    MAX-ACCESS   read-only
    STATUS       current
    DESCRIPTION
        "Cisco Firepower fabric:NetflowMonSession:session
        managed object property"
    ::= { cfprFabricNetflowMonSessionEntry 13 }

cfprFabricNetflowMonSessionTransport OBJECT-TYPE
    SYNTAX       CfprFabricEthLanFlowMonTransport
    MAX-ACCESS   read-only
    STATUS       current
    DESCRIPTION
        "Cisco Firepower fabric:NetflowMonSession:transport
        managed object property"
    ::= { cfprFabricNetflowMonSessionEntry 14 }

cfprFabricNetflowMonSessionType OBJECT-TYPE
    SYNTAX       CfprFabricLanFlowMonType
    MAX-ACCESS   read-only
    STATUS       current
    DESCRIPTION
        "Cisco Firepower fabric:NetflowMonSession:type
        managed object property"
    ::= { cfprFabricNetflowMonSessionEntry 15 }

cfprFabricNetflowMonSrcEpTable OBJECT-TYPE
    SYNTAX           SEQUENCE OF CfprFabricNetflowMonSrcEpEntry
    MAX-ACCESS       not-accessible
    STATUS           current
    DESCRIPTION
        "Cisco Firepower fabric:NetflowMonSrcEp managed object table"
    ::= { cfprFabricObjects 88 }

cfprFabricNetflowMonSrcEpEntry OBJECT-TYPE
    SYNTAX           CfprFabricNetflowMonSrcEpEntry
    MAX-ACCESS       not-accessible
    STATUS           current
    DESCRIPTION
        "Entry for the cfprFabricNetflowMonSrcEpTable table."
    INDEX { cfprFabricNetflowMonSrcEpInstanceId }
    ::= { cfprFabricNetflowMonSrcEpTable 1 }

CfprFabricNetflowMonSrcEpEntry ::= SEQUENCE {
    cfprFabricNetflowMonSrcEpInstanceId                              CfprManagedObjectId,
    cfprFabricNetflowMonSrcEpDn                                      CfprManagedObjectDn,
    cfprFabricNetflowMonSrcEpRn                                      SnmpAdminString,
    cfprFabricNetflowMonSrcEpName                                    SnmpAdminString,
    cfprFabricNetflowMonSrcEpProtocol                                CfprFabricNetflowMonSrcEpProtocol,
    cfprFabricNetflowMonSrcEpSession                                 Gauge32,
    cfprFabricNetflowMonSrcEpTransport                               CfprFabricEthLanFlowMonSrcEpTransport,
    cfprFabricNetflowMonSrcEpType                                    CfprFabricLanFlowMonSrcEpType
}

cfprFabricNetflowMonSrcEpInstanceId OBJECT-TYPE
    SYNTAX       CfprManagedObjectId
    MAX-ACCESS   not-accessible
    STATUS       current
    DESCRIPTION
        "Instance identifier of the managed object."
    ::= { cfprFabricNetflowMonSrcEpEntry 1 }

cfprFabricNetflowMonSrcEpDn OBJECT-TYPE
    SYNTAX       CfprManagedObjectDn
    MAX-ACCESS   read-only
    STATUS       current
    DESCRIPTION
        "Cisco Firepower fabric:NetflowMonSrcEp:dn managed
        object property"
    ::= { cfprFabricNetflowMonSrcEpEntry 2 }

cfprFabricNetflowMonSrcEpRn OBJECT-TYPE
    SYNTAX       SnmpAdminString
    MAX-ACCESS   read-only
    STATUS       current
    DESCRIPTION
        "Cisco Firepower fabric:NetflowMonSrcEp:rn managed
        object property"
    ::= { cfprFabricNetflowMonSrcEpEntry 3 }

cfprFabricNetflowMonSrcEpName OBJECT-TYPE
    SYNTAX       SnmpAdminString
    MAX-ACCESS   read-only
    STATUS       current
    DESCRIPTION
        "Cisco Firepower fabric:NetflowMonSrcEp:name managed
        object property"
    ::= { cfprFabricNetflowMonSrcEpEntry 4 }

cfprFabricNetflowMonSrcEpProtocol OBJECT-TYPE
    SYNTAX       CfprFabricNetflowMonSrcEpProtocol
    MAX-ACCESS   read-only
    STATUS       current
    DESCRIPTION
        "Cisco Firepower fabric:NetflowMonSrcEp:protocol
        managed object property"
    ::= { cfprFabricNetflowMonSrcEpEntry 5 }

cfprFabricNetflowMonSrcEpSession OBJECT-TYPE
    SYNTAX       Gauge32
    MAX-ACCESS   read-only
    STATUS       current
    DESCRIPTION
        "Cisco Firepower fabric:NetflowMonSrcEp:session
        managed object property"
    ::= { cfprFabricNetflowMonSrcEpEntry 6 }

cfprFabricNetflowMonSrcEpTransport OBJECT-TYPE
    SYNTAX       CfprFabricEthLanFlowMonSrcEpTransport
    MAX-ACCESS   read-only
    STATUS       current
    DESCRIPTION
        "Cisco Firepower fabric:NetflowMonSrcEp:transport
        managed object property"
    ::= { cfprFabricNetflowMonSrcEpEntry 7 }

cfprFabricNetflowMonSrcEpType OBJECT-TYPE
    SYNTAX       CfprFabricLanFlowMonSrcEpType
    MAX-ACCESS   read-only
    STATUS       current
    DESCRIPTION
        "Cisco Firepower fabric:NetflowMonSrcEp:type managed
        object property"
    ::= { cfprFabricNetflowMonSrcEpEntry 8 }

cfprFabricNetflowMonSrcRefTable OBJECT-TYPE
    SYNTAX           SEQUENCE OF CfprFabricNetflowMonSrcRefEntry
    MAX-ACCESS       not-accessible
    STATUS           current
    DESCRIPTION
        "Cisco Firepower fabric:NetflowMonSrcRef managed object table"
    ::= { cfprFabricObjects 89 }

cfprFabricNetflowMonSrcRefEntry OBJECT-TYPE
    SYNTAX           CfprFabricNetflowMonSrcRefEntry
    MAX-ACCESS       not-accessible
    STATUS           current
    DESCRIPTION
        "Entry for the cfprFabricNetflowMonSrcRefTable table."
    INDEX { cfprFabricNetflowMonSrcRefInstanceId }
    ::= { cfprFabricNetflowMonSrcRefTable 1 }

CfprFabricNetflowMonSrcRefEntry ::= SEQUENCE {
    cfprFabricNetflowMonSrcRefInstanceId                             CfprManagedObjectId,
    cfprFabricNetflowMonSrcRefDn                                     CfprManagedObjectDn,
    cfprFabricNetflowMonSrcRefRn                                     SnmpAdminString,
    cfprFabricNetflowMonSrcRefId                                     Unsigned64,
    cfprFabricNetflowMonSrcRefProtocol                               CfprFabricNetflowMonSrcRefProtocol,
    cfprFabricNetflowMonSrcRefSourceDn                               SnmpAdminString,
    cfprFabricNetflowMonSrcRefSourceType                             CfprFabricEthFlowMonSourceType,
    cfprFabricNetflowMonSrcRefType                                   CfprFabricEthFlowMonSrcRefType
}

cfprFabricNetflowMonSrcRefInstanceId OBJECT-TYPE
    SYNTAX       CfprManagedObjectId
    MAX-ACCESS   not-accessible
    STATUS       current
    DESCRIPTION
        "Instance identifier of the managed object."
    ::= { cfprFabricNetflowMonSrcRefEntry 1 }

cfprFabricNetflowMonSrcRefDn OBJECT-TYPE
    SYNTAX       CfprManagedObjectDn
    MAX-ACCESS   read-only
    STATUS       current
    DESCRIPTION
        "Cisco Firepower fabric:NetflowMonSrcRef:dn managed
        object property"
    ::= { cfprFabricNetflowMonSrcRefEntry 2 }

cfprFabricNetflowMonSrcRefRn OBJECT-TYPE
    SYNTAX       SnmpAdminString
    MAX-ACCESS   read-only
    STATUS       current
    DESCRIPTION
        "Cisco Firepower fabric:NetflowMonSrcRef:rn managed
        object property"
    ::= { cfprFabricNetflowMonSrcRefEntry 3 }

cfprFabricNetflowMonSrcRefId OBJECT-TYPE
    SYNTAX       Unsigned64
    MAX-ACCESS   read-only
    STATUS       current
    DESCRIPTION
        "Cisco Firepower fabric:NetflowMonSrcRef:id managed
        object property"
    ::= { cfprFabricNetflowMonSrcRefEntry 4 }

cfprFabricNetflowMonSrcRefProtocol OBJECT-TYPE
    SYNTAX       CfprFabricNetflowMonSrcRefProtocol
    MAX-ACCESS   read-only
    STATUS       current
    DESCRIPTION
        "Cisco Firepower fabric:NetflowMonSrcRef:protocol
        managed object property"
    ::= { cfprFabricNetflowMonSrcRefEntry 5 }

cfprFabricNetflowMonSrcRefSourceDn OBJECT-TYPE
    SYNTAX       SnmpAdminString
    MAX-ACCESS   read-only
    STATUS       current
    DESCRIPTION
        "Cisco Firepower fabric:NetflowMonSrcRef:sourceDn
        managed object property"
    ::= { cfprFabricNetflowMonSrcRefEntry 6 }

cfprFabricNetflowMonSrcRefSourceType OBJECT-TYPE
    SYNTAX       CfprFabricEthFlowMonSourceType
    MAX-ACCESS   read-only
    STATUS       current
    DESCRIPTION
        "Cisco Firepower fabric:NetflowMonSrcRef:sourceType
        managed object property"
    ::= { cfprFabricNetflowMonSrcRefEntry 7 }

cfprFabricNetflowMonSrcRefType OBJECT-TYPE
    SYNTAX       CfprFabricEthFlowMonSrcRefType
    MAX-ACCESS   read-only
    STATUS       current
    DESCRIPTION
        "Cisco Firepower fabric:NetflowMonSrcRef:type managed
        object property"
    ::= { cfprFabricNetflowMonSrcRefEntry 8 }

cfprFabricNetflowMonitorTable OBJECT-TYPE
    SYNTAX           SEQUENCE OF CfprFabricNetflowMonitorEntry
    MAX-ACCESS       not-accessible
    STATUS           current
    DESCRIPTION
        "Cisco Firepower fabric:NetflowMonitor managed object table"
    ::= { cfprFabricObjects 90 }

cfprFabricNetflowMonitorEntry OBJECT-TYPE
    SYNTAX           CfprFabricNetflowMonitorEntry
    MAX-ACCESS       not-accessible
    STATUS           current
    DESCRIPTION
        "Entry for the cfprFabricNetflowMonitorTable table."
    INDEX { cfprFabricNetflowMonitorInstanceId }
    ::= { cfprFabricNetflowMonitorTable 1 }

CfprFabricNetflowMonitorEntry ::= SEQUENCE {
    cfprFabricNetflowMonitorInstanceId                               CfprManagedObjectId,
    cfprFabricNetflowMonitorDn                                       CfprManagedObjectDn,
    cfprFabricNetflowMonitorRn                                       SnmpAdminString,
    cfprFabricNetflowMonitorDescr                                    SnmpAdminString,
    cfprFabricNetflowMonitorFlowMonProtocol                          CfprFabricNetflowMonitorFlowMonProtocol,
    cfprFabricNetflowMonitorFlowMonRecordDef                         SnmpAdminString,
    cfprFabricNetflowMonitorFlowTimeoutPolicy                        SnmpAdminString,
    cfprFabricNetflowMonitorIntId                                    SnmpAdminString,
    cfprFabricNetflowMonitorName                                     SnmpAdminString,
    cfprFabricNetflowMonitorOperFlowMonRecordDef                     SnmpAdminString,
    cfprFabricNetflowMonitorOperFlowTimeoutPolicy                    SnmpAdminString,
    cfprFabricNetflowMonitorPolicyLevel                              Gauge32,
    cfprFabricNetflowMonitorPolicyOwner                              CfprPolicyPolicyOwner,
    cfprFabricNetflowMonitorTransport                                CfprFabricEthLanFlowMonitorTransport,
    cfprFabricNetflowMonitorType                                     CfprFabricLanFlowMonitorType
}

cfprFabricNetflowMonitorInstanceId OBJECT-TYPE
    SYNTAX       CfprManagedObjectId
    MAX-ACCESS   not-accessible
    STATUS       current
    DESCRIPTION
        "Instance identifier of the managed object."
    ::= { cfprFabricNetflowMonitorEntry 1 }

cfprFabricNetflowMonitorDn OBJECT-TYPE
    SYNTAX       CfprManagedObjectDn
    MAX-ACCESS   read-only
    STATUS       current
    DESCRIPTION
        "Cisco Firepower fabric:NetflowMonitor:dn managed object property"
    ::= { cfprFabricNetflowMonitorEntry 2 }

cfprFabricNetflowMonitorRn OBJECT-TYPE
    SYNTAX       SnmpAdminString
    MAX-ACCESS   read-only
    STATUS       current
    DESCRIPTION
        "Cisco Firepower fabric:NetflowMonitor:rn managed object property"
    ::= { cfprFabricNetflowMonitorEntry 3 }

cfprFabricNetflowMonitorDescr OBJECT-TYPE
    SYNTAX       SnmpAdminString
    MAX-ACCESS   read-only
    STATUS       current
    DESCRIPTION
        "Cisco Firepower fabric:NetflowMonitor:descr managed
        object property"
    ::= { cfprFabricNetflowMonitorEntry 4 }

cfprFabricNetflowMonitorFlowMonProtocol OBJECT-TYPE
    SYNTAX       CfprFabricNetflowMonitorFlowMonProtocol
    MAX-ACCESS   read-only
    STATUS       current
    DESCRIPTION
        "Cisco Firepower fabric:NetflowMonitor:flowMonProtocol
        managed object property"
    ::= { cfprFabricNetflowMonitorEntry 5 }

cfprFabricNetflowMonitorFlowMonRecordDef OBJECT-TYPE
    SYNTAX       SnmpAdminString
    MAX-ACCESS   read-only
    STATUS       current
    DESCRIPTION
        "Cisco Firepower fabric:NetflowMonitor:flowMonRecordDef
        managed object property"
    ::= { cfprFabricNetflowMonitorEntry 6 }

cfprFabricNetflowMonitorFlowTimeoutPolicy OBJECT-TYPE
    SYNTAX       SnmpAdminString
    MAX-ACCESS   read-only
    STATUS       current
    DESCRIPTION
        "Cisco Firepower fabric:NetflowMonitor:flowTimeoutPolicy
        managed object property"
    ::= { cfprFabricNetflowMonitorEntry 7 }

cfprFabricNetflowMonitorIntId OBJECT-TYPE
    SYNTAX       SnmpAdminString
    MAX-ACCESS   read-only
    STATUS       current
    DESCRIPTION
        "Cisco Firepower fabric:NetflowMonitor:intId managed
        object property"
    ::= { cfprFabricNetflowMonitorEntry 8 }

cfprFabricNetflowMonitorName OBJECT-TYPE
    SYNTAX       SnmpAdminString
    MAX-ACCESS   read-only
    STATUS       current
    DESCRIPTION
        "Cisco Firepower fabric:NetflowMonitor:name managed
        object property"
    ::= { cfprFabricNetflowMonitorEntry 9 }

cfprFabricNetflowMonitorOperFlowMonRecordDef OBJECT-TYPE
    SYNTAX       SnmpAdminString
    MAX-ACCESS   read-only
    STATUS       current
    DESCRIPTION
        "Cisco Firepower fabric:NetflowMonitor:operFlowMonRecordDef
        managed object property"
    ::= { cfprFabricNetflowMonitorEntry 10 }

cfprFabricNetflowMonitorOperFlowTimeoutPolicy OBJECT-TYPE
    SYNTAX       SnmpAdminString
    MAX-ACCESS   read-only
    STATUS       current
    DESCRIPTION
        "Cisco Firepower fabric:NetflowMonitor:operFlowTimeoutPolicy
        managed object property"
    ::= { cfprFabricNetflowMonitorEntry 11 }

cfprFabricNetflowMonitorPolicyLevel OBJECT-TYPE
    SYNTAX       Gauge32
    MAX-ACCESS   read-only
    STATUS       current
    DESCRIPTION
        "Cisco Firepower fabric:NetflowMonitor:policyLevel
        managed object property"
    ::= { cfprFabricNetflowMonitorEntry 12 }

cfprFabricNetflowMonitorPolicyOwner OBJECT-TYPE
    SYNTAX       CfprPolicyPolicyOwner
    MAX-ACCESS   read-only
    STATUS       current
    DESCRIPTION
        "Cisco Firepower fabric:NetflowMonitor:policyOwner
        managed object property"
    ::= { cfprFabricNetflowMonitorEntry 13 }

cfprFabricNetflowMonitorTransport OBJECT-TYPE
    SYNTAX       CfprFabricEthLanFlowMonitorTransport
    MAX-ACCESS   read-only
    STATUS       current
    DESCRIPTION
        "Cisco Firepower fabric:NetflowMonitor:transport
        managed object property"
    ::= { cfprFabricNetflowMonitorEntry 14 }

cfprFabricNetflowMonitorType OBJECT-TYPE
    SYNTAX       CfprFabricLanFlowMonitorType
    MAX-ACCESS   read-only
    STATUS       current
    DESCRIPTION
        "Cisco Firepower fabric:NetflowMonitor:type managed
        object property"
    ::= { cfprFabricNetflowMonitorEntry 15 }

cfprFabricNetflowMonitorRefTable OBJECT-TYPE
    SYNTAX           SEQUENCE OF CfprFabricNetflowMonitorRefEntry
    MAX-ACCESS       not-accessible
    STATUS           current
    DESCRIPTION
        "Cisco Firepower fabric:NetflowMonitorRef managed object table"
    ::= { cfprFabricObjects 91 }

cfprFabricNetflowMonitorRefEntry OBJECT-TYPE
    SYNTAX           CfprFabricNetflowMonitorRefEntry
    MAX-ACCESS       not-accessible
    STATUS           current
    DESCRIPTION
        "Entry for the cfprFabricNetflowMonitorRefTable table."
    INDEX { cfprFabricNetflowMonitorRefInstanceId }
    ::= { cfprFabricNetflowMonitorRefTable 1 }

CfprFabricNetflowMonitorRefEntry ::= SEQUENCE {
    cfprFabricNetflowMonitorRefInstanceId                            CfprManagedObjectId,
    cfprFabricNetflowMonitorRefDn                                    CfprManagedObjectDn,
    cfprFabricNetflowMonitorRefRn                                    SnmpAdminString,
    cfprFabricNetflowMonitorRefDirection                             CfprFabricDirection,
    cfprFabricNetflowMonitorRefIndex                                 Gauge32,
    cfprFabricNetflowMonitorRefNfMonitorName                         SnmpAdminString,
    cfprFabricNetflowMonitorRefOperNfMonitorName                     SnmpAdminString,
    cfprFabricNetflowMonitorRefSwitchId                              CfprNetworkSwitchId
}

cfprFabricNetflowMonitorRefInstanceId OBJECT-TYPE
    SYNTAX       CfprManagedObjectId
    MAX-ACCESS   not-accessible
    STATUS       current
    DESCRIPTION
        "Instance identifier of the managed object."
    ::= { cfprFabricNetflowMonitorRefEntry 1 }

cfprFabricNetflowMonitorRefDn OBJECT-TYPE
    SYNTAX       CfprManagedObjectDn
    MAX-ACCESS   read-only
    STATUS       current
    DESCRIPTION
        "Cisco Firepower fabric:NetflowMonitorRef:dn managed
        object property"
    ::= { cfprFabricNetflowMonitorRefEntry 2 }

cfprFabricNetflowMonitorRefRn OBJECT-TYPE
    SYNTAX       SnmpAdminString
    MAX-ACCESS   read-only
    STATUS       current
    DESCRIPTION
        "Cisco Firepower fabric:NetflowMonitorRef:rn managed
        object property"
    ::= { cfprFabricNetflowMonitorRefEntry 3 }

cfprFabricNetflowMonitorRefDirection OBJECT-TYPE
    SYNTAX       CfprFabricDirection
    MAX-ACCESS   read-only
    STATUS       current
    DESCRIPTION
        "Cisco Firepower fabric:NetflowMonitorRef:direction
        managed object property"
    ::= { cfprFabricNetflowMonitorRefEntry 4 }

cfprFabricNetflowMonitorRefIndex OBJECT-TYPE
    SYNTAX       Gauge32
    MAX-ACCESS   read-only
    STATUS       current
    DESCRIPTION
        "Cisco Firepower fabric:NetflowMonitorRef:index
        managed object property"
    ::= { cfprFabricNetflowMonitorRefEntry 5 }

cfprFabricNetflowMonitorRefNfMonitorName OBJECT-TYPE
    SYNTAX       SnmpAdminString
    MAX-ACCESS   read-only
    STATUS       current
    DESCRIPTION
        "Cisco Firepower fabric:NetflowMonitorRef:nfMonitorName
        managed object property"
    ::= { cfprFabricNetflowMonitorRefEntry 6 }

cfprFabricNetflowMonitorRefOperNfMonitorName OBJECT-TYPE
    SYNTAX       SnmpAdminString
    MAX-ACCESS   read-only
    STATUS       current
    DESCRIPTION
        "Cisco Firepower fabric:NetflowMonitorRef:operNfMonitorName
        managed object property"
    ::= { cfprFabricNetflowMonitorRefEntry 7 }

cfprFabricNetflowMonitorRefSwitchId OBJECT-TYPE
    SYNTAX       CfprNetworkSwitchId
    MAX-ACCESS   read-only
    STATUS       current
    DESCRIPTION
        "Cisco Firepower fabric:NetflowMonitorRef:switchId
        managed object property"
    ::= { cfprFabricNetflowMonitorRefEntry 8 }

cfprFabricNetflowTimeoutPolicyTable OBJECT-TYPE
    SYNTAX           SEQUENCE OF CfprFabricNetflowTimeoutPolicyEntry
    MAX-ACCESS       not-accessible
    STATUS           current
    DESCRIPTION
        "Cisco Firepower fabric:NetflowTimeoutPolicy managed object table"
    ::= { cfprFabricObjects 92 }

cfprFabricNetflowTimeoutPolicyEntry OBJECT-TYPE
    SYNTAX           CfprFabricNetflowTimeoutPolicyEntry
    MAX-ACCESS       not-accessible
    STATUS           current
    DESCRIPTION
        "Entry for the cfprFabricNetflowTimeoutPolicyTable table."
    INDEX { cfprFabricNetflowTimeoutPolicyInstanceId }
    ::= { cfprFabricNetflowTimeoutPolicyTable 1 }

CfprFabricNetflowTimeoutPolicyEntry ::= SEQUENCE {
    cfprFabricNetflowTimeoutPolicyInstanceId                         CfprManagedObjectId,
    cfprFabricNetflowTimeoutPolicyDn                                 CfprManagedObjectDn,
    cfprFabricNetflowTimeoutPolicyRn                                 SnmpAdminString,
    cfprFabricNetflowTimeoutPolicyActiveTimeout                      Gauge32,
    cfprFabricNetflowTimeoutPolicyDescr                              SnmpAdminString,
    cfprFabricNetflowTimeoutPolicyInactiveTimeout                    Gauge32,
    cfprFabricNetflowTimeoutPolicyIntId                              SnmpAdminString,
    cfprFabricNetflowTimeoutPolicyName                               SnmpAdminString,
    cfprFabricNetflowTimeoutPolicyPolicyLevel                        Gauge32,
    cfprFabricNetflowTimeoutPolicyPolicyOwner                        CfprPolicyPolicyOwner
}

cfprFabricNetflowTimeoutPolicyInstanceId OBJECT-TYPE
    SYNTAX       CfprManagedObjectId
    MAX-ACCESS   not-accessible
    STATUS       current
    DESCRIPTION
        "Instance identifier of the managed object."
    ::= { cfprFabricNetflowTimeoutPolicyEntry 1 }

cfprFabricNetflowTimeoutPolicyDn OBJECT-TYPE
    SYNTAX       CfprManagedObjectDn
    MAX-ACCESS   read-only
    STATUS       current
    DESCRIPTION
        "Cisco Firepower fabric:NetflowTimeoutPolicy:dn
        managed object property"
    ::= { cfprFabricNetflowTimeoutPolicyEntry 2 }

cfprFabricNetflowTimeoutPolicyRn OBJECT-TYPE
    SYNTAX       SnmpAdminString
    MAX-ACCESS   read-only
    STATUS       current
    DESCRIPTION
        "Cisco Firepower fabric:NetflowTimeoutPolicy:rn
        managed object property"
    ::= { cfprFabricNetflowTimeoutPolicyEntry 3 }

cfprFabricNetflowTimeoutPolicyActiveTimeout OBJECT-TYPE
    SYNTAX       Gauge32
    MAX-ACCESS   read-only
    STATUS       current
    DESCRIPTION
        "Cisco Firepower fabric:NetflowTimeoutPolicy:activeTimeout
        managed object property"
    ::= { cfprFabricNetflowTimeoutPolicyEntry 4 }

cfprFabricNetflowTimeoutPolicyDescr OBJECT-TYPE
    SYNTAX       SnmpAdminString
    MAX-ACCESS   read-only
    STATUS       current
    DESCRIPTION
        "Cisco Firepower fabric:NetflowTimeoutPolicy:descr
        managed object property"
    ::= { cfprFabricNetflowTimeoutPolicyEntry 5 }

cfprFabricNetflowTimeoutPolicyInactiveTimeout OBJECT-TYPE
    SYNTAX       Gauge32
    MAX-ACCESS   read-only
    STATUS       current
    DESCRIPTION
        "Cisco Firepower fabric:NetflowTimeoutPolicy:inactiveTimeout
        managed object property"
    ::= { cfprFabricNetflowTimeoutPolicyEntry 6 }

cfprFabricNetflowTimeoutPolicyIntId OBJECT-TYPE
    SYNTAX       SnmpAdminString
    MAX-ACCESS   read-only
    STATUS       current
    DESCRIPTION
        "Cisco Firepower fabric:NetflowTimeoutPolicy:intId
        managed object property"
    ::= { cfprFabricNetflowTimeoutPolicyEntry 7 }

cfprFabricNetflowTimeoutPolicyName OBJECT-TYPE
    SYNTAX       SnmpAdminString
    MAX-ACCESS   read-only
    STATUS       current
    DESCRIPTION
        "Cisco Firepower fabric:NetflowTimeoutPolicy:name
        managed object property"
    ::= { cfprFabricNetflowTimeoutPolicyEntry 8 }

cfprFabricNetflowTimeoutPolicyPolicyLevel OBJECT-TYPE
    SYNTAX       Gauge32
    MAX-ACCESS   read-only
    STATUS       current
    DESCRIPTION
        "Cisco Firepower fabric:NetflowTimeoutPolicy:policyLevel
        managed object property"
    ::= { cfprFabricNetflowTimeoutPolicyEntry 9 }

cfprFabricNetflowTimeoutPolicyPolicyOwner OBJECT-TYPE
    SYNTAX       CfprPolicyPolicyOwner
    MAX-ACCESS   read-only
    STATUS       current
    DESCRIPTION
        "Cisco Firepower fabric:NetflowTimeoutPolicy:policyOwner
        managed object property"
    ::= { cfprFabricNetflowTimeoutPolicyEntry 10 }

cfprFabricOrgVlanPolicyTable OBJECT-TYPE
    SYNTAX           SEQUENCE OF CfprFabricOrgVlanPolicyEntry
    MAX-ACCESS       not-accessible
    STATUS           current
    DESCRIPTION
        "Cisco Firepower fabric:OrgVlanPolicy managed object table"
    ::= { cfprFabricObjects 93 }

cfprFabricOrgVlanPolicyEntry OBJECT-TYPE
    SYNTAX           CfprFabricOrgVlanPolicyEntry
    MAX-ACCESS       not-accessible
    STATUS           current
    DESCRIPTION
        "Entry for the cfprFabricOrgVlanPolicyTable table."
    INDEX { cfprFabricOrgVlanPolicyInstanceId }
    ::= { cfprFabricOrgVlanPolicyTable 1 }

CfprFabricOrgVlanPolicyEntry ::= SEQUENCE {
    cfprFabricOrgVlanPolicyInstanceId                                CfprManagedObjectId,
    cfprFabricOrgVlanPolicyDn                                        CfprManagedObjectDn,
    cfprFabricOrgVlanPolicyRn                                        SnmpAdminString,
    cfprFabricOrgVlanPolicyAdminState                                CfprFabricAdminState,
    cfprFabricOrgVlanPolicyName                                      SnmpAdminString
}

cfprFabricOrgVlanPolicyInstanceId OBJECT-TYPE
    SYNTAX       CfprManagedObjectId
    MAX-ACCESS   not-accessible
    STATUS       current
    DESCRIPTION
        "Instance identifier of the managed object."
    ::= { cfprFabricOrgVlanPolicyEntry 1 }

cfprFabricOrgVlanPolicyDn OBJECT-TYPE
    SYNTAX       CfprManagedObjectDn
    MAX-ACCESS   read-only
    STATUS       current
    DESCRIPTION
        "Cisco Firepower fabric:OrgVlanPolicy:dn managed object property"
    ::= { cfprFabricOrgVlanPolicyEntry 2 }

cfprFabricOrgVlanPolicyRn OBJECT-TYPE
    SYNTAX       SnmpAdminString
    MAX-ACCESS   read-only
    STATUS       current
    DESCRIPTION
        "Cisco Firepower fabric:OrgVlanPolicy:rn managed object property"
    ::= { cfprFabricOrgVlanPolicyEntry 3 }

cfprFabricOrgVlanPolicyAdminState OBJECT-TYPE
    SYNTAX       CfprFabricAdminState
    MAX-ACCESS   read-only
    STATUS       current
    DESCRIPTION
        "Cisco Firepower fabric:OrgVlanPolicy:adminState
        managed object property"
    ::= { cfprFabricOrgVlanPolicyEntry 4 }

cfprFabricOrgVlanPolicyName OBJECT-TYPE
    SYNTAX       SnmpAdminString
    MAX-ACCESS   read-only
    STATUS       current
    DESCRIPTION
        "Cisco Firepower fabric:OrgVlanPolicy:name managed
        object property"
    ::= { cfprFabricOrgVlanPolicyEntry 5 }

cfprFabricPathTable OBJECT-TYPE
    SYNTAX           SEQUENCE OF CfprFabricPathEntry
    MAX-ACCESS       not-accessible
    STATUS           current
    DESCRIPTION
        "Cisco Firepower fabric:Path managed object table"
    ::= { cfprFabricObjects 94 }

cfprFabricPathEntry OBJECT-TYPE
    SYNTAX           CfprFabricPathEntry
    MAX-ACCESS       not-accessible
    STATUS           current
    DESCRIPTION
        "Entry for the cfprFabricPathTable table."
    INDEX { cfprFabricPathInstanceId }
    ::= { cfprFabricPathTable 1 }

CfprFabricPathEntry ::= SEQUENCE {
    cfprFabricPathInstanceId                                         CfprManagedObjectId,
    cfprFabricPathDn                                                 CfprManagedObjectDn,
    cfprFabricPathRn                                                 SnmpAdminString,
    cfprFabricPathCType                                              Gauge32,
    cfprFabricPathChassisId                                          Gauge32,
    cfprFabricPathEnacp                                              Gauge32,
    cfprFabricPathId                                                 Gauge32,
    cfprFabricPathLocale                                             CfprNetworkLocale,
    cfprFabricPathName                                               SnmpAdminString,
    cfprFabricPathNsSize                                             Gauge32,
    cfprFabricPathSide                                               CfprNetworkSide,
    cfprFabricPathSwitchId                                           CfprNetworkSwitchId,
    cfprFabricPathTransport                                          CfprNetworkTransport,
    cfprFabricPathType                                               CfprNetworkConnectionType
}

cfprFabricPathInstanceId OBJECT-TYPE
    SYNTAX       CfprManagedObjectId
    MAX-ACCESS   not-accessible
    STATUS       current
    DESCRIPTION
        "Instance identifier of the managed object."
    ::= { cfprFabricPathEntry 1 }

cfprFabricPathDn OBJECT-TYPE
    SYNTAX       CfprManagedObjectDn
    MAX-ACCESS   read-only
    STATUS       current
    DESCRIPTION
        "Cisco Firepower fabric:Path:dn managed object property"
    ::= { cfprFabricPathEntry 2 }

cfprFabricPathRn OBJECT-TYPE
    SYNTAX       SnmpAdminString
    MAX-ACCESS   read-only
    STATUS       current
    DESCRIPTION
        "Cisco Firepower fabric:Path:rn managed object property"
    ::= { cfprFabricPathEntry 3 }

cfprFabricPathCType OBJECT-TYPE
    SYNTAX       Gauge32
    MAX-ACCESS   read-only
    STATUS       current
    DESCRIPTION
        "Cisco Firepower fabric:Path:cType managed object property"
    ::= { cfprFabricPathEntry 4 }

cfprFabricPathChassisId OBJECT-TYPE
    SYNTAX       Gauge32
    MAX-ACCESS   read-only
    STATUS       current
    DESCRIPTION
        "Cisco Firepower fabric:Path:chassisId managed object property"
    ::= { cfprFabricPathEntry 5 }

cfprFabricPathEnacp OBJECT-TYPE
    SYNTAX       Gauge32
    MAX-ACCESS   read-only
    STATUS       current
    DESCRIPTION
        "Cisco Firepower fabric:Path:enacp managed object property"
    ::= { cfprFabricPathEntry 6 }

cfprFabricPathId OBJECT-TYPE
    SYNTAX       Gauge32
    MAX-ACCESS   read-only
    STATUS       current
    DESCRIPTION
        "Cisco Firepower fabric:Path:id managed object property"
    ::= { cfprFabricPathEntry 7 }

cfprFabricPathLocale OBJECT-TYPE
    SYNTAX       CfprNetworkLocale
    MAX-ACCESS   read-only
    STATUS       current
    DESCRIPTION
        "Cisco Firepower fabric:Path:locale managed object property"
    ::= { cfprFabricPathEntry 8 }

cfprFabricPathName OBJECT-TYPE
    SYNTAX       SnmpAdminString
    MAX-ACCESS   read-only
    STATUS       current
    DESCRIPTION
        "Cisco Firepower fabric:Path:name managed object property"
    ::= { cfprFabricPathEntry 9 }

cfprFabricPathNsSize OBJECT-TYPE
    SYNTAX       Gauge32
    MAX-ACCESS   read-only
    STATUS       current
    DESCRIPTION
        "Cisco Firepower fabric:Path:nsSize managed object property"
    ::= { cfprFabricPathEntry 10 }

cfprFabricPathSide OBJECT-TYPE
    SYNTAX       CfprNetworkSide
    MAX-ACCESS   read-only
    STATUS       current
    DESCRIPTION
        "Cisco Firepower fabric:Path:side managed object property"
    ::= { cfprFabricPathEntry 11 }

cfprFabricPathSwitchId OBJECT-TYPE
    SYNTAX       CfprNetworkSwitchId
    MAX-ACCESS   read-only
    STATUS       current
    DESCRIPTION
        "Cisco Firepower fabric:Path:switchId managed object property"
    ::= { cfprFabricPathEntry 12 }

cfprFabricPathTransport OBJECT-TYPE
    SYNTAX       CfprNetworkTransport
    MAX-ACCESS   read-only
    STATUS       current
    DESCRIPTION
        "Cisco Firepower fabric:Path:transport managed object property"
    ::= { cfprFabricPathEntry 13 }

cfprFabricPathType OBJECT-TYPE
    SYNTAX       CfprNetworkConnectionType
    MAX-ACCESS   read-only
    STATUS       current
    DESCRIPTION
        "Cisco Firepower fabric:Path:type managed object property"
    ::= { cfprFabricPathEntry 14 }

cfprFabricPathConnTable OBJECT-TYPE
    SYNTAX           SEQUENCE OF CfprFabricPathConnEntry
    MAX-ACCESS       not-accessible
    STATUS           current
    DESCRIPTION
        "Cisco Firepower fabric:PathConn managed object table"
    ::= { cfprFabricObjects 95 }

cfprFabricPathConnEntry OBJECT-TYPE
    SYNTAX           CfprFabricPathConnEntry
    MAX-ACCESS       not-accessible
    STATUS           current
    DESCRIPTION
        "Entry for the cfprFabricPathConnTable table."
    INDEX { cfprFabricPathConnInstanceId }
    ::= { cfprFabricPathConnTable 1 }

CfprFabricPathConnEntry ::= SEQUENCE {
    cfprFabricPathConnInstanceId                                     CfprManagedObjectId,
    cfprFabricPathConnDn                                             CfprManagedObjectDn,
    cfprFabricPathConnRn                                             SnmpAdminString,
    cfprFabricPathConnCType                                          Gauge32,
    cfprFabricPathConnLocale                                         CfprNetworkLocale,
    cfprFabricPathConnName                                           SnmpAdminString,
    cfprFabricPathConnTransport                                      CfprNetworkTransport,
    cfprFabricPathConnType                                           CfprNetworkConnectionType
}

cfprFabricPathConnInstanceId OBJECT-TYPE
    SYNTAX       CfprManagedObjectId
    MAX-ACCESS   not-accessible
    STATUS       current
    DESCRIPTION
        "Instance identifier of the managed object."
    ::= { cfprFabricPathConnEntry 1 }

cfprFabricPathConnDn OBJECT-TYPE
    SYNTAX       CfprManagedObjectDn
    MAX-ACCESS   read-only
    STATUS       current
    DESCRIPTION
        "Cisco Firepower fabric:PathConn:dn managed object property"
    ::= { cfprFabricPathConnEntry 2 }

cfprFabricPathConnRn OBJECT-TYPE
    SYNTAX       SnmpAdminString
    MAX-ACCESS   read-only
    STATUS       current
    DESCRIPTION
        "Cisco Firepower fabric:PathConn:rn managed object property"
    ::= { cfprFabricPathConnEntry 3 }

cfprFabricPathConnCType OBJECT-TYPE
    SYNTAX       Gauge32
    MAX-ACCESS   read-only
    STATUS       current
    DESCRIPTION
        "Cisco Firepower fabric:PathConn:cType managed object property"
    ::= { cfprFabricPathConnEntry 4 }

cfprFabricPathConnLocale OBJECT-TYPE
    SYNTAX       CfprNetworkLocale
    MAX-ACCESS   read-only
    STATUS       current
    DESCRIPTION
        "Cisco Firepower fabric:PathConn:locale managed object property"
    ::= { cfprFabricPathConnEntry 5 }

cfprFabricPathConnName OBJECT-TYPE
    SYNTAX       SnmpAdminString
    MAX-ACCESS   read-only
    STATUS       current
    DESCRIPTION
        "Cisco Firepower fabric:PathConn:name managed object property"
    ::= { cfprFabricPathConnEntry 6 }

cfprFabricPathConnTransport OBJECT-TYPE
    SYNTAX       CfprNetworkTransport
    MAX-ACCESS   read-only
    STATUS       current
    DESCRIPTION
        "Cisco Firepower fabric:PathConn:transport managed
        object property"
    ::= { cfprFabricPathConnEntry 7 }

cfprFabricPathConnType OBJECT-TYPE
    SYNTAX       CfprNetworkConnectionType
    MAX-ACCESS   read-only
    STATUS       current
    DESCRIPTION
        "Cisco Firepower fabric:PathConn:type managed object property"
    ::= { cfprFabricPathConnEntry 8 }

cfprFabricPathEpTable OBJECT-TYPE
    SYNTAX           SEQUENCE OF CfprFabricPathEpEntry
    MAX-ACCESS       not-accessible
    STATUS           current
    DESCRIPTION
        "Cisco Firepower fabric:PathEp managed object table"
    ::= { cfprFabricObjects 96 }

cfprFabricPathEpEntry OBJECT-TYPE
    SYNTAX           CfprFabricPathEpEntry
    MAX-ACCESS       not-accessible
    STATUS           current
    DESCRIPTION
        "Entry for the cfprFabricPathEpTable table."
    INDEX { cfprFabricPathEpInstanceId }
    ::= { cfprFabricPathEpTable 1 }

CfprFabricPathEpEntry ::= SEQUENCE {
    cfprFabricPathEpInstanceId                                       CfprManagedObjectId,
    cfprFabricPathEpDn                                               CfprManagedObjectDn,
    cfprFabricPathEpRn                                               SnmpAdminString,
    cfprFabricPathEpAggrPortId                                       Gauge32,
    cfprFabricPathEpCType                                            Gauge32,
    cfprFabricPathEpChassisId                                        Gauge32,
    cfprFabricPathEpDiagLldpTransmit                                 TruthValue,
    cfprFabricPathEpEpDn                                             SnmpAdminString,
    cfprFabricPathEpIfRole                                           CfprNetworkPortRole,
    cfprFabricPathEpIfType                                           CfprFabricPathEpIfType,
    cfprFabricPathEpLocale                                           CfprFabricPathEpLocale,
    cfprFabricPathEpName                                             SnmpAdminString,
    cfprFabricPathEpPeerAggrPortId                                   Gauge32,
    cfprFabricPathEpPeerChassisId                                    Gauge32,
    cfprFabricPathEpPeerDn                                           SnmpAdminString,
    cfprFabricPathEpPeerMac                                          MacAddress,
    cfprFabricPathEpPeerPortId                                       Gauge32,
    cfprFabricPathEpPeerSlotId                                       Gauge32,
    cfprFabricPathEpPortId                                           Gauge32,
    cfprFabricPathEpSide                                             CfprNetworkSide,
    cfprFabricPathEpSlotId                                           Gauge32,
    cfprFabricPathEpSwitchId                                         CfprNetworkSwitchId,
    cfprFabricPathEpTransport                                        CfprNetworkTransport,
    cfprFabricPathEpType                                             CfprNetworkConnectionType
}

cfprFabricPathEpInstanceId OBJECT-TYPE
    SYNTAX       CfprManagedObjectId
    MAX-ACCESS   not-accessible
    STATUS       current
    DESCRIPTION
        "Instance identifier of the managed object."
    ::= { cfprFabricPathEpEntry 1 }

cfprFabricPathEpDn OBJECT-TYPE
    SYNTAX       CfprManagedObjectDn
    MAX-ACCESS   read-only
    STATUS       current
    DESCRIPTION
        "Cisco Firepower fabric:PathEp:dn managed object property"
    ::= { cfprFabricPathEpEntry 2 }

cfprFabricPathEpRn OBJECT-TYPE
    SYNTAX       SnmpAdminString
    MAX-ACCESS   read-only
    STATUS       current
    DESCRIPTION
        "Cisco Firepower fabric:PathEp:rn managed object property"
    ::= { cfprFabricPathEpEntry 3 }

cfprFabricPathEpAggrPortId OBJECT-TYPE
    SYNTAX       Gauge32
    MAX-ACCESS   read-only
    STATUS       current
    DESCRIPTION
        "Cisco Firepower fabric:PathEp:aggrPortId managed object property"
    ::= { cfprFabricPathEpEntry 4 }

cfprFabricPathEpCType OBJECT-TYPE
    SYNTAX       Gauge32
    MAX-ACCESS   read-only
    STATUS       current
    DESCRIPTION
        "Cisco Firepower fabric:PathEp:cType managed object property"
    ::= { cfprFabricPathEpEntry 5 }

cfprFabricPathEpChassisId OBJECT-TYPE
    SYNTAX       Gauge32
    MAX-ACCESS   read-only
    STATUS       current
    DESCRIPTION
        "Cisco Firepower fabric:PathEp:chassisId managed object property"
    ::= { cfprFabricPathEpEntry 6 }

cfprFabricPathEpDiagLldpTransmit OBJECT-TYPE
    SYNTAX       TruthValue
    MAX-ACCESS   read-only
    STATUS       current
    DESCRIPTION
        "Cisco Firepower fabric:PathEp:diagLldpTransmit
        managed object property"
    ::= { cfprFabricPathEpEntry 7 }

cfprFabricPathEpEpDn OBJECT-TYPE
    SYNTAX       SnmpAdminString
    MAX-ACCESS   read-only
    STATUS       current
    DESCRIPTION
        "Cisco Firepower fabric:PathEp:epDn managed object property"
    ::= { cfprFabricPathEpEntry 8 }

cfprFabricPathEpIfRole OBJECT-TYPE
    SYNTAX       CfprNetworkPortRole
    MAX-ACCESS   read-only
    STATUS       current
    DESCRIPTION
        "Cisco Firepower fabric:PathEp:ifRole managed object property"
    ::= { cfprFabricPathEpEntry 9 }

cfprFabricPathEpIfType OBJECT-TYPE
    SYNTAX       CfprFabricPathEpIfType
    MAX-ACCESS   read-only
    STATUS       current
    DESCRIPTION
        "Cisco Firepower fabric:PathEp:ifType managed object property"
    ::= { cfprFabricPathEpEntry 10 }

cfprFabricPathEpLocale OBJECT-TYPE
    SYNTAX       CfprFabricPathEpLocale
    MAX-ACCESS   read-only
    STATUS       current
    DESCRIPTION
        "Cisco Firepower fabric:PathEp:locale managed object property"
    ::= { cfprFabricPathEpEntry 11 }

cfprFabricPathEpName OBJECT-TYPE
    SYNTAX       SnmpAdminString
    MAX-ACCESS   read-only
    STATUS       current
    DESCRIPTION
        "Cisco Firepower fabric:PathEp:name managed object property"
    ::= { cfprFabricPathEpEntry 12 }

cfprFabricPathEpPeerAggrPortId OBJECT-TYPE
    SYNTAX       Gauge32
    MAX-ACCESS   read-only
    STATUS       current
    DESCRIPTION
        "Cisco Firepower fabric:PathEp:peerAggrPortId managed
        object property"
    ::= { cfprFabricPathEpEntry 13 }

cfprFabricPathEpPeerChassisId OBJECT-TYPE
    SYNTAX       Gauge32
    MAX-ACCESS   read-only
    STATUS       current
    DESCRIPTION
        "Cisco Firepower fabric:PathEp:peerChassisId managed
        object property"
    ::= { cfprFabricPathEpEntry 14 }

cfprFabricPathEpPeerDn OBJECT-TYPE
    SYNTAX       SnmpAdminString
    MAX-ACCESS   read-only
    STATUS       current
    DESCRIPTION
        "Cisco Firepower fabric:PathEp:peerDn managed object property"
    ::= { cfprFabricPathEpEntry 15 }

cfprFabricPathEpPeerMac OBJECT-TYPE
    SYNTAX       MacAddress
    MAX-ACCESS   read-only
    STATUS       current
    DESCRIPTION
        "Cisco Firepower fabric:PathEp:peerMac managed object property"
    ::= { cfprFabricPathEpEntry 16 }

cfprFabricPathEpPeerPortId OBJECT-TYPE
    SYNTAX       Gauge32
    MAX-ACCESS   read-only
    STATUS       current
    DESCRIPTION
        "Cisco Firepower fabric:PathEp:peerPortId managed object property"
    ::= { cfprFabricPathEpEntry 17 }

cfprFabricPathEpPeerSlotId OBJECT-TYPE
    SYNTAX       Gauge32
    MAX-ACCESS   read-only
    STATUS       current
    DESCRIPTION
        "Cisco Firepower fabric:PathEp:peerSlotId managed object property"
    ::= { cfprFabricPathEpEntry 18 }

cfprFabricPathEpPortId OBJECT-TYPE
    SYNTAX       Gauge32
    MAX-ACCESS   read-only
    STATUS       current
    DESCRIPTION
        "Cisco Firepower fabric:PathEp:portId managed object property"
    ::= { cfprFabricPathEpEntry 19 }

cfprFabricPathEpSide OBJECT-TYPE
    SYNTAX       CfprNetworkSide
    MAX-ACCESS   read-only
    STATUS       current
    DESCRIPTION
        "Cisco Firepower fabric:PathEp:side managed object property"
    ::= { cfprFabricPathEpEntry 20 }

cfprFabricPathEpSlotId OBJECT-TYPE
    SYNTAX       Gauge32
    MAX-ACCESS   read-only
    STATUS       current
    DESCRIPTION
        "Cisco Firepower fabric:PathEp:slotId managed object property"
    ::= { cfprFabricPathEpEntry 21 }

cfprFabricPathEpSwitchId OBJECT-TYPE
    SYNTAX       CfprNetworkSwitchId
    MAX-ACCESS   read-only
    STATUS       current
    DESCRIPTION
        "Cisco Firepower fabric:PathEp:switchId managed object property"
    ::= { cfprFabricPathEpEntry 22 }

cfprFabricPathEpTransport OBJECT-TYPE
    SYNTAX       CfprNetworkTransport
    MAX-ACCESS   read-only
    STATUS       current
    DESCRIPTION
        "Cisco Firepower fabric:PathEp:transport managed object property"
    ::= { cfprFabricPathEpEntry 23 }

cfprFabricPathEpType OBJECT-TYPE
    SYNTAX       CfprNetworkConnectionType
    MAX-ACCESS   read-only
    STATUS       current
    DESCRIPTION
        "Cisco Firepower fabric:PathEp:type managed object property"
    ::= { cfprFabricPathEpEntry 24 }

cfprFabricPoolableVlanTable OBJECT-TYPE
    SYNTAX           SEQUENCE OF CfprFabricPoolableVlanEntry
    MAX-ACCESS       not-accessible
    STATUS           current
    DESCRIPTION
        "Cisco Firepower fabric:PoolableVlan managed object table"
    ::= { cfprFabricObjects 97 }

cfprFabricPoolableVlanEntry OBJECT-TYPE
    SYNTAX           CfprFabricPoolableVlanEntry
    MAX-ACCESS       not-accessible
    STATUS           current
    DESCRIPTION
        "Entry for the cfprFabricPoolableVlanTable table."
    INDEX { cfprFabricPoolableVlanInstanceId }
    ::= { cfprFabricPoolableVlanTable 1 }

CfprFabricPoolableVlanEntry ::= SEQUENCE {
    cfprFabricPoolableVlanInstanceId                                 CfprManagedObjectId,
    cfprFabricPoolableVlanDn                                         CfprManagedObjectDn,
    cfprFabricPoolableVlanRn                                         SnmpAdminString,
    cfprFabricPoolableVlanId                                         Unsigned64,
    cfprFabricPoolableVlanPoolDn                                     SnmpAdminString
}

cfprFabricPoolableVlanInstanceId OBJECT-TYPE
    SYNTAX       CfprManagedObjectId
    MAX-ACCESS   not-accessible
    STATUS       current
    DESCRIPTION
        "Instance identifier of the managed object."
    ::= { cfprFabricPoolableVlanEntry 1 }

cfprFabricPoolableVlanDn OBJECT-TYPE
    SYNTAX       CfprManagedObjectDn
    MAX-ACCESS   read-only
    STATUS       current
    DESCRIPTION
        "Cisco Firepower fabric:PoolableVlan:dn managed object property"
    ::= { cfprFabricPoolableVlanEntry 2 }

cfprFabricPoolableVlanRn OBJECT-TYPE
    SYNTAX       SnmpAdminString
    MAX-ACCESS   read-only
    STATUS       current
    DESCRIPTION
        "Cisco Firepower fabric:PoolableVlan:rn managed object property"
    ::= { cfprFabricPoolableVlanEntry 3 }

cfprFabricPoolableVlanId OBJECT-TYPE
    SYNTAX       Unsigned64
    MAX-ACCESS   read-only
    STATUS       current
    DESCRIPTION
        "Cisco Firepower fabric:PoolableVlan:id managed object property"
    ::= { cfprFabricPoolableVlanEntry 4 }

cfprFabricPoolableVlanPoolDn OBJECT-TYPE
    SYNTAX       SnmpAdminString
    MAX-ACCESS   read-only
    STATUS       current
    DESCRIPTION
        "Cisco Firepower fabric:PoolableVlan:poolDn managed
        object property"
    ::= { cfprFabricPoolableVlanEntry 5 }

cfprFabricPooledVlanTable OBJECT-TYPE
    SYNTAX           SEQUENCE OF CfprFabricPooledVlanEntry
    MAX-ACCESS       not-accessible
    STATUS           current
    DESCRIPTION
        "Cisco Firepower fabric:PooledVlan managed object table"
    ::= { cfprFabricObjects 98 }

cfprFabricPooledVlanEntry OBJECT-TYPE
    SYNTAX           CfprFabricPooledVlanEntry
    MAX-ACCESS       not-accessible
    STATUS           current
    DESCRIPTION
        "Entry for the cfprFabricPooledVlanTable table."
    INDEX { cfprFabricPooledVlanInstanceId }
    ::= { cfprFabricPooledVlanTable 1 }

CfprFabricPooledVlanEntry ::= SEQUENCE {
    cfprFabricPooledVlanInstanceId                                   CfprManagedObjectId,
    cfprFabricPooledVlanDn                                           CfprManagedObjectDn,
    cfprFabricPooledVlanRn                                           SnmpAdminString,
    cfprFabricPooledVlanAssigned                                     TruthValue,
    cfprFabricPooledVlanAssignedToDn                                 SnmpAdminString,
    cfprFabricPooledVlanConfigIssues                                 CfprFabricPoolMemberConfigIssues,
    cfprFabricPooledVlanName                                         SnmpAdminString,
    cfprFabricPooledVlanPeerDn                                       SnmpAdminString,
    cfprFabricPooledVlanPoolableDn                                   SnmpAdminString,
    cfprFabricPooledVlanPrevAssignedToDn                             SnmpAdminString
}

cfprFabricPooledVlanInstanceId OBJECT-TYPE
    SYNTAX       CfprManagedObjectId
    MAX-ACCESS   not-accessible
    STATUS       current
    DESCRIPTION
        "Instance identifier of the managed object."
    ::= { cfprFabricPooledVlanEntry 1 }

cfprFabricPooledVlanDn OBJECT-TYPE
    SYNTAX       CfprManagedObjectDn
    MAX-ACCESS   read-only
    STATUS       current
    DESCRIPTION
        "Cisco Firepower fabric:PooledVlan:dn managed object property"
    ::= { cfprFabricPooledVlanEntry 2 }

cfprFabricPooledVlanRn OBJECT-TYPE
    SYNTAX       SnmpAdminString
    MAX-ACCESS   read-only
    STATUS       current
    DESCRIPTION
        "Cisco Firepower fabric:PooledVlan:rn managed object property"
    ::= { cfprFabricPooledVlanEntry 3 }

cfprFabricPooledVlanAssigned OBJECT-TYPE
    SYNTAX       TruthValue
    MAX-ACCESS   read-only
    STATUS       current
    DESCRIPTION
        "Cisco Firepower fabric:PooledVlan:assigned managed
        object property"
    ::= { cfprFabricPooledVlanEntry 4 }

cfprFabricPooledVlanAssignedToDn OBJECT-TYPE
    SYNTAX       SnmpAdminString
    MAX-ACCESS   read-only
    STATUS       current
    DESCRIPTION
        "Cisco Firepower fabric:PooledVlan:assignedToDn
        managed object property"
    ::= { cfprFabricPooledVlanEntry 5 }

cfprFabricPooledVlanConfigIssues OBJECT-TYPE
    SYNTAX       CfprFabricPoolMemberConfigIssues
    MAX-ACCESS   read-only
    STATUS       current
    DESCRIPTION
        "Cisco Firepower fabric:PooledVlan:configIssues
        managed object property"
    ::= { cfprFabricPooledVlanEntry 6 }

cfprFabricPooledVlanName OBJECT-TYPE
    SYNTAX       SnmpAdminString
    MAX-ACCESS   read-only
    STATUS       current
    DESCRIPTION
        "Cisco Firepower fabric:PooledVlan:name managed object property"
    ::= { cfprFabricPooledVlanEntry 7 }

cfprFabricPooledVlanPeerDn OBJECT-TYPE
    SYNTAX       SnmpAdminString
    MAX-ACCESS   read-only
    STATUS       current
    DESCRIPTION
        "Cisco Firepower fabric:PooledVlan:peerDn managed object property"
    ::= { cfprFabricPooledVlanEntry 8 }

cfprFabricPooledVlanPoolableDn OBJECT-TYPE
    SYNTAX       SnmpAdminString
    MAX-ACCESS   read-only
    STATUS       current
    DESCRIPTION
        "Cisco Firepower fabric:PooledVlan:poolableDn managed
        object property"
    ::= { cfprFabricPooledVlanEntry 9 }

cfprFabricPooledVlanPrevAssignedToDn OBJECT-TYPE
    SYNTAX       SnmpAdminString
    MAX-ACCESS   read-only
    STATUS       current
    DESCRIPTION
        "Cisco Firepower fabric:PooledVlan:prevAssignedToDn
        managed object property"
    ::= { cfprFabricPooledVlanEntry 10 }

cfprFabricSanCloudTable OBJECT-TYPE
    SYNTAX           SEQUENCE OF CfprFabricSanCloudEntry
    MAX-ACCESS       not-accessible
    STATUS           current
    DESCRIPTION
        "Cisco Firepower fabric:SanCloud managed object table"
    ::= { cfprFabricObjects 99 }

cfprFabricSanCloudEntry OBJECT-TYPE
    SYNTAX           CfprFabricSanCloudEntry
    MAX-ACCESS       not-accessible
    STATUS           current
    DESCRIPTION
        "Entry for the cfprFabricSanCloudTable table."
    INDEX { cfprFabricSanCloudInstanceId }
    ::= { cfprFabricSanCloudTable 1 }

CfprFabricSanCloudEntry ::= SEQUENCE {
    cfprFabricSanCloudInstanceId                                     CfprManagedObjectId,
    cfprFabricSanCloudDn                                             CfprManagedObjectDn,
    cfprFabricSanCloudRn                                             SnmpAdminString,
    cfprFabricSanCloudFsmDescr                                       SnmpAdminString,
    cfprFabricSanCloudFsmPrev                                        SnmpAdminString,
    cfprFabricSanCloudFsmProgr                                       Gauge32,
    cfprFabricSanCloudFsmRmtInvErrCode                               Gauge32,
    cfprFabricSanCloudFsmRmtInvErrDescr                              SnmpAdminString,
    cfprFabricSanCloudFsmRmtInvRslt                                  CfprConditionRemoteInvRslt,
    cfprFabricSanCloudFsmStageDescr                                  SnmpAdminString,
    cfprFabricSanCloudFsmStamp                                       DateAndTime,
    cfprFabricSanCloudFsmStatus                                      SnmpAdminString,
    cfprFabricSanCloudFsmTry                                         Gauge32,
    cfprFabricSanCloudMode                                           CfprFabricSwitchingMode
}

cfprFabricSanCloudInstanceId OBJECT-TYPE
    SYNTAX       CfprManagedObjectId
    MAX-ACCESS   not-accessible
    STATUS       current
    DESCRIPTION
        "Instance identifier of the managed object."
    ::= { cfprFabricSanCloudEntry 1 }

cfprFabricSanCloudDn OBJECT-TYPE
    SYNTAX       CfprManagedObjectDn
    MAX-ACCESS   read-only
    STATUS       current
    DESCRIPTION
        "Cisco Firepower fabric:SanCloud:dn managed object property"
    ::= { cfprFabricSanCloudEntry 2 }

cfprFabricSanCloudRn OBJECT-TYPE
    SYNTAX       SnmpAdminString
    MAX-ACCESS   read-only
    STATUS       current
    DESCRIPTION
        "Cisco Firepower fabric:SanCloud:rn managed object property"
    ::= { cfprFabricSanCloudEntry 3 }

cfprFabricSanCloudFsmDescr OBJECT-TYPE
    SYNTAX       SnmpAdminString
    MAX-ACCESS   read-only
    STATUS       current
    DESCRIPTION
        "Cisco Firepower fabric:SanCloud:fsmDescr managed object property"
    ::= { cfprFabricSanCloudEntry 4 }

cfprFabricSanCloudFsmPrev OBJECT-TYPE
    SYNTAX       SnmpAdminString
    MAX-ACCESS   read-only
    STATUS       current
    DESCRIPTION
        "Cisco Firepower fabric:SanCloud:fsmPrev managed object property"
    ::= { cfprFabricSanCloudEntry 5 }

cfprFabricSanCloudFsmProgr OBJECT-TYPE
    SYNTAX       Gauge32
    MAX-ACCESS   read-only
    STATUS       current
    DESCRIPTION
        "Cisco Firepower fabric:SanCloud:fsmProgr managed object property"
    ::= { cfprFabricSanCloudEntry 6 }

cfprFabricSanCloudFsmRmtInvErrCode OBJECT-TYPE
    SYNTAX       Gauge32
    MAX-ACCESS   read-only
    STATUS       current
    DESCRIPTION
        "Cisco Firepower fabric:SanCloud:fsmRmtInvErrCode
        managed object property"
    ::= { cfprFabricSanCloudEntry 7 }

cfprFabricSanCloudFsmRmtInvErrDescr OBJECT-TYPE
    SYNTAX       SnmpAdminString
    MAX-ACCESS   read-only
    STATUS       current
    DESCRIPTION
        "Cisco Firepower fabric:SanCloud:fsmRmtInvErrDescr
        managed object property"
    ::= { cfprFabricSanCloudEntry 8 }

cfprFabricSanCloudFsmRmtInvRslt OBJECT-TYPE
    SYNTAX       CfprConditionRemoteInvRslt
    MAX-ACCESS   read-only
    STATUS       current
    DESCRIPTION
        "Cisco Firepower fabric:SanCloud:fsmRmtInvRslt
        managed object property"
    ::= { cfprFabricSanCloudEntry 9 }

cfprFabricSanCloudFsmStageDescr OBJECT-TYPE
    SYNTAX       SnmpAdminString
    MAX-ACCESS   read-only
    STATUS       current
    DESCRIPTION
        "Cisco Firepower fabric:SanCloud:fsmStageDescr
        managed object property"
    ::= { cfprFabricSanCloudEntry 10 }

cfprFabricSanCloudFsmStamp OBJECT-TYPE
    SYNTAX       DateAndTime
    MAX-ACCESS   read-only
    STATUS       current
    DESCRIPTION
        "Cisco Firepower fabric:SanCloud:fsmStamp managed object property"
    ::= { cfprFabricSanCloudEntry 11 }

cfprFabricSanCloudFsmStatus OBJECT-TYPE
    SYNTAX       SnmpAdminString
    MAX-ACCESS   read-only
    STATUS       current
    DESCRIPTION
        "Cisco Firepower fabric:SanCloud:fsmStatus managed
        object property"
    ::= { cfprFabricSanCloudEntry 12 }

cfprFabricSanCloudFsmTry OBJECT-TYPE
    SYNTAX       Gauge32
    MAX-ACCESS   read-only
    STATUS       current
    DESCRIPTION
        "Cisco Firepower fabric:SanCloud:fsmTry managed object property"
    ::= { cfprFabricSanCloudEntry 13 }

cfprFabricSanCloudMode OBJECT-TYPE
    SYNTAX       CfprFabricSwitchingMode
    MAX-ACCESS   read-only
    STATUS       current
    DESCRIPTION
        "Cisco Firepower fabric:SanCloud:mode managed object property"
    ::= { cfprFabricSanCloudEntry 14 }

cfprFabricSanCloudFsmTable OBJECT-TYPE
    SYNTAX           SEQUENCE OF CfprFabricSanCloudFsmEntry
    MAX-ACCESS       not-accessible
    STATUS           current
    DESCRIPTION
        "Cisco Firepower fabric:SanCloudFsm managed object table"
    ::= { cfprFabricObjects 100 }

cfprFabricSanCloudFsmEntry OBJECT-TYPE
    SYNTAX           CfprFabricSanCloudFsmEntry
    MAX-ACCESS       not-accessible
    STATUS           current
    DESCRIPTION
        "Entry for the cfprFabricSanCloudFsmTable table."
    INDEX { cfprFabricSanCloudFsmInstanceId }
    ::= { cfprFabricSanCloudFsmTable 1 }

CfprFabricSanCloudFsmEntry ::= SEQUENCE {
    cfprFabricSanCloudFsmInstanceId                                  CfprManagedObjectId,
    cfprFabricSanCloudFsmDn                                          CfprManagedObjectDn,
    cfprFabricSanCloudFsmRn                                          SnmpAdminString,
    cfprFabricSanCloudFsmCompletionTime                              DateAndTime,
    cfprFabricSanCloudFsmCurrentFsm                                  CfprFabricSanCloudFsmCurrentFsm,
    cfprFabricSanCloudFsmDescrData                                   SnmpAdminString,
    cfprFabricSanCloudFsmFsmStatus                                   CfprFsmFsmStageStatus,
    cfprFabricSanCloudFsmProgress                                    Gauge32,
    cfprFabricSanCloudFsmRmtErrCode                                  Gauge32,
    cfprFabricSanCloudFsmRmtErrDescr                                 SnmpAdminString,
    cfprFabricSanCloudFsmRmtRslt                                     CfprConditionRemoteInvRslt
}

cfprFabricSanCloudFsmInstanceId OBJECT-TYPE
    SYNTAX       CfprManagedObjectId
    MAX-ACCESS   not-accessible
    STATUS       current
    DESCRIPTION
        "Instance identifier of the managed object."
    ::= { cfprFabricSanCloudFsmEntry 1 }

cfprFabricSanCloudFsmDn OBJECT-TYPE
    SYNTAX       CfprManagedObjectDn
    MAX-ACCESS   read-only
    STATUS       current
    DESCRIPTION
        "Cisco Firepower fabric:SanCloudFsm:dn managed object property"
    ::= { cfprFabricSanCloudFsmEntry 2 }

cfprFabricSanCloudFsmRn OBJECT-TYPE
    SYNTAX       SnmpAdminString
    MAX-ACCESS   read-only
    STATUS       current
    DESCRIPTION
        "Cisco Firepower fabric:SanCloudFsm:rn managed object property"
    ::= { cfprFabricSanCloudFsmEntry 3 }

cfprFabricSanCloudFsmCompletionTime OBJECT-TYPE
    SYNTAX       DateAndTime
    MAX-ACCESS   read-only
    STATUS       current
    DESCRIPTION
        "Cisco Firepower fabric:SanCloudFsm:completionTime
        managed object property"
    ::= { cfprFabricSanCloudFsmEntry 4 }

cfprFabricSanCloudFsmCurrentFsm OBJECT-TYPE
    SYNTAX       CfprFabricSanCloudFsmCurrentFsm
    MAX-ACCESS   read-only
    STATUS       current
    DESCRIPTION
        "Cisco Firepower fabric:SanCloudFsm:currentFsm
        managed object property"
    ::= { cfprFabricSanCloudFsmEntry 5 }

cfprFabricSanCloudFsmDescrData OBJECT-TYPE
    SYNTAX       SnmpAdminString
    MAX-ACCESS   read-only
    STATUS       current
    DESCRIPTION
        "Cisco Firepower fabric:SanCloudFsm:descr managed object property"
    ::= { cfprFabricSanCloudFsmEntry 6 }

cfprFabricSanCloudFsmFsmStatus OBJECT-TYPE
    SYNTAX       CfprFsmFsmStageStatus
    MAX-ACCESS   read-only
    STATUS       current
    DESCRIPTION
        "Cisco Firepower fabric:SanCloudFsm:fsmStatus managed
        object property"
    ::= { cfprFabricSanCloudFsmEntry 7 }

cfprFabricSanCloudFsmProgress OBJECT-TYPE
    SYNTAX       Gauge32
    MAX-ACCESS   read-only
    STATUS       current
    DESCRIPTION
        "Cisco Firepower fabric:SanCloudFsm:progress managed
        object property"
    ::= { cfprFabricSanCloudFsmEntry 8 }

cfprFabricSanCloudFsmRmtErrCode OBJECT-TYPE
    SYNTAX       Gauge32
    MAX-ACCESS   read-only
    STATUS       current
    DESCRIPTION
        "Cisco Firepower fabric:SanCloudFsm:rmtErrCode
        managed object property"
    ::= { cfprFabricSanCloudFsmEntry 9 }

cfprFabricSanCloudFsmRmtErrDescr OBJECT-TYPE
    SYNTAX       SnmpAdminString
    MAX-ACCESS   read-only
    STATUS       current
    DESCRIPTION
        "Cisco Firepower fabric:SanCloudFsm:rmtErrDescr
        managed object property"
    ::= { cfprFabricSanCloudFsmEntry 10 }

cfprFabricSanCloudFsmRmtRslt OBJECT-TYPE
    SYNTAX       CfprConditionRemoteInvRslt
    MAX-ACCESS   read-only
    STATUS       current
    DESCRIPTION
        "Cisco Firepower fabric:SanCloudFsm:rmtRslt managed
        object property"
    ::= { cfprFabricSanCloudFsmEntry 11 }

cfprFabricSanCloudFsmStageTable OBJECT-TYPE
    SYNTAX           SEQUENCE OF CfprFabricSanCloudFsmStageEntry
    MAX-ACCESS       not-accessible
    STATUS           current
    DESCRIPTION
        "Cisco Firepower fabric:SanCloudFsmStage managed object table"
    ::= { cfprFabricObjects 101 }

cfprFabricSanCloudFsmStageEntry OBJECT-TYPE
    SYNTAX           CfprFabricSanCloudFsmStageEntry
    MAX-ACCESS       not-accessible
    STATUS           current
    DESCRIPTION
        "Entry for the cfprFabricSanCloudFsmStageTable table."
    INDEX { cfprFabricSanCloudFsmStageInstanceId }
    ::= { cfprFabricSanCloudFsmStageTable 1 }

CfprFabricSanCloudFsmStageEntry ::= SEQUENCE {
    cfprFabricSanCloudFsmStageInstanceId                             CfprManagedObjectId,
    cfprFabricSanCloudFsmStageDn                                     CfprManagedObjectDn,
    cfprFabricSanCloudFsmStageRn                                     SnmpAdminString,
    cfprFabricSanCloudFsmStageDescrData                              SnmpAdminString,
    cfprFabricSanCloudFsmStageLastUpdateTime                         DateAndTime,
    cfprFabricSanCloudFsmStageName                                   CfprFabricSanCloudFsmStageName,
    cfprFabricSanCloudFsmStageOrder                                  Gauge32,
    cfprFabricSanCloudFsmStageRetry                                  Gauge32,
    cfprFabricSanCloudFsmStageStageStatus                            CfprFsmFsmStageStatus
}

cfprFabricSanCloudFsmStageInstanceId OBJECT-TYPE
    SYNTAX       CfprManagedObjectId
    MAX-ACCESS   not-accessible
    STATUS       current
    DESCRIPTION
        "Instance identifier of the managed object."
    ::= { cfprFabricSanCloudFsmStageEntry 1 }

cfprFabricSanCloudFsmStageDn OBJECT-TYPE
    SYNTAX       CfprManagedObjectDn
    MAX-ACCESS   read-only
    STATUS       current
    DESCRIPTION
        "Cisco Firepower fabric:SanCloudFsmStage:dn managed
        object property"
    ::= { cfprFabricSanCloudFsmStageEntry 2 }

cfprFabricSanCloudFsmStageRn OBJECT-TYPE
    SYNTAX       SnmpAdminString
    MAX-ACCESS   read-only
    STATUS       current
    DESCRIPTION
        "Cisco Firepower fabric:SanCloudFsmStage:rn managed
        object property"
    ::= { cfprFabricSanCloudFsmStageEntry 3 }

cfprFabricSanCloudFsmStageDescrData OBJECT-TYPE
    SYNTAX       SnmpAdminString
    MAX-ACCESS   read-only
    STATUS       current
    DESCRIPTION
        "Cisco Firepower fabric:SanCloudFsmStage:descr
        managed object property"
    ::= { cfprFabricSanCloudFsmStageEntry 4 }

cfprFabricSanCloudFsmStageLastUpdateTime OBJECT-TYPE
    SYNTAX       DateAndTime
    MAX-ACCESS   read-only
    STATUS       current
    DESCRIPTION
        "Cisco Firepower fabric:SanCloudFsmStage:lastUpdateTime
        managed object property"
    ::= { cfprFabricSanCloudFsmStageEntry 5 }

cfprFabricSanCloudFsmStageName OBJECT-TYPE
    SYNTAX       CfprFabricSanCloudFsmStageName
    MAX-ACCESS   read-only
    STATUS       current
    DESCRIPTION
        "Cisco Firepower fabric:SanCloudFsmStage:name managed
        object property"
    ::= { cfprFabricSanCloudFsmStageEntry 6 }

cfprFabricSanCloudFsmStageOrder OBJECT-TYPE
    SYNTAX       Gauge32
    MAX-ACCESS   read-only
    STATUS       current
    DESCRIPTION
        "Cisco Firepower fabric:SanCloudFsmStage:order
        managed object property"
    ::= { cfprFabricSanCloudFsmStageEntry 7 }

cfprFabricSanCloudFsmStageRetry OBJECT-TYPE
    SYNTAX       Gauge32
    MAX-ACCESS   read-only
    STATUS       current
    DESCRIPTION
        "Cisco Firepower fabric:SanCloudFsmStage:retry
        managed object property"
    ::= { cfprFabricSanCloudFsmStageEntry 8 }

cfprFabricSanCloudFsmStageStageStatus OBJECT-TYPE
    SYNTAX       CfprFsmFsmStageStatus
    MAX-ACCESS   read-only
    STATUS       current
    DESCRIPTION
        "Cisco Firepower fabric:SanCloudFsmStage:stageStatus
        managed object property"
    ::= { cfprFabricSanCloudFsmStageEntry 9 }

cfprFabricSanCloudFsmTaskTable OBJECT-TYPE
    SYNTAX           SEQUENCE OF CfprFabricSanCloudFsmTaskEntry
    MAX-ACCESS       not-accessible
    STATUS           current
    DESCRIPTION
        "Cisco Firepower fabric:SanCloudFsmTask managed object table"
    ::= { cfprFabricObjects 102 }

cfprFabricSanCloudFsmTaskEntry OBJECT-TYPE
    SYNTAX           CfprFabricSanCloudFsmTaskEntry
    MAX-ACCESS       not-accessible
    STATUS           current
    DESCRIPTION
        "Entry for the cfprFabricSanCloudFsmTaskTable table."
    INDEX { cfprFabricSanCloudFsmTaskInstanceId }
    ::= { cfprFabricSanCloudFsmTaskTable 1 }

CfprFabricSanCloudFsmTaskEntry ::= SEQUENCE {
    cfprFabricSanCloudFsmTaskInstanceId                              CfprManagedObjectId,
    cfprFabricSanCloudFsmTaskDn                                      CfprManagedObjectDn,
    cfprFabricSanCloudFsmTaskRn                                      SnmpAdminString,
    cfprFabricSanCloudFsmTaskCompletion                              CfprFsmCompletion,
    cfprFabricSanCloudFsmTaskFlags                                   CfprFsmFlags,
    cfprFabricSanCloudFsmTaskItem                                    CfprFabricSanCloudFsmTaskItem,
    cfprFabricSanCloudFsmTaskSeqId                                   Gauge32
}

cfprFabricSanCloudFsmTaskInstanceId OBJECT-TYPE
    SYNTAX       CfprManagedObjectId
    MAX-ACCESS   not-accessible
    STATUS       current
    DESCRIPTION
        "Instance identifier of the managed object."
    ::= { cfprFabricSanCloudFsmTaskEntry 1 }

cfprFabricSanCloudFsmTaskDn OBJECT-TYPE
    SYNTAX       CfprManagedObjectDn
    MAX-ACCESS   read-only
    STATUS       current
    DESCRIPTION
        "Cisco Firepower fabric:SanCloudFsmTask:dn managed
        object property"
    ::= { cfprFabricSanCloudFsmTaskEntry 2 }

cfprFabricSanCloudFsmTaskRn OBJECT-TYPE
    SYNTAX       SnmpAdminString
    MAX-ACCESS   read-only
    STATUS       current
    DESCRIPTION
        "Cisco Firepower fabric:SanCloudFsmTask:rn managed
        object property"
    ::= { cfprFabricSanCloudFsmTaskEntry 3 }

cfprFabricSanCloudFsmTaskCompletion OBJECT-TYPE
    SYNTAX       CfprFsmCompletion
    MAX-ACCESS   read-only
    STATUS       current
    DESCRIPTION
        "Cisco Firepower fabric:SanCloudFsmTask:completion
        managed object property"
    ::= { cfprFabricSanCloudFsmTaskEntry 4 }

cfprFabricSanCloudFsmTaskFlags OBJECT-TYPE
    SYNTAX       CfprFsmFlags
    MAX-ACCESS   read-only
    STATUS       current
    DESCRIPTION
        "Cisco Firepower fabric:SanCloudFsmTask:flags managed
        object property"
    ::= { cfprFabricSanCloudFsmTaskEntry 5 }

cfprFabricSanCloudFsmTaskItem OBJECT-TYPE
    SYNTAX       CfprFabricSanCloudFsmTaskItem
    MAX-ACCESS   read-only
    STATUS       current
    DESCRIPTION
        "Cisco Firepower fabric:SanCloudFsmTask:item managed
        object property"
    ::= { cfprFabricSanCloudFsmTaskEntry 6 }

cfprFabricSanCloudFsmTaskSeqId OBJECT-TYPE
    SYNTAX       Gauge32
    MAX-ACCESS   read-only
    STATUS       current
    DESCRIPTION
        "Cisco Firepower fabric:SanCloudFsmTask:seqId managed
        object property"
    ::= { cfprFabricSanCloudFsmTaskEntry 7 }

cfprFabricSanMonCloudTable OBJECT-TYPE
    SYNTAX           SEQUENCE OF CfprFabricSanMonCloudEntry
    MAX-ACCESS       not-accessible
    STATUS           current
    DESCRIPTION
        "Cisco Firepower fabric:SanMonCloud managed object table"
    ::= { cfprFabricObjects 103 }

cfprFabricSanMonCloudEntry OBJECT-TYPE
    SYNTAX           CfprFabricSanMonCloudEntry
    MAX-ACCESS       not-accessible
    STATUS           current
    DESCRIPTION
        "Entry for the cfprFabricSanMonCloudTable table."
    INDEX { cfprFabricSanMonCloudInstanceId }
    ::= { cfprFabricSanMonCloudTable 1 }

CfprFabricSanMonCloudEntry ::= SEQUENCE {
    cfprFabricSanMonCloudInstanceId                                  CfprManagedObjectId,
    cfprFabricSanMonCloudDn                                          CfprManagedObjectDn,
    cfprFabricSanMonCloudRn                                          SnmpAdminString,
    cfprFabricSanMonCloudMode                                        CfprFabricSwitchingMode
}

cfprFabricSanMonCloudInstanceId OBJECT-TYPE
    SYNTAX       CfprManagedObjectId
    MAX-ACCESS   not-accessible
    STATUS       current
    DESCRIPTION
        "Instance identifier of the managed object."
    ::= { cfprFabricSanMonCloudEntry 1 }

cfprFabricSanMonCloudDn OBJECT-TYPE
    SYNTAX       CfprManagedObjectDn
    MAX-ACCESS   read-only
    STATUS       current
    DESCRIPTION
        "Cisco Firepower fabric:SanMonCloud:dn managed object property"
    ::= { cfprFabricSanMonCloudEntry 2 }

cfprFabricSanMonCloudRn OBJECT-TYPE
    SYNTAX       SnmpAdminString
    MAX-ACCESS   read-only
    STATUS       current
    DESCRIPTION
        "Cisco Firepower fabric:SanMonCloud:rn managed object property"
    ::= { cfprFabricSanMonCloudEntry 3 }

cfprFabricSanMonCloudMode OBJECT-TYPE
    SYNTAX       CfprFabricSwitchingMode
    MAX-ACCESS   read-only
    STATUS       current
    DESCRIPTION
        "Cisco Firepower fabric:SanMonCloud:mode managed object property"
    ::= { cfprFabricSanMonCloudEntry 4 }

cfprFabricSanPinGroupTable OBJECT-TYPE
    SYNTAX           SEQUENCE OF CfprFabricSanPinGroupEntry
    MAX-ACCESS       not-accessible
    STATUS           current
    DESCRIPTION
        "Cisco Firepower fabric:SanPinGroup managed object table"
    ::= { cfprFabricObjects 104 }

cfprFabricSanPinGroupEntry OBJECT-TYPE
    SYNTAX           CfprFabricSanPinGroupEntry
    MAX-ACCESS       not-accessible
    STATUS           current
    DESCRIPTION
        "Entry for the cfprFabricSanPinGroupTable table."
    INDEX { cfprFabricSanPinGroupInstanceId }
    ::= { cfprFabricSanPinGroupTable 1 }

CfprFabricSanPinGroupEntry ::= SEQUENCE {
    cfprFabricSanPinGroupInstanceId                                  CfprManagedObjectId,
    cfprFabricSanPinGroupDn                                          CfprManagedObjectDn,
    cfprFabricSanPinGroupRn                                          SnmpAdminString,
    cfprFabricSanPinGroupDescr                                       SnmpAdminString,
    cfprFabricSanPinGroupIntId                                       SnmpAdminString,
    cfprFabricSanPinGroupName                                        SnmpAdminString,
    cfprFabricSanPinGroupPolicyLevel                                 Gauge32,
    cfprFabricSanPinGroupPolicyOwner                                 CfprPolicyPolicyOwner,
    cfprFabricSanPinGroupSize                                        Gauge32
}

cfprFabricSanPinGroupInstanceId OBJECT-TYPE
    SYNTAX       CfprManagedObjectId
    MAX-ACCESS   not-accessible
    STATUS       current
    DESCRIPTION
        "Instance identifier of the managed object."
    ::= { cfprFabricSanPinGroupEntry 1 }

cfprFabricSanPinGroupDn OBJECT-TYPE
    SYNTAX       CfprManagedObjectDn
    MAX-ACCESS   read-only
    STATUS       current
    DESCRIPTION
        "Cisco Firepower fabric:SanPinGroup:dn managed object property"
    ::= { cfprFabricSanPinGroupEntry 2 }

cfprFabricSanPinGroupRn OBJECT-TYPE
    SYNTAX       SnmpAdminString
    MAX-ACCESS   read-only
    STATUS       current
    DESCRIPTION
        "Cisco Firepower fabric:SanPinGroup:rn managed object property"
    ::= { cfprFabricSanPinGroupEntry 3 }

cfprFabricSanPinGroupDescr OBJECT-TYPE
    SYNTAX       SnmpAdminString
    MAX-ACCESS   read-only
    STATUS       current
    DESCRIPTION
        "Cisco Firepower fabric:SanPinGroup:descr managed object property"
    ::= { cfprFabricSanPinGroupEntry 4 }

cfprFabricSanPinGroupIntId OBJECT-TYPE
    SYNTAX       SnmpAdminString
    MAX-ACCESS   read-only
    STATUS       current
    DESCRIPTION
        "Cisco Firepower fabric:SanPinGroup:intId managed object property"
    ::= { cfprFabricSanPinGroupEntry 5 }

cfprFabricSanPinGroupName OBJECT-TYPE
    SYNTAX       SnmpAdminString
    MAX-ACCESS   read-only
    STATUS       current
    DESCRIPTION
        "Cisco Firepower fabric:SanPinGroup:name managed object property"
    ::= { cfprFabricSanPinGroupEntry 6 }

cfprFabricSanPinGroupPolicyLevel OBJECT-TYPE
    SYNTAX       Gauge32
    MAX-ACCESS   read-only
    STATUS       current
    DESCRIPTION
        "Cisco Firepower fabric:SanPinGroup:policyLevel
        managed object property"
    ::= { cfprFabricSanPinGroupEntry 7 }

cfprFabricSanPinGroupPolicyOwner OBJECT-TYPE
    SYNTAX       CfprPolicyPolicyOwner
    MAX-ACCESS   read-only
    STATUS       current
    DESCRIPTION
        "Cisco Firepower fabric:SanPinGroup:policyOwner
        managed object property"
    ::= { cfprFabricSanPinGroupEntry 8 }

cfprFabricSanPinGroupSize OBJECT-TYPE
    SYNTAX       Gauge32
    MAX-ACCESS   read-only
    STATUS       current
    DESCRIPTION
        "Cisco Firepower fabric:SanPinGroup:size managed object property"
    ::= { cfprFabricSanPinGroupEntry 9 }

cfprFabricSanPinTargetTable OBJECT-TYPE
    SYNTAX           SEQUENCE OF CfprFabricSanPinTargetEntry
    MAX-ACCESS       not-accessible
    STATUS           current
    DESCRIPTION
        "Cisco Firepower fabric:SanPinTarget managed object table"
    ::= { cfprFabricObjects 105 }

cfprFabricSanPinTargetEntry OBJECT-TYPE
    SYNTAX           CfprFabricSanPinTargetEntry
    MAX-ACCESS       not-accessible
    STATUS           current
    DESCRIPTION
        "Entry for the cfprFabricSanPinTargetTable table."
    INDEX { cfprFabricSanPinTargetInstanceId }
    ::= { cfprFabricSanPinTargetTable 1 }

CfprFabricSanPinTargetEntry ::= SEQUENCE {
    cfprFabricSanPinTargetInstanceId                                 CfprManagedObjectId,
    cfprFabricSanPinTargetDn                                         CfprManagedObjectDn,
    cfprFabricSanPinTargetRn                                         SnmpAdminString,
    cfprFabricSanPinTargetEpDn                                       SnmpAdminString,
    cfprFabricSanPinTargetFabricId                                   SnmpAdminString,
    cfprFabricSanPinTargetTargetStatus                               CfprFabricTargetStatus
}

cfprFabricSanPinTargetInstanceId OBJECT-TYPE
    SYNTAX       CfprManagedObjectId
    MAX-ACCESS   not-accessible
    STATUS       current
    DESCRIPTION
        "Instance identifier of the managed object."
    ::= { cfprFabricSanPinTargetEntry 1 }

cfprFabricSanPinTargetDn OBJECT-TYPE
    SYNTAX       CfprManagedObjectDn
    MAX-ACCESS   read-only
    STATUS       current
    DESCRIPTION
        "Cisco Firepower fabric:SanPinTarget:dn managed object property"
    ::= { cfprFabricSanPinTargetEntry 2 }

cfprFabricSanPinTargetRn OBJECT-TYPE
    SYNTAX       SnmpAdminString
    MAX-ACCESS   read-only
    STATUS       current
    DESCRIPTION
        "Cisco Firepower fabric:SanPinTarget:rn managed object property"
    ::= { cfprFabricSanPinTargetEntry 3 }

cfprFabricSanPinTargetEpDn OBJECT-TYPE
    SYNTAX       SnmpAdminString
    MAX-ACCESS   read-only
    STATUS       current
    DESCRIPTION
        "Cisco Firepower fabric:SanPinTarget:epDn managed object property"
    ::= { cfprFabricSanPinTargetEntry 4 }

cfprFabricSanPinTargetFabricId OBJECT-TYPE
    SYNTAX       SnmpAdminString
    MAX-ACCESS   read-only
    STATUS       current
    DESCRIPTION
        "Cisco Firepower fabric:SanPinTarget:fabricId managed
        object property"
    ::= { cfprFabricSanPinTargetEntry 5 }

cfprFabricSanPinTargetTargetStatus OBJECT-TYPE
    SYNTAX       CfprFabricTargetStatus
    MAX-ACCESS   read-only
    STATUS       current
    DESCRIPTION
        "Cisco Firepower fabric:SanPinTarget:targetStatus
        managed object property"
    ::= { cfprFabricSanPinTargetEntry 6 }

cfprFabricSspEthMonTable OBJECT-TYPE
    SYNTAX           SEQUENCE OF CfprFabricSspEthMonEntry
    MAX-ACCESS       not-accessible
    STATUS           current
    DESCRIPTION
        "Cisco Firepower fabric:SspEthMon managed object table"
    ::= { cfprFabricObjects 126 }

cfprFabricSspEthMonEntry OBJECT-TYPE
    SYNTAX           CfprFabricSspEthMonEntry
    MAX-ACCESS       not-accessible
    STATUS           current
    DESCRIPTION
        "Entry for the cfprFabricSspEthMonTable table."
    INDEX { cfprFabricSspEthMonInstanceId }
    ::= { cfprFabricSspEthMonTable 1 }

CfprFabricSspEthMonEntry ::= SEQUENCE {
    cfprFabricSspEthMonInstanceId                                    CfprManagedObjectId,
    cfprFabricSspEthMonDn                                            CfprManagedObjectDn,
    cfprFabricSspEthMonRn                                            SnmpAdminString,
    cfprFabricSspEthMonAdminState                                    CfprFabricSspMonAdminState,
    cfprFabricSspEthMonAppendFlag                                    CfprFabricSspEthMonAppendFlag,
    cfprFabricSspEthMonConfigFailReason                              SnmpAdminString,
    cfprFabricSspEthMonDelPcap                                       CfprFabricSspMonDelPcap,
    cfprFabricSspEthMonId                                            CfprNetworkSwitchId,
    cfprFabricSspEthMonIsConfigSuccess                               TruthValue,
    cfprFabricSspEthMonName                                          SnmpAdminString,
    cfprFabricSspEthMonOperState                                     CfprFabricSspMonOperState,
    cfprFabricSspEthMonOperStateReason                               CfprFabricSspMonOperStateReason,
    cfprFabricSspEthMonPeerDn                                        SnmpAdminString,
    cfprFabricSspEthMonSession                                       Gauge32,
    cfprFabricSspEthMonSessionMemUsage                               Gauge32,
    cfprFabricSspEthMonSourceConfigured                              Gauge32,
    cfprFabricSspEthMonDelAllSessEnabledState                        CfprFabricSspEthMonDelAllSessEnabledState,
    cfprFabricSspEthMonDropCount                                     Unsigned64,
    cfprFabricSspEthMonErrorCode                                     SnmpAdminString,
    cfprFabricSspEthMonIsConfiguredByAG                              TruthValue,
    cfprFabricSspEthMonReBoot                                        SnmpAdminString,
    cfprFabricSspEthMonSessionPcapSnapLen                            Gauge32
}

cfprFabricSspEthMonInstanceId OBJECT-TYPE
    SYNTAX       CfprManagedObjectId
    MAX-ACCESS   not-accessible
    STATUS       current
    DESCRIPTION
        "Instance identifier of the managed object."
    ::= { cfprFabricSspEthMonEntry 1 }

cfprFabricSspEthMonDn OBJECT-TYPE
    SYNTAX       CfprManagedObjectDn
    MAX-ACCESS   read-only
    STATUS       current
    DESCRIPTION
        "Cisco Firepower fabric:SspEthMon:dn managed object property"
    ::= { cfprFabricSspEthMonEntry 2 }

cfprFabricSspEthMonRn OBJECT-TYPE
    SYNTAX       SnmpAdminString
    MAX-ACCESS   read-only
    STATUS       current
    DESCRIPTION
        "Cisco Firepower fabric:SspEthMon:rn managed object property"
    ::= { cfprFabricSspEthMonEntry 3 }

cfprFabricSspEthMonAdminState OBJECT-TYPE
    SYNTAX       CfprFabricSspMonAdminState
    MAX-ACCESS   read-only
    STATUS       current
    DESCRIPTION
        "Cisco Firepower fabric:SspEthMon:adminState managed
        object property"
    ::= { cfprFabricSspEthMonEntry 4 }

cfprFabricSspEthMonAppendFlag OBJECT-TYPE
    SYNTAX       CfprFabricSspEthMonAppendFlag
    MAX-ACCESS   read-only
    STATUS       current
    DESCRIPTION
        "Cisco Firepower fabric:SspEthMon:appendFlag managed
        object property"
    ::= { cfprFabricSspEthMonEntry 5 }

cfprFabricSspEthMonConfigFailReason OBJECT-TYPE
    SYNTAX       SnmpAdminString
    MAX-ACCESS   read-only
    STATUS       current
    DESCRIPTION
        "Cisco Firepower fabric:SspEthMon:configFailReason
        managed object property"
    ::= { cfprFabricSspEthMonEntry 6 }

cfprFabricSspEthMonDelPcap OBJECT-TYPE
    SYNTAX       CfprFabricSspMonDelPcap
    MAX-ACCESS   read-only
    STATUS       current
    DESCRIPTION
        "Cisco Firepower fabric:SspEthMon:delPcap managed object property"
    ::= { cfprFabricSspEthMonEntry 7 }

cfprFabricSspEthMonId OBJECT-TYPE
    SYNTAX       CfprNetworkSwitchId
    MAX-ACCESS   read-only
    STATUS       current
    DESCRIPTION
        "Cisco Firepower fabric:SspEthMon:id managed object property"
    ::= { cfprFabricSspEthMonEntry 8 }

cfprFabricSspEthMonIsConfigSuccess OBJECT-TYPE
    SYNTAX       TruthValue
    MAX-ACCESS   read-only
    STATUS       current
    DESCRIPTION
        "Cisco Firepower fabric:SspEthMon:isConfigSuccess
        managed object property"
    ::= { cfprFabricSspEthMonEntry 9 }

cfprFabricSspEthMonName OBJECT-TYPE
    SYNTAX       SnmpAdminString
    MAX-ACCESS   read-only
    STATUS       current
    DESCRIPTION
        "Cisco Firepower fabric:SspEthMon:name managed object property"
    ::= { cfprFabricSspEthMonEntry 10 }

cfprFabricSspEthMonOperState OBJECT-TYPE
    SYNTAX       CfprFabricSspMonOperState
    MAX-ACCESS   read-only
    STATUS       current
    DESCRIPTION
        "Cisco Firepower fabric:SspEthMon:operState managed
        object property"
    ::= { cfprFabricSspEthMonEntry 11 }

cfprFabricSspEthMonOperStateReason OBJECT-TYPE
    SYNTAX       CfprFabricSspMonOperStateReason
    MAX-ACCESS   read-only
    STATUS       current
    DESCRIPTION
        "Cisco Firepower fabric:SspEthMon:operStateReason
        managed object property"
    ::= { cfprFabricSspEthMonEntry 12 }

cfprFabricSspEthMonPeerDn OBJECT-TYPE
    SYNTAX       SnmpAdminString
    MAX-ACCESS   read-only
    STATUS       current
    DESCRIPTION
        "Cisco Firepower fabric:SspEthMon:peerDn managed object property"
    ::= { cfprFabricSspEthMonEntry 13 }

cfprFabricSspEthMonSession OBJECT-TYPE
    SYNTAX       Gauge32
    MAX-ACCESS   read-only
    STATUS       current
    DESCRIPTION
        "Cisco Firepower fabric:SspEthMon:session managed object property"
    ::= { cfprFabricSspEthMonEntry 14 }

cfprFabricSspEthMonSessionMemUsage OBJECT-TYPE
    SYNTAX       Gauge32
    MAX-ACCESS   read-only
    STATUS       current
    DESCRIPTION
        "Cisco Firepower fabric:SspEthMon:sessionMemUsage
        managed object property"
    ::= { cfprFabricSspEthMonEntry 15 }

cfprFabricSspEthMonSourceConfigured OBJECT-TYPE
    SYNTAX       Gauge32
    MAX-ACCESS   read-only
    STATUS       current
    DESCRIPTION
        "Cisco Firepower fabric:SspEthMon:sourceConfigured
        managed object property"
    ::= { cfprFabricSspEthMonEntry 16 }

cfprFabricSspEthMonDelAllSessEnabledState OBJECT-TYPE
    SYNTAX       CfprFabricSspEthMonDelAllSessEnabledState
    MAX-ACCESS   read-only
    STATUS       current
    DESCRIPTION
        "Cisco Firepower fabric:SspEthMon:delAllSessEnabledState
        managed object property"
    ::= { cfprFabricSspEthMonEntry 17 }

cfprFabricSspEthMonDropCount OBJECT-TYPE
    SYNTAX       Unsigned64
    MAX-ACCESS   read-only
    STATUS       current
    DESCRIPTION
        "Cisco Firepower fabric:SspEthMon:dropCount managed
        object property"
    ::= { cfprFabricSspEthMonEntry 18 }

cfprFabricSspEthMonErrorCode OBJECT-TYPE
    SYNTAX       SnmpAdminString
    MAX-ACCESS   read-only
    STATUS       current
    DESCRIPTION
        "Cisco Firepower fabric:SspEthMon:errorCode managed
        object property"
    ::= { cfprFabricSspEthMonEntry 19 }

cfprFabricSspEthMonIsConfiguredByAG OBJECT-TYPE
    SYNTAX       TruthValue
    MAX-ACCESS   read-only
    STATUS       current
    DESCRIPTION
        "Cisco Firepower fabric:SspEthMon:isConfiguredByAG
        managed object property"
    ::= { cfprFabricSspEthMonEntry 20 }

cfprFabricSspEthMonReBoot OBJECT-TYPE
    SYNTAX       SnmpAdminString
    MAX-ACCESS   read-only
    STATUS       current
    DESCRIPTION
        "Cisco Firepower fabric:SspEthMon:reBoot managed object property"
    ::= { cfprFabricSspEthMonEntry 21 }

cfprFabricSspEthMonSessionPcapSnapLen OBJECT-TYPE
    SYNTAX       Gauge32
    MAX-ACCESS   read-only
    STATUS       current
    DESCRIPTION
        "Cisco Firepower fabric:SspEthMon:sessionPcapSnapLen
        managed object property"
    ::= { cfprFabricSspEthMonEntry 22 }

cfprFabricSspEthMonFilterEpTable OBJECT-TYPE
    SYNTAX           SEQUENCE OF CfprFabricSspEthMonFilterEpEntry
    MAX-ACCESS       not-accessible
    STATUS           current
    DESCRIPTION
        "Cisco Firepower fabric:SspEthMonFilterEp managed object table"
    ::= { cfprFabricObjects 127 }

cfprFabricSspEthMonFilterEpEntry OBJECT-TYPE
    SYNTAX           CfprFabricSspEthMonFilterEpEntry
    MAX-ACCESS       not-accessible
    STATUS           current
    DESCRIPTION
        "Entry for the cfprFabricSspEthMonFilterEpTable table."
    INDEX { cfprFabricSspEthMonFilterEpInstanceId }
    ::= { cfprFabricSspEthMonFilterEpTable 1 }

CfprFabricSspEthMonFilterEpEntry ::= SEQUENCE {
    cfprFabricSspEthMonFilterEpInstanceId                            CfprManagedObjectId,
    cfprFabricSspEthMonFilterEpDn                                    CfprManagedObjectDn,
    cfprFabricSspEthMonFilterEpRn                                    SnmpAdminString,
    cfprFabricSspEthMonFilterEpDestIp                                InetAddressIPv4,
    cfprFabricSspEthMonFilterEpDestMAC                               MacAddress,
    cfprFabricSspEthMonFilterEpDestPort                              Gauge32,
    cfprFabricSspEthMonFilterEpEthertype                             Gauge32,
    cfprFabricSspEthMonFilterEpIvlan                                 Gauge32,
    cfprFabricSspEthMonFilterEpNameId                                SnmpAdminString,
    cfprFabricSspEthMonFilterEpOvlan                                 Gauge32,
    cfprFabricSspEthMonFilterEpProtocol                              Gauge32,
    cfprFabricSspEthMonFilterEpSrcIp                                 InetAddressIPv4,
    cfprFabricSspEthMonFilterEpSrcMAC                                MacAddress,
    cfprFabricSspEthMonFilterEpSrcPort                               Gauge32,
    cfprFabricSspEthMonFilterEpDestIpv6                              InetAddressIPv6,
    cfprFabricSspEthMonFilterEpEcmpId                                Gauge32,
    cfprFabricSspEthMonFilterEpSrcIpv6                               InetAddressIPv6,
    cfprFabricSspEthMonFilterEpSubvlan                               Gauge32,
    cfprFabricSspEthMonFilterEpVifId                                 Gauge32
}

cfprFabricSspEthMonFilterEpInstanceId OBJECT-TYPE
    SYNTAX       CfprManagedObjectId
    MAX-ACCESS   not-accessible
    STATUS       current
    DESCRIPTION
        "Instance identifier of the managed object."
    ::= { cfprFabricSspEthMonFilterEpEntry 1 }

cfprFabricSspEthMonFilterEpDn OBJECT-TYPE
    SYNTAX       CfprManagedObjectDn
    MAX-ACCESS   read-only
    STATUS       current
    DESCRIPTION
        "Cisco Firepower fabric:SspEthMonFilterEp:dn managed
        object property"
    ::= { cfprFabricSspEthMonFilterEpEntry 2 }

cfprFabricSspEthMonFilterEpRn OBJECT-TYPE
    SYNTAX       SnmpAdminString
    MAX-ACCESS   read-only
    STATUS       current
    DESCRIPTION
        "Cisco Firepower fabric:SspEthMonFilterEp:rn managed
        object property"
    ::= { cfprFabricSspEthMonFilterEpEntry 3 }

cfprFabricSspEthMonFilterEpDestIp OBJECT-TYPE
    SYNTAX       InetAddressIPv4
    MAX-ACCESS   read-only
    STATUS       current
    DESCRIPTION
        "Cisco Firepower fabric:SspEthMonFilterEp:destIp
        managed object property"
    ::= { cfprFabricSspEthMonFilterEpEntry 4 }

cfprFabricSspEthMonFilterEpDestMAC OBJECT-TYPE
    SYNTAX       MacAddress
    MAX-ACCESS   read-only
    STATUS       current
    DESCRIPTION
        "Cisco Firepower fabric:SspEthMonFilterEp:destMAC
        managed object property"
    ::= { cfprFabricSspEthMonFilterEpEntry 5 }

cfprFabricSspEthMonFilterEpDestPort OBJECT-TYPE
    SYNTAX       Gauge32
    MAX-ACCESS   read-only
    STATUS       current
    DESCRIPTION
        "Cisco Firepower fabric:SspEthMonFilterEp:destPort
        managed object property"
    ::= { cfprFabricSspEthMonFilterEpEntry 6 }

cfprFabricSspEthMonFilterEpEthertype OBJECT-TYPE
    SYNTAX       Gauge32
    MAX-ACCESS   read-only
    STATUS       current
    DESCRIPTION
        "Cisco Firepower fabric:SspEthMonFilterEp:ethertype
        managed object property"
    ::= { cfprFabricSspEthMonFilterEpEntry 7 }

cfprFabricSspEthMonFilterEpIvlan OBJECT-TYPE
    SYNTAX       Gauge32
    MAX-ACCESS   read-only
    STATUS       current
    DESCRIPTION
        "Cisco Firepower fabric:SspEthMonFilterEp:ivlan
        managed object property"
    ::= { cfprFabricSspEthMonFilterEpEntry 8 }

cfprFabricSspEthMonFilterEpNameId OBJECT-TYPE
    SYNTAX       SnmpAdminString
    MAX-ACCESS   read-only
    STATUS       current
    DESCRIPTION
        "Cisco Firepower fabric:SspEthMonFilterEp:nameId
        managed object property"
    ::= { cfprFabricSspEthMonFilterEpEntry 9 }

cfprFabricSspEthMonFilterEpOvlan OBJECT-TYPE
    SYNTAX       Gauge32
    MAX-ACCESS   read-only
    STATUS       current
    DESCRIPTION
        "Cisco Firepower fabric:SspEthMonFilterEp:ovlan
        managed object property"
    ::= { cfprFabricSspEthMonFilterEpEntry 10 }

cfprFabricSspEthMonFilterEpProtocol OBJECT-TYPE
    SYNTAX       Gauge32
    MAX-ACCESS   read-only
    STATUS       current
    DESCRIPTION
        "Cisco Firepower fabric:SspEthMonFilterEp:protocol
        managed object property"
    ::= { cfprFabricSspEthMonFilterEpEntry 11 }

cfprFabricSspEthMonFilterEpSrcIp OBJECT-TYPE
    SYNTAX       InetAddressIPv4
    MAX-ACCESS   read-only
    STATUS       current
    DESCRIPTION
        "Cisco Firepower fabric:SspEthMonFilterEp:srcIp
        managed object property"
    ::= { cfprFabricSspEthMonFilterEpEntry 12 }

cfprFabricSspEthMonFilterEpSrcMAC OBJECT-TYPE
    SYNTAX       MacAddress
    MAX-ACCESS   read-only
    STATUS       current
    DESCRIPTION
        "Cisco Firepower fabric:SspEthMonFilterEp:srcMAC
        managed object property"
    ::= { cfprFabricSspEthMonFilterEpEntry 13 }

cfprFabricSspEthMonFilterEpSrcPort OBJECT-TYPE
    SYNTAX       Gauge32
    MAX-ACCESS   read-only
    STATUS       current
    DESCRIPTION
        "Cisco Firepower fabric:SspEthMonFilterEp:srcPort
        managed object property"
    ::= { cfprFabricSspEthMonFilterEpEntry 14 }

cfprFabricSspEthMonFilterEpDestIpv6 OBJECT-TYPE
    SYNTAX       InetAddressIPv6
    MAX-ACCESS   read-only
    STATUS       current
    DESCRIPTION
        "Cisco Firepower fabric:SspEthMonFilterEp:destIpv6
        managed object property"
    ::= { cfprFabricSspEthMonFilterEpEntry 15 }

cfprFabricSspEthMonFilterEpEcmpId OBJECT-TYPE
    SYNTAX       Gauge32
    MAX-ACCESS   read-only
    STATUS       current
    DESCRIPTION
        "Cisco Firepower fabric:SspEthMonFilterEp:ecmpId
        managed object property"
    ::= { cfprFabricSspEthMonFilterEpEntry 16 }

cfprFabricSspEthMonFilterEpSrcIpv6 OBJECT-TYPE
    SYNTAX       InetAddressIPv6
    MAX-ACCESS   read-only
    STATUS       current
    DESCRIPTION
        "Cisco Firepower fabric:SspEthMonFilterEp:srcIpv6
        managed object property"
    ::= { cfprFabricSspEthMonFilterEpEntry 17 }

cfprFabricSspEthMonFilterEpSubvlan OBJECT-TYPE
    SYNTAX       Gauge32
    MAX-ACCESS   read-only
    STATUS       current
    DESCRIPTION
        "Cisco Firepower fabric:SspEthMonFilterEp:subvlan
        managed object property"
    ::= { cfprFabricSspEthMonFilterEpEntry 18 }

cfprFabricSspEthMonFilterEpVifId OBJECT-TYPE
    SYNTAX       Gauge32
    MAX-ACCESS   read-only
    STATUS       current
    DESCRIPTION
        "Cisco Firepower fabric:SspEthMonFilterEp:vifId
        managed object property"
    ::= { cfprFabricSspEthMonFilterEpEntry 19 }

cfprFabricSspEthMonSrcAppEpTable OBJECT-TYPE
    SYNTAX           SEQUENCE OF CfprFabricSspEthMonSrcAppEpEntry
    MAX-ACCESS       not-accessible
    STATUS           current
    DESCRIPTION
        "Cisco Firepower fabric:SspEthMonSrcAppEp managed object table"
    ::= { cfprFabricObjects 128 }

cfprFabricSspEthMonSrcAppEpEntry OBJECT-TYPE
    SYNTAX           CfprFabricSspEthMonSrcAppEpEntry
    MAX-ACCESS       not-accessible
    STATUS           current
    DESCRIPTION
        "Entry for the cfprFabricSspEthMonSrcAppEpTable table."
    INDEX { cfprFabricSspEthMonSrcAppEpInstanceId }
    ::= { cfprFabricSspEthMonSrcAppEpTable 1 }

CfprFabricSspEthMonSrcAppEpEntry ::= SEQUENCE {
    cfprFabricSspEthMonSrcAppEpInstanceId                            CfprManagedObjectId,
    cfprFabricSspEthMonSrcAppEpDn                                    CfprManagedObjectDn,
    cfprFabricSspEthMonSrcAppEpRn                                    SnmpAdminString,
    cfprFabricSspEthMonSrcAppEpAppName                               SnmpAdminString,
    cfprFabricSspEthMonSrcAppEpFilter                                SnmpAdminString,
    cfprFabricSspEthMonSrcAppEpLinkName                              SnmpAdminString,
    cfprFabricSspEthMonSrcAppEpPcapfile                              SnmpAdminString,
    cfprFabricSspEthMonSrcAppEpPcapfilename                          SnmpAdminString,
    cfprFabricSspEthMonSrcAppEpPcapsize                              Gauge32,
    cfprFabricSspEthMonSrcAppEpPortName                              SnmpAdminString,
    cfprFabricSspEthMonSrcAppEpSlotId                                CfprFabricPktCaptureAppSlotId,
    cfprFabricSspEthMonSrcAppEpAppInstance                           SnmpAdminString,
    cfprFabricSspEthMonSrcAppEpSubInterface                          Gauge32,
    cfprFabricSspEthMonSrcAppEpExternalLduLinkDn                     SnmpAdminString
}

cfprFabricSspEthMonSrcAppEpInstanceId OBJECT-TYPE
    SYNTAX       CfprManagedObjectId
    MAX-ACCESS   not-accessible
    STATUS       current
    DESCRIPTION
        "Instance identifier of the managed object."
    ::= { cfprFabricSspEthMonSrcAppEpEntry 1 }

cfprFabricSspEthMonSrcAppEpDn OBJECT-TYPE
    SYNTAX       CfprManagedObjectDn
    MAX-ACCESS   read-only
    STATUS       current
    DESCRIPTION
        "Cisco Firepower fabric:SspEthMonSrcAppEp:dn managed
        object property"
    ::= { cfprFabricSspEthMonSrcAppEpEntry 2 }

cfprFabricSspEthMonSrcAppEpRn OBJECT-TYPE
    SYNTAX       SnmpAdminString
    MAX-ACCESS   read-only
    STATUS       current
    DESCRIPTION
        "Cisco Firepower fabric:SspEthMonSrcAppEp:rn managed
        object property"
    ::= { cfprFabricSspEthMonSrcAppEpEntry 3 }

cfprFabricSspEthMonSrcAppEpAppName OBJECT-TYPE
    SYNTAX       SnmpAdminString
    MAX-ACCESS   read-only
    STATUS       current
    DESCRIPTION
        "Cisco Firepower fabric:SspEthMonSrcAppEp:appName
        managed object property"
    ::= { cfprFabricSspEthMonSrcAppEpEntry 4 }

cfprFabricSspEthMonSrcAppEpFilter OBJECT-TYPE
    SYNTAX       SnmpAdminString
    MAX-ACCESS   read-only
    STATUS       current
    DESCRIPTION
        "Cisco Firepower fabric:SspEthMonSrcAppEp:filter
        managed object property"
    ::= { cfprFabricSspEthMonSrcAppEpEntry 5 }

cfprFabricSspEthMonSrcAppEpLinkName OBJECT-TYPE
    SYNTAX       SnmpAdminString
    MAX-ACCESS   read-only
    STATUS       current
    DESCRIPTION
        "Cisco Firepower fabric:SspEthMonSrcAppEp:linkName
        managed object property"
    ::= { cfprFabricSspEthMonSrcAppEpEntry 6 }

cfprFabricSspEthMonSrcAppEpPcapfile OBJECT-TYPE
    SYNTAX       SnmpAdminString
    MAX-ACCESS   read-only
    STATUS       current
    DESCRIPTION
        "Cisco Firepower fabric:SspEthMonSrcAppEp:pcapfile
        managed object property"
    ::= { cfprFabricSspEthMonSrcAppEpEntry 7 }

cfprFabricSspEthMonSrcAppEpPcapfilename OBJECT-TYPE
    SYNTAX       SnmpAdminString
    MAX-ACCESS   read-only
    STATUS       current
    DESCRIPTION
        "Cisco Firepower fabric:SspEthMonSrcAppEp:pcapfilename
        managed object property"
    ::= { cfprFabricSspEthMonSrcAppEpEntry 8 }

cfprFabricSspEthMonSrcAppEpPcapsize OBJECT-TYPE
    SYNTAX       Gauge32
    MAX-ACCESS   read-only
    STATUS       current
    DESCRIPTION
        "Cisco Firepower fabric:SspEthMonSrcAppEp:pcapsize
        managed object property"
    ::= { cfprFabricSspEthMonSrcAppEpEntry 9 }

cfprFabricSspEthMonSrcAppEpPortName OBJECT-TYPE
    SYNTAX       SnmpAdminString
    MAX-ACCESS   read-only
    STATUS       current
    DESCRIPTION
        "Cisco Firepower fabric:SspEthMonSrcAppEp:portName
        managed object property"
    ::= { cfprFabricSspEthMonSrcAppEpEntry 10 }

cfprFabricSspEthMonSrcAppEpSlotId OBJECT-TYPE
    SYNTAX       CfprFabricPktCaptureAppSlotId
    MAX-ACCESS   read-only
    STATUS       current
    DESCRIPTION
        "Cisco Firepower fabric:SspEthMonSrcAppEp:slotId
        managed object property"
    ::= { cfprFabricSspEthMonSrcAppEpEntry 11 }

cfprFabricSspEthMonSrcAppEpAppInstance OBJECT-TYPE
    SYNTAX       SnmpAdminString
    MAX-ACCESS   read-only
    STATUS       current
    DESCRIPTION
        "Cisco Firepower fabric:SspEthMonSrcAppEp:appInstance
        managed object property"
    ::= { cfprFabricSspEthMonSrcAppEpEntry 12 }

cfprFabricSspEthMonSrcAppEpSubInterface OBJECT-TYPE
    SYNTAX       Gauge32
    MAX-ACCESS   read-only
    STATUS       current
    DESCRIPTION
        "Cisco Firepower fabric:SspEthMonSrcAppEp:subInterface
        managed object property"
    ::= { cfprFabricSspEthMonSrcAppEpEntry 13 }

cfprFabricSspEthMonSrcAppEpExternalLduLinkDn OBJECT-TYPE
    SYNTAX       SnmpAdminString
    MAX-ACCESS   read-only
    STATUS       current
    DESCRIPTION
        "Cisco Firepower fabric:SspEthMonSrcAppEp:externalLduLinkDn
        managed object property"
    ::= { cfprFabricSspEthMonSrcAppEpEntry 14 }

cfprFabricSspEthMonSrcAppLinksEpTable OBJECT-TYPE
    SYNTAX           SEQUENCE OF CfprFabricSspEthMonSrcAppLinksEpEntry
    MAX-ACCESS       not-accessible
    STATUS           current
    DESCRIPTION
        "Cisco Firepower fabric:SspEthMonSrcAppLinksEp
        managed object table"
    ::= { cfprFabricObjects 129 }

cfprFabricSspEthMonSrcAppLinksEpEntry OBJECT-TYPE
    SYNTAX           CfprFabricSspEthMonSrcAppLinksEpEntry
    MAX-ACCESS       not-accessible
    STATUS           current
    DESCRIPTION
        "Entry for the cfprFabricSspEthMonSrcAppLinksEpTable table."
    INDEX { cfprFabricSspEthMonSrcAppLinksEpInstanceId }
    ::= { cfprFabricSspEthMonSrcAppLinksEpTable 1 }

CfprFabricSspEthMonSrcAppLinksEpEntry ::= SEQUENCE {
    cfprFabricSspEthMonSrcAppLinksEpInstanceId                       CfprManagedObjectId,
    cfprFabricSspEthMonSrcAppLinksEpDn                               CfprManagedObjectDn,
    cfprFabricSspEthMonSrcAppLinksEpRn                               SnmpAdminString,
    cfprFabricSspEthMonSrcAppLinksEpChassisId                        Gauge32,
    cfprFabricSspEthMonSrcAppLinksEpEqAggrPortId                     Gauge32,
    cfprFabricSspEthMonSrcAppLinksEpEqPortId                         Gauge32,
    cfprFabricSspEthMonSrcAppLinksEpEqSlotId                         Gauge32,
    cfprFabricSspEthMonSrcAppLinksEpFilter                           SnmpAdminString,
    cfprFabricSspEthMonSrcAppLinksEpFilterDn                         SnmpAdminString,
    cfprFabricSspEthMonSrcAppLinksEpLifeCycle                        CfprSwPktCaptureLifeCycle,
    cfprFabricSspEthMonSrcAppLinksEpName                             SnmpAdminString,
    cfprFabricSspEthMonSrcAppLinksEpPcapfile                         SnmpAdminString,
    cfprFabricSspEthMonSrcAppLinksEpPcapfilename                     SnmpAdminString,
    cfprFabricSspEthMonSrcAppLinksEpPcapsize                         Gauge32,
    cfprFabricSspEthMonSrcAppLinksEpSwitchId                         CfprNetworkSwitchId,
    cfprFabricSspEthMonSrcAppLinksEpVlan                             Gauge32,
    cfprFabricSspEthMonSrcAppLinksEpVifId                            Gauge32
}

cfprFabricSspEthMonSrcAppLinksEpInstanceId OBJECT-TYPE
    SYNTAX       CfprManagedObjectId
    MAX-ACCESS   not-accessible
    STATUS       current
    DESCRIPTION
        "Instance identifier of the managed object."
    ::= { cfprFabricSspEthMonSrcAppLinksEpEntry 1 }

cfprFabricSspEthMonSrcAppLinksEpDn OBJECT-TYPE
    SYNTAX       CfprManagedObjectDn
    MAX-ACCESS   read-only
    STATUS       current
    DESCRIPTION
        "Cisco Firepower fabric:SspEthMonSrcAppLinksEp:dn
        managed object property"
    ::= { cfprFabricSspEthMonSrcAppLinksEpEntry 2 }

cfprFabricSspEthMonSrcAppLinksEpRn OBJECT-TYPE
    SYNTAX       SnmpAdminString
    MAX-ACCESS   read-only
    STATUS       current
    DESCRIPTION
        "Cisco Firepower fabric:SspEthMonSrcAppLinksEp:rn
        managed object property"
    ::= { cfprFabricSspEthMonSrcAppLinksEpEntry 3 }

cfprFabricSspEthMonSrcAppLinksEpChassisId OBJECT-TYPE
    SYNTAX       Gauge32
    MAX-ACCESS   read-only
    STATUS       current
    DESCRIPTION
        "Cisco Firepower fabric:SspEthMonSrcAppLinksEp:chassisId
        managed object property"
    ::= { cfprFabricSspEthMonSrcAppLinksEpEntry 4 }

cfprFabricSspEthMonSrcAppLinksEpEqAggrPortId OBJECT-TYPE
    SYNTAX       Gauge32
    MAX-ACCESS   read-only
    STATUS       current
    DESCRIPTION
        "Cisco Firepower fabric:SspEthMonSrcAppLinksEp:eqAggrPortId
        managed object property"
    ::= { cfprFabricSspEthMonSrcAppLinksEpEntry 5 }

cfprFabricSspEthMonSrcAppLinksEpEqPortId OBJECT-TYPE
    SYNTAX       Gauge32
    MAX-ACCESS   read-only
    STATUS       current
    DESCRIPTION
        "Cisco Firepower fabric:SspEthMonSrcAppLinksEp:eqPortId
        managed object property"
    ::= { cfprFabricSspEthMonSrcAppLinksEpEntry 6 }

cfprFabricSspEthMonSrcAppLinksEpEqSlotId OBJECT-TYPE
    SYNTAX       Gauge32
    MAX-ACCESS   read-only
    STATUS       current
    DESCRIPTION
        "Cisco Firepower fabric:SspEthMonSrcAppLinksEp:eqSlotId
        managed object property"
    ::= { cfprFabricSspEthMonSrcAppLinksEpEntry 7 }

cfprFabricSspEthMonSrcAppLinksEpFilter OBJECT-TYPE
    SYNTAX       SnmpAdminString
    MAX-ACCESS   read-only
    STATUS       current
    DESCRIPTION
        "Cisco Firepower fabric:SspEthMonSrcAppLinksEp:filter
        managed object property"
    ::= { cfprFabricSspEthMonSrcAppLinksEpEntry 8 }

cfprFabricSspEthMonSrcAppLinksEpFilterDn OBJECT-TYPE
    SYNTAX       SnmpAdminString
    MAX-ACCESS   read-only
    STATUS       current
    DESCRIPTION
        "Cisco Firepower fabric:SspEthMonSrcAppLinksEp:filterDn
        managed object property"
    ::= { cfprFabricSspEthMonSrcAppLinksEpEntry 9 }

cfprFabricSspEthMonSrcAppLinksEpLifeCycle OBJECT-TYPE
    SYNTAX       CfprSwPktCaptureLifeCycle
    MAX-ACCESS   read-only
    STATUS       current
    DESCRIPTION
        "Cisco Firepower fabric:SspEthMonSrcAppLinksEp:lifeCycle
        managed object property"
    ::= { cfprFabricSspEthMonSrcAppLinksEpEntry 10 }

cfprFabricSspEthMonSrcAppLinksEpName OBJECT-TYPE
    SYNTAX       SnmpAdminString
    MAX-ACCESS   read-only
    STATUS       current
    DESCRIPTION
        "Cisco Firepower fabric:SspEthMonSrcAppLinksEp:name
        managed object property"
    ::= { cfprFabricSspEthMonSrcAppLinksEpEntry 11 }

cfprFabricSspEthMonSrcAppLinksEpPcapfile OBJECT-TYPE
    SYNTAX       SnmpAdminString
    MAX-ACCESS   read-only
    STATUS       current
    DESCRIPTION
        "Cisco Firepower fabric:SspEthMonSrcAppLinksEp:pcapfile
        managed object property"
    ::= { cfprFabricSspEthMonSrcAppLinksEpEntry 12 }

cfprFabricSspEthMonSrcAppLinksEpPcapfilename OBJECT-TYPE
    SYNTAX       SnmpAdminString
    MAX-ACCESS   read-only
    STATUS       current
    DESCRIPTION
        "Cisco Firepower fabric:SspEthMonSrcAppLinksEp:pcapfilename
        managed object property"
    ::= { cfprFabricSspEthMonSrcAppLinksEpEntry 13 }

cfprFabricSspEthMonSrcAppLinksEpPcapsize OBJECT-TYPE
    SYNTAX       Gauge32
    MAX-ACCESS   read-only
    STATUS       current
    DESCRIPTION
        "Cisco Firepower fabric:SspEthMonSrcAppLinksEp:pcapsize
        managed object property"
    ::= { cfprFabricSspEthMonSrcAppLinksEpEntry 14 }

cfprFabricSspEthMonSrcAppLinksEpSwitchId OBJECT-TYPE
    SYNTAX       CfprNetworkSwitchId
    MAX-ACCESS   read-only
    STATUS       current
    DESCRIPTION
        "Cisco Firepower fabric:SspEthMonSrcAppLinksEp:switchId
        managed object property"
    ::= { cfprFabricSspEthMonSrcAppLinksEpEntry 15 }

cfprFabricSspEthMonSrcAppLinksEpVlan OBJECT-TYPE
    SYNTAX       Gauge32
    MAX-ACCESS   read-only
    STATUS       current
    DESCRIPTION
        "Cisco Firepower fabric:SspEthMonSrcAppLinksEp:vlan
        managed object property"
    ::= { cfprFabricSspEthMonSrcAppLinksEpEntry 16 }

cfprFabricSspEthMonSrcAppLinksEpVifId OBJECT-TYPE
    SYNTAX       Gauge32
    MAX-ACCESS   read-only
    STATUS       current
    DESCRIPTION
        "Cisco Firepower fabric:SspEthMonSrcAppLinksEp:vifId
        managed object property"
    ::= { cfprFabricSspEthMonSrcAppLinksEpEntry 17 }

cfprFabricSspEthMonSrcPhyAggrEpTable OBJECT-TYPE
    SYNTAX           SEQUENCE OF CfprFabricSspEthMonSrcPhyAggrEpEntry
    MAX-ACCESS       not-accessible
    STATUS           current
    DESCRIPTION
        "Cisco Firepower fabric:SspEthMonSrcPhyAggrEp managed
        object table"
    ::= { cfprFabricObjects 130 }

cfprFabricSspEthMonSrcPhyAggrEpEntry OBJECT-TYPE
    SYNTAX           CfprFabricSspEthMonSrcPhyAggrEpEntry
    MAX-ACCESS       not-accessible
    STATUS           current
    DESCRIPTION
        "Entry for the cfprFabricSspEthMonSrcPhyAggrEpTable table."
    INDEX { cfprFabricSspEthMonSrcPhyAggrEpInstanceId }
    ::= { cfprFabricSspEthMonSrcPhyAggrEpTable 1 }

CfprFabricSspEthMonSrcPhyAggrEpEntry ::= SEQUENCE {
    cfprFabricSspEthMonSrcPhyAggrEpInstanceId                        CfprManagedObjectId,
    cfprFabricSspEthMonSrcPhyAggrEpDn                                CfprManagedObjectDn,
    cfprFabricSspEthMonSrcPhyAggrEpRn                                SnmpAdminString,
    cfprFabricSspEthMonSrcPhyAggrEpAggrPortId                        Gauge32,
    cfprFabricSspEthMonSrcPhyAggrEpBreakoutPortId                    Gauge32,
    cfprFabricSspEthMonSrcPhyAggrEpChassisId                         Gauge32,
    cfprFabricSspEthMonSrcPhyAggrEpFilter                            SnmpAdminString,
    cfprFabricSspEthMonSrcPhyAggrEpPcapfile                          SnmpAdminString,
    cfprFabricSspEthMonSrcPhyAggrEpPcapfilename                      SnmpAdminString,
    cfprFabricSspEthMonSrcPhyAggrEpPcapsize                          Gauge32,
    cfprFabricSspEthMonSrcPhyAggrEpSlotId                            Gauge32,
    cfprFabricSspEthMonSrcPhyAggrEpSwitchId                          CfprNetworkSwitchId,
    cfprFabricSspEthMonSrcPhyAggrEpAppInstance                       SnmpAdminString,
    cfprFabricSspEthMonSrcPhyAggrEpAppName                           SnmpAdminString,
    cfprFabricSspEthMonSrcPhyAggrEpSubInterface                      Gauge32,
    cfprFabricSspEthMonSrcPhyAggrEpEcmpId                            Gauge32
}

cfprFabricSspEthMonSrcPhyAggrEpInstanceId OBJECT-TYPE
    SYNTAX       CfprManagedObjectId
    MAX-ACCESS   not-accessible
    STATUS       current
    DESCRIPTION
        "Instance identifier of the managed object."
    ::= { cfprFabricSspEthMonSrcPhyAggrEpEntry 1 }

cfprFabricSspEthMonSrcPhyAggrEpDn OBJECT-TYPE
    SYNTAX       CfprManagedObjectDn
    MAX-ACCESS   read-only
    STATUS       current
    DESCRIPTION
        "Cisco Firepower fabric:SspEthMonSrcPhyAggrEp:dn
        managed object property"
    ::= { cfprFabricSspEthMonSrcPhyAggrEpEntry 2 }

cfprFabricSspEthMonSrcPhyAggrEpRn OBJECT-TYPE
    SYNTAX       SnmpAdminString
    MAX-ACCESS   read-only
    STATUS       current
    DESCRIPTION
        "Cisco Firepower fabric:SspEthMonSrcPhyAggrEp:rn
        managed object property"
    ::= { cfprFabricSspEthMonSrcPhyAggrEpEntry 3 }

cfprFabricSspEthMonSrcPhyAggrEpAggrPortId OBJECT-TYPE
    SYNTAX       Gauge32
    MAX-ACCESS   read-only
    STATUS       current
    DESCRIPTION
        "Cisco Firepower fabric:SspEthMonSrcPhyAggrEp:aggrPortId
        managed object property"
    ::= { cfprFabricSspEthMonSrcPhyAggrEpEntry 4 }

cfprFabricSspEthMonSrcPhyAggrEpBreakoutPortId OBJECT-TYPE
    SYNTAX       Gauge32
    MAX-ACCESS   read-only
    STATUS       current
    DESCRIPTION
        "Cisco Firepower fabric:SspEthMonSrcPhyAggrEp:breakoutPortId
        managed object property"
    ::= { cfprFabricSspEthMonSrcPhyAggrEpEntry 5 }

cfprFabricSspEthMonSrcPhyAggrEpChassisId OBJECT-TYPE
    SYNTAX       Gauge32
    MAX-ACCESS   read-only
    STATUS       current
    DESCRIPTION
        "Cisco Firepower fabric:SspEthMonSrcPhyAggrEp:chassisId
        managed object property"
    ::= { cfprFabricSspEthMonSrcPhyAggrEpEntry 6 }

cfprFabricSspEthMonSrcPhyAggrEpFilter OBJECT-TYPE
    SYNTAX       SnmpAdminString
    MAX-ACCESS   read-only
    STATUS       current
    DESCRIPTION
        "Cisco Firepower fabric:SspEthMonSrcPhyAggrEp:filter
        managed object property"
    ::= { cfprFabricSspEthMonSrcPhyAggrEpEntry 7 }

cfprFabricSspEthMonSrcPhyAggrEpPcapfile OBJECT-TYPE
    SYNTAX       SnmpAdminString
    MAX-ACCESS   read-only
    STATUS       current
    DESCRIPTION
        "Cisco Firepower fabric:SspEthMonSrcPhyAggrEp:pcapfile
        managed object property"
    ::= { cfprFabricSspEthMonSrcPhyAggrEpEntry 8 }

cfprFabricSspEthMonSrcPhyAggrEpPcapfilename OBJECT-TYPE
    SYNTAX       SnmpAdminString
    MAX-ACCESS   read-only
    STATUS       current
    DESCRIPTION
        "Cisco Firepower fabric:SspEthMonSrcPhyAggrEp:pcapfilename
        managed object property"
    ::= { cfprFabricSspEthMonSrcPhyAggrEpEntry 9 }

cfprFabricSspEthMonSrcPhyAggrEpPcapsize OBJECT-TYPE
    SYNTAX       Gauge32
    MAX-ACCESS   read-only
    STATUS       current
    DESCRIPTION
        "Cisco Firepower fabric:SspEthMonSrcPhyAggrEp:pcapsize
        managed object property"
    ::= { cfprFabricSspEthMonSrcPhyAggrEpEntry 10 }

cfprFabricSspEthMonSrcPhyAggrEpSlotId OBJECT-TYPE
    SYNTAX       Gauge32
    MAX-ACCESS   read-only
    STATUS       current
    DESCRIPTION
        "Cisco Firepower fabric:SspEthMonSrcPhyAggrEp:slotId
        managed object property"
    ::= { cfprFabricSspEthMonSrcPhyAggrEpEntry 11 }

cfprFabricSspEthMonSrcPhyAggrEpSwitchId OBJECT-TYPE
    SYNTAX       CfprNetworkSwitchId
    MAX-ACCESS   read-only
    STATUS       current
    DESCRIPTION
        "Cisco Firepower fabric:SspEthMonSrcPhyAggrEp:switchId
        managed object property"
    ::= { cfprFabricSspEthMonSrcPhyAggrEpEntry 12 }

cfprFabricSspEthMonSrcPhyAggrEpAppInstance OBJECT-TYPE
    SYNTAX       SnmpAdminString
    MAX-ACCESS   read-only
    STATUS       current
    DESCRIPTION
        "Cisco Firepower fabric:SspEthMonSrcPhyAggrEp:appInstance
        managed object property"
    ::= { cfprFabricSspEthMonSrcPhyAggrEpEntry 13 }

cfprFabricSspEthMonSrcPhyAggrEpAppName OBJECT-TYPE
    SYNTAX       SnmpAdminString
    MAX-ACCESS   read-only
    STATUS       current
    DESCRIPTION
        "Cisco Firepower fabric:SspEthMonSrcPhyAggrEp:appName
        managed object property"
    ::= { cfprFabricSspEthMonSrcPhyAggrEpEntry 14 }

cfprFabricSspEthMonSrcPhyAggrEpSubInterface OBJECT-TYPE
    SYNTAX       Gauge32
    MAX-ACCESS   read-only
    STATUS       current
    DESCRIPTION
        "Cisco Firepower fabric:SspEthMonSrcPhyAggrEp:subInterface
        managed object property"
    ::= { cfprFabricSspEthMonSrcPhyAggrEpEntry 15 }

cfprFabricSspEthMonSrcPhyAggrEpEcmpId OBJECT-TYPE
    SYNTAX       Gauge32
    MAX-ACCESS   read-only
    STATUS       current
    DESCRIPTION
        "Cisco Firepower fabric:SspEthMonSrcPhyAggrEp:ecmpId
        managed object property"
    ::= { cfprFabricSspEthMonSrcPhyAggrEpEntry 16 }

cfprFabricSspEthMonSrcPhyEpTable OBJECT-TYPE
    SYNTAX           SEQUENCE OF CfprFabricSspEthMonSrcPhyEpEntry
    MAX-ACCESS       not-accessible
    STATUS           current
    DESCRIPTION
        "Cisco Firepower fabric:SspEthMonSrcPhyEp managed object table"
    ::= { cfprFabricObjects 131 }

cfprFabricSspEthMonSrcPhyEpEntry OBJECT-TYPE
    SYNTAX           CfprFabricSspEthMonSrcPhyEpEntry
    MAX-ACCESS       not-accessible
    STATUS           current
    DESCRIPTION
        "Entry for the cfprFabricSspEthMonSrcPhyEpTable table."
    INDEX { cfprFabricSspEthMonSrcPhyEpInstanceId }
    ::= { cfprFabricSspEthMonSrcPhyEpTable 1 }

CfprFabricSspEthMonSrcPhyEpEntry ::= SEQUENCE {
    cfprFabricSspEthMonSrcPhyEpInstanceId                            CfprManagedObjectId,
    cfprFabricSspEthMonSrcPhyEpDn                                    CfprManagedObjectDn,
    cfprFabricSspEthMonSrcPhyEpRn                                    SnmpAdminString,
    cfprFabricSspEthMonSrcPhyEpChassisId                             Gauge32,
    cfprFabricSspEthMonSrcPhyEpFilter                                SnmpAdminString,
    cfprFabricSspEthMonSrcPhyEpPcapfile                              SnmpAdminString,
    cfprFabricSspEthMonSrcPhyEpPcapfilename                          SnmpAdminString,
    cfprFabricSspEthMonSrcPhyEpPcapsize                              Gauge32,
    cfprFabricSspEthMonSrcPhyEpPortId                                Gauge32,
    cfprFabricSspEthMonSrcPhyEpSlotId                                Gauge32,
    cfprFabricSspEthMonSrcPhyEpSwitchId                              CfprNetworkSwitchId,
    cfprFabricSspEthMonSrcPhyEpAppInstance                           SnmpAdminString,
    cfprFabricSspEthMonSrcPhyEpAppName                               SnmpAdminString,
    cfprFabricSspEthMonSrcPhyEpSubInterface                          Gauge32,
    cfprFabricSspEthMonSrcPhyEpEcmpId                                Gauge32
}

cfprFabricSspEthMonSrcPhyEpInstanceId OBJECT-TYPE
    SYNTAX       CfprManagedObjectId
    MAX-ACCESS   not-accessible
    STATUS       current
    DESCRIPTION
        "Instance identifier of the managed object."
    ::= { cfprFabricSspEthMonSrcPhyEpEntry 1 }

cfprFabricSspEthMonSrcPhyEpDn OBJECT-TYPE
    SYNTAX       CfprManagedObjectDn
    MAX-ACCESS   read-only
    STATUS       current
    DESCRIPTION
        "Cisco Firepower fabric:SspEthMonSrcPhyEp:dn managed
        object property"
    ::= { cfprFabricSspEthMonSrcPhyEpEntry 2 }

cfprFabricSspEthMonSrcPhyEpRn OBJECT-TYPE
    SYNTAX       SnmpAdminString
    MAX-ACCESS   read-only
    STATUS       current
    DESCRIPTION
        "Cisco Firepower fabric:SspEthMonSrcPhyEp:rn managed
        object property"
    ::= { cfprFabricSspEthMonSrcPhyEpEntry 3 }

cfprFabricSspEthMonSrcPhyEpChassisId OBJECT-TYPE
    SYNTAX       Gauge32
    MAX-ACCESS   read-only
    STATUS       current
    DESCRIPTION
        "Cisco Firepower fabric:SspEthMonSrcPhyEp:chassisId
        managed object property"
    ::= { cfprFabricSspEthMonSrcPhyEpEntry 4 }

cfprFabricSspEthMonSrcPhyEpFilter OBJECT-TYPE
    SYNTAX       SnmpAdminString
    MAX-ACCESS   read-only
    STATUS       current
    DESCRIPTION
        "Cisco Firepower fabric:SspEthMonSrcPhyEp:filter
        managed object property"
    ::= { cfprFabricSspEthMonSrcPhyEpEntry 5 }

cfprFabricSspEthMonSrcPhyEpPcapfile OBJECT-TYPE
    SYNTAX       SnmpAdminString
    MAX-ACCESS   read-only
    STATUS       current
    DESCRIPTION
        "Cisco Firepower fabric:SspEthMonSrcPhyEp:pcapfile
        managed object property"
    ::= { cfprFabricSspEthMonSrcPhyEpEntry 6 }

cfprFabricSspEthMonSrcPhyEpPcapfilename OBJECT-TYPE
    SYNTAX       SnmpAdminString
    MAX-ACCESS   read-only
    STATUS       current
    DESCRIPTION
        "Cisco Firepower fabric:SspEthMonSrcPhyEp:pcapfilename
        managed object property"
    ::= { cfprFabricSspEthMonSrcPhyEpEntry 7 }

cfprFabricSspEthMonSrcPhyEpPcapsize OBJECT-TYPE
    SYNTAX       Gauge32
    MAX-ACCESS   read-only
    STATUS       current
    DESCRIPTION
        "Cisco Firepower fabric:SspEthMonSrcPhyEp:pcapsize
        managed object property"
    ::= { cfprFabricSspEthMonSrcPhyEpEntry 8 }

cfprFabricSspEthMonSrcPhyEpPortId OBJECT-TYPE
    SYNTAX       Gauge32
    MAX-ACCESS   read-only
    STATUS       current
    DESCRIPTION
        "Cisco Firepower fabric:SspEthMonSrcPhyEp:portId
        managed object property"
    ::= { cfprFabricSspEthMonSrcPhyEpEntry 9 }

cfprFabricSspEthMonSrcPhyEpSlotId OBJECT-TYPE
    SYNTAX       Gauge32
    MAX-ACCESS   read-only
    STATUS       current
    DESCRIPTION
        "Cisco Firepower fabric:SspEthMonSrcPhyEp:slotId
        managed object property"
    ::= { cfprFabricSspEthMonSrcPhyEpEntry 10 }

cfprFabricSspEthMonSrcPhyEpSwitchId OBJECT-TYPE
    SYNTAX       CfprNetworkSwitchId
    MAX-ACCESS   read-only
    STATUS       current
    DESCRIPTION
        "Cisco Firepower fabric:SspEthMonSrcPhyEp:switchId
        managed object property"
    ::= { cfprFabricSspEthMonSrcPhyEpEntry 11 }

cfprFabricSspEthMonSrcPhyEpAppInstance OBJECT-TYPE
    SYNTAX       SnmpAdminString
    MAX-ACCESS   read-only
    STATUS       current
    DESCRIPTION
        "Cisco Firepower fabric:SspEthMonSrcPhyEp:appInstance
        managed object property"
    ::= { cfprFabricSspEthMonSrcPhyEpEntry 12 }

cfprFabricSspEthMonSrcPhyEpAppName OBJECT-TYPE
    SYNTAX       SnmpAdminString
    MAX-ACCESS   read-only
    STATUS       current
    DESCRIPTION
        "Cisco Firepower fabric:SspEthMonSrcPhyEp:appName
        managed object property"
    ::= { cfprFabricSspEthMonSrcPhyEpEntry 13 }

cfprFabricSspEthMonSrcPhyEpSubInterface OBJECT-TYPE
    SYNTAX       Gauge32
    MAX-ACCESS   read-only
    STATUS       current
    DESCRIPTION
        "Cisco Firepower fabric:SspEthMonSrcPhyEp:subInterface
        managed object property"
    ::= { cfprFabricSspEthMonSrcPhyEpEntry 14 }

cfprFabricSspEthMonSrcPhyEpEcmpId OBJECT-TYPE
    SYNTAX       Gauge32
    MAX-ACCESS   read-only
    STATUS       current
    DESCRIPTION
        "Cisco Firepower fabric:SspEthMonSrcPhyEp:ecmpId
        managed object property"
    ::= { cfprFabricSspEthMonSrcPhyEpEntry 15 }

cfprFabricSspLanMonCloudTable OBJECT-TYPE
    SYNTAX           SEQUENCE OF CfprFabricSspLanMonCloudEntry
    MAX-ACCESS       not-accessible
    STATUS           current
    DESCRIPTION
        "Cisco Firepower fabric:SspLanMonCloud managed object table"
    ::= { cfprFabricObjects 132 }

cfprFabricSspLanMonCloudEntry OBJECT-TYPE
    SYNTAX           CfprFabricSspLanMonCloudEntry
    MAX-ACCESS       not-accessible
    STATUS           current
    DESCRIPTION
        "Entry for the cfprFabricSspLanMonCloudTable table."
    INDEX { cfprFabricSspLanMonCloudInstanceId }
    ::= { cfprFabricSspLanMonCloudTable 1 }

CfprFabricSspLanMonCloudEntry ::= SEQUENCE {
    cfprFabricSspLanMonCloudInstanceId                               CfprManagedObjectId,
    cfprFabricSspLanMonCloudDn                                       CfprManagedObjectDn,
    cfprFabricSspLanMonCloudRn                                       SnmpAdminString,
    cfprFabricSspLanMonCloudMode                                     CfprFabricSwitchingMode,
    cfprFabricSspLanMonCloudDelAllSess                               CfprFabricSspLanMonCloudDelAllSess
}

cfprFabricSspLanMonCloudInstanceId OBJECT-TYPE
    SYNTAX       CfprManagedObjectId
    MAX-ACCESS   not-accessible
    STATUS       current
    DESCRIPTION
        "Instance identifier of the managed object."
    ::= { cfprFabricSspLanMonCloudEntry 1 }

cfprFabricSspLanMonCloudDn OBJECT-TYPE
    SYNTAX       CfprManagedObjectDn
    MAX-ACCESS   read-only
    STATUS       current
    DESCRIPTION
        "Cisco Firepower fabric:SspLanMonCloud:dn managed object property"
    ::= { cfprFabricSspLanMonCloudEntry 2 }

cfprFabricSspLanMonCloudRn OBJECT-TYPE
    SYNTAX       SnmpAdminString
    MAX-ACCESS   read-only
    STATUS       current
    DESCRIPTION
        "Cisco Firepower fabric:SspLanMonCloud:rn managed object property"
    ::= { cfprFabricSspLanMonCloudEntry 3 }

cfprFabricSspLanMonCloudMode OBJECT-TYPE
    SYNTAX       CfprFabricSwitchingMode
    MAX-ACCESS   read-only
    STATUS       current
    DESCRIPTION
        "Cisco Firepower fabric:SspLanMonCloud:mode managed
        object property"
    ::= { cfprFabricSspLanMonCloudEntry 4 }

cfprFabricSspLanMonCloudDelAllSess OBJECT-TYPE
    SYNTAX       CfprFabricSspLanMonCloudDelAllSess
    MAX-ACCESS   read-only
    STATUS       current
    DESCRIPTION
        "Cisco Firepower fabric:SspLanMonCloud:delAllSess
        managed object property"
    ::= { cfprFabricSspLanMonCloudEntry 5 }

cfprFabricSubGroupTable OBJECT-TYPE
    SYNTAX           SEQUENCE OF CfprFabricSubGroupEntry
    MAX-ACCESS       not-accessible
    STATUS           current
    DESCRIPTION
        "Cisco Firepower fabric:SubGroup managed object table"
    ::= { cfprFabricObjects 106 }

cfprFabricSubGroupEntry OBJECT-TYPE
    SYNTAX           CfprFabricSubGroupEntry
    MAX-ACCESS       not-accessible
    STATUS           current
    DESCRIPTION
        "Entry for the cfprFabricSubGroupTable table."
    INDEX { cfprFabricSubGroupInstanceId }
    ::= { cfprFabricSubGroupTable 1 }

CfprFabricSubGroupEntry ::= SEQUENCE {
    cfprFabricSubGroupInstanceId                                     CfprManagedObjectId,
    cfprFabricSubGroupDn                                             CfprManagedObjectDn,
    cfprFabricSubGroupRn                                             SnmpAdminString,
    cfprFabricSubGroupAggrPortId                                     CfprFabricSubGroupAggrPortId,
    cfprFabricSubGroupConfigState                                    CfprFabricSubGroupConfigState,
    cfprFabricSubGroupLicGP                                          Unsigned64,
    cfprFabricSubGroupLicState                                       CfprLicenseState,
    cfprFabricSubGroupLocale                                         CfprNetworkLocale,
    cfprFabricSubGroupName                                           SnmpAdminString,
    cfprFabricSubGroupSlotId                                         CfprFabricSubGroupSlotId,
    cfprFabricSubGroupSwitchId                                       CfprNetworkSwitchId,
    cfprFabricSubGroupTransport                                      CfprNetworkTransport,
    cfprFabricSubGroupType                                           CfprNetworkConnectionType
}

cfprFabricSubGroupInstanceId OBJECT-TYPE
    SYNTAX       CfprManagedObjectId
    MAX-ACCESS   not-accessible
    STATUS       current
    DESCRIPTION
        "Instance identifier of the managed object."
    ::= { cfprFabricSubGroupEntry 1 }

cfprFabricSubGroupDn OBJECT-TYPE
    SYNTAX       CfprManagedObjectDn
    MAX-ACCESS   read-only
    STATUS       current
    DESCRIPTION
        "Cisco Firepower fabric:SubGroup:dn managed object property"
    ::= { cfprFabricSubGroupEntry 2 }

cfprFabricSubGroupRn OBJECT-TYPE
    SYNTAX       SnmpAdminString
    MAX-ACCESS   read-only
    STATUS       current
    DESCRIPTION
        "Cisco Firepower fabric:SubGroup:rn managed object property"
    ::= { cfprFabricSubGroupEntry 3 }

cfprFabricSubGroupAggrPortId OBJECT-TYPE
    SYNTAX       CfprFabricSubGroupAggrPortId
    MAX-ACCESS   read-only
    STATUS       current
    DESCRIPTION
        "Cisco Firepower fabric:SubGroup:aggrPortId managed
        object property"
    ::= { cfprFabricSubGroupEntry 4 }

cfprFabricSubGroupConfigState OBJECT-TYPE
    SYNTAX       CfprFabricSubGroupConfigState
    MAX-ACCESS   read-only
    STATUS       current
    DESCRIPTION
        "Cisco Firepower fabric:SubGroup:configState managed
        object property"
    ::= { cfprFabricSubGroupEntry 5 }

cfprFabricSubGroupLicGP OBJECT-TYPE
    SYNTAX       Unsigned64
    MAX-ACCESS   read-only
    STATUS       current
    DESCRIPTION
        "Cisco Firepower fabric:SubGroup:licGP managed object property"
    ::= { cfprFabricSubGroupEntry 6 }

cfprFabricSubGroupLicState OBJECT-TYPE
    SYNTAX       CfprLicenseState
    MAX-ACCESS   read-only
    STATUS       current
    DESCRIPTION
        "Cisco Firepower fabric:SubGroup:licState managed object property"
    ::= { cfprFabricSubGroupEntry 7 }

cfprFabricSubGroupLocale OBJECT-TYPE
    SYNTAX       CfprNetworkLocale
    MAX-ACCESS   read-only
    STATUS       current
    DESCRIPTION
        "Cisco Firepower fabric:SubGroup:locale managed object property"
    ::= { cfprFabricSubGroupEntry 8 }

cfprFabricSubGroupName OBJECT-TYPE
    SYNTAX       SnmpAdminString
    MAX-ACCESS   read-only
    STATUS       current
    DESCRIPTION
        "Cisco Firepower fabric:SubGroup:name managed object property"
    ::= { cfprFabricSubGroupEntry 9 }

cfprFabricSubGroupSlotId OBJECT-TYPE
    SYNTAX       CfprFabricSubGroupSlotId
    MAX-ACCESS   read-only
    STATUS       current
    DESCRIPTION
        "Cisco Firepower fabric:SubGroup:slotId managed object property"
    ::= { cfprFabricSubGroupEntry 10 }

cfprFabricSubGroupSwitchId OBJECT-TYPE
    SYNTAX       CfprNetworkSwitchId
    MAX-ACCESS   read-only
    STATUS       current
    DESCRIPTION
        "Cisco Firepower fabric:SubGroup:switchId managed object property"
    ::= { cfprFabricSubGroupEntry 11 }

cfprFabricSubGroupTransport OBJECT-TYPE
    SYNTAX       CfprNetworkTransport
    MAX-ACCESS   read-only
    STATUS       current
    DESCRIPTION
        "Cisco Firepower fabric:SubGroup:transport managed
        object property"
    ::= { cfprFabricSubGroupEntry 12 }

cfprFabricSubGroupType OBJECT-TYPE
    SYNTAX       CfprNetworkConnectionType
    MAX-ACCESS   read-only
    STATUS       current
    DESCRIPTION
        "Cisco Firepower fabric:SubGroup:type managed object property"
    ::= { cfprFabricSubGroupEntry 13 }

cfprFabricSubIfTable OBJECT-TYPE
    SYNTAX           SEQUENCE OF CfprFabricSubIfEntry
    MAX-ACCESS       not-accessible
    STATUS           current
    DESCRIPTION
        "Cisco Firepower fabric:SubIf managed object table"
    ::= { cfprFabricObjects 134 }

cfprFabricSubIfEntry OBJECT-TYPE
    SYNTAX           CfprFabricSubIfEntry
    MAX-ACCESS       not-accessible
    STATUS           current
    DESCRIPTION
        "Entry for the cfprFabricSubIfTable table."
    INDEX { cfprFabricSubIfInstanceId }
    ::= { cfprFabricSubIfTable 1 }

CfprFabricSubIfEntry ::= SEQUENCE {
    cfprFabricSubIfInstanceId                                        CfprManagedObjectId,
    cfprFabricSubIfDn                                                CfprManagedObjectDn,
    cfprFabricSubIfRn                                                SnmpAdminString,
    cfprFabricSubIfAllowSharing                                      TruthValue,
    cfprFabricSubIfDescr                                             SnmpAdminString,
    cfprFabricSubIfIfName                                            SnmpAdminString,
    cfprFabricSubIfSsaPortType                                       CfprFabricSSASubPortType,
    cfprFabricSubIfSubId                                             Gauge32,
    cfprFabricSubIfVlanId                                            INTEGER
}

cfprFabricSubIfInstanceId OBJECT-TYPE
    SYNTAX       CfprManagedObjectId
    MAX-ACCESS   not-accessible
    STATUS       current
    DESCRIPTION
        "Instance identifier of the managed object."
    ::= { cfprFabricSubIfEntry 1 }

cfprFabricSubIfDn OBJECT-TYPE
    SYNTAX       CfprManagedObjectDn
    MAX-ACCESS   read-only
    STATUS       current
    DESCRIPTION
        "Cisco Firepower fabric:SubIf:dn managed object property"
    ::= { cfprFabricSubIfEntry 2 }

cfprFabricSubIfRn OBJECT-TYPE
    SYNTAX       SnmpAdminString
    MAX-ACCESS   read-only
    STATUS       current
    DESCRIPTION
        "Cisco Firepower fabric:SubIf:rn managed object property"
    ::= { cfprFabricSubIfEntry 3 }

cfprFabricSubIfAllowSharing OBJECT-TYPE
    SYNTAX       TruthValue
    MAX-ACCESS   read-only
    STATUS       current
    DESCRIPTION
        "Cisco Firepower fabric:SubIf:allowSharing managed
        object property"
    ::= { cfprFabricSubIfEntry 4 }

cfprFabricSubIfDescr OBJECT-TYPE
    SYNTAX       SnmpAdminString
    MAX-ACCESS   read-only
    STATUS       current
    DESCRIPTION
        "Cisco Firepower fabric:SubIf:descr managed object property"
    ::= { cfprFabricSubIfEntry 5 }

cfprFabricSubIfIfName OBJECT-TYPE
    SYNTAX       SnmpAdminString
    MAX-ACCESS   read-only
    STATUS       current
    DESCRIPTION
        "Cisco Firepower fabric:SubIf:ifName managed object property"
    ::= { cfprFabricSubIfEntry 6 }

cfprFabricSubIfSsaPortType OBJECT-TYPE
    SYNTAX       CfprFabricSSASubPortType
    MAX-ACCESS   read-only
    STATUS       current
    DESCRIPTION
        "Cisco Firepower fabric:SubIf:ssaPortType managed object property"
    ::= { cfprFabricSubIfEntry 7 }

cfprFabricSubIfSubId OBJECT-TYPE
    SYNTAX       Gauge32
    MAX-ACCESS   read-only
    STATUS       current
    DESCRIPTION
        "Cisco Firepower fabric:SubIf:subId managed object property"
    ::= { cfprFabricSubIfEntry 8 }

cfprFabricSubIfVlanId OBJECT-TYPE
    SYNTAX       INTEGER
    MAX-ACCESS   read-only
    STATUS       current
    DESCRIPTION
        "Cisco Firepower fabric:SubIf:vlanId managed object property"
    ::= { cfprFabricSubIfEntry 9 }

cfprFabricSwChPhEpTable OBJECT-TYPE
    SYNTAX           SEQUENCE OF CfprFabricSwChPhEpEntry
    MAX-ACCESS       not-accessible
    STATUS           current
    DESCRIPTION
        "Cisco Firepower fabric:SwChPhEp managed object table"
    ::= { cfprFabricObjects 107 }

cfprFabricSwChPhEpEntry OBJECT-TYPE
    SYNTAX           CfprFabricSwChPhEpEntry
    MAX-ACCESS       not-accessible
    STATUS           current
    DESCRIPTION
        "Entry for the cfprFabricSwChPhEpTable table."
    INDEX { cfprFabricSwChPhEpInstanceId }
    ::= { cfprFabricSwChPhEpTable 1 }

CfprFabricSwChPhEpEntry ::= SEQUENCE {
    cfprFabricSwChPhEpInstanceId                                     CfprManagedObjectId,
    cfprFabricSwChPhEpDn                                             CfprManagedObjectDn,
    cfprFabricSwChPhEpRn                                             SnmpAdminString,
    cfprFabricSwChPhEpAdminState                                     CfprFabricSwChPhEpAdminState,
    cfprFabricSwChPhEpAggrPortId                                     Gauge32,
    cfprFabricSwChPhEpChassisId                                      Gauge32,
    cfprFabricSwChPhEpEpDn                                           SnmpAdminString,
    cfprFabricSwChPhEpEqType                                         CfprEquipmentFabricEpType,
    cfprFabricSwChPhEpFltAggr                                        Unsigned64,
    cfprFabricSwChPhEpIfRole                                         CfprFabricSwChEpIfRole,
    cfprFabricSwChPhEpIfType                                         CfprFabricPIoEpIfType,
    cfprFabricSwChPhEpLc                                             CfprFabricLifeCycle,
    cfprFabricSwChPhEpLicGP                                          Unsigned64,
    cfprFabricSwChPhEpLicState                                       CfprLicenseState,
    cfprFabricSwChPhEpLocale                                         CfprFabricInternalEpLocale,
    cfprFabricSwChPhEpModel                                          SnmpAdminString,
    cfprFabricSwChPhEpName                                           SnmpAdminString,
    cfprFabricSwChPhEpOperState                                      CfprFabricPIoEpOperState,
    cfprFabricSwChPhEpOperStateReason                                SnmpAdminString,
    cfprFabricSwChPhEpPeerAggrPortId                                 Gauge32,
    cfprFabricSwChPhEpPeerChassisId                                  Gauge32,
    cfprFabricSwChPhEpPeerDn                                         SnmpAdminString,
    cfprFabricSwChPhEpPeerPortId                                     Gauge32,
    cfprFabricSwChPhEpPeerSlotId                                     Gauge32,
    cfprFabricSwChPhEpPortId                                         CfprFabricPIoEpPortId,
    cfprFabricSwChPhEpRevision                                       SnmpAdminString,
    cfprFabricSwChPhEpSerial                                         SnmpAdminString,
    cfprFabricSwChPhEpSlotId                                         CfprFabricPIoEpSlotId,
    cfprFabricSwChPhEpSwitchId                                       CfprNetworkSwitchId,
    cfprFabricSwChPhEpTransport                                      CfprNetworkTransport,
    cfprFabricSwChPhEpType                                           CfprFabricSwChEpType,
    cfprFabricSwChPhEpVendor                                         SnmpAdminString
}

cfprFabricSwChPhEpInstanceId OBJECT-TYPE
    SYNTAX       CfprManagedObjectId
    MAX-ACCESS   not-accessible
    STATUS       current
    DESCRIPTION
        "Instance identifier of the managed object."
    ::= { cfprFabricSwChPhEpEntry 1 }

cfprFabricSwChPhEpDn OBJECT-TYPE
    SYNTAX       CfprManagedObjectDn
    MAX-ACCESS   read-only
    STATUS       current
    DESCRIPTION
        "Cisco Firepower fabric:SwChPhEp:dn managed object property"
    ::= { cfprFabricSwChPhEpEntry 2 }

cfprFabricSwChPhEpRn OBJECT-TYPE
    SYNTAX       SnmpAdminString
    MAX-ACCESS   read-only
    STATUS       current
    DESCRIPTION
        "Cisco Firepower fabric:SwChPhEp:rn managed object property"
    ::= { cfprFabricSwChPhEpEntry 3 }

cfprFabricSwChPhEpAdminState OBJECT-TYPE
    SYNTAX       CfprFabricSwChPhEpAdminState
    MAX-ACCESS   read-only
    STATUS       current
    DESCRIPTION
        "Cisco Firepower fabric:SwChPhEp:adminState managed
        object property"
    ::= { cfprFabricSwChPhEpEntry 4 }

cfprFabricSwChPhEpAggrPortId OBJECT-TYPE
    SYNTAX       Gauge32
    MAX-ACCESS   read-only
    STATUS       current
    DESCRIPTION
        "Cisco Firepower fabric:SwChPhEp:aggrPortId managed
        object property"
    ::= { cfprFabricSwChPhEpEntry 5 }

cfprFabricSwChPhEpChassisId OBJECT-TYPE
    SYNTAX       Gauge32
    MAX-ACCESS   read-only
    STATUS       current
    DESCRIPTION
        "Cisco Firepower fabric:SwChPhEp:chassisId managed
        object property"
    ::= { cfprFabricSwChPhEpEntry 6 }

cfprFabricSwChPhEpEpDn OBJECT-TYPE
    SYNTAX       SnmpAdminString
    MAX-ACCESS   read-only
    STATUS       current
    DESCRIPTION
        "Cisco Firepower fabric:SwChPhEp:epDn managed object property"
    ::= { cfprFabricSwChPhEpEntry 7 }

cfprFabricSwChPhEpEqType OBJECT-TYPE
    SYNTAX       CfprEquipmentFabricEpType
    MAX-ACCESS   read-only
    STATUS       current
    DESCRIPTION
        "Cisco Firepower fabric:SwChPhEp:eqType managed object property"
    ::= { cfprFabricSwChPhEpEntry 8 }

cfprFabricSwChPhEpFltAggr OBJECT-TYPE
    SYNTAX       Unsigned64
    MAX-ACCESS   read-only
    STATUS       current
    DESCRIPTION
        "Cisco Firepower fabric:SwChPhEp:fltAggr managed object property"
    ::= { cfprFabricSwChPhEpEntry 9 }

cfprFabricSwChPhEpIfRole OBJECT-TYPE
    SYNTAX       CfprFabricSwChEpIfRole
    MAX-ACCESS   read-only
    STATUS       current
    DESCRIPTION
        "Cisco Firepower fabric:SwChPhEp:ifRole managed object property"
    ::= { cfprFabricSwChPhEpEntry 10 }

cfprFabricSwChPhEpIfType OBJECT-TYPE
    SYNTAX       CfprFabricPIoEpIfType
    MAX-ACCESS   read-only
    STATUS       current
    DESCRIPTION
        "Cisco Firepower fabric:SwChPhEp:ifType managed object property"
    ::= { cfprFabricSwChPhEpEntry 11 }

cfprFabricSwChPhEpLc OBJECT-TYPE
    SYNTAX       CfprFabricLifeCycle
    MAX-ACCESS   read-only
    STATUS       current
    DESCRIPTION
        "Cisco Firepower fabric:SwChPhEp:lc managed object property"
    ::= { cfprFabricSwChPhEpEntry 12 }

cfprFabricSwChPhEpLicGP OBJECT-TYPE
    SYNTAX       Unsigned64
    MAX-ACCESS   read-only
    STATUS       current
    DESCRIPTION
        "Cisco Firepower fabric:SwChPhEp:licGP managed object property"
    ::= { cfprFabricSwChPhEpEntry 13 }

cfprFabricSwChPhEpLicState OBJECT-TYPE
    SYNTAX       CfprLicenseState
    MAX-ACCESS   read-only
    STATUS       current
    DESCRIPTION
        "Cisco Firepower fabric:SwChPhEp:licState managed object property"
    ::= { cfprFabricSwChPhEpEntry 14 }

cfprFabricSwChPhEpLocale OBJECT-TYPE
    SYNTAX       CfprFabricInternalEpLocale
    MAX-ACCESS   read-only
    STATUS       current
    DESCRIPTION
        "Cisco Firepower fabric:SwChPhEp:locale managed object property"
    ::= { cfprFabricSwChPhEpEntry 15 }

cfprFabricSwChPhEpModel OBJECT-TYPE
    SYNTAX       SnmpAdminString
    MAX-ACCESS   read-only
    STATUS       current
    DESCRIPTION
        "Cisco Firepower fabric:SwChPhEp:model managed object property"
    ::= { cfprFabricSwChPhEpEntry 16 }

cfprFabricSwChPhEpName OBJECT-TYPE
    SYNTAX       SnmpAdminString
    MAX-ACCESS   read-only
    STATUS       current
    DESCRIPTION
        "Cisco Firepower fabric:SwChPhEp:name managed object property"
    ::= { cfprFabricSwChPhEpEntry 17 }

cfprFabricSwChPhEpOperState OBJECT-TYPE
    SYNTAX       CfprFabricPIoEpOperState
    MAX-ACCESS   read-only
    STATUS       current
    DESCRIPTION
        "Cisco Firepower fabric:SwChPhEp:operState managed
        object property"
    ::= { cfprFabricSwChPhEpEntry 18 }

cfprFabricSwChPhEpOperStateReason OBJECT-TYPE
    SYNTAX       SnmpAdminString
    MAX-ACCESS   read-only
    STATUS       current
    DESCRIPTION
        "Cisco Firepower fabric:SwChPhEp:operStateReason
        managed object property"
    ::= { cfprFabricSwChPhEpEntry 19 }

cfprFabricSwChPhEpPeerAggrPortId OBJECT-TYPE
    SYNTAX       Gauge32
    MAX-ACCESS   read-only
    STATUS       current
    DESCRIPTION
        "Cisco Firepower fabric:SwChPhEp:peerAggrPortId
        managed object property"
    ::= { cfprFabricSwChPhEpEntry 20 }

cfprFabricSwChPhEpPeerChassisId OBJECT-TYPE
    SYNTAX       Gauge32
    MAX-ACCESS   read-only
    STATUS       current
    DESCRIPTION
        "Cisco Firepower fabric:SwChPhEp:peerChassisId
        managed object property"
    ::= { cfprFabricSwChPhEpEntry 21 }

cfprFabricSwChPhEpPeerDn OBJECT-TYPE
    SYNTAX       SnmpAdminString
    MAX-ACCESS   read-only
    STATUS       current
    DESCRIPTION
        "Cisco Firepower fabric:SwChPhEp:peerDn managed object property"
    ::= { cfprFabricSwChPhEpEntry 22 }

cfprFabricSwChPhEpPeerPortId OBJECT-TYPE
    SYNTAX       Gauge32
    MAX-ACCESS   read-only
    STATUS       current
    DESCRIPTION
        "Cisco Firepower fabric:SwChPhEp:peerPortId managed
        object property"
    ::= { cfprFabricSwChPhEpEntry 23 }

cfprFabricSwChPhEpPeerSlotId OBJECT-TYPE
    SYNTAX       Gauge32
    MAX-ACCESS   read-only
    STATUS       current
    DESCRIPTION
        "Cisco Firepower fabric:SwChPhEp:peerSlotId managed
        object property"
    ::= { cfprFabricSwChPhEpEntry 24 }

cfprFabricSwChPhEpPortId OBJECT-TYPE
    SYNTAX       CfprFabricPIoEpPortId
    MAX-ACCESS   read-only
    STATUS       current
    DESCRIPTION
        "Cisco Firepower fabric:SwChPhEp:portId managed object property"
    ::= { cfprFabricSwChPhEpEntry 25 }

cfprFabricSwChPhEpRevision OBJECT-TYPE
    SYNTAX       SnmpAdminString
    MAX-ACCESS   read-only
    STATUS       current
    DESCRIPTION
        "Cisco Firepower fabric:SwChPhEp:revision managed object property"
    ::= { cfprFabricSwChPhEpEntry 26 }

cfprFabricSwChPhEpSerial OBJECT-TYPE
    SYNTAX       SnmpAdminString
    MAX-ACCESS   read-only
    STATUS       current
    DESCRIPTION
        "Cisco Firepower fabric:SwChPhEp:serial managed object property"
    ::= { cfprFabricSwChPhEpEntry 27 }

cfprFabricSwChPhEpSlotId OBJECT-TYPE
    SYNTAX       CfprFabricPIoEpSlotId
    MAX-ACCESS   read-only
    STATUS       current
    DESCRIPTION
        "Cisco Firepower fabric:SwChPhEp:slotId managed object property"
    ::= { cfprFabricSwChPhEpEntry 28 }

cfprFabricSwChPhEpSwitchId OBJECT-TYPE
    SYNTAX       CfprNetworkSwitchId
    MAX-ACCESS   read-only
    STATUS       current
    DESCRIPTION
        "Cisco Firepower fabric:SwChPhEp:switchId managed object property"
    ::= { cfprFabricSwChPhEpEntry 29 }

cfprFabricSwChPhEpTransport OBJECT-TYPE
    SYNTAX       CfprNetworkTransport
    MAX-ACCESS   read-only
    STATUS       current
    DESCRIPTION
        "Cisco Firepower fabric:SwChPhEp:transport managed
        object property"
    ::= { cfprFabricSwChPhEpEntry 30 }

cfprFabricSwChPhEpType OBJECT-TYPE
    SYNTAX       CfprFabricSwChEpType
    MAX-ACCESS   read-only
    STATUS       current
    DESCRIPTION
        "Cisco Firepower fabric:SwChPhEp:type managed object property"
    ::= { cfprFabricSwChPhEpEntry 31 }

cfprFabricSwChPhEpVendor OBJECT-TYPE
    SYNTAX       SnmpAdminString
    MAX-ACCESS   read-only
    STATUS       current
    DESCRIPTION
        "Cisco Firepower fabric:SwChPhEp:vendor managed object property"
    ::= { cfprFabricSwChPhEpEntry 32 }

cfprFabricSwSubGroupTable OBJECT-TYPE
    SYNTAX           SEQUENCE OF CfprFabricSwSubGroupEntry
    MAX-ACCESS       not-accessible
    STATUS           current
    DESCRIPTION
        "Cisco Firepower fabric:SwSubGroup managed object table"
    ::= { cfprFabricObjects 108 }

cfprFabricSwSubGroupEntry OBJECT-TYPE
    SYNTAX           CfprFabricSwSubGroupEntry
    MAX-ACCESS       not-accessible
    STATUS           current
    DESCRIPTION
        "Entry for the cfprFabricSwSubGroupTable table."
    INDEX { cfprFabricSwSubGroupInstanceId }
    ::= { cfprFabricSwSubGroupTable 1 }

CfprFabricSwSubGroupEntry ::= SEQUENCE {
    cfprFabricSwSubGroupInstanceId                                   CfprManagedObjectId,
    cfprFabricSwSubGroupDn                                           CfprManagedObjectDn,
    cfprFabricSwSubGroupRn                                           SnmpAdminString,
    cfprFabricSwSubGroupAggrPortId                                   CfprFabricSwSubGroupAggrPortId,
    cfprFabricSwSubGroupConfigState                                  CfprFabricSwSubGroupConfigState,
    cfprFabricSwSubGroupLicGP                                        Unsigned64,
    cfprFabricSwSubGroupLicState                                     CfprLicenseState,
    cfprFabricSwSubGroupLocale                                       CfprNetworkLocale,
    cfprFabricSwSubGroupName                                         SnmpAdminString,
    cfprFabricSwSubGroupSlotId                                       CfprFabricSwSubGroupSlotId,
    cfprFabricSwSubGroupSwitchId                                     CfprNetworkSwitchId,
    cfprFabricSwSubGroupTransport                                    CfprNetworkTransport,
    cfprFabricSwSubGroupType                                         CfprNetworkConnectionType
}

cfprFabricSwSubGroupInstanceId OBJECT-TYPE
    SYNTAX       CfprManagedObjectId
    MAX-ACCESS   not-accessible
    STATUS       current
    DESCRIPTION
        "Instance identifier of the managed object."
    ::= { cfprFabricSwSubGroupEntry 1 }

cfprFabricSwSubGroupDn OBJECT-TYPE
    SYNTAX       CfprManagedObjectDn
    MAX-ACCESS   read-only
    STATUS       current
    DESCRIPTION
        "Cisco Firepower fabric:SwSubGroup:dn managed object property"
    ::= { cfprFabricSwSubGroupEntry 2 }

cfprFabricSwSubGroupRn OBJECT-TYPE
    SYNTAX       SnmpAdminString
    MAX-ACCESS   read-only
    STATUS       current
    DESCRIPTION
        "Cisco Firepower fabric:SwSubGroup:rn managed object property"
    ::= { cfprFabricSwSubGroupEntry 3 }

cfprFabricSwSubGroupAggrPortId OBJECT-TYPE
    SYNTAX       CfprFabricSwSubGroupAggrPortId
    MAX-ACCESS   read-only
    STATUS       current
    DESCRIPTION
        "Cisco Firepower fabric:SwSubGroup:aggrPortId managed
        object property"
    ::= { cfprFabricSwSubGroupEntry 4 }

cfprFabricSwSubGroupConfigState OBJECT-TYPE
    SYNTAX       CfprFabricSwSubGroupConfigState
    MAX-ACCESS   read-only
    STATUS       current
    DESCRIPTION
        "Cisco Firepower fabric:SwSubGroup:configState
        managed object property"
    ::= { cfprFabricSwSubGroupEntry 5 }

cfprFabricSwSubGroupLicGP OBJECT-TYPE
    SYNTAX       Unsigned64
    MAX-ACCESS   read-only
    STATUS       current
    DESCRIPTION
        "Cisco Firepower fabric:SwSubGroup:licGP managed object property"
    ::= { cfprFabricSwSubGroupEntry 6 }

cfprFabricSwSubGroupLicState OBJECT-TYPE
    SYNTAX       CfprLicenseState
    MAX-ACCESS   read-only
    STATUS       current
    DESCRIPTION
        "Cisco Firepower fabric:SwSubGroup:licState managed
        object property"
    ::= { cfprFabricSwSubGroupEntry 7 }

cfprFabricSwSubGroupLocale OBJECT-TYPE
    SYNTAX       CfprNetworkLocale
    MAX-ACCESS   read-only
    STATUS       current
    DESCRIPTION
        "Cisco Firepower fabric:SwSubGroup:locale managed object property"
    ::= { cfprFabricSwSubGroupEntry 8 }

cfprFabricSwSubGroupName OBJECT-TYPE
    SYNTAX       SnmpAdminString
    MAX-ACCESS   read-only
    STATUS       current
    DESCRIPTION
        "Cisco Firepower fabric:SwSubGroup:name managed object property"
    ::= { cfprFabricSwSubGroupEntry 9 }

cfprFabricSwSubGroupSlotId OBJECT-TYPE
    SYNTAX       CfprFabricSwSubGroupSlotId
    MAX-ACCESS   read-only
    STATUS       current
    DESCRIPTION
        "Cisco Firepower fabric:SwSubGroup:slotId managed object property"
    ::= { cfprFabricSwSubGroupEntry 10 }

cfprFabricSwSubGroupSwitchId OBJECT-TYPE
    SYNTAX       CfprNetworkSwitchId
    MAX-ACCESS   read-only
    STATUS       current
    DESCRIPTION
        "Cisco Firepower fabric:SwSubGroup:switchId managed
        object property"
    ::= { cfprFabricSwSubGroupEntry 11 }

cfprFabricSwSubGroupTransport OBJECT-TYPE
    SYNTAX       CfprNetworkTransport
    MAX-ACCESS   read-only
    STATUS       current
    DESCRIPTION
        "Cisco Firepower fabric:SwSubGroup:transport managed
        object property"
    ::= { cfprFabricSwSubGroupEntry 12 }

cfprFabricSwSubGroupType OBJECT-TYPE
    SYNTAX       CfprNetworkConnectionType
    MAX-ACCESS   read-only
    STATUS       current
    DESCRIPTION
        "Cisco Firepower fabric:SwSubGroup:type managed object property"
    ::= { cfprFabricSwSubGroupEntry 13 }

cfprFabricUdldLinkPolicyTable OBJECT-TYPE
    SYNTAX           SEQUENCE OF CfprFabricUdldLinkPolicyEntry
    MAX-ACCESS       not-accessible
    STATUS           current
    DESCRIPTION
        "Cisco Firepower fabric:UdldLinkPolicy managed object table"
    ::= { cfprFabricObjects 109 }

cfprFabricUdldLinkPolicyEntry OBJECT-TYPE
    SYNTAX           CfprFabricUdldLinkPolicyEntry
    MAX-ACCESS       not-accessible
    STATUS           current
    DESCRIPTION
        "Entry for the cfprFabricUdldLinkPolicyTable table."
    INDEX { cfprFabricUdldLinkPolicyInstanceId }
    ::= { cfprFabricUdldLinkPolicyTable 1 }

CfprFabricUdldLinkPolicyEntry ::= SEQUENCE {
    cfprFabricUdldLinkPolicyInstanceId                               CfprManagedObjectId,
    cfprFabricUdldLinkPolicyDn                                       CfprManagedObjectDn,
    cfprFabricUdldLinkPolicyRn                                       SnmpAdminString,
    cfprFabricUdldLinkPolicyAdminState                               CfprFabricUdldLinkPolicyAdminState,
    cfprFabricUdldLinkPolicyDescr                                    SnmpAdminString,
    cfprFabricUdldLinkPolicyIntId                                    SnmpAdminString,
    cfprFabricUdldLinkPolicyMode                                     CfprFabricUdldLinkPolicyMode,
    cfprFabricUdldLinkPolicyName                                     SnmpAdminString,
    cfprFabricUdldLinkPolicyPolicyLevel                              Gauge32,
    cfprFabricUdldLinkPolicyPolicyOwner                              CfprPolicyPolicyOwner,
    cfprFabricUdldLinkPolicyProtocol                                 CfprFabricEthUdldPolicyProtocol,
    cfprFabricUdldLinkPolicyType                                     CfprFabricEthLinkPolicyType
}

cfprFabricUdldLinkPolicyInstanceId OBJECT-TYPE
    SYNTAX       CfprManagedObjectId
    MAX-ACCESS   not-accessible
    STATUS       current
    DESCRIPTION
        "Instance identifier of the managed object."
    ::= { cfprFabricUdldLinkPolicyEntry 1 }

cfprFabricUdldLinkPolicyDn OBJECT-TYPE
    SYNTAX       CfprManagedObjectDn
    MAX-ACCESS   read-only
    STATUS       current
    DESCRIPTION
        "Cisco Firepower fabric:UdldLinkPolicy:dn managed object property"
    ::= { cfprFabricUdldLinkPolicyEntry 2 }

cfprFabricUdldLinkPolicyRn OBJECT-TYPE
    SYNTAX       SnmpAdminString
    MAX-ACCESS   read-only
    STATUS       current
    DESCRIPTION
        "Cisco Firepower fabric:UdldLinkPolicy:rn managed object property"
    ::= { cfprFabricUdldLinkPolicyEntry 3 }

cfprFabricUdldLinkPolicyAdminState OBJECT-TYPE
    SYNTAX       CfprFabricUdldLinkPolicyAdminState
    MAX-ACCESS   read-only
    STATUS       current
    DESCRIPTION
        "Cisco Firepower fabric:UdldLinkPolicy:adminState
        managed object property"
    ::= { cfprFabricUdldLinkPolicyEntry 4 }

cfprFabricUdldLinkPolicyDescr OBJECT-TYPE
    SYNTAX       SnmpAdminString
    MAX-ACCESS   read-only
    STATUS       current
    DESCRIPTION
        "Cisco Firepower fabric:UdldLinkPolicy:descr managed
        object property"
    ::= { cfprFabricUdldLinkPolicyEntry 5 }

cfprFabricUdldLinkPolicyIntId OBJECT-TYPE
    SYNTAX       SnmpAdminString
    MAX-ACCESS   read-only
    STATUS       current
    DESCRIPTION
        "Cisco Firepower fabric:UdldLinkPolicy:intId managed
        object property"
    ::= { cfprFabricUdldLinkPolicyEntry 6 }

cfprFabricUdldLinkPolicyMode OBJECT-TYPE
    SYNTAX       CfprFabricUdldLinkPolicyMode
    MAX-ACCESS   read-only
    STATUS       current
    DESCRIPTION
        "Cisco Firepower fabric:UdldLinkPolicy:mode managed
        object property"
    ::= { cfprFabricUdldLinkPolicyEntry 7 }

cfprFabricUdldLinkPolicyName OBJECT-TYPE
    SYNTAX       SnmpAdminString
    MAX-ACCESS   read-only
    STATUS       current
    DESCRIPTION
        "Cisco Firepower fabric:UdldLinkPolicy:name managed
        object property"
    ::= { cfprFabricUdldLinkPolicyEntry 8 }

cfprFabricUdldLinkPolicyPolicyLevel OBJECT-TYPE
    SYNTAX       Gauge32
    MAX-ACCESS   read-only
    STATUS       current
    DESCRIPTION
        "Cisco Firepower fabric:UdldLinkPolicy:policyLevel
        managed object property"
    ::= { cfprFabricUdldLinkPolicyEntry 9 }

cfprFabricUdldLinkPolicyPolicyOwner OBJECT-TYPE
    SYNTAX       CfprPolicyPolicyOwner
    MAX-ACCESS   read-only
    STATUS       current
    DESCRIPTION
        "Cisco Firepower fabric:UdldLinkPolicy:policyOwner
        managed object property"
    ::= { cfprFabricUdldLinkPolicyEntry 10 }

cfprFabricUdldLinkPolicyProtocol OBJECT-TYPE
    SYNTAX       CfprFabricEthUdldPolicyProtocol
    MAX-ACCESS   read-only
    STATUS       current
    DESCRIPTION
        "Cisco Firepower fabric:UdldLinkPolicy:protocol
        managed object property"
    ::= { cfprFabricUdldLinkPolicyEntry 11 }

cfprFabricUdldLinkPolicyType OBJECT-TYPE
    SYNTAX       CfprFabricEthLinkPolicyType
    MAX-ACCESS   read-only
    STATUS       current
    DESCRIPTION
        "Cisco Firepower fabric:UdldLinkPolicy:type managed
        object property"
    ::= { cfprFabricUdldLinkPolicyEntry 12 }

cfprFabricUdldPolicyTable OBJECT-TYPE
    SYNTAX           SEQUENCE OF CfprFabricUdldPolicyEntry
    MAX-ACCESS       not-accessible
    STATUS           current
    DESCRIPTION
        "Cisco Firepower fabric:UdldPolicy managed object table"
    ::= { cfprFabricObjects 110 }

cfprFabricUdldPolicyEntry OBJECT-TYPE
    SYNTAX           CfprFabricUdldPolicyEntry
    MAX-ACCESS       not-accessible
    STATUS           current
    DESCRIPTION
        "Entry for the cfprFabricUdldPolicyTable table."
    INDEX { cfprFabricUdldPolicyInstanceId }
    ::= { cfprFabricUdldPolicyTable 1 }

CfprFabricUdldPolicyEntry ::= SEQUENCE {
    cfprFabricUdldPolicyInstanceId                                   CfprManagedObjectId,
    cfprFabricUdldPolicyDn                                           CfprManagedObjectDn,
    cfprFabricUdldPolicyRn                                           SnmpAdminString,
    cfprFabricUdldPolicyDescr                                        SnmpAdminString,
    cfprFabricUdldPolicyIntId                                        SnmpAdminString,
    cfprFabricUdldPolicyMsgInterval                                  Gauge32,
    cfprFabricUdldPolicyName                                         SnmpAdminString,
    cfprFabricUdldPolicyPolicyLevel                                  Gauge32,
    cfprFabricUdldPolicyPolicyOwner                                  CfprPolicyPolicyOwner,
    cfprFabricUdldPolicyRecoveryAction                               CfprFabricRecoveryAction
}

cfprFabricUdldPolicyInstanceId OBJECT-TYPE
    SYNTAX       CfprManagedObjectId
    MAX-ACCESS   not-accessible
    STATUS       current
    DESCRIPTION
        "Instance identifier of the managed object."
    ::= { cfprFabricUdldPolicyEntry 1 }

cfprFabricUdldPolicyDn OBJECT-TYPE
    SYNTAX       CfprManagedObjectDn
    MAX-ACCESS   read-only
    STATUS       current
    DESCRIPTION
        "Cisco Firepower fabric:UdldPolicy:dn managed object property"
    ::= { cfprFabricUdldPolicyEntry 2 }

cfprFabricUdldPolicyRn OBJECT-TYPE
    SYNTAX       SnmpAdminString
    MAX-ACCESS   read-only
    STATUS       current
    DESCRIPTION
        "Cisco Firepower fabric:UdldPolicy:rn managed object property"
    ::= { cfprFabricUdldPolicyEntry 3 }

cfprFabricUdldPolicyDescr OBJECT-TYPE
    SYNTAX       SnmpAdminString
    MAX-ACCESS   read-only
    STATUS       current
    DESCRIPTION
        "Cisco Firepower fabric:UdldPolicy:descr managed object property"
    ::= { cfprFabricUdldPolicyEntry 4 }

cfprFabricUdldPolicyIntId OBJECT-TYPE
    SYNTAX       SnmpAdminString
    MAX-ACCESS   read-only
    STATUS       current
    DESCRIPTION
        "Cisco Firepower fabric:UdldPolicy:intId managed object property"
    ::= { cfprFabricUdldPolicyEntry 5 }

cfprFabricUdldPolicyMsgInterval OBJECT-TYPE
    SYNTAX       Gauge32
    MAX-ACCESS   read-only
    STATUS       current
    DESCRIPTION
        "Cisco Firepower fabric:UdldPolicy:msgInterval
        managed object property"
    ::= { cfprFabricUdldPolicyEntry 6 }

cfprFabricUdldPolicyName OBJECT-TYPE
    SYNTAX       SnmpAdminString
    MAX-ACCESS   read-only
    STATUS       current
    DESCRIPTION
        "Cisco Firepower fabric:UdldPolicy:name managed object property"
    ::= { cfprFabricUdldPolicyEntry 7 }

cfprFabricUdldPolicyPolicyLevel OBJECT-TYPE
    SYNTAX       Gauge32
    MAX-ACCESS   read-only
    STATUS       current
    DESCRIPTION
        "Cisco Firepower fabric:UdldPolicy:policyLevel
        managed object property"
    ::= { cfprFabricUdldPolicyEntry 8 }

cfprFabricUdldPolicyPolicyOwner OBJECT-TYPE
    SYNTAX       CfprPolicyPolicyOwner
    MAX-ACCESS   read-only
    STATUS       current
    DESCRIPTION
        "Cisco Firepower fabric:UdldPolicy:policyOwner
        managed object property"
    ::= { cfprFabricUdldPolicyEntry 9 }

cfprFabricUdldPolicyRecoveryAction OBJECT-TYPE
    SYNTAX       CfprFabricRecoveryAction
    MAX-ACCESS   read-only
    STATUS       current
    DESCRIPTION
        "Cisco Firepower fabric:UdldPolicy:recoveryAction
        managed object property"
    ::= { cfprFabricUdldPolicyEntry 10 }

cfprFabricVConTable OBJECT-TYPE
    SYNTAX           SEQUENCE OF CfprFabricVConEntry
    MAX-ACCESS       not-accessible
    STATUS           current
    DESCRIPTION
        "Cisco Firepower fabric:VCon managed object table"
    ::= { cfprFabricObjects 111 }

cfprFabricVConEntry OBJECT-TYPE
    SYNTAX           CfprFabricVConEntry
    MAX-ACCESS       not-accessible
    STATUS           current
    DESCRIPTION
        "Entry for the cfprFabricVConTable table."
    INDEX { cfprFabricVConInstanceId }
    ::= { cfprFabricVConTable 1 }

CfprFabricVConEntry ::= SEQUENCE {
    cfprFabricVConInstanceId                                         CfprManagedObjectId,
    cfprFabricVConDn                                                 CfprManagedObjectDn,
    cfprFabricVConRn                                                 SnmpAdminString,
    cfprFabricVConEquipmentDn                                        SnmpAdminString,
    cfprFabricVConFabric                                             SnmpAdminString,
    cfprFabricVConId                                                 SnmpAdminString,
    cfprFabricVConInstType                                           CfprFabricVConInstType,
    cfprFabricVConPlacement                                          CfprFabricVConPlacementPref,
    cfprFabricVConSelect                                             CfprFabricVConSelectPref,
    cfprFabricVConShare                                              CfprFabricVConSharePref,
    cfprFabricVConTransport                                          CfprFabricVConTransportPref
}

cfprFabricVConInstanceId OBJECT-TYPE
    SYNTAX       CfprManagedObjectId
    MAX-ACCESS   not-accessible
    STATUS       current
    DESCRIPTION
        "Instance identifier of the managed object."
    ::= { cfprFabricVConEntry 1 }

cfprFabricVConDn OBJECT-TYPE
    SYNTAX       CfprManagedObjectDn
    MAX-ACCESS   read-only
    STATUS       current
    DESCRIPTION
        "Cisco Firepower fabric:VCon:dn managed object property"
    ::= { cfprFabricVConEntry 2 }

cfprFabricVConRn OBJECT-TYPE
    SYNTAX       SnmpAdminString
    MAX-ACCESS   read-only
    STATUS       current
    DESCRIPTION
        "Cisco Firepower fabric:VCon:rn managed object property"
    ::= { cfprFabricVConEntry 3 }

cfprFabricVConEquipmentDn OBJECT-TYPE
    SYNTAX       SnmpAdminString
    MAX-ACCESS   read-only
    STATUS       current
    DESCRIPTION
        "Cisco Firepower fabric:VCon:equipmentDn managed object property"
    ::= { cfprFabricVConEntry 4 }

cfprFabricVConFabric OBJECT-TYPE
    SYNTAX       SnmpAdminString
    MAX-ACCESS   read-only
    STATUS       current
    DESCRIPTION
        "Cisco Firepower fabric:VCon:fabric managed object property"
    ::= { cfprFabricVConEntry 5 }

cfprFabricVConId OBJECT-TYPE
    SYNTAX       SnmpAdminString
    MAX-ACCESS   read-only
    STATUS       current
    DESCRIPTION
        "Cisco Firepower fabric:VCon:id managed object property"
    ::= { cfprFabricVConEntry 6 }

cfprFabricVConInstType OBJECT-TYPE
    SYNTAX       CfprFabricVConInstType
    MAX-ACCESS   read-only
    STATUS       current
    DESCRIPTION
        "Cisco Firepower fabric:VCon:instType managed object property"
    ::= { cfprFabricVConEntry 7 }

cfprFabricVConPlacement OBJECT-TYPE
    SYNTAX       CfprFabricVConPlacementPref
    MAX-ACCESS   read-only
    STATUS       current
    DESCRIPTION
        "Cisco Firepower fabric:VCon:placement managed object property"
    ::= { cfprFabricVConEntry 8 }

cfprFabricVConSelect OBJECT-TYPE
    SYNTAX       CfprFabricVConSelectPref
    MAX-ACCESS   read-only
    STATUS       current
    DESCRIPTION
        "Cisco Firepower fabric:VCon:select managed object property"
    ::= { cfprFabricVConEntry 9 }

cfprFabricVConShare OBJECT-TYPE
    SYNTAX       CfprFabricVConSharePref
    MAX-ACCESS   read-only
    STATUS       current
    DESCRIPTION
        "Cisco Firepower fabric:VCon:share managed object property"
    ::= { cfprFabricVConEntry 10 }

cfprFabricVConTransport OBJECT-TYPE
    SYNTAX       CfprFabricVConTransportPref
    MAX-ACCESS   read-only
    STATUS       current
    DESCRIPTION
        "Cisco Firepower fabric:VCon:transport managed object property"
    ::= { cfprFabricVConEntry 11 }

cfprFabricVConProfileTable OBJECT-TYPE
    SYNTAX           SEQUENCE OF CfprFabricVConProfileEntry
    MAX-ACCESS       not-accessible
    STATUS           current
    DESCRIPTION
        "Cisco Firepower fabric:VConProfile managed object table"
    ::= { cfprFabricObjects 112 }

cfprFabricVConProfileEntry OBJECT-TYPE
    SYNTAX           CfprFabricVConProfileEntry
    MAX-ACCESS       not-accessible
    STATUS           current
    DESCRIPTION
        "Entry for the cfprFabricVConProfileTable table."
    INDEX { cfprFabricVConProfileInstanceId }
    ::= { cfprFabricVConProfileTable 1 }

CfprFabricVConProfileEntry ::= SEQUENCE {
    cfprFabricVConProfileInstanceId                                  CfprManagedObjectId,
    cfprFabricVConProfileDn                                          CfprManagedObjectDn,
    cfprFabricVConProfileRn                                          SnmpAdminString,
    cfprFabricVConProfileDescr                                       SnmpAdminString,
    cfprFabricVConProfileIntId                                       SnmpAdminString,
    cfprFabricVConProfileMezzMapping                                 CfprFabricVConMappingScheme,
    cfprFabricVConProfileName                                        SnmpAdminString,
    cfprFabricVConProfilePolicyLevel                                 Gauge32,
    cfprFabricVConProfilePolicyOwner                                 CfprPolicyPolicyOwner
}

cfprFabricVConProfileInstanceId OBJECT-TYPE
    SYNTAX       CfprManagedObjectId
    MAX-ACCESS   not-accessible
    STATUS       current
    DESCRIPTION
        "Instance identifier of the managed object."
    ::= { cfprFabricVConProfileEntry 1 }

cfprFabricVConProfileDn OBJECT-TYPE
    SYNTAX       CfprManagedObjectDn
    MAX-ACCESS   read-only
    STATUS       current
    DESCRIPTION
        "Cisco Firepower fabric:VConProfile:dn managed object property"
    ::= { cfprFabricVConProfileEntry 2 }

cfprFabricVConProfileRn OBJECT-TYPE
    SYNTAX       SnmpAdminString
    MAX-ACCESS   read-only
    STATUS       current
    DESCRIPTION
        "Cisco Firepower fabric:VConProfile:rn managed object property"
    ::= { cfprFabricVConProfileEntry 3 }

cfprFabricVConProfileDescr OBJECT-TYPE
    SYNTAX       SnmpAdminString
    MAX-ACCESS   read-only
    STATUS       current
    DESCRIPTION
        "Cisco Firepower fabric:VConProfile:descr managed object property"
    ::= { cfprFabricVConProfileEntry 4 }

cfprFabricVConProfileIntId OBJECT-TYPE
    SYNTAX       SnmpAdminString
    MAX-ACCESS   read-only
    STATUS       current
    DESCRIPTION
        "Cisco Firepower fabric:VConProfile:intId managed object property"
    ::= { cfprFabricVConProfileEntry 5 }

cfprFabricVConProfileMezzMapping OBJECT-TYPE
    SYNTAX       CfprFabricVConMappingScheme
    MAX-ACCESS   read-only
    STATUS       current
    DESCRIPTION
        "Cisco Firepower fabric:VConProfile:mezzMapping
        managed object property"
    ::= { cfprFabricVConProfileEntry 6 }

cfprFabricVConProfileName OBJECT-TYPE
    SYNTAX       SnmpAdminString
    MAX-ACCESS   read-only
    STATUS       current
    DESCRIPTION
        "Cisco Firepower fabric:VConProfile:name managed object property"
    ::= { cfprFabricVConProfileEntry 7 }

cfprFabricVConProfilePolicyLevel OBJECT-TYPE
    SYNTAX       Gauge32
    MAX-ACCESS   read-only
    STATUS       current
    DESCRIPTION
        "Cisco Firepower fabric:VConProfile:policyLevel
        managed object property"
    ::= { cfprFabricVConProfileEntry 8 }

cfprFabricVConProfilePolicyOwner OBJECT-TYPE
    SYNTAX       CfprPolicyPolicyOwner
    MAX-ACCESS   read-only
    STATUS       current
    DESCRIPTION
        "Cisco Firepower fabric:VConProfile:policyOwner
        managed object property"
    ::= { cfprFabricVConProfileEntry 9 }

cfprFabricVlanTable OBJECT-TYPE
    SYNTAX           SEQUENCE OF CfprFabricVlanEntry
    MAX-ACCESS       not-accessible
    STATUS           current
    DESCRIPTION
        "Cisco Firepower fabric:Vlan managed object table"
    ::= { cfprFabricObjects 113 }

cfprFabricVlanEntry OBJECT-TYPE
    SYNTAX           CfprFabricVlanEntry
    MAX-ACCESS       not-accessible
    STATUS           current
    DESCRIPTION
        "Entry for the cfprFabricVlanTable table."
    INDEX { cfprFabricVlanInstanceId }
    ::= { cfprFabricVlanTable 1 }

CfprFabricVlanEntry ::= SEQUENCE {
    cfprFabricVlanInstanceId                                         CfprManagedObjectId,
    cfprFabricVlanDn                                                 CfprManagedObjectDn,
    cfprFabricVlanRn                                                 SnmpAdminString,
    cfprFabricVlanAssocPrimaryVlanState                              CfprFabricVlanAssocPrimaryVlanState,
    cfprFabricVlanAssocPrimaryVlanSwitchId                           CfprFabricAVlanAssocPrimaryVlanSwitchId,
    cfprFabricVlanCloud                                              CfprFabricCloudType,
    cfprFabricVlanCompressionType                                    CfprFabricVlanCompType,
    cfprFabricVlanConfigIssues                                       CfprFabricVlanConfigIssues,
    cfprFabricVlanDefaultNet                                         TruthValue,
    cfprFabricVlanEpDn                                               SnmpAdminString,
    cfprFabricVlanFltAggr                                            Unsigned64,
    cfprFabricVlanGlobal                                             Unsigned64,
    cfprFabricVlanId                                                 Gauge32,
    cfprFabricVlanIfRole                                             CfprFabricVnetEpIfRole,
    cfprFabricVlanIfType                                             CfprNetworkVnetEpIfType,
    cfprFabricVlanLocal                                              Unsigned64,
    cfprFabricVlanLocale                                             CfprFabricVnetEpLocale,
    cfprFabricVlanMcastPolicyName                                    SnmpAdminString,
    cfprFabricVlanName                                               SnmpAdminString,
    cfprFabricVlanOperMcastPolicyName                                SnmpAdminString,
    cfprFabricVlanOperState                                          CfprFabricVlanOperState,
    cfprFabricVlanOverlapStateForA                                   CfprFabricVlanOverlapState,
    cfprFabricVlanOverlapStateForB                                   CfprFabricVlanOverlapState,
    cfprFabricVlanPeerDn                                             SnmpAdminString,
    cfprFabricVlanPolicyOwner                                        CfprFabricVnetEpPolicyOwner,
    cfprFabricVlanPubNwDn                                            SnmpAdminString,
    cfprFabricVlanPubNwId                                            Gauge32,
    cfprFabricVlanPubNwName                                          SnmpAdminString,
    cfprFabricVlanSharing                                            CfprFabricAVlanSharing,
    cfprFabricVlanSwitchId                                           CfprFabricVlanSwitchId,
    cfprFabricVlanTransport                                          CfprFabricAVlanTransport,
    cfprFabricVlanType                                               CfprFabricAVlanType
}

cfprFabricVlanInstanceId OBJECT-TYPE
    SYNTAX       CfprManagedObjectId
    MAX-ACCESS   not-accessible
    STATUS       current
    DESCRIPTION
        "Instance identifier of the managed object."
    ::= { cfprFabricVlanEntry 1 }

cfprFabricVlanDn OBJECT-TYPE
    SYNTAX       CfprManagedObjectDn
    MAX-ACCESS   read-only
    STATUS       current
    DESCRIPTION
        "Cisco Firepower fabric:Vlan:dn managed object property"
    ::= { cfprFabricVlanEntry 2 }

cfprFabricVlanRn OBJECT-TYPE
    SYNTAX       SnmpAdminString
    MAX-ACCESS   read-only
    STATUS       current
    DESCRIPTION
        "Cisco Firepower fabric:Vlan:rn managed object property"
    ::= { cfprFabricVlanEntry 3 }

cfprFabricVlanAssocPrimaryVlanState OBJECT-TYPE
    SYNTAX       CfprFabricVlanAssocPrimaryVlanState
    MAX-ACCESS   read-only
    STATUS       current
    DESCRIPTION
        "Cisco Firepower fabric:Vlan:assocPrimaryVlanState
        managed object property"
    ::= { cfprFabricVlanEntry 4 }

cfprFabricVlanAssocPrimaryVlanSwitchId OBJECT-TYPE
    SYNTAX       CfprFabricAVlanAssocPrimaryVlanSwitchId
    MAX-ACCESS   read-only
    STATUS       current
    DESCRIPTION
        "Cisco Firepower fabric:Vlan:assocPrimaryVlanSwitchId
        managed object property"
    ::= { cfprFabricVlanEntry 5 }

cfprFabricVlanCloud OBJECT-TYPE
    SYNTAX       CfprFabricCloudType
    MAX-ACCESS   read-only
    STATUS       current
    DESCRIPTION
        "Cisco Firepower fabric:Vlan:cloud managed object property"
    ::= { cfprFabricVlanEntry 6 }

cfprFabricVlanCompressionType OBJECT-TYPE
    SYNTAX       CfprFabricVlanCompType
    MAX-ACCESS   read-only
    STATUS       current
    DESCRIPTION
        "Cisco Firepower fabric:Vlan:compressionType managed
        object property"
    ::= { cfprFabricVlanEntry 7 }

cfprFabricVlanConfigIssues OBJECT-TYPE
    SYNTAX       CfprFabricVlanConfigIssues
    MAX-ACCESS   read-only
    STATUS       current
    DESCRIPTION
        "Cisco Firepower fabric:Vlan:configIssues managed object property"
    ::= { cfprFabricVlanEntry 8 }

cfprFabricVlanDefaultNet OBJECT-TYPE
    SYNTAX       TruthValue
    MAX-ACCESS   read-only
    STATUS       current
    DESCRIPTION
        "Cisco Firepower fabric:Vlan:defaultNet managed object property"
    ::= { cfprFabricVlanEntry 9 }

cfprFabricVlanEpDn OBJECT-TYPE
    SYNTAX       SnmpAdminString
    MAX-ACCESS   read-only
    STATUS       current
    DESCRIPTION
        "Cisco Firepower fabric:Vlan:epDn managed object property"
    ::= { cfprFabricVlanEntry 10 }

cfprFabricVlanFltAggr OBJECT-TYPE
    SYNTAX       Unsigned64
    MAX-ACCESS   read-only
    STATUS       current
    DESCRIPTION
        "Cisco Firepower fabric:Vlan:fltAggr managed object property"
    ::= { cfprFabricVlanEntry 11 }

cfprFabricVlanGlobal OBJECT-TYPE
    SYNTAX       Unsigned64
    MAX-ACCESS   read-only
    STATUS       current
    DESCRIPTION
        "Cisco Firepower fabric:Vlan:global managed object property"
    ::= { cfprFabricVlanEntry 12 }

cfprFabricVlanId OBJECT-TYPE
    SYNTAX       Gauge32
    MAX-ACCESS   read-only
    STATUS       current
    DESCRIPTION
        "Cisco Firepower fabric:Vlan:id managed object property"
    ::= { cfprFabricVlanEntry 13 }

cfprFabricVlanIfRole OBJECT-TYPE
    SYNTAX       CfprFabricVnetEpIfRole
    MAX-ACCESS   read-only
    STATUS       current
    DESCRIPTION
        "Cisco Firepower fabric:Vlan:ifRole managed object property"
    ::= { cfprFabricVlanEntry 14 }

cfprFabricVlanIfType OBJECT-TYPE
    SYNTAX       CfprNetworkVnetEpIfType
    MAX-ACCESS   read-only
    STATUS       current
    DESCRIPTION
        "Cisco Firepower fabric:Vlan:ifType managed object property"
    ::= { cfprFabricVlanEntry 15 }

cfprFabricVlanLocal OBJECT-TYPE
    SYNTAX       Unsigned64
    MAX-ACCESS   read-only
    STATUS       current
    DESCRIPTION
        "Cisco Firepower fabric:Vlan:local managed object property"
    ::= { cfprFabricVlanEntry 16 }

cfprFabricVlanLocale OBJECT-TYPE
    SYNTAX       CfprFabricVnetEpLocale
    MAX-ACCESS   read-only
    STATUS       current
    DESCRIPTION
        "Cisco Firepower fabric:Vlan:locale managed object property"
    ::= { cfprFabricVlanEntry 17 }

cfprFabricVlanMcastPolicyName OBJECT-TYPE
    SYNTAX       SnmpAdminString
    MAX-ACCESS   read-only
    STATUS       current
    DESCRIPTION
        "Cisco Firepower fabric:Vlan:mcastPolicyName managed
        object property"
    ::= { cfprFabricVlanEntry 18 }

cfprFabricVlanName OBJECT-TYPE
    SYNTAX       SnmpAdminString
    MAX-ACCESS   read-only
    STATUS       current
    DESCRIPTION
        "Cisco Firepower fabric:Vlan:name managed object property"
    ::= { cfprFabricVlanEntry 19 }

cfprFabricVlanOperMcastPolicyName OBJECT-TYPE
    SYNTAX       SnmpAdminString
    MAX-ACCESS   read-only
    STATUS       current
    DESCRIPTION
        "Cisco Firepower fabric:Vlan:operMcastPolicyName
        managed object property"
    ::= { cfprFabricVlanEntry 20 }

cfprFabricVlanOperState OBJECT-TYPE
    SYNTAX       CfprFabricVlanOperState
    MAX-ACCESS   read-only
    STATUS       current
    DESCRIPTION
        "Cisco Firepower fabric:Vlan:operState managed object property"
    ::= { cfprFabricVlanEntry 21 }

cfprFabricVlanOverlapStateForA OBJECT-TYPE
    SYNTAX       CfprFabricVlanOverlapState
    MAX-ACCESS   read-only
    STATUS       current
    DESCRIPTION
        "Cisco Firepower fabric:Vlan:overlapStateForA managed
        object property"
    ::= { cfprFabricVlanEntry 22 }

cfprFabricVlanOverlapStateForB OBJECT-TYPE
    SYNTAX       CfprFabricVlanOverlapState
    MAX-ACCESS   read-only
    STATUS       current
    DESCRIPTION
        "Cisco Firepower fabric:Vlan:overlapStateForB managed
        object property"
    ::= { cfprFabricVlanEntry 23 }

cfprFabricVlanPeerDn OBJECT-TYPE
    SYNTAX       SnmpAdminString
    MAX-ACCESS   read-only
    STATUS       current
    DESCRIPTION
        "Cisco Firepower fabric:Vlan:peerDn managed object property"
    ::= { cfprFabricVlanEntry 24 }

cfprFabricVlanPolicyOwner OBJECT-TYPE
    SYNTAX       CfprFabricVnetEpPolicyOwner
    MAX-ACCESS   read-only
    STATUS       current
    DESCRIPTION
        "Cisco Firepower fabric:Vlan:policyOwner managed object property"
    ::= { cfprFabricVlanEntry 25 }

cfprFabricVlanPubNwDn OBJECT-TYPE
    SYNTAX       SnmpAdminString
    MAX-ACCESS   read-only
    STATUS       current
    DESCRIPTION
        "Cisco Firepower fabric:Vlan:pubNwDn managed object property"
    ::= { cfprFabricVlanEntry 26 }

cfprFabricVlanPubNwId OBJECT-TYPE
    SYNTAX       Gauge32
    MAX-ACCESS   read-only
    STATUS       current
    DESCRIPTION
        "Cisco Firepower fabric:Vlan:pubNwId managed object property"
    ::= { cfprFabricVlanEntry 27 }

cfprFabricVlanPubNwName OBJECT-TYPE
    SYNTAX       SnmpAdminString
    MAX-ACCESS   read-only
    STATUS       current
    DESCRIPTION
        "Cisco Firepower fabric:Vlan:pubNwName managed object property"
    ::= { cfprFabricVlanEntry 28 }

cfprFabricVlanSharing OBJECT-TYPE
    SYNTAX       CfprFabricAVlanSharing
    MAX-ACCESS   read-only
    STATUS       current
    DESCRIPTION
        "Cisco Firepower fabric:Vlan:sharing managed object property"
    ::= { cfprFabricVlanEntry 29 }

cfprFabricVlanSwitchId OBJECT-TYPE
    SYNTAX       CfprFabricVlanSwitchId
    MAX-ACCESS   read-only
    STATUS       current
    DESCRIPTION
        "Cisco Firepower fabric:Vlan:switchId managed object property"
    ::= { cfprFabricVlanEntry 30 }

cfprFabricVlanTransport OBJECT-TYPE
    SYNTAX       CfprFabricAVlanTransport
    MAX-ACCESS   read-only
    STATUS       current
    DESCRIPTION
        "Cisco Firepower fabric:Vlan:transport managed object property"
    ::= { cfprFabricVlanEntry 31 }

cfprFabricVlanType OBJECT-TYPE
    SYNTAX       CfprFabricAVlanType
    MAX-ACCESS   read-only
    STATUS       current
    DESCRIPTION
        "Cisco Firepower fabric:Vlan:type managed object property"
    ::= { cfprFabricVlanEntry 32 }

cfprFabricVlanEpTable OBJECT-TYPE
    SYNTAX           SEQUENCE OF CfprFabricVlanEpEntry
    MAX-ACCESS       not-accessible
    STATUS           current
    DESCRIPTION
        "Cisco Firepower fabric:VlanEp managed object table"
    ::= { cfprFabricObjects 114 }

cfprFabricVlanEpEntry OBJECT-TYPE
    SYNTAX           CfprFabricVlanEpEntry
    MAX-ACCESS       not-accessible
    STATUS           current
    DESCRIPTION
        "Entry for the cfprFabricVlanEpTable table."
    INDEX { cfprFabricVlanEpInstanceId }
    ::= { cfprFabricVlanEpTable 1 }

CfprFabricVlanEpEntry ::= SEQUENCE {
    cfprFabricVlanEpInstanceId                                       CfprManagedObjectId,
    cfprFabricVlanEpDnData                                           CfprManagedObjectDn,
    cfprFabricVlanEpRn                                               SnmpAdminString,
    cfprFabricVlanEpAssocPrimaryVlanState                            CfprFabricVlanAssocPrimaryVlanState,
    cfprFabricVlanEpAssocPrimaryVlanSwitchId                         CfprFabricAVlanAssocPrimaryVlanSwitchId,
    cfprFabricVlanEpEpDn                                             SnmpAdminString,
    cfprFabricVlanEpId                                               Gauge32,
    cfprFabricVlanEpIfRole                                           CfprFabricVnetEpIfRole,
    cfprFabricVlanEpIfType                                           CfprNetworkVnetEpIfType,
    cfprFabricVlanEpIsNative                                         TruthValue,
    cfprFabricVlanEpLocale                                           CfprFabricVnetEpLocale,
    cfprFabricVlanEpName                                             SnmpAdminString,
    cfprFabricVlanEpOperState                                        CfprFabricVlanOperState,
    cfprFabricVlanEpOverlapStateForA                                 CfprFabricVlanOverlapState,
    cfprFabricVlanEpOverlapStateForB                                 CfprFabricVlanOverlapState,
    cfprFabricVlanEpPeerDn                                           SnmpAdminString,
    cfprFabricVlanEpPolicyOwner                                      CfprFabricVnetEpPolicyOwner,
    cfprFabricVlanEpPubNwDn                                          SnmpAdminString,
    cfprFabricVlanEpPubNwId                                          Gauge32,
    cfprFabricVlanEpPubNwName                                        SnmpAdminString,
    cfprFabricVlanEpSharing                                          CfprFabricAVlanSharing,
    cfprFabricVlanEpSwitchId                                         CfprNetworkSwitchId,
    cfprFabricVlanEpTransport                                        CfprFabricAVlanTransport,
    cfprFabricVlanEpType                                             CfprFabricAVlanType
}

cfprFabricVlanEpInstanceId OBJECT-TYPE
    SYNTAX       CfprManagedObjectId
    MAX-ACCESS   not-accessible
    STATUS       current
    DESCRIPTION
        "Instance identifier of the managed object."
    ::= { cfprFabricVlanEpEntry 1 }

cfprFabricVlanEpDnData OBJECT-TYPE
    SYNTAX       CfprManagedObjectDn
    MAX-ACCESS   read-only
    STATUS       current
    DESCRIPTION
        "Cisco Firepower fabric:VlanEp:dn managed object property"
    ::= { cfprFabricVlanEpEntry 2 }

cfprFabricVlanEpRn OBJECT-TYPE
    SYNTAX       SnmpAdminString
    MAX-ACCESS   read-only
    STATUS       current
    DESCRIPTION
        "Cisco Firepower fabric:VlanEp:rn managed object property"
    ::= { cfprFabricVlanEpEntry 3 }

cfprFabricVlanEpAssocPrimaryVlanState OBJECT-TYPE
    SYNTAX       CfprFabricVlanAssocPrimaryVlanState
    MAX-ACCESS   read-only
    STATUS       current
    DESCRIPTION
        "Cisco Firepower fabric:VlanEp:assocPrimaryVlanState
        managed object property"
    ::= { cfprFabricVlanEpEntry 4 }

cfprFabricVlanEpAssocPrimaryVlanSwitchId OBJECT-TYPE
    SYNTAX       CfprFabricAVlanAssocPrimaryVlanSwitchId
    MAX-ACCESS   read-only
    STATUS       current
    DESCRIPTION
        "Cisco Firepower fabric:VlanEp:assocPrimaryVlanSwitchId
        managed object property"
    ::= { cfprFabricVlanEpEntry 5 }

cfprFabricVlanEpEpDn OBJECT-TYPE
    SYNTAX       SnmpAdminString
    MAX-ACCESS   read-only
    STATUS       current
    DESCRIPTION
        "Cisco Firepower fabric:VlanEp:epDn managed object property"
    ::= { cfprFabricVlanEpEntry 6 }

cfprFabricVlanEpId OBJECT-TYPE
    SYNTAX       Gauge32
    MAX-ACCESS   read-only
    STATUS       current
    DESCRIPTION
        "Cisco Firepower fabric:VlanEp:id managed object property"
    ::= { cfprFabricVlanEpEntry 7 }

cfprFabricVlanEpIfRole OBJECT-TYPE
    SYNTAX       CfprFabricVnetEpIfRole
    MAX-ACCESS   read-only
    STATUS       current
    DESCRIPTION
        "Cisco Firepower fabric:VlanEp:ifRole managed object property"
    ::= { cfprFabricVlanEpEntry 8 }

cfprFabricVlanEpIfType OBJECT-TYPE
    SYNTAX       CfprNetworkVnetEpIfType
    MAX-ACCESS   read-only
    STATUS       current
    DESCRIPTION
        "Cisco Firepower fabric:VlanEp:ifType managed object property"
    ::= { cfprFabricVlanEpEntry 9 }

cfprFabricVlanEpIsNative OBJECT-TYPE
    SYNTAX       TruthValue
    MAX-ACCESS   read-only
    STATUS       current
    DESCRIPTION
        "Cisco Firepower fabric:VlanEp:isNative managed object property"
    ::= { cfprFabricVlanEpEntry 10 }

cfprFabricVlanEpLocale OBJECT-TYPE
    SYNTAX       CfprFabricVnetEpLocale
    MAX-ACCESS   read-only
    STATUS       current
    DESCRIPTION
        "Cisco Firepower fabric:VlanEp:locale managed object property"
    ::= { cfprFabricVlanEpEntry 11 }

cfprFabricVlanEpName OBJECT-TYPE
    SYNTAX       SnmpAdminString
    MAX-ACCESS   read-only
    STATUS       current
    DESCRIPTION
        "Cisco Firepower fabric:VlanEp:name managed object property"
    ::= { cfprFabricVlanEpEntry 12 }

cfprFabricVlanEpOperState OBJECT-TYPE
    SYNTAX       CfprFabricVlanOperState
    MAX-ACCESS   read-only
    STATUS       current
    DESCRIPTION
        "Cisco Firepower fabric:VlanEp:operState managed object property"
    ::= { cfprFabricVlanEpEntry 13 }

cfprFabricVlanEpOverlapStateForA OBJECT-TYPE
    SYNTAX       CfprFabricVlanOverlapState
    MAX-ACCESS   read-only
    STATUS       current
    DESCRIPTION
        "Cisco Firepower fabric:VlanEp:overlapStateForA
        managed object property"
    ::= { cfprFabricVlanEpEntry 14 }

cfprFabricVlanEpOverlapStateForB OBJECT-TYPE
    SYNTAX       CfprFabricVlanOverlapState
    MAX-ACCESS   read-only
    STATUS       current
    DESCRIPTION
        "Cisco Firepower fabric:VlanEp:overlapStateForB
        managed object property"
    ::= { cfprFabricVlanEpEntry 15 }

cfprFabricVlanEpPeerDn OBJECT-TYPE
    SYNTAX       SnmpAdminString
    MAX-ACCESS   read-only
    STATUS       current
    DESCRIPTION
        "Cisco Firepower fabric:VlanEp:peerDn managed object property"
    ::= { cfprFabricVlanEpEntry 16 }

cfprFabricVlanEpPolicyOwner OBJECT-TYPE
    SYNTAX       CfprFabricVnetEpPolicyOwner
    MAX-ACCESS   read-only
    STATUS       current
    DESCRIPTION
        "Cisco Firepower fabric:VlanEp:policyOwner managed
        object property"
    ::= { cfprFabricVlanEpEntry 17 }

cfprFabricVlanEpPubNwDn OBJECT-TYPE
    SYNTAX       SnmpAdminString
    MAX-ACCESS   read-only
    STATUS       current
    DESCRIPTION
        "Cisco Firepower fabric:VlanEp:pubNwDn managed object property"
    ::= { cfprFabricVlanEpEntry 18 }

cfprFabricVlanEpPubNwId OBJECT-TYPE
    SYNTAX       Gauge32
    MAX-ACCESS   read-only
    STATUS       current
    DESCRIPTION
        "Cisco Firepower fabric:VlanEp:pubNwId managed object property"
    ::= { cfprFabricVlanEpEntry 19 }

cfprFabricVlanEpPubNwName OBJECT-TYPE
    SYNTAX       SnmpAdminString
    MAX-ACCESS   read-only
    STATUS       current
    DESCRIPTION
        "Cisco Firepower fabric:VlanEp:pubNwName managed object property"
    ::= { cfprFabricVlanEpEntry 20 }

cfprFabricVlanEpSharing OBJECT-TYPE
    SYNTAX       CfprFabricAVlanSharing
    MAX-ACCESS   read-only
    STATUS       current
    DESCRIPTION
        "Cisco Firepower fabric:VlanEp:sharing managed object property"
    ::= { cfprFabricVlanEpEntry 21 }

cfprFabricVlanEpSwitchId OBJECT-TYPE
    SYNTAX       CfprNetworkSwitchId
    MAX-ACCESS   read-only
    STATUS       current
    DESCRIPTION
        "Cisco Firepower fabric:VlanEp:switchId managed object property"
    ::= { cfprFabricVlanEpEntry 22 }

cfprFabricVlanEpTransport OBJECT-TYPE
    SYNTAX       CfprFabricAVlanTransport
    MAX-ACCESS   read-only
    STATUS       current
    DESCRIPTION
        "Cisco Firepower fabric:VlanEp:transport managed object property"
    ::= { cfprFabricVlanEpEntry 23 }

cfprFabricVlanEpType OBJECT-TYPE
    SYNTAX       CfprFabricAVlanType
    MAX-ACCESS   read-only
    STATUS       current
    DESCRIPTION
        "Cisco Firepower fabric:VlanEp:type managed object property"
    ::= { cfprFabricVlanEpEntry 24 }

cfprFabricVlanGroupReqTable OBJECT-TYPE
    SYNTAX           SEQUENCE OF CfprFabricVlanGroupReqEntry
    MAX-ACCESS       not-accessible
    STATUS           current
    DESCRIPTION
        "Cisco Firepower fabric:VlanGroupReq managed object table"
    ::= { cfprFabricObjects 115 }

cfprFabricVlanGroupReqEntry OBJECT-TYPE
    SYNTAX           CfprFabricVlanGroupReqEntry
    MAX-ACCESS       not-accessible
    STATUS           current
    DESCRIPTION
        "Entry for the cfprFabricVlanGroupReqTable table."
    INDEX { cfprFabricVlanGroupReqInstanceId }
    ::= { cfprFabricVlanGroupReqTable 1 }

CfprFabricVlanGroupReqEntry ::= SEQUENCE {
    cfprFabricVlanGroupReqInstanceId                                 CfprManagedObjectId,
    cfprFabricVlanGroupReqDn                                         CfprManagedObjectDn,
    cfprFabricVlanGroupReqRn                                         SnmpAdminString,
    cfprFabricVlanGroupReqConfigIssues                               CfprFabricReqIssues,
    cfprFabricVlanGroupReqName                                       SnmpAdminString,
    cfprFabricVlanGroupReqType                                       CfprFabricAccessType
}

cfprFabricVlanGroupReqInstanceId OBJECT-TYPE
    SYNTAX       CfprManagedObjectId
    MAX-ACCESS   not-accessible
    STATUS       current
    DESCRIPTION
        "Instance identifier of the managed object."
    ::= { cfprFabricVlanGroupReqEntry 1 }

cfprFabricVlanGroupReqDn OBJECT-TYPE
    SYNTAX       CfprManagedObjectDn
    MAX-ACCESS   read-only
    STATUS       current
    DESCRIPTION
        "Cisco Firepower fabric:VlanGroupReq:dn managed object property"
    ::= { cfprFabricVlanGroupReqEntry 2 }

cfprFabricVlanGroupReqRn OBJECT-TYPE
    SYNTAX       SnmpAdminString
    MAX-ACCESS   read-only
    STATUS       current
    DESCRIPTION
        "Cisco Firepower fabric:VlanGroupReq:rn managed object property"
    ::= { cfprFabricVlanGroupReqEntry 3 }

cfprFabricVlanGroupReqConfigIssues OBJECT-TYPE
    SYNTAX       CfprFabricReqIssues
    MAX-ACCESS   read-only
    STATUS       current
    DESCRIPTION
        "Cisco Firepower fabric:VlanGroupReq:configIssues
        managed object property"
    ::= { cfprFabricVlanGroupReqEntry 4 }

cfprFabricVlanGroupReqName OBJECT-TYPE
    SYNTAX       SnmpAdminString
    MAX-ACCESS   read-only
    STATUS       current
    DESCRIPTION
        "Cisco Firepower fabric:VlanGroupReq:name managed object property"
    ::= { cfprFabricVlanGroupReqEntry 5 }

cfprFabricVlanGroupReqType OBJECT-TYPE
    SYNTAX       CfprFabricAccessType
    MAX-ACCESS   read-only
    STATUS       current
    DESCRIPTION
        "Cisco Firepower fabric:VlanGroupReq:type managed object property"
    ::= { cfprFabricVlanGroupReqEntry 6 }

cfprFabricVlanPermitTable OBJECT-TYPE
    SYNTAX           SEQUENCE OF CfprFabricVlanPermitEntry
    MAX-ACCESS       not-accessible
    STATUS           current
    DESCRIPTION
        "Cisco Firepower fabric:VlanPermit managed object table"
    ::= { cfprFabricObjects 116 }

cfprFabricVlanPermitEntry OBJECT-TYPE
    SYNTAX           CfprFabricVlanPermitEntry
    MAX-ACCESS       not-accessible
    STATUS           current
    DESCRIPTION
        "Entry for the cfprFabricVlanPermitTable table."
    INDEX { cfprFabricVlanPermitInstanceId }
    ::= { cfprFabricVlanPermitTable 1 }

CfprFabricVlanPermitEntry ::= SEQUENCE {
    cfprFabricVlanPermitInstanceId                                   CfprManagedObjectId,
    cfprFabricVlanPermitDn                                           CfprManagedObjectDn,
    cfprFabricVlanPermitRn                                           SnmpAdminString,
    cfprFabricVlanPermitCloud                                        CfprFabricCloudType,
    cfprFabricVlanPermitName                                         SnmpAdminString,
    cfprFabricVlanPermitSwitchId                                     SnmpAdminString
}

cfprFabricVlanPermitInstanceId OBJECT-TYPE
    SYNTAX       CfprManagedObjectId
    MAX-ACCESS   not-accessible
    STATUS       current
    DESCRIPTION
        "Instance identifier of the managed object."
    ::= { cfprFabricVlanPermitEntry 1 }

cfprFabricVlanPermitDn OBJECT-TYPE
    SYNTAX       CfprManagedObjectDn
    MAX-ACCESS   read-only
    STATUS       current
    DESCRIPTION
        "Cisco Firepower fabric:VlanPermit:dn managed object property"
    ::= { cfprFabricVlanPermitEntry 2 }

cfprFabricVlanPermitRn OBJECT-TYPE
    SYNTAX       SnmpAdminString
    MAX-ACCESS   read-only
    STATUS       current
    DESCRIPTION
        "Cisco Firepower fabric:VlanPermit:rn managed object property"
    ::= { cfprFabricVlanPermitEntry 3 }

cfprFabricVlanPermitCloud OBJECT-TYPE
    SYNTAX       CfprFabricCloudType
    MAX-ACCESS   read-only
    STATUS       current
    DESCRIPTION
        "Cisco Firepower fabric:VlanPermit:cloud managed object property"
    ::= { cfprFabricVlanPermitEntry 4 }

cfprFabricVlanPermitName OBJECT-TYPE
    SYNTAX       SnmpAdminString
    MAX-ACCESS   read-only
    STATUS       current
    DESCRIPTION
        "Cisco Firepower fabric:VlanPermit:name managed object property"
    ::= { cfprFabricVlanPermitEntry 5 }

cfprFabricVlanPermitSwitchId OBJECT-TYPE
    SYNTAX       SnmpAdminString
    MAX-ACCESS   read-only
    STATUS       current
    DESCRIPTION
        "Cisco Firepower fabric:VlanPermit:switchId managed
        object property"
    ::= { cfprFabricVlanPermitEntry 6 }

cfprFabricVlanReqTable OBJECT-TYPE
    SYNTAX           SEQUENCE OF CfprFabricVlanReqEntry
    MAX-ACCESS       not-accessible
    STATUS           current
    DESCRIPTION
        "Cisco Firepower fabric:VlanReq managed object table"
    ::= { cfprFabricObjects 117 }

cfprFabricVlanReqEntry OBJECT-TYPE
    SYNTAX           CfprFabricVlanReqEntry
    MAX-ACCESS       not-accessible
    STATUS           current
    DESCRIPTION
        "Entry for the cfprFabricVlanReqTable table."
    INDEX { cfprFabricVlanReqInstanceId }
    ::= { cfprFabricVlanReqTable 1 }

CfprFabricVlanReqEntry ::= SEQUENCE {
    cfprFabricVlanReqInstanceId                                      CfprManagedObjectId,
    cfprFabricVlanReqDn                                              CfprManagedObjectDn,
    cfprFabricVlanReqRn                                              SnmpAdminString,
    cfprFabricVlanReqConfigIssues                                    CfprFabricReqIssues,
    cfprFabricVlanReqName                                            SnmpAdminString,
    cfprFabricVlanReqType                                            CfprFabricAccessType
}

cfprFabricVlanReqInstanceId OBJECT-TYPE
    SYNTAX       CfprManagedObjectId
    MAX-ACCESS   not-accessible
    STATUS       current
    DESCRIPTION
        "Instance identifier of the managed object."
    ::= { cfprFabricVlanReqEntry 1 }

cfprFabricVlanReqDn OBJECT-TYPE
    SYNTAX       CfprManagedObjectDn
    MAX-ACCESS   read-only
    STATUS       current
    DESCRIPTION
        "Cisco Firepower fabric:VlanReq:dn managed object property"
    ::= { cfprFabricVlanReqEntry 2 }

cfprFabricVlanReqRn OBJECT-TYPE
    SYNTAX       SnmpAdminString
    MAX-ACCESS   read-only
    STATUS       current
    DESCRIPTION
        "Cisco Firepower fabric:VlanReq:rn managed object property"
    ::= { cfprFabricVlanReqEntry 3 }

cfprFabricVlanReqConfigIssues OBJECT-TYPE
    SYNTAX       CfprFabricReqIssues
    MAX-ACCESS   read-only
    STATUS       current
    DESCRIPTION
        "Cisco Firepower fabric:VlanReq:configIssues managed
        object property"
    ::= { cfprFabricVlanReqEntry 4 }

cfprFabricVlanReqName OBJECT-TYPE
    SYNTAX       SnmpAdminString
    MAX-ACCESS   read-only
    STATUS       current
    DESCRIPTION
        "Cisco Firepower fabric:VlanReq:name managed object property"
    ::= { cfprFabricVlanReqEntry 5 }

cfprFabricVlanReqType OBJECT-TYPE
    SYNTAX       CfprFabricAccessType
    MAX-ACCESS   read-only
    STATUS       current
    DESCRIPTION
        "Cisco Firepower fabric:VlanReq:type managed object property"
    ::= { cfprFabricVlanReqEntry 6 }

cfprFabricVnetEpSyncEpTable OBJECT-TYPE
    SYNTAX           SEQUENCE OF CfprFabricVnetEpSyncEpEntry
    MAX-ACCESS       not-accessible
    STATUS           current
    DESCRIPTION
        "Cisco Firepower fabric:VnetEpSyncEp managed object table"
    ::= { cfprFabricObjects 118 }

cfprFabricVnetEpSyncEpEntry OBJECT-TYPE
    SYNTAX           CfprFabricVnetEpSyncEpEntry
    MAX-ACCESS       not-accessible
    STATUS           current
    DESCRIPTION
        "Entry for the cfprFabricVnetEpSyncEpTable table."
    INDEX { cfprFabricVnetEpSyncEpInstanceId }
    ::= { cfprFabricVnetEpSyncEpTable 1 }

CfprFabricVnetEpSyncEpEntry ::= SEQUENCE {
    cfprFabricVnetEpSyncEpInstanceId                                 CfprManagedObjectId,
    cfprFabricVnetEpSyncEpDn                                         CfprManagedObjectDn,
    cfprFabricVnetEpSyncEpRn                                         SnmpAdminString,
    cfprFabricVnetEpSyncEpFsmDescr                                   SnmpAdminString,
    cfprFabricVnetEpSyncEpFsmPrev                                    SnmpAdminString,
    cfprFabricVnetEpSyncEpFsmProgr                                   Gauge32,
    cfprFabricVnetEpSyncEpFsmRmtInvErrCode                           Gauge32,
    cfprFabricVnetEpSyncEpFsmRmtInvErrDescr                          SnmpAdminString,
    cfprFabricVnetEpSyncEpFsmRmtInvRslt                              CfprConditionRemoteInvRslt,
    cfprFabricVnetEpSyncEpFsmStageDescr                              SnmpAdminString,
    cfprFabricVnetEpSyncEpFsmStamp                                   DateAndTime,
    cfprFabricVnetEpSyncEpFsmStatus                                  SnmpAdminString,
    cfprFabricVnetEpSyncEpFsmTry                                     Gauge32,
    cfprFabricVnetEpSyncEpGenNumSync                                 Gauge32,
    cfprFabricVnetEpSyncEpId                                         Gauge32,
    cfprFabricVnetEpSyncEpIsChangedObjectUpdate                      TruthValue
}

cfprFabricVnetEpSyncEpInstanceId OBJECT-TYPE
    SYNTAX       CfprManagedObjectId
    MAX-ACCESS   not-accessible
    STATUS       current
    DESCRIPTION
        "Instance identifier of the managed object."
    ::= { cfprFabricVnetEpSyncEpEntry 1 }

cfprFabricVnetEpSyncEpDn OBJECT-TYPE
    SYNTAX       CfprManagedObjectDn
    MAX-ACCESS   read-only
    STATUS       current
    DESCRIPTION
        "Cisco Firepower fabric:VnetEpSyncEp:dn managed object property"
    ::= { cfprFabricVnetEpSyncEpEntry 2 }

cfprFabricVnetEpSyncEpRn OBJECT-TYPE
    SYNTAX       SnmpAdminString
    MAX-ACCESS   read-only
    STATUS       current
    DESCRIPTION
        "Cisco Firepower fabric:VnetEpSyncEp:rn managed object property"
    ::= { cfprFabricVnetEpSyncEpEntry 3 }

cfprFabricVnetEpSyncEpFsmDescr OBJECT-TYPE
    SYNTAX       SnmpAdminString
    MAX-ACCESS   read-only
    STATUS       current
    DESCRIPTION
        "Cisco Firepower fabric:VnetEpSyncEp:fsmDescr managed
        object property"
    ::= { cfprFabricVnetEpSyncEpEntry 4 }

cfprFabricVnetEpSyncEpFsmPrev OBJECT-TYPE
    SYNTAX       SnmpAdminString
    MAX-ACCESS   read-only
    STATUS       current
    DESCRIPTION
        "Cisco Firepower fabric:VnetEpSyncEp:fsmPrev managed
        object property"
    ::= { cfprFabricVnetEpSyncEpEntry 5 }

cfprFabricVnetEpSyncEpFsmProgr OBJECT-TYPE
    SYNTAX       Gauge32
    MAX-ACCESS   read-only
    STATUS       current
    DESCRIPTION
        "Cisco Firepower fabric:VnetEpSyncEp:fsmProgr managed
        object property"
    ::= { cfprFabricVnetEpSyncEpEntry 6 }

cfprFabricVnetEpSyncEpFsmRmtInvErrCode OBJECT-TYPE
    SYNTAX       Gauge32
    MAX-ACCESS   read-only
    STATUS       current
    DESCRIPTION
        "Cisco Firepower fabric:VnetEpSyncEp:fsmRmtInvErrCode
        managed object property"
    ::= { cfprFabricVnetEpSyncEpEntry 7 }

cfprFabricVnetEpSyncEpFsmRmtInvErrDescr OBJECT-TYPE
    SYNTAX       SnmpAdminString
    MAX-ACCESS   read-only
    STATUS       current
    DESCRIPTION
        "Cisco Firepower fabric:VnetEpSyncEp:fsmRmtInvErrDescr
        managed object property"
    ::= { cfprFabricVnetEpSyncEpEntry 8 }

cfprFabricVnetEpSyncEpFsmRmtInvRslt OBJECT-TYPE
    SYNTAX       CfprConditionRemoteInvRslt
    MAX-ACCESS   read-only
    STATUS       current
    DESCRIPTION
        "Cisco Firepower fabric:VnetEpSyncEp:fsmRmtInvRslt
        managed object property"
    ::= { cfprFabricVnetEpSyncEpEntry 9 }

cfprFabricVnetEpSyncEpFsmStageDescr OBJECT-TYPE
    SYNTAX       SnmpAdminString
    MAX-ACCESS   read-only
    STATUS       current
    DESCRIPTION
        "Cisco Firepower fabric:VnetEpSyncEp:fsmStageDescr
        managed object property"
    ::= { cfprFabricVnetEpSyncEpEntry 10 }

cfprFabricVnetEpSyncEpFsmStamp OBJECT-TYPE
    SYNTAX       DateAndTime
    MAX-ACCESS   read-only
    STATUS       current
    DESCRIPTION
        "Cisco Firepower fabric:VnetEpSyncEp:fsmStamp managed
        object property"
    ::= { cfprFabricVnetEpSyncEpEntry 11 }

cfprFabricVnetEpSyncEpFsmStatus OBJECT-TYPE
    SYNTAX       SnmpAdminString
    MAX-ACCESS   read-only
    STATUS       current
    DESCRIPTION
        "Cisco Firepower fabric:VnetEpSyncEp:fsmStatus
        managed object property"
    ::= { cfprFabricVnetEpSyncEpEntry 12 }

cfprFabricVnetEpSyncEpFsmTry OBJECT-TYPE
    SYNTAX       Gauge32
    MAX-ACCESS   read-only
    STATUS       current
    DESCRIPTION
        "Cisco Firepower fabric:VnetEpSyncEp:fsmTry managed
        object property"
    ::= { cfprFabricVnetEpSyncEpEntry 13 }

cfprFabricVnetEpSyncEpGenNumSync OBJECT-TYPE
    SYNTAX       Gauge32
    MAX-ACCESS   read-only
    STATUS       current
    DESCRIPTION
        "Cisco Firepower fabric:VnetEpSyncEp:genNumSync
        managed object property"
    ::= { cfprFabricVnetEpSyncEpEntry 14 }

cfprFabricVnetEpSyncEpId OBJECT-TYPE
    SYNTAX       Gauge32
    MAX-ACCESS   read-only
    STATUS       current
    DESCRIPTION
        "Cisco Firepower fabric:VnetEpSyncEp:id managed object property"
    ::= { cfprFabricVnetEpSyncEpEntry 15 }

cfprFabricVnetEpSyncEpIsChangedObjectUpdate OBJECT-TYPE
    SYNTAX       TruthValue
    MAX-ACCESS   read-only
    STATUS       current
    DESCRIPTION
        "Cisco Firepower fabric:VnetEpSyncEp:isChangedObjectUpdate
        managed object property"
    ::= { cfprFabricVnetEpSyncEpEntry 16 }

cfprFabricVnetEpSyncEpFsmTable OBJECT-TYPE
    SYNTAX           SEQUENCE OF CfprFabricVnetEpSyncEpFsmEntry
    MAX-ACCESS       not-accessible
    STATUS           current
    DESCRIPTION
        "Cisco Firepower fabric:VnetEpSyncEpFsm managed object table"
    ::= { cfprFabricObjects 119 }

cfprFabricVnetEpSyncEpFsmEntry OBJECT-TYPE
    SYNTAX           CfprFabricVnetEpSyncEpFsmEntry
    MAX-ACCESS       not-accessible
    STATUS           current
    DESCRIPTION
        "Entry for the cfprFabricVnetEpSyncEpFsmTable table."
    INDEX { cfprFabricVnetEpSyncEpFsmInstanceId }
    ::= { cfprFabricVnetEpSyncEpFsmTable 1 }

CfprFabricVnetEpSyncEpFsmEntry ::= SEQUENCE {
    cfprFabricVnetEpSyncEpFsmInstanceId                              CfprManagedObjectId,
    cfprFabricVnetEpSyncEpFsmDn                                      CfprManagedObjectDn,
    cfprFabricVnetEpSyncEpFsmRn                                      SnmpAdminString,
    cfprFabricVnetEpSyncEpFsmCompletionTime                          DateAndTime,
    cfprFabricVnetEpSyncEpFsmCurrentFsm                              CfprFabricVnetEpSyncEpFsmCurrentFsm,
    cfprFabricVnetEpSyncEpFsmDescrData                               SnmpAdminString,
    cfprFabricVnetEpSyncEpFsmFsmStatus                               CfprFsmFsmStageStatus,
    cfprFabricVnetEpSyncEpFsmProgress                                Gauge32,
    cfprFabricVnetEpSyncEpFsmRmtErrCode                              Gauge32,
    cfprFabricVnetEpSyncEpFsmRmtErrDescr                             SnmpAdminString,
    cfprFabricVnetEpSyncEpFsmRmtRslt                                 CfprConditionRemoteInvRslt
}

cfprFabricVnetEpSyncEpFsmInstanceId OBJECT-TYPE
    SYNTAX       CfprManagedObjectId
    MAX-ACCESS   not-accessible
    STATUS       current
    DESCRIPTION
        "Instance identifier of the managed object."
    ::= { cfprFabricVnetEpSyncEpFsmEntry 1 }

cfprFabricVnetEpSyncEpFsmDn OBJECT-TYPE
    SYNTAX       CfprManagedObjectDn
    MAX-ACCESS   read-only
    STATUS       current
    DESCRIPTION
        "Cisco Firepower fabric:VnetEpSyncEpFsm:dn managed
        object property"
    ::= { cfprFabricVnetEpSyncEpFsmEntry 2 }

cfprFabricVnetEpSyncEpFsmRn OBJECT-TYPE
    SYNTAX       SnmpAdminString
    MAX-ACCESS   read-only
    STATUS       current
    DESCRIPTION
        "Cisco Firepower fabric:VnetEpSyncEpFsm:rn managed
        object property"
    ::= { cfprFabricVnetEpSyncEpFsmEntry 3 }

cfprFabricVnetEpSyncEpFsmCompletionTime OBJECT-TYPE
    SYNTAX       DateAndTime
    MAX-ACCESS   read-only
    STATUS       current
    DESCRIPTION
        "Cisco Firepower fabric:VnetEpSyncEpFsm:completionTime
        managed object property"
    ::= { cfprFabricVnetEpSyncEpFsmEntry 4 }

cfprFabricVnetEpSyncEpFsmCurrentFsm OBJECT-TYPE
    SYNTAX       CfprFabricVnetEpSyncEpFsmCurrentFsm
    MAX-ACCESS   read-only
    STATUS       current
    DESCRIPTION
        "Cisco Firepower fabric:VnetEpSyncEpFsm:currentFsm
        managed object property"
    ::= { cfprFabricVnetEpSyncEpFsmEntry 5 }

cfprFabricVnetEpSyncEpFsmDescrData OBJECT-TYPE
    SYNTAX       SnmpAdminString
    MAX-ACCESS   read-only
    STATUS       current
    DESCRIPTION
        "Cisco Firepower fabric:VnetEpSyncEpFsm:descr managed
        object property"
    ::= { cfprFabricVnetEpSyncEpFsmEntry 6 }

cfprFabricVnetEpSyncEpFsmFsmStatus OBJECT-TYPE
    SYNTAX       CfprFsmFsmStageStatus
    MAX-ACCESS   read-only
    STATUS       current
    DESCRIPTION
        "Cisco Firepower fabric:VnetEpSyncEpFsm:fsmStatus
        managed object property"
    ::= { cfprFabricVnetEpSyncEpFsmEntry 7 }

cfprFabricVnetEpSyncEpFsmProgress OBJECT-TYPE
    SYNTAX       Gauge32
    MAX-ACCESS   read-only
    STATUS       current
    DESCRIPTION
        "Cisco Firepower fabric:VnetEpSyncEpFsm:progress
        managed object property"
    ::= { cfprFabricVnetEpSyncEpFsmEntry 8 }

cfprFabricVnetEpSyncEpFsmRmtErrCode OBJECT-TYPE
    SYNTAX       Gauge32
    MAX-ACCESS   read-only
    STATUS       current
    DESCRIPTION
        "Cisco Firepower fabric:VnetEpSyncEpFsm:rmtErrCode
        managed object property"
    ::= { cfprFabricVnetEpSyncEpFsmEntry 9 }

cfprFabricVnetEpSyncEpFsmRmtErrDescr OBJECT-TYPE
    SYNTAX       SnmpAdminString
    MAX-ACCESS   read-only
    STATUS       current
    DESCRIPTION
        "Cisco Firepower fabric:VnetEpSyncEpFsm:rmtErrDescr
        managed object property"
    ::= { cfprFabricVnetEpSyncEpFsmEntry 10 }

cfprFabricVnetEpSyncEpFsmRmtRslt OBJECT-TYPE
    SYNTAX       CfprConditionRemoteInvRslt
    MAX-ACCESS   read-only
    STATUS       current
    DESCRIPTION
        "Cisco Firepower fabric:VnetEpSyncEpFsm:rmtRslt
        managed object property"
    ::= { cfprFabricVnetEpSyncEpFsmEntry 11 }

cfprFabricVnetEpSyncEpFsmStageTable OBJECT-TYPE
    SYNTAX           SEQUENCE OF CfprFabricVnetEpSyncEpFsmStageEntry
    MAX-ACCESS       not-accessible
    STATUS           current
    DESCRIPTION
        "Cisco Firepower fabric:VnetEpSyncEpFsmStage managed object table"
    ::= { cfprFabricObjects 120 }

cfprFabricVnetEpSyncEpFsmStageEntry OBJECT-TYPE
    SYNTAX           CfprFabricVnetEpSyncEpFsmStageEntry
    MAX-ACCESS       not-accessible
    STATUS           current
    DESCRIPTION
        "Entry for the cfprFabricVnetEpSyncEpFsmStageTable table."
    INDEX { cfprFabricVnetEpSyncEpFsmStageInstanceId }
    ::= { cfprFabricVnetEpSyncEpFsmStageTable 1 }

CfprFabricVnetEpSyncEpFsmStageEntry ::= SEQUENCE {
    cfprFabricVnetEpSyncEpFsmStageInstanceId                         CfprManagedObjectId,
    cfprFabricVnetEpSyncEpFsmStageDn                                 CfprManagedObjectDn,
    cfprFabricVnetEpSyncEpFsmStageRn                                 SnmpAdminString,
    cfprFabricVnetEpSyncEpFsmStageDescrData                          SnmpAdminString,
    cfprFabricVnetEpSyncEpFsmStageLastUpdateTime                     DateAndTime,
    cfprFabricVnetEpSyncEpFsmStageName                               CfprFabricVnetEpSyncEpFsmStageName,
    cfprFabricVnetEpSyncEpFsmStageOrder                              Gauge32,
    cfprFabricVnetEpSyncEpFsmStageRetry                              Gauge32,
    cfprFabricVnetEpSyncEpFsmStageStageStatus                        CfprFsmFsmStageStatus
}

cfprFabricVnetEpSyncEpFsmStageInstanceId OBJECT-TYPE
    SYNTAX       CfprManagedObjectId
    MAX-ACCESS   not-accessible
    STATUS       current
    DESCRIPTION
        "Instance identifier of the managed object."
    ::= { cfprFabricVnetEpSyncEpFsmStageEntry 1 }

cfprFabricVnetEpSyncEpFsmStageDn OBJECT-TYPE
    SYNTAX       CfprManagedObjectDn
    MAX-ACCESS   read-only
    STATUS       current
    DESCRIPTION
        "Cisco Firepower fabric:VnetEpSyncEpFsmStage:dn
        managed object property"
    ::= { cfprFabricVnetEpSyncEpFsmStageEntry 2 }

cfprFabricVnetEpSyncEpFsmStageRn OBJECT-TYPE
    SYNTAX       SnmpAdminString
    MAX-ACCESS   read-only
    STATUS       current
    DESCRIPTION
        "Cisco Firepower fabric:VnetEpSyncEpFsmStage:rn
        managed object property"
    ::= { cfprFabricVnetEpSyncEpFsmStageEntry 3 }

cfprFabricVnetEpSyncEpFsmStageDescrData OBJECT-TYPE
    SYNTAX       SnmpAdminString
    MAX-ACCESS   read-only
    STATUS       current
    DESCRIPTION
        "Cisco Firepower fabric:VnetEpSyncEpFsmStage:descr
        managed object property"
    ::= { cfprFabricVnetEpSyncEpFsmStageEntry 4 }

cfprFabricVnetEpSyncEpFsmStageLastUpdateTime OBJECT-TYPE
    SYNTAX       DateAndTime
    MAX-ACCESS   read-only
    STATUS       current
    DESCRIPTION
        "Cisco Firepower fabric:VnetEpSyncEpFsmStage:lastUpdateTime
        managed object property"
    ::= { cfprFabricVnetEpSyncEpFsmStageEntry 5 }

cfprFabricVnetEpSyncEpFsmStageName OBJECT-TYPE
    SYNTAX       CfprFabricVnetEpSyncEpFsmStageName
    MAX-ACCESS   read-only
    STATUS       current
    DESCRIPTION
        "Cisco Firepower fabric:VnetEpSyncEpFsmStage:name
        managed object property"
    ::= { cfprFabricVnetEpSyncEpFsmStageEntry 6 }

cfprFabricVnetEpSyncEpFsmStageOrder OBJECT-TYPE
    SYNTAX       Gauge32
    MAX-ACCESS   read-only
    STATUS       current
    DESCRIPTION
        "Cisco Firepower fabric:VnetEpSyncEpFsmStage:order
        managed object property"
    ::= { cfprFabricVnetEpSyncEpFsmStageEntry 7 }

cfprFabricVnetEpSyncEpFsmStageRetry OBJECT-TYPE
    SYNTAX       Gauge32
    MAX-ACCESS   read-only
    STATUS       current
    DESCRIPTION
        "Cisco Firepower fabric:VnetEpSyncEpFsmStage:retry
        managed object property"
    ::= { cfprFabricVnetEpSyncEpFsmStageEntry 8 }

cfprFabricVnetEpSyncEpFsmStageStageStatus OBJECT-TYPE
    SYNTAX       CfprFsmFsmStageStatus
    MAX-ACCESS   read-only
    STATUS       current
    DESCRIPTION
        "Cisco Firepower fabric:VnetEpSyncEpFsmStage:stageStatus
        managed object property"
    ::= { cfprFabricVnetEpSyncEpFsmStageEntry 9 }

cfprFabricVnetEpSyncEpFsmTaskTable OBJECT-TYPE
    SYNTAX           SEQUENCE OF CfprFabricVnetEpSyncEpFsmTaskEntry
    MAX-ACCESS       not-accessible
    STATUS           current
    DESCRIPTION
        "Cisco Firepower fabric:VnetEpSyncEpFsmTask managed object table"
    ::= { cfprFabricObjects 121 }

cfprFabricVnetEpSyncEpFsmTaskEntry OBJECT-TYPE
    SYNTAX           CfprFabricVnetEpSyncEpFsmTaskEntry
    MAX-ACCESS       not-accessible
    STATUS           current
    DESCRIPTION
        "Entry for the cfprFabricVnetEpSyncEpFsmTaskTable table."
    INDEX { cfprFabricVnetEpSyncEpFsmTaskInstanceId }
    ::= { cfprFabricVnetEpSyncEpFsmTaskTable 1 }

CfprFabricVnetEpSyncEpFsmTaskEntry ::= SEQUENCE {
    cfprFabricVnetEpSyncEpFsmTaskInstanceId                          CfprManagedObjectId,
    cfprFabricVnetEpSyncEpFsmTaskDn                                  CfprManagedObjectDn,
    cfprFabricVnetEpSyncEpFsmTaskRn                                  SnmpAdminString,
    cfprFabricVnetEpSyncEpFsmTaskCompletion                          CfprFsmCompletion,
    cfprFabricVnetEpSyncEpFsmTaskFlags                               CfprFsmFlags,
    cfprFabricVnetEpSyncEpFsmTaskItem                                CfprFabricVnetEpSyncEpFsmTaskItem,
    cfprFabricVnetEpSyncEpFsmTaskSeqId                               Gauge32
}

cfprFabricVnetEpSyncEpFsmTaskInstanceId OBJECT-TYPE
    SYNTAX       CfprManagedObjectId
    MAX-ACCESS   not-accessible
    STATUS       current
    DESCRIPTION
        "Instance identifier of the managed object."
    ::= { cfprFabricVnetEpSyncEpFsmTaskEntry 1 }

cfprFabricVnetEpSyncEpFsmTaskDn OBJECT-TYPE
    SYNTAX       CfprManagedObjectDn
    MAX-ACCESS   read-only
    STATUS       current
    DESCRIPTION
        "Cisco Firepower fabric:VnetEpSyncEpFsmTask:dn
        managed object property"
    ::= { cfprFabricVnetEpSyncEpFsmTaskEntry 2 }

cfprFabricVnetEpSyncEpFsmTaskRn OBJECT-TYPE
    SYNTAX       SnmpAdminString
    MAX-ACCESS   read-only
    STATUS       current
    DESCRIPTION
        "Cisco Firepower fabric:VnetEpSyncEpFsmTask:rn
        managed object property"
    ::= { cfprFabricVnetEpSyncEpFsmTaskEntry 3 }

cfprFabricVnetEpSyncEpFsmTaskCompletion OBJECT-TYPE
    SYNTAX       CfprFsmCompletion
    MAX-ACCESS   read-only
    STATUS       current
    DESCRIPTION
        "Cisco Firepower fabric:VnetEpSyncEpFsmTask:completion
        managed object property"
    ::= { cfprFabricVnetEpSyncEpFsmTaskEntry 4 }

cfprFabricVnetEpSyncEpFsmTaskFlags OBJECT-TYPE
    SYNTAX       CfprFsmFlags
    MAX-ACCESS   read-only
    STATUS       current
    DESCRIPTION
        "Cisco Firepower fabric:VnetEpSyncEpFsmTask:flags
        managed object property"
    ::= { cfprFabricVnetEpSyncEpFsmTaskEntry 5 }

cfprFabricVnetEpSyncEpFsmTaskItem OBJECT-TYPE
    SYNTAX       CfprFabricVnetEpSyncEpFsmTaskItem
    MAX-ACCESS   read-only
    STATUS       current
    DESCRIPTION
        "Cisco Firepower fabric:VnetEpSyncEpFsmTask:item
        managed object property"
    ::= { cfprFabricVnetEpSyncEpFsmTaskEntry 6 }

cfprFabricVnetEpSyncEpFsmTaskSeqId OBJECT-TYPE
    SYNTAX       Gauge32
    MAX-ACCESS   read-only
    STATUS       current
    DESCRIPTION
        "Cisco Firepower fabric:VnetEpSyncEpFsmTask:seqId
        managed object property"
    ::= { cfprFabricVnetEpSyncEpFsmTaskEntry 7 }

cfprFabricVsanTable OBJECT-TYPE
    SYNTAX           SEQUENCE OF CfprFabricVsanEntry
    MAX-ACCESS       not-accessible
    STATUS           current
    DESCRIPTION
        "Cisco Firepower fabric:Vsan managed object table"
    ::= { cfprFabricObjects 122 }

cfprFabricVsanEntry OBJECT-TYPE
    SYNTAX           CfprFabricVsanEntry
    MAX-ACCESS       not-accessible
    STATUS           current
    DESCRIPTION
        "Entry for the cfprFabricVsanTable table."
    INDEX { cfprFabricVsanInstanceId }
    ::= { cfprFabricVsanTable 1 }

CfprFabricVsanEntry ::= SEQUENCE {
    cfprFabricVsanInstanceId                                         CfprManagedObjectId,
    cfprFabricVsanDn                                                 CfprManagedObjectDn,
    cfprFabricVsanRn                                                 SnmpAdminString,
    cfprFabricVsanDefaultZoning                                      CfprFabricDefaultZoningState,
    cfprFabricVsanEpDn                                               SnmpAdminString,
    cfprFabricVsanFcZoneSharingMode                                  CfprFabricFcZoneSharingMode,
    cfprFabricVsanFcoeVlan                                           Gauge32,
    cfprFabricVsanFltAggr                                            Unsigned64,
    cfprFabricVsanGlobal                                             Unsigned64,
    cfprFabricVsanId                                                 Gauge32,
    cfprFabricVsanIfRole                                             CfprFabricVnetEpIfRole,
    cfprFabricVsanIfType                                             CfprNetworkVnetEpIfType,
    cfprFabricVsanLocal                                              Unsigned64,
    cfprFabricVsanLocale                                             CfprFabricVnetEpLocale,
    cfprFabricVsanName                                               SnmpAdminString,
    cfprFabricVsanOperState                                          CfprFabricVsanOperState,
    cfprFabricVsanPeerDn                                             SnmpAdminString,
    cfprFabricVsanPolicyOwner                                        CfprFabricVnetEpPolicyOwner,
    cfprFabricVsanSwitchId                                           CfprFabricVsanSwitchId,
    cfprFabricVsanTransport                                          CfprFabricAVsanTransport,
    cfprFabricVsanType                                               CfprFabricAVsanType,
    cfprFabricVsanZoningState                                        CfprFabricZoningState
}

cfprFabricVsanInstanceId OBJECT-TYPE
    SYNTAX       CfprManagedObjectId
    MAX-ACCESS   not-accessible
    STATUS       current
    DESCRIPTION
        "Instance identifier of the managed object."
    ::= { cfprFabricVsanEntry 1 }

cfprFabricVsanDn OBJECT-TYPE
    SYNTAX       CfprManagedObjectDn
    MAX-ACCESS   read-only
    STATUS       current
    DESCRIPTION
        "Cisco Firepower fabric:Vsan:dn managed object property"
    ::= { cfprFabricVsanEntry 2 }

cfprFabricVsanRn OBJECT-TYPE
    SYNTAX       SnmpAdminString
    MAX-ACCESS   read-only
    STATUS       current
    DESCRIPTION
        "Cisco Firepower fabric:Vsan:rn managed object property"
    ::= { cfprFabricVsanEntry 3 }

cfprFabricVsanDefaultZoning OBJECT-TYPE
    SYNTAX       CfprFabricDefaultZoningState
    MAX-ACCESS   read-only
    STATUS       current
    DESCRIPTION
        "Cisco Firepower fabric:Vsan:defaultZoning managed
        object property"
    ::= { cfprFabricVsanEntry 4 }

cfprFabricVsanEpDn OBJECT-TYPE
    SYNTAX       SnmpAdminString
    MAX-ACCESS   read-only
    STATUS       current
    DESCRIPTION
        "Cisco Firepower fabric:Vsan:epDn managed object property"
    ::= { cfprFabricVsanEntry 5 }

cfprFabricVsanFcZoneSharingMode OBJECT-TYPE
    SYNTAX       CfprFabricFcZoneSharingMode
    MAX-ACCESS   read-only
    STATUS       current
    DESCRIPTION
        "Cisco Firepower fabric:Vsan:fcZoneSharingMode
        managed object property"
    ::= { cfprFabricVsanEntry 6 }

cfprFabricVsanFcoeVlan OBJECT-TYPE
    SYNTAX       Gauge32
    MAX-ACCESS   read-only
    STATUS       current
    DESCRIPTION
        "Cisco Firepower fabric:Vsan:fcoeVlan managed object property"
    ::= { cfprFabricVsanEntry 7 }

cfprFabricVsanFltAggr OBJECT-TYPE
    SYNTAX       Unsigned64
    MAX-ACCESS   read-only
    STATUS       current
    DESCRIPTION
        "Cisco Firepower fabric:Vsan:fltAggr managed object property"
    ::= { cfprFabricVsanEntry 8 }

cfprFabricVsanGlobal OBJECT-TYPE
    SYNTAX       Unsigned64
    MAX-ACCESS   read-only
    STATUS       current
    DESCRIPTION
        "Cisco Firepower fabric:Vsan:global managed object property"
    ::= { cfprFabricVsanEntry 9 }

cfprFabricVsanId OBJECT-TYPE
    SYNTAX       Gauge32
    MAX-ACCESS   read-only
    STATUS       current
    DESCRIPTION
        "Cisco Firepower fabric:Vsan:id managed object property"
    ::= { cfprFabricVsanEntry 10 }

cfprFabricVsanIfRole OBJECT-TYPE
    SYNTAX       CfprFabricVnetEpIfRole
    MAX-ACCESS   read-only
    STATUS       current
    DESCRIPTION
        "Cisco Firepower fabric:Vsan:ifRole managed object property"
    ::= { cfprFabricVsanEntry 11 }

cfprFabricVsanIfType OBJECT-TYPE
    SYNTAX       CfprNetworkVnetEpIfType
    MAX-ACCESS   read-only
    STATUS       current
    DESCRIPTION
        "Cisco Firepower fabric:Vsan:ifType managed object property"
    ::= { cfprFabricVsanEntry 12 }

cfprFabricVsanLocal OBJECT-TYPE
    SYNTAX       Unsigned64
    MAX-ACCESS   read-only
    STATUS       current
    DESCRIPTION
        "Cisco Firepower fabric:Vsan:local managed object property"
    ::= { cfprFabricVsanEntry 13 }

cfprFabricVsanLocale OBJECT-TYPE
    SYNTAX       CfprFabricVnetEpLocale
    MAX-ACCESS   read-only
    STATUS       current
    DESCRIPTION
        "Cisco Firepower fabric:Vsan:locale managed object property"
    ::= { cfprFabricVsanEntry 14 }

cfprFabricVsanName OBJECT-TYPE
    SYNTAX       SnmpAdminString
    MAX-ACCESS   read-only
    STATUS       current
    DESCRIPTION
        "Cisco Firepower fabric:Vsan:name managed object property"
    ::= { cfprFabricVsanEntry 15 }

cfprFabricVsanOperState OBJECT-TYPE
    SYNTAX       CfprFabricVsanOperState
    MAX-ACCESS   read-only
    STATUS       current
    DESCRIPTION
        "Cisco Firepower fabric:Vsan:operState managed object property"
    ::= { cfprFabricVsanEntry 16 }

cfprFabricVsanPeerDn OBJECT-TYPE
    SYNTAX       SnmpAdminString
    MAX-ACCESS   read-only
    STATUS       current
    DESCRIPTION
        "Cisco Firepower fabric:Vsan:peerDn managed object property"
    ::= { cfprFabricVsanEntry 17 }

cfprFabricVsanPolicyOwner OBJECT-TYPE
    SYNTAX       CfprFabricVnetEpPolicyOwner
    MAX-ACCESS   read-only
    STATUS       current
    DESCRIPTION
        "Cisco Firepower fabric:Vsan:policyOwner managed object property"
    ::= { cfprFabricVsanEntry 18 }

cfprFabricVsanSwitchId OBJECT-TYPE
    SYNTAX       CfprFabricVsanSwitchId
    MAX-ACCESS   read-only
    STATUS       current
    DESCRIPTION
        "Cisco Firepower fabric:Vsan:switchId managed object property"
    ::= { cfprFabricVsanEntry 19 }

cfprFabricVsanTransport OBJECT-TYPE
    SYNTAX       CfprFabricAVsanTransport
    MAX-ACCESS   read-only
    STATUS       current
    DESCRIPTION
        "Cisco Firepower fabric:Vsan:transport managed object property"
    ::= { cfprFabricVsanEntry 20 }

cfprFabricVsanType OBJECT-TYPE
    SYNTAX       CfprFabricAVsanType
    MAX-ACCESS   read-only
    STATUS       current
    DESCRIPTION
        "Cisco Firepower fabric:Vsan:type managed object property"
    ::= { cfprFabricVsanEntry 21 }

cfprFabricVsanZoningState OBJECT-TYPE
    SYNTAX       CfprFabricZoningState
    MAX-ACCESS   read-only
    STATUS       current
    DESCRIPTION
        "Cisco Firepower fabric:Vsan:zoningState managed object property"
    ::= { cfprFabricVsanEntry 22 }

cfprFabricVsanEpTable OBJECT-TYPE
    SYNTAX           SEQUENCE OF CfprFabricVsanEpEntry
    MAX-ACCESS       not-accessible
    STATUS           current
    DESCRIPTION
        "Cisco Firepower fabric:VsanEp managed object table"
    ::= { cfprFabricObjects 123 }

cfprFabricVsanEpEntry OBJECT-TYPE
    SYNTAX           CfprFabricVsanEpEntry
    MAX-ACCESS       not-accessible
    STATUS           current
    DESCRIPTION
        "Entry for the cfprFabricVsanEpTable table."
    INDEX { cfprFabricVsanEpInstanceId }
    ::= { cfprFabricVsanEpTable 1 }

CfprFabricVsanEpEntry ::= SEQUENCE {
    cfprFabricVsanEpInstanceId                                       CfprManagedObjectId,
    cfprFabricVsanEpDnData                                           CfprManagedObjectDn,
    cfprFabricVsanEpRn                                               SnmpAdminString,
    cfprFabricVsanEpEpDn                                             SnmpAdminString,
    cfprFabricVsanEpFcoeVlan                                         Gauge32,
    cfprFabricVsanEpId                                               Gauge32,
    cfprFabricVsanEpIfRole                                           CfprFabricVnetEpIfRole,
    cfprFabricVsanEpIfType                                           CfprNetworkVnetEpIfType,
    cfprFabricVsanEpLocale                                           CfprFabricVnetEpLocale,
    cfprFabricVsanEpName                                             SnmpAdminString,
    cfprFabricVsanEpOperState                                        CfprFabricVsanOperState,
    cfprFabricVsanEpPeerDn                                           SnmpAdminString,
    cfprFabricVsanEpPolicyOwner                                      CfprFabricVnetEpPolicyOwner,
    cfprFabricVsanEpSwitchId                                         CfprNetworkSwitchId,
    cfprFabricVsanEpTransport                                        CfprFabricAVsanTransport,
    cfprFabricVsanEpType                                             CfprFabricAVsanType,
    cfprFabricVsanEpZoningState                                      CfprFabricZoningState
}

cfprFabricVsanEpInstanceId OBJECT-TYPE
    SYNTAX       CfprManagedObjectId
    MAX-ACCESS   not-accessible
    STATUS       current
    DESCRIPTION
        "Instance identifier of the managed object."
    ::= { cfprFabricVsanEpEntry 1 }

cfprFabricVsanEpDnData OBJECT-TYPE
    SYNTAX       CfprManagedObjectDn
    MAX-ACCESS   read-only
    STATUS       current
    DESCRIPTION
        "Cisco Firepower fabric:VsanEp:dn managed object property"
    ::= { cfprFabricVsanEpEntry 2 }

cfprFabricVsanEpRn OBJECT-TYPE
    SYNTAX       SnmpAdminString
    MAX-ACCESS   read-only
    STATUS       current
    DESCRIPTION
        "Cisco Firepower fabric:VsanEp:rn managed object property"
    ::= { cfprFabricVsanEpEntry 3 }

cfprFabricVsanEpEpDn OBJECT-TYPE
    SYNTAX       SnmpAdminString
    MAX-ACCESS   read-only
    STATUS       current
    DESCRIPTION
        "Cisco Firepower fabric:VsanEp:epDn managed object property"
    ::= { cfprFabricVsanEpEntry 4 }

cfprFabricVsanEpFcoeVlan OBJECT-TYPE
    SYNTAX       Gauge32
    MAX-ACCESS   read-only
    STATUS       current
    DESCRIPTION
        "Cisco Firepower fabric:VsanEp:fcoeVlan managed object property"
    ::= { cfprFabricVsanEpEntry 5 }

cfprFabricVsanEpId OBJECT-TYPE
    SYNTAX       Gauge32
    MAX-ACCESS   read-only
    STATUS       current
    DESCRIPTION
        "Cisco Firepower fabric:VsanEp:id managed object property"
    ::= { cfprFabricVsanEpEntry 6 }

cfprFabricVsanEpIfRole OBJECT-TYPE
    SYNTAX       CfprFabricVnetEpIfRole
    MAX-ACCESS   read-only
    STATUS       current
    DESCRIPTION
        "Cisco Firepower fabric:VsanEp:ifRole managed object property"
    ::= { cfprFabricVsanEpEntry 7 }

cfprFabricVsanEpIfType OBJECT-TYPE
    SYNTAX       CfprNetworkVnetEpIfType
    MAX-ACCESS   read-only
    STATUS       current
    DESCRIPTION
        "Cisco Firepower fabric:VsanEp:ifType managed object property"
    ::= { cfprFabricVsanEpEntry 8 }

cfprFabricVsanEpLocale OBJECT-TYPE
    SYNTAX       CfprFabricVnetEpLocale
    MAX-ACCESS   read-only
    STATUS       current
    DESCRIPTION
        "Cisco Firepower fabric:VsanEp:locale managed object property"
    ::= { cfprFabricVsanEpEntry 9 }

cfprFabricVsanEpName OBJECT-TYPE
    SYNTAX       SnmpAdminString
    MAX-ACCESS   read-only
    STATUS       current
    DESCRIPTION
        "Cisco Firepower fabric:VsanEp:name managed object property"
    ::= { cfprFabricVsanEpEntry 10 }

cfprFabricVsanEpOperState OBJECT-TYPE
    SYNTAX       CfprFabricVsanOperState
    MAX-ACCESS   read-only
    STATUS       current
    DESCRIPTION
        "Cisco Firepower fabric:VsanEp:operState managed object property"
    ::= { cfprFabricVsanEpEntry 11 }

cfprFabricVsanEpPeerDn OBJECT-TYPE
    SYNTAX       SnmpAdminString
    MAX-ACCESS   read-only
    STATUS       current
    DESCRIPTION
        "Cisco Firepower fabric:VsanEp:peerDn managed object property"
    ::= { cfprFabricVsanEpEntry 12 }

cfprFabricVsanEpPolicyOwner OBJECT-TYPE
    SYNTAX       CfprFabricVnetEpPolicyOwner
    MAX-ACCESS   read-only
    STATUS       current
    DESCRIPTION
        "Cisco Firepower fabric:VsanEp:policyOwner managed
        object property"
    ::= { cfprFabricVsanEpEntry 13 }

cfprFabricVsanEpSwitchId OBJECT-TYPE
    SYNTAX       CfprNetworkSwitchId
    MAX-ACCESS   read-only
    STATUS       current
    DESCRIPTION
        "Cisco Firepower fabric:VsanEp:switchId managed object property"
    ::= { cfprFabricVsanEpEntry 14 }

cfprFabricVsanEpTransport OBJECT-TYPE
    SYNTAX       CfprFabricAVsanTransport
    MAX-ACCESS   read-only
    STATUS       current
    DESCRIPTION
        "Cisco Firepower fabric:VsanEp:transport managed object property"
    ::= { cfprFabricVsanEpEntry 15 }

cfprFabricVsanEpType OBJECT-TYPE
    SYNTAX       CfprFabricAVsanType
    MAX-ACCESS   read-only
    STATUS       current
    DESCRIPTION
        "Cisco Firepower fabric:VsanEp:type managed object property"
    ::= { cfprFabricVsanEpEntry 16 }

cfprFabricVsanEpZoningState OBJECT-TYPE
    SYNTAX       CfprFabricZoningState
    MAX-ACCESS   read-only
    STATUS       current
    DESCRIPTION
        "Cisco Firepower fabric:VsanEp:zoningState managed
        object property"
    ::= { cfprFabricVsanEpEntry 17 }

cfprFabricVsanMembershipTable OBJECT-TYPE
    SYNTAX           SEQUENCE OF CfprFabricVsanMembershipEntry
    MAX-ACCESS       not-accessible
    STATUS           current
    DESCRIPTION
        "Cisco Firepower fabric:VsanMembership managed object table"
    ::= { cfprFabricObjects 124 }

cfprFabricVsanMembershipEntry OBJECT-TYPE
    SYNTAX           CfprFabricVsanMembershipEntry
    MAX-ACCESS       not-accessible
    STATUS           current
    DESCRIPTION
        "Entry for the cfprFabricVsanMembershipTable table."
    INDEX { cfprFabricVsanMembershipInstanceId }
    ::= { cfprFabricVsanMembershipTable 1 }

CfprFabricVsanMembershipEntry ::= SEQUENCE {
    cfprFabricVsanMembershipInstanceId                               CfprManagedObjectId,
    cfprFabricVsanMembershipDn                                       CfprManagedObjectDn,
    cfprFabricVsanMembershipRn                                       SnmpAdminString,
    cfprFabricVsanMembershipMemberStatus                             CfprFabricMemberStatus,
    cfprFabricVsanMembershipParentAdminState                         CfprFabricAdminState,
    cfprFabricVsanMembershipStateQual                                SnmpAdminString,
    cfprFabricVsanMembershipVsanId                                   Gauge32
}

cfprFabricVsanMembershipInstanceId OBJECT-TYPE
    SYNTAX       CfprManagedObjectId
    MAX-ACCESS   not-accessible
    STATUS       current
    DESCRIPTION
        "Instance identifier of the managed object."
    ::= { cfprFabricVsanMembershipEntry 1 }

cfprFabricVsanMembershipDn OBJECT-TYPE
    SYNTAX       CfprManagedObjectDn
    MAX-ACCESS   read-only
    STATUS       current
    DESCRIPTION
        "Cisco Firepower fabric:VsanMembership:dn managed object property"
    ::= { cfprFabricVsanMembershipEntry 2 }

cfprFabricVsanMembershipRn OBJECT-TYPE
    SYNTAX       SnmpAdminString
    MAX-ACCESS   read-only
    STATUS       current
    DESCRIPTION
        "Cisco Firepower fabric:VsanMembership:rn managed object property"
    ::= { cfprFabricVsanMembershipEntry 3 }

cfprFabricVsanMembershipMemberStatus OBJECT-TYPE
    SYNTAX       CfprFabricMemberStatus
    MAX-ACCESS   read-only
    STATUS       current
    DESCRIPTION
        "Cisco Firepower fabric:VsanMembership:memberStatus
        managed object property"
    ::= { cfprFabricVsanMembershipEntry 4 }

cfprFabricVsanMembershipParentAdminState OBJECT-TYPE
    SYNTAX       CfprFabricAdminState
    MAX-ACCESS   read-only
    STATUS       current
    DESCRIPTION
        "Cisco Firepower fabric:VsanMembership:parentAdminState
        managed object property"
    ::= { cfprFabricVsanMembershipEntry 5 }

cfprFabricVsanMembershipStateQual OBJECT-TYPE
    SYNTAX       SnmpAdminString
    MAX-ACCESS   read-only
    STATUS       current
    DESCRIPTION
        "Cisco Firepower fabric:VsanMembership:stateQual
        managed object property"
    ::= { cfprFabricVsanMembershipEntry 6 }

cfprFabricVsanMembershipVsanId OBJECT-TYPE
    SYNTAX       Gauge32
    MAX-ACCESS   read-only
    STATUS       current
    DESCRIPTION
        "Cisco Firepower fabric:VsanMembership:vsanId managed
        object property"
    ::= { cfprFabricVsanMembershipEntry 7 }

cfprFabricZoneIdUniverseTable OBJECT-TYPE
    SYNTAX           SEQUENCE OF CfprFabricZoneIdUniverseEntry
    MAX-ACCESS       not-accessible
    STATUS           current
    DESCRIPTION
        "Cisco Firepower fabric:ZoneIdUniverse managed object table"
    ::= { cfprFabricObjects 125 }

cfprFabricZoneIdUniverseEntry OBJECT-TYPE
    SYNTAX           CfprFabricZoneIdUniverseEntry
    MAX-ACCESS       not-accessible
    STATUS           current
    DESCRIPTION
        "Entry for the cfprFabricZoneIdUniverseTable table."
    INDEX { cfprFabricZoneIdUniverseInstanceId }
    ::= { cfprFabricZoneIdUniverseTable 1 }

CfprFabricZoneIdUniverseEntry ::= SEQUENCE {
    cfprFabricZoneIdUniverseInstanceId                               CfprManagedObjectId,
    cfprFabricZoneIdUniverseDn                                       CfprManagedObjectDn,
    cfprFabricZoneIdUniverseRn                                       SnmpAdminString
}

cfprFabricZoneIdUniverseInstanceId OBJECT-TYPE
    SYNTAX       CfprManagedObjectId
    MAX-ACCESS   not-accessible
    STATUS       current
    DESCRIPTION
        "Instance identifier of the managed object."
    ::= { cfprFabricZoneIdUniverseEntry 1 }

cfprFabricZoneIdUniverseDn OBJECT-TYPE
    SYNTAX       CfprManagedObjectDn
    MAX-ACCESS   read-only
    STATUS       current
    DESCRIPTION
        "Cisco Firepower fabric:ZoneIdUniverse:dn managed object property"
    ::= { cfprFabricZoneIdUniverseEntry 2 }

cfprFabricZoneIdUniverseRn OBJECT-TYPE
    SYNTAX       SnmpAdminString
    MAX-ACCESS   read-only
    STATUS       current
    DESCRIPTION
        "Cisco Firepower fabric:ZoneIdUniverse:rn managed object property"
    ::= { cfprFabricZoneIdUniverseEntry 3 }

END

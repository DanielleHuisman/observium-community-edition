-- *********************************************************************
-- CISCO-FIREPOWER-FAULT-MIB.my
-- 
-- MIB representation of the Cisco Firepower
-- FAULT management information model package
-- 
-- Created March 2020 by Charles Bullis
-- 
-- Copyright (c) 2005-2020 Cisco Systems, Inc. All rights reserved.
-- 
-- *********************************************************************

CISCO-FIREPOWER-FAULT-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerMIBObjects,
    CfprManagedObjectId,
    CfprManagedObjectDn
        FROM CISCO-FIREPOWER-MIB
    CfprConditionAckAction,
    CfprConditionCause,
    CfprConditionCode,
    CfprConditionLifecycle,
    CfprConditionRule,
    CfprConditionSeverity,
    CfprConditionTag,
    CfprConditionType,
    CfprFaultBasePolicyClearAction,
    CfprFaultBasePolicySoakingSeverity,
    CfprMoMoClassId,
    CfprPolicyPolicyOwner,
    CfprTrigAdminState,
    CfprTrigTrigOperState
        FROM CISCO-FIREPOWER-TC-MIB;

cfprFaultObjects MODULE-IDENTITY
    LAST-UPDATED    "202003100000Z"
    ORGANIZATION    "Cisco Systems Inc."
    CONTACT-INFO
        "Cisco Systems
        Customer Service
        
        Postal: 170 W Tasman Drive
        San Jose, CA  95134
        USA
        
        Tel: +1 800 553-NETS
        
        E-mail: firepower-mibs@cisco.com"
    DESCRIPTION
        "MIB representation of the Cisco Firepower
        FAULT management information model package"
    ::= { ciscoFirepowerMIBObjects 1 }

cfprFaultAffectedClassTable OBJECT-TYPE
    SYNTAX           SEQUENCE OF CfprFaultAffectedClassEntry
    MAX-ACCESS       not-accessible
    STATUS           current
    DESCRIPTION
        "Cisco Firepower fault:AffectedClass managed object table"
    ::= { cfprFaultObjects 2 }

cfprFaultAffectedClassEntry OBJECT-TYPE
    SYNTAX           CfprFaultAffectedClassEntry
    MAX-ACCESS       not-accessible
    STATUS           current
    DESCRIPTION
        "Entry for the cfprFaultAffectedClassTable table."
    INDEX { cfprFaultAffectedClassInstanceId }
    ::= { cfprFaultAffectedClassTable 1 }

CfprFaultAffectedClassEntry ::= SEQUENCE {
    cfprFaultAffectedClassInstanceId                                 CfprManagedObjectId,
    cfprFaultAffectedClassDn                                         CfprManagedObjectDn,
    cfprFaultAffectedClassRn                                         SnmpAdminString,
    cfprFaultAffectedClassMoClassId                                  CfprMoMoClassId
}

cfprFaultAffectedClassInstanceId OBJECT-TYPE
    SYNTAX       CfprManagedObjectId
    MAX-ACCESS   not-accessible
    STATUS       current
    DESCRIPTION
        "Instance identifier of the managed object."
    ::= { cfprFaultAffectedClassEntry 1 }

cfprFaultAffectedClassDn OBJECT-TYPE
    SYNTAX       CfprManagedObjectDn
    MAX-ACCESS   read-only
    STATUS       current
    DESCRIPTION
        "Cisco Firepower fault:AffectedClass:dn managed object property"
    ::= { cfprFaultAffectedClassEntry 2 }

cfprFaultAffectedClassRn OBJECT-TYPE
    SYNTAX       SnmpAdminString
    MAX-ACCESS   read-only
    STATUS       current
    DESCRIPTION
        "Cisco Firepower fault:AffectedClass:rn managed object property"
    ::= { cfprFaultAffectedClassEntry 3 }

cfprFaultAffectedClassMoClassId OBJECT-TYPE
    SYNTAX       CfprMoMoClassId
    MAX-ACCESS   read-only
    STATUS       current
    DESCRIPTION
        "Cisco Firepower fault:AffectedClass:moClassId
        managed object property"
    ::= { cfprFaultAffectedClassEntry 4 }

cfprFaultHolderTable OBJECT-TYPE
    SYNTAX           SEQUENCE OF CfprFaultHolderEntry
    MAX-ACCESS       not-accessible
    STATUS           current
    DESCRIPTION
        "Cisco Firepower fault:Holder managed object table"
    ::= { cfprFaultObjects 3 }

cfprFaultHolderEntry OBJECT-TYPE
    SYNTAX           CfprFaultHolderEntry
    MAX-ACCESS       not-accessible
    STATUS           current
    DESCRIPTION
        "Entry for the cfprFaultHolderTable table."
    INDEX { cfprFaultHolderInstanceId }
    ::= { cfprFaultHolderTable 1 }

CfprFaultHolderEntry ::= SEQUENCE {
    cfprFaultHolderInstanceId                                        CfprManagedObjectId,
    cfprFaultHolderDn                                                CfprManagedObjectDn,
    cfprFaultHolderRn                                                SnmpAdminString,
    cfprFaultHolderName                                              SnmpAdminString,
    cfprFaultHolderTotalFaults                                       Unsigned64
}

cfprFaultHolderInstanceId OBJECT-TYPE
    SYNTAX       CfprManagedObjectId
    MAX-ACCESS   not-accessible
    STATUS       current
    DESCRIPTION
        "Instance identifier of the managed object."
    ::= { cfprFaultHolderEntry 1 }

cfprFaultHolderDn OBJECT-TYPE
    SYNTAX       CfprManagedObjectDn
    MAX-ACCESS   read-only
    STATUS       current
    DESCRIPTION
        "Cisco Firepower fault:Holder:dn managed object property"
    ::= { cfprFaultHolderEntry 2 }

cfprFaultHolderRn OBJECT-TYPE
    SYNTAX       SnmpAdminString
    MAX-ACCESS   read-only
    STATUS       current
    DESCRIPTION
        "Cisco Firepower fault:Holder:rn managed object property"
    ::= { cfprFaultHolderEntry 3 }

cfprFaultHolderName OBJECT-TYPE
    SYNTAX       SnmpAdminString
    MAX-ACCESS   read-only
    STATUS       current
    DESCRIPTION
        "Cisco Firepower fault:Holder:name managed object property"
    ::= { cfprFaultHolderEntry 4 }

cfprFaultHolderTotalFaults OBJECT-TYPE
    SYNTAX       Unsigned64
    MAX-ACCESS   read-only
    STATUS       current
    DESCRIPTION
        "Cisco Firepower fault:Holder:totalFaults managed object property"
    ::= { cfprFaultHolderEntry 5 }

cfprFaultInstTable OBJECT-TYPE
    SYNTAX           SEQUENCE OF CfprFaultInstEntry
    MAX-ACCESS       not-accessible
    STATUS           current
    DESCRIPTION
        "Cisco Firepower fault:Inst managed object table"
    ::= { cfprFaultObjects 1 }

cfprFaultInstEntry OBJECT-TYPE
    SYNTAX           CfprFaultInstEntry
    MAX-ACCESS       not-accessible
    STATUS           current
    DESCRIPTION
        "Entry for the cfprFaultInstTable table."
    INDEX { cfprFaultInstInstanceId }
    ::= { cfprFaultInstTable 1 }

CfprFaultInstEntry ::= SEQUENCE {
    cfprFaultInstInstanceId                                          CfprManagedObjectId,
    cfprFaultInstDn                                                  CfprManagedObjectDn,
    cfprFaultInstRn                                                  SnmpAdminString,
    cfprFaultInstAffectedObjectId                                    RowPointer,
    cfprFaultInstAffectedObjectDn                                    CfprManagedObjectDn,
    cfprFaultInstAck                                                 TruthValue,
    cfprFaultInstCause                                               CfprConditionCause,
    cfprFaultInstChangeSet                                           SnmpAdminString,
    cfprFaultInstCode                                                CfprConditionCode,
    cfprFaultInstCreated                                             DateAndTime,
    cfprFaultInstDescr                                               SnmpAdminString,
    cfprFaultInstHighestSeverity                                     CfprConditionSeverity,
    cfprFaultInstId                                                  Unsigned64,
    cfprFaultInstLastTransition                                      DateAndTime,
    cfprFaultInstLc                                                  CfprConditionLifecycle,
    cfprFaultInstOccur                                               Gauge32,
    cfprFaultInstOrigSeverity                                        CfprConditionSeverity,
    cfprFaultInstPrevSeverity                                        CfprConditionSeverity,
    cfprFaultInstRule                                                CfprConditionRule,
    cfprFaultInstSeverity                                            CfprConditionSeverity,
    cfprFaultInstTags                                                CfprConditionTag,
    cfprFaultInstType                                                CfprConditionType
}

cfprFaultInstInstanceId OBJECT-TYPE
    SYNTAX       CfprManagedObjectId
    MAX-ACCESS   not-accessible
    STATUS       current
    DESCRIPTION
        "Instance identifier of the managed object."
    ::= { cfprFaultInstEntry 1 }

cfprFaultInstDn OBJECT-TYPE
    SYNTAX       CfprManagedObjectDn
    MAX-ACCESS   read-only
    STATUS       current
    DESCRIPTION
        "Cisco Firepower fault:Inst:dn managed object property"
    ::= { cfprFaultInstEntry 2 }

cfprFaultInstRn OBJECT-TYPE
    SYNTAX       SnmpAdminString
    MAX-ACCESS   read-only
    STATUS       current
    DESCRIPTION
        "Cisco Firepower fault:Inst:rn managed object property"
    ::= { cfprFaultInstEntry 3 }

cfprFaultInstAffectedObjectId OBJECT-TYPE
    SYNTAX       RowPointer
    MAX-ACCESS   read-only
    STATUS       current
    DESCRIPTION
        "Cisco Firepower fault:Inst:affectedObjectId managed
        object property"
    ::= { cfprFaultInstEntry 4 }

cfprFaultInstAffectedObjectDn OBJECT-TYPE
    SYNTAX       CfprManagedObjectDn
    MAX-ACCESS   read-only
    STATUS       current
    DESCRIPTION
        "Cisco Firepower fault:Inst:affectedObjectDn managed
        object property"
    ::= { cfprFaultInstEntry 5 }

cfprFaultInstAck OBJECT-TYPE
    SYNTAX       TruthValue
    MAX-ACCESS   read-only
    STATUS       current
    DESCRIPTION
        "Cisco Firepower fault:Inst:ack managed object property"
    ::= { cfprFaultInstEntry 6 }

cfprFaultInstCause OBJECT-TYPE
    SYNTAX       CfprConditionCause
    MAX-ACCESS   read-only
    STATUS       current
    DESCRIPTION
        "Cisco Firepower fault:Inst:cause managed object property"
    ::= { cfprFaultInstEntry 7 }

cfprFaultInstChangeSet OBJECT-TYPE
    SYNTAX       SnmpAdminString
    MAX-ACCESS   read-only
    STATUS       current
    DESCRIPTION
        "Cisco Firepower fault:Inst:changeSet managed object property"
    ::= { cfprFaultInstEntry 8 }

cfprFaultInstCode OBJECT-TYPE
    SYNTAX       CfprConditionCode
    MAX-ACCESS   read-only
    STATUS       current
    DESCRIPTION
        "Cisco Firepower fault:Inst:code managed object property"
    ::= { cfprFaultInstEntry 9 }

cfprFaultInstCreated OBJECT-TYPE
    SYNTAX       DateAndTime
    MAX-ACCESS   read-only
    STATUS       current
    DESCRIPTION
        "Cisco Firepower fault:Inst:created managed object property"
    ::= { cfprFaultInstEntry 10 }

cfprFaultInstDescr OBJECT-TYPE
    SYNTAX       SnmpAdminString
    MAX-ACCESS   read-only
    STATUS       current
    DESCRIPTION
        "Cisco Firepower fault:Inst:descr managed object property"
    ::= { cfprFaultInstEntry 11 }

cfprFaultInstHighestSeverity OBJECT-TYPE
    SYNTAX       CfprConditionSeverity
    MAX-ACCESS   read-only
    STATUS       current
    DESCRIPTION
        "Cisco Firepower fault:Inst:highestSeverity managed
        object property"
    ::= { cfprFaultInstEntry 12 }

cfprFaultInstId OBJECT-TYPE
    SYNTAX       Unsigned64
    MAX-ACCESS   read-only
    STATUS       current
    DESCRIPTION
        "Cisco Firepower fault:Inst:id managed object property"
    ::= { cfprFaultInstEntry 13 }

cfprFaultInstLastTransition OBJECT-TYPE
    SYNTAX       DateAndTime
    MAX-ACCESS   read-only
    STATUS       current
    DESCRIPTION
        "Cisco Firepower fault:Inst:lastTransition managed
        object property"
    ::= { cfprFaultInstEntry 14 }

cfprFaultInstLc OBJECT-TYPE
    SYNTAX       CfprConditionLifecycle
    MAX-ACCESS   read-only
    STATUS       current
    DESCRIPTION
        "Cisco Firepower fault:Inst:lc managed object property"
    ::= { cfprFaultInstEntry 15 }

cfprFaultInstOccur OBJECT-TYPE
    SYNTAX       Gauge32
    MAX-ACCESS   read-only
    STATUS       current
    DESCRIPTION
        "Cisco Firepower fault:Inst:occur managed object property"
    ::= { cfprFaultInstEntry 16 }

cfprFaultInstOrigSeverity OBJECT-TYPE
    SYNTAX       CfprConditionSeverity
    MAX-ACCESS   read-only
    STATUS       current
    DESCRIPTION
        "Cisco Firepower fault:Inst:origSeverity managed object property"
    ::= { cfprFaultInstEntry 17 }

cfprFaultInstPrevSeverity OBJECT-TYPE
    SYNTAX       CfprConditionSeverity
    MAX-ACCESS   read-only
    STATUS       current
    DESCRIPTION
        "Cisco Firepower fault:Inst:prevSeverity managed object property"
    ::= { cfprFaultInstEntry 18 }

cfprFaultInstRule OBJECT-TYPE
    SYNTAX       CfprConditionRule
    MAX-ACCESS   read-only
    STATUS       current
    DESCRIPTION
        "Cisco Firepower fault:Inst:rule managed object property"
    ::= { cfprFaultInstEntry 19 }

cfprFaultInstSeverity OBJECT-TYPE
    SYNTAX       CfprConditionSeverity
    MAX-ACCESS   read-only
    STATUS       current
    DESCRIPTION
        "Cisco Firepower fault:Inst:severity managed object property"
    ::= { cfprFaultInstEntry 20 }

cfprFaultInstTags OBJECT-TYPE
    SYNTAX       CfprConditionTag
    MAX-ACCESS   read-only
    STATUS       current
    DESCRIPTION
        "Cisco Firepower fault:Inst:tags managed object property"
    ::= { cfprFaultInstEntry 21 }

cfprFaultInstType OBJECT-TYPE
    SYNTAX       CfprConditionType
    MAX-ACCESS   read-only
    STATUS       current
    DESCRIPTION
        "Cisco Firepower fault:Inst:type managed object property"
    ::= { cfprFaultInstEntry 22 }

cfprFaultLocalTypedHolderTable OBJECT-TYPE
    SYNTAX           SEQUENCE OF CfprFaultLocalTypedHolderEntry
    MAX-ACCESS       not-accessible
    STATUS           current
    DESCRIPTION
        "Cisco Firepower fault:LocalTypedHolder managed object table"
    ::= { cfprFaultObjects 4 }

cfprFaultLocalTypedHolderEntry OBJECT-TYPE
    SYNTAX           CfprFaultLocalTypedHolderEntry
    MAX-ACCESS       not-accessible
    STATUS           current
    DESCRIPTION
        "Entry for the cfprFaultLocalTypedHolderTable table."
    INDEX { cfprFaultLocalTypedHolderInstanceId }
    ::= { cfprFaultLocalTypedHolderTable 1 }

CfprFaultLocalTypedHolderEntry ::= SEQUENCE {
    cfprFaultLocalTypedHolderInstanceId                              CfprManagedObjectId,
    cfprFaultLocalTypedHolderDn                                      CfprManagedObjectDn,
    cfprFaultLocalTypedHolderRn                                      SnmpAdminString,
    cfprFaultLocalTypedHolderName                                    SnmpAdminString,
    cfprFaultLocalTypedHolderTotalFaults                             Unsigned64,
    cfprFaultLocalTypedHolderType                                    CfprConditionType
}

cfprFaultLocalTypedHolderInstanceId OBJECT-TYPE
    SYNTAX       CfprManagedObjectId
    MAX-ACCESS   not-accessible
    STATUS       current
    DESCRIPTION
        "Instance identifier of the managed object."
    ::= { cfprFaultLocalTypedHolderEntry 1 }

cfprFaultLocalTypedHolderDn OBJECT-TYPE
    SYNTAX       CfprManagedObjectDn
    MAX-ACCESS   read-only
    STATUS       current
    DESCRIPTION
        "Cisco Firepower fault:LocalTypedHolder:dn managed
        object property"
    ::= { cfprFaultLocalTypedHolderEntry 2 }

cfprFaultLocalTypedHolderRn OBJECT-TYPE
    SYNTAX       SnmpAdminString
    MAX-ACCESS   read-only
    STATUS       current
    DESCRIPTION
        "Cisco Firepower fault:LocalTypedHolder:rn managed
        object property"
    ::= { cfprFaultLocalTypedHolderEntry 3 }

cfprFaultLocalTypedHolderName OBJECT-TYPE
    SYNTAX       SnmpAdminString
    MAX-ACCESS   read-only
    STATUS       current
    DESCRIPTION
        "Cisco Firepower fault:LocalTypedHolder:name managed
        object property"
    ::= { cfprFaultLocalTypedHolderEntry 4 }

cfprFaultLocalTypedHolderTotalFaults OBJECT-TYPE
    SYNTAX       Unsigned64
    MAX-ACCESS   read-only
    STATUS       current
    DESCRIPTION
        "Cisco Firepower fault:LocalTypedHolder:totalFaults
        managed object property"
    ::= { cfprFaultLocalTypedHolderEntry 5 }

cfprFaultLocalTypedHolderType OBJECT-TYPE
    SYNTAX       CfprConditionType
    MAX-ACCESS   read-only
    STATUS       current
    DESCRIPTION
        "Cisco Firepower fault:LocalTypedHolder:type managed
        object property"
    ::= { cfprFaultLocalTypedHolderEntry 6 }

cfprFaultPolicyTable OBJECT-TYPE
    SYNTAX           SEQUENCE OF CfprFaultPolicyEntry
    MAX-ACCESS       not-accessible
    STATUS           current
    DESCRIPTION
        "Cisco Firepower fault:Policy managed object table"
    ::= { cfprFaultObjects 5 }

cfprFaultPolicyEntry OBJECT-TYPE
    SYNTAX           CfprFaultPolicyEntry
    MAX-ACCESS       not-accessible
    STATUS           current
    DESCRIPTION
        "Entry for the cfprFaultPolicyTable table."
    INDEX { cfprFaultPolicyInstanceId }
    ::= { cfprFaultPolicyTable 1 }

CfprFaultPolicyEntry ::= SEQUENCE {
    cfprFaultPolicyInstanceId                                        CfprManagedObjectId,
    cfprFaultPolicyDn                                                CfprManagedObjectDn,
    cfprFaultPolicyRn                                                SnmpAdminString,
    cfprFaultPolicyAckAction                                         CfprConditionAckAction,
    cfprFaultPolicyClearAction                                       CfprFaultBasePolicyClearAction,
    cfprFaultPolicyClearInterval                                     TimeIntervalSec,
    cfprFaultPolicyDescr                                             SnmpAdminString,
    cfprFaultPolicyFlapInterval                                      Unsigned64,
    cfprFaultPolicyIntId                                             SnmpAdminString,
    cfprFaultPolicyName                                              SnmpAdminString,
    cfprFaultPolicyPolicyLevel                                       Gauge32,
    cfprFaultPolicyPolicyOwner                                       CfprPolicyPolicyOwner,
    cfprFaultPolicyRetentionInterval                                 TimeIntervalSec,
    cfprFaultPolicySizeLimit                                         Gauge32,
    cfprFaultPolicySoakInterval                                      TimeIntervalSec,
    cfprFaultPolicySoakingSeverity                                   CfprFaultBasePolicySoakingSeverity
}

cfprFaultPolicyInstanceId OBJECT-TYPE
    SYNTAX       CfprManagedObjectId
    MAX-ACCESS   not-accessible
    STATUS       current
    DESCRIPTION
        "Instance identifier of the managed object."
    ::= { cfprFaultPolicyEntry 1 }

cfprFaultPolicyDn OBJECT-TYPE
    SYNTAX       CfprManagedObjectDn
    MAX-ACCESS   read-only
    STATUS       current
    DESCRIPTION
        "Cisco Firepower fault:Policy:dn managed object property"
    ::= { cfprFaultPolicyEntry 2 }

cfprFaultPolicyRn OBJECT-TYPE
    SYNTAX       SnmpAdminString
    MAX-ACCESS   read-only
    STATUS       current
    DESCRIPTION
        "Cisco Firepower fault:Policy:rn managed object property"
    ::= { cfprFaultPolicyEntry 3 }

cfprFaultPolicyAckAction OBJECT-TYPE
    SYNTAX       CfprConditionAckAction
    MAX-ACCESS   read-only
    STATUS       current
    DESCRIPTION
        "Cisco Firepower fault:Policy:ackAction managed object property"
    ::= { cfprFaultPolicyEntry 4 }

cfprFaultPolicyClearAction OBJECT-TYPE
    SYNTAX       CfprFaultBasePolicyClearAction
    MAX-ACCESS   read-only
    STATUS       current
    DESCRIPTION
        "Cisco Firepower fault:Policy:clearAction managed object property"
    ::= { cfprFaultPolicyEntry 5 }

cfprFaultPolicyClearInterval OBJECT-TYPE
    SYNTAX       TimeIntervalSec
    MAX-ACCESS   read-only
    STATUS       current
    DESCRIPTION
        "Cisco Firepower fault:Policy:clearInterval managed
        object property"
    ::= { cfprFaultPolicyEntry 6 }

cfprFaultPolicyDescr OBJECT-TYPE
    SYNTAX       SnmpAdminString
    MAX-ACCESS   read-only
    STATUS       current
    DESCRIPTION
        "Cisco Firepower fault:Policy:descr managed object property"
    ::= { cfprFaultPolicyEntry 7 }

cfprFaultPolicyFlapInterval OBJECT-TYPE
    SYNTAX       Unsigned64
    MAX-ACCESS   read-only
    STATUS       current
    DESCRIPTION
        "Cisco Firepower fault:Policy:flapInterval managed
        object property"
    ::= { cfprFaultPolicyEntry 8 }

cfprFaultPolicyIntId OBJECT-TYPE
    SYNTAX       SnmpAdminString
    MAX-ACCESS   read-only
    STATUS       current
    DESCRIPTION
        "Cisco Firepower fault:Policy:intId managed object property"
    ::= { cfprFaultPolicyEntry 9 }

cfprFaultPolicyName OBJECT-TYPE
    SYNTAX       SnmpAdminString
    MAX-ACCESS   read-only
    STATUS       current
    DESCRIPTION
        "Cisco Firepower fault:Policy:name managed object property"
    ::= { cfprFaultPolicyEntry 10 }

cfprFaultPolicyPolicyLevel OBJECT-TYPE
    SYNTAX       Gauge32
    MAX-ACCESS   read-only
    STATUS       current
    DESCRIPTION
        "Cisco Firepower fault:Policy:policyLevel managed object property"
    ::= { cfprFaultPolicyEntry 11 }

cfprFaultPolicyPolicyOwner OBJECT-TYPE
    SYNTAX       CfprPolicyPolicyOwner
    MAX-ACCESS   read-only
    STATUS       current
    DESCRIPTION
        "Cisco Firepower fault:Policy:policyOwner managed object property"
    ::= { cfprFaultPolicyEntry 12 }

cfprFaultPolicyRetentionInterval OBJECT-TYPE
    SYNTAX       TimeIntervalSec
    MAX-ACCESS   read-only
    STATUS       current
    DESCRIPTION
        "Cisco Firepower fault:Policy:retentionInterval
        managed object property"
    ::= { cfprFaultPolicyEntry 13 }

cfprFaultPolicySizeLimit OBJECT-TYPE
    SYNTAX       Gauge32
    MAX-ACCESS   read-only
    STATUS       current
    DESCRIPTION
        "Cisco Firepower fault:Policy:sizeLimit managed object property"
    ::= { cfprFaultPolicyEntry 14 }

cfprFaultPolicySoakInterval OBJECT-TYPE
    SYNTAX       TimeIntervalSec
    MAX-ACCESS   read-only
    STATUS       current
    DESCRIPTION
        "Cisco Firepower fault:Policy:soakInterval managed
        object property"
    ::= { cfprFaultPolicyEntry 15 }

cfprFaultPolicySoakingSeverity OBJECT-TYPE
    SYNTAX       CfprFaultBasePolicySoakingSeverity
    MAX-ACCESS   read-only
    STATUS       current
    DESCRIPTION
        "Cisco Firepower fault:Policy:soakingSeverity managed
        object property"
    ::= { cfprFaultPolicyEntry 16 }

cfprFaultSuppressPolicyTable OBJECT-TYPE
    SYNTAX           SEQUENCE OF CfprFaultSuppressPolicyEntry
    MAX-ACCESS       not-accessible
    STATUS           current
    DESCRIPTION
        "Cisco Firepower fault:SuppressPolicy managed object table"
    ::= { cfprFaultObjects 6 }

cfprFaultSuppressPolicyEntry OBJECT-TYPE
    SYNTAX           CfprFaultSuppressPolicyEntry
    MAX-ACCESS       not-accessible
    STATUS           current
    DESCRIPTION
        "Entry for the cfprFaultSuppressPolicyTable table."
    INDEX { cfprFaultSuppressPolicyInstanceId }
    ::= { cfprFaultSuppressPolicyTable 1 }

CfprFaultSuppressPolicyEntry ::= SEQUENCE {
    cfprFaultSuppressPolicyInstanceId                                CfprManagedObjectId,
    cfprFaultSuppressPolicyDn                                        CfprManagedObjectDn,
    cfprFaultSuppressPolicyRn                                        SnmpAdminString,
    cfprFaultSuppressPolicyDescr                                     SnmpAdminString,
    cfprFaultSuppressPolicyIntId                                     SnmpAdminString,
    cfprFaultSuppressPolicyName                                      SnmpAdminString,
    cfprFaultSuppressPolicyPolicyLevel                               Gauge32,
    cfprFaultSuppressPolicyPolicyOwner                               CfprPolicyPolicyOwner
}

cfprFaultSuppressPolicyInstanceId OBJECT-TYPE
    SYNTAX       CfprManagedObjectId
    MAX-ACCESS   not-accessible
    STATUS       current
    DESCRIPTION
        "Instance identifier of the managed object."
    ::= { cfprFaultSuppressPolicyEntry 1 }

cfprFaultSuppressPolicyDn OBJECT-TYPE
    SYNTAX       CfprManagedObjectDn
    MAX-ACCESS   read-only
    STATUS       current
    DESCRIPTION
        "Cisco Firepower fault:SuppressPolicy:dn managed object property"
    ::= { cfprFaultSuppressPolicyEntry 2 }

cfprFaultSuppressPolicyRn OBJECT-TYPE
    SYNTAX       SnmpAdminString
    MAX-ACCESS   read-only
    STATUS       current
    DESCRIPTION
        "Cisco Firepower fault:SuppressPolicy:rn managed object property"
    ::= { cfprFaultSuppressPolicyEntry 3 }

cfprFaultSuppressPolicyDescr OBJECT-TYPE
    SYNTAX       SnmpAdminString
    MAX-ACCESS   read-only
    STATUS       current
    DESCRIPTION
        "Cisco Firepower fault:SuppressPolicy:descr managed
        object property"
    ::= { cfprFaultSuppressPolicyEntry 4 }

cfprFaultSuppressPolicyIntId OBJECT-TYPE
    SYNTAX       SnmpAdminString
    MAX-ACCESS   read-only
    STATUS       current
    DESCRIPTION
        "Cisco Firepower fault:SuppressPolicy:intId managed
        object property"
    ::= { cfprFaultSuppressPolicyEntry 5 }

cfprFaultSuppressPolicyName OBJECT-TYPE
    SYNTAX       SnmpAdminString
    MAX-ACCESS   read-only
    STATUS       current
    DESCRIPTION
        "Cisco Firepower fault:SuppressPolicy:name managed
        object property"
    ::= { cfprFaultSuppressPolicyEntry 6 }

cfprFaultSuppressPolicyPolicyLevel OBJECT-TYPE
    SYNTAX       Gauge32
    MAX-ACCESS   read-only
    STATUS       current
    DESCRIPTION
        "Cisco Firepower fault:SuppressPolicy:policyLevel
        managed object property"
    ::= { cfprFaultSuppressPolicyEntry 7 }

cfprFaultSuppressPolicyPolicyOwner OBJECT-TYPE
    SYNTAX       CfprPolicyPolicyOwner
    MAX-ACCESS   read-only
    STATUS       current
    DESCRIPTION
        "Cisco Firepower fault:SuppressPolicy:policyOwner
        managed object property"
    ::= { cfprFaultSuppressPolicyEntry 8 }

cfprFaultSuppressPolicyItemTable OBJECT-TYPE
    SYNTAX           SEQUENCE OF CfprFaultSuppressPolicyItemEntry
    MAX-ACCESS       not-accessible
    STATUS           current
    DESCRIPTION
        "Cisco Firepower fault:SuppressPolicyItem managed object table"
    ::= { cfprFaultObjects 7 }

cfprFaultSuppressPolicyItemEntry OBJECT-TYPE
    SYNTAX           CfprFaultSuppressPolicyItemEntry
    MAX-ACCESS       not-accessible
    STATUS           current
    DESCRIPTION
        "Entry for the cfprFaultSuppressPolicyItemTable table."
    INDEX { cfprFaultSuppressPolicyItemInstanceId }
    ::= { cfprFaultSuppressPolicyItemTable 1 }

CfprFaultSuppressPolicyItemEntry ::= SEQUENCE {
    cfprFaultSuppressPolicyItemInstanceId                            CfprManagedObjectId,
    cfprFaultSuppressPolicyItemDn                                    CfprManagedObjectDn,
    cfprFaultSuppressPolicyItemRn                                    SnmpAdminString,
    cfprFaultSuppressPolicyItemCause                                 CfprConditionCause,
    cfprFaultSuppressPolicyItemDescr                                 SnmpAdminString,
    cfprFaultSuppressPolicyItemType                                  CfprConditionType
}

cfprFaultSuppressPolicyItemInstanceId OBJECT-TYPE
    SYNTAX       CfprManagedObjectId
    MAX-ACCESS   not-accessible
    STATUS       current
    DESCRIPTION
        "Instance identifier of the managed object."
    ::= { cfprFaultSuppressPolicyItemEntry 1 }

cfprFaultSuppressPolicyItemDn OBJECT-TYPE
    SYNTAX       CfprManagedObjectDn
    MAX-ACCESS   read-only
    STATUS       current
    DESCRIPTION
        "Cisco Firepower fault:SuppressPolicyItem:dn managed
        object property"
    ::= { cfprFaultSuppressPolicyItemEntry 2 }

cfprFaultSuppressPolicyItemRn OBJECT-TYPE
    SYNTAX       SnmpAdminString
    MAX-ACCESS   read-only
    STATUS       current
    DESCRIPTION
        "Cisco Firepower fault:SuppressPolicyItem:rn managed
        object property"
    ::= { cfprFaultSuppressPolicyItemEntry 3 }

cfprFaultSuppressPolicyItemCause OBJECT-TYPE
    SYNTAX       CfprConditionCause
    MAX-ACCESS   read-only
    STATUS       current
    DESCRIPTION
        "Cisco Firepower fault:SuppressPolicyItem:cause
        managed object property"
    ::= { cfprFaultSuppressPolicyItemEntry 4 }

cfprFaultSuppressPolicyItemDescr OBJECT-TYPE
    SYNTAX       SnmpAdminString
    MAX-ACCESS   read-only
    STATUS       current
    DESCRIPTION
        "Cisco Firepower fault:SuppressPolicyItem:descr
        managed object property"
    ::= { cfprFaultSuppressPolicyItemEntry 5 }

cfprFaultSuppressPolicyItemType OBJECT-TYPE
    SYNTAX       CfprConditionType
    MAX-ACCESS   read-only
    STATUS       current
    DESCRIPTION
        "Cisco Firepower fault:SuppressPolicyItem:type
        managed object property"
    ::= { cfprFaultSuppressPolicyItemEntry 6 }

cfprFaultSuppressTaskTable OBJECT-TYPE
    SYNTAX           SEQUENCE OF CfprFaultSuppressTaskEntry
    MAX-ACCESS       not-accessible
    STATUS           current
    DESCRIPTION
        "Cisco Firepower fault:SuppressTask managed object table"
    ::= { cfprFaultObjects 8 }

cfprFaultSuppressTaskEntry OBJECT-TYPE
    SYNTAX           CfprFaultSuppressTaskEntry
    MAX-ACCESS       not-accessible
    STATUS           current
    DESCRIPTION
        "Entry for the cfprFaultSuppressTaskTable table."
    INDEX { cfprFaultSuppressTaskInstanceId }
    ::= { cfprFaultSuppressTaskTable 1 }

CfprFaultSuppressTaskEntry ::= SEQUENCE {
    cfprFaultSuppressTaskInstanceId                                  CfprManagedObjectId,
    cfprFaultSuppressTaskDn                                          CfprManagedObjectDn,
    cfprFaultSuppressTaskRn                                          SnmpAdminString,
    cfprFaultSuppressTaskAdminState                                  CfprTrigAdminState,
    cfprFaultSuppressTaskAutoDelete                                  TruthValue,
    cfprFaultSuppressTaskDescr                                       SnmpAdminString,
    cfprFaultSuppressTaskIgnoreCap                                   TruthValue,
    cfprFaultSuppressTaskIntId                                       SnmpAdminString,
    cfprFaultSuppressTaskName                                        SnmpAdminString,
    cfprFaultSuppressTaskOperScheduler                               SnmpAdminString,
    cfprFaultSuppressTaskOperState                                   CfprTrigTrigOperState,
    cfprFaultSuppressTaskOperSuppressPolicyName                      SnmpAdminString,
    cfprFaultSuppressTaskPolicyLevel                                 Gauge32,
    cfprFaultSuppressTaskPolicyOwner                                 CfprPolicyPolicyOwner,
    cfprFaultSuppressTaskScheduler                                   SnmpAdminString,
    cfprFaultSuppressTaskSuppressPolicyName                          SnmpAdminString
}

cfprFaultSuppressTaskInstanceId OBJECT-TYPE
    SYNTAX       CfprManagedObjectId
    MAX-ACCESS   not-accessible
    STATUS       current
    DESCRIPTION
        "Instance identifier of the managed object."
    ::= { cfprFaultSuppressTaskEntry 1 }

cfprFaultSuppressTaskDn OBJECT-TYPE
    SYNTAX       CfprManagedObjectDn
    MAX-ACCESS   read-only
    STATUS       current
    DESCRIPTION
        "Cisco Firepower fault:SuppressTask:dn managed object property"
    ::= { cfprFaultSuppressTaskEntry 2 }

cfprFaultSuppressTaskRn OBJECT-TYPE
    SYNTAX       SnmpAdminString
    MAX-ACCESS   read-only
    STATUS       current
    DESCRIPTION
        "Cisco Firepower fault:SuppressTask:rn managed object property"
    ::= { cfprFaultSuppressTaskEntry 3 }

cfprFaultSuppressTaskAdminState OBJECT-TYPE
    SYNTAX       CfprTrigAdminState
    MAX-ACCESS   read-only
    STATUS       current
    DESCRIPTION
        "Cisco Firepower fault:SuppressTask:adminState
        managed object property"
    ::= { cfprFaultSuppressTaskEntry 4 }

cfprFaultSuppressTaskAutoDelete OBJECT-TYPE
    SYNTAX       TruthValue
    MAX-ACCESS   read-only
    STATUS       current
    DESCRIPTION
        "Cisco Firepower fault:SuppressTask:autoDelete
        managed object property"
    ::= { cfprFaultSuppressTaskEntry 5 }

cfprFaultSuppressTaskDescr OBJECT-TYPE
    SYNTAX       SnmpAdminString
    MAX-ACCESS   read-only
    STATUS       current
    DESCRIPTION
        "Cisco Firepower fault:SuppressTask:descr managed object property"
    ::= { cfprFaultSuppressTaskEntry 6 }

cfprFaultSuppressTaskIgnoreCap OBJECT-TYPE
    SYNTAX       TruthValue
    MAX-ACCESS   read-only
    STATUS       current
    DESCRIPTION
        "Cisco Firepower fault:SuppressTask:ignoreCap managed
        object property"
    ::= { cfprFaultSuppressTaskEntry 7 }

cfprFaultSuppressTaskIntId OBJECT-TYPE
    SYNTAX       SnmpAdminString
    MAX-ACCESS   read-only
    STATUS       current
    DESCRIPTION
        "Cisco Firepower fault:SuppressTask:intId managed object property"
    ::= { cfprFaultSuppressTaskEntry 8 }

cfprFaultSuppressTaskName OBJECT-TYPE
    SYNTAX       SnmpAdminString
    MAX-ACCESS   read-only
    STATUS       current
    DESCRIPTION
        "Cisco Firepower fault:SuppressTask:name managed object property"
    ::= { cfprFaultSuppressTaskEntry 9 }

cfprFaultSuppressTaskOperScheduler OBJECT-TYPE
    SYNTAX       SnmpAdminString
    MAX-ACCESS   read-only
    STATUS       current
    DESCRIPTION
        "Cisco Firepower fault:SuppressTask:operScheduler
        managed object property"
    ::= { cfprFaultSuppressTaskEntry 10 }

cfprFaultSuppressTaskOperState OBJECT-TYPE
    SYNTAX       CfprTrigTrigOperState
    MAX-ACCESS   read-only
    STATUS       current
    DESCRIPTION
        "Cisco Firepower fault:SuppressTask:operState managed
        object property"
    ::= { cfprFaultSuppressTaskEntry 11 }

cfprFaultSuppressTaskOperSuppressPolicyName OBJECT-TYPE
    SYNTAX       SnmpAdminString
    MAX-ACCESS   read-only
    STATUS       current
    DESCRIPTION
        "Cisco Firepower fault:SuppressTask:operSuppressPolicyName
        managed object property"
    ::= { cfprFaultSuppressTaskEntry 12 }

cfprFaultSuppressTaskPolicyLevel OBJECT-TYPE
    SYNTAX       Gauge32
    MAX-ACCESS   read-only
    STATUS       current
    DESCRIPTION
        "Cisco Firepower fault:SuppressTask:policyLevel
        managed object property"
    ::= { cfprFaultSuppressTaskEntry 13 }

cfprFaultSuppressTaskPolicyOwner OBJECT-TYPE
    SYNTAX       CfprPolicyPolicyOwner
    MAX-ACCESS   read-only
    STATUS       current
    DESCRIPTION
        "Cisco Firepower fault:SuppressTask:policyOwner
        managed object property"
    ::= { cfprFaultSuppressTaskEntry 14 }

cfprFaultSuppressTaskScheduler OBJECT-TYPE
    SYNTAX       SnmpAdminString
    MAX-ACCESS   read-only
    STATUS       current
    DESCRIPTION
        "Cisco Firepower fault:SuppressTask:scheduler managed
        object property"
    ::= { cfprFaultSuppressTaskEntry 15 }

cfprFaultSuppressTaskSuppressPolicyName OBJECT-TYPE
    SYNTAX       SnmpAdminString
    MAX-ACCESS   read-only
    STATUS       current
    DESCRIPTION
        "Cisco Firepower fault:SuppressTask:suppressPolicyName
        managed object property"
    ::= { cfprFaultSuppressTaskEntry 16 }

END

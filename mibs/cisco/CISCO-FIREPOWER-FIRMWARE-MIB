-- *********************************************************************
-- CISCO-FIREPOWER-FIRMWARE-MIB.my
-- 
-- MIB representation of the Cisco Firepower
-- FIRMWARE management information model package
-- 
-- Created March 2020 by Charles Bullis
-- 
-- Copyright (c) 2005-2020 Cisco Systems, Inc. All rights reserved.
-- 
-- *********************************************************************

CISCO-FIREPOWER-FIRMWARE-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerMIBObjects,
    CfprManagedObjectId,
    CfprManagedObjectDn
        FROM CISCO-FIREPOWER-MIB
    CfprConditionRemoteInvRslt,
    CfprExtpolConnProtocol,
    CfprFirmwareAdminState,
    CfprFirmwareAutoSyncConfigIssue,
    CfprFirmwareAutoSyncState,
    CfprFirmwareBootUnitImage,
    CfprFirmwareBootUnitMode,
    CfprFirmwareCatalogPackConfigState,
    CfprFirmwareCompleteness,
    CfprFirmwareComponentType,
    CfprFirmwareDependencyRelationship,
    CfprFirmwareDependencyScope,
    CfprFirmwareDependencySensitivity,
    CfprFirmwareDeployment,
    CfprFirmwareDistributableFsmCurrentFsm,
    CfprFirmwareDistributableFsmStageName,
    CfprFirmwareDistributableFsmTaskItem,
    CfprFirmwareDistributableType,
    CfprFirmwareDownloadActivity,
    CfprFirmwareDownloaderFsmCurrentFsm,
    CfprFirmwareDownloaderFsmStageName,
    CfprFirmwareDownloaderFsmTaskItem,
    CfprFirmwareEquipmentType,
    CfprFirmwareFirmwareState,
    CfprFirmwareFwState,
    CfprFirmwareFwUpgradeState,
    CfprFirmwareHostPackConfigQualifier,
    CfprFirmwareImageDeleted,
    CfprFirmwareImageError,
    CfprFirmwareImageFsmCurrentFsm,
    CfprFirmwareImageFsmStageName,
    CfprFirmwareImageFsmTaskItem,
    CfprFirmwareImagePresence,
    CfprFirmwareImageState,
    CfprFirmwareImageValidationStateType,
    CfprFirmwareImageValidationType,
    CfprFirmwareImpactType,
    CfprFirmwareInstallState,
    CfprFirmwareItemType,
    CfprFirmwarePackItemPresence,
    CfprFirmwarePackMode,
    CfprFirmwarePlatformPackFsmCurrentFsm,
    CfprFirmwarePlatformPackFsmStageName,
    CfprFirmwarePlatformPackFsmTaskFlags,
    CfprFirmwarePlatformPackFsmTaskItem,
    CfprFirmwarePlatformType,
    CfprFirmwareRunningDeployment,
    CfprFirmwareSupFirmwareFsmCurrentFsm,
    CfprFirmwareSupFirmwareFsmStageName,
    CfprFirmwareSupFirmwareFsmTaskFlags,
    CfprFirmwareSupFirmwareFsmTaskItem,
    CfprFirmwareSupportedModeType,
    CfprFirmwareSystemFsmCurrentFsm,
    CfprFirmwareSystemFsmStageName,
    CfprFirmwareSystemFsmTaskFlags,
    CfprFirmwareSystemFsmTaskItem,
    CfprFirmwareTransferState,
    CfprFirmwareTransport,
    CfprFirmwareTriggerState,
    CfprFirmwareType,
    CfprFirmwareUpdatableDeployment,
    CfprFirmwareUpgradeCategory,
    CfprFirmwareUpgradeSeverity,
    CfprFirmwareUpgradeStatus,
    CfprFirmwareValidationStatusFsmCurrentFsm,
    CfprFirmwareValidationStatusFsmStageName,
    CfprFirmwareValidationStatusFsmTaskFlags,
    CfprFirmwareValidationStatusFsmTaskItem,
    CfprFirmwareVerifyPackStatus,
    CfprFsmCompletion,
    CfprFsmFlags,
    CfprFsmFsmStageStatus,
    CfprPolicyPolicyOwner,
    CfprTrigAckChangeDetails,
    CfprTrigAckChanges,
    CfprTrigAckDisr,
    CfprTrigAckOperState,
    CfprTrigAckPrevOperState,
    CfprTrigAdminState,
    CfprTrigTrigOperState
        FROM CISCO-FIREPOWER-TC-MIB;

cfprFirmwareObjects MODULE-IDENTITY
    LAST-UPDATED    "202003100000Z"
    ORGANIZATION    "Cisco Systems Inc."
    CONTACT-INFO
        "Cisco Systems
        Customer Service
        
        Postal: 170 W Tasman Drive
        San Jose, CA  95134
        USA
        
        Tel: +1 800 553-NETS
        
        E-mail: firepower-mibs@cisco.com"
    DESCRIPTION
        "MIB representation of the Cisco Firepower
        FIRMWARE management information model package"
    ::= { ciscoFirepowerMIBObjects 30 }

cfprFirmwareAckTable OBJECT-TYPE
    SYNTAX           SEQUENCE OF CfprFirmwareAckEntry
    MAX-ACCESS       not-accessible
    STATUS           current
    DESCRIPTION
        "Cisco Firepower firmware:Ack managed object table"
    ::= { cfprFirmwareObjects 1 }

cfprFirmwareAckEntry OBJECT-TYPE
    SYNTAX           CfprFirmwareAckEntry
    MAX-ACCESS       not-accessible
    STATUS           current
    DESCRIPTION
        "Entry for the cfprFirmwareAckTable table."
    INDEX { cfprFirmwareAckInstanceId }
    ::= { cfprFirmwareAckTable 1 }

CfprFirmwareAckEntry ::= SEQUENCE {
    cfprFirmwareAckInstanceId                                        CfprManagedObjectId,
    cfprFirmwareAckDn                                                CfprManagedObjectDn,
    cfprFirmwareAckRn                                                SnmpAdminString,
    cfprFirmwareAckAcked                                             DateAndTime,
    cfprFirmwareAckAckedBy                                           SnmpAdminString,
    cfprFirmwareAckAdminState                                        CfprTrigAdminState,
    cfprFirmwareAckAutoDelete                                        TruthValue,
    cfprFirmwareAckChangeBy                                          SnmpAdminString,
    cfprFirmwareAckChangeDetails                                     CfprTrigAckChangeDetails,
    cfprFirmwareAckChanges                                           CfprTrigAckChanges,
    cfprFirmwareAckDescr                                             SnmpAdminString,
    cfprFirmwareAckDisr                                              CfprTrigAckDisr,
    cfprFirmwareAckIgnoreCap                                         TruthValue,
    cfprFirmwareAckIntId                                             SnmpAdminString,
    cfprFirmwareAckModified                                          DateAndTime,
    cfprFirmwareAckName                                              SnmpAdminString,
    cfprFirmwareAckOperScheduler                                     SnmpAdminString,
    cfprFirmwareAckOperState                                         CfprTrigAckOperState,
    cfprFirmwareAckPolicyLevel                                       Gauge32,
    cfprFirmwareAckPolicyOwner                                       CfprPolicyPolicyOwner,
    cfprFirmwareAckPrevOperState                                     CfprTrigAckPrevOperState,
    cfprFirmwareAckScheduler                                         SnmpAdminString
}

cfprFirmwareAckInstanceId OBJECT-TYPE
    SYNTAX       CfprManagedObjectId
    MAX-ACCESS   not-accessible
    STATUS       current
    DESCRIPTION
        "Instance identifier of the managed object."
    ::= { cfprFirmwareAckEntry 1 }

cfprFirmwareAckDn OBJECT-TYPE
    SYNTAX       CfprManagedObjectDn
    MAX-ACCESS   read-only
    STATUS       current
    DESCRIPTION
        "Cisco Firepower firmware:Ack:dn managed object property"
    ::= { cfprFirmwareAckEntry 2 }

cfprFirmwareAckRn OBJECT-TYPE
    SYNTAX       SnmpAdminString
    MAX-ACCESS   read-only
    STATUS       current
    DESCRIPTION
        "Cisco Firepower firmware:Ack:rn managed object property"
    ::= { cfprFirmwareAckEntry 3 }

cfprFirmwareAckAcked OBJECT-TYPE
    SYNTAX       DateAndTime
    MAX-ACCESS   read-only
    STATUS       current
    DESCRIPTION
        "Cisco Firepower firmware:Ack:acked managed object property"
    ::= { cfprFirmwareAckEntry 4 }

cfprFirmwareAckAckedBy OBJECT-TYPE
    SYNTAX       SnmpAdminString
    MAX-ACCESS   read-only
    STATUS       current
    DESCRIPTION
        "Cisco Firepower firmware:Ack:ackedBy managed object property"
    ::= { cfprFirmwareAckEntry 5 }

cfprFirmwareAckAdminState OBJECT-TYPE
    SYNTAX       CfprTrigAdminState
    MAX-ACCESS   read-only
    STATUS       current
    DESCRIPTION
        "Cisco Firepower firmware:Ack:adminState managed object property"
    ::= { cfprFirmwareAckEntry 6 }

cfprFirmwareAckAutoDelete OBJECT-TYPE
    SYNTAX       TruthValue
    MAX-ACCESS   read-only
    STATUS       current
    DESCRIPTION
        "Cisco Firepower firmware:Ack:autoDelete managed object property"
    ::= { cfprFirmwareAckEntry 7 }

cfprFirmwareAckChangeBy OBJECT-TYPE
    SYNTAX       SnmpAdminString
    MAX-ACCESS   read-only
    STATUS       current
    DESCRIPTION
        "Cisco Firepower firmware:Ack:changeBy managed object property"
    ::= { cfprFirmwareAckEntry 8 }

cfprFirmwareAckChangeDetails OBJECT-TYPE
    SYNTAX       CfprTrigAckChangeDetails
    MAX-ACCESS   read-only
    STATUS       current
    DESCRIPTION
        "Cisco Firepower firmware:Ack:changeDetails managed
        object property"
    ::= { cfprFirmwareAckEntry 9 }

cfprFirmwareAckChanges OBJECT-TYPE
    SYNTAX       CfprTrigAckChanges
    MAX-ACCESS   read-only
    STATUS       current
    DESCRIPTION
        "Cisco Firepower firmware:Ack:changes managed object property"
    ::= { cfprFirmwareAckEntry 10 }

cfprFirmwareAckDescr OBJECT-TYPE
    SYNTAX       SnmpAdminString
    MAX-ACCESS   read-only
    STATUS       current
    DESCRIPTION
        "Cisco Firepower firmware:Ack:descr managed object property"
    ::= { cfprFirmwareAckEntry 11 }

cfprFirmwareAckDisr OBJECT-TYPE
    SYNTAX       CfprTrigAckDisr
    MAX-ACCESS   read-only
    STATUS       current
    DESCRIPTION
        "Cisco Firepower firmware:Ack:disr managed object property"
    ::= { cfprFirmwareAckEntry 12 }

cfprFirmwareAckIgnoreCap OBJECT-TYPE
    SYNTAX       TruthValue
    MAX-ACCESS   read-only
    STATUS       current
    DESCRIPTION
        "Cisco Firepower firmware:Ack:ignoreCap managed object property"
    ::= { cfprFirmwareAckEntry 13 }

cfprFirmwareAckIntId OBJECT-TYPE
    SYNTAX       SnmpAdminString
    MAX-ACCESS   read-only
    STATUS       current
    DESCRIPTION
        "Cisco Firepower firmware:Ack:intId managed object property"
    ::= { cfprFirmwareAckEntry 14 }

cfprFirmwareAckModified OBJECT-TYPE
    SYNTAX       DateAndTime
    MAX-ACCESS   read-only
    STATUS       current
    DESCRIPTION
        "Cisco Firepower firmware:Ack:modified managed object property"
    ::= { cfprFirmwareAckEntry 15 }

cfprFirmwareAckName OBJECT-TYPE
    SYNTAX       SnmpAdminString
    MAX-ACCESS   read-only
    STATUS       current
    DESCRIPTION
        "Cisco Firepower firmware:Ack:name managed object property"
    ::= { cfprFirmwareAckEntry 16 }

cfprFirmwareAckOperScheduler OBJECT-TYPE
    SYNTAX       SnmpAdminString
    MAX-ACCESS   read-only
    STATUS       current
    DESCRIPTION
        "Cisco Firepower firmware:Ack:operScheduler managed
        object property"
    ::= { cfprFirmwareAckEntry 17 }

cfprFirmwareAckOperState OBJECT-TYPE
    SYNTAX       CfprTrigAckOperState
    MAX-ACCESS   read-only
    STATUS       current
    DESCRIPTION
        "Cisco Firepower firmware:Ack:operState managed object property"
    ::= { cfprFirmwareAckEntry 18 }

cfprFirmwareAckPolicyLevel OBJECT-TYPE
    SYNTAX       Gauge32
    MAX-ACCESS   read-only
    STATUS       current
    DESCRIPTION
        "Cisco Firepower firmware:Ack:policyLevel managed object property"
    ::= { cfprFirmwareAckEntry 19 }

cfprFirmwareAckPolicyOwner OBJECT-TYPE
    SYNTAX       CfprPolicyPolicyOwner
    MAX-ACCESS   read-only
    STATUS       current
    DESCRIPTION
        "Cisco Firepower firmware:Ack:policyOwner managed object property"
    ::= { cfprFirmwareAckEntry 20 }

cfprFirmwareAckPrevOperState OBJECT-TYPE
    SYNTAX       CfprTrigAckPrevOperState
    MAX-ACCESS   read-only
    STATUS       current
    DESCRIPTION
        "Cisco Firepower firmware:Ack:prevOperState managed
        object property"
    ::= { cfprFirmwareAckEntry 21 }

cfprFirmwareAckScheduler OBJECT-TYPE
    SYNTAX       SnmpAdminString
    MAX-ACCESS   read-only
    STATUS       current
    DESCRIPTION
        "Cisco Firepower firmware:Ack:scheduler managed object property"
    ::= { cfprFirmwareAckEntry 22 }

cfprFirmwareAutoSyncPolicyTable OBJECT-TYPE
    SYNTAX           SEQUENCE OF CfprFirmwareAutoSyncPolicyEntry
    MAX-ACCESS       not-accessible
    STATUS           current
    DESCRIPTION
        "Cisco Firepower firmware:AutoSyncPolicy managed object table"
    ::= { cfprFirmwareObjects 2 }

cfprFirmwareAutoSyncPolicyEntry OBJECT-TYPE
    SYNTAX           CfprFirmwareAutoSyncPolicyEntry
    MAX-ACCESS       not-accessible
    STATUS           current
    DESCRIPTION
        "Entry for the cfprFirmwareAutoSyncPolicyTable table."
    INDEX { cfprFirmwareAutoSyncPolicyInstanceId }
    ::= { cfprFirmwareAutoSyncPolicyTable 1 }

CfprFirmwareAutoSyncPolicyEntry ::= SEQUENCE {
    cfprFirmwareAutoSyncPolicyInstanceId                             CfprManagedObjectId,
    cfprFirmwareAutoSyncPolicyDn                                     CfprManagedObjectDn,
    cfprFirmwareAutoSyncPolicyRn                                     SnmpAdminString,
    cfprFirmwareAutoSyncPolicyConfigIssue                            CfprFirmwareAutoSyncConfigIssue,
    cfprFirmwareAutoSyncPolicyDescr                                  SnmpAdminString,
    cfprFirmwareAutoSyncPolicyIntId                                  SnmpAdminString,
    cfprFirmwareAutoSyncPolicyName                                   SnmpAdminString,
    cfprFirmwareAutoSyncPolicyPolicyLevel                            Gauge32,
    cfprFirmwareAutoSyncPolicyPolicyOwner                            CfprPolicyPolicyOwner,
    cfprFirmwareAutoSyncPolicySyncState                              CfprFirmwareAutoSyncState
}

cfprFirmwareAutoSyncPolicyInstanceId OBJECT-TYPE
    SYNTAX       CfprManagedObjectId
    MAX-ACCESS   not-accessible
    STATUS       current
    DESCRIPTION
        "Instance identifier of the managed object."
    ::= { cfprFirmwareAutoSyncPolicyEntry 1 }

cfprFirmwareAutoSyncPolicyDn OBJECT-TYPE
    SYNTAX       CfprManagedObjectDn
    MAX-ACCESS   read-only
    STATUS       current
    DESCRIPTION
        "Cisco Firepower firmware:AutoSyncPolicy:dn managed
        object property"
    ::= { cfprFirmwareAutoSyncPolicyEntry 2 }

cfprFirmwareAutoSyncPolicyRn OBJECT-TYPE
    SYNTAX       SnmpAdminString
    MAX-ACCESS   read-only
    STATUS       current
    DESCRIPTION
        "Cisco Firepower firmware:AutoSyncPolicy:rn managed
        object property"
    ::= { cfprFirmwareAutoSyncPolicyEntry 3 }

cfprFirmwareAutoSyncPolicyConfigIssue OBJECT-TYPE
    SYNTAX       CfprFirmwareAutoSyncConfigIssue
    MAX-ACCESS   read-only
    STATUS       current
    DESCRIPTION
        "Cisco Firepower firmware:AutoSyncPolicy:configIssue
        managed object property"
    ::= { cfprFirmwareAutoSyncPolicyEntry 4 }

cfprFirmwareAutoSyncPolicyDescr OBJECT-TYPE
    SYNTAX       SnmpAdminString
    MAX-ACCESS   read-only
    STATUS       current
    DESCRIPTION
        "Cisco Firepower firmware:AutoSyncPolicy:descr
        managed object property"
    ::= { cfprFirmwareAutoSyncPolicyEntry 5 }

cfprFirmwareAutoSyncPolicyIntId OBJECT-TYPE
    SYNTAX       SnmpAdminString
    MAX-ACCESS   read-only
    STATUS       current
    DESCRIPTION
        "Cisco Firepower firmware:AutoSyncPolicy:intId
        managed object property"
    ::= { cfprFirmwareAutoSyncPolicyEntry 6 }

cfprFirmwareAutoSyncPolicyName OBJECT-TYPE
    SYNTAX       SnmpAdminString
    MAX-ACCESS   read-only
    STATUS       current
    DESCRIPTION
        "Cisco Firepower firmware:AutoSyncPolicy:name managed
        object property"
    ::= { cfprFirmwareAutoSyncPolicyEntry 7 }

cfprFirmwareAutoSyncPolicyPolicyLevel OBJECT-TYPE
    SYNTAX       Gauge32
    MAX-ACCESS   read-only
    STATUS       current
    DESCRIPTION
        "Cisco Firepower firmware:AutoSyncPolicy:policyLevel
        managed object property"
    ::= { cfprFirmwareAutoSyncPolicyEntry 8 }

cfprFirmwareAutoSyncPolicyPolicyOwner OBJECT-TYPE
    SYNTAX       CfprPolicyPolicyOwner
    MAX-ACCESS   read-only
    STATUS       current
    DESCRIPTION
        "Cisco Firepower firmware:AutoSyncPolicy:policyOwner
        managed object property"
    ::= { cfprFirmwareAutoSyncPolicyEntry 9 }

cfprFirmwareAutoSyncPolicySyncState OBJECT-TYPE
    SYNTAX       CfprFirmwareAutoSyncState
    MAX-ACCESS   read-only
    STATUS       current
    DESCRIPTION
        "Cisco Firepower firmware:AutoSyncPolicy:syncState
        managed object property"
    ::= { cfprFirmwareAutoSyncPolicyEntry 10 }

cfprFirmwareBladeTable OBJECT-TYPE
    SYNTAX           SEQUENCE OF CfprFirmwareBladeEntry
    MAX-ACCESS       not-accessible
    STATUS           current
    DESCRIPTION
        "Cisco Firepower firmware:Blade managed object table"
    ::= { cfprFirmwareObjects 3 }

cfprFirmwareBladeEntry OBJECT-TYPE
    SYNTAX           CfprFirmwareBladeEntry
    MAX-ACCESS       not-accessible
    STATUS           current
    DESCRIPTION
        "Entry for the cfprFirmwareBladeTable table."
    INDEX { cfprFirmwareBladeInstanceId }
    ::= { cfprFirmwareBladeTable 1 }

CfprFirmwareBladeEntry ::= SEQUENCE {
    cfprFirmwareBladeInstanceId                                      CfprManagedObjectId,
    cfprFirmwareBladeDn                                              CfprManagedObjectDn,
    cfprFirmwareBladeRn                                              SnmpAdminString,
    cfprFirmwareBladeOperVersion                                     SnmpAdminString
}

cfprFirmwareBladeInstanceId OBJECT-TYPE
    SYNTAX       CfprManagedObjectId
    MAX-ACCESS   not-accessible
    STATUS       current
    DESCRIPTION
        "Instance identifier of the managed object."
    ::= { cfprFirmwareBladeEntry 1 }

cfprFirmwareBladeDn OBJECT-TYPE
    SYNTAX       CfprManagedObjectDn
    MAX-ACCESS   read-only
    STATUS       current
    DESCRIPTION
        "Cisco Firepower firmware:Blade:dn managed object property"
    ::= { cfprFirmwareBladeEntry 2 }

cfprFirmwareBladeRn OBJECT-TYPE
    SYNTAX       SnmpAdminString
    MAX-ACCESS   read-only
    STATUS       current
    DESCRIPTION
        "Cisco Firepower firmware:Blade:rn managed object property"
    ::= { cfprFirmwareBladeEntry 3 }

cfprFirmwareBladeOperVersion OBJECT-TYPE
    SYNTAX       SnmpAdminString
    MAX-ACCESS   read-only
    STATUS       current
    DESCRIPTION
        "Cisco Firepower firmware:Blade:operVersion managed
        object property"
    ::= { cfprFirmwareBladeEntry 4 }

cfprFirmwareBootDefinitionTable OBJECT-TYPE
    SYNTAX           SEQUENCE OF CfprFirmwareBootDefinitionEntry
    MAX-ACCESS       not-accessible
    STATUS           current
    DESCRIPTION
        "Cisco Firepower firmware:BootDefinition managed object table"
    ::= { cfprFirmwareObjects 4 }

cfprFirmwareBootDefinitionEntry OBJECT-TYPE
    SYNTAX           CfprFirmwareBootDefinitionEntry
    MAX-ACCESS       not-accessible
    STATUS           current
    DESCRIPTION
        "Entry for the cfprFirmwareBootDefinitionTable table."
    INDEX { cfprFirmwareBootDefinitionInstanceId }
    ::= { cfprFirmwareBootDefinitionTable 1 }

CfprFirmwareBootDefinitionEntry ::= SEQUENCE {
    cfprFirmwareBootDefinitionInstanceId                             CfprManagedObjectId,
    cfprFirmwareBootDefinitionDn                                     CfprManagedObjectDn,
    cfprFirmwareBootDefinitionRn                                     SnmpAdminString,
    cfprFirmwareBootDefinitionType                                   CfprFirmwareType
}

cfprFirmwareBootDefinitionInstanceId OBJECT-TYPE
    SYNTAX       CfprManagedObjectId
    MAX-ACCESS   not-accessible
    STATUS       current
    DESCRIPTION
        "Instance identifier of the managed object."
    ::= { cfprFirmwareBootDefinitionEntry 1 }

cfprFirmwareBootDefinitionDn OBJECT-TYPE
    SYNTAX       CfprManagedObjectDn
    MAX-ACCESS   read-only
    STATUS       current
    DESCRIPTION
        "Cisco Firepower firmware:BootDefinition:dn managed
        object property"
    ::= { cfprFirmwareBootDefinitionEntry 2 }

cfprFirmwareBootDefinitionRn OBJECT-TYPE
    SYNTAX       SnmpAdminString
    MAX-ACCESS   read-only
    STATUS       current
    DESCRIPTION
        "Cisco Firepower firmware:BootDefinition:rn managed
        object property"
    ::= { cfprFirmwareBootDefinitionEntry 3 }

cfprFirmwareBootDefinitionType OBJECT-TYPE
    SYNTAX       CfprFirmwareType
    MAX-ACCESS   read-only
    STATUS       current
    DESCRIPTION
        "Cisco Firepower firmware:BootDefinition:type managed
        object property"
    ::= { cfprFirmwareBootDefinitionEntry 4 }

cfprFirmwareBootUnitTable OBJECT-TYPE
    SYNTAX           SEQUENCE OF CfprFirmwareBootUnitEntry
    MAX-ACCESS       not-accessible
    STATUS           current
    DESCRIPTION
        "Cisco Firepower firmware:BootUnit managed object table"
    ::= { cfprFirmwareObjects 5 }

cfprFirmwareBootUnitEntry OBJECT-TYPE
    SYNTAX           CfprFirmwareBootUnitEntry
    MAX-ACCESS       not-accessible
    STATUS           current
    DESCRIPTION
        "Entry for the cfprFirmwareBootUnitTable table."
    INDEX { cfprFirmwareBootUnitInstanceId }
    ::= { cfprFirmwareBootUnitTable 1 }

CfprFirmwareBootUnitEntry ::= SEQUENCE {
    cfprFirmwareBootUnitInstanceId                                   CfprManagedObjectId,
    cfprFirmwareBootUnitDn                                           CfprManagedObjectDn,
    cfprFirmwareBootUnitRn                                           SnmpAdminString,
    cfprFirmwareBootUnitAdminState                                   CfprFirmwareTriggerState,
    cfprFirmwareBootUnitIgnoreCompCheck                              TruthValue,
    cfprFirmwareBootUnitImage                                        CfprFirmwareBootUnitImage,
    cfprFirmwareBootUnitInvTag                                       SnmpAdminString,
    cfprFirmwareBootUnitMode                                         CfprFirmwareBootUnitMode,
    cfprFirmwareBootUnitOperState                                    CfprFirmwareImageState,
    cfprFirmwareBootUnitPrevVersion                                  SnmpAdminString,
    cfprFirmwareBootUnitResetOnActivate                              TruthValue,
    cfprFirmwareBootUnitSkipValidation                               TruthValue,
    cfprFirmwareBootUnitType                                         CfprFirmwareComponentType,
    cfprFirmwareBootUnitVersion                                      SnmpAdminString
}

cfprFirmwareBootUnitInstanceId OBJECT-TYPE
    SYNTAX       CfprManagedObjectId
    MAX-ACCESS   not-accessible
    STATUS       current
    DESCRIPTION
        "Instance identifier of the managed object."
    ::= { cfprFirmwareBootUnitEntry 1 }

cfprFirmwareBootUnitDn OBJECT-TYPE
    SYNTAX       CfprManagedObjectDn
    MAX-ACCESS   read-only
    STATUS       current
    DESCRIPTION
        "Cisco Firepower firmware:BootUnit:dn managed object property"
    ::= { cfprFirmwareBootUnitEntry 2 }

cfprFirmwareBootUnitRn OBJECT-TYPE
    SYNTAX       SnmpAdminString
    MAX-ACCESS   read-only
    STATUS       current
    DESCRIPTION
        "Cisco Firepower firmware:BootUnit:rn managed object property"
    ::= { cfprFirmwareBootUnitEntry 3 }

cfprFirmwareBootUnitAdminState OBJECT-TYPE
    SYNTAX       CfprFirmwareTriggerState
    MAX-ACCESS   read-only
    STATUS       current
    DESCRIPTION
        "Cisco Firepower firmware:BootUnit:adminState managed
        object property"
    ::= { cfprFirmwareBootUnitEntry 4 }

cfprFirmwareBootUnitIgnoreCompCheck OBJECT-TYPE
    SYNTAX       TruthValue
    MAX-ACCESS   read-only
    STATUS       current
    DESCRIPTION
        "Cisco Firepower firmware:BootUnit:ignoreCompCheck
        managed object property"
    ::= { cfprFirmwareBootUnitEntry 5 }

cfprFirmwareBootUnitImage OBJECT-TYPE
    SYNTAX       CfprFirmwareBootUnitImage
    MAX-ACCESS   read-only
    STATUS       current
    DESCRIPTION
        "Cisco Firepower firmware:BootUnit:image managed object property"
    ::= { cfprFirmwareBootUnitEntry 6 }

cfprFirmwareBootUnitInvTag OBJECT-TYPE
    SYNTAX       SnmpAdminString
    MAX-ACCESS   read-only
    STATUS       current
    DESCRIPTION
        "Cisco Firepower firmware:BootUnit:invTag managed object property"
    ::= { cfprFirmwareBootUnitEntry 7 }

cfprFirmwareBootUnitMode OBJECT-TYPE
    SYNTAX       CfprFirmwareBootUnitMode
    MAX-ACCESS   read-only
    STATUS       current
    DESCRIPTION
        "Cisco Firepower firmware:BootUnit:mode managed object property"
    ::= { cfprFirmwareBootUnitEntry 8 }

cfprFirmwareBootUnitOperState OBJECT-TYPE
    SYNTAX       CfprFirmwareImageState
    MAX-ACCESS   read-only
    STATUS       current
    DESCRIPTION
        "Cisco Firepower firmware:BootUnit:operState managed
        object property"
    ::= { cfprFirmwareBootUnitEntry 9 }

cfprFirmwareBootUnitPrevVersion OBJECT-TYPE
    SYNTAX       SnmpAdminString
    MAX-ACCESS   read-only
    STATUS       current
    DESCRIPTION
        "Cisco Firepower firmware:BootUnit:prevVersion
        managed object property"
    ::= { cfprFirmwareBootUnitEntry 10 }

cfprFirmwareBootUnitResetOnActivate OBJECT-TYPE
    SYNTAX       TruthValue
    MAX-ACCESS   read-only
    STATUS       current
    DESCRIPTION
        "Cisco Firepower firmware:BootUnit:resetOnActivate
        managed object property"
    ::= { cfprFirmwareBootUnitEntry 11 }

cfprFirmwareBootUnitSkipValidation OBJECT-TYPE
    SYNTAX       TruthValue
    MAX-ACCESS   read-only
    STATUS       current
    DESCRIPTION
        "Cisco Firepower firmware:BootUnit:skipValidation
        managed object property"
    ::= { cfprFirmwareBootUnitEntry 12 }

cfprFirmwareBootUnitType OBJECT-TYPE
    SYNTAX       CfprFirmwareComponentType
    MAX-ACCESS   read-only
    STATUS       current
    DESCRIPTION
        "Cisco Firepower firmware:BootUnit:type managed object property"
    ::= { cfprFirmwareBootUnitEntry 13 }

cfprFirmwareBootUnitVersion OBJECT-TYPE
    SYNTAX       SnmpAdminString
    MAX-ACCESS   read-only
    STATUS       current
    DESCRIPTION
        "Cisco Firepower firmware:BootUnit:version managed
        object property"
    ::= { cfprFirmwareBootUnitEntry 14 }

cfprFirmwareBundleInfoTable OBJECT-TYPE
    SYNTAX           SEQUENCE OF CfprFirmwareBundleInfoEntry
    MAX-ACCESS       not-accessible
    STATUS           current
    DESCRIPTION
        "Cisco Firepower firmware:BundleInfo managed object table"
    ::= { cfprFirmwareObjects 6 }

cfprFirmwareBundleInfoEntry OBJECT-TYPE
    SYNTAX           CfprFirmwareBundleInfoEntry
    MAX-ACCESS       not-accessible
    STATUS           current
    DESCRIPTION
        "Entry for the cfprFirmwareBundleInfoTable table."
    INDEX { cfprFirmwareBundleInfoInstanceId }
    ::= { cfprFirmwareBundleInfoTable 1 }

CfprFirmwareBundleInfoEntry ::= SEQUENCE {
    cfprFirmwareBundleInfoInstanceId                                 CfprManagedObjectId,
    cfprFirmwareBundleInfoDn                                         CfprManagedObjectDn,
    cfprFirmwareBundleInfoRn                                         SnmpAdminString,
    cfprFirmwareBundleInfoType                                       CfprFirmwareDistributableType,
    cfprFirmwareBundleInfoVersion                                    SnmpAdminString,
    cfprFirmwareBundleInfoSecModelSupported                          SnmpAdminString
}

cfprFirmwareBundleInfoInstanceId OBJECT-TYPE
    SYNTAX       CfprManagedObjectId
    MAX-ACCESS   not-accessible
    STATUS       current
    DESCRIPTION
        "Instance identifier of the managed object."
    ::= { cfprFirmwareBundleInfoEntry 1 }

cfprFirmwareBundleInfoDn OBJECT-TYPE
    SYNTAX       CfprManagedObjectDn
    MAX-ACCESS   read-only
    STATUS       current
    DESCRIPTION
        "Cisco Firepower firmware:BundleInfo:dn managed object property"
    ::= { cfprFirmwareBundleInfoEntry 2 }

cfprFirmwareBundleInfoRn OBJECT-TYPE
    SYNTAX       SnmpAdminString
    MAX-ACCESS   read-only
    STATUS       current
    DESCRIPTION
        "Cisco Firepower firmware:BundleInfo:rn managed object property"
    ::= { cfprFirmwareBundleInfoEntry 3 }

cfprFirmwareBundleInfoType OBJECT-TYPE
    SYNTAX       CfprFirmwareDistributableType
    MAX-ACCESS   read-only
    STATUS       current
    DESCRIPTION
        "Cisco Firepower firmware:BundleInfo:type managed object property"
    ::= { cfprFirmwareBundleInfoEntry 4 }

cfprFirmwareBundleInfoVersion OBJECT-TYPE
    SYNTAX       SnmpAdminString
    MAX-ACCESS   read-only
    STATUS       current
    DESCRIPTION
        "Cisco Firepower firmware:BundleInfo:version managed
        object property"
    ::= { cfprFirmwareBundleInfoEntry 5 }

cfprFirmwareBundleInfoSecModelSupported OBJECT-TYPE
    SYNTAX       SnmpAdminString
    MAX-ACCESS   read-only
    STATUS       current
    DESCRIPTION
        "Cisco Firepower firmware:BundleInfo:secModelSupported
        managed object property"
    ::= { cfprFirmwareBundleInfoEntry 6 }

cfprFirmwareBundleInfoDigestTable OBJECT-TYPE
    SYNTAX           SEQUENCE OF CfprFirmwareBundleInfoDigestEntry
    MAX-ACCESS       not-accessible
    STATUS           current
    DESCRIPTION
        "Cisco Firepower firmware:BundleInfoDigest managed object table"
    ::= { cfprFirmwareObjects 7 }

cfprFirmwareBundleInfoDigestEntry OBJECT-TYPE
    SYNTAX           CfprFirmwareBundleInfoDigestEntry
    MAX-ACCESS       not-accessible
    STATUS           current
    DESCRIPTION
        "Entry for the cfprFirmwareBundleInfoDigestTable table."
    INDEX { cfprFirmwareBundleInfoDigestInstanceId }
    ::= { cfprFirmwareBundleInfoDigestTable 1 }

CfprFirmwareBundleInfoDigestEntry ::= SEQUENCE {
    cfprFirmwareBundleInfoDigestInstanceId                           CfprManagedObjectId,
    cfprFirmwareBundleInfoDigestDn                                   CfprManagedObjectDn,
    cfprFirmwareBundleInfoDigestRn                                   SnmpAdminString,
    cfprFirmwareBundleInfoDigestBundleName                           SnmpAdminString,
    cfprFirmwareBundleInfoDigestType                                 CfprFirmwareDistributableType,
    cfprFirmwareBundleInfoDigestVersion                              SnmpAdminString
}

cfprFirmwareBundleInfoDigestInstanceId OBJECT-TYPE
    SYNTAX       CfprManagedObjectId
    MAX-ACCESS   not-accessible
    STATUS       current
    DESCRIPTION
        "Instance identifier of the managed object."
    ::= { cfprFirmwareBundleInfoDigestEntry 1 }

cfprFirmwareBundleInfoDigestDn OBJECT-TYPE
    SYNTAX       CfprManagedObjectDn
    MAX-ACCESS   read-only
    STATUS       current
    DESCRIPTION
        "Cisco Firepower firmware:BundleInfoDigest:dn managed
        object property"
    ::= { cfprFirmwareBundleInfoDigestEntry 2 }

cfprFirmwareBundleInfoDigestRn OBJECT-TYPE
    SYNTAX       SnmpAdminString
    MAX-ACCESS   read-only
    STATUS       current
    DESCRIPTION
        "Cisco Firepower firmware:BundleInfoDigest:rn managed
        object property"
    ::= { cfprFirmwareBundleInfoDigestEntry 3 }

cfprFirmwareBundleInfoDigestBundleName OBJECT-TYPE
    SYNTAX       SnmpAdminString
    MAX-ACCESS   read-only
    STATUS       current
    DESCRIPTION
        "Cisco Firepower firmware:BundleInfoDigest:bundleName
        managed object property"
    ::= { cfprFirmwareBundleInfoDigestEntry 4 }

cfprFirmwareBundleInfoDigestType OBJECT-TYPE
    SYNTAX       CfprFirmwareDistributableType
    MAX-ACCESS   read-only
    STATUS       current
    DESCRIPTION
        "Cisco Firepower firmware:BundleInfoDigest:type
        managed object property"
    ::= { cfprFirmwareBundleInfoDigestEntry 5 }

cfprFirmwareBundleInfoDigestVersion OBJECT-TYPE
    SYNTAX       SnmpAdminString
    MAX-ACCESS   read-only
    STATUS       current
    DESCRIPTION
        "Cisco Firepower firmware:BundleInfoDigest:version
        managed object property"
    ::= { cfprFirmwareBundleInfoDigestEntry 6 }

cfprFirmwareBundleTypeTable OBJECT-TYPE
    SYNTAX           SEQUENCE OF CfprFirmwareBundleTypeEntry
    MAX-ACCESS       not-accessible
    STATUS           current
    DESCRIPTION
        "Cisco Firepower firmware:BundleType managed object table"
    ::= { cfprFirmwareObjects 8 }

cfprFirmwareBundleTypeEntry OBJECT-TYPE
    SYNTAX           CfprFirmwareBundleTypeEntry
    MAX-ACCESS       not-accessible
    STATUS           current
    DESCRIPTION
        "Entry for the cfprFirmwareBundleTypeTable table."
    INDEX { cfprFirmwareBundleTypeInstanceId }
    ::= { cfprFirmwareBundleTypeTable 1 }

CfprFirmwareBundleTypeEntry ::= SEQUENCE {
    cfprFirmwareBundleTypeInstanceId                                 CfprManagedObjectId,
    cfprFirmwareBundleTypeDn                                         CfprManagedObjectDn,
    cfprFirmwareBundleTypeRn                                         SnmpAdminString,
    cfprFirmwareBundleTypeInvTag                                     SnmpAdminString,
    cfprFirmwareBundleTypeType                                       CfprFirmwareDistributableType
}

cfprFirmwareBundleTypeInstanceId OBJECT-TYPE
    SYNTAX       CfprManagedObjectId
    MAX-ACCESS   not-accessible
    STATUS       current
    DESCRIPTION
        "Instance identifier of the managed object."
    ::= { cfprFirmwareBundleTypeEntry 1 }

cfprFirmwareBundleTypeDn OBJECT-TYPE
    SYNTAX       CfprManagedObjectDn
    MAX-ACCESS   read-only
    STATUS       current
    DESCRIPTION
        "Cisco Firepower firmware:BundleType:dn managed object property"
    ::= { cfprFirmwareBundleTypeEntry 2 }

cfprFirmwareBundleTypeRn OBJECT-TYPE
    SYNTAX       SnmpAdminString
    MAX-ACCESS   read-only
    STATUS       current
    DESCRIPTION
        "Cisco Firepower firmware:BundleType:rn managed object property"
    ::= { cfprFirmwareBundleTypeEntry 3 }

cfprFirmwareBundleTypeInvTag OBJECT-TYPE
    SYNTAX       SnmpAdminString
    MAX-ACCESS   read-only
    STATUS       current
    DESCRIPTION
        "Cisco Firepower firmware:BundleType:invTag managed
        object property"
    ::= { cfprFirmwareBundleTypeEntry 4 }

cfprFirmwareBundleTypeType OBJECT-TYPE
    SYNTAX       CfprFirmwareDistributableType
    MAX-ACCESS   read-only
    STATUS       current
    DESCRIPTION
        "Cisco Firepower firmware:BundleType:type managed object property"
    ::= { cfprFirmwareBundleTypeEntry 5 }

cfprFirmwareBundleTypeCapProviderTable OBJECT-TYPE
    SYNTAX           SEQUENCE OF CfprFirmwareBundleTypeCapProviderEntry
    MAX-ACCESS       not-accessible
    STATUS           current
    DESCRIPTION
        "Cisco Firepower firmware:BundleTypeCapProvider
        managed object table"
    ::= { cfprFirmwareObjects 9 }

cfprFirmwareBundleTypeCapProviderEntry OBJECT-TYPE
    SYNTAX           CfprFirmwareBundleTypeCapProviderEntry
    MAX-ACCESS       not-accessible
    STATUS           current
    DESCRIPTION
        "Entry for the cfprFirmwareBundleTypeCapProviderTable table."
    INDEX { cfprFirmwareBundleTypeCapProviderInstanceId }
    ::= { cfprFirmwareBundleTypeCapProviderTable 1 }

CfprFirmwareBundleTypeCapProviderEntry ::= SEQUENCE {
    cfprFirmwareBundleTypeCapProviderInstanceId                      CfprManagedObjectId,
    cfprFirmwareBundleTypeCapProviderDn                              CfprManagedObjectDn,
    cfprFirmwareBundleTypeCapProviderRn                              SnmpAdminString,
    cfprFirmwareBundleTypeCapProviderDeleted                         TruthValue,
    cfprFirmwareBundleTypeCapProviderDeprecated                      TruthValue,
    cfprFirmwareBundleTypeCapProviderElementLoadFailures             Gauge32,
    cfprFirmwareBundleTypeCapProviderElementsLoaded                  Gauge32,
    cfprFirmwareBundleTypeCapProviderGencount                        Gauge32,
    cfprFirmwareBundleTypeCapProviderLoadErrors                      Gauge32,
    cfprFirmwareBundleTypeCapProviderLoadWarnings                    Gauge32,
    cfprFirmwareBundleTypeCapProviderMgmtPlaneVer                    SnmpAdminString,
    cfprFirmwareBundleTypeCapProviderModel                           SnmpAdminString,
    cfprFirmwareBundleTypeCapProviderPlatformType                    CfprFirmwarePlatformType,
    cfprFirmwareBundleTypeCapProviderVendor                          SnmpAdminString
}

cfprFirmwareBundleTypeCapProviderInstanceId OBJECT-TYPE
    SYNTAX       CfprManagedObjectId
    MAX-ACCESS   not-accessible
    STATUS       current
    DESCRIPTION
        "Instance identifier of the managed object."
    ::= { cfprFirmwareBundleTypeCapProviderEntry 1 }

cfprFirmwareBundleTypeCapProviderDn OBJECT-TYPE
    SYNTAX       CfprManagedObjectDn
    MAX-ACCESS   read-only
    STATUS       current
    DESCRIPTION
        "Cisco Firepower firmware:BundleTypeCapProvider:dn
        managed object property"
    ::= { cfprFirmwareBundleTypeCapProviderEntry 2 }

cfprFirmwareBundleTypeCapProviderRn OBJECT-TYPE
    SYNTAX       SnmpAdminString
    MAX-ACCESS   read-only
    STATUS       current
    DESCRIPTION
        "Cisco Firepower firmware:BundleTypeCapProvider:rn
        managed object property"
    ::= { cfprFirmwareBundleTypeCapProviderEntry 3 }

cfprFirmwareBundleTypeCapProviderDeleted OBJECT-TYPE
    SYNTAX       TruthValue
    MAX-ACCESS   read-only
    STATUS       current
    DESCRIPTION
        "Cisco Firepower firmware:BundleTypeCapProvider:deleted
        managed object property"
    ::= { cfprFirmwareBundleTypeCapProviderEntry 4 }

cfprFirmwareBundleTypeCapProviderDeprecated OBJECT-TYPE
    SYNTAX       TruthValue
    MAX-ACCESS   read-only
    STATUS       current
    DESCRIPTION
        "Cisco Firepower firmware:BundleTypeCapProvider:deprecated
        managed object property"
    ::= { cfprFirmwareBundleTypeCapProviderEntry 5 }

cfprFirmwareBundleTypeCapProviderElementLoadFailures OBJECT-TYPE
    SYNTAX       Gauge32
    MAX-ACCESS   read-only
    STATUS       current
    DESCRIPTION
        "Cisco Firepower firmware:BundleTypeCapProvider:elementLoadFailure
        s managed object property"
    ::= { cfprFirmwareBundleTypeCapProviderEntry 6 }

cfprFirmwareBundleTypeCapProviderElementsLoaded OBJECT-TYPE
    SYNTAX       Gauge32
    MAX-ACCESS   read-only
    STATUS       current
    DESCRIPTION
        "Cisco Firepower firmware:BundleTypeCapProvider:elementsLoaded
        managed object property"
    ::= { cfprFirmwareBundleTypeCapProviderEntry 7 }

cfprFirmwareBundleTypeCapProviderGencount OBJECT-TYPE
    SYNTAX       Gauge32
    MAX-ACCESS   read-only
    STATUS       current
    DESCRIPTION
        "Cisco Firepower firmware:BundleTypeCapProvider:gencount
        managed object property"
    ::= { cfprFirmwareBundleTypeCapProviderEntry 8 }

cfprFirmwareBundleTypeCapProviderLoadErrors OBJECT-TYPE
    SYNTAX       Gauge32
    MAX-ACCESS   read-only
    STATUS       current
    DESCRIPTION
        "Cisco Firepower firmware:BundleTypeCapProvider:loadErrors
        managed object property"
    ::= { cfprFirmwareBundleTypeCapProviderEntry 9 }

cfprFirmwareBundleTypeCapProviderLoadWarnings OBJECT-TYPE
    SYNTAX       Gauge32
    MAX-ACCESS   read-only
    STATUS       current
    DESCRIPTION
        "Cisco Firepower firmware:BundleTypeCapProvider:loadWarnings
        managed object property"
    ::= { cfprFirmwareBundleTypeCapProviderEntry 10 }

cfprFirmwareBundleTypeCapProviderMgmtPlaneVer OBJECT-TYPE
    SYNTAX       SnmpAdminString
    MAX-ACCESS   read-only
    STATUS       current
    DESCRIPTION
        "Cisco Firepower firmware:BundleTypeCapProvider:mgmtPlaneVer
        managed object property"
    ::= { cfprFirmwareBundleTypeCapProviderEntry 11 }

cfprFirmwareBundleTypeCapProviderModel OBJECT-TYPE
    SYNTAX       SnmpAdminString
    MAX-ACCESS   read-only
    STATUS       current
    DESCRIPTION
        "Cisco Firepower firmware:BundleTypeCapProvider:model
        managed object property"
    ::= { cfprFirmwareBundleTypeCapProviderEntry 12 }

cfprFirmwareBundleTypeCapProviderPlatformType OBJECT-TYPE
    SYNTAX       CfprFirmwarePlatformType
    MAX-ACCESS   read-only
    STATUS       current
    DESCRIPTION
        "Cisco Firepower firmware:BundleTypeCapProvider:platformType
        managed object property"
    ::= { cfprFirmwareBundleTypeCapProviderEntry 13 }

cfprFirmwareBundleTypeCapProviderVendor OBJECT-TYPE
    SYNTAX       SnmpAdminString
    MAX-ACCESS   read-only
    STATUS       current
    DESCRIPTION
        "Cisco Firepower firmware:BundleTypeCapProvider:vendor
        managed object property"
    ::= { cfprFirmwareBundleTypeCapProviderEntry 14 }

cfprFirmwareCatalogPackTable OBJECT-TYPE
    SYNTAX           SEQUENCE OF CfprFirmwareCatalogPackEntry
    MAX-ACCESS       not-accessible
    STATUS           current
    DESCRIPTION
        "Cisco Firepower firmware:CatalogPack managed object table"
    ::= { cfprFirmwareObjects 10 }

cfprFirmwareCatalogPackEntry OBJECT-TYPE
    SYNTAX           CfprFirmwareCatalogPackEntry
    MAX-ACCESS       not-accessible
    STATUS           current
    DESCRIPTION
        "Entry for the cfprFirmwareCatalogPackTable table."
    INDEX { cfprFirmwareCatalogPackInstanceId }
    ::= { cfprFirmwareCatalogPackTable 1 }

CfprFirmwareCatalogPackEntry ::= SEQUENCE {
    cfprFirmwareCatalogPackInstanceId                                CfprManagedObjectId,
    cfprFirmwareCatalogPackDn                                        CfprManagedObjectDn,
    cfprFirmwareCatalogPackRn                                        SnmpAdminString,
    cfprFirmwareCatalogPackCatalogName                               SnmpAdminString,
    cfprFirmwareCatalogPackCatalogVersion                            SnmpAdminString,
    cfprFirmwareCatalogPackConfigState                               CfprFirmwareCatalogPackConfigState,
    cfprFirmwareCatalogPackConfigStatusMessage                       SnmpAdminString,
    cfprFirmwareCatalogPackDescr                                     SnmpAdminString,
    cfprFirmwareCatalogPackIntId                                     SnmpAdminString,
    cfprFirmwareCatalogPackMode                                      CfprFirmwarePackMode,
    cfprFirmwareCatalogPackName                                      SnmpAdminString,
    cfprFirmwareCatalogPackPolicyLevel                               Gauge32,
    cfprFirmwareCatalogPackPolicyOwner                               CfprPolicyPolicyOwner,
    cfprFirmwareCatalogPackStageSize                                 Gauge32,
    cfprFirmwareCatalogPackUpdateTrigger                             DateAndTime
}

cfprFirmwareCatalogPackInstanceId OBJECT-TYPE
    SYNTAX       CfprManagedObjectId
    MAX-ACCESS   not-accessible
    STATUS       current
    DESCRIPTION
        "Instance identifier of the managed object."
    ::= { cfprFirmwareCatalogPackEntry 1 }

cfprFirmwareCatalogPackDn OBJECT-TYPE
    SYNTAX       CfprManagedObjectDn
    MAX-ACCESS   read-only
    STATUS       current
    DESCRIPTION
        "Cisco Firepower firmware:CatalogPack:dn managed object property"
    ::= { cfprFirmwareCatalogPackEntry 2 }

cfprFirmwareCatalogPackRn OBJECT-TYPE
    SYNTAX       SnmpAdminString
    MAX-ACCESS   read-only
    STATUS       current
    DESCRIPTION
        "Cisco Firepower firmware:CatalogPack:rn managed object property"
    ::= { cfprFirmwareCatalogPackEntry 3 }

cfprFirmwareCatalogPackCatalogName OBJECT-TYPE
    SYNTAX       SnmpAdminString
    MAX-ACCESS   read-only
    STATUS       current
    DESCRIPTION
        "Cisco Firepower firmware:CatalogPack:catalogName
        managed object property"
    ::= { cfprFirmwareCatalogPackEntry 4 }

cfprFirmwareCatalogPackCatalogVersion OBJECT-TYPE
    SYNTAX       SnmpAdminString
    MAX-ACCESS   read-only
    STATUS       current
    DESCRIPTION
        "Cisco Firepower firmware:CatalogPack:catalogVersion
        managed object property"
    ::= { cfprFirmwareCatalogPackEntry 5 }

cfprFirmwareCatalogPackConfigState OBJECT-TYPE
    SYNTAX       CfprFirmwareCatalogPackConfigState
    MAX-ACCESS   read-only
    STATUS       current
    DESCRIPTION
        "Cisco Firepower firmware:CatalogPack:configState
        managed object property"
    ::= { cfprFirmwareCatalogPackEntry 6 }

cfprFirmwareCatalogPackConfigStatusMessage OBJECT-TYPE
    SYNTAX       SnmpAdminString
    MAX-ACCESS   read-only
    STATUS       current
    DESCRIPTION
        "Cisco Firepower firmware:CatalogPack:configStatusMessage
        managed object property"
    ::= { cfprFirmwareCatalogPackEntry 7 }

cfprFirmwareCatalogPackDescr OBJECT-TYPE
    SYNTAX       SnmpAdminString
    MAX-ACCESS   read-only
    STATUS       current
    DESCRIPTION
        "Cisco Firepower firmware:CatalogPack:descr managed
        object property"
    ::= { cfprFirmwareCatalogPackEntry 8 }

cfprFirmwareCatalogPackIntId OBJECT-TYPE
    SYNTAX       SnmpAdminString
    MAX-ACCESS   read-only
    STATUS       current
    DESCRIPTION
        "Cisco Firepower firmware:CatalogPack:intId managed
        object property"
    ::= { cfprFirmwareCatalogPackEntry 9 }

cfprFirmwareCatalogPackMode OBJECT-TYPE
    SYNTAX       CfprFirmwarePackMode
    MAX-ACCESS   read-only
    STATUS       current
    DESCRIPTION
        "Cisco Firepower firmware:CatalogPack:mode managed
        object property"
    ::= { cfprFirmwareCatalogPackEntry 10 }

cfprFirmwareCatalogPackName OBJECT-TYPE
    SYNTAX       SnmpAdminString
    MAX-ACCESS   read-only
    STATUS       current
    DESCRIPTION
        "Cisco Firepower firmware:CatalogPack:name managed
        object property"
    ::= { cfprFirmwareCatalogPackEntry 11 }

cfprFirmwareCatalogPackPolicyLevel OBJECT-TYPE
    SYNTAX       Gauge32
    MAX-ACCESS   read-only
    STATUS       current
    DESCRIPTION
        "Cisco Firepower firmware:CatalogPack:policyLevel
        managed object property"
    ::= { cfprFirmwareCatalogPackEntry 12 }

cfprFirmwareCatalogPackPolicyOwner OBJECT-TYPE
    SYNTAX       CfprPolicyPolicyOwner
    MAX-ACCESS   read-only
    STATUS       current
    DESCRIPTION
        "Cisco Firepower firmware:CatalogPack:policyOwner
        managed object property"
    ::= { cfprFirmwareCatalogPackEntry 13 }

cfprFirmwareCatalogPackStageSize OBJECT-TYPE
    SYNTAX       Gauge32
    MAX-ACCESS   read-only
    STATUS       current
    DESCRIPTION
        "Cisco Firepower firmware:CatalogPack:stageSize
        managed object property"
    ::= { cfprFirmwareCatalogPackEntry 14 }

cfprFirmwareCatalogPackUpdateTrigger OBJECT-TYPE
    SYNTAX       DateAndTime
    MAX-ACCESS   read-only
    STATUS       current
    DESCRIPTION
        "Cisco Firepower firmware:CatalogPack:updateTrigger
        managed object property"
    ::= { cfprFirmwareCatalogPackEntry 15 }

cfprFirmwareCatalogueTable OBJECT-TYPE
    SYNTAX           SEQUENCE OF CfprFirmwareCatalogueEntry
    MAX-ACCESS       not-accessible
    STATUS           current
    DESCRIPTION
        "Cisco Firepower firmware:Catalogue managed object table"
    ::= { cfprFirmwareObjects 11 }

cfprFirmwareCatalogueEntry OBJECT-TYPE
    SYNTAX           CfprFirmwareCatalogueEntry
    MAX-ACCESS       not-accessible
    STATUS           current
    DESCRIPTION
        "Entry for the cfprFirmwareCatalogueTable table."
    INDEX { cfprFirmwareCatalogueInstanceId }
    ::= { cfprFirmwareCatalogueTable 1 }

CfprFirmwareCatalogueEntry ::= SEQUENCE {
    cfprFirmwareCatalogueInstanceId                                  CfprManagedObjectId,
    cfprFirmwareCatalogueDn                                          CfprManagedObjectDn,
    cfprFirmwareCatalogueRn                                          SnmpAdminString,
    cfprFirmwareCatalogueSyncTrigger                                 TruthValue
}

cfprFirmwareCatalogueInstanceId OBJECT-TYPE
    SYNTAX       CfprManagedObjectId
    MAX-ACCESS   not-accessible
    STATUS       current
    DESCRIPTION
        "Instance identifier of the managed object."
    ::= { cfprFirmwareCatalogueEntry 1 }

cfprFirmwareCatalogueDn OBJECT-TYPE
    SYNTAX       CfprManagedObjectDn
    MAX-ACCESS   read-only
    STATUS       current
    DESCRIPTION
        "Cisco Firepower firmware:Catalogue:dn managed object property"
    ::= { cfprFirmwareCatalogueEntry 2 }

cfprFirmwareCatalogueRn OBJECT-TYPE
    SYNTAX       SnmpAdminString
    MAX-ACCESS   read-only
    STATUS       current
    DESCRIPTION
        "Cisco Firepower firmware:Catalogue:rn managed object property"
    ::= { cfprFirmwareCatalogueEntry 3 }

cfprFirmwareCatalogueSyncTrigger OBJECT-TYPE
    SYNTAX       TruthValue
    MAX-ACCESS   read-only
    STATUS       current
    DESCRIPTION
        "Cisco Firepower firmware:Catalogue:syncTrigger
        managed object property"
    ::= { cfprFirmwareCatalogueEntry 4 }

cfprFirmwareCompSourceTable OBJECT-TYPE
    SYNTAX           SEQUENCE OF CfprFirmwareCompSourceEntry
    MAX-ACCESS       not-accessible
    STATUS           current
    DESCRIPTION
        "Cisco Firepower firmware:CompSource managed object table"
    ::= { cfprFirmwareObjects 12 }

cfprFirmwareCompSourceEntry OBJECT-TYPE
    SYNTAX           CfprFirmwareCompSourceEntry
    MAX-ACCESS       not-accessible
    STATUS           current
    DESCRIPTION
        "Entry for the cfprFirmwareCompSourceTable table."
    INDEX { cfprFirmwareCompSourceInstanceId }
    ::= { cfprFirmwareCompSourceTable 1 }

CfprFirmwareCompSourceEntry ::= SEQUENCE {
    cfprFirmwareCompSourceInstanceId                                 CfprManagedObjectId,
    cfprFirmwareCompSourceDn                                         CfprManagedObjectDn,
    cfprFirmwareCompSourceRn                                         SnmpAdminString,
    cfprFirmwareCompSourceDescr                                      SnmpAdminString,
    cfprFirmwareCompSourceIntId                                      SnmpAdminString,
    cfprFirmwareCompSourceInvTag                                     SnmpAdminString,
    cfprFirmwareCompSourceName                                       SnmpAdminString,
    cfprFirmwareCompSourcePolicyLevel                                Gauge32,
    cfprFirmwareCompSourcePolicyOwner                                CfprPolicyPolicyOwner,
    cfprFirmwareCompSourceVersion                                    SnmpAdminString
}

cfprFirmwareCompSourceInstanceId OBJECT-TYPE
    SYNTAX       CfprManagedObjectId
    MAX-ACCESS   not-accessible
    STATUS       current
    DESCRIPTION
        "Instance identifier of the managed object."
    ::= { cfprFirmwareCompSourceEntry 1 }

cfprFirmwareCompSourceDn OBJECT-TYPE
    SYNTAX       CfprManagedObjectDn
    MAX-ACCESS   read-only
    STATUS       current
    DESCRIPTION
        "Cisco Firepower firmware:CompSource:dn managed object property"
    ::= { cfprFirmwareCompSourceEntry 2 }

cfprFirmwareCompSourceRn OBJECT-TYPE
    SYNTAX       SnmpAdminString
    MAX-ACCESS   read-only
    STATUS       current
    DESCRIPTION
        "Cisco Firepower firmware:CompSource:rn managed object property"
    ::= { cfprFirmwareCompSourceEntry 3 }

cfprFirmwareCompSourceDescr OBJECT-TYPE
    SYNTAX       SnmpAdminString
    MAX-ACCESS   read-only
    STATUS       current
    DESCRIPTION
        "Cisco Firepower firmware:CompSource:descr managed
        object property"
    ::= { cfprFirmwareCompSourceEntry 4 }

cfprFirmwareCompSourceIntId OBJECT-TYPE
    SYNTAX       SnmpAdminString
    MAX-ACCESS   read-only
    STATUS       current
    DESCRIPTION
        "Cisco Firepower firmware:CompSource:intId managed
        object property"
    ::= { cfprFirmwareCompSourceEntry 5 }

cfprFirmwareCompSourceInvTag OBJECT-TYPE
    SYNTAX       SnmpAdminString
    MAX-ACCESS   read-only
    STATUS       current
    DESCRIPTION
        "Cisco Firepower firmware:CompSource:invTag managed
        object property"
    ::= { cfprFirmwareCompSourceEntry 6 }

cfprFirmwareCompSourceName OBJECT-TYPE
    SYNTAX       SnmpAdminString
    MAX-ACCESS   read-only
    STATUS       current
    DESCRIPTION
        "Cisco Firepower firmware:CompSource:name managed object property"
    ::= { cfprFirmwareCompSourceEntry 7 }

cfprFirmwareCompSourcePolicyLevel OBJECT-TYPE
    SYNTAX       Gauge32
    MAX-ACCESS   read-only
    STATUS       current
    DESCRIPTION
        "Cisco Firepower firmware:CompSource:policyLevel
        managed object property"
    ::= { cfprFirmwareCompSourceEntry 8 }

cfprFirmwareCompSourcePolicyOwner OBJECT-TYPE
    SYNTAX       CfprPolicyPolicyOwner
    MAX-ACCESS   read-only
    STATUS       current
    DESCRIPTION
        "Cisco Firepower firmware:CompSource:policyOwner
        managed object property"
    ::= { cfprFirmwareCompSourceEntry 9 }

cfprFirmwareCompSourceVersion OBJECT-TYPE
    SYNTAX       SnmpAdminString
    MAX-ACCESS   read-only
    STATUS       current
    DESCRIPTION
        "Cisco Firepower firmware:CompSource:version managed
        object property"
    ::= { cfprFirmwareCompSourceEntry 10 }

cfprFirmwareCompTargetTable OBJECT-TYPE
    SYNTAX           SEQUENCE OF CfprFirmwareCompTargetEntry
    MAX-ACCESS       not-accessible
    STATUS           current
    DESCRIPTION
        "Cisco Firepower firmware:CompTarget managed object table"
    ::= { cfprFirmwareObjects 13 }

cfprFirmwareCompTargetEntry OBJECT-TYPE
    SYNTAX           CfprFirmwareCompTargetEntry
    MAX-ACCESS       not-accessible
    STATUS           current
    DESCRIPTION
        "Entry for the cfprFirmwareCompTargetTable table."
    INDEX { cfprFirmwareCompTargetInstanceId }
    ::= { cfprFirmwareCompTargetTable 1 }

CfprFirmwareCompTargetEntry ::= SEQUENCE {
    cfprFirmwareCompTargetInstanceId                                 CfprManagedObjectId,
    cfprFirmwareCompTargetDn                                         CfprManagedObjectDn,
    cfprFirmwareCompTargetRn                                         SnmpAdminString,
    cfprFirmwareCompTargetDescr                                      SnmpAdminString,
    cfprFirmwareCompTargetIntId                                      SnmpAdminString,
    cfprFirmwareCompTargetInvTag                                     SnmpAdminString,
    cfprFirmwareCompTargetName                                       SnmpAdminString,
    cfprFirmwareCompTargetPolicyLevel                                Gauge32,
    cfprFirmwareCompTargetPolicyOwner                                CfprPolicyPolicyOwner,
    cfprFirmwareCompTargetVersion                                    SnmpAdminString
}

cfprFirmwareCompTargetInstanceId OBJECT-TYPE
    SYNTAX       CfprManagedObjectId
    MAX-ACCESS   not-accessible
    STATUS       current
    DESCRIPTION
        "Instance identifier of the managed object."
    ::= { cfprFirmwareCompTargetEntry 1 }

cfprFirmwareCompTargetDn OBJECT-TYPE
    SYNTAX       CfprManagedObjectDn
    MAX-ACCESS   read-only
    STATUS       current
    DESCRIPTION
        "Cisco Firepower firmware:CompTarget:dn managed object property"
    ::= { cfprFirmwareCompTargetEntry 2 }

cfprFirmwareCompTargetRn OBJECT-TYPE
    SYNTAX       SnmpAdminString
    MAX-ACCESS   read-only
    STATUS       current
    DESCRIPTION
        "Cisco Firepower firmware:CompTarget:rn managed object property"
    ::= { cfprFirmwareCompTargetEntry 3 }

cfprFirmwareCompTargetDescr OBJECT-TYPE
    SYNTAX       SnmpAdminString
    MAX-ACCESS   read-only
    STATUS       current
    DESCRIPTION
        "Cisco Firepower firmware:CompTarget:descr managed
        object property"
    ::= { cfprFirmwareCompTargetEntry 4 }

cfprFirmwareCompTargetIntId OBJECT-TYPE
    SYNTAX       SnmpAdminString
    MAX-ACCESS   read-only
    STATUS       current
    DESCRIPTION
        "Cisco Firepower firmware:CompTarget:intId managed
        object property"
    ::= { cfprFirmwareCompTargetEntry 5 }

cfprFirmwareCompTargetInvTag OBJECT-TYPE
    SYNTAX       SnmpAdminString
    MAX-ACCESS   read-only
    STATUS       current
    DESCRIPTION
        "Cisco Firepower firmware:CompTarget:invTag managed
        object property"
    ::= { cfprFirmwareCompTargetEntry 6 }

cfprFirmwareCompTargetName OBJECT-TYPE
    SYNTAX       SnmpAdminString
    MAX-ACCESS   read-only
    STATUS       current
    DESCRIPTION
        "Cisco Firepower firmware:CompTarget:name managed object property"
    ::= { cfprFirmwareCompTargetEntry 7 }

cfprFirmwareCompTargetPolicyLevel OBJECT-TYPE
    SYNTAX       Gauge32
    MAX-ACCESS   read-only
    STATUS       current
    DESCRIPTION
        "Cisco Firepower firmware:CompTarget:policyLevel
        managed object property"
    ::= { cfprFirmwareCompTargetEntry 8 }

cfprFirmwareCompTargetPolicyOwner OBJECT-TYPE
    SYNTAX       CfprPolicyPolicyOwner
    MAX-ACCESS   read-only
    STATUS       current
    DESCRIPTION
        "Cisco Firepower firmware:CompTarget:policyOwner
        managed object property"
    ::= { cfprFirmwareCompTargetEntry 9 }

cfprFirmwareCompTargetVersion OBJECT-TYPE
    SYNTAX       SnmpAdminString
    MAX-ACCESS   read-only
    STATUS       current
    DESCRIPTION
        "Cisco Firepower firmware:CompTarget:version managed
        object property"
    ::= { cfprFirmwareCompTargetEntry 10 }

cfprFirmwareComputeHostPackTable OBJECT-TYPE
    SYNTAX           SEQUENCE OF CfprFirmwareComputeHostPackEntry
    MAX-ACCESS       not-accessible
    STATUS           current
    DESCRIPTION
        "Cisco Firepower firmware:ComputeHostPack managed object table"
    ::= { cfprFirmwareObjects 14 }

cfprFirmwareComputeHostPackEntry OBJECT-TYPE
    SYNTAX           CfprFirmwareComputeHostPackEntry
    MAX-ACCESS       not-accessible
    STATUS           current
    DESCRIPTION
        "Entry for the cfprFirmwareComputeHostPackTable table."
    INDEX { cfprFirmwareComputeHostPackInstanceId }
    ::= { cfprFirmwareComputeHostPackTable 1 }

CfprFirmwareComputeHostPackEntry ::= SEQUENCE {
    cfprFirmwareComputeHostPackInstanceId                            CfprManagedObjectId,
    cfprFirmwareComputeHostPackDn                                    CfprManagedObjectDn,
    cfprFirmwareComputeHostPackRn                                    SnmpAdminString,
    cfprFirmwareComputeHostPackBladeBundleName                       SnmpAdminString,
    cfprFirmwareComputeHostPackBladeBundleVersion                    SnmpAdminString,
    cfprFirmwareComputeHostPackConfigQualifier                       CfprFirmwareHostPackConfigQualifier,
    cfprFirmwareComputeHostPackDescr                                 SnmpAdminString,
    cfprFirmwareComputeHostPackIgnoreCompCheck                       TruthValue,
    cfprFirmwareComputeHostPackIntId                                 SnmpAdminString,
    cfprFirmwareComputeHostPackMode                                  CfprFirmwarePackMode,
    cfprFirmwareComputeHostPackName                                  SnmpAdminString,
    cfprFirmwareComputeHostPackPlatformBundleVersion                 SnmpAdminString,
    cfprFirmwareComputeHostPackPolicyLevel                           Gauge32,
    cfprFirmwareComputeHostPackPolicyOwner                           CfprPolicyPolicyOwner,
    cfprFirmwareComputeHostPackRackBundleName                        SnmpAdminString,
    cfprFirmwareComputeHostPackRackBundleVersion                     SnmpAdminString,
    cfprFirmwareComputeHostPackStageSize                             Gauge32,
    cfprFirmwareComputeHostPackUpdateTrigger                         DateAndTime
}

cfprFirmwareComputeHostPackInstanceId OBJECT-TYPE
    SYNTAX       CfprManagedObjectId
    MAX-ACCESS   not-accessible
    STATUS       current
    DESCRIPTION
        "Instance identifier of the managed object."
    ::= { cfprFirmwareComputeHostPackEntry 1 }

cfprFirmwareComputeHostPackDn OBJECT-TYPE
    SYNTAX       CfprManagedObjectDn
    MAX-ACCESS   read-only
    STATUS       current
    DESCRIPTION
        "Cisco Firepower firmware:ComputeHostPack:dn managed
        object property"
    ::= { cfprFirmwareComputeHostPackEntry 2 }

cfprFirmwareComputeHostPackRn OBJECT-TYPE
    SYNTAX       SnmpAdminString
    MAX-ACCESS   read-only
    STATUS       current
    DESCRIPTION
        "Cisco Firepower firmware:ComputeHostPack:rn managed
        object property"
    ::= { cfprFirmwareComputeHostPackEntry 3 }

cfprFirmwareComputeHostPackBladeBundleName OBJECT-TYPE
    SYNTAX       SnmpAdminString
    MAX-ACCESS   read-only
    STATUS       current
    DESCRIPTION
        "Cisco Firepower firmware:ComputeHostPack:bladeBundleName
        managed object property"
    ::= { cfprFirmwareComputeHostPackEntry 4 }

cfprFirmwareComputeHostPackBladeBundleVersion OBJECT-TYPE
    SYNTAX       SnmpAdminString
    MAX-ACCESS   read-only
    STATUS       current
    DESCRIPTION
        "Cisco Firepower firmware:ComputeHostPack:bladeBundleVersion
        managed object property"
    ::= { cfprFirmwareComputeHostPackEntry 5 }

cfprFirmwareComputeHostPackConfigQualifier OBJECT-TYPE
    SYNTAX       CfprFirmwareHostPackConfigQualifier
    MAX-ACCESS   read-only
    STATUS       current
    DESCRIPTION
        "Cisco Firepower firmware:ComputeHostPack:configQualifier
        managed object property"
    ::= { cfprFirmwareComputeHostPackEntry 6 }

cfprFirmwareComputeHostPackDescr OBJECT-TYPE
    SYNTAX       SnmpAdminString
    MAX-ACCESS   read-only
    STATUS       current
    DESCRIPTION
        "Cisco Firepower firmware:ComputeHostPack:descr
        managed object property"
    ::= { cfprFirmwareComputeHostPackEntry 7 }

cfprFirmwareComputeHostPackIgnoreCompCheck OBJECT-TYPE
    SYNTAX       TruthValue
    MAX-ACCESS   read-only
    STATUS       current
    DESCRIPTION
        "Cisco Firepower firmware:ComputeHostPack:ignoreCompCheck
        managed object property"
    ::= { cfprFirmwareComputeHostPackEntry 8 }

cfprFirmwareComputeHostPackIntId OBJECT-TYPE
    SYNTAX       SnmpAdminString
    MAX-ACCESS   read-only
    STATUS       current
    DESCRIPTION
        "Cisco Firepower firmware:ComputeHostPack:intId
        managed object property"
    ::= { cfprFirmwareComputeHostPackEntry 9 }

cfprFirmwareComputeHostPackMode OBJECT-TYPE
    SYNTAX       CfprFirmwarePackMode
    MAX-ACCESS   read-only
    STATUS       current
    DESCRIPTION
        "Cisco Firepower firmware:ComputeHostPack:mode
        managed object property"
    ::= { cfprFirmwareComputeHostPackEntry 10 }

cfprFirmwareComputeHostPackName OBJECT-TYPE
    SYNTAX       SnmpAdminString
    MAX-ACCESS   read-only
    STATUS       current
    DESCRIPTION
        "Cisco Firepower firmware:ComputeHostPack:name
        managed object property"
    ::= { cfprFirmwareComputeHostPackEntry 11 }

cfprFirmwareComputeHostPackPlatformBundleVersion OBJECT-TYPE
    SYNTAX       SnmpAdminString
    MAX-ACCESS   read-only
    STATUS       current
    DESCRIPTION
        "Cisco Firepower firmware:ComputeHostPack:platformBundleVersion
        managed object property"
    ::= { cfprFirmwareComputeHostPackEntry 12 }

cfprFirmwareComputeHostPackPolicyLevel OBJECT-TYPE
    SYNTAX       Gauge32
    MAX-ACCESS   read-only
    STATUS       current
    DESCRIPTION
        "Cisco Firepower firmware:ComputeHostPack:policyLevel
        managed object property"
    ::= { cfprFirmwareComputeHostPackEntry 13 }

cfprFirmwareComputeHostPackPolicyOwner OBJECT-TYPE
    SYNTAX       CfprPolicyPolicyOwner
    MAX-ACCESS   read-only
    STATUS       current
    DESCRIPTION
        "Cisco Firepower firmware:ComputeHostPack:policyOwner
        managed object property"
    ::= { cfprFirmwareComputeHostPackEntry 14 }

cfprFirmwareComputeHostPackRackBundleName OBJECT-TYPE
    SYNTAX       SnmpAdminString
    MAX-ACCESS   read-only
    STATUS       current
    DESCRIPTION
        "Cisco Firepower firmware:ComputeHostPack:rackBundleName
        managed object property"
    ::= { cfprFirmwareComputeHostPackEntry 15 }

cfprFirmwareComputeHostPackRackBundleVersion OBJECT-TYPE
    SYNTAX       SnmpAdminString
    MAX-ACCESS   read-only
    STATUS       current
    DESCRIPTION
        "Cisco Firepower firmware:ComputeHostPack:rackBundleVersion
        managed object property"
    ::= { cfprFirmwareComputeHostPackEntry 16 }

cfprFirmwareComputeHostPackStageSize OBJECT-TYPE
    SYNTAX       Gauge32
    MAX-ACCESS   read-only
    STATUS       current
    DESCRIPTION
        "Cisco Firepower firmware:ComputeHostPack:stageSize
        managed object property"
    ::= { cfprFirmwareComputeHostPackEntry 17 }

cfprFirmwareComputeHostPackUpdateTrigger OBJECT-TYPE
    SYNTAX       DateAndTime
    MAX-ACCESS   read-only
    STATUS       current
    DESCRIPTION
        "Cisco Firepower firmware:ComputeHostPack:updateTrigger
        managed object property"
    ::= { cfprFirmwareComputeHostPackEntry 18 }

cfprFirmwareComputeMgmtPackTable OBJECT-TYPE
    SYNTAX           SEQUENCE OF CfprFirmwareComputeMgmtPackEntry
    MAX-ACCESS       not-accessible
    STATUS           current
    DESCRIPTION
        "Cisco Firepower firmware:ComputeMgmtPack managed object table"
    ::= { cfprFirmwareObjects 15 }

cfprFirmwareComputeMgmtPackEntry OBJECT-TYPE
    SYNTAX           CfprFirmwareComputeMgmtPackEntry
    MAX-ACCESS       not-accessible
    STATUS           current
    DESCRIPTION
        "Entry for the cfprFirmwareComputeMgmtPackTable table."
    INDEX { cfprFirmwareComputeMgmtPackInstanceId }
    ::= { cfprFirmwareComputeMgmtPackTable 1 }

CfprFirmwareComputeMgmtPackEntry ::= SEQUENCE {
    cfprFirmwareComputeMgmtPackInstanceId                            CfprManagedObjectId,
    cfprFirmwareComputeMgmtPackDn                                    CfprManagedObjectDn,
    cfprFirmwareComputeMgmtPackRn                                    SnmpAdminString,
    cfprFirmwareComputeMgmtPackDescr                                 SnmpAdminString,
    cfprFirmwareComputeMgmtPackIgnoreCompCheck                       TruthValue,
    cfprFirmwareComputeMgmtPackIntId                                 SnmpAdminString,
    cfprFirmwareComputeMgmtPackMode                                  CfprFirmwarePackMode,
    cfprFirmwareComputeMgmtPackName                                  SnmpAdminString,
    cfprFirmwareComputeMgmtPackPolicyLevel                           Gauge32,
    cfprFirmwareComputeMgmtPackPolicyOwner                           CfprPolicyPolicyOwner,
    cfprFirmwareComputeMgmtPackStageSize                             Gauge32,
    cfprFirmwareComputeMgmtPackUpdateTrigger                         DateAndTime
}

cfprFirmwareComputeMgmtPackInstanceId OBJECT-TYPE
    SYNTAX       CfprManagedObjectId
    MAX-ACCESS   not-accessible
    STATUS       current
    DESCRIPTION
        "Instance identifier of the managed object."
    ::= { cfprFirmwareComputeMgmtPackEntry 1 }

cfprFirmwareComputeMgmtPackDn OBJECT-TYPE
    SYNTAX       CfprManagedObjectDn
    MAX-ACCESS   read-only
    STATUS       current
    DESCRIPTION
        "Cisco Firepower firmware:ComputeMgmtPack:dn managed
        object property"
    ::= { cfprFirmwareComputeMgmtPackEntry 2 }

cfprFirmwareComputeMgmtPackRn OBJECT-TYPE
    SYNTAX       SnmpAdminString
    MAX-ACCESS   read-only
    STATUS       current
    DESCRIPTION
        "Cisco Firepower firmware:ComputeMgmtPack:rn managed
        object property"
    ::= { cfprFirmwareComputeMgmtPackEntry 3 }

cfprFirmwareComputeMgmtPackDescr OBJECT-TYPE
    SYNTAX       SnmpAdminString
    MAX-ACCESS   read-only
    STATUS       current
    DESCRIPTION
        "Cisco Firepower firmware:ComputeMgmtPack:descr
        managed object property"
    ::= { cfprFirmwareComputeMgmtPackEntry 4 }

cfprFirmwareComputeMgmtPackIgnoreCompCheck OBJECT-TYPE
    SYNTAX       TruthValue
    MAX-ACCESS   read-only
    STATUS       current
    DESCRIPTION
        "Cisco Firepower firmware:ComputeMgmtPack:ignoreCompCheck
        managed object property"
    ::= { cfprFirmwareComputeMgmtPackEntry 5 }

cfprFirmwareComputeMgmtPackIntId OBJECT-TYPE
    SYNTAX       SnmpAdminString
    MAX-ACCESS   read-only
    STATUS       current
    DESCRIPTION
        "Cisco Firepower firmware:ComputeMgmtPack:intId
        managed object property"
    ::= { cfprFirmwareComputeMgmtPackEntry 6 }

cfprFirmwareComputeMgmtPackMode OBJECT-TYPE
    SYNTAX       CfprFirmwarePackMode
    MAX-ACCESS   read-only
    STATUS       current
    DESCRIPTION
        "Cisco Firepower firmware:ComputeMgmtPack:mode
        managed object property"
    ::= { cfprFirmwareComputeMgmtPackEntry 7 }

cfprFirmwareComputeMgmtPackName OBJECT-TYPE
    SYNTAX       SnmpAdminString
    MAX-ACCESS   read-only
    STATUS       current
    DESCRIPTION
        "Cisco Firepower firmware:ComputeMgmtPack:name
        managed object property"
    ::= { cfprFirmwareComputeMgmtPackEntry 8 }

cfprFirmwareComputeMgmtPackPolicyLevel OBJECT-TYPE
    SYNTAX       Gauge32
    MAX-ACCESS   read-only
    STATUS       current
    DESCRIPTION
        "Cisco Firepower firmware:ComputeMgmtPack:policyLevel
        managed object property"
    ::= { cfprFirmwareComputeMgmtPackEntry 9 }

cfprFirmwareComputeMgmtPackPolicyOwner OBJECT-TYPE
    SYNTAX       CfprPolicyPolicyOwner
    MAX-ACCESS   read-only
    STATUS       current
    DESCRIPTION
        "Cisco Firepower firmware:ComputeMgmtPack:policyOwner
        managed object property"
    ::= { cfprFirmwareComputeMgmtPackEntry 10 }

cfprFirmwareComputeMgmtPackStageSize OBJECT-TYPE
    SYNTAX       Gauge32
    MAX-ACCESS   read-only
    STATUS       current
    DESCRIPTION
        "Cisco Firepower firmware:ComputeMgmtPack:stageSize
        managed object property"
    ::= { cfprFirmwareComputeMgmtPackEntry 11 }

cfprFirmwareComputeMgmtPackUpdateTrigger OBJECT-TYPE
    SYNTAX       DateAndTime
    MAX-ACCESS   read-only
    STATUS       current
    DESCRIPTION
        "Cisco Firepower firmware:ComputeMgmtPack:updateTrigger
        managed object property"
    ::= { cfprFirmwareComputeMgmtPackEntry 12 }

cfprFirmwareConstraintTable OBJECT-TYPE
    SYNTAX           SEQUENCE OF CfprFirmwareConstraintEntry
    MAX-ACCESS       not-accessible
    STATUS           current
    DESCRIPTION
        "Cisco Firepower firmware:Constraint managed object table"
    ::= { cfprFirmwareObjects 16 }

cfprFirmwareConstraintEntry OBJECT-TYPE
    SYNTAX           CfprFirmwareConstraintEntry
    MAX-ACCESS       not-accessible
    STATUS           current
    DESCRIPTION
        "Entry for the cfprFirmwareConstraintTable table."
    INDEX { cfprFirmwareConstraintInstanceId }
    ::= { cfprFirmwareConstraintTable 1 }

CfprFirmwareConstraintEntry ::= SEQUENCE {
    cfprFirmwareConstraintInstanceId                                 CfprManagedObjectId,
    cfprFirmwareConstraintDn                                         CfprManagedObjectDn,
    cfprFirmwareConstraintRn                                         SnmpAdminString,
    cfprFirmwareConstraintFeature                                    SnmpAdminString,
    cfprFirmwareConstraintMinBiosVersion                             SnmpAdminString,
    cfprFirmwareConstraintMinCimcVersion                             SnmpAdminString
}

cfprFirmwareConstraintInstanceId OBJECT-TYPE
    SYNTAX       CfprManagedObjectId
    MAX-ACCESS   not-accessible
    STATUS       current
    DESCRIPTION
        "Instance identifier of the managed object."
    ::= { cfprFirmwareConstraintEntry 1 }

cfprFirmwareConstraintDn OBJECT-TYPE
    SYNTAX       CfprManagedObjectDn
    MAX-ACCESS   read-only
    STATUS       current
    DESCRIPTION
        "Cisco Firepower firmware:Constraint:dn managed object property"
    ::= { cfprFirmwareConstraintEntry 2 }

cfprFirmwareConstraintRn OBJECT-TYPE
    SYNTAX       SnmpAdminString
    MAX-ACCESS   read-only
    STATUS       current
    DESCRIPTION
        "Cisco Firepower firmware:Constraint:rn managed object property"
    ::= { cfprFirmwareConstraintEntry 3 }

cfprFirmwareConstraintFeature OBJECT-TYPE
    SYNTAX       SnmpAdminString
    MAX-ACCESS   read-only
    STATUS       current
    DESCRIPTION
        "Cisco Firepower firmware:Constraint:feature managed
        object property"
    ::= { cfprFirmwareConstraintEntry 4 }

cfprFirmwareConstraintMinBiosVersion OBJECT-TYPE
    SYNTAX       SnmpAdminString
    MAX-ACCESS   read-only
    STATUS       current
    DESCRIPTION
        "Cisco Firepower firmware:Constraint:minBiosVersion
        managed object property"
    ::= { cfprFirmwareConstraintEntry 5 }

cfprFirmwareConstraintMinCimcVersion OBJECT-TYPE
    SYNTAX       SnmpAdminString
    MAX-ACCESS   read-only
    STATUS       current
    DESCRIPTION
        "Cisco Firepower firmware:Constraint:minCimcVersion
        managed object property"
    ::= { cfprFirmwareConstraintEntry 6 }

cfprFirmwareConstraintsTable OBJECT-TYPE
    SYNTAX           SEQUENCE OF CfprFirmwareConstraintsEntry
    MAX-ACCESS       not-accessible
    STATUS           current
    DESCRIPTION
        "Cisco Firepower firmware:Constraints managed object table"
    ::= { cfprFirmwareObjects 17 }

cfprFirmwareConstraintsEntry OBJECT-TYPE
    SYNTAX           CfprFirmwareConstraintsEntry
    MAX-ACCESS       not-accessible
    STATUS           current
    DESCRIPTION
        "Entry for the cfprFirmwareConstraintsTable table."
    INDEX { cfprFirmwareConstraintsInstanceId }
    ::= { cfprFirmwareConstraintsTable 1 }

CfprFirmwareConstraintsEntry ::= SEQUENCE {
    cfprFirmwareConstraintsInstanceId                                CfprManagedObjectId,
    cfprFirmwareConstraintsDn                                        CfprManagedObjectDn,
    cfprFirmwareConstraintsRn                                        SnmpAdminString
}

cfprFirmwareConstraintsInstanceId OBJECT-TYPE
    SYNTAX       CfprManagedObjectId
    MAX-ACCESS   not-accessible
    STATUS       current
    DESCRIPTION
        "Instance identifier of the managed object."
    ::= { cfprFirmwareConstraintsEntry 1 }

cfprFirmwareConstraintsDn OBJECT-TYPE
    SYNTAX       CfprManagedObjectDn
    MAX-ACCESS   read-only
    STATUS       current
    DESCRIPTION
        "Cisco Firepower firmware:Constraints:dn managed object property"
    ::= { cfprFirmwareConstraintsEntry 2 }

cfprFirmwareConstraintsRn OBJECT-TYPE
    SYNTAX       SnmpAdminString
    MAX-ACCESS   read-only
    STATUS       current
    DESCRIPTION
        "Cisco Firepower firmware:Constraints:rn managed object property"
    ::= { cfprFirmwareConstraintsEntry 3 }

cfprFirmwareCspAppListTable OBJECT-TYPE
    SYNTAX           SEQUENCE OF CfprFirmwareCspAppListEntry
    MAX-ACCESS       not-accessible
    STATUS           current
    DESCRIPTION
        "Cisco Firepower firmware:CspAppList managed object table"
    ::= { cfprFirmwareObjects 61 }

cfprFirmwareCspAppListEntry OBJECT-TYPE
    SYNTAX           CfprFirmwareCspAppListEntry
    MAX-ACCESS       not-accessible
    STATUS           current
    DESCRIPTION
        "Entry for the cfprFirmwareCspAppListTable table."
    INDEX { cfprFirmwareCspAppListInstanceId }
    ::= { cfprFirmwareCspAppListTable 1 }

CfprFirmwareCspAppListEntry ::= SEQUENCE {
    cfprFirmwareCspAppListInstanceId                                 CfprManagedObjectId,
    cfprFirmwareCspAppListDn                                         CfprManagedObjectDn,
    cfprFirmwareCspAppListRn                                         SnmpAdminString,
    cfprFirmwareCspAppListName                                       SnmpAdminString
}

cfprFirmwareCspAppListInstanceId OBJECT-TYPE
    SYNTAX       CfprManagedObjectId
    MAX-ACCESS   not-accessible
    STATUS       current
    DESCRIPTION
        "Instance identifier of the managed object."
    ::= { cfprFirmwareCspAppListEntry 1 }

cfprFirmwareCspAppListDn OBJECT-TYPE
    SYNTAX       CfprManagedObjectDn
    MAX-ACCESS   read-only
    STATUS       current
    DESCRIPTION
        "Cisco Firepower firmware:CspAppList:dn managed object property"
    ::= { cfprFirmwareCspAppListEntry 2 }

cfprFirmwareCspAppListRn OBJECT-TYPE
    SYNTAX       SnmpAdminString
    MAX-ACCESS   read-only
    STATUS       current
    DESCRIPTION
        "Cisco Firepower firmware:CspAppList:rn managed object property"
    ::= { cfprFirmwareCspAppListEntry 3 }

cfprFirmwareCspAppListName OBJECT-TYPE
    SYNTAX       SnmpAdminString
    MAX-ACCESS   read-only
    STATUS       current
    DESCRIPTION
        "Cisco Firepower firmware:CspAppList:name managed object property"
    ::= { cfprFirmwareCspAppListEntry 4 }

cfprFirmwareCspVersionTable OBJECT-TYPE
    SYNTAX           SEQUENCE OF CfprFirmwareCspVersionEntry
    MAX-ACCESS       not-accessible
    STATUS           current
    DESCRIPTION
        "Cisco Firepower firmware:CspVersion managed object table"
    ::= { cfprFirmwareObjects 62 }

cfprFirmwareCspVersionEntry OBJECT-TYPE
    SYNTAX           CfprFirmwareCspVersionEntry
    MAX-ACCESS       not-accessible
    STATUS           current
    DESCRIPTION
        "Entry for the cfprFirmwareCspVersionTable table."
    INDEX { cfprFirmwareCspVersionInstanceId }
    ::= { cfprFirmwareCspVersionTable 1 }

CfprFirmwareCspVersionEntry ::= SEQUENCE {
    cfprFirmwareCspVersionInstanceId                                 CfprManagedObjectId,
    cfprFirmwareCspVersionDn                                         CfprManagedObjectDn,
    cfprFirmwareCspVersionRn                                         SnmpAdminString,
    cfprFirmwareCspVersionAppName                                    SnmpAdminString,
    cfprFirmwareCspVersionFromVersion                                SnmpAdminString,
    cfprFirmwareCspVersionName                                       SnmpAdminString,
    cfprFirmwareCspVersionSecModelSupported                          SnmpAdminString,
    cfprFirmwareCspVersionSupportMode                                CfprFirmwareSupportedModeType,
    cfprFirmwareCspVersionToVersion                                  SnmpAdminString
}

cfprFirmwareCspVersionInstanceId OBJECT-TYPE
    SYNTAX       CfprManagedObjectId
    MAX-ACCESS   not-accessible
    STATUS       current
    DESCRIPTION
        "Instance identifier of the managed object."
    ::= { cfprFirmwareCspVersionEntry 1 }

cfprFirmwareCspVersionDn OBJECT-TYPE
    SYNTAX       CfprManagedObjectDn
    MAX-ACCESS   read-only
    STATUS       current
    DESCRIPTION
        "Cisco Firepower firmware:CspVersion:dn managed object property"
    ::= { cfprFirmwareCspVersionEntry 2 }

cfprFirmwareCspVersionRn OBJECT-TYPE
    SYNTAX       SnmpAdminString
    MAX-ACCESS   read-only
    STATUS       current
    DESCRIPTION
        "Cisco Firepower firmware:CspVersion:rn managed object property"
    ::= { cfprFirmwareCspVersionEntry 3 }

cfprFirmwareCspVersionAppName OBJECT-TYPE
    SYNTAX       SnmpAdminString
    MAX-ACCESS   read-only
    STATUS       current
    DESCRIPTION
        "Cisco Firepower firmware:CspVersion:appName managed
        object property"
    ::= { cfprFirmwareCspVersionEntry 4 }

cfprFirmwareCspVersionFromVersion OBJECT-TYPE
    SYNTAX       SnmpAdminString
    MAX-ACCESS   read-only
    STATUS       current
    DESCRIPTION
        "Cisco Firepower firmware:CspVersion:fromVersion
        managed object property"
    ::= { cfprFirmwareCspVersionEntry 5 }

cfprFirmwareCspVersionName OBJECT-TYPE
    SYNTAX       SnmpAdminString
    MAX-ACCESS   read-only
    STATUS       current
    DESCRIPTION
        "Cisco Firepower firmware:CspVersion:name managed object property"
    ::= { cfprFirmwareCspVersionEntry 6 }

cfprFirmwareCspVersionSecModelSupported OBJECT-TYPE
    SYNTAX       SnmpAdminString
    MAX-ACCESS   read-only
    STATUS       current
    DESCRIPTION
        "Cisco Firepower firmware:CspVersion:secModelSupported
        managed object property"
    ::= { cfprFirmwareCspVersionEntry 7 }

cfprFirmwareCspVersionSupportMode OBJECT-TYPE
    SYNTAX       CfprFirmwareSupportedModeType
    MAX-ACCESS   read-only
    STATUS       current
    DESCRIPTION
        "Cisco Firepower firmware:CspVersion:supportMode
        managed object property"
    ::= { cfprFirmwareCspVersionEntry 8 }

cfprFirmwareCspVersionToVersion OBJECT-TYPE
    SYNTAX       SnmpAdminString
    MAX-ACCESS   read-only
    STATUS       current
    DESCRIPTION
        "Cisco Firepower firmware:CspVersion:toVersion
        managed object property"
    ::= { cfprFirmwareCspVersionEntry 9 }

cfprFirmwareDependencyTable OBJECT-TYPE
    SYNTAX           SEQUENCE OF CfprFirmwareDependencyEntry
    MAX-ACCESS       not-accessible
    STATUS           current
    DESCRIPTION
        "Cisco Firepower firmware:Dependency managed object table"
    ::= { cfprFirmwareObjects 18 }

cfprFirmwareDependencyEntry OBJECT-TYPE
    SYNTAX           CfprFirmwareDependencyEntry
    MAX-ACCESS       not-accessible
    STATUS           current
    DESCRIPTION
        "Entry for the cfprFirmwareDependencyTable table."
    INDEX { cfprFirmwareDependencyInstanceId }
    ::= { cfprFirmwareDependencyTable 1 }

CfprFirmwareDependencyEntry ::= SEQUENCE {
    cfprFirmwareDependencyInstanceId                                 CfprManagedObjectId,
    cfprFirmwareDependencyDn                                         CfprManagedObjectDn,
    cfprFirmwareDependencyRn                                         SnmpAdminString,
    cfprFirmwareDependencyEp                                         CfprFirmwareType,
    cfprFirmwareDependencyHwModel                                    SnmpAdminString,
    cfprFirmwareDependencyHwRevision                                 SnmpAdminString,
    cfprFirmwareDependencyHwVendor                                   SnmpAdminString,
    cfprFirmwareDependencyInvTag                                     SnmpAdminString,
    cfprFirmwareDependencyMaxVer                                     SnmpAdminString,
    cfprFirmwareDependencyMinVer                                     SnmpAdminString,
    cfprFirmwareDependencyRelationship                               CfprFirmwareDependencyRelationship,
    cfprFirmwareDependencyScope                                      CfprFirmwareDependencyScope,
    cfprFirmwareDependencySensitivity                                CfprFirmwareDependencySensitivity,
    cfprFirmwareDependencyValidationStatus                           CfprFirmwareVerifyPackStatus
}

cfprFirmwareDependencyInstanceId OBJECT-TYPE
    SYNTAX       CfprManagedObjectId
    MAX-ACCESS   not-accessible
    STATUS       current
    DESCRIPTION
        "Instance identifier of the managed object."
    ::= { cfprFirmwareDependencyEntry 1 }

cfprFirmwareDependencyDn OBJECT-TYPE
    SYNTAX       CfprManagedObjectDn
    MAX-ACCESS   read-only
    STATUS       current
    DESCRIPTION
        "Cisco Firepower firmware:Dependency:dn managed object property"
    ::= { cfprFirmwareDependencyEntry 2 }

cfprFirmwareDependencyRn OBJECT-TYPE
    SYNTAX       SnmpAdminString
    MAX-ACCESS   read-only
    STATUS       current
    DESCRIPTION
        "Cisco Firepower firmware:Dependency:rn managed object property"
    ::= { cfprFirmwareDependencyEntry 3 }

cfprFirmwareDependencyEp OBJECT-TYPE
    SYNTAX       CfprFirmwareType
    MAX-ACCESS   read-only
    STATUS       current
    DESCRIPTION
        "Cisco Firepower firmware:Dependency:ep managed object property"
    ::= { cfprFirmwareDependencyEntry 4 }

cfprFirmwareDependencyHwModel OBJECT-TYPE
    SYNTAX       SnmpAdminString
    MAX-ACCESS   read-only
    STATUS       current
    DESCRIPTION
        "Cisco Firepower firmware:Dependency:hwModel managed
        object property"
    ::= { cfprFirmwareDependencyEntry 5 }

cfprFirmwareDependencyHwRevision OBJECT-TYPE
    SYNTAX       SnmpAdminString
    MAX-ACCESS   read-only
    STATUS       current
    DESCRIPTION
        "Cisco Firepower firmware:Dependency:hwRevision
        managed object property"
    ::= { cfprFirmwareDependencyEntry 6 }

cfprFirmwareDependencyHwVendor OBJECT-TYPE
    SYNTAX       SnmpAdminString
    MAX-ACCESS   read-only
    STATUS       current
    DESCRIPTION
        "Cisco Firepower firmware:Dependency:hwVendor managed
        object property"
    ::= { cfprFirmwareDependencyEntry 7 }

cfprFirmwareDependencyInvTag OBJECT-TYPE
    SYNTAX       SnmpAdminString
    MAX-ACCESS   read-only
    STATUS       current
    DESCRIPTION
        "Cisco Firepower firmware:Dependency:invTag managed
        object property"
    ::= { cfprFirmwareDependencyEntry 8 }

cfprFirmwareDependencyMaxVer OBJECT-TYPE
    SYNTAX       SnmpAdminString
    MAX-ACCESS   read-only
    STATUS       current
    DESCRIPTION
        "Cisco Firepower firmware:Dependency:maxVer managed
        object property"
    ::= { cfprFirmwareDependencyEntry 9 }

cfprFirmwareDependencyMinVer OBJECT-TYPE
    SYNTAX       SnmpAdminString
    MAX-ACCESS   read-only
    STATUS       current
    DESCRIPTION
        "Cisco Firepower firmware:Dependency:minVer managed
        object property"
    ::= { cfprFirmwareDependencyEntry 10 }

cfprFirmwareDependencyRelationship OBJECT-TYPE
    SYNTAX       CfprFirmwareDependencyRelationship
    MAX-ACCESS   read-only
    STATUS       current
    DESCRIPTION
        "Cisco Firepower firmware:Dependency:relationship
        managed object property"
    ::= { cfprFirmwareDependencyEntry 11 }

cfprFirmwareDependencyScope OBJECT-TYPE
    SYNTAX       CfprFirmwareDependencyScope
    MAX-ACCESS   read-only
    STATUS       current
    DESCRIPTION
        "Cisco Firepower firmware:Dependency:scope managed
        object property"
    ::= { cfprFirmwareDependencyEntry 12 }

cfprFirmwareDependencySensitivity OBJECT-TYPE
    SYNTAX       CfprFirmwareDependencySensitivity
    MAX-ACCESS   read-only
    STATUS       current
    DESCRIPTION
        "Cisco Firepower firmware:Dependency:sensitivity
        managed object property"
    ::= { cfprFirmwareDependencyEntry 13 }

cfprFirmwareDependencyValidationStatus OBJECT-TYPE
    SYNTAX       CfprFirmwareVerifyPackStatus
    MAX-ACCESS   read-only
    STATUS       current
    DESCRIPTION
        "Cisco Firepower firmware:Dependency:validationStatus
        managed object property"
    ::= { cfprFirmwareDependencyEntry 14 }

cfprFirmwareDistCspBlackListTable OBJECT-TYPE
    SYNTAX           SEQUENCE OF CfprFirmwareDistCspBlackListEntry
    MAX-ACCESS       not-accessible
    STATUS           current
    DESCRIPTION
        "Cisco Firepower firmware:DistCspBlackList managed object table"
    ::= { cfprFirmwareObjects 63 }

cfprFirmwareDistCspBlackListEntry OBJECT-TYPE
    SYNTAX           CfprFirmwareDistCspBlackListEntry
    MAX-ACCESS       not-accessible
    STATUS           current
    DESCRIPTION
        "Entry for the cfprFirmwareDistCspBlackListTable table."
    INDEX { cfprFirmwareDistCspBlackListInstanceId }
    ::= { cfprFirmwareDistCspBlackListTable 1 }

CfprFirmwareDistCspBlackListEntry ::= SEQUENCE {
    cfprFirmwareDistCspBlackListInstanceId                           CfprManagedObjectId,
    cfprFirmwareDistCspBlackListDn                                   CfprManagedObjectDn,
    cfprFirmwareDistCspBlackListRn                                   SnmpAdminString,
    cfprFirmwareDistCspBlackListName                                 SnmpAdminString,
    cfprFirmwareDistCspBlackListTimeStamp                            DateAndTime,
    cfprFirmwareDistCspBlackListVersion                              SnmpAdminString
}

cfprFirmwareDistCspBlackListInstanceId OBJECT-TYPE
    SYNTAX       CfprManagedObjectId
    MAX-ACCESS   not-accessible
    STATUS       current
    DESCRIPTION
        "Instance identifier of the managed object."
    ::= { cfprFirmwareDistCspBlackListEntry 1 }

cfprFirmwareDistCspBlackListDn OBJECT-TYPE
    SYNTAX       CfprManagedObjectDn
    MAX-ACCESS   read-only
    STATUS       current
    DESCRIPTION
        "Cisco Firepower firmware:DistCspBlackList:dn managed
        object property"
    ::= { cfprFirmwareDistCspBlackListEntry 2 }

cfprFirmwareDistCspBlackListRn OBJECT-TYPE
    SYNTAX       SnmpAdminString
    MAX-ACCESS   read-only
    STATUS       current
    DESCRIPTION
        "Cisco Firepower firmware:DistCspBlackList:rn managed
        object property"
    ::= { cfprFirmwareDistCspBlackListEntry 3 }

cfprFirmwareDistCspBlackListName OBJECT-TYPE
    SYNTAX       SnmpAdminString
    MAX-ACCESS   read-only
    STATUS       current
    DESCRIPTION
        "Cisco Firepower firmware:DistCspBlackList:name
        managed object property"
    ::= { cfprFirmwareDistCspBlackListEntry 4 }

cfprFirmwareDistCspBlackListTimeStamp OBJECT-TYPE
    SYNTAX       DateAndTime
    MAX-ACCESS   read-only
    STATUS       current
    DESCRIPTION
        "Cisco Firepower firmware:DistCspBlackList:timeStamp
        managed object property"
    ::= { cfprFirmwareDistCspBlackListEntry 5 }

cfprFirmwareDistCspBlackListVersion OBJECT-TYPE
    SYNTAX       SnmpAdminString
    MAX-ACCESS   read-only
    STATUS       current
    DESCRIPTION
        "Cisco Firepower firmware:DistCspBlackList:version
        managed object property"
    ::= { cfprFirmwareDistCspBlackListEntry 6 }

cfprFirmwareDistImageTable OBJECT-TYPE
    SYNTAX           SEQUENCE OF CfprFirmwareDistImageEntry
    MAX-ACCESS       not-accessible
    STATUS           current
    DESCRIPTION
        "Cisco Firepower firmware:DistImage managed object table"
    ::= { cfprFirmwareObjects 19 }

cfprFirmwareDistImageEntry OBJECT-TYPE
    SYNTAX           CfprFirmwareDistImageEntry
    MAX-ACCESS       not-accessible
    STATUS           current
    DESCRIPTION
        "Entry for the cfprFirmwareDistImageTable table."
    INDEX { cfprFirmwareDistImageInstanceId }
    ::= { cfprFirmwareDistImageTable 1 }

CfprFirmwareDistImageEntry ::= SEQUENCE {
    cfprFirmwareDistImageInstanceId                                  CfprManagedObjectId,
    cfprFirmwareDistImageDn                                          CfprManagedObjectDn,
    cfprFirmwareDistImageRn                                          SnmpAdminString,
    cfprFirmwareDistImageImageDeleted                                CfprFirmwareImageDeleted,
    cfprFirmwareDistImageName                                        SnmpAdminString,
    cfprFirmwareDistImageType                                        CfprFirmwareType
}

cfprFirmwareDistImageInstanceId OBJECT-TYPE
    SYNTAX       CfprManagedObjectId
    MAX-ACCESS   not-accessible
    STATUS       current
    DESCRIPTION
        "Instance identifier of the managed object."
    ::= { cfprFirmwareDistImageEntry 1 }

cfprFirmwareDistImageDn OBJECT-TYPE
    SYNTAX       CfprManagedObjectDn
    MAX-ACCESS   read-only
    STATUS       current
    DESCRIPTION
        "Cisco Firepower firmware:DistImage:dn managed object property"
    ::= { cfprFirmwareDistImageEntry 2 }

cfprFirmwareDistImageRn OBJECT-TYPE
    SYNTAX       SnmpAdminString
    MAX-ACCESS   read-only
    STATUS       current
    DESCRIPTION
        "Cisco Firepower firmware:DistImage:rn managed object property"
    ::= { cfprFirmwareDistImageEntry 3 }

cfprFirmwareDistImageImageDeleted OBJECT-TYPE
    SYNTAX       CfprFirmwareImageDeleted
    MAX-ACCESS   read-only
    STATUS       current
    DESCRIPTION
        "Cisco Firepower firmware:DistImage:imageDeleted
        managed object property"
    ::= { cfprFirmwareDistImageEntry 4 }

cfprFirmwareDistImageName OBJECT-TYPE
    SYNTAX       SnmpAdminString
    MAX-ACCESS   read-only
    STATUS       current
    DESCRIPTION
        "Cisco Firepower firmware:DistImage:name managed object property"
    ::= { cfprFirmwareDistImageEntry 5 }

cfprFirmwareDistImageType OBJECT-TYPE
    SYNTAX       CfprFirmwareType
    MAX-ACCESS   read-only
    STATUS       current
    DESCRIPTION
        "Cisco Firepower firmware:DistImage:type managed object property"
    ::= { cfprFirmwareDistImageEntry 6 }

cfprFirmwareDistributableTable OBJECT-TYPE
    SYNTAX           SEQUENCE OF CfprFirmwareDistributableEntry
    MAX-ACCESS       not-accessible
    STATUS           current
    DESCRIPTION
        "Cisco Firepower firmware:Distributable managed object table"
    ::= { cfprFirmwareObjects 20 }

cfprFirmwareDistributableEntry OBJECT-TYPE
    SYNTAX           CfprFirmwareDistributableEntry
    MAX-ACCESS       not-accessible
    STATUS           current
    DESCRIPTION
        "Entry for the cfprFirmwareDistributableTable table."
    INDEX { cfprFirmwareDistributableInstanceId }
    ::= { cfprFirmwareDistributableTable 1 }

CfprFirmwareDistributableEntry ::= SEQUENCE {
    cfprFirmwareDistributableInstanceId                              CfprManagedObjectId,
    cfprFirmwareDistributableDn                                      CfprManagedObjectDn,
    cfprFirmwareDistributableRn                                      SnmpAdminString,
    cfprFirmwareDistributableAdminState                              CfprFirmwareAdminState,
    cfprFirmwareDistributableCompleteness                            CfprFirmwareCompleteness,
    cfprFirmwareDistributableDescr                                   SnmpAdminString,
    cfprFirmwareDistributableFsmDescr                                SnmpAdminString,
    cfprFirmwareDistributableFsmPrev                                 SnmpAdminString,
    cfprFirmwareDistributableFsmProgr                                Gauge32,
    cfprFirmwareDistributableFsmRmtInvErrCode                        Gauge32,
    cfprFirmwareDistributableFsmRmtInvErrDescr                       SnmpAdminString,
    cfprFirmwareDistributableFsmRmtInvRslt                           CfprConditionRemoteInvRslt,
    cfprFirmwareDistributableFsmStageDescr                           SnmpAdminString,
    cfprFirmwareDistributableFsmStamp                                DateAndTime,
    cfprFirmwareDistributableFsmStatus                               SnmpAdminString,
    cfprFirmwareDistributableFsmTry                                  Gauge32,
    cfprFirmwareDistributableImagePresence                           CfprFirmwareImagePresence,
    cfprFirmwareDistributableIntId                                   SnmpAdminString,
    cfprFirmwareDistributableInvTag                                  SnmpAdminString,
    cfprFirmwareDistributableModel                                   SnmpAdminString,
    cfprFirmwareDistributableName                                    SnmpAdminString,
    cfprFirmwareDistributablePolicyLevel                             Gauge32,
    cfprFirmwareDistributablePolicyOwner                             CfprPolicyPolicyOwner,
    cfprFirmwareDistributableTransferState                           CfprFirmwareTransferState,
    cfprFirmwareDistributableType                                    CfprFirmwareDistributableType,
    cfprFirmwareDistributableVendor                                  SnmpAdminString,
    cfprFirmwareDistributableVersion                                 SnmpAdminString,
    cfprFirmwareDistributableBuildDate                               SnmpAdminString,
    cfprFirmwareDistributableDisplayFlag                             TruthValue,
    cfprFirmwareDistributableSupportsMultiInstance                   TruthValue,
    cfprFirmwareDistributableTimeStamp                               DateAndTime
}

cfprFirmwareDistributableInstanceId OBJECT-TYPE
    SYNTAX       CfprManagedObjectId
    MAX-ACCESS   not-accessible
    STATUS       current
    DESCRIPTION
        "Instance identifier of the managed object."
    ::= { cfprFirmwareDistributableEntry 1 }

cfprFirmwareDistributableDn OBJECT-TYPE
    SYNTAX       CfprManagedObjectDn
    MAX-ACCESS   read-only
    STATUS       current
    DESCRIPTION
        "Cisco Firepower firmware:Distributable:dn managed
        object property"
    ::= { cfprFirmwareDistributableEntry 2 }

cfprFirmwareDistributableRn OBJECT-TYPE
    SYNTAX       SnmpAdminString
    MAX-ACCESS   read-only
    STATUS       current
    DESCRIPTION
        "Cisco Firepower firmware:Distributable:rn managed
        object property"
    ::= { cfprFirmwareDistributableEntry 3 }

cfprFirmwareDistributableAdminState OBJECT-TYPE
    SYNTAX       CfprFirmwareAdminState
    MAX-ACCESS   read-only
    STATUS       current
    DESCRIPTION
        "Cisco Firepower firmware:Distributable:adminState
        managed object property"
    ::= { cfprFirmwareDistributableEntry 4 }

cfprFirmwareDistributableCompleteness OBJECT-TYPE
    SYNTAX       CfprFirmwareCompleteness
    MAX-ACCESS   read-only
    STATUS       current
    DESCRIPTION
        "Cisco Firepower firmware:Distributable:completeness
        managed object property"
    ::= { cfprFirmwareDistributableEntry 5 }

cfprFirmwareDistributableDescr OBJECT-TYPE
    SYNTAX       SnmpAdminString
    MAX-ACCESS   read-only
    STATUS       current
    DESCRIPTION
        "Cisco Firepower firmware:Distributable:descr managed
        object property"
    ::= { cfprFirmwareDistributableEntry 6 }

cfprFirmwareDistributableFsmDescr OBJECT-TYPE
    SYNTAX       SnmpAdminString
    MAX-ACCESS   read-only
    STATUS       current
    DESCRIPTION
        "Cisco Firepower firmware:Distributable:fsmDescr
        managed object property"
    ::= { cfprFirmwareDistributableEntry 7 }

cfprFirmwareDistributableFsmPrev OBJECT-TYPE
    SYNTAX       SnmpAdminString
    MAX-ACCESS   read-only
    STATUS       current
    DESCRIPTION
        "Cisco Firepower firmware:Distributable:fsmPrev
        managed object property"
    ::= { cfprFirmwareDistributableEntry 8 }

cfprFirmwareDistributableFsmProgr OBJECT-TYPE
    SYNTAX       Gauge32
    MAX-ACCESS   read-only
    STATUS       current
    DESCRIPTION
        "Cisco Firepower firmware:Distributable:fsmProgr
        managed object property"
    ::= { cfprFirmwareDistributableEntry 9 }

cfprFirmwareDistributableFsmRmtInvErrCode OBJECT-TYPE
    SYNTAX       Gauge32
    MAX-ACCESS   read-only
    STATUS       current
    DESCRIPTION
        "Cisco Firepower firmware:Distributable:fsmRmtInvErrCode
        managed object property"
    ::= { cfprFirmwareDistributableEntry 10 }

cfprFirmwareDistributableFsmRmtInvErrDescr OBJECT-TYPE
    SYNTAX       SnmpAdminString
    MAX-ACCESS   read-only
    STATUS       current
    DESCRIPTION
        "Cisco Firepower firmware:Distributable:fsmRmtInvErrDescr
        managed object property"
    ::= { cfprFirmwareDistributableEntry 11 }

cfprFirmwareDistributableFsmRmtInvRslt OBJECT-TYPE
    SYNTAX       CfprConditionRemoteInvRslt
    MAX-ACCESS   read-only
    STATUS       current
    DESCRIPTION
        "Cisco Firepower firmware:Distributable:fsmRmtInvRslt
        managed object property"
    ::= { cfprFirmwareDistributableEntry 12 }

cfprFirmwareDistributableFsmStageDescr OBJECT-TYPE
    SYNTAX       SnmpAdminString
    MAX-ACCESS   read-only
    STATUS       current
    DESCRIPTION
        "Cisco Firepower firmware:Distributable:fsmStageDescr
        managed object property"
    ::= { cfprFirmwareDistributableEntry 13 }

cfprFirmwareDistributableFsmStamp OBJECT-TYPE
    SYNTAX       DateAndTime
    MAX-ACCESS   read-only
    STATUS       current
    DESCRIPTION
        "Cisco Firepower firmware:Distributable:fsmStamp
        managed object property"
    ::= { cfprFirmwareDistributableEntry 14 }

cfprFirmwareDistributableFsmStatus OBJECT-TYPE
    SYNTAX       SnmpAdminString
    MAX-ACCESS   read-only
    STATUS       current
    DESCRIPTION
        "Cisco Firepower firmware:Distributable:fsmStatus
        managed object property"
    ::= { cfprFirmwareDistributableEntry 15 }

cfprFirmwareDistributableFsmTry OBJECT-TYPE
    SYNTAX       Gauge32
    MAX-ACCESS   read-only
    STATUS       current
    DESCRIPTION
        "Cisco Firepower firmware:Distributable:fsmTry
        managed object property"
    ::= { cfprFirmwareDistributableEntry 16 }

cfprFirmwareDistributableImagePresence OBJECT-TYPE
    SYNTAX       CfprFirmwareImagePresence
    MAX-ACCESS   read-only
    STATUS       current
    DESCRIPTION
        "Cisco Firepower firmware:Distributable:imagePresence
        managed object property"
    ::= { cfprFirmwareDistributableEntry 17 }

cfprFirmwareDistributableIntId OBJECT-TYPE
    SYNTAX       SnmpAdminString
    MAX-ACCESS   read-only
    STATUS       current
    DESCRIPTION
        "Cisco Firepower firmware:Distributable:intId managed
        object property"
    ::= { cfprFirmwareDistributableEntry 18 }

cfprFirmwareDistributableInvTag OBJECT-TYPE
    SYNTAX       SnmpAdminString
    MAX-ACCESS   read-only
    STATUS       current
    DESCRIPTION
        "Cisco Firepower firmware:Distributable:invTag
        managed object property"
    ::= { cfprFirmwareDistributableEntry 19 }

cfprFirmwareDistributableModel OBJECT-TYPE
    SYNTAX       SnmpAdminString
    MAX-ACCESS   read-only
    STATUS       current
    DESCRIPTION
        "Cisco Firepower firmware:Distributable:model managed
        object property"
    ::= { cfprFirmwareDistributableEntry 20 }

cfprFirmwareDistributableName OBJECT-TYPE
    SYNTAX       SnmpAdminString
    MAX-ACCESS   read-only
    STATUS       current
    DESCRIPTION
        "Cisco Firepower firmware:Distributable:name managed
        object property"
    ::= { cfprFirmwareDistributableEntry 21 }

cfprFirmwareDistributablePolicyLevel OBJECT-TYPE
    SYNTAX       Gauge32
    MAX-ACCESS   read-only
    STATUS       current
    DESCRIPTION
        "Cisco Firepower firmware:Distributable:policyLevel
        managed object property"
    ::= { cfprFirmwareDistributableEntry 22 }

cfprFirmwareDistributablePolicyOwner OBJECT-TYPE
    SYNTAX       CfprPolicyPolicyOwner
    MAX-ACCESS   read-only
    STATUS       current
    DESCRIPTION
        "Cisco Firepower firmware:Distributable:policyOwner
        managed object property"
    ::= { cfprFirmwareDistributableEntry 23 }

cfprFirmwareDistributableTransferState OBJECT-TYPE
    SYNTAX       CfprFirmwareTransferState
    MAX-ACCESS   read-only
    STATUS       current
    DESCRIPTION
        "Cisco Firepower firmware:Distributable:transferState
        managed object property"
    ::= { cfprFirmwareDistributableEntry 24 }

cfprFirmwareDistributableType OBJECT-TYPE
    SYNTAX       CfprFirmwareDistributableType
    MAX-ACCESS   read-only
    STATUS       current
    DESCRIPTION
        "Cisco Firepower firmware:Distributable:type managed
        object property"
    ::= { cfprFirmwareDistributableEntry 25 }

cfprFirmwareDistributableVendor OBJECT-TYPE
    SYNTAX       SnmpAdminString
    MAX-ACCESS   read-only
    STATUS       current
    DESCRIPTION
        "Cisco Firepower firmware:Distributable:vendor
        managed object property"
    ::= { cfprFirmwareDistributableEntry 26 }

cfprFirmwareDistributableVersion OBJECT-TYPE
    SYNTAX       SnmpAdminString
    MAX-ACCESS   read-only
    STATUS       current
    DESCRIPTION
        "Cisco Firepower firmware:Distributable:version
        managed object property"
    ::= { cfprFirmwareDistributableEntry 27 }

cfprFirmwareDistributableBuildDate OBJECT-TYPE
    SYNTAX       SnmpAdminString
    MAX-ACCESS   read-only
    STATUS       current
    DESCRIPTION
        "Cisco Firepower firmware:Distributable:buildDate
        managed object property"
    ::= { cfprFirmwareDistributableEntry 28 }

cfprFirmwareDistributableDisplayFlag OBJECT-TYPE
    SYNTAX       TruthValue
    MAX-ACCESS   read-only
    STATUS       current
    DESCRIPTION
        "Cisco Firepower firmware:Distributable:displayFlag
        managed object property"
    ::= { cfprFirmwareDistributableEntry 29 }

cfprFirmwareDistributableSupportsMultiInstance OBJECT-TYPE
    SYNTAX       TruthValue
    MAX-ACCESS   read-only
    STATUS       current
    DESCRIPTION
        "Cisco Firepower firmware:Distributable:supportsMultiInstance
        managed object property"
    ::= { cfprFirmwareDistributableEntry 30 }

cfprFirmwareDistributableTimeStamp OBJECT-TYPE
    SYNTAX       DateAndTime
    MAX-ACCESS   read-only
    STATUS       current
    DESCRIPTION
        "Cisco Firepower firmware:Distributable:timeStamp
        managed object property"
    ::= { cfprFirmwareDistributableEntry 31 }

cfprFirmwareDistributableFsmTable OBJECT-TYPE
    SYNTAX           SEQUENCE OF CfprFirmwareDistributableFsmEntry
    MAX-ACCESS       not-accessible
    STATUS           current
    DESCRIPTION
        "Cisco Firepower firmware:DistributableFsm managed object table"
    ::= { cfprFirmwareObjects 21 }

cfprFirmwareDistributableFsmEntry OBJECT-TYPE
    SYNTAX           CfprFirmwareDistributableFsmEntry
    MAX-ACCESS       not-accessible
    STATUS           current
    DESCRIPTION
        "Entry for the cfprFirmwareDistributableFsmTable table."
    INDEX { cfprFirmwareDistributableFsmInstanceId }
    ::= { cfprFirmwareDistributableFsmTable 1 }

CfprFirmwareDistributableFsmEntry ::= SEQUENCE {
    cfprFirmwareDistributableFsmInstanceId                           CfprManagedObjectId,
    cfprFirmwareDistributableFsmDn                                   CfprManagedObjectDn,
    cfprFirmwareDistributableFsmRn                                   SnmpAdminString,
    cfprFirmwareDistributableFsmCompletionTime                       DateAndTime,
    cfprFirmwareDistributableFsmCurrentFsm                           CfprFirmwareDistributableFsmCurrentFsm,
    cfprFirmwareDistributableFsmDescrData                            SnmpAdminString,
    cfprFirmwareDistributableFsmFsmStatus                            CfprFsmFsmStageStatus,
    cfprFirmwareDistributableFsmProgress                             Gauge32,
    cfprFirmwareDistributableFsmRmtErrCode                           Gauge32,
    cfprFirmwareDistributableFsmRmtErrDescr                          SnmpAdminString,
    cfprFirmwareDistributableFsmRmtRslt                              CfprConditionRemoteInvRslt
}

cfprFirmwareDistributableFsmInstanceId OBJECT-TYPE
    SYNTAX       CfprManagedObjectId
    MAX-ACCESS   not-accessible
    STATUS       current
    DESCRIPTION
        "Instance identifier of the managed object."
    ::= { cfprFirmwareDistributableFsmEntry 1 }

cfprFirmwareDistributableFsmDn OBJECT-TYPE
    SYNTAX       CfprManagedObjectDn
    MAX-ACCESS   read-only
    STATUS       current
    DESCRIPTION
        "Cisco Firepower firmware:DistributableFsm:dn managed
        object property"
    ::= { cfprFirmwareDistributableFsmEntry 2 }

cfprFirmwareDistributableFsmRn OBJECT-TYPE
    SYNTAX       SnmpAdminString
    MAX-ACCESS   read-only
    STATUS       current
    DESCRIPTION
        "Cisco Firepower firmware:DistributableFsm:rn managed
        object property"
    ::= { cfprFirmwareDistributableFsmEntry 3 }

cfprFirmwareDistributableFsmCompletionTime OBJECT-TYPE
    SYNTAX       DateAndTime
    MAX-ACCESS   read-only
    STATUS       current
    DESCRIPTION
        "Cisco Firepower firmware:DistributableFsm:completionTime
        managed object property"
    ::= { cfprFirmwareDistributableFsmEntry 4 }

cfprFirmwareDistributableFsmCurrentFsm OBJECT-TYPE
    SYNTAX       CfprFirmwareDistributableFsmCurrentFsm
    MAX-ACCESS   read-only
    STATUS       current
    DESCRIPTION
        "Cisco Firepower firmware:DistributableFsm:currentFsm
        managed object property"
    ::= { cfprFirmwareDistributableFsmEntry 5 }

cfprFirmwareDistributableFsmDescrData OBJECT-TYPE
    SYNTAX       SnmpAdminString
    MAX-ACCESS   read-only
    STATUS       current
    DESCRIPTION
        "Cisco Firepower firmware:DistributableFsm:descr
        managed object property"
    ::= { cfprFirmwareDistributableFsmEntry 6 }

cfprFirmwareDistributableFsmFsmStatus OBJECT-TYPE
    SYNTAX       CfprFsmFsmStageStatus
    MAX-ACCESS   read-only
    STATUS       current
    DESCRIPTION
        "Cisco Firepower firmware:DistributableFsm:fsmStatus
        managed object property"
    ::= { cfprFirmwareDistributableFsmEntry 7 }

cfprFirmwareDistributableFsmProgress OBJECT-TYPE
    SYNTAX       Gauge32
    MAX-ACCESS   read-only
    STATUS       current
    DESCRIPTION
        "Cisco Firepower firmware:DistributableFsm:progress
        managed object property"
    ::= { cfprFirmwareDistributableFsmEntry 8 }

cfprFirmwareDistributableFsmRmtErrCode OBJECT-TYPE
    SYNTAX       Gauge32
    MAX-ACCESS   read-only
    STATUS       current
    DESCRIPTION
        "Cisco Firepower firmware:DistributableFsm:rmtErrCode
        managed object property"
    ::= { cfprFirmwareDistributableFsmEntry 9 }

cfprFirmwareDistributableFsmRmtErrDescr OBJECT-TYPE
    SYNTAX       SnmpAdminString
    MAX-ACCESS   read-only
    STATUS       current
    DESCRIPTION
        "Cisco Firepower firmware:DistributableFsm:rmtErrDescr
        managed object property"
    ::= { cfprFirmwareDistributableFsmEntry 10 }

cfprFirmwareDistributableFsmRmtRslt OBJECT-TYPE
    SYNTAX       CfprConditionRemoteInvRslt
    MAX-ACCESS   read-only
    STATUS       current
    DESCRIPTION
        "Cisco Firepower firmware:DistributableFsm:rmtRslt
        managed object property"
    ::= { cfprFirmwareDistributableFsmEntry 11 }

cfprFirmwareDistributableFsmStageTable OBJECT-TYPE
    SYNTAX           SEQUENCE OF CfprFirmwareDistributableFsmStageEntry
    MAX-ACCESS       not-accessible
    STATUS           current
    DESCRIPTION
        "Cisco Firepower firmware:DistributableFsmStage
        managed object table"
    ::= { cfprFirmwareObjects 22 }

cfprFirmwareDistributableFsmStageEntry OBJECT-TYPE
    SYNTAX           CfprFirmwareDistributableFsmStageEntry
    MAX-ACCESS       not-accessible
    STATUS           current
    DESCRIPTION
        "Entry for the cfprFirmwareDistributableFsmStageTable table."
    INDEX { cfprFirmwareDistributableFsmStageInstanceId }
    ::= { cfprFirmwareDistributableFsmStageTable 1 }

CfprFirmwareDistributableFsmStageEntry ::= SEQUENCE {
    cfprFirmwareDistributableFsmStageInstanceId                      CfprManagedObjectId,
    cfprFirmwareDistributableFsmStageDn                              CfprManagedObjectDn,
    cfprFirmwareDistributableFsmStageRn                              SnmpAdminString,
    cfprFirmwareDistributableFsmStageDescrData                       SnmpAdminString,
    cfprFirmwareDistributableFsmStageLastUpdateTime                  DateAndTime,
    cfprFirmwareDistributableFsmStageName                            CfprFirmwareDistributableFsmStageName,
    cfprFirmwareDistributableFsmStageOrder                           Gauge32,
    cfprFirmwareDistributableFsmStageRetry                           Gauge32,
    cfprFirmwareDistributableFsmStageStageStatus                     CfprFsmFsmStageStatus
}

cfprFirmwareDistributableFsmStageInstanceId OBJECT-TYPE
    SYNTAX       CfprManagedObjectId
    MAX-ACCESS   not-accessible
    STATUS       current
    DESCRIPTION
        "Instance identifier of the managed object."
    ::= { cfprFirmwareDistributableFsmStageEntry 1 }

cfprFirmwareDistributableFsmStageDn OBJECT-TYPE
    SYNTAX       CfprManagedObjectDn
    MAX-ACCESS   read-only
    STATUS       current
    DESCRIPTION
        "Cisco Firepower firmware:DistributableFsmStage:dn
        managed object property"
    ::= { cfprFirmwareDistributableFsmStageEntry 2 }

cfprFirmwareDistributableFsmStageRn OBJECT-TYPE
    SYNTAX       SnmpAdminString
    MAX-ACCESS   read-only
    STATUS       current
    DESCRIPTION
        "Cisco Firepower firmware:DistributableFsmStage:rn
        managed object property"
    ::= { cfprFirmwareDistributableFsmStageEntry 3 }

cfprFirmwareDistributableFsmStageDescrData OBJECT-TYPE
    SYNTAX       SnmpAdminString
    MAX-ACCESS   read-only
    STATUS       current
    DESCRIPTION
        "Cisco Firepower firmware:DistributableFsmStage:descr
        managed object property"
    ::= { cfprFirmwareDistributableFsmStageEntry 4 }

cfprFirmwareDistributableFsmStageLastUpdateTime OBJECT-TYPE
    SYNTAX       DateAndTime
    MAX-ACCESS   read-only
    STATUS       current
    DESCRIPTION
        "Cisco Firepower firmware:DistributableFsmStage:lastUpdateTime
        managed object property"
    ::= { cfprFirmwareDistributableFsmStageEntry 5 }

cfprFirmwareDistributableFsmStageName OBJECT-TYPE
    SYNTAX       CfprFirmwareDistributableFsmStageName
    MAX-ACCESS   read-only
    STATUS       current
    DESCRIPTION
        "Cisco Firepower firmware:DistributableFsmStage:name
        managed object property"
    ::= { cfprFirmwareDistributableFsmStageEntry 6 }

cfprFirmwareDistributableFsmStageOrder OBJECT-TYPE
    SYNTAX       Gauge32
    MAX-ACCESS   read-only
    STATUS       current
    DESCRIPTION
        "Cisco Firepower firmware:DistributableFsmStage:order
        managed object property"
    ::= { cfprFirmwareDistributableFsmStageEntry 7 }

cfprFirmwareDistributableFsmStageRetry OBJECT-TYPE
    SYNTAX       Gauge32
    MAX-ACCESS   read-only
    STATUS       current
    DESCRIPTION
        "Cisco Firepower firmware:DistributableFsmStage:retry
        managed object property"
    ::= { cfprFirmwareDistributableFsmStageEntry 8 }

cfprFirmwareDistributableFsmStageStageStatus OBJECT-TYPE
    SYNTAX       CfprFsmFsmStageStatus
    MAX-ACCESS   read-only
    STATUS       current
    DESCRIPTION
        "Cisco Firepower firmware:DistributableFsmStage:stageStatus
        managed object property"
    ::= { cfprFirmwareDistributableFsmStageEntry 9 }

cfprFirmwareDistributableFsmTaskTable OBJECT-TYPE
    SYNTAX           SEQUENCE OF CfprFirmwareDistributableFsmTaskEntry
    MAX-ACCESS       not-accessible
    STATUS           current
    DESCRIPTION
        "Cisco Firepower firmware:DistributableFsmTask
        managed object table"
    ::= { cfprFirmwareObjects 23 }

cfprFirmwareDistributableFsmTaskEntry OBJECT-TYPE
    SYNTAX           CfprFirmwareDistributableFsmTaskEntry
    MAX-ACCESS       not-accessible
    STATUS           current
    DESCRIPTION
        "Entry for the cfprFirmwareDistributableFsmTaskTable table."
    INDEX { cfprFirmwareDistributableFsmTaskInstanceId }
    ::= { cfprFirmwareDistributableFsmTaskTable 1 }

CfprFirmwareDistributableFsmTaskEntry ::= SEQUENCE {
    cfprFirmwareDistributableFsmTaskInstanceId                       CfprManagedObjectId,
    cfprFirmwareDistributableFsmTaskDn                               CfprManagedObjectDn,
    cfprFirmwareDistributableFsmTaskRn                               SnmpAdminString,
    cfprFirmwareDistributableFsmTaskCompletion                       CfprFsmCompletion,
    cfprFirmwareDistributableFsmTaskFlags                            CfprFsmFlags,
    cfprFirmwareDistributableFsmTaskItem                             CfprFirmwareDistributableFsmTaskItem,
    cfprFirmwareDistributableFsmTaskSeqId                            Gauge32
}

cfprFirmwareDistributableFsmTaskInstanceId OBJECT-TYPE
    SYNTAX       CfprManagedObjectId
    MAX-ACCESS   not-accessible
    STATUS       current
    DESCRIPTION
        "Instance identifier of the managed object."
    ::= { cfprFirmwareDistributableFsmTaskEntry 1 }

cfprFirmwareDistributableFsmTaskDn OBJECT-TYPE
    SYNTAX       CfprManagedObjectDn
    MAX-ACCESS   read-only
    STATUS       current
    DESCRIPTION
        "Cisco Firepower firmware:DistributableFsmTask:dn
        managed object property"
    ::= { cfprFirmwareDistributableFsmTaskEntry 2 }

cfprFirmwareDistributableFsmTaskRn OBJECT-TYPE
    SYNTAX       SnmpAdminString
    MAX-ACCESS   read-only
    STATUS       current
    DESCRIPTION
        "Cisco Firepower firmware:DistributableFsmTask:rn
        managed object property"
    ::= { cfprFirmwareDistributableFsmTaskEntry 3 }

cfprFirmwareDistributableFsmTaskCompletion OBJECT-TYPE
    SYNTAX       CfprFsmCompletion
    MAX-ACCESS   read-only
    STATUS       current
    DESCRIPTION
        "Cisco Firepower firmware:DistributableFsmTask:completion
        managed object property"
    ::= { cfprFirmwareDistributableFsmTaskEntry 4 }

cfprFirmwareDistributableFsmTaskFlags OBJECT-TYPE
    SYNTAX       CfprFsmFlags
    MAX-ACCESS   read-only
    STATUS       current
    DESCRIPTION
        "Cisco Firepower firmware:DistributableFsmTask:flags
        managed object property"
    ::= { cfprFirmwareDistributableFsmTaskEntry 5 }

cfprFirmwareDistributableFsmTaskItem OBJECT-TYPE
    SYNTAX       CfprFirmwareDistributableFsmTaskItem
    MAX-ACCESS   read-only
    STATUS       current
    DESCRIPTION
        "Cisco Firepower firmware:DistributableFsmTask:item
        managed object property"
    ::= { cfprFirmwareDistributableFsmTaskEntry 6 }

cfprFirmwareDistributableFsmTaskSeqId OBJECT-TYPE
    SYNTAX       Gauge32
    MAX-ACCESS   read-only
    STATUS       current
    DESCRIPTION
        "Cisco Firepower firmware:DistributableFsmTask:seqId
        managed object property"
    ::= { cfprFirmwareDistributableFsmTaskEntry 7 }

cfprFirmwareDownloaderTable OBJECT-TYPE
    SYNTAX           SEQUENCE OF CfprFirmwareDownloaderEntry
    MAX-ACCESS       not-accessible
    STATUS           current
    DESCRIPTION
        "Cisco Firepower firmware:Downloader managed object table"
    ::= { cfprFirmwareObjects 24 }

cfprFirmwareDownloaderEntry OBJECT-TYPE
    SYNTAX           CfprFirmwareDownloaderEntry
    MAX-ACCESS       not-accessible
    STATUS           current
    DESCRIPTION
        "Entry for the cfprFirmwareDownloaderTable table."
    INDEX { cfprFirmwareDownloaderInstanceId }
    ::= { cfprFirmwareDownloaderTable 1 }

CfprFirmwareDownloaderEntry ::= SEQUENCE {
    cfprFirmwareDownloaderInstanceId                                 CfprManagedObjectId,
    cfprFirmwareDownloaderDn                                         CfprManagedObjectDn,
    cfprFirmwareDownloaderRn                                         SnmpAdminString,
    cfprFirmwareDownloaderAdminState                                 CfprFirmwareDownloadActivity,
    cfprFirmwareDownloaderFileName                                   SnmpAdminString,
    cfprFirmwareDownloaderFsmDescr                                   SnmpAdminString,
    cfprFirmwareDownloaderFsmPrev                                    SnmpAdminString,
    cfprFirmwareDownloaderFsmProgr                                   Gauge32,
    cfprFirmwareDownloaderFsmRmtInvErrCode                           Gauge32,
    cfprFirmwareDownloaderFsmRmtInvErrDescr                          SnmpAdminString,
    cfprFirmwareDownloaderFsmRmtInvRslt                              CfprConditionRemoteInvRslt,
    cfprFirmwareDownloaderFsmStageDescr                              SnmpAdminString,
    cfprFirmwareDownloaderFsmStamp                                   DateAndTime,
    cfprFirmwareDownloaderFsmStatus                                  SnmpAdminString,
    cfprFirmwareDownloaderFsmTry                                     Gauge32,
    cfprFirmwareDownloaderImageSize                                  Unsigned64,
    cfprFirmwareDownloaderProtocol                                   CfprFirmwareTransport,
    cfprFirmwareDownloaderPwd                                        SnmpAdminString,
    cfprFirmwareDownloaderRemotePath                                 SnmpAdminString,
    cfprFirmwareDownloaderServer                                     SnmpAdminString,
    cfprFirmwareDownloaderTransferState                              CfprFirmwareTransferState,
    cfprFirmwareDownloaderUser                                       SnmpAdminString,
    cfprFirmwareDownloaderTimeStamp                                  DateAndTime,
    cfprFirmwareDownloaderMsgStatus                                  SnmpAdminString,
    cfprFirmwareDownloaderPort                                       Gauge32,
    cfprFirmwareDownloaderStartTime                                  DateAndTime,
    cfprFirmwareDownloaderTransferRate                               INTEGER,
    cfprFirmwareDownloaderSilent                                     Gauge32,
    cfprFirmwareDownloaderTtyName                                    SnmpAdminString
}

cfprFirmwareDownloaderInstanceId OBJECT-TYPE
    SYNTAX       CfprManagedObjectId
    MAX-ACCESS   not-accessible
    STATUS       current
    DESCRIPTION
        "Instance identifier of the managed object."
    ::= { cfprFirmwareDownloaderEntry 1 }

cfprFirmwareDownloaderDn OBJECT-TYPE
    SYNTAX       CfprManagedObjectDn
    MAX-ACCESS   read-only
    STATUS       current
    DESCRIPTION
        "Cisco Firepower firmware:Downloader:dn managed object property"
    ::= { cfprFirmwareDownloaderEntry 2 }

cfprFirmwareDownloaderRn OBJECT-TYPE
    SYNTAX       SnmpAdminString
    MAX-ACCESS   read-only
    STATUS       current
    DESCRIPTION
        "Cisco Firepower firmware:Downloader:rn managed object property"
    ::= { cfprFirmwareDownloaderEntry 3 }

cfprFirmwareDownloaderAdminState OBJECT-TYPE
    SYNTAX       CfprFirmwareDownloadActivity
    MAX-ACCESS   read-only
    STATUS       current
    DESCRIPTION
        "Cisco Firepower firmware:Downloader:adminState
        managed object property"
    ::= { cfprFirmwareDownloaderEntry 4 }

cfprFirmwareDownloaderFileName OBJECT-TYPE
    SYNTAX       SnmpAdminString
    MAX-ACCESS   read-only
    STATUS       current
    DESCRIPTION
        "Cisco Firepower firmware:Downloader:fileName managed
        object property"
    ::= { cfprFirmwareDownloaderEntry 5 }

cfprFirmwareDownloaderFsmDescr OBJECT-TYPE
    SYNTAX       SnmpAdminString
    MAX-ACCESS   read-only
    STATUS       current
    DESCRIPTION
        "Cisco Firepower firmware:Downloader:fsmDescr managed
        object property"
    ::= { cfprFirmwareDownloaderEntry 6 }

cfprFirmwareDownloaderFsmPrev OBJECT-TYPE
    SYNTAX       SnmpAdminString
    MAX-ACCESS   read-only
    STATUS       current
    DESCRIPTION
        "Cisco Firepower firmware:Downloader:fsmPrev managed
        object property"
    ::= { cfprFirmwareDownloaderEntry 7 }

cfprFirmwareDownloaderFsmProgr OBJECT-TYPE
    SYNTAX       Gauge32
    MAX-ACCESS   read-only
    STATUS       current
    DESCRIPTION
        "Cisco Firepower firmware:Downloader:fsmProgr managed
        object property"
    ::= { cfprFirmwareDownloaderEntry 8 }

cfprFirmwareDownloaderFsmRmtInvErrCode OBJECT-TYPE
    SYNTAX       Gauge32
    MAX-ACCESS   read-only
    STATUS       current
    DESCRIPTION
        "Cisco Firepower firmware:Downloader:fsmRmtInvErrCode
        managed object property"
    ::= { cfprFirmwareDownloaderEntry 9 }

cfprFirmwareDownloaderFsmRmtInvErrDescr OBJECT-TYPE
    SYNTAX       SnmpAdminString
    MAX-ACCESS   read-only
    STATUS       current
    DESCRIPTION
        "Cisco Firepower firmware:Downloader:fsmRmtInvErrDescr
        managed object property"
    ::= { cfprFirmwareDownloaderEntry 10 }

cfprFirmwareDownloaderFsmRmtInvRslt OBJECT-TYPE
    SYNTAX       CfprConditionRemoteInvRslt
    MAX-ACCESS   read-only
    STATUS       current
    DESCRIPTION
        "Cisco Firepower firmware:Downloader:fsmRmtInvRslt
        managed object property"
    ::= { cfprFirmwareDownloaderEntry 11 }

cfprFirmwareDownloaderFsmStageDescr OBJECT-TYPE
    SYNTAX       SnmpAdminString
    MAX-ACCESS   read-only
    STATUS       current
    DESCRIPTION
        "Cisco Firepower firmware:Downloader:fsmStageDescr
        managed object property"
    ::= { cfprFirmwareDownloaderEntry 12 }

cfprFirmwareDownloaderFsmStamp OBJECT-TYPE
    SYNTAX       DateAndTime
    MAX-ACCESS   read-only
    STATUS       current
    DESCRIPTION
        "Cisco Firepower firmware:Downloader:fsmStamp managed
        object property"
    ::= { cfprFirmwareDownloaderEntry 13 }

cfprFirmwareDownloaderFsmStatus OBJECT-TYPE
    SYNTAX       SnmpAdminString
    MAX-ACCESS   read-only
    STATUS       current
    DESCRIPTION
        "Cisco Firepower firmware:Downloader:fsmStatus
        managed object property"
    ::= { cfprFirmwareDownloaderEntry 14 }

cfprFirmwareDownloaderFsmTry OBJECT-TYPE
    SYNTAX       Gauge32
    MAX-ACCESS   read-only
    STATUS       current
    DESCRIPTION
        "Cisco Firepower firmware:Downloader:fsmTry managed
        object property"
    ::= { cfprFirmwareDownloaderEntry 15 }

cfprFirmwareDownloaderImageSize OBJECT-TYPE
    SYNTAX       Unsigned64
    MAX-ACCESS   read-only
    STATUS       current
    DESCRIPTION
        "Cisco Firepower firmware:Downloader:imageSize
        managed object property"
    ::= { cfprFirmwareDownloaderEntry 16 }

cfprFirmwareDownloaderProtocol OBJECT-TYPE
    SYNTAX       CfprFirmwareTransport
    MAX-ACCESS   read-only
    STATUS       current
    DESCRIPTION
        "Cisco Firepower firmware:Downloader:protocol managed
        object property"
    ::= { cfprFirmwareDownloaderEntry 17 }

cfprFirmwareDownloaderPwd OBJECT-TYPE
    SYNTAX       SnmpAdminString
    MAX-ACCESS   read-only
    STATUS       current
    DESCRIPTION
        "Cisco Firepower firmware:Downloader:pwd managed object property"
    ::= { cfprFirmwareDownloaderEntry 18 }

cfprFirmwareDownloaderRemotePath OBJECT-TYPE
    SYNTAX       SnmpAdminString
    MAX-ACCESS   read-only
    STATUS       current
    DESCRIPTION
        "Cisco Firepower firmware:Downloader:remotePath
        managed object property"
    ::= { cfprFirmwareDownloaderEntry 19 }

cfprFirmwareDownloaderServer OBJECT-TYPE
    SYNTAX       SnmpAdminString
    MAX-ACCESS   read-only
    STATUS       current
    DESCRIPTION
        "Cisco Firepower firmware:Downloader:server managed
        object property"
    ::= { cfprFirmwareDownloaderEntry 20 }

cfprFirmwareDownloaderTransferState OBJECT-TYPE
    SYNTAX       CfprFirmwareTransferState
    MAX-ACCESS   read-only
    STATUS       current
    DESCRIPTION
        "Cisco Firepower firmware:Downloader:transferState
        managed object property"
    ::= { cfprFirmwareDownloaderEntry 21 }

cfprFirmwareDownloaderUser OBJECT-TYPE
    SYNTAX       SnmpAdminString
    MAX-ACCESS   read-only
    STATUS       current
    DESCRIPTION
        "Cisco Firepower firmware:Downloader:user managed object property"
    ::= { cfprFirmwareDownloaderEntry 22 }

cfprFirmwareDownloaderTimeStamp OBJECT-TYPE
    SYNTAX       DateAndTime
    MAX-ACCESS   read-only
    STATUS       current
    DESCRIPTION
        "Cisco Firepower firmware:Downloader:timeStamp
        managed object property"
    ::= { cfprFirmwareDownloaderEntry 23 }

cfprFirmwareDownloaderMsgStatus OBJECT-TYPE
    SYNTAX       SnmpAdminString
    MAX-ACCESS   read-only
    STATUS       current
    DESCRIPTION
        "Cisco Firepower firmware:Downloader:msgStatus
        managed object property"
    ::= { cfprFirmwareDownloaderEntry 24 }

cfprFirmwareDownloaderPort OBJECT-TYPE
    SYNTAX       Gauge32
    MAX-ACCESS   read-only
    STATUS       current
    DESCRIPTION
        "Cisco Firepower firmware:Downloader:port managed object property"
    ::= { cfprFirmwareDownloaderEntry 25 }

cfprFirmwareDownloaderStartTime OBJECT-TYPE
    SYNTAX       DateAndTime
    MAX-ACCESS   read-only
    STATUS       current
    DESCRIPTION
        "Cisco Firepower firmware:Downloader:startTime
        managed object property"
    ::= { cfprFirmwareDownloaderEntry 26 }

cfprFirmwareDownloaderTransferRate OBJECT-TYPE
    SYNTAX       INTEGER
    MAX-ACCESS   read-only
    STATUS       current
    DESCRIPTION
        "Cisco Firepower firmware:Downloader:transferRate
        managed object property"
    ::= { cfprFirmwareDownloaderEntry 27 }

cfprFirmwareDownloaderSilent OBJECT-TYPE
    SYNTAX       Gauge32
    MAX-ACCESS   read-only
    STATUS       current
    DESCRIPTION
        "Cisco Firepower firmware:Downloader:silent managed
        object property"
    ::= { cfprFirmwareDownloaderEntry 28 }

cfprFirmwareDownloaderTtyName OBJECT-TYPE
    SYNTAX       SnmpAdminString
    MAX-ACCESS   read-only
    STATUS       current
    DESCRIPTION
        "Cisco Firepower firmware:Downloader:ttyName managed
        object property"
    ::= { cfprFirmwareDownloaderEntry 29 }

cfprFirmwareDownloaderFsmTable OBJECT-TYPE
    SYNTAX           SEQUENCE OF CfprFirmwareDownloaderFsmEntry
    MAX-ACCESS       not-accessible
    STATUS           current
    DESCRIPTION
        "Cisco Firepower firmware:DownloaderFsm managed object table"
    ::= { cfprFirmwareObjects 25 }

cfprFirmwareDownloaderFsmEntry OBJECT-TYPE
    SYNTAX           CfprFirmwareDownloaderFsmEntry
    MAX-ACCESS       not-accessible
    STATUS           current
    DESCRIPTION
        "Entry for the cfprFirmwareDownloaderFsmTable table."
    INDEX { cfprFirmwareDownloaderFsmInstanceId }
    ::= { cfprFirmwareDownloaderFsmTable 1 }

CfprFirmwareDownloaderFsmEntry ::= SEQUENCE {
    cfprFirmwareDownloaderFsmInstanceId                              CfprManagedObjectId,
    cfprFirmwareDownloaderFsmDn                                      CfprManagedObjectDn,
    cfprFirmwareDownloaderFsmRn                                      SnmpAdminString,
    cfprFirmwareDownloaderFsmCompletionTime                          DateAndTime,
    cfprFirmwareDownloaderFsmCurrentFsm                              CfprFirmwareDownloaderFsmCurrentFsm,
    cfprFirmwareDownloaderFsmDescrData                               SnmpAdminString,
    cfprFirmwareDownloaderFsmFsmStatus                               CfprFsmFsmStageStatus,
    cfprFirmwareDownloaderFsmProgress                                Gauge32,
    cfprFirmwareDownloaderFsmRmtErrCode                              Gauge32,
    cfprFirmwareDownloaderFsmRmtErrDescr                             SnmpAdminString,
    cfprFirmwareDownloaderFsmRmtRslt                                 CfprConditionRemoteInvRslt
}

cfprFirmwareDownloaderFsmInstanceId OBJECT-TYPE
    SYNTAX       CfprManagedObjectId
    MAX-ACCESS   not-accessible
    STATUS       current
    DESCRIPTION
        "Instance identifier of the managed object."
    ::= { cfprFirmwareDownloaderFsmEntry 1 }

cfprFirmwareDownloaderFsmDn OBJECT-TYPE
    SYNTAX       CfprManagedObjectDn
    MAX-ACCESS   read-only
    STATUS       current
    DESCRIPTION
        "Cisco Firepower firmware:DownloaderFsm:dn managed
        object property"
    ::= { cfprFirmwareDownloaderFsmEntry 2 }

cfprFirmwareDownloaderFsmRn OBJECT-TYPE
    SYNTAX       SnmpAdminString
    MAX-ACCESS   read-only
    STATUS       current
    DESCRIPTION
        "Cisco Firepower firmware:DownloaderFsm:rn managed
        object property"
    ::= { cfprFirmwareDownloaderFsmEntry 3 }

cfprFirmwareDownloaderFsmCompletionTime OBJECT-TYPE
    SYNTAX       DateAndTime
    MAX-ACCESS   read-only
    STATUS       current
    DESCRIPTION
        "Cisco Firepower firmware:DownloaderFsm:completionTime
        managed object property"
    ::= { cfprFirmwareDownloaderFsmEntry 4 }

cfprFirmwareDownloaderFsmCurrentFsm OBJECT-TYPE
    SYNTAX       CfprFirmwareDownloaderFsmCurrentFsm
    MAX-ACCESS   read-only
    STATUS       current
    DESCRIPTION
        "Cisco Firepower firmware:DownloaderFsm:currentFsm
        managed object property"
    ::= { cfprFirmwareDownloaderFsmEntry 5 }

cfprFirmwareDownloaderFsmDescrData OBJECT-TYPE
    SYNTAX       SnmpAdminString
    MAX-ACCESS   read-only
    STATUS       current
    DESCRIPTION
        "Cisco Firepower firmware:DownloaderFsm:descr managed
        object property"
    ::= { cfprFirmwareDownloaderFsmEntry 6 }

cfprFirmwareDownloaderFsmFsmStatus OBJECT-TYPE
    SYNTAX       CfprFsmFsmStageStatus
    MAX-ACCESS   read-only
    STATUS       current
    DESCRIPTION
        "Cisco Firepower firmware:DownloaderFsm:fsmStatus
        managed object property"
    ::= { cfprFirmwareDownloaderFsmEntry 7 }

cfprFirmwareDownloaderFsmProgress OBJECT-TYPE
    SYNTAX       Gauge32
    MAX-ACCESS   read-only
    STATUS       current
    DESCRIPTION
        "Cisco Firepower firmware:DownloaderFsm:progress
        managed object property"
    ::= { cfprFirmwareDownloaderFsmEntry 8 }

cfprFirmwareDownloaderFsmRmtErrCode OBJECT-TYPE
    SYNTAX       Gauge32
    MAX-ACCESS   read-only
    STATUS       current
    DESCRIPTION
        "Cisco Firepower firmware:DownloaderFsm:rmtErrCode
        managed object property"
    ::= { cfprFirmwareDownloaderFsmEntry 9 }

cfprFirmwareDownloaderFsmRmtErrDescr OBJECT-TYPE
    SYNTAX       SnmpAdminString
    MAX-ACCESS   read-only
    STATUS       current
    DESCRIPTION
        "Cisco Firepower firmware:DownloaderFsm:rmtErrDescr
        managed object property"
    ::= { cfprFirmwareDownloaderFsmEntry 10 }

cfprFirmwareDownloaderFsmRmtRslt OBJECT-TYPE
    SYNTAX       CfprConditionRemoteInvRslt
    MAX-ACCESS   read-only
    STATUS       current
    DESCRIPTION
        "Cisco Firepower firmware:DownloaderFsm:rmtRslt
        managed object property"
    ::= { cfprFirmwareDownloaderFsmEntry 11 }

cfprFirmwareDownloaderFsmStageTable OBJECT-TYPE
    SYNTAX           SEQUENCE OF CfprFirmwareDownloaderFsmStageEntry
    MAX-ACCESS       not-accessible
    STATUS           current
    DESCRIPTION
        "Cisco Firepower firmware:DownloaderFsmStage managed object table"
    ::= { cfprFirmwareObjects 26 }

cfprFirmwareDownloaderFsmStageEntry OBJECT-TYPE
    SYNTAX           CfprFirmwareDownloaderFsmStageEntry
    MAX-ACCESS       not-accessible
    STATUS           current
    DESCRIPTION
        "Entry for the cfprFirmwareDownloaderFsmStageTable table."
    INDEX { cfprFirmwareDownloaderFsmStageInstanceId }
    ::= { cfprFirmwareDownloaderFsmStageTable 1 }

CfprFirmwareDownloaderFsmStageEntry ::= SEQUENCE {
    cfprFirmwareDownloaderFsmStageInstanceId                         CfprManagedObjectId,
    cfprFirmwareDownloaderFsmStageDn                                 CfprManagedObjectDn,
    cfprFirmwareDownloaderFsmStageRn                                 SnmpAdminString,
    cfprFirmwareDownloaderFsmStageDescrData                          SnmpAdminString,
    cfprFirmwareDownloaderFsmStageLastUpdateTime                     DateAndTime,
    cfprFirmwareDownloaderFsmStageName                               CfprFirmwareDownloaderFsmStageName,
    cfprFirmwareDownloaderFsmStageOrder                              Gauge32,
    cfprFirmwareDownloaderFsmStageRetry                              Gauge32,
    cfprFirmwareDownloaderFsmStageStageStatus                        CfprFsmFsmStageStatus
}

cfprFirmwareDownloaderFsmStageInstanceId OBJECT-TYPE
    SYNTAX       CfprManagedObjectId
    MAX-ACCESS   not-accessible
    STATUS       current
    DESCRIPTION
        "Instance identifier of the managed object."
    ::= { cfprFirmwareDownloaderFsmStageEntry 1 }

cfprFirmwareDownloaderFsmStageDn OBJECT-TYPE
    SYNTAX       CfprManagedObjectDn
    MAX-ACCESS   read-only
    STATUS       current
    DESCRIPTION
        "Cisco Firepower firmware:DownloaderFsmStage:dn
        managed object property"
    ::= { cfprFirmwareDownloaderFsmStageEntry 2 }

cfprFirmwareDownloaderFsmStageRn OBJECT-TYPE
    SYNTAX       SnmpAdminString
    MAX-ACCESS   read-only
    STATUS       current
    DESCRIPTION
        "Cisco Firepower firmware:DownloaderFsmStage:rn
        managed object property"
    ::= { cfprFirmwareDownloaderFsmStageEntry 3 }

cfprFirmwareDownloaderFsmStageDescrData OBJECT-TYPE
    SYNTAX       SnmpAdminString
    MAX-ACCESS   read-only
    STATUS       current
    DESCRIPTION
        "Cisco Firepower firmware:DownloaderFsmStage:descr
        managed object property"
    ::= { cfprFirmwareDownloaderFsmStageEntry 4 }

cfprFirmwareDownloaderFsmStageLastUpdateTime OBJECT-TYPE
    SYNTAX       DateAndTime
    MAX-ACCESS   read-only
    STATUS       current
    DESCRIPTION
        "Cisco Firepower firmware:DownloaderFsmStage:lastUpdateTime
        managed object property"
    ::= { cfprFirmwareDownloaderFsmStageEntry 5 }

cfprFirmwareDownloaderFsmStageName OBJECT-TYPE
    SYNTAX       CfprFirmwareDownloaderFsmStageName
    MAX-ACCESS   read-only
    STATUS       current
    DESCRIPTION
        "Cisco Firepower firmware:DownloaderFsmStage:name
        managed object property"
    ::= { cfprFirmwareDownloaderFsmStageEntry 6 }

cfprFirmwareDownloaderFsmStageOrder OBJECT-TYPE
    SYNTAX       Gauge32
    MAX-ACCESS   read-only
    STATUS       current
    DESCRIPTION
        "Cisco Firepower firmware:DownloaderFsmStage:order
        managed object property"
    ::= { cfprFirmwareDownloaderFsmStageEntry 7 }

cfprFirmwareDownloaderFsmStageRetry OBJECT-TYPE
    SYNTAX       Gauge32
    MAX-ACCESS   read-only
    STATUS       current
    DESCRIPTION
        "Cisco Firepower firmware:DownloaderFsmStage:retry
        managed object property"
    ::= { cfprFirmwareDownloaderFsmStageEntry 8 }

cfprFirmwareDownloaderFsmStageStageStatus OBJECT-TYPE
    SYNTAX       CfprFsmFsmStageStatus
    MAX-ACCESS   read-only
    STATUS       current
    DESCRIPTION
        "Cisco Firepower firmware:DownloaderFsmStage:stageStatus
        managed object property"
    ::= { cfprFirmwareDownloaderFsmStageEntry 9 }

cfprFirmwareDownloaderFsmTaskTable OBJECT-TYPE
    SYNTAX           SEQUENCE OF CfprFirmwareDownloaderFsmTaskEntry
    MAX-ACCESS       not-accessible
    STATUS           current
    DESCRIPTION
        "Cisco Firepower firmware:DownloaderFsmTask managed object table"
    ::= { cfprFirmwareObjects 27 }

cfprFirmwareDownloaderFsmTaskEntry OBJECT-TYPE
    SYNTAX           CfprFirmwareDownloaderFsmTaskEntry
    MAX-ACCESS       not-accessible
    STATUS           current
    DESCRIPTION
        "Entry for the cfprFirmwareDownloaderFsmTaskTable table."
    INDEX { cfprFirmwareDownloaderFsmTaskInstanceId }
    ::= { cfprFirmwareDownloaderFsmTaskTable 1 }

CfprFirmwareDownloaderFsmTaskEntry ::= SEQUENCE {
    cfprFirmwareDownloaderFsmTaskInstanceId                          CfprManagedObjectId,
    cfprFirmwareDownloaderFsmTaskDn                                  CfprManagedObjectDn,
    cfprFirmwareDownloaderFsmTaskRn                                  SnmpAdminString,
    cfprFirmwareDownloaderFsmTaskCompletion                          CfprFsmCompletion,
    cfprFirmwareDownloaderFsmTaskFlags                               CfprFsmFlags,
    cfprFirmwareDownloaderFsmTaskItem                                CfprFirmwareDownloaderFsmTaskItem,
    cfprFirmwareDownloaderFsmTaskSeqId                               Gauge32
}

cfprFirmwareDownloaderFsmTaskInstanceId OBJECT-TYPE
    SYNTAX       CfprManagedObjectId
    MAX-ACCESS   not-accessible
    STATUS       current
    DESCRIPTION
        "Instance identifier of the managed object."
    ::= { cfprFirmwareDownloaderFsmTaskEntry 1 }

cfprFirmwareDownloaderFsmTaskDn OBJECT-TYPE
    SYNTAX       CfprManagedObjectDn
    MAX-ACCESS   read-only
    STATUS       current
    DESCRIPTION
        "Cisco Firepower firmware:DownloaderFsmTask:dn
        managed object property"
    ::= { cfprFirmwareDownloaderFsmTaskEntry 2 }

cfprFirmwareDownloaderFsmTaskRn OBJECT-TYPE
    SYNTAX       SnmpAdminString
    MAX-ACCESS   read-only
    STATUS       current
    DESCRIPTION
        "Cisco Firepower firmware:DownloaderFsmTask:rn
        managed object property"
    ::= { cfprFirmwareDownloaderFsmTaskEntry 3 }

cfprFirmwareDownloaderFsmTaskCompletion OBJECT-TYPE
    SYNTAX       CfprFsmCompletion
    MAX-ACCESS   read-only
    STATUS       current
    DESCRIPTION
        "Cisco Firepower firmware:DownloaderFsmTask:completion
        managed object property"
    ::= { cfprFirmwareDownloaderFsmTaskEntry 4 }

cfprFirmwareDownloaderFsmTaskFlags OBJECT-TYPE
    SYNTAX       CfprFsmFlags
    MAX-ACCESS   read-only
    STATUS       current
    DESCRIPTION
        "Cisco Firepower firmware:DownloaderFsmTask:flags
        managed object property"
    ::= { cfprFirmwareDownloaderFsmTaskEntry 5 }

cfprFirmwareDownloaderFsmTaskItem OBJECT-TYPE
    SYNTAX       CfprFirmwareDownloaderFsmTaskItem
    MAX-ACCESS   read-only
    STATUS       current
    DESCRIPTION
        "Cisco Firepower firmware:DownloaderFsmTask:item
        managed object property"
    ::= { cfprFirmwareDownloaderFsmTaskEntry 6 }

cfprFirmwareDownloaderFsmTaskSeqId OBJECT-TYPE
    SYNTAX       Gauge32
    MAX-ACCESS   read-only
    STATUS       current
    DESCRIPTION
        "Cisco Firepower firmware:DownloaderFsmTask:seqId
        managed object property"
    ::= { cfprFirmwareDownloaderFsmTaskEntry 7 }

cfprFirmwareHostTable OBJECT-TYPE
    SYNTAX           SEQUENCE OF CfprFirmwareHostEntry
    MAX-ACCESS       not-accessible
    STATUS           current
    DESCRIPTION
        "Cisco Firepower firmware:Host managed object table"
    ::= { cfprFirmwareObjects 28 }

cfprFirmwareHostEntry OBJECT-TYPE
    SYNTAX           CfprFirmwareHostEntry
    MAX-ACCESS       not-accessible
    STATUS           current
    DESCRIPTION
        "Entry for the cfprFirmwareHostTable table."
    INDEX { cfprFirmwareHostInstanceId }
    ::= { cfprFirmwareHostTable 1 }

CfprFirmwareHostEntry ::= SEQUENCE {
    cfprFirmwareHostInstanceId                                       CfprManagedObjectId,
    cfprFirmwareHostDn                                               CfprManagedObjectDn,
    cfprFirmwareHostRn                                               SnmpAdminString
}

cfprFirmwareHostInstanceId OBJECT-TYPE
    SYNTAX       CfprManagedObjectId
    MAX-ACCESS   not-accessible
    STATUS       current
    DESCRIPTION
        "Instance identifier of the managed object."
    ::= { cfprFirmwareHostEntry 1 }

cfprFirmwareHostDn OBJECT-TYPE
    SYNTAX       CfprManagedObjectDn
    MAX-ACCESS   read-only
    STATUS       current
    DESCRIPTION
        "Cisco Firepower firmware:Host:dn managed object property"
    ::= { cfprFirmwareHostEntry 2 }

cfprFirmwareHostRn OBJECT-TYPE
    SYNTAX       SnmpAdminString
    MAX-ACCESS   read-only
    STATUS       current
    DESCRIPTION
        "Cisco Firepower firmware:Host:rn managed object property"
    ::= { cfprFirmwareHostEntry 3 }

cfprFirmwareHostPackModImpactTable OBJECT-TYPE
    SYNTAX           SEQUENCE OF CfprFirmwareHostPackModImpactEntry
    MAX-ACCESS       not-accessible
    STATUS           current
    DESCRIPTION
        "Cisco Firepower firmware:HostPackModImpact managed object table"
    ::= { cfprFirmwareObjects 29 }

cfprFirmwareHostPackModImpactEntry OBJECT-TYPE
    SYNTAX           CfprFirmwareHostPackModImpactEntry
    MAX-ACCESS       not-accessible
    STATUS           current
    DESCRIPTION
        "Entry for the cfprFirmwareHostPackModImpactTable table."
    INDEX { cfprFirmwareHostPackModImpactInstanceId }
    ::= { cfprFirmwareHostPackModImpactTable 1 }

CfprFirmwareHostPackModImpactEntry ::= SEQUENCE {
    cfprFirmwareHostPackModImpactInstanceId                          CfprManagedObjectId,
    cfprFirmwareHostPackModImpactDn                                  CfprManagedObjectDn,
    cfprFirmwareHostPackModImpactRn                                  SnmpAdminString,
    cfprFirmwareHostPackModImpactKeyDn                               SnmpAdminString,
    cfprFirmwareHostPackModImpactMaintPolicyDn                       SnmpAdminString,
    cfprFirmwareHostPackModImpactPnDn                                SnmpAdminString,
    cfprFirmwareHostPackModImpactRebootPolicy                        SnmpAdminString,
    cfprFirmwareHostPackModImpactServiceProfileDn                    SnmpAdminString
}

cfprFirmwareHostPackModImpactInstanceId OBJECT-TYPE
    SYNTAX       CfprManagedObjectId
    MAX-ACCESS   not-accessible
    STATUS       current
    DESCRIPTION
        "Instance identifier of the managed object."
    ::= { cfprFirmwareHostPackModImpactEntry 1 }

cfprFirmwareHostPackModImpactDn OBJECT-TYPE
    SYNTAX       CfprManagedObjectDn
    MAX-ACCESS   read-only
    STATUS       current
    DESCRIPTION
        "Cisco Firepower firmware:HostPackModImpact:dn
        managed object property"
    ::= { cfprFirmwareHostPackModImpactEntry 2 }

cfprFirmwareHostPackModImpactRn OBJECT-TYPE
    SYNTAX       SnmpAdminString
    MAX-ACCESS   read-only
    STATUS       current
    DESCRIPTION
        "Cisco Firepower firmware:HostPackModImpact:rn
        managed object property"
    ::= { cfprFirmwareHostPackModImpactEntry 3 }

cfprFirmwareHostPackModImpactKeyDn OBJECT-TYPE
    SYNTAX       SnmpAdminString
    MAX-ACCESS   read-only
    STATUS       current
    DESCRIPTION
        "Cisco Firepower firmware:HostPackModImpact:keyDn
        managed object property"
    ::= { cfprFirmwareHostPackModImpactEntry 4 }

cfprFirmwareHostPackModImpactMaintPolicyDn OBJECT-TYPE
    SYNTAX       SnmpAdminString
    MAX-ACCESS   read-only
    STATUS       current
    DESCRIPTION
        "Cisco Firepower firmware:HostPackModImpact:maintPolicyDn
        managed object property"
    ::= { cfprFirmwareHostPackModImpactEntry 5 }

cfprFirmwareHostPackModImpactPnDn OBJECT-TYPE
    SYNTAX       SnmpAdminString
    MAX-ACCESS   read-only
    STATUS       current
    DESCRIPTION
        "Cisco Firepower firmware:HostPackModImpact:pnDn
        managed object property"
    ::= { cfprFirmwareHostPackModImpactEntry 6 }

cfprFirmwareHostPackModImpactRebootPolicy OBJECT-TYPE
    SYNTAX       SnmpAdminString
    MAX-ACCESS   read-only
    STATUS       current
    DESCRIPTION
        "Cisco Firepower firmware:HostPackModImpact:rebootPolicy
        managed object property"
    ::= { cfprFirmwareHostPackModImpactEntry 7 }

cfprFirmwareHostPackModImpactServiceProfileDn OBJECT-TYPE
    SYNTAX       SnmpAdminString
    MAX-ACCESS   read-only
    STATUS       current
    DESCRIPTION
        "Cisco Firepower firmware:HostPackModImpact:serviceProfileDn
        managed object property"
    ::= { cfprFirmwareHostPackModImpactEntry 8 }

cfprFirmwareImageTable OBJECT-TYPE
    SYNTAX           SEQUENCE OF CfprFirmwareImageEntry
    MAX-ACCESS       not-accessible
    STATUS           current
    DESCRIPTION
        "Cisco Firepower firmware:Image managed object table"
    ::= { cfprFirmwareObjects 30 }

cfprFirmwareImageEntry OBJECT-TYPE
    SYNTAX           CfprFirmwareImageEntry
    MAX-ACCESS       not-accessible
    STATUS           current
    DESCRIPTION
        "Entry for the cfprFirmwareImageTable table."
    INDEX { cfprFirmwareImageInstanceId }
    ::= { cfprFirmwareImageTable 1 }

CfprFirmwareImageEntry ::= SEQUENCE {
    cfprFirmwareImageInstanceId                                      CfprManagedObjectId,
    cfprFirmwareImageDn                                              CfprManagedObjectDn,
    cfprFirmwareImageRn                                              SnmpAdminString,
    cfprFirmwareImageAdminState                                      CfprFirmwareAdminState,
    cfprFirmwareImageChecksum                                        SnmpAdminString,
    cfprFirmwareImageDescr                                           SnmpAdminString,
    cfprFirmwareImageDownloadDate                                    DateAndTime,
    cfprFirmwareImageFsmDescr                                        SnmpAdminString,
    cfprFirmwareImageFsmPrev                                         SnmpAdminString,
    cfprFirmwareImageFsmProgr                                        Gauge32,
    cfprFirmwareImageFsmRmtInvErrCode                                Gauge32,
    cfprFirmwareImageFsmRmtInvErrDescr                               SnmpAdminString,
    cfprFirmwareImageFsmRmtInvRslt                                   CfprConditionRemoteInvRslt,
    cfprFirmwareImageFsmStageDescr                                   SnmpAdminString,
    cfprFirmwareImageFsmStamp                                        DateAndTime,
    cfprFirmwareImageFsmStatus                                       SnmpAdminString,
    cfprFirmwareImageFsmTry                                          Gauge32,
    cfprFirmwareImageImagePresence                                   CfprFirmwareImagePresence,
    cfprFirmwareImageIntId                                           SnmpAdminString,
    cfprFirmwareImageInvTag                                          SnmpAdminString,
    cfprFirmwareImageIsoname                                         SnmpAdminString,
    cfprFirmwareImageLocation                                        SnmpAdminString,
    cfprFirmwareImageName                                            SnmpAdminString,
    cfprFirmwareImagePolicyLevel                                     Gauge32,
    cfprFirmwareImagePolicyOwner                                     CfprPolicyPolicyOwner,
    cfprFirmwareImageSize                                            Unsigned64,
    cfprFirmwareImageType                                            CfprFirmwareType,
    cfprFirmwareImageVersion                                         SnmpAdminString
}

cfprFirmwareImageInstanceId OBJECT-TYPE
    SYNTAX       CfprManagedObjectId
    MAX-ACCESS   not-accessible
    STATUS       current
    DESCRIPTION
        "Instance identifier of the managed object."
    ::= { cfprFirmwareImageEntry 1 }

cfprFirmwareImageDn OBJECT-TYPE
    SYNTAX       CfprManagedObjectDn
    MAX-ACCESS   read-only
    STATUS       current
    DESCRIPTION
        "Cisco Firepower firmware:Image:dn managed object property"
    ::= { cfprFirmwareImageEntry 2 }

cfprFirmwareImageRn OBJECT-TYPE
    SYNTAX       SnmpAdminString
    MAX-ACCESS   read-only
    STATUS       current
    DESCRIPTION
        "Cisco Firepower firmware:Image:rn managed object property"
    ::= { cfprFirmwareImageEntry 3 }

cfprFirmwareImageAdminState OBJECT-TYPE
    SYNTAX       CfprFirmwareAdminState
    MAX-ACCESS   read-only
    STATUS       current
    DESCRIPTION
        "Cisco Firepower firmware:Image:adminState managed
        object property"
    ::= { cfprFirmwareImageEntry 4 }

cfprFirmwareImageChecksum OBJECT-TYPE
    SYNTAX       SnmpAdminString
    MAX-ACCESS   read-only
    STATUS       current
    DESCRIPTION
        "Cisco Firepower firmware:Image:checksum managed object property"
    ::= { cfprFirmwareImageEntry 5 }

cfprFirmwareImageDescr OBJECT-TYPE
    SYNTAX       SnmpAdminString
    MAX-ACCESS   read-only
    STATUS       current
    DESCRIPTION
        "Cisco Firepower firmware:Image:descr managed object property"
    ::= { cfprFirmwareImageEntry 6 }

cfprFirmwareImageDownloadDate OBJECT-TYPE
    SYNTAX       DateAndTime
    MAX-ACCESS   read-only
    STATUS       current
    DESCRIPTION
        "Cisco Firepower firmware:Image:downloadDate managed
        object property"
    ::= { cfprFirmwareImageEntry 7 }

cfprFirmwareImageFsmDescr OBJECT-TYPE
    SYNTAX       SnmpAdminString
    MAX-ACCESS   read-only
    STATUS       current
    DESCRIPTION
        "Cisco Firepower firmware:Image:fsmDescr managed object property"
    ::= { cfprFirmwareImageEntry 8 }

cfprFirmwareImageFsmPrev OBJECT-TYPE
    SYNTAX       SnmpAdminString
    MAX-ACCESS   read-only
    STATUS       current
    DESCRIPTION
        "Cisco Firepower firmware:Image:fsmPrev managed object property"
    ::= { cfprFirmwareImageEntry 9 }

cfprFirmwareImageFsmProgr OBJECT-TYPE
    SYNTAX       Gauge32
    MAX-ACCESS   read-only
    STATUS       current
    DESCRIPTION
        "Cisco Firepower firmware:Image:fsmProgr managed object property"
    ::= { cfprFirmwareImageEntry 10 }

cfprFirmwareImageFsmRmtInvErrCode OBJECT-TYPE
    SYNTAX       Gauge32
    MAX-ACCESS   read-only
    STATUS       current
    DESCRIPTION
        "Cisco Firepower firmware:Image:fsmRmtInvErrCode
        managed object property"
    ::= { cfprFirmwareImageEntry 11 }

cfprFirmwareImageFsmRmtInvErrDescr OBJECT-TYPE
    SYNTAX       SnmpAdminString
    MAX-ACCESS   read-only
    STATUS       current
    DESCRIPTION
        "Cisco Firepower firmware:Image:fsmRmtInvErrDescr
        managed object property"
    ::= { cfprFirmwareImageEntry 12 }

cfprFirmwareImageFsmRmtInvRslt OBJECT-TYPE
    SYNTAX       CfprConditionRemoteInvRslt
    MAX-ACCESS   read-only
    STATUS       current
    DESCRIPTION
        "Cisco Firepower firmware:Image:fsmRmtInvRslt managed
        object property"
    ::= { cfprFirmwareImageEntry 13 }

cfprFirmwareImageFsmStageDescr OBJECT-TYPE
    SYNTAX       SnmpAdminString
    MAX-ACCESS   read-only
    STATUS       current
    DESCRIPTION
        "Cisco Firepower firmware:Image:fsmStageDescr managed
        object property"
    ::= { cfprFirmwareImageEntry 14 }

cfprFirmwareImageFsmStamp OBJECT-TYPE
    SYNTAX       DateAndTime
    MAX-ACCESS   read-only
    STATUS       current
    DESCRIPTION
        "Cisco Firepower firmware:Image:fsmStamp managed object property"
    ::= { cfprFirmwareImageEntry 15 }

cfprFirmwareImageFsmStatus OBJECT-TYPE
    SYNTAX       SnmpAdminString
    MAX-ACCESS   read-only
    STATUS       current
    DESCRIPTION
        "Cisco Firepower firmware:Image:fsmStatus managed object property"
    ::= { cfprFirmwareImageEntry 16 }

cfprFirmwareImageFsmTry OBJECT-TYPE
    SYNTAX       Gauge32
    MAX-ACCESS   read-only
    STATUS       current
    DESCRIPTION
        "Cisco Firepower firmware:Image:fsmTry managed object property"
    ::= { cfprFirmwareImageEntry 17 }

cfprFirmwareImageImagePresence OBJECT-TYPE
    SYNTAX       CfprFirmwareImagePresence
    MAX-ACCESS   read-only
    STATUS       current
    DESCRIPTION
        "Cisco Firepower firmware:Image:imagePresence managed
        object property"
    ::= { cfprFirmwareImageEntry 18 }

cfprFirmwareImageIntId OBJECT-TYPE
    SYNTAX       SnmpAdminString
    MAX-ACCESS   read-only
    STATUS       current
    DESCRIPTION
        "Cisco Firepower firmware:Image:intId managed object property"
    ::= { cfprFirmwareImageEntry 19 }

cfprFirmwareImageInvTag OBJECT-TYPE
    SYNTAX       SnmpAdminString
    MAX-ACCESS   read-only
    STATUS       current
    DESCRIPTION
        "Cisco Firepower firmware:Image:invTag managed object property"
    ::= { cfprFirmwareImageEntry 20 }

cfprFirmwareImageIsoname OBJECT-TYPE
    SYNTAX       SnmpAdminString
    MAX-ACCESS   read-only
    STATUS       current
    DESCRIPTION
        "Cisco Firepower firmware:Image:isoname managed object property"
    ::= { cfprFirmwareImageEntry 21 }

cfprFirmwareImageLocation OBJECT-TYPE
    SYNTAX       SnmpAdminString
    MAX-ACCESS   read-only
    STATUS       current
    DESCRIPTION
        "Cisco Firepower firmware:Image:location managed object property"
    ::= { cfprFirmwareImageEntry 22 }

cfprFirmwareImageName OBJECT-TYPE
    SYNTAX       SnmpAdminString
    MAX-ACCESS   read-only
    STATUS       current
    DESCRIPTION
        "Cisco Firepower firmware:Image:name managed object property"
    ::= { cfprFirmwareImageEntry 23 }

cfprFirmwareImagePolicyLevel OBJECT-TYPE
    SYNTAX       Gauge32
    MAX-ACCESS   read-only
    STATUS       current
    DESCRIPTION
        "Cisco Firepower firmware:Image:policyLevel managed
        object property"
    ::= { cfprFirmwareImageEntry 24 }

cfprFirmwareImagePolicyOwner OBJECT-TYPE
    SYNTAX       CfprPolicyPolicyOwner
    MAX-ACCESS   read-only
    STATUS       current
    DESCRIPTION
        "Cisco Firepower firmware:Image:policyOwner managed
        object property"
    ::= { cfprFirmwareImageEntry 25 }

cfprFirmwareImageSize OBJECT-TYPE
    SYNTAX       Unsigned64
    MAX-ACCESS   read-only
    STATUS       current
    DESCRIPTION
        "Cisco Firepower firmware:Image:size managed object property"
    ::= { cfprFirmwareImageEntry 26 }

cfprFirmwareImageType OBJECT-TYPE
    SYNTAX       CfprFirmwareType
    MAX-ACCESS   read-only
    STATUS       current
    DESCRIPTION
        "Cisco Firepower firmware:Image:type managed object property"
    ::= { cfprFirmwareImageEntry 27 }

cfprFirmwareImageVersion OBJECT-TYPE
    SYNTAX       SnmpAdminString
    MAX-ACCESS   read-only
    STATUS       current
    DESCRIPTION
        "Cisco Firepower firmware:Image:version managed object property"
    ::= { cfprFirmwareImageEntry 28 }

cfprFirmwareImageFsmTable OBJECT-TYPE
    SYNTAX           SEQUENCE OF CfprFirmwareImageFsmEntry
    MAX-ACCESS       not-accessible
    STATUS           current
    DESCRIPTION
        "Cisco Firepower firmware:ImageFsm managed object table"
    ::= { cfprFirmwareObjects 31 }

cfprFirmwareImageFsmEntry OBJECT-TYPE
    SYNTAX           CfprFirmwareImageFsmEntry
    MAX-ACCESS       not-accessible
    STATUS           current
    DESCRIPTION
        "Entry for the cfprFirmwareImageFsmTable table."
    INDEX { cfprFirmwareImageFsmInstanceId }
    ::= { cfprFirmwareImageFsmTable 1 }

CfprFirmwareImageFsmEntry ::= SEQUENCE {
    cfprFirmwareImageFsmInstanceId                                   CfprManagedObjectId,
    cfprFirmwareImageFsmDn                                           CfprManagedObjectDn,
    cfprFirmwareImageFsmRn                                           SnmpAdminString,
    cfprFirmwareImageFsmCompletionTime                               DateAndTime,
    cfprFirmwareImageFsmCurrentFsm                                   CfprFirmwareImageFsmCurrentFsm,
    cfprFirmwareImageFsmDescrData                                    SnmpAdminString,
    cfprFirmwareImageFsmFsmStatus                                    CfprFsmFsmStageStatus,
    cfprFirmwareImageFsmProgress                                     Gauge32,
    cfprFirmwareImageFsmRmtErrCode                                   Gauge32,
    cfprFirmwareImageFsmRmtErrDescr                                  SnmpAdminString,
    cfprFirmwareImageFsmRmtRslt                                      CfprConditionRemoteInvRslt
}

cfprFirmwareImageFsmInstanceId OBJECT-TYPE
    SYNTAX       CfprManagedObjectId
    MAX-ACCESS   not-accessible
    STATUS       current
    DESCRIPTION
        "Instance identifier of the managed object."
    ::= { cfprFirmwareImageFsmEntry 1 }

cfprFirmwareImageFsmDn OBJECT-TYPE
    SYNTAX       CfprManagedObjectDn
    MAX-ACCESS   read-only
    STATUS       current
    DESCRIPTION
        "Cisco Firepower firmware:ImageFsm:dn managed object property"
    ::= { cfprFirmwareImageFsmEntry 2 }

cfprFirmwareImageFsmRn OBJECT-TYPE
    SYNTAX       SnmpAdminString
    MAX-ACCESS   read-only
    STATUS       current
    DESCRIPTION
        "Cisco Firepower firmware:ImageFsm:rn managed object property"
    ::= { cfprFirmwareImageFsmEntry 3 }

cfprFirmwareImageFsmCompletionTime OBJECT-TYPE
    SYNTAX       DateAndTime
    MAX-ACCESS   read-only
    STATUS       current
    DESCRIPTION
        "Cisco Firepower firmware:ImageFsm:completionTime
        managed object property"
    ::= { cfprFirmwareImageFsmEntry 4 }

cfprFirmwareImageFsmCurrentFsm OBJECT-TYPE
    SYNTAX       CfprFirmwareImageFsmCurrentFsm
    MAX-ACCESS   read-only
    STATUS       current
    DESCRIPTION
        "Cisco Firepower firmware:ImageFsm:currentFsm managed
        object property"
    ::= { cfprFirmwareImageFsmEntry 5 }

cfprFirmwareImageFsmDescrData OBJECT-TYPE
    SYNTAX       SnmpAdminString
    MAX-ACCESS   read-only
    STATUS       current
    DESCRIPTION
        "Cisco Firepower firmware:ImageFsm:descr managed object property"
    ::= { cfprFirmwareImageFsmEntry 6 }

cfprFirmwareImageFsmFsmStatus OBJECT-TYPE
    SYNTAX       CfprFsmFsmStageStatus
    MAX-ACCESS   read-only
    STATUS       current
    DESCRIPTION
        "Cisco Firepower firmware:ImageFsm:fsmStatus managed
        object property"
    ::= { cfprFirmwareImageFsmEntry 7 }

cfprFirmwareImageFsmProgress OBJECT-TYPE
    SYNTAX       Gauge32
    MAX-ACCESS   read-only
    STATUS       current
    DESCRIPTION
        "Cisco Firepower firmware:ImageFsm:progress managed
        object property"
    ::= { cfprFirmwareImageFsmEntry 8 }

cfprFirmwareImageFsmRmtErrCode OBJECT-TYPE
    SYNTAX       Gauge32
    MAX-ACCESS   read-only
    STATUS       current
    DESCRIPTION
        "Cisco Firepower firmware:ImageFsm:rmtErrCode managed
        object property"
    ::= { cfprFirmwareImageFsmEntry 9 }

cfprFirmwareImageFsmRmtErrDescr OBJECT-TYPE
    SYNTAX       SnmpAdminString
    MAX-ACCESS   read-only
    STATUS       current
    DESCRIPTION
        "Cisco Firepower firmware:ImageFsm:rmtErrDescr
        managed object property"
    ::= { cfprFirmwareImageFsmEntry 10 }

cfprFirmwareImageFsmRmtRslt OBJECT-TYPE
    SYNTAX       CfprConditionRemoteInvRslt
    MAX-ACCESS   read-only
    STATUS       current
    DESCRIPTION
        "Cisco Firepower firmware:ImageFsm:rmtRslt managed
        object property"
    ::= { cfprFirmwareImageFsmEntry 11 }

cfprFirmwareImageFsmStageTable OBJECT-TYPE
    SYNTAX           SEQUENCE OF CfprFirmwareImageFsmStageEntry
    MAX-ACCESS       not-accessible
    STATUS           current
    DESCRIPTION
        "Cisco Firepower firmware:ImageFsmStage managed object table"
    ::= { cfprFirmwareObjects 32 }

cfprFirmwareImageFsmStageEntry OBJECT-TYPE
    SYNTAX           CfprFirmwareImageFsmStageEntry
    MAX-ACCESS       not-accessible
    STATUS           current
    DESCRIPTION
        "Entry for the cfprFirmwareImageFsmStageTable table."
    INDEX { cfprFirmwareImageFsmStageInstanceId }
    ::= { cfprFirmwareImageFsmStageTable 1 }

CfprFirmwareImageFsmStageEntry ::= SEQUENCE {
    cfprFirmwareImageFsmStageInstanceId                              CfprManagedObjectId,
    cfprFirmwareImageFsmStageDn                                      CfprManagedObjectDn,
    cfprFirmwareImageFsmStageRn                                      SnmpAdminString,
    cfprFirmwareImageFsmStageDescrData                               SnmpAdminString,
    cfprFirmwareImageFsmStageLastUpdateTime                          DateAndTime,
    cfprFirmwareImageFsmStageName                                    CfprFirmwareImageFsmStageName,
    cfprFirmwareImageFsmStageOrder                                   Gauge32,
    cfprFirmwareImageFsmStageRetry                                   Gauge32,
    cfprFirmwareImageFsmStageStageStatus                             CfprFsmFsmStageStatus
}

cfprFirmwareImageFsmStageInstanceId OBJECT-TYPE
    SYNTAX       CfprManagedObjectId
    MAX-ACCESS   not-accessible
    STATUS       current
    DESCRIPTION
        "Instance identifier of the managed object."
    ::= { cfprFirmwareImageFsmStageEntry 1 }

cfprFirmwareImageFsmStageDn OBJECT-TYPE
    SYNTAX       CfprManagedObjectDn
    MAX-ACCESS   read-only
    STATUS       current
    DESCRIPTION
        "Cisco Firepower firmware:ImageFsmStage:dn managed
        object property"
    ::= { cfprFirmwareImageFsmStageEntry 2 }

cfprFirmwareImageFsmStageRn OBJECT-TYPE
    SYNTAX       SnmpAdminString
    MAX-ACCESS   read-only
    STATUS       current
    DESCRIPTION
        "Cisco Firepower firmware:ImageFsmStage:rn managed
        object property"
    ::= { cfprFirmwareImageFsmStageEntry 3 }

cfprFirmwareImageFsmStageDescrData OBJECT-TYPE
    SYNTAX       SnmpAdminString
    MAX-ACCESS   read-only
    STATUS       current
    DESCRIPTION
        "Cisco Firepower firmware:ImageFsmStage:descr managed
        object property"
    ::= { cfprFirmwareImageFsmStageEntry 4 }

cfprFirmwareImageFsmStageLastUpdateTime OBJECT-TYPE
    SYNTAX       DateAndTime
    MAX-ACCESS   read-only
    STATUS       current
    DESCRIPTION
        "Cisco Firepower firmware:ImageFsmStage:lastUpdateTime
        managed object property"
    ::= { cfprFirmwareImageFsmStageEntry 5 }

cfprFirmwareImageFsmStageName OBJECT-TYPE
    SYNTAX       CfprFirmwareImageFsmStageName
    MAX-ACCESS   read-only
    STATUS       current
    DESCRIPTION
        "Cisco Firepower firmware:ImageFsmStage:name managed
        object property"
    ::= { cfprFirmwareImageFsmStageEntry 6 }

cfprFirmwareImageFsmStageOrder OBJECT-TYPE
    SYNTAX       Gauge32
    MAX-ACCESS   read-only
    STATUS       current
    DESCRIPTION
        "Cisco Firepower firmware:ImageFsmStage:order managed
        object property"
    ::= { cfprFirmwareImageFsmStageEntry 7 }

cfprFirmwareImageFsmStageRetry OBJECT-TYPE
    SYNTAX       Gauge32
    MAX-ACCESS   read-only
    STATUS       current
    DESCRIPTION
        "Cisco Firepower firmware:ImageFsmStage:retry managed
        object property"
    ::= { cfprFirmwareImageFsmStageEntry 8 }

cfprFirmwareImageFsmStageStageStatus OBJECT-TYPE
    SYNTAX       CfprFsmFsmStageStatus
    MAX-ACCESS   read-only
    STATUS       current
    DESCRIPTION
        "Cisco Firepower firmware:ImageFsmStage:stageStatus
        managed object property"
    ::= { cfprFirmwareImageFsmStageEntry 9 }

cfprFirmwareImageFsmTaskTable OBJECT-TYPE
    SYNTAX           SEQUENCE OF CfprFirmwareImageFsmTaskEntry
    MAX-ACCESS       not-accessible
    STATUS           current
    DESCRIPTION
        "Cisco Firepower firmware:ImageFsmTask managed object table"
    ::= { cfprFirmwareObjects 33 }

cfprFirmwareImageFsmTaskEntry OBJECT-TYPE
    SYNTAX           CfprFirmwareImageFsmTaskEntry
    MAX-ACCESS       not-accessible
    STATUS           current
    DESCRIPTION
        "Entry for the cfprFirmwareImageFsmTaskTable table."
    INDEX { cfprFirmwareImageFsmTaskInstanceId }
    ::= { cfprFirmwareImageFsmTaskTable 1 }

CfprFirmwareImageFsmTaskEntry ::= SEQUENCE {
    cfprFirmwareImageFsmTaskInstanceId                               CfprManagedObjectId,
    cfprFirmwareImageFsmTaskDn                                       CfprManagedObjectDn,
    cfprFirmwareImageFsmTaskRn                                       SnmpAdminString,
    cfprFirmwareImageFsmTaskCompletion                               CfprFsmCompletion,
    cfprFirmwareImageFsmTaskFlags                                    CfprFsmFlags,
    cfprFirmwareImageFsmTaskItem                                     CfprFirmwareImageFsmTaskItem,
    cfprFirmwareImageFsmTaskSeqId                                    Gauge32
}

cfprFirmwareImageFsmTaskInstanceId OBJECT-TYPE
    SYNTAX       CfprManagedObjectId
    MAX-ACCESS   not-accessible
    STATUS       current
    DESCRIPTION
        "Instance identifier of the managed object."
    ::= { cfprFirmwareImageFsmTaskEntry 1 }

cfprFirmwareImageFsmTaskDn OBJECT-TYPE
    SYNTAX       CfprManagedObjectDn
    MAX-ACCESS   read-only
    STATUS       current
    DESCRIPTION
        "Cisco Firepower firmware:ImageFsmTask:dn managed object property"
    ::= { cfprFirmwareImageFsmTaskEntry 2 }

cfprFirmwareImageFsmTaskRn OBJECT-TYPE
    SYNTAX       SnmpAdminString
    MAX-ACCESS   read-only
    STATUS       current
    DESCRIPTION
        "Cisco Firepower firmware:ImageFsmTask:rn managed object property"
    ::= { cfprFirmwareImageFsmTaskEntry 3 }

cfprFirmwareImageFsmTaskCompletion OBJECT-TYPE
    SYNTAX       CfprFsmCompletion
    MAX-ACCESS   read-only
    STATUS       current
    DESCRIPTION
        "Cisco Firepower firmware:ImageFsmTask:completion
        managed object property"
    ::= { cfprFirmwareImageFsmTaskEntry 4 }

cfprFirmwareImageFsmTaskFlags OBJECT-TYPE
    SYNTAX       CfprFsmFlags
    MAX-ACCESS   read-only
    STATUS       current
    DESCRIPTION
        "Cisco Firepower firmware:ImageFsmTask:flags managed
        object property"
    ::= { cfprFirmwareImageFsmTaskEntry 5 }

cfprFirmwareImageFsmTaskItem OBJECT-TYPE
    SYNTAX       CfprFirmwareImageFsmTaskItem
    MAX-ACCESS   read-only
    STATUS       current
    DESCRIPTION
        "Cisco Firepower firmware:ImageFsmTask:item managed
        object property"
    ::= { cfprFirmwareImageFsmTaskEntry 6 }

cfprFirmwareImageFsmTaskSeqId OBJECT-TYPE
    SYNTAX       Gauge32
    MAX-ACCESS   read-only
    STATUS       current
    DESCRIPTION
        "Cisco Firepower firmware:ImageFsmTask:seqId managed
        object property"
    ::= { cfprFirmwareImageFsmTaskEntry 7 }

cfprFirmwareImageLockTable OBJECT-TYPE
    SYNTAX           SEQUENCE OF CfprFirmwareImageLockEntry
    MAX-ACCESS       not-accessible
    STATUS           current
    DESCRIPTION
        "Cisco Firepower firmware:ImageLock managed object table"
    ::= { cfprFirmwareObjects 34 }

cfprFirmwareImageLockEntry OBJECT-TYPE
    SYNTAX           CfprFirmwareImageLockEntry
    MAX-ACCESS       not-accessible
    STATUS           current
    DESCRIPTION
        "Entry for the cfprFirmwareImageLockTable table."
    INDEX { cfprFirmwareImageLockInstanceId }
    ::= { cfprFirmwareImageLockTable 1 }

CfprFirmwareImageLockEntry ::= SEQUENCE {
    cfprFirmwareImageLockInstanceId                                  CfprManagedObjectId,
    cfprFirmwareImageLockDn                                          CfprManagedObjectDn,
    cfprFirmwareImageLockRn                                          SnmpAdminString,
    cfprFirmwareImageLockImageNameDn                                 SnmpAdminString,
    cfprFirmwareImageLockName                                        SnmpAdminString
}

cfprFirmwareImageLockInstanceId OBJECT-TYPE
    SYNTAX       CfprManagedObjectId
    MAX-ACCESS   not-accessible
    STATUS       current
    DESCRIPTION
        "Instance identifier of the managed object."
    ::= { cfprFirmwareImageLockEntry 1 }

cfprFirmwareImageLockDn OBJECT-TYPE
    SYNTAX       CfprManagedObjectDn
    MAX-ACCESS   read-only
    STATUS       current
    DESCRIPTION
        "Cisco Firepower firmware:ImageLock:dn managed object property"
    ::= { cfprFirmwareImageLockEntry 2 }

cfprFirmwareImageLockRn OBJECT-TYPE
    SYNTAX       SnmpAdminString
    MAX-ACCESS   read-only
    STATUS       current
    DESCRIPTION
        "Cisco Firepower firmware:ImageLock:rn managed object property"
    ::= { cfprFirmwareImageLockEntry 3 }

cfprFirmwareImageLockImageNameDn OBJECT-TYPE
    SYNTAX       SnmpAdminString
    MAX-ACCESS   read-only
    STATUS       current
    DESCRIPTION
        "Cisco Firepower firmware:ImageLock:ImageNameDn
        managed object property"
    ::= { cfprFirmwareImageLockEntry 4 }

cfprFirmwareImageLockName OBJECT-TYPE
    SYNTAX       SnmpAdminString
    MAX-ACCESS   read-only
    STATUS       current
    DESCRIPTION
        "Cisco Firepower firmware:ImageLock:name managed object property"
    ::= { cfprFirmwareImageLockEntry 5 }

cfprFirmwareInfraTable OBJECT-TYPE
    SYNTAX           SEQUENCE OF CfprFirmwareInfraEntry
    MAX-ACCESS       not-accessible
    STATUS           current
    DESCRIPTION
        "Cisco Firepower firmware:Infra managed object table"
    ::= { cfprFirmwareObjects 35 }

cfprFirmwareInfraEntry OBJECT-TYPE
    SYNTAX           CfprFirmwareInfraEntry
    MAX-ACCESS       not-accessible
    STATUS           current
    DESCRIPTION
        "Entry for the cfprFirmwareInfraTable table."
    INDEX { cfprFirmwareInfraInstanceId }
    ::= { cfprFirmwareInfraTable 1 }

CfprFirmwareInfraEntry ::= SEQUENCE {
    cfprFirmwareInfraInstanceId                                      CfprManagedObjectId,
    cfprFirmwareInfraDn                                              CfprManagedObjectDn,
    cfprFirmwareInfraRn                                              SnmpAdminString,
    cfprFirmwareInfraAdminState                                      CfprTrigAdminState,
    cfprFirmwareInfraAutoDelete                                      TruthValue,
    cfprFirmwareInfraDescr                                           SnmpAdminString,
    cfprFirmwareInfraIgnoreCap                                       TruthValue,
    cfprFirmwareInfraIntId                                           SnmpAdminString,
    cfprFirmwareInfraName                                            SnmpAdminString,
    cfprFirmwareInfraOperScheduler                                   SnmpAdminString,
    cfprFirmwareInfraOperState                                       CfprTrigTrigOperState,
    cfprFirmwareInfraOperVersion                                     SnmpAdminString,
    cfprFirmwareInfraPolicyLevel                                     Gauge32,
    cfprFirmwareInfraPolicyOwner                                     CfprPolicyPolicyOwner,
    cfprFirmwareInfraScheduler                                       SnmpAdminString
}

cfprFirmwareInfraInstanceId OBJECT-TYPE
    SYNTAX       CfprManagedObjectId
    MAX-ACCESS   not-accessible
    STATUS       current
    DESCRIPTION
        "Instance identifier of the managed object."
    ::= { cfprFirmwareInfraEntry 1 }

cfprFirmwareInfraDn OBJECT-TYPE
    SYNTAX       CfprManagedObjectDn
    MAX-ACCESS   read-only
    STATUS       current
    DESCRIPTION
        "Cisco Firepower firmware:Infra:dn managed object property"
    ::= { cfprFirmwareInfraEntry 2 }

cfprFirmwareInfraRn OBJECT-TYPE
    SYNTAX       SnmpAdminString
    MAX-ACCESS   read-only
    STATUS       current
    DESCRIPTION
        "Cisco Firepower firmware:Infra:rn managed object property"
    ::= { cfprFirmwareInfraEntry 3 }

cfprFirmwareInfraAdminState OBJECT-TYPE
    SYNTAX       CfprTrigAdminState
    MAX-ACCESS   read-only
    STATUS       current
    DESCRIPTION
        "Cisco Firepower firmware:Infra:adminState managed
        object property"
    ::= { cfprFirmwareInfraEntry 4 }

cfprFirmwareInfraAutoDelete OBJECT-TYPE
    SYNTAX       TruthValue
    MAX-ACCESS   read-only
    STATUS       current
    DESCRIPTION
        "Cisco Firepower firmware:Infra:autoDelete managed
        object property"
    ::= { cfprFirmwareInfraEntry 5 }

cfprFirmwareInfraDescr OBJECT-TYPE
    SYNTAX       SnmpAdminString
    MAX-ACCESS   read-only
    STATUS       current
    DESCRIPTION
        "Cisco Firepower firmware:Infra:descr managed object property"
    ::= { cfprFirmwareInfraEntry 6 }

cfprFirmwareInfraIgnoreCap OBJECT-TYPE
    SYNTAX       TruthValue
    MAX-ACCESS   read-only
    STATUS       current
    DESCRIPTION
        "Cisco Firepower firmware:Infra:ignoreCap managed object property"
    ::= { cfprFirmwareInfraEntry 7 }

cfprFirmwareInfraIntId OBJECT-TYPE
    SYNTAX       SnmpAdminString
    MAX-ACCESS   read-only
    STATUS       current
    DESCRIPTION
        "Cisco Firepower firmware:Infra:intId managed object property"
    ::= { cfprFirmwareInfraEntry 8 }

cfprFirmwareInfraName OBJECT-TYPE
    SYNTAX       SnmpAdminString
    MAX-ACCESS   read-only
    STATUS       current
    DESCRIPTION
        "Cisco Firepower firmware:Infra:name managed object property"
    ::= { cfprFirmwareInfraEntry 9 }

cfprFirmwareInfraOperScheduler OBJECT-TYPE
    SYNTAX       SnmpAdminString
    MAX-ACCESS   read-only
    STATUS       current
    DESCRIPTION
        "Cisco Firepower firmware:Infra:operScheduler managed
        object property"
    ::= { cfprFirmwareInfraEntry 10 }

cfprFirmwareInfraOperState OBJECT-TYPE
    SYNTAX       CfprTrigTrigOperState
    MAX-ACCESS   read-only
    STATUS       current
    DESCRIPTION
        "Cisco Firepower firmware:Infra:operState managed object property"
    ::= { cfprFirmwareInfraEntry 11 }

cfprFirmwareInfraOperVersion OBJECT-TYPE
    SYNTAX       SnmpAdminString
    MAX-ACCESS   read-only
    STATUS       current
    DESCRIPTION
        "Cisco Firepower firmware:Infra:operVersion managed
        object property"
    ::= { cfprFirmwareInfraEntry 12 }

cfprFirmwareInfraPolicyLevel OBJECT-TYPE
    SYNTAX       Gauge32
    MAX-ACCESS   read-only
    STATUS       current
    DESCRIPTION
        "Cisco Firepower firmware:Infra:policyLevel managed
        object property"
    ::= { cfprFirmwareInfraEntry 13 }

cfprFirmwareInfraPolicyOwner OBJECT-TYPE
    SYNTAX       CfprPolicyPolicyOwner
    MAX-ACCESS   read-only
    STATUS       current
    DESCRIPTION
        "Cisco Firepower firmware:Infra:policyOwner managed
        object property"
    ::= { cfprFirmwareInfraEntry 14 }

cfprFirmwareInfraScheduler OBJECT-TYPE
    SYNTAX       SnmpAdminString
    MAX-ACCESS   read-only
    STATUS       current
    DESCRIPTION
        "Cisco Firepower firmware:Infra:scheduler managed object property"
    ::= { cfprFirmwareInfraEntry 15 }

cfprFirmwareInfraPackTable OBJECT-TYPE
    SYNTAX           SEQUENCE OF CfprFirmwareInfraPackEntry
    MAX-ACCESS       not-accessible
    STATUS           current
    DESCRIPTION
        "Cisco Firepower firmware:InfraPack managed object table"
    ::= { cfprFirmwareObjects 36 }

cfprFirmwareInfraPackEntry OBJECT-TYPE
    SYNTAX           CfprFirmwareInfraPackEntry
    MAX-ACCESS       not-accessible
    STATUS           current
    DESCRIPTION
        "Entry for the cfprFirmwareInfraPackTable table."
    INDEX { cfprFirmwareInfraPackInstanceId }
    ::= { cfprFirmwareInfraPackTable 1 }

CfprFirmwareInfraPackEntry ::= SEQUENCE {
    cfprFirmwareInfraPackInstanceId                                  CfprManagedObjectId,
    cfprFirmwareInfraPackDn                                          CfprManagedObjectDn,
    cfprFirmwareInfraPackRn                                          SnmpAdminString,
    cfprFirmwareInfraPackDescr                                       SnmpAdminString,
    cfprFirmwareInfraPackForceDeploy                                 TruthValue,
    cfprFirmwareInfraPackInfraBundleName                             SnmpAdminString,
    cfprFirmwareInfraPackInfraBundleVersion                          SnmpAdminString,
    cfprFirmwareInfraPackIntId                                       SnmpAdminString,
    cfprFirmwareInfraPackMode                                        CfprFirmwarePackMode,
    cfprFirmwareInfraPackName                                        SnmpAdminString,
    cfprFirmwareInfraPackPolicyLevel                                 Gauge32,
    cfprFirmwareInfraPackPolicyOwner                                 CfprPolicyPolicyOwner,
    cfprFirmwareInfraPackStageSize                                   Gauge32,
    cfprFirmwareInfraPackUpdateTrigger                               DateAndTime
}

cfprFirmwareInfraPackInstanceId OBJECT-TYPE
    SYNTAX       CfprManagedObjectId
    MAX-ACCESS   not-accessible
    STATUS       current
    DESCRIPTION
        "Instance identifier of the managed object."
    ::= { cfprFirmwareInfraPackEntry 1 }

cfprFirmwareInfraPackDn OBJECT-TYPE
    SYNTAX       CfprManagedObjectDn
    MAX-ACCESS   read-only
    STATUS       current
    DESCRIPTION
        "Cisco Firepower firmware:InfraPack:dn managed object property"
    ::= { cfprFirmwareInfraPackEntry 2 }

cfprFirmwareInfraPackRn OBJECT-TYPE
    SYNTAX       SnmpAdminString
    MAX-ACCESS   read-only
    STATUS       current
    DESCRIPTION
        "Cisco Firepower firmware:InfraPack:rn managed object property"
    ::= { cfprFirmwareInfraPackEntry 3 }

cfprFirmwareInfraPackDescr OBJECT-TYPE
    SYNTAX       SnmpAdminString
    MAX-ACCESS   read-only
    STATUS       current
    DESCRIPTION
        "Cisco Firepower firmware:InfraPack:descr managed object property"
    ::= { cfprFirmwareInfraPackEntry 4 }

cfprFirmwareInfraPackForceDeploy OBJECT-TYPE
    SYNTAX       TruthValue
    MAX-ACCESS   read-only
    STATUS       current
    DESCRIPTION
        "Cisco Firepower firmware:InfraPack:forceDeploy
        managed object property"
    ::= { cfprFirmwareInfraPackEntry 5 }

cfprFirmwareInfraPackInfraBundleName OBJECT-TYPE
    SYNTAX       SnmpAdminString
    MAX-ACCESS   read-only
    STATUS       current
    DESCRIPTION
        "Cisco Firepower firmware:InfraPack:infraBundleName
        managed object property"
    ::= { cfprFirmwareInfraPackEntry 6 }

cfprFirmwareInfraPackInfraBundleVersion OBJECT-TYPE
    SYNTAX       SnmpAdminString
    MAX-ACCESS   read-only
    STATUS       current
    DESCRIPTION
        "Cisco Firepower firmware:InfraPack:infraBundleVersion
        managed object property"
    ::= { cfprFirmwareInfraPackEntry 7 }

cfprFirmwareInfraPackIntId OBJECT-TYPE
    SYNTAX       SnmpAdminString
    MAX-ACCESS   read-only
    STATUS       current
    DESCRIPTION
        "Cisco Firepower firmware:InfraPack:intId managed object property"
    ::= { cfprFirmwareInfraPackEntry 8 }

cfprFirmwareInfraPackMode OBJECT-TYPE
    SYNTAX       CfprFirmwarePackMode
    MAX-ACCESS   read-only
    STATUS       current
    DESCRIPTION
        "Cisco Firepower firmware:InfraPack:mode managed object property"
    ::= { cfprFirmwareInfraPackEntry 9 }

cfprFirmwareInfraPackName OBJECT-TYPE
    SYNTAX       SnmpAdminString
    MAX-ACCESS   read-only
    STATUS       current
    DESCRIPTION
        "Cisco Firepower firmware:InfraPack:name managed object property"
    ::= { cfprFirmwareInfraPackEntry 10 }

cfprFirmwareInfraPackPolicyLevel OBJECT-TYPE
    SYNTAX       Gauge32
    MAX-ACCESS   read-only
    STATUS       current
    DESCRIPTION
        "Cisco Firepower firmware:InfraPack:policyLevel
        managed object property"
    ::= { cfprFirmwareInfraPackEntry 11 }

cfprFirmwareInfraPackPolicyOwner OBJECT-TYPE
    SYNTAX       CfprPolicyPolicyOwner
    MAX-ACCESS   read-only
    STATUS       current
    DESCRIPTION
        "Cisco Firepower firmware:InfraPack:policyOwner
        managed object property"
    ::= { cfprFirmwareInfraPackEntry 12 }

cfprFirmwareInfraPackStageSize OBJECT-TYPE
    SYNTAX       Gauge32
    MAX-ACCESS   read-only
    STATUS       current
    DESCRIPTION
        "Cisco Firepower firmware:InfraPack:stageSize managed
        object property"
    ::= { cfprFirmwareInfraPackEntry 13 }

cfprFirmwareInfraPackUpdateTrigger OBJECT-TYPE
    SYNTAX       DateAndTime
    MAX-ACCESS   read-only
    STATUS       current
    DESCRIPTION
        "Cisco Firepower firmware:InfraPack:updateTrigger
        managed object property"
    ::= { cfprFirmwareInfraPackEntry 14 }

cfprFirmwareInstallImpactTable OBJECT-TYPE
    SYNTAX           SEQUENCE OF CfprFirmwareInstallImpactEntry
    MAX-ACCESS       not-accessible
    STATUS           current
    DESCRIPTION
        "Cisco Firepower firmware:InstallImpact managed object table"
    ::= { cfprFirmwareObjects 37 }

cfprFirmwareInstallImpactEntry OBJECT-TYPE
    SYNTAX           CfprFirmwareInstallImpactEntry
    MAX-ACCESS       not-accessible
    STATUS           current
    DESCRIPTION
        "Entry for the cfprFirmwareInstallImpactTable table."
    INDEX { cfprFirmwareInstallImpactInstanceId }
    ::= { cfprFirmwareInstallImpactTable 1 }

CfprFirmwareInstallImpactEntry ::= SEQUENCE {
    cfprFirmwareInstallImpactInstanceId                              CfprManagedObjectId,
    cfprFirmwareInstallImpactDn                                      CfprManagedObjectDn,
    cfprFirmwareInstallImpactRn                                      SnmpAdminString,
    cfprFirmwareInstallImpactDescr                                   SnmpAdminString,
    cfprFirmwareInstallImpactKeyDn                                   SnmpAdminString,
    cfprFirmwareInstallImpactMaintPolicyDn                           SnmpAdminString,
    cfprFirmwareInstallImpactRebootPolicy                            SnmpAdminString,
    cfprFirmwareInstallImpactSubject                                 CfprFirmwareEquipmentType,
    cfprFirmwareInstallImpactType                                    CfprFirmwareImpactType
}

cfprFirmwareInstallImpactInstanceId OBJECT-TYPE
    SYNTAX       CfprManagedObjectId
    MAX-ACCESS   not-accessible
    STATUS       current
    DESCRIPTION
        "Instance identifier of the managed object."
    ::= { cfprFirmwareInstallImpactEntry 1 }

cfprFirmwareInstallImpactDn OBJECT-TYPE
    SYNTAX       CfprManagedObjectDn
    MAX-ACCESS   read-only
    STATUS       current
    DESCRIPTION
        "Cisco Firepower firmware:InstallImpact:dn managed
        object property"
    ::= { cfprFirmwareInstallImpactEntry 2 }

cfprFirmwareInstallImpactRn OBJECT-TYPE
    SYNTAX       SnmpAdminString
    MAX-ACCESS   read-only
    STATUS       current
    DESCRIPTION
        "Cisco Firepower firmware:InstallImpact:rn managed
        object property"
    ::= { cfprFirmwareInstallImpactEntry 3 }

cfprFirmwareInstallImpactDescr OBJECT-TYPE
    SYNTAX       SnmpAdminString
    MAX-ACCESS   read-only
    STATUS       current
    DESCRIPTION
        "Cisco Firepower firmware:InstallImpact:descr managed
        object property"
    ::= { cfprFirmwareInstallImpactEntry 4 }

cfprFirmwareInstallImpactKeyDn OBJECT-TYPE
    SYNTAX       SnmpAdminString
    MAX-ACCESS   read-only
    STATUS       current
    DESCRIPTION
        "Cisco Firepower firmware:InstallImpact:keyDn managed
        object property"
    ::= { cfprFirmwareInstallImpactEntry 5 }

cfprFirmwareInstallImpactMaintPolicyDn OBJECT-TYPE
    SYNTAX       SnmpAdminString
    MAX-ACCESS   read-only
    STATUS       current
    DESCRIPTION
        "Cisco Firepower firmware:InstallImpact:maintPolicyDn
        managed object property"
    ::= { cfprFirmwareInstallImpactEntry 6 }

cfprFirmwareInstallImpactRebootPolicy OBJECT-TYPE
    SYNTAX       SnmpAdminString
    MAX-ACCESS   read-only
    STATUS       current
    DESCRIPTION
        "Cisco Firepower firmware:InstallImpact:rebootPolicy
        managed object property"
    ::= { cfprFirmwareInstallImpactEntry 7 }

cfprFirmwareInstallImpactSubject OBJECT-TYPE
    SYNTAX       CfprFirmwareEquipmentType
    MAX-ACCESS   read-only
    STATUS       current
    DESCRIPTION
        "Cisco Firepower firmware:InstallImpact:subject
        managed object property"
    ::= { cfprFirmwareInstallImpactEntry 8 }

cfprFirmwareInstallImpactType OBJECT-TYPE
    SYNTAX       CfprFirmwareImpactType
    MAX-ACCESS   read-only
    STATUS       current
    DESCRIPTION
        "Cisco Firepower firmware:InstallImpact:type managed
        object property"
    ::= { cfprFirmwareInstallImpactEntry 9 }

cfprFirmwareInstallableTable OBJECT-TYPE
    SYNTAX           SEQUENCE OF CfprFirmwareInstallableEntry
    MAX-ACCESS       not-accessible
    STATUS           current
    DESCRIPTION
        "Cisco Firepower firmware:Installable managed object table"
    ::= { cfprFirmwareObjects 38 }

cfprFirmwareInstallableEntry OBJECT-TYPE
    SYNTAX           CfprFirmwareInstallableEntry
    MAX-ACCESS       not-accessible
    STATUS           current
    DESCRIPTION
        "Entry for the cfprFirmwareInstallableTable table."
    INDEX { cfprFirmwareInstallableInstanceId }
    ::= { cfprFirmwareInstallableTable 1 }

CfprFirmwareInstallableEntry ::= SEQUENCE {
    cfprFirmwareInstallableInstanceId                                CfprManagedObjectId,
    cfprFirmwareInstallableDn                                        CfprManagedObjectDn,
    cfprFirmwareInstallableRn                                        SnmpAdminString,
    cfprFirmwareInstallableChecksum                                  SnmpAdminString,
    cfprFirmwareInstallableInProgress                                Gauge32,
    cfprFirmwareInstallableIsoname                                   SnmpAdminString,
    cfprFirmwareInstallableLocation                                  SnmpAdminString,
    cfprFirmwareInstallableModel                                     SnmpAdminString,
    cfprFirmwareInstallableName                                      SnmpAdminString,
    cfprFirmwareInstallableSize                                      Unsigned64,
    cfprFirmwareInstallableType                                      CfprFirmwareType,
    cfprFirmwareInstallableVendor                                    SnmpAdminString,
    cfprFirmwareInstallableVersion                                   SnmpAdminString
}

cfprFirmwareInstallableInstanceId OBJECT-TYPE
    SYNTAX       CfprManagedObjectId
    MAX-ACCESS   not-accessible
    STATUS       current
    DESCRIPTION
        "Instance identifier of the managed object."
    ::= { cfprFirmwareInstallableEntry 1 }

cfprFirmwareInstallableDn OBJECT-TYPE
    SYNTAX       CfprManagedObjectDn
    MAX-ACCESS   read-only
    STATUS       current
    DESCRIPTION
        "Cisco Firepower firmware:Installable:dn managed object property"
    ::= { cfprFirmwareInstallableEntry 2 }

cfprFirmwareInstallableRn OBJECT-TYPE
    SYNTAX       SnmpAdminString
    MAX-ACCESS   read-only
    STATUS       current
    DESCRIPTION
        "Cisco Firepower firmware:Installable:rn managed object property"
    ::= { cfprFirmwareInstallableEntry 3 }

cfprFirmwareInstallableChecksum OBJECT-TYPE
    SYNTAX       SnmpAdminString
    MAX-ACCESS   read-only
    STATUS       current
    DESCRIPTION
        "Cisco Firepower firmware:Installable:checksum
        managed object property"
    ::= { cfprFirmwareInstallableEntry 4 }

cfprFirmwareInstallableInProgress OBJECT-TYPE
    SYNTAX       Gauge32
    MAX-ACCESS   read-only
    STATUS       current
    DESCRIPTION
        "Cisco Firepower firmware:Installable:inProgress
        managed object property"
    ::= { cfprFirmwareInstallableEntry 5 }

cfprFirmwareInstallableIsoname OBJECT-TYPE
    SYNTAX       SnmpAdminString
    MAX-ACCESS   read-only
    STATUS       current
    DESCRIPTION
        "Cisco Firepower firmware:Installable:isoname managed
        object property"
    ::= { cfprFirmwareInstallableEntry 6 }

cfprFirmwareInstallableLocation OBJECT-TYPE
    SYNTAX       SnmpAdminString
    MAX-ACCESS   read-only
    STATUS       current
    DESCRIPTION
        "Cisco Firepower firmware:Installable:location
        managed object property"
    ::= { cfprFirmwareInstallableEntry 7 }

cfprFirmwareInstallableModel OBJECT-TYPE
    SYNTAX       SnmpAdminString
    MAX-ACCESS   read-only
    STATUS       current
    DESCRIPTION
        "Cisco Firepower firmware:Installable:model managed
        object property"
    ::= { cfprFirmwareInstallableEntry 8 }

cfprFirmwareInstallableName OBJECT-TYPE
    SYNTAX       SnmpAdminString
    MAX-ACCESS   read-only
    STATUS       current
    DESCRIPTION
        "Cisco Firepower firmware:Installable:name managed
        object property"
    ::= { cfprFirmwareInstallableEntry 9 }

cfprFirmwareInstallableSize OBJECT-TYPE
    SYNTAX       Unsigned64
    MAX-ACCESS   read-only
    STATUS       current
    DESCRIPTION
        "Cisco Firepower firmware:Installable:size managed
        object property"
    ::= { cfprFirmwareInstallableEntry 10 }

cfprFirmwareInstallableType OBJECT-TYPE
    SYNTAX       CfprFirmwareType
    MAX-ACCESS   read-only
    STATUS       current
    DESCRIPTION
        "Cisco Firepower firmware:Installable:type managed
        object property"
    ::= { cfprFirmwareInstallableEntry 11 }

cfprFirmwareInstallableVendor OBJECT-TYPE
    SYNTAX       SnmpAdminString
    MAX-ACCESS   read-only
    STATUS       current
    DESCRIPTION
        "Cisco Firepower firmware:Installable:vendor managed
        object property"
    ::= { cfprFirmwareInstallableEntry 12 }

cfprFirmwareInstallableVersion OBJECT-TYPE
    SYNTAX       SnmpAdminString
    MAX-ACCESS   read-only
    STATUS       current
    DESCRIPTION
        "Cisco Firepower firmware:Installable:version managed
        object property"
    ::= { cfprFirmwareInstallableEntry 13 }

cfprFirmwarePackItemTable OBJECT-TYPE
    SYNTAX           SEQUENCE OF CfprFirmwarePackItemEntry
    MAX-ACCESS       not-accessible
    STATUS           current
    DESCRIPTION
        "Cisco Firepower firmware:PackItem managed object table"
    ::= { cfprFirmwareObjects 39 }

cfprFirmwarePackItemEntry OBJECT-TYPE
    SYNTAX           CfprFirmwarePackItemEntry
    MAX-ACCESS       not-accessible
    STATUS           current
    DESCRIPTION
        "Entry for the cfprFirmwarePackItemTable table."
    INDEX { cfprFirmwarePackItemInstanceId }
    ::= { cfprFirmwarePackItemTable 1 }

CfprFirmwarePackItemEntry ::= SEQUENCE {
    cfprFirmwarePackItemInstanceId                                   CfprManagedObjectId,
    cfprFirmwarePackItemDn                                           CfprManagedObjectDn,
    cfprFirmwarePackItemRn                                           SnmpAdminString,
    cfprFirmwarePackItemHwModel                                      SnmpAdminString,
    cfprFirmwarePackItemHwVendor                                     SnmpAdminString,
    cfprFirmwarePackItemPresence                                     CfprFirmwarePackItemPresence,
    cfprFirmwarePackItemType                                         CfprFirmwareItemType,
    cfprFirmwarePackItemVersion                                      SnmpAdminString
}

cfprFirmwarePackItemInstanceId OBJECT-TYPE
    SYNTAX       CfprManagedObjectId
    MAX-ACCESS   not-accessible
    STATUS       current
    DESCRIPTION
        "Instance identifier of the managed object."
    ::= { cfprFirmwarePackItemEntry 1 }

cfprFirmwarePackItemDn OBJECT-TYPE
    SYNTAX       CfprManagedObjectDn
    MAX-ACCESS   read-only
    STATUS       current
    DESCRIPTION
        "Cisco Firepower firmware:PackItem:dn managed object property"
    ::= { cfprFirmwarePackItemEntry 2 }

cfprFirmwarePackItemRn OBJECT-TYPE
    SYNTAX       SnmpAdminString
    MAX-ACCESS   read-only
    STATUS       current
    DESCRIPTION
        "Cisco Firepower firmware:PackItem:rn managed object property"
    ::= { cfprFirmwarePackItemEntry 3 }

cfprFirmwarePackItemHwModel OBJECT-TYPE
    SYNTAX       SnmpAdminString
    MAX-ACCESS   read-only
    STATUS       current
    DESCRIPTION
        "Cisco Firepower firmware:PackItem:hwModel managed
        object property"
    ::= { cfprFirmwarePackItemEntry 4 }

cfprFirmwarePackItemHwVendor OBJECT-TYPE
    SYNTAX       SnmpAdminString
    MAX-ACCESS   read-only
    STATUS       current
    DESCRIPTION
        "Cisco Firepower firmware:PackItem:hwVendor managed
        object property"
    ::= { cfprFirmwarePackItemEntry 5 }

cfprFirmwarePackItemPresence OBJECT-TYPE
    SYNTAX       CfprFirmwarePackItemPresence
    MAX-ACCESS   read-only
    STATUS       current
    DESCRIPTION
        "Cisco Firepower firmware:PackItem:presence managed
        object property"
    ::= { cfprFirmwarePackItemEntry 6 }

cfprFirmwarePackItemType OBJECT-TYPE
    SYNTAX       CfprFirmwareItemType
    MAX-ACCESS   read-only
    STATUS       current
    DESCRIPTION
        "Cisco Firepower firmware:PackItem:type managed object property"
    ::= { cfprFirmwarePackItemEntry 7 }

cfprFirmwarePackItemVersion OBJECT-TYPE
    SYNTAX       SnmpAdminString
    MAX-ACCESS   read-only
    STATUS       current
    DESCRIPTION
        "Cisco Firepower firmware:PackItem:version managed
        object property"
    ::= { cfprFirmwarePackItemEntry 8 }

cfprFirmwarePlatformTable OBJECT-TYPE
    SYNTAX           SEQUENCE OF CfprFirmwarePlatformEntry
    MAX-ACCESS       not-accessible
    STATUS           current
    DESCRIPTION
        "Cisco Firepower firmware:Platform managed object table"
    ::= { cfprFirmwareObjects 40 }

cfprFirmwarePlatformEntry OBJECT-TYPE
    SYNTAX           CfprFirmwarePlatformEntry
    MAX-ACCESS       not-accessible
    STATUS           current
    DESCRIPTION
        "Entry for the cfprFirmwarePlatformTable table."
    INDEX { cfprFirmwarePlatformInstanceId }
    ::= { cfprFirmwarePlatformTable 1 }

CfprFirmwarePlatformEntry ::= SEQUENCE {
    cfprFirmwarePlatformInstanceId                                   CfprManagedObjectId,
    cfprFirmwarePlatformDn                                           CfprManagedObjectDn,
    cfprFirmwarePlatformRn                                           SnmpAdminString,
    cfprFirmwarePlatformAdminState                                   CfprTrigAdminState,
    cfprFirmwarePlatformAutoDelete                                   TruthValue,
    cfprFirmwarePlatformDescr                                        SnmpAdminString,
    cfprFirmwarePlatformIgnoreCap                                    TruthValue,
    cfprFirmwarePlatformIntId                                        SnmpAdminString,
    cfprFirmwarePlatformName                                         SnmpAdminString,
    cfprFirmwarePlatformOperScheduler                                SnmpAdminString,
    cfprFirmwarePlatformOperState                                    CfprTrigTrigOperState,
    cfprFirmwarePlatformOperVersion                                  SnmpAdminString,
    cfprFirmwarePlatformPolicyLevel                                  Gauge32,
    cfprFirmwarePlatformPolicyOwner                                  CfprPolicyPolicyOwner,
    cfprFirmwarePlatformScheduler                                    SnmpAdminString
}

cfprFirmwarePlatformInstanceId OBJECT-TYPE
    SYNTAX       CfprManagedObjectId
    MAX-ACCESS   not-accessible
    STATUS       current
    DESCRIPTION
        "Instance identifier of the managed object."
    ::= { cfprFirmwarePlatformEntry 1 }

cfprFirmwarePlatformDn OBJECT-TYPE
    SYNTAX       CfprManagedObjectDn
    MAX-ACCESS   read-only
    STATUS       current
    DESCRIPTION
        "Cisco Firepower firmware:Platform:dn managed object property"
    ::= { cfprFirmwarePlatformEntry 2 }

cfprFirmwarePlatformRn OBJECT-TYPE
    SYNTAX       SnmpAdminString
    MAX-ACCESS   read-only
    STATUS       current
    DESCRIPTION
        "Cisco Firepower firmware:Platform:rn managed object property"
    ::= { cfprFirmwarePlatformEntry 3 }

cfprFirmwarePlatformAdminState OBJECT-TYPE
    SYNTAX       CfprTrigAdminState
    MAX-ACCESS   read-only
    STATUS       current
    DESCRIPTION
        "Cisco Firepower firmware:Platform:adminState managed
        object property"
    ::= { cfprFirmwarePlatformEntry 4 }

cfprFirmwarePlatformAutoDelete OBJECT-TYPE
    SYNTAX       TruthValue
    MAX-ACCESS   read-only
    STATUS       current
    DESCRIPTION
        "Cisco Firepower firmware:Platform:autoDelete managed
        object property"
    ::= { cfprFirmwarePlatformEntry 5 }

cfprFirmwarePlatformDescr OBJECT-TYPE
    SYNTAX       SnmpAdminString
    MAX-ACCESS   read-only
    STATUS       current
    DESCRIPTION
        "Cisco Firepower firmware:Platform:descr managed object property"
    ::= { cfprFirmwarePlatformEntry 6 }

cfprFirmwarePlatformIgnoreCap OBJECT-TYPE
    SYNTAX       TruthValue
    MAX-ACCESS   read-only
    STATUS       current
    DESCRIPTION
        "Cisco Firepower firmware:Platform:ignoreCap managed
        object property"
    ::= { cfprFirmwarePlatformEntry 7 }

cfprFirmwarePlatformIntId OBJECT-TYPE
    SYNTAX       SnmpAdminString
    MAX-ACCESS   read-only
    STATUS       current
    DESCRIPTION
        "Cisco Firepower firmware:Platform:intId managed object property"
    ::= { cfprFirmwarePlatformEntry 8 }

cfprFirmwarePlatformName OBJECT-TYPE
    SYNTAX       SnmpAdminString
    MAX-ACCESS   read-only
    STATUS       current
    DESCRIPTION
        "Cisco Firepower firmware:Platform:name managed object property"
    ::= { cfprFirmwarePlatformEntry 9 }

cfprFirmwarePlatformOperScheduler OBJECT-TYPE
    SYNTAX       SnmpAdminString
    MAX-ACCESS   read-only
    STATUS       current
    DESCRIPTION
        "Cisco Firepower firmware:Platform:operScheduler
        managed object property"
    ::= { cfprFirmwarePlatformEntry 10 }

cfprFirmwarePlatformOperState OBJECT-TYPE
    SYNTAX       CfprTrigTrigOperState
    MAX-ACCESS   read-only
    STATUS       current
    DESCRIPTION
        "Cisco Firepower firmware:Platform:operState managed
        object property"
    ::= { cfprFirmwarePlatformEntry 11 }

cfprFirmwarePlatformOperVersion OBJECT-TYPE
    SYNTAX       SnmpAdminString
    MAX-ACCESS   read-only
    STATUS       current
    DESCRIPTION
        "Cisco Firepower firmware:Platform:operVersion
        managed object property"
    ::= { cfprFirmwarePlatformEntry 12 }

cfprFirmwarePlatformPolicyLevel OBJECT-TYPE
    SYNTAX       Gauge32
    MAX-ACCESS   read-only
    STATUS       current
    DESCRIPTION
        "Cisco Firepower firmware:Platform:policyLevel
        managed object property"
    ::= { cfprFirmwarePlatformEntry 13 }

cfprFirmwarePlatformPolicyOwner OBJECT-TYPE
    SYNTAX       CfprPolicyPolicyOwner
    MAX-ACCESS   read-only
    STATUS       current
    DESCRIPTION
        "Cisco Firepower firmware:Platform:policyOwner
        managed object property"
    ::= { cfprFirmwarePlatformEntry 14 }

cfprFirmwarePlatformScheduler OBJECT-TYPE
    SYNTAX       SnmpAdminString
    MAX-ACCESS   read-only
    STATUS       current
    DESCRIPTION
        "Cisco Firepower firmware:Platform:scheduler managed
        object property"
    ::= { cfprFirmwarePlatformEntry 15 }

cfprFirmwarePlatformBundleTypeCapProviderTable OBJECT-TYPE
    SYNTAX           SEQUENCE OF CfprFirmwarePlatformBundleTypeCapProviderEntry
    MAX-ACCESS       not-accessible
    STATUS           current
    DESCRIPTION
        "Cisco Firepower firmware:PlatformBundleTypeCapProvider
        managed object table"
    ::= { cfprFirmwareObjects 41 }

cfprFirmwarePlatformBundleTypeCapProviderEntry OBJECT-TYPE
    SYNTAX           CfprFirmwarePlatformBundleTypeCapProviderEntry
    MAX-ACCESS       not-accessible
    STATUS           current
    DESCRIPTION
        "Entry for the cfprFirmwarePlatformBundleTypeCapProviderTable table."
    INDEX { cfprFirmwarePlatformBundleTypeCapProviderInstanceId }
    ::= { cfprFirmwarePlatformBundleTypeCapProviderTable 1 }

CfprFirmwarePlatformBundleTypeCapProviderEntry ::= SEQUENCE {
    cfprFirmwarePlatformBundleTypeCapProviderInstanceId              CfprManagedObjectId,
    cfprFirmwarePlatformBundleTypeCapProviderDn                      CfprManagedObjectDn,
    cfprFirmwarePlatformBundleTypeCapProviderRn                      SnmpAdminString,
    cfprFirmwarePlatformBundleTypeCapProviderDeleted                 TruthValue,
    cfprFirmwarePlatformBundleTypeCapProviderDeprecated              TruthValue,
    cfprFirmwarePlatformBundleTypeCapProviderElementLoadFailures     Gauge32,
    cfprFirmwarePlatformBundleTypeCapProviderElementsLoaded          Gauge32,
    cfprFirmwarePlatformBundleTypeCapProviderGencount                Gauge32,
    cfprFirmwarePlatformBundleTypeCapProviderLoadErrors              Gauge32,
    cfprFirmwarePlatformBundleTypeCapProviderLoadWarnings            Gauge32,
    cfprFirmwarePlatformBundleTypeCapProviderMgmtPlaneVer            SnmpAdminString,
    cfprFirmwarePlatformBundleTypeCapProviderModel                   SnmpAdminString,
    cfprFirmwarePlatformBundleTypeCapProviderPlatformType            CfprFirmwarePlatformType,
    cfprFirmwarePlatformBundleTypeCapProviderVendor                  SnmpAdminString
}

cfprFirmwarePlatformBundleTypeCapProviderInstanceId OBJECT-TYPE
    SYNTAX       CfprManagedObjectId
    MAX-ACCESS   not-accessible
    STATUS       current
    DESCRIPTION
        "Instance identifier of the managed object."
    ::= { cfprFirmwarePlatformBundleTypeCapProviderEntry 1 }

cfprFirmwarePlatformBundleTypeCapProviderDn OBJECT-TYPE
    SYNTAX       CfprManagedObjectDn
    MAX-ACCESS   read-only
    STATUS       current
    DESCRIPTION
        "Cisco Firepower firmware:PlatformBundleTypeCapProvider:dn
        managed object property"
    ::= { cfprFirmwarePlatformBundleTypeCapProviderEntry 2 }

cfprFirmwarePlatformBundleTypeCapProviderRn OBJECT-TYPE
    SYNTAX       SnmpAdminString
    MAX-ACCESS   read-only
    STATUS       current
    DESCRIPTION
        "Cisco Firepower firmware:PlatformBundleTypeCapProvider:rn
        managed object property"
    ::= { cfprFirmwarePlatformBundleTypeCapProviderEntry 3 }

cfprFirmwarePlatformBundleTypeCapProviderDeleted OBJECT-TYPE
    SYNTAX       TruthValue
    MAX-ACCESS   read-only
    STATUS       current
    DESCRIPTION
        "Cisco Firepower firmware:PlatformBundleTypeCapProvider:deleted
        managed object property"
    ::= { cfprFirmwarePlatformBundleTypeCapProviderEntry 4 }

cfprFirmwarePlatformBundleTypeCapProviderDeprecated OBJECT-TYPE
    SYNTAX       TruthValue
    MAX-ACCESS   read-only
    STATUS       current
    DESCRIPTION
        "Cisco Firepower firmware:PlatformBundleTypeCapProvider:deprecated
         managed object property"
    ::= { cfprFirmwarePlatformBundleTypeCapProviderEntry 5 }

cfprFirmwarePlatformBundleTypeCapProviderElementLoadFailures OBJECT-TYPE
    SYNTAX       Gauge32
    MAX-ACCESS   read-only
    STATUS       current
    DESCRIPTION
        "Cisco Firepower firmware:PlatformBundleTypeCapProvider:elementLoa
        dFailures managed object property"
    ::= { cfprFirmwarePlatformBundleTypeCapProviderEntry 6 }

cfprFirmwarePlatformBundleTypeCapProviderElementsLoaded OBJECT-TYPE
    SYNTAX       Gauge32
    MAX-ACCESS   read-only
    STATUS       current
    DESCRIPTION
        "Cisco Firepower firmware:PlatformBundleTypeCapProvider:elementsLo
        aded managed object property"
    ::= { cfprFirmwarePlatformBundleTypeCapProviderEntry 7 }

cfprFirmwarePlatformBundleTypeCapProviderGencount OBJECT-TYPE
    SYNTAX       Gauge32
    MAX-ACCESS   read-only
    STATUS       current
    DESCRIPTION
        "Cisco Firepower firmware:PlatformBundleTypeCapProvider:gencount
        managed object property"
    ::= { cfprFirmwarePlatformBundleTypeCapProviderEntry 8 }

cfprFirmwarePlatformBundleTypeCapProviderLoadErrors OBJECT-TYPE
    SYNTAX       Gauge32
    MAX-ACCESS   read-only
    STATUS       current
    DESCRIPTION
        "Cisco Firepower firmware:PlatformBundleTypeCapProvider:loadErrors
         managed object property"
    ::= { cfprFirmwarePlatformBundleTypeCapProviderEntry 9 }

cfprFirmwarePlatformBundleTypeCapProviderLoadWarnings OBJECT-TYPE
    SYNTAX       Gauge32
    MAX-ACCESS   read-only
    STATUS       current
    DESCRIPTION
        "Cisco Firepower firmware:PlatformBundleTypeCapProvider:loadWarnin
        gs managed object property"
    ::= { cfprFirmwarePlatformBundleTypeCapProviderEntry 10 }

cfprFirmwarePlatformBundleTypeCapProviderMgmtPlaneVer OBJECT-TYPE
    SYNTAX       SnmpAdminString
    MAX-ACCESS   read-only
    STATUS       current
    DESCRIPTION
        "Cisco Firepower firmware:PlatformBundleTypeCapProvider:mgmtPlaneV
        er managed object property"
    ::= { cfprFirmwarePlatformBundleTypeCapProviderEntry 11 }

cfprFirmwarePlatformBundleTypeCapProviderModel OBJECT-TYPE
    SYNTAX       SnmpAdminString
    MAX-ACCESS   read-only
    STATUS       current
    DESCRIPTION
        "Cisco Firepower firmware:PlatformBundleTypeCapProvider:model
        managed object property"
    ::= { cfprFirmwarePlatformBundleTypeCapProviderEntry 12 }

cfprFirmwarePlatformBundleTypeCapProviderPlatformType OBJECT-TYPE
    SYNTAX       CfprFirmwarePlatformType
    MAX-ACCESS   read-only
    STATUS       current
    DESCRIPTION
        "Cisco Firepower firmware:PlatformBundleTypeCapProvider:platformTy
        pe managed object property"
    ::= { cfprFirmwarePlatformBundleTypeCapProviderEntry 13 }

cfprFirmwarePlatformBundleTypeCapProviderVendor OBJECT-TYPE
    SYNTAX       SnmpAdminString
    MAX-ACCESS   read-only
    STATUS       current
    DESCRIPTION
        "Cisco Firepower firmware:PlatformBundleTypeCapProvider:vendor
        managed object property"
    ::= { cfprFirmwarePlatformBundleTypeCapProviderEntry 14 }

cfprFirmwarePlatformPackTable OBJECT-TYPE
    SYNTAX           SEQUENCE OF CfprFirmwarePlatformPackEntry
    MAX-ACCESS       not-accessible
    STATUS           current
    DESCRIPTION
        "Cisco Firepower firmware:PlatformPack managed object table"
    ::= { cfprFirmwareObjects 42 }

cfprFirmwarePlatformPackEntry OBJECT-TYPE
    SYNTAX           CfprFirmwarePlatformPackEntry
    MAX-ACCESS       not-accessible
    STATUS           current
    DESCRIPTION
        "Entry for the cfprFirmwarePlatformPackTable table."
    INDEX { cfprFirmwarePlatformPackInstanceId }
    ::= { cfprFirmwarePlatformPackTable 1 }

CfprFirmwarePlatformPackEntry ::= SEQUENCE {
    cfprFirmwarePlatformPackInstanceId                               CfprManagedObjectId,
    cfprFirmwarePlatformPackDn                                       CfprManagedObjectDn,
    cfprFirmwarePlatformPackRn                                       SnmpAdminString,
    cfprFirmwarePlatformPackDescr                                    SnmpAdminString,
    cfprFirmwarePlatformPackForceDeploy                              TruthValue,
    cfprFirmwarePlatformPackFsmDescr                                 SnmpAdminString,
    cfprFirmwarePlatformPackFsmFlags                                 SnmpAdminString,
    cfprFirmwarePlatformPackFsmPrev                                  SnmpAdminString,
    cfprFirmwarePlatformPackFsmProgr                                 Gauge32,
    cfprFirmwarePlatformPackFsmRmtInvErrCode                         Gauge32,
    cfprFirmwarePlatformPackFsmRmtInvErrDescr                        SnmpAdminString,
    cfprFirmwarePlatformPackFsmRmtInvRslt                            CfprConditionRemoteInvRslt,
    cfprFirmwarePlatformPackFsmStageDescr                            SnmpAdminString,
    cfprFirmwarePlatformPackFsmStamp                                 DateAndTime,
    cfprFirmwarePlatformPackFsmStatus                                SnmpAdminString,
    cfprFirmwarePlatformPackFsmTry                                   Gauge32,
    cfprFirmwarePlatformPackIntId                                    SnmpAdminString,
    cfprFirmwarePlatformPackMode                                     CfprFirmwarePackMode,
    cfprFirmwarePlatformPackName                                     SnmpAdminString,
    cfprFirmwarePlatformPackPlatformBundleName                       SnmpAdminString,
    cfprFirmwarePlatformPackPlatformBundleVersion                    SnmpAdminString,
    cfprFirmwarePlatformPackPolicyLevel                              Gauge32,
    cfprFirmwarePlatformPackPolicyOwner                              CfprPolicyPolicyOwner,
    cfprFirmwarePlatformPackPreviousBundleVersion                    SnmpAdminString,
    cfprFirmwarePlatformPackRestoreVersion                           TruthValue,
    cfprFirmwarePlatformPackSerializeHostUpgrade                     TruthValue,
    cfprFirmwarePlatformPackSkipManagerValidation                    TruthValue,
    cfprFirmwarePlatformPackStageSize                                Gauge32,
    cfprFirmwarePlatformPackUpdateTrigger                            DateAndTime,
    cfprFirmwarePlatformPackPrevBundleVersion                        SnmpAdminString,
    cfprFirmwarePlatformPackVersionChecked                           TruthValue
}

cfprFirmwarePlatformPackInstanceId OBJECT-TYPE
    SYNTAX       CfprManagedObjectId
    MAX-ACCESS   not-accessible
    STATUS       current
    DESCRIPTION
        "Instance identifier of the managed object."
    ::= { cfprFirmwarePlatformPackEntry 1 }

cfprFirmwarePlatformPackDn OBJECT-TYPE
    SYNTAX       CfprManagedObjectDn
    MAX-ACCESS   read-only
    STATUS       current
    DESCRIPTION
        "Cisco Firepower firmware:PlatformPack:dn managed object property"
    ::= { cfprFirmwarePlatformPackEntry 2 }

cfprFirmwarePlatformPackRn OBJECT-TYPE
    SYNTAX       SnmpAdminString
    MAX-ACCESS   read-only
    STATUS       current
    DESCRIPTION
        "Cisco Firepower firmware:PlatformPack:rn managed object property"
    ::= { cfprFirmwarePlatformPackEntry 3 }

cfprFirmwarePlatformPackDescr OBJECT-TYPE
    SYNTAX       SnmpAdminString
    MAX-ACCESS   read-only
    STATUS       current
    DESCRIPTION
        "Cisco Firepower firmware:PlatformPack:descr managed
        object property"
    ::= { cfprFirmwarePlatformPackEntry 4 }

cfprFirmwarePlatformPackForceDeploy OBJECT-TYPE
    SYNTAX       TruthValue
    MAX-ACCESS   read-only
    STATUS       current
    DESCRIPTION
        "Cisco Firepower firmware:PlatformPack:forceDeploy
        managed object property"
    ::= { cfprFirmwarePlatformPackEntry 5 }

cfprFirmwarePlatformPackFsmDescr OBJECT-TYPE
    SYNTAX       SnmpAdminString
    MAX-ACCESS   read-only
    STATUS       current
    DESCRIPTION
        "Cisco Firepower firmware:PlatformPack:fsmDescr
        managed object property"
    ::= { cfprFirmwarePlatformPackEntry 6 }

cfprFirmwarePlatformPackFsmFlags OBJECT-TYPE
    SYNTAX       SnmpAdminString
    MAX-ACCESS   read-only
    STATUS       current
    DESCRIPTION
        "Cisco Firepower firmware:PlatformPack:fsmFlags
        managed object property"
    ::= { cfprFirmwarePlatformPackEntry 7 }

cfprFirmwarePlatformPackFsmPrev OBJECT-TYPE
    SYNTAX       SnmpAdminString
    MAX-ACCESS   read-only
    STATUS       current
    DESCRIPTION
        "Cisco Firepower firmware:PlatformPack:fsmPrev
        managed object property"
    ::= { cfprFirmwarePlatformPackEntry 8 }

cfprFirmwarePlatformPackFsmProgr OBJECT-TYPE
    SYNTAX       Gauge32
    MAX-ACCESS   read-only
    STATUS       current
    DESCRIPTION
        "Cisco Firepower firmware:PlatformPack:fsmProgr
        managed object property"
    ::= { cfprFirmwarePlatformPackEntry 9 }

cfprFirmwarePlatformPackFsmRmtInvErrCode OBJECT-TYPE
    SYNTAX       Gauge32
    MAX-ACCESS   read-only
    STATUS       current
    DESCRIPTION
        "Cisco Firepower firmware:PlatformPack:fsmRmtInvErrCode
        managed object property"
    ::= { cfprFirmwarePlatformPackEntry 10 }

cfprFirmwarePlatformPackFsmRmtInvErrDescr OBJECT-TYPE
    SYNTAX       SnmpAdminString
    MAX-ACCESS   read-only
    STATUS       current
    DESCRIPTION
        "Cisco Firepower firmware:PlatformPack:fsmRmtInvErrDescr
        managed object property"
    ::= { cfprFirmwarePlatformPackEntry 11 }

cfprFirmwarePlatformPackFsmRmtInvRslt OBJECT-TYPE
    SYNTAX       CfprConditionRemoteInvRslt
    MAX-ACCESS   read-only
    STATUS       current
    DESCRIPTION
        "Cisco Firepower firmware:PlatformPack:fsmRmtInvRslt
        managed object property"
    ::= { cfprFirmwarePlatformPackEntry 12 }

cfprFirmwarePlatformPackFsmStageDescr OBJECT-TYPE
    SYNTAX       SnmpAdminString
    MAX-ACCESS   read-only
    STATUS       current
    DESCRIPTION
        "Cisco Firepower firmware:PlatformPack:fsmStageDescr
        managed object property"
    ::= { cfprFirmwarePlatformPackEntry 13 }

cfprFirmwarePlatformPackFsmStamp OBJECT-TYPE
    SYNTAX       DateAndTime
    MAX-ACCESS   read-only
    STATUS       current
    DESCRIPTION
        "Cisco Firepower firmware:PlatformPack:fsmStamp
        managed object property"
    ::= { cfprFirmwarePlatformPackEntry 14 }

cfprFirmwarePlatformPackFsmStatus OBJECT-TYPE
    SYNTAX       SnmpAdminString
    MAX-ACCESS   read-only
    STATUS       current
    DESCRIPTION
        "Cisco Firepower firmware:PlatformPack:fsmStatus
        managed object property"
    ::= { cfprFirmwarePlatformPackEntry 15 }

cfprFirmwarePlatformPackFsmTry OBJECT-TYPE
    SYNTAX       Gauge32
    MAX-ACCESS   read-only
    STATUS       current
    DESCRIPTION
        "Cisco Firepower firmware:PlatformPack:fsmTry managed
        object property"
    ::= { cfprFirmwarePlatformPackEntry 16 }

cfprFirmwarePlatformPackIntId OBJECT-TYPE
    SYNTAX       SnmpAdminString
    MAX-ACCESS   read-only
    STATUS       current
    DESCRIPTION
        "Cisco Firepower firmware:PlatformPack:intId managed
        object property"
    ::= { cfprFirmwarePlatformPackEntry 17 }

cfprFirmwarePlatformPackMode OBJECT-TYPE
    SYNTAX       CfprFirmwarePackMode
    MAX-ACCESS   read-only
    STATUS       current
    DESCRIPTION
        "Cisco Firepower firmware:PlatformPack:mode managed
        object property"
    ::= { cfprFirmwarePlatformPackEntry 18 }

cfprFirmwarePlatformPackName OBJECT-TYPE
    SYNTAX       SnmpAdminString
    MAX-ACCESS   read-only
    STATUS       current
    DESCRIPTION
        "Cisco Firepower firmware:PlatformPack:name managed
        object property"
    ::= { cfprFirmwarePlatformPackEntry 19 }

cfprFirmwarePlatformPackPlatformBundleName OBJECT-TYPE
    SYNTAX       SnmpAdminString
    MAX-ACCESS   read-only
    STATUS       current
    DESCRIPTION
        "Cisco Firepower firmware:PlatformPack:platformBundleName
        managed object property"
    ::= { cfprFirmwarePlatformPackEntry 20 }

cfprFirmwarePlatformPackPlatformBundleVersion OBJECT-TYPE
    SYNTAX       SnmpAdminString
    MAX-ACCESS   read-only
    STATUS       current
    DESCRIPTION
        "Cisco Firepower firmware:PlatformPack:platformBundleVersion
        managed object property"
    ::= { cfprFirmwarePlatformPackEntry 21 }

cfprFirmwarePlatformPackPolicyLevel OBJECT-TYPE
    SYNTAX       Gauge32
    MAX-ACCESS   read-only
    STATUS       current
    DESCRIPTION
        "Cisco Firepower firmware:PlatformPack:policyLevel
        managed object property"
    ::= { cfprFirmwarePlatformPackEntry 22 }

cfprFirmwarePlatformPackPolicyOwner OBJECT-TYPE
    SYNTAX       CfprPolicyPolicyOwner
    MAX-ACCESS   read-only
    STATUS       current
    DESCRIPTION
        "Cisco Firepower firmware:PlatformPack:policyOwner
        managed object property"
    ::= { cfprFirmwarePlatformPackEntry 23 }

cfprFirmwarePlatformPackPreviousBundleVersion OBJECT-TYPE
    SYNTAX       SnmpAdminString
    MAX-ACCESS   read-only
    STATUS       current
    DESCRIPTION
        "Cisco Firepower firmware:PlatformPack:previousBundleVersion
        managed object property"
    ::= { cfprFirmwarePlatformPackEntry 24 }

cfprFirmwarePlatformPackRestoreVersion OBJECT-TYPE
    SYNTAX       TruthValue
    MAX-ACCESS   read-only
    STATUS       current
    DESCRIPTION
        "Cisco Firepower firmware:PlatformPack:restoreVersion
        managed object property"
    ::= { cfprFirmwarePlatformPackEntry 25 }

cfprFirmwarePlatformPackSerializeHostUpgrade OBJECT-TYPE
    SYNTAX       TruthValue
    MAX-ACCESS   read-only
    STATUS       current
    DESCRIPTION
        "Cisco Firepower firmware:PlatformPack:serializeHostUpgrade
        managed object property"
    ::= { cfprFirmwarePlatformPackEntry 26 }

cfprFirmwarePlatformPackSkipManagerValidation OBJECT-TYPE
    SYNTAX       TruthValue
    MAX-ACCESS   read-only
    STATUS       current
    DESCRIPTION
        "Cisco Firepower firmware:PlatformPack:skipManagerValidation
        managed object property"
    ::= { cfprFirmwarePlatformPackEntry 27 }

cfprFirmwarePlatformPackStageSize OBJECT-TYPE
    SYNTAX       Gauge32
    MAX-ACCESS   read-only
    STATUS       current
    DESCRIPTION
        "Cisco Firepower firmware:PlatformPack:stageSize
        managed object property"
    ::= { cfprFirmwarePlatformPackEntry 28 }

cfprFirmwarePlatformPackUpdateTrigger OBJECT-TYPE
    SYNTAX       DateAndTime
    MAX-ACCESS   read-only
    STATUS       current
    DESCRIPTION
        "Cisco Firepower firmware:PlatformPack:updateTrigger
        managed object property"
    ::= { cfprFirmwarePlatformPackEntry 29 }

cfprFirmwarePlatformPackPrevBundleVersion OBJECT-TYPE
    SYNTAX       SnmpAdminString
    MAX-ACCESS   read-only
    STATUS       current
    DESCRIPTION
        "Cisco Firepower firmware:PlatformPack:prevBundleVersion
        managed object property"
    ::= { cfprFirmwarePlatformPackEntry 30 }

cfprFirmwarePlatformPackVersionChecked OBJECT-TYPE
    SYNTAX       TruthValue
    MAX-ACCESS   read-only
    STATUS       current
    DESCRIPTION
        "Cisco Firepower firmware:PlatformPack:versionChecked
        managed object property"
    ::= { cfprFirmwarePlatformPackEntry 31 }

cfprFirmwarePlatformPackFsmTable OBJECT-TYPE
    SYNTAX           SEQUENCE OF CfprFirmwarePlatformPackFsmEntry
    MAX-ACCESS       not-accessible
    STATUS           current
    DESCRIPTION
        "Cisco Firepower firmware:PlatformPackFsm managed object table"
    ::= { cfprFirmwareObjects 43 }

cfprFirmwarePlatformPackFsmEntry OBJECT-TYPE
    SYNTAX           CfprFirmwarePlatformPackFsmEntry
    MAX-ACCESS       not-accessible
    STATUS           current
    DESCRIPTION
        "Entry for the cfprFirmwarePlatformPackFsmTable table."
    INDEX { cfprFirmwarePlatformPackFsmInstanceId }
    ::= { cfprFirmwarePlatformPackFsmTable 1 }

CfprFirmwarePlatformPackFsmEntry ::= SEQUENCE {
    cfprFirmwarePlatformPackFsmInstanceId                            CfprManagedObjectId,
    cfprFirmwarePlatformPackFsmDn                                    CfprManagedObjectDn,
    cfprFirmwarePlatformPackFsmRn                                    SnmpAdminString,
    cfprFirmwarePlatformPackFsmCompletionTime                        DateAndTime,
    cfprFirmwarePlatformPackFsmCurrentFsm                            CfprFirmwarePlatformPackFsmCurrentFsm,
    cfprFirmwarePlatformPackFsmDescrData                             SnmpAdminString,
    cfprFirmwarePlatformPackFsmFsmStatus                             CfprFsmFsmStageStatus,
    cfprFirmwarePlatformPackFsmProgress                              Gauge32,
    cfprFirmwarePlatformPackFsmRmtErrCode                            Gauge32,
    cfprFirmwarePlatformPackFsmRmtErrDescr                           SnmpAdminString,
    cfprFirmwarePlatformPackFsmRmtRslt                               CfprConditionRemoteInvRslt
}

cfprFirmwarePlatformPackFsmInstanceId OBJECT-TYPE
    SYNTAX       CfprManagedObjectId
    MAX-ACCESS   not-accessible
    STATUS       current
    DESCRIPTION
        "Instance identifier of the managed object."
    ::= { cfprFirmwarePlatformPackFsmEntry 1 }

cfprFirmwarePlatformPackFsmDn OBJECT-TYPE
    SYNTAX       CfprManagedObjectDn
    MAX-ACCESS   read-only
    STATUS       current
    DESCRIPTION
        "Cisco Firepower firmware:PlatformPackFsm:dn managed
        object property"
    ::= { cfprFirmwarePlatformPackFsmEntry 2 }

cfprFirmwarePlatformPackFsmRn OBJECT-TYPE
    SYNTAX       SnmpAdminString
    MAX-ACCESS   read-only
    STATUS       current
    DESCRIPTION
        "Cisco Firepower firmware:PlatformPackFsm:rn managed
        object property"
    ::= { cfprFirmwarePlatformPackFsmEntry 3 }

cfprFirmwarePlatformPackFsmCompletionTime OBJECT-TYPE
    SYNTAX       DateAndTime
    MAX-ACCESS   read-only
    STATUS       current
    DESCRIPTION
        "Cisco Firepower firmware:PlatformPackFsm:completionTime
        managed object property"
    ::= { cfprFirmwarePlatformPackFsmEntry 4 }

cfprFirmwarePlatformPackFsmCurrentFsm OBJECT-TYPE
    SYNTAX       CfprFirmwarePlatformPackFsmCurrentFsm
    MAX-ACCESS   read-only
    STATUS       current
    DESCRIPTION
        "Cisco Firepower firmware:PlatformPackFsm:currentFsm
        managed object property"
    ::= { cfprFirmwarePlatformPackFsmEntry 5 }

cfprFirmwarePlatformPackFsmDescrData OBJECT-TYPE
    SYNTAX       SnmpAdminString
    MAX-ACCESS   read-only
    STATUS       current
    DESCRIPTION
        "Cisco Firepower firmware:PlatformPackFsm:descr
        managed object property"
    ::= { cfprFirmwarePlatformPackFsmEntry 6 }

cfprFirmwarePlatformPackFsmFsmStatus OBJECT-TYPE
    SYNTAX       CfprFsmFsmStageStatus
    MAX-ACCESS   read-only
    STATUS       current
    DESCRIPTION
        "Cisco Firepower firmware:PlatformPackFsm:fsmStatus
        managed object property"
    ::= { cfprFirmwarePlatformPackFsmEntry 7 }

cfprFirmwarePlatformPackFsmProgress OBJECT-TYPE
    SYNTAX       Gauge32
    MAX-ACCESS   read-only
    STATUS       current
    DESCRIPTION
        "Cisco Firepower firmware:PlatformPackFsm:progress
        managed object property"
    ::= { cfprFirmwarePlatformPackFsmEntry 8 }

cfprFirmwarePlatformPackFsmRmtErrCode OBJECT-TYPE
    SYNTAX       Gauge32
    MAX-ACCESS   read-only
    STATUS       current
    DESCRIPTION
        "Cisco Firepower firmware:PlatformPackFsm:rmtErrCode
        managed object property"
    ::= { cfprFirmwarePlatformPackFsmEntry 9 }

cfprFirmwarePlatformPackFsmRmtErrDescr OBJECT-TYPE
    SYNTAX       SnmpAdminString
    MAX-ACCESS   read-only
    STATUS       current
    DESCRIPTION
        "Cisco Firepower firmware:PlatformPackFsm:rmtErrDescr
        managed object property"
    ::= { cfprFirmwarePlatformPackFsmEntry 10 }

cfprFirmwarePlatformPackFsmRmtRslt OBJECT-TYPE
    SYNTAX       CfprConditionRemoteInvRslt
    MAX-ACCESS   read-only
    STATUS       current
    DESCRIPTION
        "Cisco Firepower firmware:PlatformPackFsm:rmtRslt
        managed object property"
    ::= { cfprFirmwarePlatformPackFsmEntry 11 }

cfprFirmwarePlatformPackFsmStageTable OBJECT-TYPE
    SYNTAX           SEQUENCE OF CfprFirmwarePlatformPackFsmStageEntry
    MAX-ACCESS       not-accessible
    STATUS           current
    DESCRIPTION
        "Cisco Firepower firmware:PlatformPackFsmStage
        managed object table"
    ::= { cfprFirmwareObjects 44 }

cfprFirmwarePlatformPackFsmStageEntry OBJECT-TYPE
    SYNTAX           CfprFirmwarePlatformPackFsmStageEntry
    MAX-ACCESS       not-accessible
    STATUS           current
    DESCRIPTION
        "Entry for the cfprFirmwarePlatformPackFsmStageTable table."
    INDEX { cfprFirmwarePlatformPackFsmStageInstanceId }
    ::= { cfprFirmwarePlatformPackFsmStageTable 1 }

CfprFirmwarePlatformPackFsmStageEntry ::= SEQUENCE {
    cfprFirmwarePlatformPackFsmStageInstanceId                       CfprManagedObjectId,
    cfprFirmwarePlatformPackFsmStageDn                               CfprManagedObjectDn,
    cfprFirmwarePlatformPackFsmStageRn                               SnmpAdminString,
    cfprFirmwarePlatformPackFsmStageDescrData                        SnmpAdminString,
    cfprFirmwarePlatformPackFsmStageLastUpdateTime                   DateAndTime,
    cfprFirmwarePlatformPackFsmStageName                             CfprFirmwarePlatformPackFsmStageName,
    cfprFirmwarePlatformPackFsmStageOrder                            Gauge32,
    cfprFirmwarePlatformPackFsmStageRetry                            Gauge32,
    cfprFirmwarePlatformPackFsmStageStageStatus                      CfprFsmFsmStageStatus
}

cfprFirmwarePlatformPackFsmStageInstanceId OBJECT-TYPE
    SYNTAX       CfprManagedObjectId
    MAX-ACCESS   not-accessible
    STATUS       current
    DESCRIPTION
        "Instance identifier of the managed object."
    ::= { cfprFirmwarePlatformPackFsmStageEntry 1 }

cfprFirmwarePlatformPackFsmStageDn OBJECT-TYPE
    SYNTAX       CfprManagedObjectDn
    MAX-ACCESS   read-only
    STATUS       current
    DESCRIPTION
        "Cisco Firepower firmware:PlatformPackFsmStage:dn
        managed object property"
    ::= { cfprFirmwarePlatformPackFsmStageEntry 2 }

cfprFirmwarePlatformPackFsmStageRn OBJECT-TYPE
    SYNTAX       SnmpAdminString
    MAX-ACCESS   read-only
    STATUS       current
    DESCRIPTION
        "Cisco Firepower firmware:PlatformPackFsmStage:rn
        managed object property"
    ::= { cfprFirmwarePlatformPackFsmStageEntry 3 }

cfprFirmwarePlatformPackFsmStageDescrData OBJECT-TYPE
    SYNTAX       SnmpAdminString
    MAX-ACCESS   read-only
    STATUS       current
    DESCRIPTION
        "Cisco Firepower firmware:PlatformPackFsmStage:descr
        managed object property"
    ::= { cfprFirmwarePlatformPackFsmStageEntry 4 }

cfprFirmwarePlatformPackFsmStageLastUpdateTime OBJECT-TYPE
    SYNTAX       DateAndTime
    MAX-ACCESS   read-only
    STATUS       current
    DESCRIPTION
        "Cisco Firepower firmware:PlatformPackFsmStage:lastUpdateTime
        managed object property"
    ::= { cfprFirmwarePlatformPackFsmStageEntry 5 }

cfprFirmwarePlatformPackFsmStageName OBJECT-TYPE
    SYNTAX       CfprFirmwarePlatformPackFsmStageName
    MAX-ACCESS   read-only
    STATUS       current
    DESCRIPTION
        "Cisco Firepower firmware:PlatformPackFsmStage:name
        managed object property"
    ::= { cfprFirmwarePlatformPackFsmStageEntry 6 }

cfprFirmwarePlatformPackFsmStageOrder OBJECT-TYPE
    SYNTAX       Gauge32
    MAX-ACCESS   read-only
    STATUS       current
    DESCRIPTION
        "Cisco Firepower firmware:PlatformPackFsmStage:order
        managed object property"
    ::= { cfprFirmwarePlatformPackFsmStageEntry 7 }

cfprFirmwarePlatformPackFsmStageRetry OBJECT-TYPE
    SYNTAX       Gauge32
    MAX-ACCESS   read-only
    STATUS       current
    DESCRIPTION
        "Cisco Firepower firmware:PlatformPackFsmStage:retry
        managed object property"
    ::= { cfprFirmwarePlatformPackFsmStageEntry 8 }

cfprFirmwarePlatformPackFsmStageStageStatus OBJECT-TYPE
    SYNTAX       CfprFsmFsmStageStatus
    MAX-ACCESS   read-only
    STATUS       current
    DESCRIPTION
        "Cisco Firepower firmware:PlatformPackFsmStage:stageStatus
        managed object property"
    ::= { cfprFirmwarePlatformPackFsmStageEntry 9 }

cfprFirmwarePlatformPackFsmTaskTable OBJECT-TYPE
    SYNTAX           SEQUENCE OF CfprFirmwarePlatformPackFsmTaskEntry
    MAX-ACCESS       not-accessible
    STATUS           current
    DESCRIPTION
        "Cisco Firepower firmware:PlatformPackFsmTask managed
        object table"
    ::= { cfprFirmwareObjects 45 }

cfprFirmwarePlatformPackFsmTaskEntry OBJECT-TYPE
    SYNTAX           CfprFirmwarePlatformPackFsmTaskEntry
    MAX-ACCESS       not-accessible
    STATUS           current
    DESCRIPTION
        "Entry for the cfprFirmwarePlatformPackFsmTaskTable table."
    INDEX { cfprFirmwarePlatformPackFsmTaskInstanceId }
    ::= { cfprFirmwarePlatformPackFsmTaskTable 1 }

CfprFirmwarePlatformPackFsmTaskEntry ::= SEQUENCE {
    cfprFirmwarePlatformPackFsmTaskInstanceId                        CfprManagedObjectId,
    cfprFirmwarePlatformPackFsmTaskDn                                CfprManagedObjectDn,
    cfprFirmwarePlatformPackFsmTaskRn                                SnmpAdminString,
    cfprFirmwarePlatformPackFsmTaskCompletion                        CfprFsmCompletion,
    cfprFirmwarePlatformPackFsmTaskFlags                             CfprFirmwarePlatformPackFsmTaskFlags,
    cfprFirmwarePlatformPackFsmTaskItem                              CfprFirmwarePlatformPackFsmTaskItem,
    cfprFirmwarePlatformPackFsmTaskSeqId                             Gauge32
}

cfprFirmwarePlatformPackFsmTaskInstanceId OBJECT-TYPE
    SYNTAX       CfprManagedObjectId
    MAX-ACCESS   not-accessible
    STATUS       current
    DESCRIPTION
        "Instance identifier of the managed object."
    ::= { cfprFirmwarePlatformPackFsmTaskEntry 1 }

cfprFirmwarePlatformPackFsmTaskDn OBJECT-TYPE
    SYNTAX       CfprManagedObjectDn
    MAX-ACCESS   read-only
    STATUS       current
    DESCRIPTION
        "Cisco Firepower firmware:PlatformPackFsmTask:dn
        managed object property"
    ::= { cfprFirmwarePlatformPackFsmTaskEntry 2 }

cfprFirmwarePlatformPackFsmTaskRn OBJECT-TYPE
    SYNTAX       SnmpAdminString
    MAX-ACCESS   read-only
    STATUS       current
    DESCRIPTION
        "Cisco Firepower firmware:PlatformPackFsmTask:rn
        managed object property"
    ::= { cfprFirmwarePlatformPackFsmTaskEntry 3 }

cfprFirmwarePlatformPackFsmTaskCompletion OBJECT-TYPE
    SYNTAX       CfprFsmCompletion
    MAX-ACCESS   read-only
    STATUS       current
    DESCRIPTION
        "Cisco Firepower firmware:PlatformPackFsmTask:completion
        managed object property"
    ::= { cfprFirmwarePlatformPackFsmTaskEntry 4 }

cfprFirmwarePlatformPackFsmTaskFlags OBJECT-TYPE
    SYNTAX       CfprFirmwarePlatformPackFsmTaskFlags
    MAX-ACCESS   read-only
    STATUS       current
    DESCRIPTION
        "Cisco Firepower firmware:PlatformPackFsmTask:flags
        managed object property"
    ::= { cfprFirmwarePlatformPackFsmTaskEntry 5 }

cfprFirmwarePlatformPackFsmTaskItem OBJECT-TYPE
    SYNTAX       CfprFirmwarePlatformPackFsmTaskItem
    MAX-ACCESS   read-only
    STATUS       current
    DESCRIPTION
        "Cisco Firepower firmware:PlatformPackFsmTask:item
        managed object property"
    ::= { cfprFirmwarePlatformPackFsmTaskEntry 6 }

cfprFirmwarePlatformPackFsmTaskSeqId OBJECT-TYPE
    SYNTAX       Gauge32
    MAX-ACCESS   read-only
    STATUS       current
    DESCRIPTION
        "Cisco Firepower firmware:PlatformPackFsmTask:seqId
        managed object property"
    ::= { cfprFirmwarePlatformPackFsmTaskEntry 7 }

cfprFirmwareRackTable OBJECT-TYPE
    SYNTAX           SEQUENCE OF CfprFirmwareRackEntry
    MAX-ACCESS       not-accessible
    STATUS           current
    DESCRIPTION
        "Cisco Firepower firmware:Rack managed object table"
    ::= { cfprFirmwareObjects 46 }

cfprFirmwareRackEntry OBJECT-TYPE
    SYNTAX           CfprFirmwareRackEntry
    MAX-ACCESS       not-accessible
    STATUS           current
    DESCRIPTION
        "Entry for the cfprFirmwareRackTable table."
    INDEX { cfprFirmwareRackInstanceId }
    ::= { cfprFirmwareRackTable 1 }

CfprFirmwareRackEntry ::= SEQUENCE {
    cfprFirmwareRackInstanceId                                       CfprManagedObjectId,
    cfprFirmwareRackDn                                               CfprManagedObjectDn,
    cfprFirmwareRackRn                                               SnmpAdminString,
    cfprFirmwareRackOperVersion                                      SnmpAdminString
}

cfprFirmwareRackInstanceId OBJECT-TYPE
    SYNTAX       CfprManagedObjectId
    MAX-ACCESS   not-accessible
    STATUS       current
    DESCRIPTION
        "Instance identifier of the managed object."
    ::= { cfprFirmwareRackEntry 1 }

cfprFirmwareRackDn OBJECT-TYPE
    SYNTAX       CfprManagedObjectDn
    MAX-ACCESS   read-only
    STATUS       current
    DESCRIPTION
        "Cisco Firepower firmware:Rack:dn managed object property"
    ::= { cfprFirmwareRackEntry 2 }

cfprFirmwareRackRn OBJECT-TYPE
    SYNTAX       SnmpAdminString
    MAX-ACCESS   read-only
    STATUS       current
    DESCRIPTION
        "Cisco Firepower firmware:Rack:rn managed object property"
    ::= { cfprFirmwareRackEntry 3 }

cfprFirmwareRackOperVersion OBJECT-TYPE
    SYNTAX       SnmpAdminString
    MAX-ACCESS   read-only
    STATUS       current
    DESCRIPTION
        "Cisco Firepower firmware:Rack:operVersion managed
        object property"
    ::= { cfprFirmwareRackEntry 4 }

cfprFirmwareRunnableTable OBJECT-TYPE
    SYNTAX           SEQUENCE OF CfprFirmwareRunnableEntry
    MAX-ACCESS       not-accessible
    STATUS           current
    DESCRIPTION
        "Cisco Firepower firmware:Runnable managed object table"
    ::= { cfprFirmwareObjects 64 }

cfprFirmwareRunnableEntry OBJECT-TYPE
    SYNTAX           CfprFirmwareRunnableEntry
    MAX-ACCESS       not-accessible
    STATUS           current
    DESCRIPTION
        "Entry for the cfprFirmwareRunnableTable table."
    INDEX { cfprFirmwareRunnableInstanceId }
    ::= { cfprFirmwareRunnableTable 1 }

CfprFirmwareRunnableEntry ::= SEQUENCE {
    cfprFirmwareRunnableInstanceId                                   CfprManagedObjectId,
    cfprFirmwareRunnableDn                                           CfprManagedObjectDn,
    cfprFirmwareRunnableRn                                           SnmpAdminString,
    cfprFirmwareRunnableAdminState                                   CfprFirmwareTriggerState,
    cfprFirmwareRunnableDeployment                                   CfprFirmwareDeployment,
    cfprFirmwareRunnableMemFault                                     TruthValue,
    cfprFirmwareRunnableOperState                                    CfprFirmwareImageState,
    cfprFirmwareRunnablePrevVersion                                  SnmpAdminString,
    cfprFirmwareRunnableVersion                                      SnmpAdminString
}

cfprFirmwareRunnableInstanceId OBJECT-TYPE
    SYNTAX       CfprManagedObjectId
    MAX-ACCESS   not-accessible
    STATUS       current
    DESCRIPTION
        "Instance identifier of the managed object."
    ::= { cfprFirmwareRunnableEntry 1 }

cfprFirmwareRunnableDn OBJECT-TYPE
    SYNTAX       CfprManagedObjectDn
    MAX-ACCESS   read-only
    STATUS       current
    DESCRIPTION
        "Cisco Firepower firmware:Runnable:dn managed object property"
    ::= { cfprFirmwareRunnableEntry 2 }

cfprFirmwareRunnableRn OBJECT-TYPE
    SYNTAX       SnmpAdminString
    MAX-ACCESS   read-only
    STATUS       current
    DESCRIPTION
        "Cisco Firepower firmware:Runnable:rn managed object property"
    ::= { cfprFirmwareRunnableEntry 3 }

cfprFirmwareRunnableAdminState OBJECT-TYPE
    SYNTAX       CfprFirmwareTriggerState
    MAX-ACCESS   read-only
    STATUS       current
    DESCRIPTION
        "Cisco Firepower firmware:Runnable:adminState managed
        object property"
    ::= { cfprFirmwareRunnableEntry 4 }

cfprFirmwareRunnableDeployment OBJECT-TYPE
    SYNTAX       CfprFirmwareDeployment
    MAX-ACCESS   read-only
    STATUS       current
    DESCRIPTION
        "Cisco Firepower firmware:Runnable:deployment managed
        object property"
    ::= { cfprFirmwareRunnableEntry 5 }

cfprFirmwareRunnableMemFault OBJECT-TYPE
    SYNTAX       TruthValue
    MAX-ACCESS   read-only
    STATUS       current
    DESCRIPTION
        "Cisco Firepower firmware:Runnable:memFault managed
        object property"
    ::= { cfprFirmwareRunnableEntry 6 }

cfprFirmwareRunnableOperState OBJECT-TYPE
    SYNTAX       CfprFirmwareImageState
    MAX-ACCESS   read-only
    STATUS       current
    DESCRIPTION
        "Cisco Firepower firmware:Runnable:operState managed
        object property"
    ::= { cfprFirmwareRunnableEntry 7 }

cfprFirmwareRunnablePrevVersion OBJECT-TYPE
    SYNTAX       SnmpAdminString
    MAX-ACCESS   read-only
    STATUS       current
    DESCRIPTION
        "Cisco Firepower firmware:Runnable:prevVersion
        managed object property"
    ::= { cfprFirmwareRunnableEntry 8 }

cfprFirmwareRunnableVersion OBJECT-TYPE
    SYNTAX       SnmpAdminString
    MAX-ACCESS   read-only
    STATUS       current
    DESCRIPTION
        "Cisco Firepower firmware:Runnable:version managed
        object property"
    ::= { cfprFirmwareRunnableEntry 9 }

cfprFirmwareRunningTable OBJECT-TYPE
    SYNTAX           SEQUENCE OF CfprFirmwareRunningEntry
    MAX-ACCESS       not-accessible
    STATUS           current
    DESCRIPTION
        "Cisco Firepower firmware:Running managed object table"
    ::= { cfprFirmwareObjects 47 }

cfprFirmwareRunningEntry OBJECT-TYPE
    SYNTAX           CfprFirmwareRunningEntry
    MAX-ACCESS       not-accessible
    STATUS           current
    DESCRIPTION
        "Entry for the cfprFirmwareRunningTable table."
    INDEX { cfprFirmwareRunningInstanceId }
    ::= { cfprFirmwareRunningTable 1 }

CfprFirmwareRunningEntry ::= SEQUENCE {
    cfprFirmwareRunningInstanceId                                    CfprManagedObjectId,
    cfprFirmwareRunningDn                                            CfprManagedObjectDn,
    cfprFirmwareRunningRn                                            SnmpAdminString,
    cfprFirmwareRunningDeployment                                    CfprFirmwareRunningDeployment,
    cfprFirmwareRunningInvTag                                        SnmpAdminString,
    cfprFirmwareRunningPackageVersion                                SnmpAdminString,
    cfprFirmwareRunningType                                          CfprFirmwareType,
    cfprFirmwareRunningVersion                                       SnmpAdminString
}

cfprFirmwareRunningInstanceId OBJECT-TYPE
    SYNTAX       CfprManagedObjectId
    MAX-ACCESS   not-accessible
    STATUS       current
    DESCRIPTION
        "Instance identifier of the managed object."
    ::= { cfprFirmwareRunningEntry 1 }

cfprFirmwareRunningDn OBJECT-TYPE
    SYNTAX       CfprManagedObjectDn
    MAX-ACCESS   read-only
    STATUS       current
    DESCRIPTION
        "Cisco Firepower firmware:Running:dn managed object property"
    ::= { cfprFirmwareRunningEntry 2 }

cfprFirmwareRunningRn OBJECT-TYPE
    SYNTAX       SnmpAdminString
    MAX-ACCESS   read-only
    STATUS       current
    DESCRIPTION
        "Cisco Firepower firmware:Running:rn managed object property"
    ::= { cfprFirmwareRunningEntry 3 }

cfprFirmwareRunningDeployment OBJECT-TYPE
    SYNTAX       CfprFirmwareRunningDeployment
    MAX-ACCESS   read-only
    STATUS       current
    DESCRIPTION
        "Cisco Firepower firmware:Running:deployment managed
        object property"
    ::= { cfprFirmwareRunningEntry 4 }

cfprFirmwareRunningInvTag OBJECT-TYPE
    SYNTAX       SnmpAdminString
    MAX-ACCESS   read-only
    STATUS       current
    DESCRIPTION
        "Cisco Firepower firmware:Running:invTag managed object property"
    ::= { cfprFirmwareRunningEntry 5 }

cfprFirmwareRunningPackageVersion OBJECT-TYPE
    SYNTAX       SnmpAdminString
    MAX-ACCESS   read-only
    STATUS       current
    DESCRIPTION
        "Cisco Firepower firmware:Running:packageVersion
        managed object property"
    ::= { cfprFirmwareRunningEntry 6 }

cfprFirmwareRunningType OBJECT-TYPE
    SYNTAX       CfprFirmwareType
    MAX-ACCESS   read-only
    STATUS       current
    DESCRIPTION
        "Cisco Firepower firmware:Running:type managed object property"
    ::= { cfprFirmwareRunningEntry 7 }

cfprFirmwareRunningVersion OBJECT-TYPE
    SYNTAX       SnmpAdminString
    MAX-ACCESS   read-only
    STATUS       current
    DESCRIPTION
        "Cisco Firepower firmware:Running:version managed object property"
    ::= { cfprFirmwareRunningEntry 8 }

cfprFirmwareSpecTable OBJECT-TYPE
    SYNTAX           SEQUENCE OF CfprFirmwareSpecEntry
    MAX-ACCESS       not-accessible
    STATUS           current
    DESCRIPTION
        "Cisco Firepower firmware:Spec managed object table"
    ::= { cfprFirmwareObjects 48 }

cfprFirmwareSpecEntry OBJECT-TYPE
    SYNTAX           CfprFirmwareSpecEntry
    MAX-ACCESS       not-accessible
    STATUS           current
    DESCRIPTION
        "Entry for the cfprFirmwareSpecTable table."
    INDEX { cfprFirmwareSpecInstanceId }
    ::= { cfprFirmwareSpecTable 1 }

CfprFirmwareSpecEntry ::= SEQUENCE {
    cfprFirmwareSpecInstanceId                                       CfprManagedObjectId,
    cfprFirmwareSpecDn                                               CfprManagedObjectDn,
    cfprFirmwareSpecRn                                               SnmpAdminString,
    cfprFirmwareSpecBundleVersion                                    SnmpAdminString,
    cfprFirmwareSpecEthEFIVersion                                    SnmpAdminString,
    cfprFirmwareSpecEthOptionRomVersion                              SnmpAdminString,
    cfprFirmwareSpecFcFWVersion                                      SnmpAdminString,
    cfprFirmwareSpecFcOptionRomVersion                               SnmpAdminString
}

cfprFirmwareSpecInstanceId OBJECT-TYPE
    SYNTAX       CfprManagedObjectId
    MAX-ACCESS   not-accessible
    STATUS       current
    DESCRIPTION
        "Instance identifier of the managed object."
    ::= { cfprFirmwareSpecEntry 1 }

cfprFirmwareSpecDn OBJECT-TYPE
    SYNTAX       CfprManagedObjectDn
    MAX-ACCESS   read-only
    STATUS       current
    DESCRIPTION
        "Cisco Firepower firmware:Spec:dn managed object property"
    ::= { cfprFirmwareSpecEntry 2 }

cfprFirmwareSpecRn OBJECT-TYPE
    SYNTAX       SnmpAdminString
    MAX-ACCESS   read-only
    STATUS       current
    DESCRIPTION
        "Cisco Firepower firmware:Spec:rn managed object property"
    ::= { cfprFirmwareSpecEntry 3 }

cfprFirmwareSpecBundleVersion OBJECT-TYPE
    SYNTAX       SnmpAdminString
    MAX-ACCESS   read-only
    STATUS       current
    DESCRIPTION
        "Cisco Firepower firmware:Spec:bundleVersion managed
        object property"
    ::= { cfprFirmwareSpecEntry 4 }

cfprFirmwareSpecEthEFIVersion OBJECT-TYPE
    SYNTAX       SnmpAdminString
    MAX-ACCESS   read-only
    STATUS       current
    DESCRIPTION
        "Cisco Firepower firmware:Spec:ethEFIVersion managed
        object property"
    ::= { cfprFirmwareSpecEntry 5 }

cfprFirmwareSpecEthOptionRomVersion OBJECT-TYPE
    SYNTAX       SnmpAdminString
    MAX-ACCESS   read-only
    STATUS       current
    DESCRIPTION
        "Cisco Firepower firmware:Spec:ethOptionRomVersion
        managed object property"
    ::= { cfprFirmwareSpecEntry 6 }

cfprFirmwareSpecFcFWVersion OBJECT-TYPE
    SYNTAX       SnmpAdminString
    MAX-ACCESS   read-only
    STATUS       current
    DESCRIPTION
        "Cisco Firepower firmware:Spec:fcFWVersion managed
        object property"
    ::= { cfprFirmwareSpecEntry 7 }

cfprFirmwareSpecFcOptionRomVersion OBJECT-TYPE
    SYNTAX       SnmpAdminString
    MAX-ACCESS   read-only
    STATUS       current
    DESCRIPTION
        "Cisco Firepower firmware:Spec:fcOptionRomVersion
        managed object property"
    ::= { cfprFirmwareSpecEntry 8 }

cfprFirmwareStatusTable OBJECT-TYPE
    SYNTAX           SEQUENCE OF CfprFirmwareStatusEntry
    MAX-ACCESS       not-accessible
    STATUS           current
    DESCRIPTION
        "Cisco Firepower firmware:Status managed object table"
    ::= { cfprFirmwareObjects 49 }

cfprFirmwareStatusEntry OBJECT-TYPE
    SYNTAX           CfprFirmwareStatusEntry
    MAX-ACCESS       not-accessible
    STATUS           current
    DESCRIPTION
        "Entry for the cfprFirmwareStatusTable table."
    INDEX { cfprFirmwareStatusInstanceId }
    ::= { cfprFirmwareStatusTable 1 }

CfprFirmwareStatusEntry ::= SEQUENCE {
    cfprFirmwareStatusInstanceId                                     CfprManagedObjectId,
    cfprFirmwareStatusDn                                             CfprManagedObjectDn,
    cfprFirmwareStatusRn                                             SnmpAdminString,
    cfprFirmwareStatusCimcVersion                                    SnmpAdminString,
    cfprFirmwareStatusFirmwareState                                  CfprFirmwareFirmwareState,
    cfprFirmwareStatusOperState                                      CfprFirmwareImageState,
    cfprFirmwareStatusPackageVersion                                 SnmpAdminString,
    cfprFirmwareStatusPldVersion                                     SnmpAdminString
}

cfprFirmwareStatusInstanceId OBJECT-TYPE
    SYNTAX       CfprManagedObjectId
    MAX-ACCESS   not-accessible
    STATUS       current
    DESCRIPTION
        "Instance identifier of the managed object."
    ::= { cfprFirmwareStatusEntry 1 }

cfprFirmwareStatusDn OBJECT-TYPE
    SYNTAX       CfprManagedObjectDn
    MAX-ACCESS   read-only
    STATUS       current
    DESCRIPTION
        "Cisco Firepower firmware:Status:dn managed object property"
    ::= { cfprFirmwareStatusEntry 2 }

cfprFirmwareStatusRn OBJECT-TYPE
    SYNTAX       SnmpAdminString
    MAX-ACCESS   read-only
    STATUS       current
    DESCRIPTION
        "Cisco Firepower firmware:Status:rn managed object property"
    ::= { cfprFirmwareStatusEntry 3 }

cfprFirmwareStatusCimcVersion OBJECT-TYPE
    SYNTAX       SnmpAdminString
    MAX-ACCESS   read-only
    STATUS       current
    DESCRIPTION
        "Cisco Firepower firmware:Status:cimcVersion managed
        object property"
    ::= { cfprFirmwareStatusEntry 4 }

cfprFirmwareStatusFirmwareState OBJECT-TYPE
    SYNTAX       CfprFirmwareFirmwareState
    MAX-ACCESS   read-only
    STATUS       current
    DESCRIPTION
        "Cisco Firepower firmware:Status:firmwareState
        managed object property"
    ::= { cfprFirmwareStatusEntry 5 }

cfprFirmwareStatusOperState OBJECT-TYPE
    SYNTAX       CfprFirmwareImageState
    MAX-ACCESS   read-only
    STATUS       current
    DESCRIPTION
        "Cisco Firepower firmware:Status:operState managed
        object property"
    ::= { cfprFirmwareStatusEntry 6 }

cfprFirmwareStatusPackageVersion OBJECT-TYPE
    SYNTAX       SnmpAdminString
    MAX-ACCESS   read-only
    STATUS       current
    DESCRIPTION
        "Cisco Firepower firmware:Status:packageVersion
        managed object property"
    ::= { cfprFirmwareStatusEntry 7 }

cfprFirmwareStatusPldVersion OBJECT-TYPE
    SYNTAX       SnmpAdminString
    MAX-ACCESS   read-only
    STATUS       current
    DESCRIPTION
        "Cisco Firepower firmware:Status:pldVersion managed
        object property"
    ::= { cfprFirmwareStatusEntry 8 }

cfprFirmwareSupFirmwareTable OBJECT-TYPE
    SYNTAX           SEQUENCE OF CfprFirmwareSupFirmwareEntry
    MAX-ACCESS       not-accessible
    STATUS           current
    DESCRIPTION
        "Cisco Firepower firmware:SupFirmware managed object table"
    ::= { cfprFirmwareObjects 65 }

cfprFirmwareSupFirmwareEntry OBJECT-TYPE
    SYNTAX           CfprFirmwareSupFirmwareEntry
    MAX-ACCESS       not-accessible
    STATUS           current
    DESCRIPTION
        "Entry for the cfprFirmwareSupFirmwareTable table."
    INDEX { cfprFirmwareSupFirmwareInstanceId }
    ::= { cfprFirmwareSupFirmwareTable 1 }

CfprFirmwareSupFirmwareEntry ::= SEQUENCE {
    cfprFirmwareSupFirmwareInstanceId                                CfprManagedObjectId,
    cfprFirmwareSupFirmwareDn                                        CfprManagedObjectDn,
    cfprFirmwareSupFirmwareRn                                        SnmpAdminString,
    cfprFirmwareSupFirmwareForceUpgrade                              TruthValue,
    cfprFirmwareSupFirmwareFsmDescr                                  SnmpAdminString,
    cfprFirmwareSupFirmwareFsmFlags                                  SnmpAdminString,
    cfprFirmwareSupFirmwareFsmPrev                                   SnmpAdminString,
    cfprFirmwareSupFirmwareFsmProgr                                  Gauge32,
    cfprFirmwareSupFirmwareFsmRmtInvErrCode                          Gauge32,
    cfprFirmwareSupFirmwareFsmRmtInvErrDescr                         SnmpAdminString,
    cfprFirmwareSupFirmwareFsmRmtInvRslt                             CfprConditionRemoteInvRslt,
    cfprFirmwareSupFirmwareFsmStageDescr                             SnmpAdminString,
    cfprFirmwareSupFirmwareFsmStamp                                  DateAndTime,
    cfprFirmwareSupFirmwareFsmStatus                                 SnmpAdminString,
    cfprFirmwareSupFirmwareFsmTry                                    Gauge32,
    cfprFirmwareSupFirmwareOperState                                 CfprFirmwareFwUpgradeState,
    cfprFirmwareSupFirmwarePackVersion                               SnmpAdminString,
    cfprFirmwareSupFirmwareState                                     CfprFirmwareFwState,
    cfprFirmwareSupFirmwareUpgradeStatus                             SnmpAdminString
}

cfprFirmwareSupFirmwareInstanceId OBJECT-TYPE
    SYNTAX       CfprManagedObjectId
    MAX-ACCESS   not-accessible
    STATUS       current
    DESCRIPTION
        "Instance identifier of the managed object."
    ::= { cfprFirmwareSupFirmwareEntry 1 }

cfprFirmwareSupFirmwareDn OBJECT-TYPE
    SYNTAX       CfprManagedObjectDn
    MAX-ACCESS   read-only
    STATUS       current
    DESCRIPTION
        "Cisco Firepower firmware:SupFirmware:dn managed object property"
    ::= { cfprFirmwareSupFirmwareEntry 2 }

cfprFirmwareSupFirmwareRn OBJECT-TYPE
    SYNTAX       SnmpAdminString
    MAX-ACCESS   read-only
    STATUS       current
    DESCRIPTION
        "Cisco Firepower firmware:SupFirmware:rn managed object property"
    ::= { cfprFirmwareSupFirmwareEntry 3 }

cfprFirmwareSupFirmwareForceUpgrade OBJECT-TYPE
    SYNTAX       TruthValue
    MAX-ACCESS   read-only
    STATUS       current
    DESCRIPTION
        "Cisco Firepower firmware:SupFirmware:forceUpgrade
        managed object property"
    ::= { cfprFirmwareSupFirmwareEntry 4 }

cfprFirmwareSupFirmwareFsmDescr OBJECT-TYPE
    SYNTAX       SnmpAdminString
    MAX-ACCESS   read-only
    STATUS       current
    DESCRIPTION
        "Cisco Firepower firmware:SupFirmware:fsmDescr
        managed object property"
    ::= { cfprFirmwareSupFirmwareEntry 5 }

cfprFirmwareSupFirmwareFsmFlags OBJECT-TYPE
    SYNTAX       SnmpAdminString
    MAX-ACCESS   read-only
    STATUS       current
    DESCRIPTION
        "Cisco Firepower firmware:SupFirmware:fsmFlags
        managed object property"
    ::= { cfprFirmwareSupFirmwareEntry 6 }

cfprFirmwareSupFirmwareFsmPrev OBJECT-TYPE
    SYNTAX       SnmpAdminString
    MAX-ACCESS   read-only
    STATUS       current
    DESCRIPTION
        "Cisco Firepower firmware:SupFirmware:fsmPrev managed
        object property"
    ::= { cfprFirmwareSupFirmwareEntry 7 }

cfprFirmwareSupFirmwareFsmProgr OBJECT-TYPE
    SYNTAX       Gauge32
    MAX-ACCESS   read-only
    STATUS       current
    DESCRIPTION
        "Cisco Firepower firmware:SupFirmware:fsmProgr
        managed object property"
    ::= { cfprFirmwareSupFirmwareEntry 8 }

cfprFirmwareSupFirmwareFsmRmtInvErrCode OBJECT-TYPE
    SYNTAX       Gauge32
    MAX-ACCESS   read-only
    STATUS       current
    DESCRIPTION
        "Cisco Firepower firmware:SupFirmware:fsmRmtInvErrCode
        managed object property"
    ::= { cfprFirmwareSupFirmwareEntry 9 }

cfprFirmwareSupFirmwareFsmRmtInvErrDescr OBJECT-TYPE
    SYNTAX       SnmpAdminString
    MAX-ACCESS   read-only
    STATUS       current
    DESCRIPTION
        "Cisco Firepower firmware:SupFirmware:fsmRmtInvErrDescr
        managed object property"
    ::= { cfprFirmwareSupFirmwareEntry 10 }

cfprFirmwareSupFirmwareFsmRmtInvRslt OBJECT-TYPE
    SYNTAX       CfprConditionRemoteInvRslt
    MAX-ACCESS   read-only
    STATUS       current
    DESCRIPTION
        "Cisco Firepower firmware:SupFirmware:fsmRmtInvRslt
        managed object property"
    ::= { cfprFirmwareSupFirmwareEntry 11 }

cfprFirmwareSupFirmwareFsmStageDescr OBJECT-TYPE
    SYNTAX       SnmpAdminString
    MAX-ACCESS   read-only
    STATUS       current
    DESCRIPTION
        "Cisco Firepower firmware:SupFirmware:fsmStageDescr
        managed object property"
    ::= { cfprFirmwareSupFirmwareEntry 12 }

cfprFirmwareSupFirmwareFsmStamp OBJECT-TYPE
    SYNTAX       DateAndTime
    MAX-ACCESS   read-only
    STATUS       current
    DESCRIPTION
        "Cisco Firepower firmware:SupFirmware:fsmStamp
        managed object property"
    ::= { cfprFirmwareSupFirmwareEntry 13 }

cfprFirmwareSupFirmwareFsmStatus OBJECT-TYPE
    SYNTAX       SnmpAdminString
    MAX-ACCESS   read-only
    STATUS       current
    DESCRIPTION
        "Cisco Firepower firmware:SupFirmware:fsmStatus
        managed object property"
    ::= { cfprFirmwareSupFirmwareEntry 14 }

cfprFirmwareSupFirmwareFsmTry OBJECT-TYPE
    SYNTAX       Gauge32
    MAX-ACCESS   read-only
    STATUS       current
    DESCRIPTION
        "Cisco Firepower firmware:SupFirmware:fsmTry managed
        object property"
    ::= { cfprFirmwareSupFirmwareEntry 15 }

cfprFirmwareSupFirmwareOperState OBJECT-TYPE
    SYNTAX       CfprFirmwareFwUpgradeState
    MAX-ACCESS   read-only
    STATUS       current
    DESCRIPTION
        "Cisco Firepower firmware:SupFirmware:operState
        managed object property"
    ::= { cfprFirmwareSupFirmwareEntry 16 }

cfprFirmwareSupFirmwarePackVersion OBJECT-TYPE
    SYNTAX       SnmpAdminString
    MAX-ACCESS   read-only
    STATUS       current
    DESCRIPTION
        "Cisco Firepower firmware:SupFirmware:packVersion
        managed object property"
    ::= { cfprFirmwareSupFirmwareEntry 17 }

cfprFirmwareSupFirmwareState OBJECT-TYPE
    SYNTAX       CfprFirmwareFwState
    MAX-ACCESS   read-only
    STATUS       current
    DESCRIPTION
        "Cisco Firepower firmware:SupFirmware:state managed
        object property"
    ::= { cfprFirmwareSupFirmwareEntry 18 }

cfprFirmwareSupFirmwareUpgradeStatus OBJECT-TYPE
    SYNTAX       SnmpAdminString
    MAX-ACCESS   read-only
    STATUS       current
    DESCRIPTION
        "Cisco Firepower firmware:SupFirmware:upgradeStatus
        managed object property"
    ::= { cfprFirmwareSupFirmwareEntry 19 }

cfprFirmwareSupFirmwareFsmTable OBJECT-TYPE
    SYNTAX           SEQUENCE OF CfprFirmwareSupFirmwareFsmEntry
    MAX-ACCESS       not-accessible
    STATUS           current
    DESCRIPTION
        "Cisco Firepower firmware:SupFirmwareFsm managed object table"
    ::= { cfprFirmwareObjects 66 }

cfprFirmwareSupFirmwareFsmEntry OBJECT-TYPE
    SYNTAX           CfprFirmwareSupFirmwareFsmEntry
    MAX-ACCESS       not-accessible
    STATUS           current
    DESCRIPTION
        "Entry for the cfprFirmwareSupFirmwareFsmTable table."
    INDEX { cfprFirmwareSupFirmwareFsmInstanceId }
    ::= { cfprFirmwareSupFirmwareFsmTable 1 }

CfprFirmwareSupFirmwareFsmEntry ::= SEQUENCE {
    cfprFirmwareSupFirmwareFsmInstanceId                             CfprManagedObjectId,
    cfprFirmwareSupFirmwareFsmDn                                     CfprManagedObjectDn,
    cfprFirmwareSupFirmwareFsmRn                                     SnmpAdminString,
    cfprFirmwareSupFirmwareFsmCompletionTime                         DateAndTime,
    cfprFirmwareSupFirmwareFsmCurrentFsm                             CfprFirmwareSupFirmwareFsmCurrentFsm,
    cfprFirmwareSupFirmwareFsmDescrData                              SnmpAdminString,
    cfprFirmwareSupFirmwareFsmFsmStatus                              CfprFsmFsmStageStatus,
    cfprFirmwareSupFirmwareFsmProgress                               Gauge32,
    cfprFirmwareSupFirmwareFsmRmtErrCode                             Gauge32,
    cfprFirmwareSupFirmwareFsmRmtErrDescr                            SnmpAdminString,
    cfprFirmwareSupFirmwareFsmRmtRslt                                CfprConditionRemoteInvRslt
}

cfprFirmwareSupFirmwareFsmInstanceId OBJECT-TYPE
    SYNTAX       CfprManagedObjectId
    MAX-ACCESS   not-accessible
    STATUS       current
    DESCRIPTION
        "Instance identifier of the managed object."
    ::= { cfprFirmwareSupFirmwareFsmEntry 1 }

cfprFirmwareSupFirmwareFsmDn OBJECT-TYPE
    SYNTAX       CfprManagedObjectDn
    MAX-ACCESS   read-only
    STATUS       current
    DESCRIPTION
        "Cisco Firepower firmware:SupFirmwareFsm:dn managed
        object property"
    ::= { cfprFirmwareSupFirmwareFsmEntry 2 }

cfprFirmwareSupFirmwareFsmRn OBJECT-TYPE
    SYNTAX       SnmpAdminString
    MAX-ACCESS   read-only
    STATUS       current
    DESCRIPTION
        "Cisco Firepower firmware:SupFirmwareFsm:rn managed
        object property"
    ::= { cfprFirmwareSupFirmwareFsmEntry 3 }

cfprFirmwareSupFirmwareFsmCompletionTime OBJECT-TYPE
    SYNTAX       DateAndTime
    MAX-ACCESS   read-only
    STATUS       current
    DESCRIPTION
        "Cisco Firepower firmware:SupFirmwareFsm:completionTime
        managed object property"
    ::= { cfprFirmwareSupFirmwareFsmEntry 4 }

cfprFirmwareSupFirmwareFsmCurrentFsm OBJECT-TYPE
    SYNTAX       CfprFirmwareSupFirmwareFsmCurrentFsm
    MAX-ACCESS   read-only
    STATUS       current
    DESCRIPTION
        "Cisco Firepower firmware:SupFirmwareFsm:currentFsm
        managed object property"
    ::= { cfprFirmwareSupFirmwareFsmEntry 5 }

cfprFirmwareSupFirmwareFsmDescrData OBJECT-TYPE
    SYNTAX       SnmpAdminString
    MAX-ACCESS   read-only
    STATUS       current
    DESCRIPTION
        "Cisco Firepower firmware:SupFirmwareFsm:descr
        managed object property"
    ::= { cfprFirmwareSupFirmwareFsmEntry 6 }

cfprFirmwareSupFirmwareFsmFsmStatus OBJECT-TYPE
    SYNTAX       CfprFsmFsmStageStatus
    MAX-ACCESS   read-only
    STATUS       current
    DESCRIPTION
        "Cisco Firepower firmware:SupFirmwareFsm:fsmStatus
        managed object property"
    ::= { cfprFirmwareSupFirmwareFsmEntry 7 }

cfprFirmwareSupFirmwareFsmProgress OBJECT-TYPE
    SYNTAX       Gauge32
    MAX-ACCESS   read-only
    STATUS       current
    DESCRIPTION
        "Cisco Firepower firmware:SupFirmwareFsm:progress
        managed object property"
    ::= { cfprFirmwareSupFirmwareFsmEntry 8 }

cfprFirmwareSupFirmwareFsmRmtErrCode OBJECT-TYPE
    SYNTAX       Gauge32
    MAX-ACCESS   read-only
    STATUS       current
    DESCRIPTION
        "Cisco Firepower firmware:SupFirmwareFsm:rmtErrCode
        managed object property"
    ::= { cfprFirmwareSupFirmwareFsmEntry 9 }

cfprFirmwareSupFirmwareFsmRmtErrDescr OBJECT-TYPE
    SYNTAX       SnmpAdminString
    MAX-ACCESS   read-only
    STATUS       current
    DESCRIPTION
        "Cisco Firepower firmware:SupFirmwareFsm:rmtErrDescr
        managed object property"
    ::= { cfprFirmwareSupFirmwareFsmEntry 10 }

cfprFirmwareSupFirmwareFsmRmtRslt OBJECT-TYPE
    SYNTAX       CfprConditionRemoteInvRslt
    MAX-ACCESS   read-only
    STATUS       current
    DESCRIPTION
        "Cisco Firepower firmware:SupFirmwareFsm:rmtRslt
        managed object property"
    ::= { cfprFirmwareSupFirmwareFsmEntry 11 }

cfprFirmwareSupFirmwareFsmStageTable OBJECT-TYPE
    SYNTAX           SEQUENCE OF CfprFirmwareSupFirmwareFsmStageEntry
    MAX-ACCESS       not-accessible
    STATUS           current
    DESCRIPTION
        "Cisco Firepower firmware:SupFirmwareFsmStage managed
        object table"
    ::= { cfprFirmwareObjects 67 }

cfprFirmwareSupFirmwareFsmStageEntry OBJECT-TYPE
    SYNTAX           CfprFirmwareSupFirmwareFsmStageEntry
    MAX-ACCESS       not-accessible
    STATUS           current
    DESCRIPTION
        "Entry for the cfprFirmwareSupFirmwareFsmStageTable table."
    INDEX { cfprFirmwareSupFirmwareFsmStageInstanceId }
    ::= { cfprFirmwareSupFirmwareFsmStageTable 1 }

CfprFirmwareSupFirmwareFsmStageEntry ::= SEQUENCE {
    cfprFirmwareSupFirmwareFsmStageInstanceId                        CfprManagedObjectId,
    cfprFirmwareSupFirmwareFsmStageDn                                CfprManagedObjectDn,
    cfprFirmwareSupFirmwareFsmStageRn                                SnmpAdminString,
    cfprFirmwareSupFirmwareFsmStageDescrData                         SnmpAdminString,
    cfprFirmwareSupFirmwareFsmStageLastUpdateTime                    DateAndTime,
    cfprFirmwareSupFirmwareFsmStageName                              CfprFirmwareSupFirmwareFsmStageName,
    cfprFirmwareSupFirmwareFsmStageOrder                             Gauge32,
    cfprFirmwareSupFirmwareFsmStageRetry                             Gauge32,
    cfprFirmwareSupFirmwareFsmStageStageStatus                       CfprFsmFsmStageStatus
}

cfprFirmwareSupFirmwareFsmStageInstanceId OBJECT-TYPE
    SYNTAX       CfprManagedObjectId
    MAX-ACCESS   not-accessible
    STATUS       current
    DESCRIPTION
        "Instance identifier of the managed object."
    ::= { cfprFirmwareSupFirmwareFsmStageEntry 1 }

cfprFirmwareSupFirmwareFsmStageDn OBJECT-TYPE
    SYNTAX       CfprManagedObjectDn
    MAX-ACCESS   read-only
    STATUS       current
    DESCRIPTION
        "Cisco Firepower firmware:SupFirmwareFsmStage:dn
        managed object property"
    ::= { cfprFirmwareSupFirmwareFsmStageEntry 2 }

cfprFirmwareSupFirmwareFsmStageRn OBJECT-TYPE
    SYNTAX       SnmpAdminString
    MAX-ACCESS   read-only
    STATUS       current
    DESCRIPTION
        "Cisco Firepower firmware:SupFirmwareFsmStage:rn
        managed object property"
    ::= { cfprFirmwareSupFirmwareFsmStageEntry 3 }

cfprFirmwareSupFirmwareFsmStageDescrData OBJECT-TYPE
    SYNTAX       SnmpAdminString
    MAX-ACCESS   read-only
    STATUS       current
    DESCRIPTION
        "Cisco Firepower firmware:SupFirmwareFsmStage:descr
        managed object property"
    ::= { cfprFirmwareSupFirmwareFsmStageEntry 4 }

cfprFirmwareSupFirmwareFsmStageLastUpdateTime OBJECT-TYPE
    SYNTAX       DateAndTime
    MAX-ACCESS   read-only
    STATUS       current
    DESCRIPTION
        "Cisco Firepower firmware:SupFirmwareFsmStage:lastUpdateTime
        managed object property"
    ::= { cfprFirmwareSupFirmwareFsmStageEntry 5 }

cfprFirmwareSupFirmwareFsmStageName OBJECT-TYPE
    SYNTAX       CfprFirmwareSupFirmwareFsmStageName
    MAX-ACCESS   read-only
    STATUS       current
    DESCRIPTION
        "Cisco Firepower firmware:SupFirmwareFsmStage:name
        managed object property"
    ::= { cfprFirmwareSupFirmwareFsmStageEntry 6 }

cfprFirmwareSupFirmwareFsmStageOrder OBJECT-TYPE
    SYNTAX       Gauge32
    MAX-ACCESS   read-only
    STATUS       current
    DESCRIPTION
        "Cisco Firepower firmware:SupFirmwareFsmStage:order
        managed object property"
    ::= { cfprFirmwareSupFirmwareFsmStageEntry 7 }

cfprFirmwareSupFirmwareFsmStageRetry OBJECT-TYPE
    SYNTAX       Gauge32
    MAX-ACCESS   read-only
    STATUS       current
    DESCRIPTION
        "Cisco Firepower firmware:SupFirmwareFsmStage:retry
        managed object property"
    ::= { cfprFirmwareSupFirmwareFsmStageEntry 8 }

cfprFirmwareSupFirmwareFsmStageStageStatus OBJECT-TYPE
    SYNTAX       CfprFsmFsmStageStatus
    MAX-ACCESS   read-only
    STATUS       current
    DESCRIPTION
        "Cisco Firepower firmware:SupFirmwareFsmStage:stageStatus
        managed object property"
    ::= { cfprFirmwareSupFirmwareFsmStageEntry 9 }

cfprFirmwareSupFirmwareFsmTaskTable OBJECT-TYPE
    SYNTAX           SEQUENCE OF CfprFirmwareSupFirmwareFsmTaskEntry
    MAX-ACCESS       not-accessible
    STATUS           current
    DESCRIPTION
        "Cisco Firepower firmware:SupFirmwareFsmTask managed object table"
    ::= { cfprFirmwareObjects 68 }

cfprFirmwareSupFirmwareFsmTaskEntry OBJECT-TYPE
    SYNTAX           CfprFirmwareSupFirmwareFsmTaskEntry
    MAX-ACCESS       not-accessible
    STATUS           current
    DESCRIPTION
        "Entry for the cfprFirmwareSupFirmwareFsmTaskTable table."
    INDEX { cfprFirmwareSupFirmwareFsmTaskInstanceId }
    ::= { cfprFirmwareSupFirmwareFsmTaskTable 1 }

CfprFirmwareSupFirmwareFsmTaskEntry ::= SEQUENCE {
    cfprFirmwareSupFirmwareFsmTaskInstanceId                         CfprManagedObjectId,
    cfprFirmwareSupFirmwareFsmTaskDn                                 CfprManagedObjectDn,
    cfprFirmwareSupFirmwareFsmTaskRn                                 SnmpAdminString,
    cfprFirmwareSupFirmwareFsmTaskCompletion                         CfprFsmCompletion,
    cfprFirmwareSupFirmwareFsmTaskFlags                              CfprFirmwareSupFirmwareFsmTaskFlags,
    cfprFirmwareSupFirmwareFsmTaskItem                               CfprFirmwareSupFirmwareFsmTaskItem,
    cfprFirmwareSupFirmwareFsmTaskSeqId                              Gauge32
}

cfprFirmwareSupFirmwareFsmTaskInstanceId OBJECT-TYPE
    SYNTAX       CfprManagedObjectId
    MAX-ACCESS   not-accessible
    STATUS       current
    DESCRIPTION
        "Instance identifier of the managed object."
    ::= { cfprFirmwareSupFirmwareFsmTaskEntry 1 }

cfprFirmwareSupFirmwareFsmTaskDn OBJECT-TYPE
    SYNTAX       CfprManagedObjectDn
    MAX-ACCESS   read-only
    STATUS       current
    DESCRIPTION
        "Cisco Firepower firmware:SupFirmwareFsmTask:dn
        managed object property"
    ::= { cfprFirmwareSupFirmwareFsmTaskEntry 2 }

cfprFirmwareSupFirmwareFsmTaskRn OBJECT-TYPE
    SYNTAX       SnmpAdminString
    MAX-ACCESS   read-only
    STATUS       current
    DESCRIPTION
        "Cisco Firepower firmware:SupFirmwareFsmTask:rn
        managed object property"
    ::= { cfprFirmwareSupFirmwareFsmTaskEntry 3 }

cfprFirmwareSupFirmwareFsmTaskCompletion OBJECT-TYPE
    SYNTAX       CfprFsmCompletion
    MAX-ACCESS   read-only
    STATUS       current
    DESCRIPTION
        "Cisco Firepower firmware:SupFirmwareFsmTask:completion
        managed object property"
    ::= { cfprFirmwareSupFirmwareFsmTaskEntry 4 }

cfprFirmwareSupFirmwareFsmTaskFlags OBJECT-TYPE
    SYNTAX       CfprFirmwareSupFirmwareFsmTaskFlags
    MAX-ACCESS   read-only
    STATUS       current
    DESCRIPTION
        "Cisco Firepower firmware:SupFirmwareFsmTask:flags
        managed object property"
    ::= { cfprFirmwareSupFirmwareFsmTaskEntry 5 }

cfprFirmwareSupFirmwareFsmTaskItem OBJECT-TYPE
    SYNTAX       CfprFirmwareSupFirmwareFsmTaskItem
    MAX-ACCESS   read-only
    STATUS       current
    DESCRIPTION
        "Cisco Firepower firmware:SupFirmwareFsmTask:item
        managed object property"
    ::= { cfprFirmwareSupFirmwareFsmTaskEntry 6 }

cfprFirmwareSupFirmwareFsmTaskSeqId OBJECT-TYPE
    SYNTAX       Gauge32
    MAX-ACCESS   read-only
    STATUS       current
    DESCRIPTION
        "Cisco Firepower firmware:SupFirmwareFsmTask:seqId
        managed object property"
    ::= { cfprFirmwareSupFirmwareFsmTaskEntry 7 }

cfprFirmwareSystemTable OBJECT-TYPE
    SYNTAX           SEQUENCE OF CfprFirmwareSystemEntry
    MAX-ACCESS       not-accessible
    STATUS           current
    DESCRIPTION
        "Cisco Firepower firmware:System managed object table"
    ::= { cfprFirmwareObjects 50 }

cfprFirmwareSystemEntry OBJECT-TYPE
    SYNTAX           CfprFirmwareSystemEntry
    MAX-ACCESS       not-accessible
    STATUS           current
    DESCRIPTION
        "Entry for the cfprFirmwareSystemTable table."
    INDEX { cfprFirmwareSystemInstanceId }
    ::= { cfprFirmwareSystemTable 1 }

CfprFirmwareSystemEntry ::= SEQUENCE {
    cfprFirmwareSystemInstanceId                                     CfprManagedObjectId,
    cfprFirmwareSystemDn                                             CfprManagedObjectDn,
    cfprFirmwareSystemRn                                             SnmpAdminString,
    cfprFirmwareSystemFsmDescr                                       SnmpAdminString,
    cfprFirmwareSystemFsmFlags                                       SnmpAdminString,
    cfprFirmwareSystemFsmPrev                                        SnmpAdminString,
    cfprFirmwareSystemFsmProgr                                       Gauge32,
    cfprFirmwareSystemFsmRmtInvErrCode                               Gauge32,
    cfprFirmwareSystemFsmRmtInvErrDescr                              SnmpAdminString,
    cfprFirmwareSystemFsmRmtInvRslt                                  CfprConditionRemoteInvRslt,
    cfprFirmwareSystemFsmStageDescr                                  SnmpAdminString,
    cfprFirmwareSystemFsmStamp                                       DateAndTime,
    cfprFirmwareSystemFsmStatus                                      SnmpAdminString,
    cfprFirmwareSystemFsmTry                                         Gauge32,
    cfprFirmwareSystemOperState                                      CfprFirmwareInstallState,
    cfprFirmwareSystemState                                          CfprFirmwareFwState,
    cfprFirmwareSystemResetOnUpgrade                                 TruthValue,
    cfprFirmwareSystemScheduledInstallTime                           DateAndTime,
    cfprFirmwareSystemValidationStatus                               CfprFirmwareVerifyPackStatus
}

cfprFirmwareSystemInstanceId OBJECT-TYPE
    SYNTAX       CfprManagedObjectId
    MAX-ACCESS   not-accessible
    STATUS       current
    DESCRIPTION
        "Instance identifier of the managed object."
    ::= { cfprFirmwareSystemEntry 1 }

cfprFirmwareSystemDn OBJECT-TYPE
    SYNTAX       CfprManagedObjectDn
    MAX-ACCESS   read-only
    STATUS       current
    DESCRIPTION
        "Cisco Firepower firmware:System:dn managed object property"
    ::= { cfprFirmwareSystemEntry 2 }

cfprFirmwareSystemRn OBJECT-TYPE
    SYNTAX       SnmpAdminString
    MAX-ACCESS   read-only
    STATUS       current
    DESCRIPTION
        "Cisco Firepower firmware:System:rn managed object property"
    ::= { cfprFirmwareSystemEntry 3 }

cfprFirmwareSystemFsmDescr OBJECT-TYPE
    SYNTAX       SnmpAdminString
    MAX-ACCESS   read-only
    STATUS       current
    DESCRIPTION
        "Cisco Firepower firmware:System:fsmDescr managed object property"
    ::= { cfprFirmwareSystemEntry 4 }

cfprFirmwareSystemFsmFlags OBJECT-TYPE
    SYNTAX       SnmpAdminString
    MAX-ACCESS   read-only
    STATUS       current
    DESCRIPTION
        "Cisco Firepower firmware:System:fsmFlags managed object property"
    ::= { cfprFirmwareSystemEntry 5 }

cfprFirmwareSystemFsmPrev OBJECT-TYPE
    SYNTAX       SnmpAdminString
    MAX-ACCESS   read-only
    STATUS       current
    DESCRIPTION
        "Cisco Firepower firmware:System:fsmPrev managed object property"
    ::= { cfprFirmwareSystemEntry 6 }

cfprFirmwareSystemFsmProgr OBJECT-TYPE
    SYNTAX       Gauge32
    MAX-ACCESS   read-only
    STATUS       current
    DESCRIPTION
        "Cisco Firepower firmware:System:fsmProgr managed object property"
    ::= { cfprFirmwareSystemEntry 7 }

cfprFirmwareSystemFsmRmtInvErrCode OBJECT-TYPE
    SYNTAX       Gauge32
    MAX-ACCESS   read-only
    STATUS       current
    DESCRIPTION
        "Cisco Firepower firmware:System:fsmRmtInvErrCode
        managed object property"
    ::= { cfprFirmwareSystemEntry 8 }

cfprFirmwareSystemFsmRmtInvErrDescr OBJECT-TYPE
    SYNTAX       SnmpAdminString
    MAX-ACCESS   read-only
    STATUS       current
    DESCRIPTION
        "Cisco Firepower firmware:System:fsmRmtInvErrDescr
        managed object property"
    ::= { cfprFirmwareSystemEntry 9 }

cfprFirmwareSystemFsmRmtInvRslt OBJECT-TYPE
    SYNTAX       CfprConditionRemoteInvRslt
    MAX-ACCESS   read-only
    STATUS       current
    DESCRIPTION
        "Cisco Firepower firmware:System:fsmRmtInvRslt
        managed object property"
    ::= { cfprFirmwareSystemEntry 10 }

cfprFirmwareSystemFsmStageDescr OBJECT-TYPE
    SYNTAX       SnmpAdminString
    MAX-ACCESS   read-only
    STATUS       current
    DESCRIPTION
        "Cisco Firepower firmware:System:fsmStageDescr
        managed object property"
    ::= { cfprFirmwareSystemEntry 11 }

cfprFirmwareSystemFsmStamp OBJECT-TYPE
    SYNTAX       DateAndTime
    MAX-ACCESS   read-only
    STATUS       current
    DESCRIPTION
        "Cisco Firepower firmware:System:fsmStamp managed object property"
    ::= { cfprFirmwareSystemEntry 12 }

cfprFirmwareSystemFsmStatus OBJECT-TYPE
    SYNTAX       SnmpAdminString
    MAX-ACCESS   read-only
    STATUS       current
    DESCRIPTION
        "Cisco Firepower firmware:System:fsmStatus managed
        object property"
    ::= { cfprFirmwareSystemEntry 13 }

cfprFirmwareSystemFsmTry OBJECT-TYPE
    SYNTAX       Gauge32
    MAX-ACCESS   read-only
    STATUS       current
    DESCRIPTION
        "Cisco Firepower firmware:System:fsmTry managed object property"
    ::= { cfprFirmwareSystemEntry 14 }

cfprFirmwareSystemOperState OBJECT-TYPE
    SYNTAX       CfprFirmwareInstallState
    MAX-ACCESS   read-only
    STATUS       current
    DESCRIPTION
        "Cisco Firepower firmware:System:operState managed
        object property"
    ::= { cfprFirmwareSystemEntry 15 }

cfprFirmwareSystemState OBJECT-TYPE
    SYNTAX       CfprFirmwareFwState
    MAX-ACCESS   read-only
    STATUS       current
    DESCRIPTION
        "Cisco Firepower firmware:System:state managed object property"
    ::= { cfprFirmwareSystemEntry 16 }

cfprFirmwareSystemResetOnUpgrade OBJECT-TYPE
    SYNTAX       TruthValue
    MAX-ACCESS   read-only
    STATUS       current
    DESCRIPTION
        "Cisco Firepower firmware:System:resetOnUpgrade
        managed object property"
    ::= { cfprFirmwareSystemEntry 17 }

cfprFirmwareSystemScheduledInstallTime OBJECT-TYPE
    SYNTAX       DateAndTime
    MAX-ACCESS   read-only
    STATUS       current
    DESCRIPTION
        "Cisco Firepower firmware:System:scheduledInstallTime
        managed object property"
    ::= { cfprFirmwareSystemEntry 18 }

cfprFirmwareSystemValidationStatus OBJECT-TYPE
    SYNTAX       CfprFirmwareVerifyPackStatus
    MAX-ACCESS   read-only
    STATUS       current
    DESCRIPTION
        "Cisco Firepower firmware:System:validationStatus
        managed object property"
    ::= { cfprFirmwareSystemEntry 19 }

cfprFirmwareSystemCompCheckResultTable OBJECT-TYPE
    SYNTAX           SEQUENCE OF CfprFirmwareSystemCompCheckResultEntry
    MAX-ACCESS       not-accessible
    STATUS           current
    DESCRIPTION
        "Cisco Firepower firmware:SystemCompCheckResult
        managed object table"
    ::= { cfprFirmwareObjects 51 }

cfprFirmwareSystemCompCheckResultEntry OBJECT-TYPE
    SYNTAX           CfprFirmwareSystemCompCheckResultEntry
    MAX-ACCESS       not-accessible
    STATUS           current
    DESCRIPTION
        "Entry for the cfprFirmwareSystemCompCheckResultTable table."
    INDEX { cfprFirmwareSystemCompCheckResultInstanceId }
    ::= { cfprFirmwareSystemCompCheckResultTable 1 }

CfprFirmwareSystemCompCheckResultEntry ::= SEQUENCE {
    cfprFirmwareSystemCompCheckResultInstanceId                      CfprManagedObjectId,
    cfprFirmwareSystemCompCheckResultDn                              CfprManagedObjectDn,
    cfprFirmwareSystemCompCheckResultRn                              SnmpAdminString,
    cfprFirmwareSystemCompCheckResultKeyDescr                        SnmpAdminString,
    cfprFirmwareSystemCompCheckResultKeyDn                           SnmpAdminString,
    cfprFirmwareSystemCompCheckResultNonCompDescr                    SnmpAdminString,
    cfprFirmwareSystemCompCheckResultNonCompDns                      SnmpAdminString,
    cfprFirmwareSystemCompCheckResultSubject                         CfprFirmwareEquipmentType
}

cfprFirmwareSystemCompCheckResultInstanceId OBJECT-TYPE
    SYNTAX       CfprManagedObjectId
    MAX-ACCESS   not-accessible
    STATUS       current
    DESCRIPTION
        "Instance identifier of the managed object."
    ::= { cfprFirmwareSystemCompCheckResultEntry 1 }

cfprFirmwareSystemCompCheckResultDn OBJECT-TYPE
    SYNTAX       CfprManagedObjectDn
    MAX-ACCESS   read-only
    STATUS       current
    DESCRIPTION
        "Cisco Firepower firmware:SystemCompCheckResult:dn
        managed object property"
    ::= { cfprFirmwareSystemCompCheckResultEntry 2 }

cfprFirmwareSystemCompCheckResultRn OBJECT-TYPE
    SYNTAX       SnmpAdminString
    MAX-ACCESS   read-only
    STATUS       current
    DESCRIPTION
        "Cisco Firepower firmware:SystemCompCheckResult:rn
        managed object property"
    ::= { cfprFirmwareSystemCompCheckResultEntry 3 }

cfprFirmwareSystemCompCheckResultKeyDescr OBJECT-TYPE
    SYNTAX       SnmpAdminString
    MAX-ACCESS   read-only
    STATUS       current
    DESCRIPTION
        "Cisco Firepower firmware:SystemCompCheckResult:keyDescr
        managed object property"
    ::= { cfprFirmwareSystemCompCheckResultEntry 4 }

cfprFirmwareSystemCompCheckResultKeyDn OBJECT-TYPE
    SYNTAX       SnmpAdminString
    MAX-ACCESS   read-only
    STATUS       current
    DESCRIPTION
        "Cisco Firepower firmware:SystemCompCheckResult:keyDn
        managed object property"
    ::= { cfprFirmwareSystemCompCheckResultEntry 5 }

cfprFirmwareSystemCompCheckResultNonCompDescr OBJECT-TYPE
    SYNTAX       SnmpAdminString
    MAX-ACCESS   read-only
    STATUS       current
    DESCRIPTION
        "Cisco Firepower firmware:SystemCompCheckResult:nonCompDescr
        managed object property"
    ::= { cfprFirmwareSystemCompCheckResultEntry 6 }

cfprFirmwareSystemCompCheckResultNonCompDns OBJECT-TYPE
    SYNTAX       SnmpAdminString
    MAX-ACCESS   read-only
    STATUS       current
    DESCRIPTION
        "Cisco Firepower firmware:SystemCompCheckResult:nonCompDns
        managed object property"
    ::= { cfprFirmwareSystemCompCheckResultEntry 7 }

cfprFirmwareSystemCompCheckResultSubject OBJECT-TYPE
    SYNTAX       CfprFirmwareEquipmentType
    MAX-ACCESS   read-only
    STATUS       current
    DESCRIPTION
        "Cisco Firepower firmware:SystemCompCheckResult:subject
        managed object property"
    ::= { cfprFirmwareSystemCompCheckResultEntry 8 }

cfprFirmwareSystemFsmTable OBJECT-TYPE
    SYNTAX           SEQUENCE OF CfprFirmwareSystemFsmEntry
    MAX-ACCESS       not-accessible
    STATUS           current
    DESCRIPTION
        "Cisco Firepower firmware:SystemFsm managed object table"
    ::= { cfprFirmwareObjects 52 }

cfprFirmwareSystemFsmEntry OBJECT-TYPE
    SYNTAX           CfprFirmwareSystemFsmEntry
    MAX-ACCESS       not-accessible
    STATUS           current
    DESCRIPTION
        "Entry for the cfprFirmwareSystemFsmTable table."
    INDEX { cfprFirmwareSystemFsmInstanceId }
    ::= { cfprFirmwareSystemFsmTable 1 }

CfprFirmwareSystemFsmEntry ::= SEQUENCE {
    cfprFirmwareSystemFsmInstanceId                                  CfprManagedObjectId,
    cfprFirmwareSystemFsmDn                                          CfprManagedObjectDn,
    cfprFirmwareSystemFsmRn                                          SnmpAdminString,
    cfprFirmwareSystemFsmCompletionTime                              DateAndTime,
    cfprFirmwareSystemFsmCurrentFsm                                  CfprFirmwareSystemFsmCurrentFsm,
    cfprFirmwareSystemFsmDescrData                                   SnmpAdminString,
    cfprFirmwareSystemFsmFsmStatus                                   CfprFsmFsmStageStatus,
    cfprFirmwareSystemFsmProgress                                    Gauge32,
    cfprFirmwareSystemFsmRmtErrCode                                  Gauge32,
    cfprFirmwareSystemFsmRmtErrDescr                                 SnmpAdminString,
    cfprFirmwareSystemFsmRmtRslt                                     CfprConditionRemoteInvRslt
}

cfprFirmwareSystemFsmInstanceId OBJECT-TYPE
    SYNTAX       CfprManagedObjectId
    MAX-ACCESS   not-accessible
    STATUS       current
    DESCRIPTION
        "Instance identifier of the managed object."
    ::= { cfprFirmwareSystemFsmEntry 1 }

cfprFirmwareSystemFsmDn OBJECT-TYPE
    SYNTAX       CfprManagedObjectDn
    MAX-ACCESS   read-only
    STATUS       current
    DESCRIPTION
        "Cisco Firepower firmware:SystemFsm:dn managed object property"
    ::= { cfprFirmwareSystemFsmEntry 2 }

cfprFirmwareSystemFsmRn OBJECT-TYPE
    SYNTAX       SnmpAdminString
    MAX-ACCESS   read-only
    STATUS       current
    DESCRIPTION
        "Cisco Firepower firmware:SystemFsm:rn managed object property"
    ::= { cfprFirmwareSystemFsmEntry 3 }

cfprFirmwareSystemFsmCompletionTime OBJECT-TYPE
    SYNTAX       DateAndTime
    MAX-ACCESS   read-only
    STATUS       current
    DESCRIPTION
        "Cisco Firepower firmware:SystemFsm:completionTime
        managed object property"
    ::= { cfprFirmwareSystemFsmEntry 4 }

cfprFirmwareSystemFsmCurrentFsm OBJECT-TYPE
    SYNTAX       CfprFirmwareSystemFsmCurrentFsm
    MAX-ACCESS   read-only
    STATUS       current
    DESCRIPTION
        "Cisco Firepower firmware:SystemFsm:currentFsm
        managed object property"
    ::= { cfprFirmwareSystemFsmEntry 5 }

cfprFirmwareSystemFsmDescrData OBJECT-TYPE
    SYNTAX       SnmpAdminString
    MAX-ACCESS   read-only
    STATUS       current
    DESCRIPTION
        "Cisco Firepower firmware:SystemFsm:descr managed object property"
    ::= { cfprFirmwareSystemFsmEntry 6 }

cfprFirmwareSystemFsmFsmStatus OBJECT-TYPE
    SYNTAX       CfprFsmFsmStageStatus
    MAX-ACCESS   read-only
    STATUS       current
    DESCRIPTION
        "Cisco Firepower firmware:SystemFsm:fsmStatus managed
        object property"
    ::= { cfprFirmwareSystemFsmEntry 7 }

cfprFirmwareSystemFsmProgress OBJECT-TYPE
    SYNTAX       Gauge32
    MAX-ACCESS   read-only
    STATUS       current
    DESCRIPTION
        "Cisco Firepower firmware:SystemFsm:progress managed
        object property"
    ::= { cfprFirmwareSystemFsmEntry 8 }

cfprFirmwareSystemFsmRmtErrCode OBJECT-TYPE
    SYNTAX       Gauge32
    MAX-ACCESS   read-only
    STATUS       current
    DESCRIPTION
        "Cisco Firepower firmware:SystemFsm:rmtErrCode
        managed object property"
    ::= { cfprFirmwareSystemFsmEntry 9 }

cfprFirmwareSystemFsmRmtErrDescr OBJECT-TYPE
    SYNTAX       SnmpAdminString
    MAX-ACCESS   read-only
    STATUS       current
    DESCRIPTION
        "Cisco Firepower firmware:SystemFsm:rmtErrDescr
        managed object property"
    ::= { cfprFirmwareSystemFsmEntry 10 }

cfprFirmwareSystemFsmRmtRslt OBJECT-TYPE
    SYNTAX       CfprConditionRemoteInvRslt
    MAX-ACCESS   read-only
    STATUS       current
    DESCRIPTION
        "Cisco Firepower firmware:SystemFsm:rmtRslt managed
        object property"
    ::= { cfprFirmwareSystemFsmEntry 11 }

cfprFirmwareSystemFsmStageTable OBJECT-TYPE
    SYNTAX           SEQUENCE OF CfprFirmwareSystemFsmStageEntry
    MAX-ACCESS       not-accessible
    STATUS           current
    DESCRIPTION
        "Cisco Firepower firmware:SystemFsmStage managed object table"
    ::= { cfprFirmwareObjects 53 }

cfprFirmwareSystemFsmStageEntry OBJECT-TYPE
    SYNTAX           CfprFirmwareSystemFsmStageEntry
    MAX-ACCESS       not-accessible
    STATUS           current
    DESCRIPTION
        "Entry for the cfprFirmwareSystemFsmStageTable table."
    INDEX { cfprFirmwareSystemFsmStageInstanceId }
    ::= { cfprFirmwareSystemFsmStageTable 1 }

CfprFirmwareSystemFsmStageEntry ::= SEQUENCE {
    cfprFirmwareSystemFsmStageInstanceId                             CfprManagedObjectId,
    cfprFirmwareSystemFsmStageDn                                     CfprManagedObjectDn,
    cfprFirmwareSystemFsmStageRn                                     SnmpAdminString,
    cfprFirmwareSystemFsmStageDescrData                              SnmpAdminString,
    cfprFirmwareSystemFsmStageLastUpdateTime                         DateAndTime,
    cfprFirmwareSystemFsmStageName                                   CfprFirmwareSystemFsmStageName,
    cfprFirmwareSystemFsmStageOrder                                  Gauge32,
    cfprFirmwareSystemFsmStageRetry                                  Gauge32,
    cfprFirmwareSystemFsmStageStageStatus                            CfprFsmFsmStageStatus
}

cfprFirmwareSystemFsmStageInstanceId OBJECT-TYPE
    SYNTAX       CfprManagedObjectId
    MAX-ACCESS   not-accessible
    STATUS       current
    DESCRIPTION
        "Instance identifier of the managed object."
    ::= { cfprFirmwareSystemFsmStageEntry 1 }

cfprFirmwareSystemFsmStageDn OBJECT-TYPE
    SYNTAX       CfprManagedObjectDn
    MAX-ACCESS   read-only
    STATUS       current
    DESCRIPTION
        "Cisco Firepower firmware:SystemFsmStage:dn managed
        object property"
    ::= { cfprFirmwareSystemFsmStageEntry 2 }

cfprFirmwareSystemFsmStageRn OBJECT-TYPE
    SYNTAX       SnmpAdminString
    MAX-ACCESS   read-only
    STATUS       current
    DESCRIPTION
        "Cisco Firepower firmware:SystemFsmStage:rn managed
        object property"
    ::= { cfprFirmwareSystemFsmStageEntry 3 }

cfprFirmwareSystemFsmStageDescrData OBJECT-TYPE
    SYNTAX       SnmpAdminString
    MAX-ACCESS   read-only
    STATUS       current
    DESCRIPTION
        "Cisco Firepower firmware:SystemFsmStage:descr
        managed object property"
    ::= { cfprFirmwareSystemFsmStageEntry 4 }

cfprFirmwareSystemFsmStageLastUpdateTime OBJECT-TYPE
    SYNTAX       DateAndTime
    MAX-ACCESS   read-only
    STATUS       current
    DESCRIPTION
        "Cisco Firepower firmware:SystemFsmStage:lastUpdateTime
        managed object property"
    ::= { cfprFirmwareSystemFsmStageEntry 5 }

cfprFirmwareSystemFsmStageName OBJECT-TYPE
    SYNTAX       CfprFirmwareSystemFsmStageName
    MAX-ACCESS   read-only
    STATUS       current
    DESCRIPTION
        "Cisco Firepower firmware:SystemFsmStage:name managed
        object property"
    ::= { cfprFirmwareSystemFsmStageEntry 6 }

cfprFirmwareSystemFsmStageOrder OBJECT-TYPE
    SYNTAX       Gauge32
    MAX-ACCESS   read-only
    STATUS       current
    DESCRIPTION
        "Cisco Firepower firmware:SystemFsmStage:order
        managed object property"
    ::= { cfprFirmwareSystemFsmStageEntry 7 }

cfprFirmwareSystemFsmStageRetry OBJECT-TYPE
    SYNTAX       Gauge32
    MAX-ACCESS   read-only
    STATUS       current
    DESCRIPTION
        "Cisco Firepower firmware:SystemFsmStage:retry
        managed object property"
    ::= { cfprFirmwareSystemFsmStageEntry 8 }

cfprFirmwareSystemFsmStageStageStatus OBJECT-TYPE
    SYNTAX       CfprFsmFsmStageStatus
    MAX-ACCESS   read-only
    STATUS       current
    DESCRIPTION
        "Cisco Firepower firmware:SystemFsmStage:stageStatus
        managed object property"
    ::= { cfprFirmwareSystemFsmStageEntry 9 }

cfprFirmwareSystemFsmTaskTable OBJECT-TYPE
    SYNTAX           SEQUENCE OF CfprFirmwareSystemFsmTaskEntry
    MAX-ACCESS       not-accessible
    STATUS           current
    DESCRIPTION
        "Cisco Firepower firmware:SystemFsmTask managed object table"
    ::= { cfprFirmwareObjects 54 }

cfprFirmwareSystemFsmTaskEntry OBJECT-TYPE
    SYNTAX           CfprFirmwareSystemFsmTaskEntry
    MAX-ACCESS       not-accessible
    STATUS           current
    DESCRIPTION
        "Entry for the cfprFirmwareSystemFsmTaskTable table."
    INDEX { cfprFirmwareSystemFsmTaskInstanceId }
    ::= { cfprFirmwareSystemFsmTaskTable 1 }

CfprFirmwareSystemFsmTaskEntry ::= SEQUENCE {
    cfprFirmwareSystemFsmTaskInstanceId                              CfprManagedObjectId,
    cfprFirmwareSystemFsmTaskDn                                      CfprManagedObjectDn,
    cfprFirmwareSystemFsmTaskRn                                      SnmpAdminString,
    cfprFirmwareSystemFsmTaskCompletion                              CfprFsmCompletion,
    cfprFirmwareSystemFsmTaskFlags                                   CfprFirmwareSystemFsmTaskFlags,
    cfprFirmwareSystemFsmTaskItem                                    CfprFirmwareSystemFsmTaskItem,
    cfprFirmwareSystemFsmTaskSeqId                                   Gauge32
}

cfprFirmwareSystemFsmTaskInstanceId OBJECT-TYPE
    SYNTAX       CfprManagedObjectId
    MAX-ACCESS   not-accessible
    STATUS       current
    DESCRIPTION
        "Instance identifier of the managed object."
    ::= { cfprFirmwareSystemFsmTaskEntry 1 }

cfprFirmwareSystemFsmTaskDn OBJECT-TYPE
    SYNTAX       CfprManagedObjectDn
    MAX-ACCESS   read-only
    STATUS       current
    DESCRIPTION
        "Cisco Firepower firmware:SystemFsmTask:dn managed
        object property"
    ::= { cfprFirmwareSystemFsmTaskEntry 2 }

cfprFirmwareSystemFsmTaskRn OBJECT-TYPE
    SYNTAX       SnmpAdminString
    MAX-ACCESS   read-only
    STATUS       current
    DESCRIPTION
        "Cisco Firepower firmware:SystemFsmTask:rn managed
        object property"
    ::= { cfprFirmwareSystemFsmTaskEntry 3 }

cfprFirmwareSystemFsmTaskCompletion OBJECT-TYPE
    SYNTAX       CfprFsmCompletion
    MAX-ACCESS   read-only
    STATUS       current
    DESCRIPTION
        "Cisco Firepower firmware:SystemFsmTask:completion
        managed object property"
    ::= { cfprFirmwareSystemFsmTaskEntry 4 }

cfprFirmwareSystemFsmTaskFlags OBJECT-TYPE
    SYNTAX       CfprFirmwareSystemFsmTaskFlags
    MAX-ACCESS   read-only
    STATUS       current
    DESCRIPTION
        "Cisco Firepower firmware:SystemFsmTask:flags managed
        object property"
    ::= { cfprFirmwareSystemFsmTaskEntry 5 }

cfprFirmwareSystemFsmTaskItem OBJECT-TYPE
    SYNTAX       CfprFirmwareSystemFsmTaskItem
    MAX-ACCESS   read-only
    STATUS       current
    DESCRIPTION
        "Cisco Firepower firmware:SystemFsmTask:item managed
        object property"
    ::= { cfprFirmwareSystemFsmTaskEntry 6 }

cfprFirmwareSystemFsmTaskSeqId OBJECT-TYPE
    SYNTAX       Gauge32
    MAX-ACCESS   read-only
    STATUS       current
    DESCRIPTION
        "Cisco Firepower firmware:SystemFsmTask:seqId managed
        object property"
    ::= { cfprFirmwareSystemFsmTaskEntry 7 }

cfprFirmwareTypeTable OBJECT-TYPE
    SYNTAX           SEQUENCE OF CfprFirmwareTypeEntry
    MAX-ACCESS       not-accessible
    STATUS           current
    DESCRIPTION
        "Cisco Firepower firmware:Type managed object table"
    ::= { cfprFirmwareObjects 55 }

cfprFirmwareTypeEntry OBJECT-TYPE
    SYNTAX           CfprFirmwareTypeEntry
    MAX-ACCESS       not-accessible
    STATUS           current
    DESCRIPTION
        "Entry for the cfprFirmwareTypeTable table."
    INDEX { cfprFirmwareTypeInstanceId }
    ::= { cfprFirmwareTypeTable 1 }

CfprFirmwareTypeEntry ::= SEQUENCE {
    cfprFirmwareTypeInstanceId                                       CfprManagedObjectId,
    cfprFirmwareTypeDn                                               CfprManagedObjectDn,
    cfprFirmwareTypeRn                                               SnmpAdminString,
    cfprFirmwareTypeEp                                               CfprFirmwareType,
    cfprFirmwareTypeInvTag                                           SnmpAdminString,
    cfprFirmwareTypeMaxVer                                           SnmpAdminString,
    cfprFirmwareTypeMinVer                                           SnmpAdminString,
    cfprFirmwareTypePid                                              SnmpAdminString,
    cfprFirmwareTypeScheduledInstallTime                             DateAndTime
}

cfprFirmwareTypeInstanceId OBJECT-TYPE
    SYNTAX       CfprManagedObjectId
    MAX-ACCESS   not-accessible
    STATUS       current
    DESCRIPTION
        "Instance identifier of the managed object."
    ::= { cfprFirmwareTypeEntry 1 }

cfprFirmwareTypeDn OBJECT-TYPE
    SYNTAX       CfprManagedObjectDn
    MAX-ACCESS   read-only
    STATUS       current
    DESCRIPTION
        "Cisco Firepower firmware:Type:dn managed object property"
    ::= { cfprFirmwareTypeEntry 2 }

cfprFirmwareTypeRn OBJECT-TYPE
    SYNTAX       SnmpAdminString
    MAX-ACCESS   read-only
    STATUS       current
    DESCRIPTION
        "Cisco Firepower firmware:Type:rn managed object property"
    ::= { cfprFirmwareTypeEntry 3 }

cfprFirmwareTypeEp OBJECT-TYPE
    SYNTAX       CfprFirmwareType
    MAX-ACCESS   read-only
    STATUS       current
    DESCRIPTION
        "Cisco Firepower firmware:Type:ep managed object property"
    ::= { cfprFirmwareTypeEntry 4 }

cfprFirmwareTypeInvTag OBJECT-TYPE
    SYNTAX       SnmpAdminString
    MAX-ACCESS   read-only
    STATUS       current
    DESCRIPTION
        "Cisco Firepower firmware:Type:invTag managed object property"
    ::= { cfprFirmwareTypeEntry 5 }

cfprFirmwareTypeMaxVer OBJECT-TYPE
    SYNTAX       SnmpAdminString
    MAX-ACCESS   read-only
    STATUS       current
    DESCRIPTION
        "Cisco Firepower firmware:Type:maxVer managed object property"
    ::= { cfprFirmwareTypeEntry 6 }

cfprFirmwareTypeMinVer OBJECT-TYPE
    SYNTAX       SnmpAdminString
    MAX-ACCESS   read-only
    STATUS       current
    DESCRIPTION
        "Cisco Firepower firmware:Type:minVer managed object property"
    ::= { cfprFirmwareTypeEntry 7 }

cfprFirmwareTypePid OBJECT-TYPE
    SYNTAX       SnmpAdminString
    MAX-ACCESS   read-only
    STATUS       current
    DESCRIPTION
        "Cisco Firepower firmware:Type:pid managed object property"
    ::= { cfprFirmwareTypeEntry 8 }

cfprFirmwareTypeScheduledInstallTime OBJECT-TYPE
    SYNTAX       DateAndTime
    MAX-ACCESS   read-only
    STATUS       current
    DESCRIPTION
        "Cisco Firepower firmware:Type:scheduledInstallTime
        managed object property"
    ::= { cfprFirmwareTypeEntry 9 }

cfprFirmwareFprcInfoTable OBJECT-TYPE
    SYNTAX           SEQUENCE OF CfprFirmwareFprcInfoEntry
    MAX-ACCESS       not-accessible
    STATUS           current
    DESCRIPTION
        "Cisco Firepower firmware:FprcInfo managed object table"
    ::= { cfprFirmwareObjects 56 }

cfprFirmwareFprcInfoEntry OBJECT-TYPE
    SYNTAX           CfprFirmwareFprcInfoEntry
    MAX-ACCESS       not-accessible
    STATUS           current
    DESCRIPTION
        "Entry for the cfprFirmwareFprcInfoTable table."
    INDEX { cfprFirmwareFprcInfoInstanceId }
    ::= { cfprFirmwareFprcInfoTable 1 }

CfprFirmwareFprcInfoEntry ::= SEQUENCE {
    cfprFirmwareFprcInfoInstanceId                                   CfprManagedObjectId,
    cfprFirmwareFprcInfoDn                                           CfprManagedObjectDn,
    cfprFirmwareFprcInfoRn                                           SnmpAdminString,
    cfprFirmwareFprcInfoConnProtocol                                 CfprExtpolConnProtocol,
    cfprFirmwareFprcInfoHost                                         SnmpAdminString,
    cfprFirmwareFprcInfoVersion                                      SnmpAdminString
}

cfprFirmwareFprcInfoInstanceId OBJECT-TYPE
    SYNTAX       CfprManagedObjectId
    MAX-ACCESS   not-accessible
    STATUS       current
    DESCRIPTION
        "Instance identifier of the managed object."
    ::= { cfprFirmwareFprcInfoEntry 1 }

cfprFirmwareFprcInfoDn OBJECT-TYPE
    SYNTAX       CfprManagedObjectDn
    MAX-ACCESS   read-only
    STATUS       current
    DESCRIPTION
        "Cisco Firepower firmware:FprcInfo:dn managed object property"
    ::= { cfprFirmwareFprcInfoEntry 2 }

cfprFirmwareFprcInfoRn OBJECT-TYPE
    SYNTAX       SnmpAdminString
    MAX-ACCESS   read-only
    STATUS       current
    DESCRIPTION
        "Cisco Firepower firmware:FprcInfo:rn managed object property"
    ::= { cfprFirmwareFprcInfoEntry 3 }

cfprFirmwareFprcInfoConnProtocol OBJECT-TYPE
    SYNTAX       CfprExtpolConnProtocol
    MAX-ACCESS   read-only
    STATUS       current
    DESCRIPTION
        "Cisco Firepower firmware:FprcInfo:connProtocol
        managed object property"
    ::= { cfprFirmwareFprcInfoEntry 4 }

cfprFirmwareFprcInfoHost OBJECT-TYPE
    SYNTAX       SnmpAdminString
    MAX-ACCESS   read-only
    STATUS       current
    DESCRIPTION
        "Cisco Firepower firmware:FprcInfo:host managed object property"
    ::= { cfprFirmwareFprcInfoEntry 5 }

cfprFirmwareFprcInfoVersion OBJECT-TYPE
    SYNTAX       SnmpAdminString
    MAX-ACCESS   read-only
    STATUS       current
    DESCRIPTION
        "Cisco Firepower firmware:FprcInfo:version managed
        object property"
    ::= { cfprFirmwareFprcInfoEntry 6 }

cfprFirmwareUpdatableTable OBJECT-TYPE
    SYNTAX           SEQUENCE OF CfprFirmwareUpdatableEntry
    MAX-ACCESS       not-accessible
    STATUS           current
    DESCRIPTION
        "Cisco Firepower firmware:Updatable managed object table"
    ::= { cfprFirmwareObjects 57 }

cfprFirmwareUpdatableEntry OBJECT-TYPE
    SYNTAX           CfprFirmwareUpdatableEntry
    MAX-ACCESS       not-accessible
    STATUS           current
    DESCRIPTION
        "Entry for the cfprFirmwareUpdatableTable table."
    INDEX { cfprFirmwareUpdatableInstanceId }
    ::= { cfprFirmwareUpdatableTable 1 }

CfprFirmwareUpdatableEntry ::= SEQUENCE {
    cfprFirmwareUpdatableInstanceId                                  CfprManagedObjectId,
    cfprFirmwareUpdatableDn                                          CfprManagedObjectDn,
    cfprFirmwareUpdatableRn                                          SnmpAdminString,
    cfprFirmwareUpdatableAdminState                                  CfprFirmwareTriggerState,
    cfprFirmwareUpdatableDeployment                                  CfprFirmwareUpdatableDeployment,
    cfprFirmwareUpdatableOperState                                   CfprFirmwareImageState,
    cfprFirmwareUpdatableOperStateQual                               CfprFirmwareImageError,
    cfprFirmwareUpdatablePrevVersion                                 SnmpAdminString,
    cfprFirmwareUpdatableVersion                                     SnmpAdminString
}

cfprFirmwareUpdatableInstanceId OBJECT-TYPE
    SYNTAX       CfprManagedObjectId
    MAX-ACCESS   not-accessible
    STATUS       current
    DESCRIPTION
        "Instance identifier of the managed object."
    ::= { cfprFirmwareUpdatableEntry 1 }

cfprFirmwareUpdatableDn OBJECT-TYPE
    SYNTAX       CfprManagedObjectDn
    MAX-ACCESS   read-only
    STATUS       current
    DESCRIPTION
        "Cisco Firepower firmware:Updatable:dn managed object property"
    ::= { cfprFirmwareUpdatableEntry 2 }

cfprFirmwareUpdatableRn OBJECT-TYPE
    SYNTAX       SnmpAdminString
    MAX-ACCESS   read-only
    STATUS       current
    DESCRIPTION
        "Cisco Firepower firmware:Updatable:rn managed object property"
    ::= { cfprFirmwareUpdatableEntry 3 }

cfprFirmwareUpdatableAdminState OBJECT-TYPE
    SYNTAX       CfprFirmwareTriggerState
    MAX-ACCESS   read-only
    STATUS       current
    DESCRIPTION
        "Cisco Firepower firmware:Updatable:adminState
        managed object property"
    ::= { cfprFirmwareUpdatableEntry 4 }

cfprFirmwareUpdatableDeployment OBJECT-TYPE
    SYNTAX       CfprFirmwareUpdatableDeployment
    MAX-ACCESS   read-only
    STATUS       current
    DESCRIPTION
        "Cisco Firepower firmware:Updatable:deployment
        managed object property"
    ::= { cfprFirmwareUpdatableEntry 5 }

cfprFirmwareUpdatableOperState OBJECT-TYPE
    SYNTAX       CfprFirmwareImageState
    MAX-ACCESS   read-only
    STATUS       current
    DESCRIPTION
        "Cisco Firepower firmware:Updatable:operState managed
        object property"
    ::= { cfprFirmwareUpdatableEntry 6 }

cfprFirmwareUpdatableOperStateQual OBJECT-TYPE
    SYNTAX       CfprFirmwareImageError
    MAX-ACCESS   read-only
    STATUS       current
    DESCRIPTION
        "Cisco Firepower firmware:Updatable:operStateQual
        managed object property"
    ::= { cfprFirmwareUpdatableEntry 7 }

cfprFirmwareUpdatablePrevVersion OBJECT-TYPE
    SYNTAX       SnmpAdminString
    MAX-ACCESS   read-only
    STATUS       current
    DESCRIPTION
        "Cisco Firepower firmware:Updatable:prevVersion
        managed object property"
    ::= { cfprFirmwareUpdatableEntry 8 }

cfprFirmwareUpdatableVersion OBJECT-TYPE
    SYNTAX       SnmpAdminString
    MAX-ACCESS   read-only
    STATUS       current
    DESCRIPTION
        "Cisco Firepower firmware:Updatable:version managed
        object property"
    ::= { cfprFirmwareUpdatableEntry 9 }

cfprFirmwareUpgradeConstraintTable OBJECT-TYPE
    SYNTAX           SEQUENCE OF CfprFirmwareUpgradeConstraintEntry
    MAX-ACCESS       not-accessible
    STATUS           current
    DESCRIPTION
        "Cisco Firepower firmware:UpgradeConstraint managed object table"
    ::= { cfprFirmwareObjects 58 }

cfprFirmwareUpgradeConstraintEntry OBJECT-TYPE
    SYNTAX           CfprFirmwareUpgradeConstraintEntry
    MAX-ACCESS       not-accessible
    STATUS           current
    DESCRIPTION
        "Entry for the cfprFirmwareUpgradeConstraintTable table."
    INDEX { cfprFirmwareUpgradeConstraintInstanceId }
    ::= { cfprFirmwareUpgradeConstraintTable 1 }

CfprFirmwareUpgradeConstraintEntry ::= SEQUENCE {
    cfprFirmwareUpgradeConstraintInstanceId                          CfprManagedObjectId,
    cfprFirmwareUpgradeConstraintDn                                  CfprManagedObjectDn,
    cfprFirmwareUpgradeConstraintRn                                  SnmpAdminString,
    cfprFirmwareUpgradeConstraintMinVer                              SnmpAdminString
}

cfprFirmwareUpgradeConstraintInstanceId OBJECT-TYPE
    SYNTAX       CfprManagedObjectId
    MAX-ACCESS   not-accessible
    STATUS       current
    DESCRIPTION
        "Instance identifier of the managed object."
    ::= { cfprFirmwareUpgradeConstraintEntry 1 }

cfprFirmwareUpgradeConstraintDn OBJECT-TYPE
    SYNTAX       CfprManagedObjectDn
    MAX-ACCESS   read-only
    STATUS       current
    DESCRIPTION
        "Cisco Firepower firmware:UpgradeConstraint:dn
        managed object property"
    ::= { cfprFirmwareUpgradeConstraintEntry 2 }

cfprFirmwareUpgradeConstraintRn OBJECT-TYPE
    SYNTAX       SnmpAdminString
    MAX-ACCESS   read-only
    STATUS       current
    DESCRIPTION
        "Cisco Firepower firmware:UpgradeConstraint:rn
        managed object property"
    ::= { cfprFirmwareUpgradeConstraintEntry 3 }

cfprFirmwareUpgradeConstraintMinVer OBJECT-TYPE
    SYNTAX       SnmpAdminString
    MAX-ACCESS   read-only
    STATUS       current
    DESCRIPTION
        "Cisco Firepower firmware:UpgradeConstraint:minVer
        managed object property"
    ::= { cfprFirmwareUpgradeConstraintEntry 4 }

cfprFirmwareUpgradeDetailTable OBJECT-TYPE
    SYNTAX           SEQUENCE OF CfprFirmwareUpgradeDetailEntry
    MAX-ACCESS       not-accessible
    STATUS           current
    DESCRIPTION
        "Cisco Firepower firmware:UpgradeDetail managed object table"
    ::= { cfprFirmwareObjects 59 }

cfprFirmwareUpgradeDetailEntry OBJECT-TYPE
    SYNTAX           CfprFirmwareUpgradeDetailEntry
    MAX-ACCESS       not-accessible
    STATUS           current
    DESCRIPTION
        "Entry for the cfprFirmwareUpgradeDetailTable table."
    INDEX { cfprFirmwareUpgradeDetailInstanceId }
    ::= { cfprFirmwareUpgradeDetailTable 1 }

CfprFirmwareUpgradeDetailEntry ::= SEQUENCE {
    cfprFirmwareUpgradeDetailInstanceId                              CfprManagedObjectId,
    cfprFirmwareUpgradeDetailDn                                      CfprManagedObjectDn,
    cfprFirmwareUpgradeDetailRn                                      SnmpAdminString,
    cfprFirmwareUpgradeDetailCategory                                CfprFirmwareUpgradeCategory,
    cfprFirmwareUpgradeDetailDescription                             SnmpAdminString,
    cfprFirmwareUpgradeDetailId                                      Gauge32,
    cfprFirmwareUpgradeDetailSeverity                                CfprFirmwareUpgradeSeverity
}

cfprFirmwareUpgradeDetailInstanceId OBJECT-TYPE
    SYNTAX       CfprManagedObjectId
    MAX-ACCESS   not-accessible
    STATUS       current
    DESCRIPTION
        "Instance identifier of the managed object."
    ::= { cfprFirmwareUpgradeDetailEntry 1 }

cfprFirmwareUpgradeDetailDn OBJECT-TYPE
    SYNTAX       CfprManagedObjectDn
    MAX-ACCESS   read-only
    STATUS       current
    DESCRIPTION
        "Cisco Firepower firmware:UpgradeDetail:dn managed
        object property"
    ::= { cfprFirmwareUpgradeDetailEntry 2 }

cfprFirmwareUpgradeDetailRn OBJECT-TYPE
    SYNTAX       SnmpAdminString
    MAX-ACCESS   read-only
    STATUS       current
    DESCRIPTION
        "Cisco Firepower firmware:UpgradeDetail:rn managed
        object property"
    ::= { cfprFirmwareUpgradeDetailEntry 3 }

cfprFirmwareUpgradeDetailCategory OBJECT-TYPE
    SYNTAX       CfprFirmwareUpgradeCategory
    MAX-ACCESS   read-only
    STATUS       current
    DESCRIPTION
        "Cisco Firepower firmware:UpgradeDetail:category
        managed object property"
    ::= { cfprFirmwareUpgradeDetailEntry 4 }

cfprFirmwareUpgradeDetailDescription OBJECT-TYPE
    SYNTAX       SnmpAdminString
    MAX-ACCESS   read-only
    STATUS       current
    DESCRIPTION
        "Cisco Firepower firmware:UpgradeDetail:description
        managed object property"
    ::= { cfprFirmwareUpgradeDetailEntry 5 }

cfprFirmwareUpgradeDetailId OBJECT-TYPE
    SYNTAX       Gauge32
    MAX-ACCESS   read-only
    STATUS       current
    DESCRIPTION
        "Cisco Firepower firmware:UpgradeDetail:id managed
        object property"
    ::= { cfprFirmwareUpgradeDetailEntry 6 }

cfprFirmwareUpgradeDetailSeverity OBJECT-TYPE
    SYNTAX       CfprFirmwareUpgradeSeverity
    MAX-ACCESS   read-only
    STATUS       current
    DESCRIPTION
        "Cisco Firepower firmware:UpgradeDetail:severity
        managed object property"
    ::= { cfprFirmwareUpgradeDetailEntry 7 }

cfprFirmwareUpgradeInfoTable OBJECT-TYPE
    SYNTAX           SEQUENCE OF CfprFirmwareUpgradeInfoEntry
    MAX-ACCESS       not-accessible
    STATUS           current
    DESCRIPTION
        "Cisco Firepower firmware:UpgradeInfo managed object table"
    ::= { cfprFirmwareObjects 60 }

cfprFirmwareUpgradeInfoEntry OBJECT-TYPE
    SYNTAX           CfprFirmwareUpgradeInfoEntry
    MAX-ACCESS       not-accessible
    STATUS           current
    DESCRIPTION
        "Entry for the cfprFirmwareUpgradeInfoTable table."
    INDEX { cfprFirmwareUpgradeInfoInstanceId }
    ::= { cfprFirmwareUpgradeInfoTable 1 }

CfprFirmwareUpgradeInfoEntry ::= SEQUENCE {
    cfprFirmwareUpgradeInfoInstanceId                                CfprManagedObjectId,
    cfprFirmwareUpgradeInfoDn                                        CfprManagedObjectDn,
    cfprFirmwareUpgradeInfoRn                                        SnmpAdminString,
    cfprFirmwareUpgradeInfoMessage                                   SnmpAdminString,
    cfprFirmwareUpgradeInfoTimeStamp                                 DateAndTime,
    cfprFirmwareUpgradeInfoValidateStatus                            CfprFirmwareUpgradeStatus,
    cfprFirmwareUpgradeInfoVersion                                   SnmpAdminString
}

cfprFirmwareUpgradeInfoInstanceId OBJECT-TYPE
    SYNTAX       CfprManagedObjectId
    MAX-ACCESS   not-accessible
    STATUS       current
    DESCRIPTION
        "Instance identifier of the managed object."
    ::= { cfprFirmwareUpgradeInfoEntry 1 }

cfprFirmwareUpgradeInfoDn OBJECT-TYPE
    SYNTAX       CfprManagedObjectDn
    MAX-ACCESS   read-only
    STATUS       current
    DESCRIPTION
        "Cisco Firepower firmware:UpgradeInfo:dn managed object property"
    ::= { cfprFirmwareUpgradeInfoEntry 2 }

cfprFirmwareUpgradeInfoRn OBJECT-TYPE
    SYNTAX       SnmpAdminString
    MAX-ACCESS   read-only
    STATUS       current
    DESCRIPTION
        "Cisco Firepower firmware:UpgradeInfo:rn managed object property"
    ::= { cfprFirmwareUpgradeInfoEntry 3 }

cfprFirmwareUpgradeInfoMessage OBJECT-TYPE
    SYNTAX       SnmpAdminString
    MAX-ACCESS   read-only
    STATUS       current
    DESCRIPTION
        "Cisco Firepower firmware:UpgradeInfo:message managed
        object property"
    ::= { cfprFirmwareUpgradeInfoEntry 4 }

cfprFirmwareUpgradeInfoTimeStamp OBJECT-TYPE
    SYNTAX       DateAndTime
    MAX-ACCESS   read-only
    STATUS       current
    DESCRIPTION
        "Cisco Firepower firmware:UpgradeInfo:timeStamp
        managed object property"
    ::= { cfprFirmwareUpgradeInfoEntry 5 }

cfprFirmwareUpgradeInfoValidateStatus OBJECT-TYPE
    SYNTAX       CfprFirmwareUpgradeStatus
    MAX-ACCESS   read-only
    STATUS       current
    DESCRIPTION
        "Cisco Firepower firmware:UpgradeInfo:validateStatus
        managed object property"
    ::= { cfprFirmwareUpgradeInfoEntry 6 }

cfprFirmwareUpgradeInfoVersion OBJECT-TYPE
    SYNTAX       SnmpAdminString
    MAX-ACCESS   read-only
    STATUS       current
    DESCRIPTION
        "Cisco Firepower firmware:UpgradeInfo:version managed
        object property"
    ::= { cfprFirmwareUpgradeInfoEntry 7 }

cfprFirmwareValidationStatusTable OBJECT-TYPE
    SYNTAX           SEQUENCE OF CfprFirmwareValidationStatusEntry
    MAX-ACCESS       not-accessible
    STATUS           current
    DESCRIPTION
        "Cisco Firepower firmware:ValidationStatus managed object table"
    ::= { cfprFirmwareObjects 69 }

cfprFirmwareValidationStatusEntry OBJECT-TYPE
    SYNTAX           CfprFirmwareValidationStatusEntry
    MAX-ACCESS       not-accessible
    STATUS           current
    DESCRIPTION
        "Entry for the cfprFirmwareValidationStatusTable table."
    INDEX { cfprFirmwareValidationStatusInstanceId }
    ::= { cfprFirmwareValidationStatusTable 1 }

CfprFirmwareValidationStatusEntry ::= SEQUENCE {
    cfprFirmwareValidationStatusInstanceId                           CfprManagedObjectId,
    cfprFirmwareValidationStatusDn                                   CfprManagedObjectDn,
    cfprFirmwareValidationStatusRn                                   SnmpAdminString,
    cfprFirmwareValidationStatusAdapterImageStatusCode               CfprFirmwareImageValidationType,
    cfprFirmwareValidationStatusBiosImageStatusCode                  CfprFirmwareImageValidationType,
    cfprFirmwareValidationStatusBmcImageStatusCode                   CfprFirmwareImageValidationType,
    cfprFirmwareValidationStatusBrdctrlImageStatusCode               CfprFirmwareImageValidationType,
    cfprFirmwareValidationStatusFsmDescr                             SnmpAdminString,
    cfprFirmwareValidationStatusFsmFlags                             SnmpAdminString,
    cfprFirmwareValidationStatusFsmPrev                              SnmpAdminString,
    cfprFirmwareValidationStatusFsmProgr                             Gauge32,
    cfprFirmwareValidationStatusFsmRmtInvErrCode                     Gauge32,
    cfprFirmwareValidationStatusFsmRmtInvErrDescr                    SnmpAdminString,
    cfprFirmwareValidationStatusFsmRmtInvRslt                        CfprConditionRemoteInvRslt,
    cfprFirmwareValidationStatusFsmStageDescr                        SnmpAdminString,
    cfprFirmwareValidationStatusFsmStamp                             DateAndTime,
    cfprFirmwareValidationStatusFsmStatus                            SnmpAdminString,
    cfprFirmwareValidationStatusFsmTry                               Gauge32,
    cfprFirmwareValidationStatusKickstartImageStatusCode             CfprFirmwareImageValidationType,
    cfprFirmwareValidationStatusMgtExtImageStatusCode                CfprFirmwareImageValidationType,
    cfprFirmwareValidationStatusOverallStatusCode                    CfprFirmwareImageValidationType,
    cfprFirmwareValidationStatusOverallStatusString                  SnmpAdminString,
    cfprFirmwareValidationStatusPackName                             SnmpAdminString,
    cfprFirmwareValidationStatusPackVersion                          SnmpAdminString,
    cfprFirmwareValidationStatusSsposImageStatusCode                 CfprFirmwareImageValidationType,
    cfprFirmwareValidationStatusState                                CfprFirmwareImageValidationStateType,
    cfprFirmwareValidationStatusStorageImageStatusCode               CfprFirmwareImageValidationType,
    cfprFirmwareValidationStatusSvcMgrImageStatusCode                CfprFirmwareImageValidationType,
    cfprFirmwareValidationStatusSystemImageStatusCode                CfprFirmwareImageValidationType,
    cfprFirmwareValidationStatusTimeStamp                            DateAndTime
}

cfprFirmwareValidationStatusInstanceId OBJECT-TYPE
    SYNTAX       CfprManagedObjectId
    MAX-ACCESS   not-accessible
    STATUS       current
    DESCRIPTION
        "Instance identifier of the managed object."
    ::= { cfprFirmwareValidationStatusEntry 1 }

cfprFirmwareValidationStatusDn OBJECT-TYPE
    SYNTAX       CfprManagedObjectDn
    MAX-ACCESS   read-only
    STATUS       current
    DESCRIPTION
        "Cisco Firepower firmware:ValidationStatus:dn managed
        object property"
    ::= { cfprFirmwareValidationStatusEntry 2 }

cfprFirmwareValidationStatusRn OBJECT-TYPE
    SYNTAX       SnmpAdminString
    MAX-ACCESS   read-only
    STATUS       current
    DESCRIPTION
        "Cisco Firepower firmware:ValidationStatus:rn managed
        object property"
    ::= { cfprFirmwareValidationStatusEntry 3 }

cfprFirmwareValidationStatusAdapterImageStatusCode OBJECT-TYPE
    SYNTAX       CfprFirmwareImageValidationType
    MAX-ACCESS   read-only
    STATUS       current
    DESCRIPTION
        "Cisco Firepower firmware:ValidationStatus:adapterImageStatusCode
        managed object property"
    ::= { cfprFirmwareValidationStatusEntry 4 }

cfprFirmwareValidationStatusBiosImageStatusCode OBJECT-TYPE
    SYNTAX       CfprFirmwareImageValidationType
    MAX-ACCESS   read-only
    STATUS       current
    DESCRIPTION
        "Cisco Firepower firmware:ValidationStatus:biosImageStatusCode
        managed object property"
    ::= { cfprFirmwareValidationStatusEntry 5 }

cfprFirmwareValidationStatusBmcImageStatusCode OBJECT-TYPE
    SYNTAX       CfprFirmwareImageValidationType
    MAX-ACCESS   read-only
    STATUS       current
    DESCRIPTION
        "Cisco Firepower firmware:ValidationStatus:bmcImageStatusCode
        managed object property"
    ::= { cfprFirmwareValidationStatusEntry 6 }

cfprFirmwareValidationStatusBrdctrlImageStatusCode OBJECT-TYPE
    SYNTAX       CfprFirmwareImageValidationType
    MAX-ACCESS   read-only
    STATUS       current
    DESCRIPTION
        "Cisco Firepower firmware:ValidationStatus:brdctrlImageStatusCode
        managed object property"
    ::= { cfprFirmwareValidationStatusEntry 7 }

cfprFirmwareValidationStatusFsmDescr OBJECT-TYPE
    SYNTAX       SnmpAdminString
    MAX-ACCESS   read-only
    STATUS       current
    DESCRIPTION
        "Cisco Firepower firmware:ValidationStatus:fsmDescr
        managed object property"
    ::= { cfprFirmwareValidationStatusEntry 8 }

cfprFirmwareValidationStatusFsmFlags OBJECT-TYPE
    SYNTAX       SnmpAdminString
    MAX-ACCESS   read-only
    STATUS       current
    DESCRIPTION
        "Cisco Firepower firmware:ValidationStatus:fsmFlags
        managed object property"
    ::= { cfprFirmwareValidationStatusEntry 9 }

cfprFirmwareValidationStatusFsmPrev OBJECT-TYPE
    SYNTAX       SnmpAdminString
    MAX-ACCESS   read-only
    STATUS       current
    DESCRIPTION
        "Cisco Firepower firmware:ValidationStatus:fsmPrev
        managed object property"
    ::= { cfprFirmwareValidationStatusEntry 10 }

cfprFirmwareValidationStatusFsmProgr OBJECT-TYPE
    SYNTAX       Gauge32
    MAX-ACCESS   read-only
    STATUS       current
    DESCRIPTION
        "Cisco Firepower firmware:ValidationStatus:fsmProgr
        managed object property"
    ::= { cfprFirmwareValidationStatusEntry 11 }

cfprFirmwareValidationStatusFsmRmtInvErrCode OBJECT-TYPE
    SYNTAX       Gauge32
    MAX-ACCESS   read-only
    STATUS       current
    DESCRIPTION
        "Cisco Firepower firmware:ValidationStatus:fsmRmtInvErrCode
        managed object property"
    ::= { cfprFirmwareValidationStatusEntry 12 }

cfprFirmwareValidationStatusFsmRmtInvErrDescr OBJECT-TYPE
    SYNTAX       SnmpAdminString
    MAX-ACCESS   read-only
    STATUS       current
    DESCRIPTION
        "Cisco Firepower firmware:ValidationStatus:fsmRmtInvErrDescr
        managed object property"
    ::= { cfprFirmwareValidationStatusEntry 13 }

cfprFirmwareValidationStatusFsmRmtInvRslt OBJECT-TYPE
    SYNTAX       CfprConditionRemoteInvRslt
    MAX-ACCESS   read-only
    STATUS       current
    DESCRIPTION
        "Cisco Firepower firmware:ValidationStatus:fsmRmtInvRslt
        managed object property"
    ::= { cfprFirmwareValidationStatusEntry 14 }

cfprFirmwareValidationStatusFsmStageDescr OBJECT-TYPE
    SYNTAX       SnmpAdminString
    MAX-ACCESS   read-only
    STATUS       current
    DESCRIPTION
        "Cisco Firepower firmware:ValidationStatus:fsmStageDescr
        managed object property"
    ::= { cfprFirmwareValidationStatusEntry 15 }

cfprFirmwareValidationStatusFsmStamp OBJECT-TYPE
    SYNTAX       DateAndTime
    MAX-ACCESS   read-only
    STATUS       current
    DESCRIPTION
        "Cisco Firepower firmware:ValidationStatus:fsmStamp
        managed object property"
    ::= { cfprFirmwareValidationStatusEntry 16 }

cfprFirmwareValidationStatusFsmStatus OBJECT-TYPE
    SYNTAX       SnmpAdminString
    MAX-ACCESS   read-only
    STATUS       current
    DESCRIPTION
        "Cisco Firepower firmware:ValidationStatus:fsmStatus
        managed object property"
    ::= { cfprFirmwareValidationStatusEntry 17 }

cfprFirmwareValidationStatusFsmTry OBJECT-TYPE
    SYNTAX       Gauge32
    MAX-ACCESS   read-only
    STATUS       current
    DESCRIPTION
        "Cisco Firepower firmware:ValidationStatus:fsmTry
        managed object property"
    ::= { cfprFirmwareValidationStatusEntry 18 }

cfprFirmwareValidationStatusKickstartImageStatusCode OBJECT-TYPE
    SYNTAX       CfprFirmwareImageValidationType
    MAX-ACCESS   read-only
    STATUS       current
    DESCRIPTION
        "Cisco Firepower firmware:ValidationStatus:kickstartImageStatusCod
        e managed object property"
    ::= { cfprFirmwareValidationStatusEntry 19 }

cfprFirmwareValidationStatusMgtExtImageStatusCode OBJECT-TYPE
    SYNTAX       CfprFirmwareImageValidationType
    MAX-ACCESS   read-only
    STATUS       current
    DESCRIPTION
        "Cisco Firepower firmware:ValidationStatus:mgtExtImageStatusCode
        managed object property"
    ::= { cfprFirmwareValidationStatusEntry 20 }

cfprFirmwareValidationStatusOverallStatusCode OBJECT-TYPE
    SYNTAX       CfprFirmwareImageValidationType
    MAX-ACCESS   read-only
    STATUS       current
    DESCRIPTION
        "Cisco Firepower firmware:ValidationStatus:overallStatusCode
        managed object property"
    ::= { cfprFirmwareValidationStatusEntry 21 }

cfprFirmwareValidationStatusOverallStatusString OBJECT-TYPE
    SYNTAX       SnmpAdminString
    MAX-ACCESS   read-only
    STATUS       current
    DESCRIPTION
        "Cisco Firepower firmware:ValidationStatus:overallStatusString
        managed object property"
    ::= { cfprFirmwareValidationStatusEntry 22 }

cfprFirmwareValidationStatusPackName OBJECT-TYPE
    SYNTAX       SnmpAdminString
    MAX-ACCESS   read-only
    STATUS       current
    DESCRIPTION
        "Cisco Firepower firmware:ValidationStatus:packName
        managed object property"
    ::= { cfprFirmwareValidationStatusEntry 23 }

cfprFirmwareValidationStatusPackVersion OBJECT-TYPE
    SYNTAX       SnmpAdminString
    MAX-ACCESS   read-only
    STATUS       current
    DESCRIPTION
        "Cisco Firepower firmware:ValidationStatus:packVersion
        managed object property"
    ::= { cfprFirmwareValidationStatusEntry 24 }

cfprFirmwareValidationStatusSsposImageStatusCode OBJECT-TYPE
    SYNTAX       CfprFirmwareImageValidationType
    MAX-ACCESS   read-only
    STATUS       current
    DESCRIPTION
        "Cisco Firepower firmware:ValidationStatus:ssposImageStatusCode
        managed object property"
    ::= { cfprFirmwareValidationStatusEntry 25 }

cfprFirmwareValidationStatusState OBJECT-TYPE
    SYNTAX       CfprFirmwareImageValidationStateType
    MAX-ACCESS   read-only
    STATUS       current
    DESCRIPTION
        "Cisco Firepower firmware:ValidationStatus:state
        managed object property"
    ::= { cfprFirmwareValidationStatusEntry 26 }

cfprFirmwareValidationStatusStorageImageStatusCode OBJECT-TYPE
    SYNTAX       CfprFirmwareImageValidationType
    MAX-ACCESS   read-only
    STATUS       current
    DESCRIPTION
        "Cisco Firepower firmware:ValidationStatus:storageImageStatusCode
        managed object property"
    ::= { cfprFirmwareValidationStatusEntry 27 }

cfprFirmwareValidationStatusSvcMgrImageStatusCode OBJECT-TYPE
    SYNTAX       CfprFirmwareImageValidationType
    MAX-ACCESS   read-only
    STATUS       current
    DESCRIPTION
        "Cisco Firepower firmware:ValidationStatus:svcMgrImageStatusCode
        managed object property"
    ::= { cfprFirmwareValidationStatusEntry 28 }

cfprFirmwareValidationStatusSystemImageStatusCode OBJECT-TYPE
    SYNTAX       CfprFirmwareImageValidationType
    MAX-ACCESS   read-only
    STATUS       current
    DESCRIPTION
        "Cisco Firepower firmware:ValidationStatus:systemImageStatusCode
        managed object property"
    ::= { cfprFirmwareValidationStatusEntry 29 }

cfprFirmwareValidationStatusTimeStamp OBJECT-TYPE
    SYNTAX       DateAndTime
    MAX-ACCESS   read-only
    STATUS       current
    DESCRIPTION
        "Cisco Firepower firmware:ValidationStatus:timeStamp
        managed object property"
    ::= { cfprFirmwareValidationStatusEntry 30 }

cfprFirmwareValidationStatusFsmTable OBJECT-TYPE
    SYNTAX           SEQUENCE OF CfprFirmwareValidationStatusFsmEntry
    MAX-ACCESS       not-accessible
    STATUS           current
    DESCRIPTION
        "Cisco Firepower firmware:ValidationStatusFsm managed
        object table"
    ::= { cfprFirmwareObjects 70 }

cfprFirmwareValidationStatusFsmEntry OBJECT-TYPE
    SYNTAX           CfprFirmwareValidationStatusFsmEntry
    MAX-ACCESS       not-accessible
    STATUS           current
    DESCRIPTION
        "Entry for the cfprFirmwareValidationStatusFsmTable table."
    INDEX { cfprFirmwareValidationStatusFsmInstanceId }
    ::= { cfprFirmwareValidationStatusFsmTable 1 }

CfprFirmwareValidationStatusFsmEntry ::= SEQUENCE {
    cfprFirmwareValidationStatusFsmInstanceId                        CfprManagedObjectId,
    cfprFirmwareValidationStatusFsmDn                                CfprManagedObjectDn,
    cfprFirmwareValidationStatusFsmRn                                SnmpAdminString,
    cfprFirmwareValidationStatusFsmCompletionTime                    DateAndTime,
    cfprFirmwareValidationStatusFsmCurrentFsm                        CfprFirmwareValidationStatusFsmCurrentFsm,
    cfprFirmwareValidationStatusFsmDescrData                         SnmpAdminString,
    cfprFirmwareValidationStatusFsmFsmStatus                         CfprFsmFsmStageStatus,
    cfprFirmwareValidationStatusFsmProgress                          Gauge32,
    cfprFirmwareValidationStatusFsmRmtErrCode                        Gauge32,
    cfprFirmwareValidationStatusFsmRmtErrDescr                       SnmpAdminString,
    cfprFirmwareValidationStatusFsmRmtRslt                           CfprConditionRemoteInvRslt
}

cfprFirmwareValidationStatusFsmInstanceId OBJECT-TYPE
    SYNTAX       CfprManagedObjectId
    MAX-ACCESS   not-accessible
    STATUS       current
    DESCRIPTION
        "Instance identifier of the managed object."
    ::= { cfprFirmwareValidationStatusFsmEntry 1 }

cfprFirmwareValidationStatusFsmDn OBJECT-TYPE
    SYNTAX       CfprManagedObjectDn
    MAX-ACCESS   read-only
    STATUS       current
    DESCRIPTION
        "Cisco Firepower firmware:ValidationStatusFsm:dn
        managed object property"
    ::= { cfprFirmwareValidationStatusFsmEntry 2 }

cfprFirmwareValidationStatusFsmRn OBJECT-TYPE
    SYNTAX       SnmpAdminString
    MAX-ACCESS   read-only
    STATUS       current
    DESCRIPTION
        "Cisco Firepower firmware:ValidationStatusFsm:rn
        managed object property"
    ::= { cfprFirmwareValidationStatusFsmEntry 3 }

cfprFirmwareValidationStatusFsmCompletionTime OBJECT-TYPE
    SYNTAX       DateAndTime
    MAX-ACCESS   read-only
    STATUS       current
    DESCRIPTION
        "Cisco Firepower firmware:ValidationStatusFsm:completionTime
        managed object property"
    ::= { cfprFirmwareValidationStatusFsmEntry 4 }

cfprFirmwareValidationStatusFsmCurrentFsm OBJECT-TYPE
    SYNTAX       CfprFirmwareValidationStatusFsmCurrentFsm
    MAX-ACCESS   read-only
    STATUS       current
    DESCRIPTION
        "Cisco Firepower firmware:ValidationStatusFsm:currentFsm
        managed object property"
    ::= { cfprFirmwareValidationStatusFsmEntry 5 }

cfprFirmwareValidationStatusFsmDescrData OBJECT-TYPE
    SYNTAX       SnmpAdminString
    MAX-ACCESS   read-only
    STATUS       current
    DESCRIPTION
        "Cisco Firepower firmware:ValidationStatusFsm:descr
        managed object property"
    ::= { cfprFirmwareValidationStatusFsmEntry 6 }

cfprFirmwareValidationStatusFsmFsmStatus OBJECT-TYPE
    SYNTAX       CfprFsmFsmStageStatus
    MAX-ACCESS   read-only
    STATUS       current
    DESCRIPTION
        "Cisco Firepower firmware:ValidationStatusFsm:fsmStatus
        managed object property"
    ::= { cfprFirmwareValidationStatusFsmEntry 7 }

cfprFirmwareValidationStatusFsmProgress OBJECT-TYPE
    SYNTAX       Gauge32
    MAX-ACCESS   read-only
    STATUS       current
    DESCRIPTION
        "Cisco Firepower firmware:ValidationStatusFsm:progress
        managed object property"
    ::= { cfprFirmwareValidationStatusFsmEntry 8 }

cfprFirmwareValidationStatusFsmRmtErrCode OBJECT-TYPE
    SYNTAX       Gauge32
    MAX-ACCESS   read-only
    STATUS       current
    DESCRIPTION
        "Cisco Firepower firmware:ValidationStatusFsm:rmtErrCode
        managed object property"
    ::= { cfprFirmwareValidationStatusFsmEntry 9 }

cfprFirmwareValidationStatusFsmRmtErrDescr OBJECT-TYPE
    SYNTAX       SnmpAdminString
    MAX-ACCESS   read-only
    STATUS       current
    DESCRIPTION
        "Cisco Firepower firmware:ValidationStatusFsm:rmtErrDescr
        managed object property"
    ::= { cfprFirmwareValidationStatusFsmEntry 10 }

cfprFirmwareValidationStatusFsmRmtRslt OBJECT-TYPE
    SYNTAX       CfprConditionRemoteInvRslt
    MAX-ACCESS   read-only
    STATUS       current
    DESCRIPTION
        "Cisco Firepower firmware:ValidationStatusFsm:rmtRslt
        managed object property"
    ::= { cfprFirmwareValidationStatusFsmEntry 11 }

cfprFirmwareValidationStatusFsmStageTable OBJECT-TYPE
    SYNTAX           SEQUENCE OF CfprFirmwareValidationStatusFsmStageEntry
    MAX-ACCESS       not-accessible
    STATUS           current
    DESCRIPTION
        "Cisco Firepower firmware:ValidationStatusFsmStage
        managed object table"
    ::= { cfprFirmwareObjects 71 }

cfprFirmwareValidationStatusFsmStageEntry OBJECT-TYPE
    SYNTAX           CfprFirmwareValidationStatusFsmStageEntry
    MAX-ACCESS       not-accessible
    STATUS           current
    DESCRIPTION
        "Entry for the cfprFirmwareValidationStatusFsmStageTable table."
    INDEX { cfprFirmwareValidationStatusFsmStageInstanceId }
    ::= { cfprFirmwareValidationStatusFsmStageTable 1 }

CfprFirmwareValidationStatusFsmStageEntry ::= SEQUENCE {
    cfprFirmwareValidationStatusFsmStageInstanceId                   CfprManagedObjectId,
    cfprFirmwareValidationStatusFsmStageDn                           CfprManagedObjectDn,
    cfprFirmwareValidationStatusFsmStageRn                           SnmpAdminString,
    cfprFirmwareValidationStatusFsmStageDescrData                    SnmpAdminString,
    cfprFirmwareValidationStatusFsmStageLastUpdateTime               DateAndTime,
    cfprFirmwareValidationStatusFsmStageName                         CfprFirmwareValidationStatusFsmStageName,
    cfprFirmwareValidationStatusFsmStageOrder                        Gauge32,
    cfprFirmwareValidationStatusFsmStageRetry                        Gauge32,
    cfprFirmwareValidationStatusFsmStageStageStatus                  CfprFsmFsmStageStatus
}

cfprFirmwareValidationStatusFsmStageInstanceId OBJECT-TYPE
    SYNTAX       CfprManagedObjectId
    MAX-ACCESS   not-accessible
    STATUS       current
    DESCRIPTION
        "Instance identifier of the managed object."
    ::= { cfprFirmwareValidationStatusFsmStageEntry 1 }

cfprFirmwareValidationStatusFsmStageDn OBJECT-TYPE
    SYNTAX       CfprManagedObjectDn
    MAX-ACCESS   read-only
    STATUS       current
    DESCRIPTION
        "Cisco Firepower firmware:ValidationStatusFsmStage:dn
        managed object property"
    ::= { cfprFirmwareValidationStatusFsmStageEntry 2 }

cfprFirmwareValidationStatusFsmStageRn OBJECT-TYPE
    SYNTAX       SnmpAdminString
    MAX-ACCESS   read-only
    STATUS       current
    DESCRIPTION
        "Cisco Firepower firmware:ValidationStatusFsmStage:rn
        managed object property"
    ::= { cfprFirmwareValidationStatusFsmStageEntry 3 }

cfprFirmwareValidationStatusFsmStageDescrData OBJECT-TYPE
    SYNTAX       SnmpAdminString
    MAX-ACCESS   read-only
    STATUS       current
    DESCRIPTION
        "Cisco Firepower firmware:ValidationStatusFsmStage:descr
        managed object property"
    ::= { cfprFirmwareValidationStatusFsmStageEntry 4 }

cfprFirmwareValidationStatusFsmStageLastUpdateTime OBJECT-TYPE
    SYNTAX       DateAndTime
    MAX-ACCESS   read-only
    STATUS       current
    DESCRIPTION
        "Cisco Firepower firmware:ValidationStatusFsmStage:lastUpdateTime
        managed object property"
    ::= { cfprFirmwareValidationStatusFsmStageEntry 5 }

cfprFirmwareValidationStatusFsmStageName OBJECT-TYPE
    SYNTAX       CfprFirmwareValidationStatusFsmStageName
    MAX-ACCESS   read-only
    STATUS       current
    DESCRIPTION
        "Cisco Firepower firmware:ValidationStatusFsmStage:name
        managed object property"
    ::= { cfprFirmwareValidationStatusFsmStageEntry 6 }

cfprFirmwareValidationStatusFsmStageOrder OBJECT-TYPE
    SYNTAX       Gauge32
    MAX-ACCESS   read-only
    STATUS       current
    DESCRIPTION
        "Cisco Firepower firmware:ValidationStatusFsmStage:order
        managed object property"
    ::= { cfprFirmwareValidationStatusFsmStageEntry 7 }

cfprFirmwareValidationStatusFsmStageRetry OBJECT-TYPE
    SYNTAX       Gauge32
    MAX-ACCESS   read-only
    STATUS       current
    DESCRIPTION
        "Cisco Firepower firmware:ValidationStatusFsmStage:retry
        managed object property"
    ::= { cfprFirmwareValidationStatusFsmStageEntry 8 }

cfprFirmwareValidationStatusFsmStageStageStatus OBJECT-TYPE
    SYNTAX       CfprFsmFsmStageStatus
    MAX-ACCESS   read-only
    STATUS       current
    DESCRIPTION
        "Cisco Firepower firmware:ValidationStatusFsmStage:stageStatus
        managed object property"
    ::= { cfprFirmwareValidationStatusFsmStageEntry 9 }

cfprFirmwareValidationStatusFsmTaskTable OBJECT-TYPE
    SYNTAX           SEQUENCE OF CfprFirmwareValidationStatusFsmTaskEntry
    MAX-ACCESS       not-accessible
    STATUS           current
    DESCRIPTION
        "Cisco Firepower firmware:ValidationStatusFsmTask
        managed object table"
    ::= { cfprFirmwareObjects 72 }

cfprFirmwareValidationStatusFsmTaskEntry OBJECT-TYPE
    SYNTAX           CfprFirmwareValidationStatusFsmTaskEntry
    MAX-ACCESS       not-accessible
    STATUS           current
    DESCRIPTION
        "Entry for the cfprFirmwareValidationStatusFsmTaskTable table."
    INDEX { cfprFirmwareValidationStatusFsmTaskInstanceId }
    ::= { cfprFirmwareValidationStatusFsmTaskTable 1 }

CfprFirmwareValidationStatusFsmTaskEntry ::= SEQUENCE {
    cfprFirmwareValidationStatusFsmTaskInstanceId                    CfprManagedObjectId,
    cfprFirmwareValidationStatusFsmTaskDn                            CfprManagedObjectDn,
    cfprFirmwareValidationStatusFsmTaskRn                            SnmpAdminString,
    cfprFirmwareValidationStatusFsmTaskCompletion                    CfprFsmCompletion,
    cfprFirmwareValidationStatusFsmTaskFlags                         CfprFirmwareValidationStatusFsmTaskFlags,
    cfprFirmwareValidationStatusFsmTaskItem                          CfprFirmwareValidationStatusFsmTaskItem,
    cfprFirmwareValidationStatusFsmTaskSeqId                         Gauge32
}

cfprFirmwareValidationStatusFsmTaskInstanceId OBJECT-TYPE
    SYNTAX       CfprManagedObjectId
    MAX-ACCESS   not-accessible
    STATUS       current
    DESCRIPTION
        "Instance identifier of the managed object."
    ::= { cfprFirmwareValidationStatusFsmTaskEntry 1 }

cfprFirmwareValidationStatusFsmTaskDn OBJECT-TYPE
    SYNTAX       CfprManagedObjectDn
    MAX-ACCESS   read-only
    STATUS       current
    DESCRIPTION
        "Cisco Firepower firmware:ValidationStatusFsmTask:dn
        managed object property"
    ::= { cfprFirmwareValidationStatusFsmTaskEntry 2 }

cfprFirmwareValidationStatusFsmTaskRn OBJECT-TYPE
    SYNTAX       SnmpAdminString
    MAX-ACCESS   read-only
    STATUS       current
    DESCRIPTION
        "Cisco Firepower firmware:ValidationStatusFsmTask:rn
        managed object property"
    ::= { cfprFirmwareValidationStatusFsmTaskEntry 3 }

cfprFirmwareValidationStatusFsmTaskCompletion OBJECT-TYPE
    SYNTAX       CfprFsmCompletion
    MAX-ACCESS   read-only
    STATUS       current
    DESCRIPTION
        "Cisco Firepower firmware:ValidationStatusFsmTask:completion
        managed object property"
    ::= { cfprFirmwareValidationStatusFsmTaskEntry 4 }

cfprFirmwareValidationStatusFsmTaskFlags OBJECT-TYPE
    SYNTAX       CfprFirmwareValidationStatusFsmTaskFlags
    MAX-ACCESS   read-only
    STATUS       current
    DESCRIPTION
        "Cisco Firepower firmware:ValidationStatusFsmTask:flags
        managed object property"
    ::= { cfprFirmwareValidationStatusFsmTaskEntry 5 }

cfprFirmwareValidationStatusFsmTaskItem OBJECT-TYPE
    SYNTAX       CfprFirmwareValidationStatusFsmTaskItem
    MAX-ACCESS   read-only
    STATUS       current
    DESCRIPTION
        "Cisco Firepower firmware:ValidationStatusFsmTask:item
        managed object property"
    ::= { cfprFirmwareValidationStatusFsmTaskEntry 6 }

cfprFirmwareValidationStatusFsmTaskSeqId OBJECT-TYPE
    SYNTAX       Gauge32
    MAX-ACCESS   read-only
    STATUS       current
    DESCRIPTION
        "Cisco Firepower firmware:ValidationStatusFsmTask:seqId
        managed object property"
    ::= { cfprFirmwareValidationStatusFsmTaskEntry 7 }

cfprFirmwareVersionIssueTable OBJECT-TYPE
    SYNTAX           SEQUENCE OF CfprFirmwareVersionIssueEntry
    MAX-ACCESS       not-accessible
    STATUS           current
    DESCRIPTION
        "Cisco Firepower firmware:VersionIssue managed object table"
    ::= { cfprFirmwareObjects 73 }

cfprFirmwareVersionIssueEntry OBJECT-TYPE
    SYNTAX           CfprFirmwareVersionIssueEntry
    MAX-ACCESS       not-accessible
    STATUS           current
    DESCRIPTION
        "Entry for the cfprFirmwareVersionIssueTable table."
    INDEX { cfprFirmwareVersionIssueInstanceId }
    ::= { cfprFirmwareVersionIssueTable 1 }

CfprFirmwareVersionIssueEntry ::= SEQUENCE {
    cfprFirmwareVersionIssueInstanceId                               CfprManagedObjectId,
    cfprFirmwareVersionIssueDn                                       CfprManagedObjectDn,
    cfprFirmwareVersionIssueRn                                       SnmpAdminString,
    cfprFirmwareVersionIssueInstalledImageVersion                    SnmpAdminString,
    cfprFirmwareVersionIssueInstalledPackageVersion                  SnmpAdminString,
    cfprFirmwareVersionIssueMismatchType                             SnmpAdminString
}

cfprFirmwareVersionIssueInstanceId OBJECT-TYPE
    SYNTAX       CfprManagedObjectId
    MAX-ACCESS   not-accessible
    STATUS       current
    DESCRIPTION
        "Instance identifier of the managed object."
    ::= { cfprFirmwareVersionIssueEntry 1 }

cfprFirmwareVersionIssueDn OBJECT-TYPE
    SYNTAX       CfprManagedObjectDn
    MAX-ACCESS   read-only
    STATUS       current
    DESCRIPTION
        "Cisco Firepower firmware:VersionIssue:dn managed object property"
    ::= { cfprFirmwareVersionIssueEntry 2 }

cfprFirmwareVersionIssueRn OBJECT-TYPE
    SYNTAX       SnmpAdminString
    MAX-ACCESS   read-only
    STATUS       current
    DESCRIPTION
        "Cisco Firepower firmware:VersionIssue:rn managed object property"
    ::= { cfprFirmwareVersionIssueEntry 3 }

cfprFirmwareVersionIssueInstalledImageVersion OBJECT-TYPE
    SYNTAX       SnmpAdminString
    MAX-ACCESS   read-only
    STATUS       current
    DESCRIPTION
        "Cisco Firepower firmware:VersionIssue:installedImageVersion
        managed object property"
    ::= { cfprFirmwareVersionIssueEntry 4 }

cfprFirmwareVersionIssueInstalledPackageVersion OBJECT-TYPE
    SYNTAX       SnmpAdminString
    MAX-ACCESS   read-only
    STATUS       current
    DESCRIPTION
        "Cisco Firepower firmware:VersionIssue:installedPackageVersion
        managed object property"
    ::= { cfprFirmwareVersionIssueEntry 5 }

cfprFirmwareVersionIssueMismatchType OBJECT-TYPE
    SYNTAX       SnmpAdminString
    MAX-ACCESS   read-only
    STATUS       current
    DESCRIPTION
        "Cisco Firepower firmware:VersionIssue:mismatchType
        managed object property"
    ::= { cfprFirmwareVersionIssueEntry 6 }

END

-- *********************************************************************
-- CISCO-FIREPOWER-MGMT-MIB.my
-- 
-- MIB representation of the Cisco Firepower
-- MGMT management information model package
-- 
-- Created March 2020 by Charles Bullis
-- 
-- Copyright (c) 2005-2020 Cisco Systems, Inc. All rights reserved.
-- 
-- *********************************************************************

CISCO-FIREPOWER-MGMT-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerMIBObjects,
    CfprManagedObjectId,
    CfprManagedObjectDn
        FROM CISCO-FIREPOWER-MIB
    CfprCommClientAdminState,
    CfprConditionRemoteInvRslt,
    CfprEtherSatelliteConnectionDisc,
    CfprFsmCompletion,
    CfprFsmFlags,
    CfprFsmFsmStageStatus,
    CfprIpProtocol,
    CfprMgmtAccess,
    CfprMgmtAdminState,
    CfprMgmtBackupFsmCurrentFsm,
    CfprMgmtBackupFsmStageName,
    CfprMgmtBackupFsmTaskItem,
    CfprMgmtBackupInterval,
    CfprMgmtBackupIssue,
    CfprMgmtBackupJob,
    CfprMgmtBackupPolicyFsmCurrentFsm,
    CfprMgmtBackupPolicyFsmStageName,
    CfprMgmtBackupPostAction,
    CfprMgmtBackupProto,
    CfprMgmtBackupStatus,
    CfprMgmtBackupType,
    CfprMgmtCfgExportPolicyFsmCurrentFsm,
    CfprMgmtCfgExportPolicyFsmStageName,
    CfprMgmtCimcSecureBootAdminState,
    CfprMgmtConfigState,
    CfprMgmtConnectionState,
    CfprMgmtControllerFsmCurrentFsm,
    CfprMgmtControllerFsmStageName,
    CfprMgmtControllerFsmTaskFlags,
    CfprMgmtControllerFsmTaskItem,
    CfprMgmtDimmBlacklistingOperState,
    CfprMgmtEntityChassisDeviceIoState1,
    CfprMgmtEntityChassisDeviceIoState2,
    CfprMgmtEntityChassisDeviceIoState3,
    CfprMgmtEntityHaFailureReason,
    CfprMgmtEntityHaReadiness,
    CfprMgmtEntityLeadership,
    CfprMgmtEntityMgmtServicesState,
    CfprMgmtEntityProblems,
    CfprMgmtEntityState,
    CfprMgmtEntityUmbilicalState,
    CfprMgmtExportPolicyAdminState,
    CfprMgmtExportPolicyFsmCurrentFsm,
    CfprMgmtExportPolicyFsmStageName,
    CfprMgmtExportPolicyFsmTaskItem,
    CfprMgmtExportPolicyProto,
    CfprMgmtIPv6IfAddrFsmCurrentFsm,
    CfprMgmtIPv6IfAddrFsmStageName,
    CfprMgmtIPv6IfAddrFsmTaskItem,
    CfprMgmtIfFsmCurrentFsm,
    CfprMgmtIfFsmStageName,
    CfprMgmtIfFsmTaskItem,
    CfprMgmtImportAction,
    CfprMgmtImportStatus,
    CfprMgmtImporterFsmCurrentFsm,
    CfprMgmtImporterFsmStageName,
    CfprMgmtImporterFsmTaskItem,
    CfprMgmtImporterPostAction,
    CfprMgmtImporterProto,
    CfprMgmtIntAuthPolicyMethod,
    CfprMgmtMode,
    CfprMgmtOperState,
    CfprMgmtPmonEntryState,
    CfprMgmtSecureBootOperState,
    CfprMgmtSource,
    CfprMgmtStateQual,
    CfprMgmtStorageSubsystemState,
    CfprMgmtSubject,
    CfprNetworkConnectionType,
    CfprNetworkLocale,
    CfprNetworkPhysEpIfType,
    CfprNetworkPortRole,
    CfprNetworkSwitchId,
    CfprNetworkTransport,
    CfprPolicyPolicyOwner,
    CfprTrigAdminState,
    CfprTrigTrigOperState,
    CfprVnicExternalMgmtIPMode
        FROM CISCO-FIREPOWER-TC-MIB;

cfprMgmtObjects MODULE-IDENTITY
    LAST-UPDATED    "202003100000Z"
    ORGANIZATION    "Cisco Systems Inc."
    CONTACT-INFO
        "Cisco Systems
        Customer Service
        
        Postal: 170 W Tasman Drive
        San Jose, CA  95134
        USA
        
        Tel: +1 800 553-NETS
        
        E-mail: firepower-mibs@cisco.com"
    DESCRIPTION
        "MIB representation of the Cisco Firepower
        MGMT management information model package"
    ::= { ciscoFirepowerMIBObjects 51 }

cfprMgmtAccessPolicyTable OBJECT-TYPE
    SYNTAX           SEQUENCE OF CfprMgmtAccessPolicyEntry
    MAX-ACCESS       not-accessible
    STATUS           current
    DESCRIPTION
        "Cisco Firepower mgmt:AccessPolicy managed object table"
    ::= { cfprMgmtObjects 1 }

cfprMgmtAccessPolicyEntry OBJECT-TYPE
    SYNTAX           CfprMgmtAccessPolicyEntry
    MAX-ACCESS       not-accessible
    STATUS           current
    DESCRIPTION
        "Entry for the cfprMgmtAccessPolicyTable table."
    INDEX { cfprMgmtAccessPolicyInstanceId }
    ::= { cfprMgmtAccessPolicyTable 1 }

CfprMgmtAccessPolicyEntry ::= SEQUENCE {
    cfprMgmtAccessPolicyInstanceId                                   CfprManagedObjectId,
    cfprMgmtAccessPolicyDn                                           CfprManagedObjectDn,
    cfprMgmtAccessPolicyRn                                           SnmpAdminString
}

cfprMgmtAccessPolicyInstanceId OBJECT-TYPE
    SYNTAX       CfprManagedObjectId
    MAX-ACCESS   not-accessible
    STATUS       current
    DESCRIPTION
        "Instance identifier of the managed object."
    ::= { cfprMgmtAccessPolicyEntry 1 }

cfprMgmtAccessPolicyDn OBJECT-TYPE
    SYNTAX       CfprManagedObjectDn
    MAX-ACCESS   read-only
    STATUS       current
    DESCRIPTION
        "Cisco Firepower mgmt:AccessPolicy:dn managed object property"
    ::= { cfprMgmtAccessPolicyEntry 2 }

cfprMgmtAccessPolicyRn OBJECT-TYPE
    SYNTAX       SnmpAdminString
    MAX-ACCESS   read-only
    STATUS       current
    DESCRIPTION
        "Cisco Firepower mgmt:AccessPolicy:rn managed object property"
    ::= { cfprMgmtAccessPolicyEntry 3 }

cfprMgmtAccessPolicyItemTable OBJECT-TYPE
    SYNTAX           SEQUENCE OF CfprMgmtAccessPolicyItemEntry
    MAX-ACCESS       not-accessible
    STATUS           current
    DESCRIPTION
        "Cisco Firepower mgmt:AccessPolicyItem managed object table"
    ::= { cfprMgmtObjects 2 }

cfprMgmtAccessPolicyItemEntry OBJECT-TYPE
    SYNTAX           CfprMgmtAccessPolicyItemEntry
    MAX-ACCESS       not-accessible
    STATUS           current
    DESCRIPTION
        "Entry for the cfprMgmtAccessPolicyItemTable table."
    INDEX { cfprMgmtAccessPolicyItemInstanceId }
    ::= { cfprMgmtAccessPolicyItemTable 1 }

CfprMgmtAccessPolicyItemEntry ::= SEQUENCE {
    cfprMgmtAccessPolicyItemInstanceId                               CfprManagedObjectId,
    cfprMgmtAccessPolicyItemDn                                       CfprManagedObjectDn,
    cfprMgmtAccessPolicyItemRn                                       SnmpAdminString,
    cfprMgmtAccessPolicyItemDescr                                    SnmpAdminString,
    cfprMgmtAccessPolicyItemIntId                                    SnmpAdminString,
    cfprMgmtAccessPolicyItemIpPoolName                               SnmpAdminString,
    cfprMgmtAccessPolicyItemName                                     SnmpAdminString,
    cfprMgmtAccessPolicyItemPolicyLevel                              Gauge32,
    cfprMgmtAccessPolicyItemPolicyOwner                              CfprPolicyPolicyOwner,
    cfprMgmtAccessPolicyItemSubject                                  CfprMgmtSubject
}

cfprMgmtAccessPolicyItemInstanceId OBJECT-TYPE
    SYNTAX       CfprManagedObjectId
    MAX-ACCESS   not-accessible
    STATUS       current
    DESCRIPTION
        "Instance identifier of the managed object."
    ::= { cfprMgmtAccessPolicyItemEntry 1 }

cfprMgmtAccessPolicyItemDn OBJECT-TYPE
    SYNTAX       CfprManagedObjectDn
    MAX-ACCESS   read-only
    STATUS       current
    DESCRIPTION
        "Cisco Firepower mgmt:AccessPolicyItem:dn managed object property"
    ::= { cfprMgmtAccessPolicyItemEntry 2 }

cfprMgmtAccessPolicyItemRn OBJECT-TYPE
    SYNTAX       SnmpAdminString
    MAX-ACCESS   read-only
    STATUS       current
    DESCRIPTION
        "Cisco Firepower mgmt:AccessPolicyItem:rn managed object property"
    ::= { cfprMgmtAccessPolicyItemEntry 3 }

cfprMgmtAccessPolicyItemDescr OBJECT-TYPE
    SYNTAX       SnmpAdminString
    MAX-ACCESS   read-only
    STATUS       current
    DESCRIPTION
        "Cisco Firepower mgmt:AccessPolicyItem:descr managed
        object property"
    ::= { cfprMgmtAccessPolicyItemEntry 4 }

cfprMgmtAccessPolicyItemIntId OBJECT-TYPE
    SYNTAX       SnmpAdminString
    MAX-ACCESS   read-only
    STATUS       current
    DESCRIPTION
        "Cisco Firepower mgmt:AccessPolicyItem:intId managed
        object property"
    ::= { cfprMgmtAccessPolicyItemEntry 5 }

cfprMgmtAccessPolicyItemIpPoolName OBJECT-TYPE
    SYNTAX       SnmpAdminString
    MAX-ACCESS   read-only
    STATUS       current
    DESCRIPTION
        "Cisco Firepower mgmt:AccessPolicyItem:ipPoolName
        managed object property"
    ::= { cfprMgmtAccessPolicyItemEntry 6 }

cfprMgmtAccessPolicyItemName OBJECT-TYPE
    SYNTAX       SnmpAdminString
    MAX-ACCESS   read-only
    STATUS       current
    DESCRIPTION
        "Cisco Firepower mgmt:AccessPolicyItem:name managed
        object property"
    ::= { cfprMgmtAccessPolicyItemEntry 7 }

cfprMgmtAccessPolicyItemPolicyLevel OBJECT-TYPE
    SYNTAX       Gauge32
    MAX-ACCESS   read-only
    STATUS       current
    DESCRIPTION
        "Cisco Firepower mgmt:AccessPolicyItem:policyLevel
        managed object property"
    ::= { cfprMgmtAccessPolicyItemEntry 8 }

cfprMgmtAccessPolicyItemPolicyOwner OBJECT-TYPE
    SYNTAX       CfprPolicyPolicyOwner
    MAX-ACCESS   read-only
    STATUS       current
    DESCRIPTION
        "Cisco Firepower mgmt:AccessPolicyItem:policyOwner
        managed object property"
    ::= { cfprMgmtAccessPolicyItemEntry 9 }

cfprMgmtAccessPolicyItemSubject OBJECT-TYPE
    SYNTAX       CfprMgmtSubject
    MAX-ACCESS   read-only
    STATUS       current
    DESCRIPTION
        "Cisco Firepower mgmt:AccessPolicyItem:subject
        managed object property"
    ::= { cfprMgmtAccessPolicyItemEntry 10 }

cfprMgmtAccessPortTable OBJECT-TYPE
    SYNTAX           SEQUENCE OF CfprMgmtAccessPortEntry
    MAX-ACCESS       not-accessible
    STATUS           current
    DESCRIPTION
        "Cisco Firepower mgmt:AccessPort managed object table"
    ::= { cfprMgmtObjects 3 }

cfprMgmtAccessPortEntry OBJECT-TYPE
    SYNTAX           CfprMgmtAccessPortEntry
    MAX-ACCESS       not-accessible
    STATUS           current
    DESCRIPTION
        "Entry for the cfprMgmtAccessPortTable table."
    INDEX { cfprMgmtAccessPortInstanceId }
    ::= { cfprMgmtAccessPortTable 1 }

CfprMgmtAccessPortEntry ::= SEQUENCE {
    cfprMgmtAccessPortInstanceId                                     CfprManagedObjectId,
    cfprMgmtAccessPortDn                                             CfprManagedObjectDn,
    cfprMgmtAccessPortRn                                             SnmpAdminString,
    cfprMgmtAccessPortPort                                           Gauge32,
    cfprMgmtAccessPortProtocol                                       CfprIpProtocol
}

cfprMgmtAccessPortInstanceId OBJECT-TYPE
    SYNTAX       CfprManagedObjectId
    MAX-ACCESS   not-accessible
    STATUS       current
    DESCRIPTION
        "Instance identifier of the managed object."
    ::= { cfprMgmtAccessPortEntry 1 }

cfprMgmtAccessPortDn OBJECT-TYPE
    SYNTAX       CfprManagedObjectDn
    MAX-ACCESS   read-only
    STATUS       current
    DESCRIPTION
        "Cisco Firepower mgmt:AccessPort:dn managed object property"
    ::= { cfprMgmtAccessPortEntry 2 }

cfprMgmtAccessPortRn OBJECT-TYPE
    SYNTAX       SnmpAdminString
    MAX-ACCESS   read-only
    STATUS       current
    DESCRIPTION
        "Cisco Firepower mgmt:AccessPort:rn managed object property"
    ::= { cfprMgmtAccessPortEntry 3 }

cfprMgmtAccessPortPort OBJECT-TYPE
    SYNTAX       Gauge32
    MAX-ACCESS   read-only
    STATUS       current
    DESCRIPTION
        "Cisco Firepower mgmt:AccessPort:port managed object property"
    ::= { cfprMgmtAccessPortEntry 4 }

cfprMgmtAccessPortProtocol OBJECT-TYPE
    SYNTAX       CfprIpProtocol
    MAX-ACCESS   read-only
    STATUS       current
    DESCRIPTION
        "Cisco Firepower mgmt:AccessPort:protocol managed object property"
    ::= { cfprMgmtAccessPortEntry 5 }

cfprMgmtBackupTable OBJECT-TYPE
    SYNTAX           SEQUENCE OF CfprMgmtBackupEntry
    MAX-ACCESS       not-accessible
    STATUS           current
    DESCRIPTION
        "Cisco Firepower mgmt:Backup managed object table"
    ::= { cfprMgmtObjects 4 }

cfprMgmtBackupEntry OBJECT-TYPE
    SYNTAX           CfprMgmtBackupEntry
    MAX-ACCESS       not-accessible
    STATUS           current
    DESCRIPTION
        "Entry for the cfprMgmtBackupTable table."
    INDEX { cfprMgmtBackupInstanceId }
    ::= { cfprMgmtBackupTable 1 }

CfprMgmtBackupEntry ::= SEQUENCE {
    cfprMgmtBackupInstanceId                                         CfprManagedObjectId,
    cfprMgmtBackupDn                                                 CfprManagedObjectDn,
    cfprMgmtBackupRn                                                 SnmpAdminString,
    cfprMgmtBackupAdminState                                         CfprCommClientAdminState,
    cfprMgmtBackupDescr                                              SnmpAdminString,
    cfprMgmtBackupFsmDescr                                           SnmpAdminString,
    cfprMgmtBackupFsmPrev                                            SnmpAdminString,
    cfprMgmtBackupFsmProgr                                           Gauge32,
    cfprMgmtBackupFsmRmtInvErrCode                                   Gauge32,
    cfprMgmtBackupFsmRmtInvErrDescr                                  SnmpAdminString,
    cfprMgmtBackupFsmRmtInvRslt                                      CfprConditionRemoteInvRslt,
    cfprMgmtBackupFsmStageDescr                                      SnmpAdminString,
    cfprMgmtBackupFsmStamp                                           DateAndTime,
    cfprMgmtBackupFsmStatus                                          SnmpAdminString,
    cfprMgmtBackupFsmTry                                             Gauge32,
    cfprMgmtBackupHostname                                           SnmpAdminString,
    cfprMgmtBackupIntId                                              SnmpAdminString,
    cfprMgmtBackupJob                                                CfprMgmtBackupJob,
    cfprMgmtBackupMaxFiles                                           Gauge32,
    cfprMgmtBackupName                                               SnmpAdminString,
    cfprMgmtBackupOwnerPolicy                                        SnmpAdminString,
    cfprMgmtBackupPolicyLevel                                        Gauge32,
    cfprMgmtBackupPolicyOwner                                        CfprPolicyPolicyOwner,
    cfprMgmtBackupPostAction                                         CfprMgmtBackupPostAction,
    cfprMgmtBackupPreservePooledValues                               TruthValue,
    cfprMgmtBackupProto                                              CfprMgmtBackupProto,
    cfprMgmtBackupPwd                                                SnmpAdminString,
    cfprMgmtBackupRemoteFile                                         SnmpAdminString,
    cfprMgmtBackupType                                               CfprMgmtBackupType,
    cfprMgmtBackupUser                                               SnmpAdminString,
    cfprMgmtBackupOperStatus                                         CfprMgmtBackupStatus,
    cfprMgmtBackupPort                                               Gauge32,
    cfprMgmtBackupErrMsg                                             SnmpAdminString
}

cfprMgmtBackupInstanceId OBJECT-TYPE
    SYNTAX       CfprManagedObjectId
    MAX-ACCESS   not-accessible
    STATUS       current
    DESCRIPTION
        "Instance identifier of the managed object."
    ::= { cfprMgmtBackupEntry 1 }

cfprMgmtBackupDn OBJECT-TYPE
    SYNTAX       CfprManagedObjectDn
    MAX-ACCESS   read-only
    STATUS       current
    DESCRIPTION
        "Cisco Firepower mgmt:Backup:dn managed object property"
    ::= { cfprMgmtBackupEntry 2 }

cfprMgmtBackupRn OBJECT-TYPE
    SYNTAX       SnmpAdminString
    MAX-ACCESS   read-only
    STATUS       current
    DESCRIPTION
        "Cisco Firepower mgmt:Backup:rn managed object property"
    ::= { cfprMgmtBackupEntry 3 }

cfprMgmtBackupAdminState OBJECT-TYPE
    SYNTAX       CfprCommClientAdminState
    MAX-ACCESS   read-only
    STATUS       current
    DESCRIPTION
        "Cisco Firepower mgmt:Backup:adminState managed object property"
    ::= { cfprMgmtBackupEntry 4 }

cfprMgmtBackupDescr OBJECT-TYPE
    SYNTAX       SnmpAdminString
    MAX-ACCESS   read-only
    STATUS       current
    DESCRIPTION
        "Cisco Firepower mgmt:Backup:descr managed object property"
    ::= { cfprMgmtBackupEntry 5 }

cfprMgmtBackupFsmDescr OBJECT-TYPE
    SYNTAX       SnmpAdminString
    MAX-ACCESS   read-only
    STATUS       current
    DESCRIPTION
        "Cisco Firepower mgmt:Backup:fsmDescr managed object property"
    ::= { cfprMgmtBackupEntry 6 }

cfprMgmtBackupFsmPrev OBJECT-TYPE
    SYNTAX       SnmpAdminString
    MAX-ACCESS   read-only
    STATUS       current
    DESCRIPTION
        "Cisco Firepower mgmt:Backup:fsmPrev managed object property"
    ::= { cfprMgmtBackupEntry 7 }

cfprMgmtBackupFsmProgr OBJECT-TYPE
    SYNTAX       Gauge32
    MAX-ACCESS   read-only
    STATUS       current
    DESCRIPTION
        "Cisco Firepower mgmt:Backup:fsmProgr managed object property"
    ::= { cfprMgmtBackupEntry 8 }

cfprMgmtBackupFsmRmtInvErrCode OBJECT-TYPE
    SYNTAX       Gauge32
    MAX-ACCESS   read-only
    STATUS       current
    DESCRIPTION
        "Cisco Firepower mgmt:Backup:fsmRmtInvErrCode managed
        object property"
    ::= { cfprMgmtBackupEntry 9 }

cfprMgmtBackupFsmRmtInvErrDescr OBJECT-TYPE
    SYNTAX       SnmpAdminString
    MAX-ACCESS   read-only
    STATUS       current
    DESCRIPTION
        "Cisco Firepower mgmt:Backup:fsmRmtInvErrDescr
        managed object property"
    ::= { cfprMgmtBackupEntry 10 }

cfprMgmtBackupFsmRmtInvRslt OBJECT-TYPE
    SYNTAX       CfprConditionRemoteInvRslt
    MAX-ACCESS   read-only
    STATUS       current
    DESCRIPTION
        "Cisco Firepower mgmt:Backup:fsmRmtInvRslt managed
        object property"
    ::= { cfprMgmtBackupEntry 11 }

cfprMgmtBackupFsmStageDescr OBJECT-TYPE
    SYNTAX       SnmpAdminString
    MAX-ACCESS   read-only
    STATUS       current
    DESCRIPTION
        "Cisco Firepower mgmt:Backup:fsmStageDescr managed
        object property"
    ::= { cfprMgmtBackupEntry 12 }

cfprMgmtBackupFsmStamp OBJECT-TYPE
    SYNTAX       DateAndTime
    MAX-ACCESS   read-only
    STATUS       current
    DESCRIPTION
        "Cisco Firepower mgmt:Backup:fsmStamp managed object property"
    ::= { cfprMgmtBackupEntry 13 }

cfprMgmtBackupFsmStatus OBJECT-TYPE
    SYNTAX       SnmpAdminString
    MAX-ACCESS   read-only
    STATUS       current
    DESCRIPTION
        "Cisco Firepower mgmt:Backup:fsmStatus managed object property"
    ::= { cfprMgmtBackupEntry 14 }

cfprMgmtBackupFsmTry OBJECT-TYPE
    SYNTAX       Gauge32
    MAX-ACCESS   read-only
    STATUS       current
    DESCRIPTION
        "Cisco Firepower mgmt:Backup:fsmTry managed object property"
    ::= { cfprMgmtBackupEntry 15 }

cfprMgmtBackupHostname OBJECT-TYPE
    SYNTAX       SnmpAdminString
    MAX-ACCESS   read-only
    STATUS       current
    DESCRIPTION
        "Cisco Firepower mgmt:Backup:hostname managed object property"
    ::= { cfprMgmtBackupEntry 16 }

cfprMgmtBackupIntId OBJECT-TYPE
    SYNTAX       SnmpAdminString
    MAX-ACCESS   read-only
    STATUS       current
    DESCRIPTION
        "Cisco Firepower mgmt:Backup:intId managed object property"
    ::= { cfprMgmtBackupEntry 17 }

cfprMgmtBackupJob OBJECT-TYPE
    SYNTAX       CfprMgmtBackupJob
    MAX-ACCESS   read-only
    STATUS       current
    DESCRIPTION
        "Cisco Firepower mgmt:Backup:job managed object property"
    ::= { cfprMgmtBackupEntry 18 }

cfprMgmtBackupMaxFiles OBJECT-TYPE
    SYNTAX       Gauge32
    MAX-ACCESS   read-only
    STATUS       current
    DESCRIPTION
        "Cisco Firepower mgmt:Backup:maxFiles managed object property"
    ::= { cfprMgmtBackupEntry 19 }

cfprMgmtBackupName OBJECT-TYPE
    SYNTAX       SnmpAdminString
    MAX-ACCESS   read-only
    STATUS       current
    DESCRIPTION
        "Cisco Firepower mgmt:Backup:name managed object property"
    ::= { cfprMgmtBackupEntry 20 }

cfprMgmtBackupOwnerPolicy OBJECT-TYPE
    SYNTAX       SnmpAdminString
    MAX-ACCESS   read-only
    STATUS       current
    DESCRIPTION
        "Cisco Firepower mgmt:Backup:ownerPolicy managed object property"
    ::= { cfprMgmtBackupEntry 21 }

cfprMgmtBackupPolicyLevel OBJECT-TYPE
    SYNTAX       Gauge32
    MAX-ACCESS   read-only
    STATUS       current
    DESCRIPTION
        "Cisco Firepower mgmt:Backup:policyLevel managed object property"
    ::= { cfprMgmtBackupEntry 22 }

cfprMgmtBackupPolicyOwner OBJECT-TYPE
    SYNTAX       CfprPolicyPolicyOwner
    MAX-ACCESS   read-only
    STATUS       current
    DESCRIPTION
        "Cisco Firepower mgmt:Backup:policyOwner managed object property"
    ::= { cfprMgmtBackupEntry 23 }

cfprMgmtBackupPostAction OBJECT-TYPE
    SYNTAX       CfprMgmtBackupPostAction
    MAX-ACCESS   read-only
    STATUS       current
    DESCRIPTION
        "Cisco Firepower mgmt:Backup:postAction managed object property"
    ::= { cfprMgmtBackupEntry 24 }

cfprMgmtBackupPreservePooledValues OBJECT-TYPE
    SYNTAX       TruthValue
    MAX-ACCESS   read-only
    STATUS       current
    DESCRIPTION
        "Cisco Firepower mgmt:Backup:preservePooledValues
        managed object property"
    ::= { cfprMgmtBackupEntry 25 }

cfprMgmtBackupProto OBJECT-TYPE
    SYNTAX       CfprMgmtBackupProto
    MAX-ACCESS   read-only
    STATUS       current
    DESCRIPTION
        "Cisco Firepower mgmt:Backup:proto managed object property"
    ::= { cfprMgmtBackupEntry 26 }

cfprMgmtBackupPwd OBJECT-TYPE
    SYNTAX       SnmpAdminString
    MAX-ACCESS   read-only
    STATUS       current
    DESCRIPTION
        "Cisco Firepower mgmt:Backup:pwd managed object property"
    ::= { cfprMgmtBackupEntry 27 }

cfprMgmtBackupRemoteFile OBJECT-TYPE
    SYNTAX       SnmpAdminString
    MAX-ACCESS   read-only
    STATUS       current
    DESCRIPTION
        "Cisco Firepower mgmt:Backup:remoteFile managed object property"
    ::= { cfprMgmtBackupEntry 28 }

cfprMgmtBackupType OBJECT-TYPE
    SYNTAX       CfprMgmtBackupType
    MAX-ACCESS   read-only
    STATUS       current
    DESCRIPTION
        "Cisco Firepower mgmt:Backup:type managed object property"
    ::= { cfprMgmtBackupEntry 29 }

cfprMgmtBackupUser OBJECT-TYPE
    SYNTAX       SnmpAdminString
    MAX-ACCESS   read-only
    STATUS       current
    DESCRIPTION
        "Cisco Firepower mgmt:Backup:user managed object property"
    ::= { cfprMgmtBackupEntry 30 }

cfprMgmtBackupOperStatus OBJECT-TYPE
    SYNTAX       CfprMgmtBackupStatus
    MAX-ACCESS   read-only
    STATUS       current
    DESCRIPTION
        "Cisco Firepower mgmt:Backup:operStatus managed object property"
    ::= { cfprMgmtBackupEntry 31 }

cfprMgmtBackupPort OBJECT-TYPE
    SYNTAX       Gauge32
    MAX-ACCESS   read-only
    STATUS       current
    DESCRIPTION
        "Cisco Firepower mgmt:Backup:port managed object property"
    ::= { cfprMgmtBackupEntry 32 }

cfprMgmtBackupErrMsg OBJECT-TYPE
    SYNTAX       SnmpAdminString
    MAX-ACCESS   read-only
    STATUS       current
    DESCRIPTION
        "Cisco Firepower mgmt:Backup:errMsg managed object property"
    ::= { cfprMgmtBackupEntry 33 }

cfprMgmtBackupExportExtPolicyTable OBJECT-TYPE
    SYNTAX           SEQUENCE OF CfprMgmtBackupExportExtPolicyEntry
    MAX-ACCESS       not-accessible
    STATUS           current
    DESCRIPTION
        "Cisco Firepower mgmt:BackupExportExtPolicy managed object table"
    ::= { cfprMgmtObjects 5 }

cfprMgmtBackupExportExtPolicyEntry OBJECT-TYPE
    SYNTAX           CfprMgmtBackupExportExtPolicyEntry
    MAX-ACCESS       not-accessible
    STATUS           current
    DESCRIPTION
        "Entry for the cfprMgmtBackupExportExtPolicyTable table."
    INDEX { cfprMgmtBackupExportExtPolicyInstanceId }
    ::= { cfprMgmtBackupExportExtPolicyTable 1 }

CfprMgmtBackupExportExtPolicyEntry ::= SEQUENCE {
    cfprMgmtBackupExportExtPolicyInstanceId                          CfprManagedObjectId,
    cfprMgmtBackupExportExtPolicyDn                                  CfprManagedObjectDn,
    cfprMgmtBackupExportExtPolicyRn                                  SnmpAdminString,
    cfprMgmtBackupExportExtPolicyAdminState                          CfprMgmtAdminState,
    cfprMgmtBackupExportExtPolicyDescr                               SnmpAdminString,
    cfprMgmtBackupExportExtPolicyFrequency                           Gauge32,
    cfprMgmtBackupExportExtPolicyIntId                               SnmpAdminString,
    cfprMgmtBackupExportExtPolicyName                                SnmpAdminString,
    cfprMgmtBackupExportExtPolicyPolicyLevel                         Gauge32,
    cfprMgmtBackupExportExtPolicyPolicyOwner                         CfprPolicyPolicyOwner
}

cfprMgmtBackupExportExtPolicyInstanceId OBJECT-TYPE
    SYNTAX       CfprManagedObjectId
    MAX-ACCESS   not-accessible
    STATUS       current
    DESCRIPTION
        "Instance identifier of the managed object."
    ::= { cfprMgmtBackupExportExtPolicyEntry 1 }

cfprMgmtBackupExportExtPolicyDn OBJECT-TYPE
    SYNTAX       CfprManagedObjectDn
    MAX-ACCESS   read-only
    STATUS       current
    DESCRIPTION
        "Cisco Firepower mgmt:BackupExportExtPolicy:dn
        managed object property"
    ::= { cfprMgmtBackupExportExtPolicyEntry 2 }

cfprMgmtBackupExportExtPolicyRn OBJECT-TYPE
    SYNTAX       SnmpAdminString
    MAX-ACCESS   read-only
    STATUS       current
    DESCRIPTION
        "Cisco Firepower mgmt:BackupExportExtPolicy:rn
        managed object property"
    ::= { cfprMgmtBackupExportExtPolicyEntry 3 }

cfprMgmtBackupExportExtPolicyAdminState OBJECT-TYPE
    SYNTAX       CfprMgmtAdminState
    MAX-ACCESS   read-only
    STATUS       current
    DESCRIPTION
        "Cisco Firepower mgmt:BackupExportExtPolicy:adminState
        managed object property"
    ::= { cfprMgmtBackupExportExtPolicyEntry 4 }

cfprMgmtBackupExportExtPolicyDescr OBJECT-TYPE
    SYNTAX       SnmpAdminString
    MAX-ACCESS   read-only
    STATUS       current
    DESCRIPTION
        "Cisco Firepower mgmt:BackupExportExtPolicy:descr
        managed object property"
    ::= { cfprMgmtBackupExportExtPolicyEntry 5 }

cfprMgmtBackupExportExtPolicyFrequency OBJECT-TYPE
    SYNTAX       Gauge32
    MAX-ACCESS   read-only
    STATUS       current
    DESCRIPTION
        "Cisco Firepower mgmt:BackupExportExtPolicy:frequency
        managed object property"
    ::= { cfprMgmtBackupExportExtPolicyEntry 6 }

cfprMgmtBackupExportExtPolicyIntId OBJECT-TYPE
    SYNTAX       SnmpAdminString
    MAX-ACCESS   read-only
    STATUS       current
    DESCRIPTION
        "Cisco Firepower mgmt:BackupExportExtPolicy:intId
        managed object property"
    ::= { cfprMgmtBackupExportExtPolicyEntry 7 }

cfprMgmtBackupExportExtPolicyName OBJECT-TYPE
    SYNTAX       SnmpAdminString
    MAX-ACCESS   read-only
    STATUS       current
    DESCRIPTION
        "Cisco Firepower mgmt:BackupExportExtPolicy:name
        managed object property"
    ::= { cfprMgmtBackupExportExtPolicyEntry 8 }

cfprMgmtBackupExportExtPolicyPolicyLevel OBJECT-TYPE
    SYNTAX       Gauge32
    MAX-ACCESS   read-only
    STATUS       current
    DESCRIPTION
        "Cisco Firepower mgmt:BackupExportExtPolicy:policyLevel
        managed object property"
    ::= { cfprMgmtBackupExportExtPolicyEntry 9 }

cfprMgmtBackupExportExtPolicyPolicyOwner OBJECT-TYPE
    SYNTAX       CfprPolicyPolicyOwner
    MAX-ACCESS   read-only
    STATUS       current
    DESCRIPTION
        "Cisco Firepower mgmt:BackupExportExtPolicy:policyOwner
        managed object property"
    ::= { cfprMgmtBackupExportExtPolicyEntry 10 }

cfprMgmtBackupFsmTable OBJECT-TYPE
    SYNTAX           SEQUENCE OF CfprMgmtBackupFsmEntry
    MAX-ACCESS       not-accessible
    STATUS           current
    DESCRIPTION
        "Cisco Firepower mgmt:BackupFsm managed object table"
    ::= { cfprMgmtObjects 6 }

cfprMgmtBackupFsmEntry OBJECT-TYPE
    SYNTAX           CfprMgmtBackupFsmEntry
    MAX-ACCESS       not-accessible
    STATUS           current
    DESCRIPTION
        "Entry for the cfprMgmtBackupFsmTable table."
    INDEX { cfprMgmtBackupFsmInstanceId }
    ::= { cfprMgmtBackupFsmTable 1 }

CfprMgmtBackupFsmEntry ::= SEQUENCE {
    cfprMgmtBackupFsmInstanceId                                      CfprManagedObjectId,
    cfprMgmtBackupFsmDn                                              CfprManagedObjectDn,
    cfprMgmtBackupFsmRn                                              SnmpAdminString,
    cfprMgmtBackupFsmCompletionTime                                  DateAndTime,
    cfprMgmtBackupFsmCurrentFsm                                      CfprMgmtBackupFsmCurrentFsm,
    cfprMgmtBackupFsmDescrData                                       SnmpAdminString,
    cfprMgmtBackupFsmFsmStatus                                       CfprFsmFsmStageStatus,
    cfprMgmtBackupFsmProgress                                        Gauge32,
    cfprMgmtBackupFsmRmtErrCode                                      Gauge32,
    cfprMgmtBackupFsmRmtErrDescr                                     SnmpAdminString,
    cfprMgmtBackupFsmRmtRslt                                         CfprConditionRemoteInvRslt
}

cfprMgmtBackupFsmInstanceId OBJECT-TYPE
    SYNTAX       CfprManagedObjectId
    MAX-ACCESS   not-accessible
    STATUS       current
    DESCRIPTION
        "Instance identifier of the managed object."
    ::= { cfprMgmtBackupFsmEntry 1 }

cfprMgmtBackupFsmDn OBJECT-TYPE
    SYNTAX       CfprManagedObjectDn
    MAX-ACCESS   read-only
    STATUS       current
    DESCRIPTION
        "Cisco Firepower mgmt:BackupFsm:dn managed object property"
    ::= { cfprMgmtBackupFsmEntry 2 }

cfprMgmtBackupFsmRn OBJECT-TYPE
    SYNTAX       SnmpAdminString
    MAX-ACCESS   read-only
    STATUS       current
    DESCRIPTION
        "Cisco Firepower mgmt:BackupFsm:rn managed object property"
    ::= { cfprMgmtBackupFsmEntry 3 }

cfprMgmtBackupFsmCompletionTime OBJECT-TYPE
    SYNTAX       DateAndTime
    MAX-ACCESS   read-only
    STATUS       current
    DESCRIPTION
        "Cisco Firepower mgmt:BackupFsm:completionTime
        managed object property"
    ::= { cfprMgmtBackupFsmEntry 4 }

cfprMgmtBackupFsmCurrentFsm OBJECT-TYPE
    SYNTAX       CfprMgmtBackupFsmCurrentFsm
    MAX-ACCESS   read-only
    STATUS       current
    DESCRIPTION
        "Cisco Firepower mgmt:BackupFsm:currentFsm managed
        object property"
    ::= { cfprMgmtBackupFsmEntry 5 }

cfprMgmtBackupFsmDescrData OBJECT-TYPE
    SYNTAX       SnmpAdminString
    MAX-ACCESS   read-only
    STATUS       current
    DESCRIPTION
        "Cisco Firepower mgmt:BackupFsm:descr managed object property"
    ::= { cfprMgmtBackupFsmEntry 6 }

cfprMgmtBackupFsmFsmStatus OBJECT-TYPE
    SYNTAX       CfprFsmFsmStageStatus
    MAX-ACCESS   read-only
    STATUS       current
    DESCRIPTION
        "Cisco Firepower mgmt:BackupFsm:fsmStatus managed object property"
    ::= { cfprMgmtBackupFsmEntry 7 }

cfprMgmtBackupFsmProgress OBJECT-TYPE
    SYNTAX       Gauge32
    MAX-ACCESS   read-only
    STATUS       current
    DESCRIPTION
        "Cisco Firepower mgmt:BackupFsm:progress managed object property"
    ::= { cfprMgmtBackupFsmEntry 8 }

cfprMgmtBackupFsmRmtErrCode OBJECT-TYPE
    SYNTAX       Gauge32
    MAX-ACCESS   read-only
    STATUS       current
    DESCRIPTION
        "Cisco Firepower mgmt:BackupFsm:rmtErrCode managed
        object property"
    ::= { cfprMgmtBackupFsmEntry 9 }

cfprMgmtBackupFsmRmtErrDescr OBJECT-TYPE
    SYNTAX       SnmpAdminString
    MAX-ACCESS   read-only
    STATUS       current
    DESCRIPTION
        "Cisco Firepower mgmt:BackupFsm:rmtErrDescr managed
        object property"
    ::= { cfprMgmtBackupFsmEntry 10 }

cfprMgmtBackupFsmRmtRslt OBJECT-TYPE
    SYNTAX       CfprConditionRemoteInvRslt
    MAX-ACCESS   read-only
    STATUS       current
    DESCRIPTION
        "Cisco Firepower mgmt:BackupFsm:rmtRslt managed object property"
    ::= { cfprMgmtBackupFsmEntry 11 }

cfprMgmtBackupFsmStageTable OBJECT-TYPE
    SYNTAX           SEQUENCE OF CfprMgmtBackupFsmStageEntry
    MAX-ACCESS       not-accessible
    STATUS           current
    DESCRIPTION
        "Cisco Firepower mgmt:BackupFsmStage managed object table"
    ::= { cfprMgmtObjects 7 }

cfprMgmtBackupFsmStageEntry OBJECT-TYPE
    SYNTAX           CfprMgmtBackupFsmStageEntry
    MAX-ACCESS       not-accessible
    STATUS           current
    DESCRIPTION
        "Entry for the cfprMgmtBackupFsmStageTable table."
    INDEX { cfprMgmtBackupFsmStageInstanceId }
    ::= { cfprMgmtBackupFsmStageTable 1 }

CfprMgmtBackupFsmStageEntry ::= SEQUENCE {
    cfprMgmtBackupFsmStageInstanceId                                 CfprManagedObjectId,
    cfprMgmtBackupFsmStageDn                                         CfprManagedObjectDn,
    cfprMgmtBackupFsmStageRn                                         SnmpAdminString,
    cfprMgmtBackupFsmStageDescrData                                  SnmpAdminString,
    cfprMgmtBackupFsmStageLastUpdateTime                             DateAndTime,
    cfprMgmtBackupFsmStageName                                       CfprMgmtBackupFsmStageName,
    cfprMgmtBackupFsmStageOrder                                      Gauge32,
    cfprMgmtBackupFsmStageRetry                                      Gauge32,
    cfprMgmtBackupFsmStageStageStatus                                CfprFsmFsmStageStatus
}

cfprMgmtBackupFsmStageInstanceId OBJECT-TYPE
    SYNTAX       CfprManagedObjectId
    MAX-ACCESS   not-accessible
    STATUS       current
    DESCRIPTION
        "Instance identifier of the managed object."
    ::= { cfprMgmtBackupFsmStageEntry 1 }

cfprMgmtBackupFsmStageDn OBJECT-TYPE
    SYNTAX       CfprManagedObjectDn
    MAX-ACCESS   read-only
    STATUS       current
    DESCRIPTION
        "Cisco Firepower mgmt:BackupFsmStage:dn managed object property"
    ::= { cfprMgmtBackupFsmStageEntry 2 }

cfprMgmtBackupFsmStageRn OBJECT-TYPE
    SYNTAX       SnmpAdminString
    MAX-ACCESS   read-only
    STATUS       current
    DESCRIPTION
        "Cisco Firepower mgmt:BackupFsmStage:rn managed object property"
    ::= { cfprMgmtBackupFsmStageEntry 3 }

cfprMgmtBackupFsmStageDescrData OBJECT-TYPE
    SYNTAX       SnmpAdminString
    MAX-ACCESS   read-only
    STATUS       current
    DESCRIPTION
        "Cisco Firepower mgmt:BackupFsmStage:descr managed
        object property"
    ::= { cfprMgmtBackupFsmStageEntry 4 }

cfprMgmtBackupFsmStageLastUpdateTime OBJECT-TYPE
    SYNTAX       DateAndTime
    MAX-ACCESS   read-only
    STATUS       current
    DESCRIPTION
        "Cisco Firepower mgmt:BackupFsmStage:lastUpdateTime
        managed object property"
    ::= { cfprMgmtBackupFsmStageEntry 5 }

cfprMgmtBackupFsmStageName OBJECT-TYPE
    SYNTAX       CfprMgmtBackupFsmStageName
    MAX-ACCESS   read-only
    STATUS       current
    DESCRIPTION
        "Cisco Firepower mgmt:BackupFsmStage:name managed object property"
    ::= { cfprMgmtBackupFsmStageEntry 6 }

cfprMgmtBackupFsmStageOrder OBJECT-TYPE
    SYNTAX       Gauge32
    MAX-ACCESS   read-only
    STATUS       current
    DESCRIPTION
        "Cisco Firepower mgmt:BackupFsmStage:order managed
        object property"
    ::= { cfprMgmtBackupFsmStageEntry 7 }

cfprMgmtBackupFsmStageRetry OBJECT-TYPE
    SYNTAX       Gauge32
    MAX-ACCESS   read-only
    STATUS       current
    DESCRIPTION
        "Cisco Firepower mgmt:BackupFsmStage:retry managed
        object property"
    ::= { cfprMgmtBackupFsmStageEntry 8 }

cfprMgmtBackupFsmStageStageStatus OBJECT-TYPE
    SYNTAX       CfprFsmFsmStageStatus
    MAX-ACCESS   read-only
    STATUS       current
    DESCRIPTION
        "Cisco Firepower mgmt:BackupFsmStage:stageStatus
        managed object property"
    ::= { cfprMgmtBackupFsmStageEntry 9 }

cfprMgmtBackupFsmTaskTable OBJECT-TYPE
    SYNTAX           SEQUENCE OF CfprMgmtBackupFsmTaskEntry
    MAX-ACCESS       not-accessible
    STATUS           current
    DESCRIPTION
        "Cisco Firepower mgmt:BackupFsmTask managed object table"
    ::= { cfprMgmtObjects 8 }

cfprMgmtBackupFsmTaskEntry OBJECT-TYPE
    SYNTAX           CfprMgmtBackupFsmTaskEntry
    MAX-ACCESS       not-accessible
    STATUS           current
    DESCRIPTION
        "Entry for the cfprMgmtBackupFsmTaskTable table."
    INDEX { cfprMgmtBackupFsmTaskInstanceId }
    ::= { cfprMgmtBackupFsmTaskTable 1 }

CfprMgmtBackupFsmTaskEntry ::= SEQUENCE {
    cfprMgmtBackupFsmTaskInstanceId                                  CfprManagedObjectId,
    cfprMgmtBackupFsmTaskDn                                          CfprManagedObjectDn,
    cfprMgmtBackupFsmTaskRn                                          SnmpAdminString,
    cfprMgmtBackupFsmTaskCompletion                                  CfprFsmCompletion,
    cfprMgmtBackupFsmTaskFlags                                       CfprFsmFlags,
    cfprMgmtBackupFsmTaskItem                                        CfprMgmtBackupFsmTaskItem,
    cfprMgmtBackupFsmTaskSeqId                                       Gauge32
}

cfprMgmtBackupFsmTaskInstanceId OBJECT-TYPE
    SYNTAX       CfprManagedObjectId
    MAX-ACCESS   not-accessible
    STATUS       current
    DESCRIPTION
        "Instance identifier of the managed object."
    ::= { cfprMgmtBackupFsmTaskEntry 1 }

cfprMgmtBackupFsmTaskDn OBJECT-TYPE
    SYNTAX       CfprManagedObjectDn
    MAX-ACCESS   read-only
    STATUS       current
    DESCRIPTION
        "Cisco Firepower mgmt:BackupFsmTask:dn managed object property"
    ::= { cfprMgmtBackupFsmTaskEntry 2 }

cfprMgmtBackupFsmTaskRn OBJECT-TYPE
    SYNTAX       SnmpAdminString
    MAX-ACCESS   read-only
    STATUS       current
    DESCRIPTION
        "Cisco Firepower mgmt:BackupFsmTask:rn managed object property"
    ::= { cfprMgmtBackupFsmTaskEntry 3 }

cfprMgmtBackupFsmTaskCompletion OBJECT-TYPE
    SYNTAX       CfprFsmCompletion
    MAX-ACCESS   read-only
    STATUS       current
    DESCRIPTION
        "Cisco Firepower mgmt:BackupFsmTask:completion
        managed object property"
    ::= { cfprMgmtBackupFsmTaskEntry 4 }

cfprMgmtBackupFsmTaskFlags OBJECT-TYPE
    SYNTAX       CfprFsmFlags
    MAX-ACCESS   read-only
    STATUS       current
    DESCRIPTION
        "Cisco Firepower mgmt:BackupFsmTask:flags managed object property"
    ::= { cfprMgmtBackupFsmTaskEntry 5 }

cfprMgmtBackupFsmTaskItem OBJECT-TYPE
    SYNTAX       CfprMgmtBackupFsmTaskItem
    MAX-ACCESS   read-only
    STATUS       current
    DESCRIPTION
        "Cisco Firepower mgmt:BackupFsmTask:item managed object property"
    ::= { cfprMgmtBackupFsmTaskEntry 6 }

cfprMgmtBackupFsmTaskSeqId OBJECT-TYPE
    SYNTAX       Gauge32
    MAX-ACCESS   read-only
    STATUS       current
    DESCRIPTION
        "Cisco Firepower mgmt:BackupFsmTask:seqId managed object property"
    ::= { cfprMgmtBackupFsmTaskEntry 7 }

cfprMgmtBackupPolicyTable OBJECT-TYPE
    SYNTAX           SEQUENCE OF CfprMgmtBackupPolicyEntry
    MAX-ACCESS       not-accessible
    STATUS           current
    DESCRIPTION
        "Cisco Firepower mgmt:BackupPolicy managed object table"
    ::= { cfprMgmtObjects 9 }

cfprMgmtBackupPolicyEntry OBJECT-TYPE
    SYNTAX           CfprMgmtBackupPolicyEntry
    MAX-ACCESS       not-accessible
    STATUS           current
    DESCRIPTION
        "Entry for the cfprMgmtBackupPolicyTable table."
    INDEX { cfprMgmtBackupPolicyInstanceId }
    ::= { cfprMgmtBackupPolicyTable 1 }

CfprMgmtBackupPolicyEntry ::= SEQUENCE {
    cfprMgmtBackupPolicyInstanceId                                   CfprManagedObjectId,
    cfprMgmtBackupPolicyDn                                           CfprManagedObjectDn,
    cfprMgmtBackupPolicyRn                                           SnmpAdminString,
    cfprMgmtBackupPolicyAdminState                                   CfprMgmtExportPolicyAdminState,
    cfprMgmtBackupPolicyDescr                                        SnmpAdminString,
    cfprMgmtBackupPolicyFsmDescr                                     SnmpAdminString,
    cfprMgmtBackupPolicyFsmPrev                                      SnmpAdminString,
    cfprMgmtBackupPolicyFsmProgr                                     Gauge32,
    cfprMgmtBackupPolicyFsmRmtInvErrCode                             Gauge32,
    cfprMgmtBackupPolicyFsmRmtInvErrDescr                            SnmpAdminString,
    cfprMgmtBackupPolicyFsmRmtInvRslt                                CfprConditionRemoteInvRslt,
    cfprMgmtBackupPolicyFsmStageDescr                                SnmpAdminString,
    cfprMgmtBackupPolicyFsmStamp                                     DateAndTime,
    cfprMgmtBackupPolicyFsmStatus                                    SnmpAdminString,
    cfprMgmtBackupPolicyFsmTry                                       Gauge32,
    cfprMgmtBackupPolicyHost                                         SnmpAdminString,
    cfprMgmtBackupPolicyIntId                                        SnmpAdminString,
    cfprMgmtBackupPolicyLastBackup                                   DateAndTime,
    cfprMgmtBackupPolicyMaxFiles                                     Gauge32,
    cfprMgmtBackupPolicyName                                         SnmpAdminString,
    cfprMgmtBackupPolicyPolicyLevel                                  Gauge32,
    cfprMgmtBackupPolicyPolicyOwner                                  CfprPolicyPolicyOwner,
    cfprMgmtBackupPolicyProto                                        CfprMgmtExportPolicyProto,
    cfprMgmtBackupPolicyPwd                                          SnmpAdminString,
    cfprMgmtBackupPolicyRemoteFile                                   SnmpAdminString,
    cfprMgmtBackupPolicySchedule                                     CfprMgmtBackupInterval,
    cfprMgmtBackupPolicyUser                                         SnmpAdminString,
    cfprMgmtBackupPolicyPort                                         Gauge32
}

cfprMgmtBackupPolicyInstanceId OBJECT-TYPE
    SYNTAX       CfprManagedObjectId
    MAX-ACCESS   not-accessible
    STATUS       current
    DESCRIPTION
        "Instance identifier of the managed object."
    ::= { cfprMgmtBackupPolicyEntry 1 }

cfprMgmtBackupPolicyDn OBJECT-TYPE
    SYNTAX       CfprManagedObjectDn
    MAX-ACCESS   read-only
    STATUS       current
    DESCRIPTION
        "Cisco Firepower mgmt:BackupPolicy:dn managed object property"
    ::= { cfprMgmtBackupPolicyEntry 2 }

cfprMgmtBackupPolicyRn OBJECT-TYPE
    SYNTAX       SnmpAdminString
    MAX-ACCESS   read-only
    STATUS       current
    DESCRIPTION
        "Cisco Firepower mgmt:BackupPolicy:rn managed object property"
    ::= { cfprMgmtBackupPolicyEntry 3 }

cfprMgmtBackupPolicyAdminState OBJECT-TYPE
    SYNTAX       CfprMgmtExportPolicyAdminState
    MAX-ACCESS   read-only
    STATUS       current
    DESCRIPTION
        "Cisco Firepower mgmt:BackupPolicy:adminState managed
        object property"
    ::= { cfprMgmtBackupPolicyEntry 4 }

cfprMgmtBackupPolicyDescr OBJECT-TYPE
    SYNTAX       SnmpAdminString
    MAX-ACCESS   read-only
    STATUS       current
    DESCRIPTION
        "Cisco Firepower mgmt:BackupPolicy:descr managed object property"
    ::= { cfprMgmtBackupPolicyEntry 5 }

cfprMgmtBackupPolicyFsmDescr OBJECT-TYPE
    SYNTAX       SnmpAdminString
    MAX-ACCESS   read-only
    STATUS       current
    DESCRIPTION
        "Cisco Firepower mgmt:BackupPolicy:fsmDescr managed
        object property"
    ::= { cfprMgmtBackupPolicyEntry 6 }

cfprMgmtBackupPolicyFsmPrev OBJECT-TYPE
    SYNTAX       SnmpAdminString
    MAX-ACCESS   read-only
    STATUS       current
    DESCRIPTION
        "Cisco Firepower mgmt:BackupPolicy:fsmPrev managed
        object property"
    ::= { cfprMgmtBackupPolicyEntry 7 }

cfprMgmtBackupPolicyFsmProgr OBJECT-TYPE
    SYNTAX       Gauge32
    MAX-ACCESS   read-only
    STATUS       current
    DESCRIPTION
        "Cisco Firepower mgmt:BackupPolicy:fsmProgr managed
        object property"
    ::= { cfprMgmtBackupPolicyEntry 8 }

cfprMgmtBackupPolicyFsmRmtInvErrCode OBJECT-TYPE
    SYNTAX       Gauge32
    MAX-ACCESS   read-only
    STATUS       current
    DESCRIPTION
        "Cisco Firepower mgmt:BackupPolicy:fsmRmtInvErrCode
        managed object property"
    ::= { cfprMgmtBackupPolicyEntry 9 }

cfprMgmtBackupPolicyFsmRmtInvErrDescr OBJECT-TYPE
    SYNTAX       SnmpAdminString
    MAX-ACCESS   read-only
    STATUS       current
    DESCRIPTION
        "Cisco Firepower mgmt:BackupPolicy:fsmRmtInvErrDescr
        managed object property"
    ::= { cfprMgmtBackupPolicyEntry 10 }

cfprMgmtBackupPolicyFsmRmtInvRslt OBJECT-TYPE
    SYNTAX       CfprConditionRemoteInvRslt
    MAX-ACCESS   read-only
    STATUS       current
    DESCRIPTION
        "Cisco Firepower mgmt:BackupPolicy:fsmRmtInvRslt
        managed object property"
    ::= { cfprMgmtBackupPolicyEntry 11 }

cfprMgmtBackupPolicyFsmStageDescr OBJECT-TYPE
    SYNTAX       SnmpAdminString
    MAX-ACCESS   read-only
    STATUS       current
    DESCRIPTION
        "Cisco Firepower mgmt:BackupPolicy:fsmStageDescr
        managed object property"
    ::= { cfprMgmtBackupPolicyEntry 12 }

cfprMgmtBackupPolicyFsmStamp OBJECT-TYPE
    SYNTAX       DateAndTime
    MAX-ACCESS   read-only
    STATUS       current
    DESCRIPTION
        "Cisco Firepower mgmt:BackupPolicy:fsmStamp managed
        object property"
    ::= { cfprMgmtBackupPolicyEntry 13 }

cfprMgmtBackupPolicyFsmStatus OBJECT-TYPE
    SYNTAX       SnmpAdminString
    MAX-ACCESS   read-only
    STATUS       current
    DESCRIPTION
        "Cisco Firepower mgmt:BackupPolicy:fsmStatus managed
        object property"
    ::= { cfprMgmtBackupPolicyEntry 14 }

cfprMgmtBackupPolicyFsmTry OBJECT-TYPE
    SYNTAX       Gauge32
    MAX-ACCESS   read-only
    STATUS       current
    DESCRIPTION
        "Cisco Firepower mgmt:BackupPolicy:fsmTry managed object property"
    ::= { cfprMgmtBackupPolicyEntry 15 }

cfprMgmtBackupPolicyHost OBJECT-TYPE
    SYNTAX       SnmpAdminString
    MAX-ACCESS   read-only
    STATUS       current
    DESCRIPTION
        "Cisco Firepower mgmt:BackupPolicy:host managed object property"
    ::= { cfprMgmtBackupPolicyEntry 16 }

cfprMgmtBackupPolicyIntId OBJECT-TYPE
    SYNTAX       SnmpAdminString
    MAX-ACCESS   read-only
    STATUS       current
    DESCRIPTION
        "Cisco Firepower mgmt:BackupPolicy:intId managed object property"
    ::= { cfprMgmtBackupPolicyEntry 17 }

cfprMgmtBackupPolicyLastBackup OBJECT-TYPE
    SYNTAX       DateAndTime
    MAX-ACCESS   read-only
    STATUS       current
    DESCRIPTION
        "Cisco Firepower mgmt:BackupPolicy:lastBackup managed
        object property"
    ::= { cfprMgmtBackupPolicyEntry 18 }

cfprMgmtBackupPolicyMaxFiles OBJECT-TYPE
    SYNTAX       Gauge32
    MAX-ACCESS   read-only
    STATUS       current
    DESCRIPTION
        "Cisco Firepower mgmt:BackupPolicy:maxFiles managed
        object property"
    ::= { cfprMgmtBackupPolicyEntry 19 }

cfprMgmtBackupPolicyName OBJECT-TYPE
    SYNTAX       SnmpAdminString
    MAX-ACCESS   read-only
    STATUS       current
    DESCRIPTION
        "Cisco Firepower mgmt:BackupPolicy:name managed object property"
    ::= { cfprMgmtBackupPolicyEntry 20 }

cfprMgmtBackupPolicyPolicyLevel OBJECT-TYPE
    SYNTAX       Gauge32
    MAX-ACCESS   read-only
    STATUS       current
    DESCRIPTION
        "Cisco Firepower mgmt:BackupPolicy:policyLevel
        managed object property"
    ::= { cfprMgmtBackupPolicyEntry 21 }

cfprMgmtBackupPolicyPolicyOwner OBJECT-TYPE
    SYNTAX       CfprPolicyPolicyOwner
    MAX-ACCESS   read-only
    STATUS       current
    DESCRIPTION
        "Cisco Firepower mgmt:BackupPolicy:policyOwner
        managed object property"
    ::= { cfprMgmtBackupPolicyEntry 22 }

cfprMgmtBackupPolicyProto OBJECT-TYPE
    SYNTAX       CfprMgmtExportPolicyProto
    MAX-ACCESS   read-only
    STATUS       current
    DESCRIPTION
        "Cisco Firepower mgmt:BackupPolicy:proto managed object property"
    ::= { cfprMgmtBackupPolicyEntry 23 }

cfprMgmtBackupPolicyPwd OBJECT-TYPE
    SYNTAX       SnmpAdminString
    MAX-ACCESS   read-only
    STATUS       current
    DESCRIPTION
        "Cisco Firepower mgmt:BackupPolicy:pwd managed object property"
    ::= { cfprMgmtBackupPolicyEntry 24 }

cfprMgmtBackupPolicyRemoteFile OBJECT-TYPE
    SYNTAX       SnmpAdminString
    MAX-ACCESS   read-only
    STATUS       current
    DESCRIPTION
        "Cisco Firepower mgmt:BackupPolicy:remoteFile managed
        object property"
    ::= { cfprMgmtBackupPolicyEntry 25 }

cfprMgmtBackupPolicySchedule OBJECT-TYPE
    SYNTAX       CfprMgmtBackupInterval
    MAX-ACCESS   read-only
    STATUS       current
    DESCRIPTION
        "Cisco Firepower mgmt:BackupPolicy:schedule managed
        object property"
    ::= { cfprMgmtBackupPolicyEntry 26 }

cfprMgmtBackupPolicyUser OBJECT-TYPE
    SYNTAX       SnmpAdminString
    MAX-ACCESS   read-only
    STATUS       current
    DESCRIPTION
        "Cisco Firepower mgmt:BackupPolicy:user managed object property"
    ::= { cfprMgmtBackupPolicyEntry 27 }

cfprMgmtBackupPolicyPort OBJECT-TYPE
    SYNTAX       Gauge32
    MAX-ACCESS   read-only
    STATUS       current
    DESCRIPTION
        "Cisco Firepower mgmt:BackupPolicy:port managed object property"
    ::= { cfprMgmtBackupPolicyEntry 28 }

cfprMgmtBackupPolicyConfigTable OBJECT-TYPE
    SYNTAX           SEQUENCE OF CfprMgmtBackupPolicyConfigEntry
    MAX-ACCESS       not-accessible
    STATUS           current
    DESCRIPTION
        "Cisco Firepower mgmt:BackupPolicyConfig managed object table"
    ::= { cfprMgmtObjects 10 }

cfprMgmtBackupPolicyConfigEntry OBJECT-TYPE
    SYNTAX           CfprMgmtBackupPolicyConfigEntry
    MAX-ACCESS       not-accessible
    STATUS           current
    DESCRIPTION
        "Entry for the cfprMgmtBackupPolicyConfigTable table."
    INDEX { cfprMgmtBackupPolicyConfigInstanceId }
    ::= { cfprMgmtBackupPolicyConfigTable 1 }

CfprMgmtBackupPolicyConfigEntry ::= SEQUENCE {
    cfprMgmtBackupPolicyConfigInstanceId                             CfprManagedObjectId,
    cfprMgmtBackupPolicyConfigDn                                     CfprManagedObjectDn,
    cfprMgmtBackupPolicyConfigRn                                     SnmpAdminString,
    cfprMgmtBackupPolicyConfigAdminState                             CfprTrigAdminState,
    cfprMgmtBackupPolicyConfigAutoDelete                             TruthValue,
    cfprMgmtBackupPolicyConfigBackupDate                             DateAndTime,
    cfprMgmtBackupPolicyConfigBackupIssue                            CfprMgmtBackupIssue,
    cfprMgmtBackupPolicyConfigDescr                                  SnmpAdminString,
    cfprMgmtBackupPolicyConfigIgnoreCap                              TruthValue,
    cfprMgmtBackupPolicyConfigIntId                                  SnmpAdminString,
    cfprMgmtBackupPolicyConfigName                                   SnmpAdminString,
    cfprMgmtBackupPolicyConfigOperScheduler                          SnmpAdminString,
    cfprMgmtBackupPolicyConfigOperState                              CfprTrigTrigOperState,
    cfprMgmtBackupPolicyConfigPolicyLevel                            Gauge32,
    cfprMgmtBackupPolicyConfigPolicyOwner                            CfprPolicyPolicyOwner,
    cfprMgmtBackupPolicyConfigScheduler                              SnmpAdminString
}

cfprMgmtBackupPolicyConfigInstanceId OBJECT-TYPE
    SYNTAX       CfprManagedObjectId
    MAX-ACCESS   not-accessible
    STATUS       current
    DESCRIPTION
        "Instance identifier of the managed object."
    ::= { cfprMgmtBackupPolicyConfigEntry 1 }

cfprMgmtBackupPolicyConfigDn OBJECT-TYPE
    SYNTAX       CfprManagedObjectDn
    MAX-ACCESS   read-only
    STATUS       current
    DESCRIPTION
        "Cisco Firepower mgmt:BackupPolicyConfig:dn managed
        object property"
    ::= { cfprMgmtBackupPolicyConfigEntry 2 }

cfprMgmtBackupPolicyConfigRn OBJECT-TYPE
    SYNTAX       SnmpAdminString
    MAX-ACCESS   read-only
    STATUS       current
    DESCRIPTION
        "Cisco Firepower mgmt:BackupPolicyConfig:rn managed
        object property"
    ::= { cfprMgmtBackupPolicyConfigEntry 3 }

cfprMgmtBackupPolicyConfigAdminState OBJECT-TYPE
    SYNTAX       CfprTrigAdminState
    MAX-ACCESS   read-only
    STATUS       current
    DESCRIPTION
        "Cisco Firepower mgmt:BackupPolicyConfig:adminState
        managed object property"
    ::= { cfprMgmtBackupPolicyConfigEntry 4 }

cfprMgmtBackupPolicyConfigAutoDelete OBJECT-TYPE
    SYNTAX       TruthValue
    MAX-ACCESS   read-only
    STATUS       current
    DESCRIPTION
        "Cisco Firepower mgmt:BackupPolicyConfig:autoDelete
        managed object property"
    ::= { cfprMgmtBackupPolicyConfigEntry 5 }

cfprMgmtBackupPolicyConfigBackupDate OBJECT-TYPE
    SYNTAX       DateAndTime
    MAX-ACCESS   read-only
    STATUS       current
    DESCRIPTION
        "Cisco Firepower mgmt:BackupPolicyConfig:backupDate
        managed object property"
    ::= { cfprMgmtBackupPolicyConfigEntry 6 }

cfprMgmtBackupPolicyConfigBackupIssue OBJECT-TYPE
    SYNTAX       CfprMgmtBackupIssue
    MAX-ACCESS   read-only
    STATUS       current
    DESCRIPTION
        "Cisco Firepower mgmt:BackupPolicyConfig:backupIssue
        managed object property"
    ::= { cfprMgmtBackupPolicyConfigEntry 7 }

cfprMgmtBackupPolicyConfigDescr OBJECT-TYPE
    SYNTAX       SnmpAdminString
    MAX-ACCESS   read-only
    STATUS       current
    DESCRIPTION
        "Cisco Firepower mgmt:BackupPolicyConfig:descr
        managed object property"
    ::= { cfprMgmtBackupPolicyConfigEntry 8 }

cfprMgmtBackupPolicyConfigIgnoreCap OBJECT-TYPE
    SYNTAX       TruthValue
    MAX-ACCESS   read-only
    STATUS       current
    DESCRIPTION
        "Cisco Firepower mgmt:BackupPolicyConfig:ignoreCap
        managed object property"
    ::= { cfprMgmtBackupPolicyConfigEntry 9 }

cfprMgmtBackupPolicyConfigIntId OBJECT-TYPE
    SYNTAX       SnmpAdminString
    MAX-ACCESS   read-only
    STATUS       current
    DESCRIPTION
        "Cisco Firepower mgmt:BackupPolicyConfig:intId
        managed object property"
    ::= { cfprMgmtBackupPolicyConfigEntry 10 }

cfprMgmtBackupPolicyConfigName OBJECT-TYPE
    SYNTAX       SnmpAdminString
    MAX-ACCESS   read-only
    STATUS       current
    DESCRIPTION
        "Cisco Firepower mgmt:BackupPolicyConfig:name managed
        object property"
    ::= { cfprMgmtBackupPolicyConfigEntry 11 }

cfprMgmtBackupPolicyConfigOperScheduler OBJECT-TYPE
    SYNTAX       SnmpAdminString
    MAX-ACCESS   read-only
    STATUS       current
    DESCRIPTION
        "Cisco Firepower mgmt:BackupPolicyConfig:operScheduler
        managed object property"
    ::= { cfprMgmtBackupPolicyConfigEntry 12 }

cfprMgmtBackupPolicyConfigOperState OBJECT-TYPE
    SYNTAX       CfprTrigTrigOperState
    MAX-ACCESS   read-only
    STATUS       current
    DESCRIPTION
        "Cisco Firepower mgmt:BackupPolicyConfig:operState
        managed object property"
    ::= { cfprMgmtBackupPolicyConfigEntry 13 }

cfprMgmtBackupPolicyConfigPolicyLevel OBJECT-TYPE
    SYNTAX       Gauge32
    MAX-ACCESS   read-only
    STATUS       current
    DESCRIPTION
        "Cisco Firepower mgmt:BackupPolicyConfig:policyLevel
        managed object property"
    ::= { cfprMgmtBackupPolicyConfigEntry 14 }

cfprMgmtBackupPolicyConfigPolicyOwner OBJECT-TYPE
    SYNTAX       CfprPolicyPolicyOwner
    MAX-ACCESS   read-only
    STATUS       current
    DESCRIPTION
        "Cisco Firepower mgmt:BackupPolicyConfig:policyOwner
        managed object property"
    ::= { cfprMgmtBackupPolicyConfigEntry 15 }

cfprMgmtBackupPolicyConfigScheduler OBJECT-TYPE
    SYNTAX       SnmpAdminString
    MAX-ACCESS   read-only
    STATUS       current
    DESCRIPTION
        "Cisco Firepower mgmt:BackupPolicyConfig:scheduler
        managed object property"
    ::= { cfprMgmtBackupPolicyConfigEntry 16 }

cfprMgmtBackupPolicyFsmTable OBJECT-TYPE
    SYNTAX           SEQUENCE OF CfprMgmtBackupPolicyFsmEntry
    MAX-ACCESS       not-accessible
    STATUS           current
    DESCRIPTION
        "Cisco Firepower mgmt:BackupPolicyFsm managed object table"
    ::= { cfprMgmtObjects 11 }

cfprMgmtBackupPolicyFsmEntry OBJECT-TYPE
    SYNTAX           CfprMgmtBackupPolicyFsmEntry
    MAX-ACCESS       not-accessible
    STATUS           current
    DESCRIPTION
        "Entry for the cfprMgmtBackupPolicyFsmTable table."
    INDEX { cfprMgmtBackupPolicyFsmInstanceId }
    ::= { cfprMgmtBackupPolicyFsmTable 1 }

CfprMgmtBackupPolicyFsmEntry ::= SEQUENCE {
    cfprMgmtBackupPolicyFsmInstanceId                                CfprManagedObjectId,
    cfprMgmtBackupPolicyFsmDn                                        CfprManagedObjectDn,
    cfprMgmtBackupPolicyFsmRn                                        SnmpAdminString,
    cfprMgmtBackupPolicyFsmCompletionTime                            DateAndTime,
    cfprMgmtBackupPolicyFsmCurrentFsm                                CfprMgmtBackupPolicyFsmCurrentFsm,
    cfprMgmtBackupPolicyFsmDescrData                                 SnmpAdminString,
    cfprMgmtBackupPolicyFsmFsmStatus                                 CfprFsmFsmStageStatus,
    cfprMgmtBackupPolicyFsmProgress                                  Gauge32,
    cfprMgmtBackupPolicyFsmRmtErrCode                                Gauge32,
    cfprMgmtBackupPolicyFsmRmtErrDescr                               SnmpAdminString,
    cfprMgmtBackupPolicyFsmRmtRslt                                   CfprConditionRemoteInvRslt
}

cfprMgmtBackupPolicyFsmInstanceId OBJECT-TYPE
    SYNTAX       CfprManagedObjectId
    MAX-ACCESS   not-accessible
    STATUS       current
    DESCRIPTION
        "Instance identifier of the managed object."
    ::= { cfprMgmtBackupPolicyFsmEntry 1 }

cfprMgmtBackupPolicyFsmDn OBJECT-TYPE
    SYNTAX       CfprManagedObjectDn
    MAX-ACCESS   read-only
    STATUS       current
    DESCRIPTION
        "Cisco Firepower mgmt:BackupPolicyFsm:dn managed object property"
    ::= { cfprMgmtBackupPolicyFsmEntry 2 }

cfprMgmtBackupPolicyFsmRn OBJECT-TYPE
    SYNTAX       SnmpAdminString
    MAX-ACCESS   read-only
    STATUS       current
    DESCRIPTION
        "Cisco Firepower mgmt:BackupPolicyFsm:rn managed object property"
    ::= { cfprMgmtBackupPolicyFsmEntry 3 }

cfprMgmtBackupPolicyFsmCompletionTime OBJECT-TYPE
    SYNTAX       DateAndTime
    MAX-ACCESS   read-only
    STATUS       current
    DESCRIPTION
        "Cisco Firepower mgmt:BackupPolicyFsm:completionTime
        managed object property"
    ::= { cfprMgmtBackupPolicyFsmEntry 4 }

cfprMgmtBackupPolicyFsmCurrentFsm OBJECT-TYPE
    SYNTAX       CfprMgmtBackupPolicyFsmCurrentFsm
    MAX-ACCESS   read-only
    STATUS       current
    DESCRIPTION
        "Cisco Firepower mgmt:BackupPolicyFsm:currentFsm
        managed object property"
    ::= { cfprMgmtBackupPolicyFsmEntry 5 }

cfprMgmtBackupPolicyFsmDescrData OBJECT-TYPE
    SYNTAX       SnmpAdminString
    MAX-ACCESS   read-only
    STATUS       current
    DESCRIPTION
        "Cisco Firepower mgmt:BackupPolicyFsm:descr managed
        object property"
    ::= { cfprMgmtBackupPolicyFsmEntry 6 }

cfprMgmtBackupPolicyFsmFsmStatus OBJECT-TYPE
    SYNTAX       CfprFsmFsmStageStatus
    MAX-ACCESS   read-only
    STATUS       current
    DESCRIPTION
        "Cisco Firepower mgmt:BackupPolicyFsm:fsmStatus
        managed object property"
    ::= { cfprMgmtBackupPolicyFsmEntry 7 }

cfprMgmtBackupPolicyFsmProgress OBJECT-TYPE
    SYNTAX       Gauge32
    MAX-ACCESS   read-only
    STATUS       current
    DESCRIPTION
        "Cisco Firepower mgmt:BackupPolicyFsm:progress
        managed object property"
    ::= { cfprMgmtBackupPolicyFsmEntry 8 }

cfprMgmtBackupPolicyFsmRmtErrCode OBJECT-TYPE
    SYNTAX       Gauge32
    MAX-ACCESS   read-only
    STATUS       current
    DESCRIPTION
        "Cisco Firepower mgmt:BackupPolicyFsm:rmtErrCode
        managed object property"
    ::= { cfprMgmtBackupPolicyFsmEntry 9 }

cfprMgmtBackupPolicyFsmRmtErrDescr OBJECT-TYPE
    SYNTAX       SnmpAdminString
    MAX-ACCESS   read-only
    STATUS       current
    DESCRIPTION
        "Cisco Firepower mgmt:BackupPolicyFsm:rmtErrDescr
        managed object property"
    ::= { cfprMgmtBackupPolicyFsmEntry 10 }

cfprMgmtBackupPolicyFsmRmtRslt OBJECT-TYPE
    SYNTAX       CfprConditionRemoteInvRslt
    MAX-ACCESS   read-only
    STATUS       current
    DESCRIPTION
        "Cisco Firepower mgmt:BackupPolicyFsm:rmtRslt managed
        object property"
    ::= { cfprMgmtBackupPolicyFsmEntry 11 }

cfprMgmtBackupPolicyFsmStageTable OBJECT-TYPE
    SYNTAX           SEQUENCE OF CfprMgmtBackupPolicyFsmStageEntry
    MAX-ACCESS       not-accessible
    STATUS           current
    DESCRIPTION
        "Cisco Firepower mgmt:BackupPolicyFsmStage managed object table"
    ::= { cfprMgmtObjects 12 }

cfprMgmtBackupPolicyFsmStageEntry OBJECT-TYPE
    SYNTAX           CfprMgmtBackupPolicyFsmStageEntry
    MAX-ACCESS       not-accessible
    STATUS           current
    DESCRIPTION
        "Entry for the cfprMgmtBackupPolicyFsmStageTable table."
    INDEX { cfprMgmtBackupPolicyFsmStageInstanceId }
    ::= { cfprMgmtBackupPolicyFsmStageTable 1 }

CfprMgmtBackupPolicyFsmStageEntry ::= SEQUENCE {
    cfprMgmtBackupPolicyFsmStageInstanceId                           CfprManagedObjectId,
    cfprMgmtBackupPolicyFsmStageDn                                   CfprManagedObjectDn,
    cfprMgmtBackupPolicyFsmStageRn                                   SnmpAdminString,
    cfprMgmtBackupPolicyFsmStageDescrData                            SnmpAdminString,
    cfprMgmtBackupPolicyFsmStageLastUpdateTime                       DateAndTime,
    cfprMgmtBackupPolicyFsmStageName                                 CfprMgmtBackupPolicyFsmStageName,
    cfprMgmtBackupPolicyFsmStageOrder                                Gauge32,
    cfprMgmtBackupPolicyFsmStageRetry                                Gauge32,
    cfprMgmtBackupPolicyFsmStageStageStatus                          CfprFsmFsmStageStatus
}

cfprMgmtBackupPolicyFsmStageInstanceId OBJECT-TYPE
    SYNTAX       CfprManagedObjectId
    MAX-ACCESS   not-accessible
    STATUS       current
    DESCRIPTION
        "Instance identifier of the managed object."
    ::= { cfprMgmtBackupPolicyFsmStageEntry 1 }

cfprMgmtBackupPolicyFsmStageDn OBJECT-TYPE
    SYNTAX       CfprManagedObjectDn
    MAX-ACCESS   read-only
    STATUS       current
    DESCRIPTION
        "Cisco Firepower mgmt:BackupPolicyFsmStage:dn managed
        object property"
    ::= { cfprMgmtBackupPolicyFsmStageEntry 2 }

cfprMgmtBackupPolicyFsmStageRn OBJECT-TYPE
    SYNTAX       SnmpAdminString
    MAX-ACCESS   read-only
    STATUS       current
    DESCRIPTION
        "Cisco Firepower mgmt:BackupPolicyFsmStage:rn managed
        object property"
    ::= { cfprMgmtBackupPolicyFsmStageEntry 3 }

cfprMgmtBackupPolicyFsmStageDescrData OBJECT-TYPE
    SYNTAX       SnmpAdminString
    MAX-ACCESS   read-only
    STATUS       current
    DESCRIPTION
        "Cisco Firepower mgmt:BackupPolicyFsmStage:descr
        managed object property"
    ::= { cfprMgmtBackupPolicyFsmStageEntry 4 }

cfprMgmtBackupPolicyFsmStageLastUpdateTime OBJECT-TYPE
    SYNTAX       DateAndTime
    MAX-ACCESS   read-only
    STATUS       current
    DESCRIPTION
        "Cisco Firepower mgmt:BackupPolicyFsmStage:lastUpdateTime
        managed object property"
    ::= { cfprMgmtBackupPolicyFsmStageEntry 5 }

cfprMgmtBackupPolicyFsmStageName OBJECT-TYPE
    SYNTAX       CfprMgmtBackupPolicyFsmStageName
    MAX-ACCESS   read-only
    STATUS       current
    DESCRIPTION
        "Cisco Firepower mgmt:BackupPolicyFsmStage:name
        managed object property"
    ::= { cfprMgmtBackupPolicyFsmStageEntry 6 }

cfprMgmtBackupPolicyFsmStageOrder OBJECT-TYPE
    SYNTAX       Gauge32
    MAX-ACCESS   read-only
    STATUS       current
    DESCRIPTION
        "Cisco Firepower mgmt:BackupPolicyFsmStage:order
        managed object property"
    ::= { cfprMgmtBackupPolicyFsmStageEntry 7 }

cfprMgmtBackupPolicyFsmStageRetry OBJECT-TYPE
    SYNTAX       Gauge32
    MAX-ACCESS   read-only
    STATUS       current
    DESCRIPTION
        "Cisco Firepower mgmt:BackupPolicyFsmStage:retry
        managed object property"
    ::= { cfprMgmtBackupPolicyFsmStageEntry 8 }

cfprMgmtBackupPolicyFsmStageStageStatus OBJECT-TYPE
    SYNTAX       CfprFsmFsmStageStatus
    MAX-ACCESS   read-only
    STATUS       current
    DESCRIPTION
        "Cisco Firepower mgmt:BackupPolicyFsmStage:stageStatus
        managed object property"
    ::= { cfprMgmtBackupPolicyFsmStageEntry 9 }

cfprMgmtCfgExportPolicyTable OBJECT-TYPE
    SYNTAX           SEQUENCE OF CfprMgmtCfgExportPolicyEntry
    MAX-ACCESS       not-accessible
    STATUS           current
    DESCRIPTION
        "Cisco Firepower mgmt:CfgExportPolicy managed object table"
    ::= { cfprMgmtObjects 13 }

cfprMgmtCfgExportPolicyEntry OBJECT-TYPE
    SYNTAX           CfprMgmtCfgExportPolicyEntry
    MAX-ACCESS       not-accessible
    STATUS           current
    DESCRIPTION
        "Entry for the cfprMgmtCfgExportPolicyTable table."
    INDEX { cfprMgmtCfgExportPolicyInstanceId }
    ::= { cfprMgmtCfgExportPolicyTable 1 }

CfprMgmtCfgExportPolicyEntry ::= SEQUENCE {
    cfprMgmtCfgExportPolicyInstanceId                                CfprManagedObjectId,
    cfprMgmtCfgExportPolicyDn                                        CfprManagedObjectDn,
    cfprMgmtCfgExportPolicyRn                                        SnmpAdminString,
    cfprMgmtCfgExportPolicyAdminState                                CfprMgmtExportPolicyAdminState,
    cfprMgmtCfgExportPolicyDescr                                     SnmpAdminString,
    cfprMgmtCfgExportPolicyFsmDescr                                  SnmpAdminString,
    cfprMgmtCfgExportPolicyFsmPrev                                   SnmpAdminString,
    cfprMgmtCfgExportPolicyFsmProgr                                  Gauge32,
    cfprMgmtCfgExportPolicyFsmRmtInvErrCode                          Gauge32,
    cfprMgmtCfgExportPolicyFsmRmtInvErrDescr                         SnmpAdminString,
    cfprMgmtCfgExportPolicyFsmRmtInvRslt                             CfprConditionRemoteInvRslt,
    cfprMgmtCfgExportPolicyFsmStageDescr                             SnmpAdminString,
    cfprMgmtCfgExportPolicyFsmStamp                                  DateAndTime,
    cfprMgmtCfgExportPolicyFsmStatus                                 SnmpAdminString,
    cfprMgmtCfgExportPolicyFsmTry                                    Gauge32,
    cfprMgmtCfgExportPolicyHost                                      SnmpAdminString,
    cfprMgmtCfgExportPolicyIntId                                     SnmpAdminString,
    cfprMgmtCfgExportPolicyLastBackup                                DateAndTime,
    cfprMgmtCfgExportPolicyMaxFiles                                  Gauge32,
    cfprMgmtCfgExportPolicyName                                      SnmpAdminString,
    cfprMgmtCfgExportPolicyPolicyLevel                               Gauge32,
    cfprMgmtCfgExportPolicyPolicyOwner                               CfprPolicyPolicyOwner,
    cfprMgmtCfgExportPolicyProto                                     CfprMgmtExportPolicyProto,
    cfprMgmtCfgExportPolicyPwd                                       SnmpAdminString,
    cfprMgmtCfgExportPolicyRemoteFile                                SnmpAdminString,
    cfprMgmtCfgExportPolicySchedule                                  CfprMgmtBackupInterval,
    cfprMgmtCfgExportPolicyUser                                      SnmpAdminString,
    cfprMgmtCfgExportPolicyPort                                      Gauge32
}

cfprMgmtCfgExportPolicyInstanceId OBJECT-TYPE
    SYNTAX       CfprManagedObjectId
    MAX-ACCESS   not-accessible
    STATUS       current
    DESCRIPTION
        "Instance identifier of the managed object."
    ::= { cfprMgmtCfgExportPolicyEntry 1 }

cfprMgmtCfgExportPolicyDn OBJECT-TYPE
    SYNTAX       CfprManagedObjectDn
    MAX-ACCESS   read-only
    STATUS       current
    DESCRIPTION
        "Cisco Firepower mgmt:CfgExportPolicy:dn managed object property"
    ::= { cfprMgmtCfgExportPolicyEntry 2 }

cfprMgmtCfgExportPolicyRn OBJECT-TYPE
    SYNTAX       SnmpAdminString
    MAX-ACCESS   read-only
    STATUS       current
    DESCRIPTION
        "Cisco Firepower mgmt:CfgExportPolicy:rn managed object property"
    ::= { cfprMgmtCfgExportPolicyEntry 3 }

cfprMgmtCfgExportPolicyAdminState OBJECT-TYPE
    SYNTAX       CfprMgmtExportPolicyAdminState
    MAX-ACCESS   read-only
    STATUS       current
    DESCRIPTION
        "Cisco Firepower mgmt:CfgExportPolicy:adminState
        managed object property"
    ::= { cfprMgmtCfgExportPolicyEntry 4 }

cfprMgmtCfgExportPolicyDescr OBJECT-TYPE
    SYNTAX       SnmpAdminString
    MAX-ACCESS   read-only
    STATUS       current
    DESCRIPTION
        "Cisco Firepower mgmt:CfgExportPolicy:descr managed
        object property"
    ::= { cfprMgmtCfgExportPolicyEntry 5 }

cfprMgmtCfgExportPolicyFsmDescr OBJECT-TYPE
    SYNTAX       SnmpAdminString
    MAX-ACCESS   read-only
    STATUS       current
    DESCRIPTION
        "Cisco Firepower mgmt:CfgExportPolicy:fsmDescr
        managed object property"
    ::= { cfprMgmtCfgExportPolicyEntry 6 }

cfprMgmtCfgExportPolicyFsmPrev OBJECT-TYPE
    SYNTAX       SnmpAdminString
    MAX-ACCESS   read-only
    STATUS       current
    DESCRIPTION
        "Cisco Firepower mgmt:CfgExportPolicy:fsmPrev managed
        object property"
    ::= { cfprMgmtCfgExportPolicyEntry 7 }

cfprMgmtCfgExportPolicyFsmProgr OBJECT-TYPE
    SYNTAX       Gauge32
    MAX-ACCESS   read-only
    STATUS       current
    DESCRIPTION
        "Cisco Firepower mgmt:CfgExportPolicy:fsmProgr
        managed object property"
    ::= { cfprMgmtCfgExportPolicyEntry 8 }

cfprMgmtCfgExportPolicyFsmRmtInvErrCode OBJECT-TYPE
    SYNTAX       Gauge32
    MAX-ACCESS   read-only
    STATUS       current
    DESCRIPTION
        "Cisco Firepower mgmt:CfgExportPolicy:fsmRmtInvErrCode
        managed object property"
    ::= { cfprMgmtCfgExportPolicyEntry 9 }

cfprMgmtCfgExportPolicyFsmRmtInvErrDescr OBJECT-TYPE
    SYNTAX       SnmpAdminString
    MAX-ACCESS   read-only
    STATUS       current
    DESCRIPTION
        "Cisco Firepower mgmt:CfgExportPolicy:fsmRmtInvErrDescr
        managed object property"
    ::= { cfprMgmtCfgExportPolicyEntry 10 }

cfprMgmtCfgExportPolicyFsmRmtInvRslt OBJECT-TYPE
    SYNTAX       CfprConditionRemoteInvRslt
    MAX-ACCESS   read-only
    STATUS       current
    DESCRIPTION
        "Cisco Firepower mgmt:CfgExportPolicy:fsmRmtInvRslt
        managed object property"
    ::= { cfprMgmtCfgExportPolicyEntry 11 }

cfprMgmtCfgExportPolicyFsmStageDescr OBJECT-TYPE
    SYNTAX       SnmpAdminString
    MAX-ACCESS   read-only
    STATUS       current
    DESCRIPTION
        "Cisco Firepower mgmt:CfgExportPolicy:fsmStageDescr
        managed object property"
    ::= { cfprMgmtCfgExportPolicyEntry 12 }

cfprMgmtCfgExportPolicyFsmStamp OBJECT-TYPE
    SYNTAX       DateAndTime
    MAX-ACCESS   read-only
    STATUS       current
    DESCRIPTION
        "Cisco Firepower mgmt:CfgExportPolicy:fsmStamp
        managed object property"
    ::= { cfprMgmtCfgExportPolicyEntry 13 }

cfprMgmtCfgExportPolicyFsmStatus OBJECT-TYPE
    SYNTAX       SnmpAdminString
    MAX-ACCESS   read-only
    STATUS       current
    DESCRIPTION
        "Cisco Firepower mgmt:CfgExportPolicy:fsmStatus
        managed object property"
    ::= { cfprMgmtCfgExportPolicyEntry 14 }

cfprMgmtCfgExportPolicyFsmTry OBJECT-TYPE
    SYNTAX       Gauge32
    MAX-ACCESS   read-only
    STATUS       current
    DESCRIPTION
        "Cisco Firepower mgmt:CfgExportPolicy:fsmTry managed
        object property"
    ::= { cfprMgmtCfgExportPolicyEntry 15 }

cfprMgmtCfgExportPolicyHost OBJECT-TYPE
    SYNTAX       SnmpAdminString
    MAX-ACCESS   read-only
    STATUS       current
    DESCRIPTION
        "Cisco Firepower mgmt:CfgExportPolicy:host managed
        object property"
    ::= { cfprMgmtCfgExportPolicyEntry 16 }

cfprMgmtCfgExportPolicyIntId OBJECT-TYPE
    SYNTAX       SnmpAdminString
    MAX-ACCESS   read-only
    STATUS       current
    DESCRIPTION
        "Cisco Firepower mgmt:CfgExportPolicy:intId managed
        object property"
    ::= { cfprMgmtCfgExportPolicyEntry 17 }

cfprMgmtCfgExportPolicyLastBackup OBJECT-TYPE
    SYNTAX       DateAndTime
    MAX-ACCESS   read-only
    STATUS       current
    DESCRIPTION
        "Cisco Firepower mgmt:CfgExportPolicy:lastBackup
        managed object property"
    ::= { cfprMgmtCfgExportPolicyEntry 18 }

cfprMgmtCfgExportPolicyMaxFiles OBJECT-TYPE
    SYNTAX       Gauge32
    MAX-ACCESS   read-only
    STATUS       current
    DESCRIPTION
        "Cisco Firepower mgmt:CfgExportPolicy:maxFiles
        managed object property"
    ::= { cfprMgmtCfgExportPolicyEntry 19 }

cfprMgmtCfgExportPolicyName OBJECT-TYPE
    SYNTAX       SnmpAdminString
    MAX-ACCESS   read-only
    STATUS       current
    DESCRIPTION
        "Cisco Firepower mgmt:CfgExportPolicy:name managed
        object property"
    ::= { cfprMgmtCfgExportPolicyEntry 20 }

cfprMgmtCfgExportPolicyPolicyLevel OBJECT-TYPE
    SYNTAX       Gauge32
    MAX-ACCESS   read-only
    STATUS       current
    DESCRIPTION
        "Cisco Firepower mgmt:CfgExportPolicy:policyLevel
        managed object property"
    ::= { cfprMgmtCfgExportPolicyEntry 21 }

cfprMgmtCfgExportPolicyPolicyOwner OBJECT-TYPE
    SYNTAX       CfprPolicyPolicyOwner
    MAX-ACCESS   read-only
    STATUS       current
    DESCRIPTION
        "Cisco Firepower mgmt:CfgExportPolicy:policyOwner
        managed object property"
    ::= { cfprMgmtCfgExportPolicyEntry 22 }

cfprMgmtCfgExportPolicyProto OBJECT-TYPE
    SYNTAX       CfprMgmtExportPolicyProto
    MAX-ACCESS   read-only
    STATUS       current
    DESCRIPTION
        "Cisco Firepower mgmt:CfgExportPolicy:proto managed
        object property"
    ::= { cfprMgmtCfgExportPolicyEntry 23 }

cfprMgmtCfgExportPolicyPwd OBJECT-TYPE
    SYNTAX       SnmpAdminString
    MAX-ACCESS   read-only
    STATUS       current
    DESCRIPTION
        "Cisco Firepower mgmt:CfgExportPolicy:pwd managed object property"
    ::= { cfprMgmtCfgExportPolicyEntry 24 }

cfprMgmtCfgExportPolicyRemoteFile OBJECT-TYPE
    SYNTAX       SnmpAdminString
    MAX-ACCESS   read-only
    STATUS       current
    DESCRIPTION
        "Cisco Firepower mgmt:CfgExportPolicy:remoteFile
        managed object property"
    ::= { cfprMgmtCfgExportPolicyEntry 25 }

cfprMgmtCfgExportPolicySchedule OBJECT-TYPE
    SYNTAX       CfprMgmtBackupInterval
    MAX-ACCESS   read-only
    STATUS       current
    DESCRIPTION
        "Cisco Firepower mgmt:CfgExportPolicy:schedule
        managed object property"
    ::= { cfprMgmtCfgExportPolicyEntry 26 }

cfprMgmtCfgExportPolicyUser OBJECT-TYPE
    SYNTAX       SnmpAdminString
    MAX-ACCESS   read-only
    STATUS       current
    DESCRIPTION
        "Cisco Firepower mgmt:CfgExportPolicy:user managed
        object property"
    ::= { cfprMgmtCfgExportPolicyEntry 27 }

cfprMgmtCfgExportPolicyPort OBJECT-TYPE
    SYNTAX       Gauge32
    MAX-ACCESS   read-only
    STATUS       current
    DESCRIPTION
        "Cisco Firepower mgmt:CfgExportPolicy:port managed
        object property"
    ::= { cfprMgmtCfgExportPolicyEntry 28 }

cfprMgmtCfgExportPolicyFsmTable OBJECT-TYPE
    SYNTAX           SEQUENCE OF CfprMgmtCfgExportPolicyFsmEntry
    MAX-ACCESS       not-accessible
    STATUS           current
    DESCRIPTION
        "Cisco Firepower mgmt:CfgExportPolicyFsm managed object table"
    ::= { cfprMgmtObjects 14 }

cfprMgmtCfgExportPolicyFsmEntry OBJECT-TYPE
    SYNTAX           CfprMgmtCfgExportPolicyFsmEntry
    MAX-ACCESS       not-accessible
    STATUS           current
    DESCRIPTION
        "Entry for the cfprMgmtCfgExportPolicyFsmTable table."
    INDEX { cfprMgmtCfgExportPolicyFsmInstanceId }
    ::= { cfprMgmtCfgExportPolicyFsmTable 1 }

CfprMgmtCfgExportPolicyFsmEntry ::= SEQUENCE {
    cfprMgmtCfgExportPolicyFsmInstanceId                             CfprManagedObjectId,
    cfprMgmtCfgExportPolicyFsmDn                                     CfprManagedObjectDn,
    cfprMgmtCfgExportPolicyFsmRn                                     SnmpAdminString,
    cfprMgmtCfgExportPolicyFsmCompletionTime                         DateAndTime,
    cfprMgmtCfgExportPolicyFsmCurrentFsm                             CfprMgmtCfgExportPolicyFsmCurrentFsm,
    cfprMgmtCfgExportPolicyFsmDescrData                              SnmpAdminString,
    cfprMgmtCfgExportPolicyFsmFsmStatus                              CfprFsmFsmStageStatus,
    cfprMgmtCfgExportPolicyFsmProgress                               Gauge32,
    cfprMgmtCfgExportPolicyFsmRmtErrCode                             Gauge32,
    cfprMgmtCfgExportPolicyFsmRmtErrDescr                            SnmpAdminString,
    cfprMgmtCfgExportPolicyFsmRmtRslt                                CfprConditionRemoteInvRslt
}

cfprMgmtCfgExportPolicyFsmInstanceId OBJECT-TYPE
    SYNTAX       CfprManagedObjectId
    MAX-ACCESS   not-accessible
    STATUS       current
    DESCRIPTION
        "Instance identifier of the managed object."
    ::= { cfprMgmtCfgExportPolicyFsmEntry 1 }

cfprMgmtCfgExportPolicyFsmDn OBJECT-TYPE
    SYNTAX       CfprManagedObjectDn
    MAX-ACCESS   read-only
    STATUS       current
    DESCRIPTION
        "Cisco Firepower mgmt:CfgExportPolicyFsm:dn managed
        object property"
    ::= { cfprMgmtCfgExportPolicyFsmEntry 2 }

cfprMgmtCfgExportPolicyFsmRn OBJECT-TYPE
    SYNTAX       SnmpAdminString
    MAX-ACCESS   read-only
    STATUS       current
    DESCRIPTION
        "Cisco Firepower mgmt:CfgExportPolicyFsm:rn managed
        object property"
    ::= { cfprMgmtCfgExportPolicyFsmEntry 3 }

cfprMgmtCfgExportPolicyFsmCompletionTime OBJECT-TYPE
    SYNTAX       DateAndTime
    MAX-ACCESS   read-only
    STATUS       current
    DESCRIPTION
        "Cisco Firepower mgmt:CfgExportPolicyFsm:completionTime
        managed object property"
    ::= { cfprMgmtCfgExportPolicyFsmEntry 4 }

cfprMgmtCfgExportPolicyFsmCurrentFsm OBJECT-TYPE
    SYNTAX       CfprMgmtCfgExportPolicyFsmCurrentFsm
    MAX-ACCESS   read-only
    STATUS       current
    DESCRIPTION
        "Cisco Firepower mgmt:CfgExportPolicyFsm:currentFsm
        managed object property"
    ::= { cfprMgmtCfgExportPolicyFsmEntry 5 }

cfprMgmtCfgExportPolicyFsmDescrData OBJECT-TYPE
    SYNTAX       SnmpAdminString
    MAX-ACCESS   read-only
    STATUS       current
    DESCRIPTION
        "Cisco Firepower mgmt:CfgExportPolicyFsm:descr
        managed object property"
    ::= { cfprMgmtCfgExportPolicyFsmEntry 6 }

cfprMgmtCfgExportPolicyFsmFsmStatus OBJECT-TYPE
    SYNTAX       CfprFsmFsmStageStatus
    MAX-ACCESS   read-only
    STATUS       current
    DESCRIPTION
        "Cisco Firepower mgmt:CfgExportPolicyFsm:fsmStatus
        managed object property"
    ::= { cfprMgmtCfgExportPolicyFsmEntry 7 }

cfprMgmtCfgExportPolicyFsmProgress OBJECT-TYPE
    SYNTAX       Gauge32
    MAX-ACCESS   read-only
    STATUS       current
    DESCRIPTION
        "Cisco Firepower mgmt:CfgExportPolicyFsm:progress
        managed object property"
    ::= { cfprMgmtCfgExportPolicyFsmEntry 8 }

cfprMgmtCfgExportPolicyFsmRmtErrCode OBJECT-TYPE
    SYNTAX       Gauge32
    MAX-ACCESS   read-only
    STATUS       current
    DESCRIPTION
        "Cisco Firepower mgmt:CfgExportPolicyFsm:rmtErrCode
        managed object property"
    ::= { cfprMgmtCfgExportPolicyFsmEntry 9 }

cfprMgmtCfgExportPolicyFsmRmtErrDescr OBJECT-TYPE
    SYNTAX       SnmpAdminString
    MAX-ACCESS   read-only
    STATUS       current
    DESCRIPTION
        "Cisco Firepower mgmt:CfgExportPolicyFsm:rmtErrDescr
        managed object property"
    ::= { cfprMgmtCfgExportPolicyFsmEntry 10 }

cfprMgmtCfgExportPolicyFsmRmtRslt OBJECT-TYPE
    SYNTAX       CfprConditionRemoteInvRslt
    MAX-ACCESS   read-only
    STATUS       current
    DESCRIPTION
        "Cisco Firepower mgmt:CfgExportPolicyFsm:rmtRslt
        managed object property"
    ::= { cfprMgmtCfgExportPolicyFsmEntry 11 }

cfprMgmtCfgExportPolicyFsmStageTable OBJECT-TYPE
    SYNTAX           SEQUENCE OF CfprMgmtCfgExportPolicyFsmStageEntry
    MAX-ACCESS       not-accessible
    STATUS           current
    DESCRIPTION
        "Cisco Firepower mgmt:CfgExportPolicyFsmStage managed
        object table"
    ::= { cfprMgmtObjects 15 }

cfprMgmtCfgExportPolicyFsmStageEntry OBJECT-TYPE
    SYNTAX           CfprMgmtCfgExportPolicyFsmStageEntry
    MAX-ACCESS       not-accessible
    STATUS           current
    DESCRIPTION
        "Entry for the cfprMgmtCfgExportPolicyFsmStageTable table."
    INDEX { cfprMgmtCfgExportPolicyFsmStageInstanceId }
    ::= { cfprMgmtCfgExportPolicyFsmStageTable 1 }

CfprMgmtCfgExportPolicyFsmStageEntry ::= SEQUENCE {
    cfprMgmtCfgExportPolicyFsmStageInstanceId                        CfprManagedObjectId,
    cfprMgmtCfgExportPolicyFsmStageDn                                CfprManagedObjectDn,
    cfprMgmtCfgExportPolicyFsmStageRn                                SnmpAdminString,
    cfprMgmtCfgExportPolicyFsmStageDescrData                         SnmpAdminString,
    cfprMgmtCfgExportPolicyFsmStageLastUpdateTime                    DateAndTime,
    cfprMgmtCfgExportPolicyFsmStageName                              CfprMgmtCfgExportPolicyFsmStageName,
    cfprMgmtCfgExportPolicyFsmStageOrder                             Gauge32,
    cfprMgmtCfgExportPolicyFsmStageRetry                             Gauge32,
    cfprMgmtCfgExportPolicyFsmStageStageStatus                       CfprFsmFsmStageStatus
}

cfprMgmtCfgExportPolicyFsmStageInstanceId OBJECT-TYPE
    SYNTAX       CfprManagedObjectId
    MAX-ACCESS   not-accessible
    STATUS       current
    DESCRIPTION
        "Instance identifier of the managed object."
    ::= { cfprMgmtCfgExportPolicyFsmStageEntry 1 }

cfprMgmtCfgExportPolicyFsmStageDn OBJECT-TYPE
    SYNTAX       CfprManagedObjectDn
    MAX-ACCESS   read-only
    STATUS       current
    DESCRIPTION
        "Cisco Firepower mgmt:CfgExportPolicyFsmStage:dn
        managed object property"
    ::= { cfprMgmtCfgExportPolicyFsmStageEntry 2 }

cfprMgmtCfgExportPolicyFsmStageRn OBJECT-TYPE
    SYNTAX       SnmpAdminString
    MAX-ACCESS   read-only
    STATUS       current
    DESCRIPTION
        "Cisco Firepower mgmt:CfgExportPolicyFsmStage:rn
        managed object property"
    ::= { cfprMgmtCfgExportPolicyFsmStageEntry 3 }

cfprMgmtCfgExportPolicyFsmStageDescrData OBJECT-TYPE
    SYNTAX       SnmpAdminString
    MAX-ACCESS   read-only
    STATUS       current
    DESCRIPTION
        "Cisco Firepower mgmt:CfgExportPolicyFsmStage:descr
        managed object property"
    ::= { cfprMgmtCfgExportPolicyFsmStageEntry 4 }

cfprMgmtCfgExportPolicyFsmStageLastUpdateTime OBJECT-TYPE
    SYNTAX       DateAndTime
    MAX-ACCESS   read-only
    STATUS       current
    DESCRIPTION
        "Cisco Firepower mgmt:CfgExportPolicyFsmStage:lastUpdateTime
        managed object property"
    ::= { cfprMgmtCfgExportPolicyFsmStageEntry 5 }

cfprMgmtCfgExportPolicyFsmStageName OBJECT-TYPE
    SYNTAX       CfprMgmtCfgExportPolicyFsmStageName
    MAX-ACCESS   read-only
    STATUS       current
    DESCRIPTION
        "Cisco Firepower mgmt:CfgExportPolicyFsmStage:name
        managed object property"
    ::= { cfprMgmtCfgExportPolicyFsmStageEntry 6 }

cfprMgmtCfgExportPolicyFsmStageOrder OBJECT-TYPE
    SYNTAX       Gauge32
    MAX-ACCESS   read-only
    STATUS       current
    DESCRIPTION
        "Cisco Firepower mgmt:CfgExportPolicyFsmStage:order
        managed object property"
    ::= { cfprMgmtCfgExportPolicyFsmStageEntry 7 }

cfprMgmtCfgExportPolicyFsmStageRetry OBJECT-TYPE
    SYNTAX       Gauge32
    MAX-ACCESS   read-only
    STATUS       current
    DESCRIPTION
        "Cisco Firepower mgmt:CfgExportPolicyFsmStage:retry
        managed object property"
    ::= { cfprMgmtCfgExportPolicyFsmStageEntry 8 }

cfprMgmtCfgExportPolicyFsmStageStageStatus OBJECT-TYPE
    SYNTAX       CfprFsmFsmStageStatus
    MAX-ACCESS   read-only
    STATUS       current
    DESCRIPTION
        "Cisco Firepower mgmt:CfgExportPolicyFsmStage:stageStatus
        managed object property"
    ::= { cfprMgmtCfgExportPolicyFsmStageEntry 9 }

cfprMgmtCimcSecureBootTable OBJECT-TYPE
    SYNTAX           SEQUENCE OF CfprMgmtCimcSecureBootEntry
    MAX-ACCESS       not-accessible
    STATUS           current
    DESCRIPTION
        "Cisco Firepower mgmt:CimcSecureBoot managed object table"
    ::= { cfprMgmtObjects 16 }

cfprMgmtCimcSecureBootEntry OBJECT-TYPE
    SYNTAX           CfprMgmtCimcSecureBootEntry
    MAX-ACCESS       not-accessible
    STATUS           current
    DESCRIPTION
        "Entry for the cfprMgmtCimcSecureBootTable table."
    INDEX { cfprMgmtCimcSecureBootInstanceId }
    ::= { cfprMgmtCimcSecureBootTable 1 }

CfprMgmtCimcSecureBootEntry ::= SEQUENCE {
    cfprMgmtCimcSecureBootInstanceId                                 CfprManagedObjectId,
    cfprMgmtCimcSecureBootDn                                         CfprManagedObjectDn,
    cfprMgmtCimcSecureBootRn                                         SnmpAdminString,
    cfprMgmtCimcSecureBootAdminState                                 CfprMgmtCimcSecureBootAdminState,
    cfprMgmtCimcSecureBootOperState                                  CfprMgmtSecureBootOperState
}

cfprMgmtCimcSecureBootInstanceId OBJECT-TYPE
    SYNTAX       CfprManagedObjectId
    MAX-ACCESS   not-accessible
    STATUS       current
    DESCRIPTION
        "Instance identifier of the managed object."
    ::= { cfprMgmtCimcSecureBootEntry 1 }

cfprMgmtCimcSecureBootDn OBJECT-TYPE
    SYNTAX       CfprManagedObjectDn
    MAX-ACCESS   read-only
    STATUS       current
    DESCRIPTION
        "Cisco Firepower mgmt:CimcSecureBoot:dn managed object property"
    ::= { cfprMgmtCimcSecureBootEntry 2 }

cfprMgmtCimcSecureBootRn OBJECT-TYPE
    SYNTAX       SnmpAdminString
    MAX-ACCESS   read-only
    STATUS       current
    DESCRIPTION
        "Cisco Firepower mgmt:CimcSecureBoot:rn managed object property"
    ::= { cfprMgmtCimcSecureBootEntry 3 }

cfprMgmtCimcSecureBootAdminState OBJECT-TYPE
    SYNTAX       CfprMgmtCimcSecureBootAdminState
    MAX-ACCESS   read-only
    STATUS       current
    DESCRIPTION
        "Cisco Firepower mgmt:CimcSecureBoot:adminState
        managed object property"
    ::= { cfprMgmtCimcSecureBootEntry 4 }

cfprMgmtCimcSecureBootOperState OBJECT-TYPE
    SYNTAX       CfprMgmtSecureBootOperState
    MAX-ACCESS   read-only
    STATUS       current
    DESCRIPTION
        "Cisco Firepower mgmt:CimcSecureBoot:operState
        managed object property"
    ::= { cfprMgmtCimcSecureBootEntry 5 }

cfprMgmtConnectionTable OBJECT-TYPE
    SYNTAX           SEQUENCE OF CfprMgmtConnectionEntry
    MAX-ACCESS       not-accessible
    STATUS           current
    DESCRIPTION
        "Cisco Firepower mgmt:Connection managed object table"
    ::= { cfprMgmtObjects 17 }

cfprMgmtConnectionEntry OBJECT-TYPE
    SYNTAX           CfprMgmtConnectionEntry
    MAX-ACCESS       not-accessible
    STATUS           current
    DESCRIPTION
        "Entry for the cfprMgmtConnectionTable table."
    INDEX { cfprMgmtConnectionInstanceId }
    ::= { cfprMgmtConnectionTable 1 }

CfprMgmtConnectionEntry ::= SEQUENCE {
    cfprMgmtConnectionInstanceId                                     CfprManagedObjectId,
    cfprMgmtConnectionDn                                             CfprManagedObjectDn,
    cfprMgmtConnectionRn                                             SnmpAdminString,
    cfprMgmtConnectionAck                                            CfprMgmtConnectionState,
    cfprMgmtConnectionOperState                                      CfprMgmtConnectionState,
    cfprMgmtConnectionType                                           CfprMgmtSource
}

cfprMgmtConnectionInstanceId OBJECT-TYPE
    SYNTAX       CfprManagedObjectId
    MAX-ACCESS   not-accessible
    STATUS       current
    DESCRIPTION
        "Instance identifier of the managed object."
    ::= { cfprMgmtConnectionEntry 1 }

cfprMgmtConnectionDn OBJECT-TYPE
    SYNTAX       CfprManagedObjectDn
    MAX-ACCESS   read-only
    STATUS       current
    DESCRIPTION
        "Cisco Firepower mgmt:Connection:dn managed object property"
    ::= { cfprMgmtConnectionEntry 2 }

cfprMgmtConnectionRn OBJECT-TYPE
    SYNTAX       SnmpAdminString
    MAX-ACCESS   read-only
    STATUS       current
    DESCRIPTION
        "Cisco Firepower mgmt:Connection:rn managed object property"
    ::= { cfprMgmtConnectionEntry 3 }

cfprMgmtConnectionAck OBJECT-TYPE
    SYNTAX       CfprMgmtConnectionState
    MAX-ACCESS   read-only
    STATUS       current
    DESCRIPTION
        "Cisco Firepower mgmt:Connection:ack managed object property"
    ::= { cfprMgmtConnectionEntry 4 }

cfprMgmtConnectionOperState OBJECT-TYPE
    SYNTAX       CfprMgmtConnectionState
    MAX-ACCESS   read-only
    STATUS       current
    DESCRIPTION
        "Cisco Firepower mgmt:Connection:operState managed
        object property"
    ::= { cfprMgmtConnectionEntry 5 }

cfprMgmtConnectionType OBJECT-TYPE
    SYNTAX       CfprMgmtSource
    MAX-ACCESS   read-only
    STATUS       current
    DESCRIPTION
        "Cisco Firepower mgmt:Connection:type managed object property"
    ::= { cfprMgmtConnectionEntry 6 }

cfprMgmtControllerTable OBJECT-TYPE
    SYNTAX           SEQUENCE OF CfprMgmtControllerEntry
    MAX-ACCESS       not-accessible
    STATUS           current
    DESCRIPTION
        "Cisco Firepower mgmt:Controller managed object table"
    ::= { cfprMgmtObjects 18 }

cfprMgmtControllerEntry OBJECT-TYPE
    SYNTAX           CfprMgmtControllerEntry
    MAX-ACCESS       not-accessible
    STATUS           current
    DESCRIPTION
        "Entry for the cfprMgmtControllerTable table."
    INDEX { cfprMgmtControllerInstanceId }
    ::= { cfprMgmtControllerTable 1 }

CfprMgmtControllerEntry ::= SEQUENCE {
    cfprMgmtControllerInstanceId                                     CfprManagedObjectId,
    cfprMgmtControllerDn                                             CfprManagedObjectDn,
    cfprMgmtControllerRn                                             SnmpAdminString,
    cfprMgmtControllerDimmBlacklistingOperState                      CfprMgmtDimmBlacklistingOperState,
    cfprMgmtControllerFsmDescr                                       SnmpAdminString,
    cfprMgmtControllerFsmFlags                                       SnmpAdminString,
    cfprMgmtControllerFsmPrev                                        SnmpAdminString,
    cfprMgmtControllerFsmProgr                                       Gauge32,
    cfprMgmtControllerFsmRmtInvErrCode                               Gauge32,
    cfprMgmtControllerFsmRmtInvErrDescr                              SnmpAdminString,
    cfprMgmtControllerFsmRmtInvRslt                                  CfprConditionRemoteInvRslt,
    cfprMgmtControllerFsmStageDescr                                  SnmpAdminString,
    cfprMgmtControllerFsmStamp                                       DateAndTime,
    cfprMgmtControllerFsmStatus                                      SnmpAdminString,
    cfprMgmtControllerFsmTry                                         Gauge32,
    cfprMgmtControllerGuid                                           SnmpAdminString,
    cfprMgmtControllerModel                                          SnmpAdminString,
    cfprMgmtControllerOperConn                                       SnmpAdminString,
    cfprMgmtControllerRevision                                       SnmpAdminString,
    cfprMgmtControllerSerial                                         SnmpAdminString,
    cfprMgmtControllerStorageOobInterfaceSupported                   TruthValue,
    cfprMgmtControllerStorageSubsystemState                          CfprMgmtStorageSubsystemState,
    cfprMgmtControllerSubject                                        CfprMgmtSubject,
    cfprMgmtControllerVendor                                         SnmpAdminString
}

cfprMgmtControllerInstanceId OBJECT-TYPE
    SYNTAX       CfprManagedObjectId
    MAX-ACCESS   not-accessible
    STATUS       current
    DESCRIPTION
        "Instance identifier of the managed object."
    ::= { cfprMgmtControllerEntry 1 }

cfprMgmtControllerDn OBJECT-TYPE
    SYNTAX       CfprManagedObjectDn
    MAX-ACCESS   read-only
    STATUS       current
    DESCRIPTION
        "Cisco Firepower mgmt:Controller:dn managed object property"
    ::= { cfprMgmtControllerEntry 2 }

cfprMgmtControllerRn OBJECT-TYPE
    SYNTAX       SnmpAdminString
    MAX-ACCESS   read-only
    STATUS       current
    DESCRIPTION
        "Cisco Firepower mgmt:Controller:rn managed object property"
    ::= { cfprMgmtControllerEntry 3 }

cfprMgmtControllerDimmBlacklistingOperState OBJECT-TYPE
    SYNTAX       CfprMgmtDimmBlacklistingOperState
    MAX-ACCESS   read-only
    STATUS       current
    DESCRIPTION
        "Cisco Firepower mgmt:Controller:dimmBlacklistingOperState
        managed object property"
    ::= { cfprMgmtControllerEntry 4 }

cfprMgmtControllerFsmDescr OBJECT-TYPE
    SYNTAX       SnmpAdminString
    MAX-ACCESS   read-only
    STATUS       current
    DESCRIPTION
        "Cisco Firepower mgmt:Controller:fsmDescr managed object property"
    ::= { cfprMgmtControllerEntry 5 }

cfprMgmtControllerFsmFlags OBJECT-TYPE
    SYNTAX       SnmpAdminString
    MAX-ACCESS   read-only
    STATUS       current
    DESCRIPTION
        "Cisco Firepower mgmt:Controller:fsmFlags managed object property"
    ::= { cfprMgmtControllerEntry 6 }

cfprMgmtControllerFsmPrev OBJECT-TYPE
    SYNTAX       SnmpAdminString
    MAX-ACCESS   read-only
    STATUS       current
    DESCRIPTION
        "Cisco Firepower mgmt:Controller:fsmPrev managed object property"
    ::= { cfprMgmtControllerEntry 7 }

cfprMgmtControllerFsmProgr OBJECT-TYPE
    SYNTAX       Gauge32
    MAX-ACCESS   read-only
    STATUS       current
    DESCRIPTION
        "Cisco Firepower mgmt:Controller:fsmProgr managed object property"
    ::= { cfprMgmtControllerEntry 8 }

cfprMgmtControllerFsmRmtInvErrCode OBJECT-TYPE
    SYNTAX       Gauge32
    MAX-ACCESS   read-only
    STATUS       current
    DESCRIPTION
        "Cisco Firepower mgmt:Controller:fsmRmtInvErrCode
        managed object property"
    ::= { cfprMgmtControllerEntry 9 }

cfprMgmtControllerFsmRmtInvErrDescr OBJECT-TYPE
    SYNTAX       SnmpAdminString
    MAX-ACCESS   read-only
    STATUS       current
    DESCRIPTION
        "Cisco Firepower mgmt:Controller:fsmRmtInvErrDescr
        managed object property"
    ::= { cfprMgmtControllerEntry 10 }

cfprMgmtControllerFsmRmtInvRslt OBJECT-TYPE
    SYNTAX       CfprConditionRemoteInvRslt
    MAX-ACCESS   read-only
    STATUS       current
    DESCRIPTION
        "Cisco Firepower mgmt:Controller:fsmRmtInvRslt
        managed object property"
    ::= { cfprMgmtControllerEntry 11 }

cfprMgmtControllerFsmStageDescr OBJECT-TYPE
    SYNTAX       SnmpAdminString
    MAX-ACCESS   read-only
    STATUS       current
    DESCRIPTION
        "Cisco Firepower mgmt:Controller:fsmStageDescr
        managed object property"
    ::= { cfprMgmtControllerEntry 12 }

cfprMgmtControllerFsmStamp OBJECT-TYPE
    SYNTAX       DateAndTime
    MAX-ACCESS   read-only
    STATUS       current
    DESCRIPTION
        "Cisco Firepower mgmt:Controller:fsmStamp managed object property"
    ::= { cfprMgmtControllerEntry 13 }

cfprMgmtControllerFsmStatus OBJECT-TYPE
    SYNTAX       SnmpAdminString
    MAX-ACCESS   read-only
    STATUS       current
    DESCRIPTION
        "Cisco Firepower mgmt:Controller:fsmStatus managed
        object property"
    ::= { cfprMgmtControllerEntry 14 }

cfprMgmtControllerFsmTry OBJECT-TYPE
    SYNTAX       Gauge32
    MAX-ACCESS   read-only
    STATUS       current
    DESCRIPTION
        "Cisco Firepower mgmt:Controller:fsmTry managed object property"
    ::= { cfprMgmtControllerEntry 15 }

cfprMgmtControllerGuid OBJECT-TYPE
    SYNTAX       SnmpAdminString
    MAX-ACCESS   read-only
    STATUS       current
    DESCRIPTION
        "Cisco Firepower mgmt:Controller:guid managed object property"
    ::= { cfprMgmtControllerEntry 16 }

cfprMgmtControllerModel OBJECT-TYPE
    SYNTAX       SnmpAdminString
    MAX-ACCESS   read-only
    STATUS       current
    DESCRIPTION
        "Cisco Firepower mgmt:Controller:model managed object property"
    ::= { cfprMgmtControllerEntry 17 }

cfprMgmtControllerOperConn OBJECT-TYPE
    SYNTAX       SnmpAdminString
    MAX-ACCESS   read-only
    STATUS       current
    DESCRIPTION
        "Cisco Firepower mgmt:Controller:operConn managed object property"
    ::= { cfprMgmtControllerEntry 18 }

cfprMgmtControllerRevision OBJECT-TYPE
    SYNTAX       SnmpAdminString
    MAX-ACCESS   read-only
    STATUS       current
    DESCRIPTION
        "Cisco Firepower mgmt:Controller:revision managed object property"
    ::= { cfprMgmtControllerEntry 19 }

cfprMgmtControllerSerial OBJECT-TYPE
    SYNTAX       SnmpAdminString
    MAX-ACCESS   read-only
    STATUS       current
    DESCRIPTION
        "Cisco Firepower mgmt:Controller:serial managed object property"
    ::= { cfprMgmtControllerEntry 20 }

cfprMgmtControllerStorageOobInterfaceSupported OBJECT-TYPE
    SYNTAX       TruthValue
    MAX-ACCESS   read-only
    STATUS       current
    DESCRIPTION
        "Cisco Firepower mgmt:Controller:storageOobInterfaceSupported
        managed object property"
    ::= { cfprMgmtControllerEntry 21 }

cfprMgmtControllerStorageSubsystemState OBJECT-TYPE
    SYNTAX       CfprMgmtStorageSubsystemState
    MAX-ACCESS   read-only
    STATUS       current
    DESCRIPTION
        "Cisco Firepower mgmt:Controller:storageSubsystemState
        managed object property"
    ::= { cfprMgmtControllerEntry 22 }

cfprMgmtControllerSubject OBJECT-TYPE
    SYNTAX       CfprMgmtSubject
    MAX-ACCESS   read-only
    STATUS       current
    DESCRIPTION
        "Cisco Firepower mgmt:Controller:subject managed object property"
    ::= { cfprMgmtControllerEntry 23 }

cfprMgmtControllerVendor OBJECT-TYPE
    SYNTAX       SnmpAdminString
    MAX-ACCESS   read-only
    STATUS       current
    DESCRIPTION
        "Cisco Firepower mgmt:Controller:vendor managed object property"
    ::= { cfprMgmtControllerEntry 24 }

cfprMgmtControllerFsmTable OBJECT-TYPE
    SYNTAX           SEQUENCE OF CfprMgmtControllerFsmEntry
    MAX-ACCESS       not-accessible
    STATUS           current
    DESCRIPTION
        "Cisco Firepower mgmt:ControllerFsm managed object table"
    ::= { cfprMgmtObjects 19 }

cfprMgmtControllerFsmEntry OBJECT-TYPE
    SYNTAX           CfprMgmtControllerFsmEntry
    MAX-ACCESS       not-accessible
    STATUS           current
    DESCRIPTION
        "Entry for the cfprMgmtControllerFsmTable table."
    INDEX { cfprMgmtControllerFsmInstanceId }
    ::= { cfprMgmtControllerFsmTable 1 }

CfprMgmtControllerFsmEntry ::= SEQUENCE {
    cfprMgmtControllerFsmInstanceId                                  CfprManagedObjectId,
    cfprMgmtControllerFsmDn                                          CfprManagedObjectDn,
    cfprMgmtControllerFsmRn                                          SnmpAdminString,
    cfprMgmtControllerFsmCompletionTime                              DateAndTime,
    cfprMgmtControllerFsmCurrentFsm                                  CfprMgmtControllerFsmCurrentFsm,
    cfprMgmtControllerFsmDescrData                                   SnmpAdminString,
    cfprMgmtControllerFsmFsmStatus                                   CfprFsmFsmStageStatus,
    cfprMgmtControllerFsmProgress                                    Gauge32,
    cfprMgmtControllerFsmRmtErrCode                                  Gauge32,
    cfprMgmtControllerFsmRmtErrDescr                                 SnmpAdminString,
    cfprMgmtControllerFsmRmtRslt                                     CfprConditionRemoteInvRslt
}

cfprMgmtControllerFsmInstanceId OBJECT-TYPE
    SYNTAX       CfprManagedObjectId
    MAX-ACCESS   not-accessible
    STATUS       current
    DESCRIPTION
        "Instance identifier of the managed object."
    ::= { cfprMgmtControllerFsmEntry 1 }

cfprMgmtControllerFsmDn OBJECT-TYPE
    SYNTAX       CfprManagedObjectDn
    MAX-ACCESS   read-only
    STATUS       current
    DESCRIPTION
        "Cisco Firepower mgmt:ControllerFsm:dn managed object property"
    ::= { cfprMgmtControllerFsmEntry 2 }

cfprMgmtControllerFsmRn OBJECT-TYPE
    SYNTAX       SnmpAdminString
    MAX-ACCESS   read-only
    STATUS       current
    DESCRIPTION
        "Cisco Firepower mgmt:ControllerFsm:rn managed object property"
    ::= { cfprMgmtControllerFsmEntry 3 }

cfprMgmtControllerFsmCompletionTime OBJECT-TYPE
    SYNTAX       DateAndTime
    MAX-ACCESS   read-only
    STATUS       current
    DESCRIPTION
        "Cisco Firepower mgmt:ControllerFsm:completionTime
        managed object property"
    ::= { cfprMgmtControllerFsmEntry 4 }

cfprMgmtControllerFsmCurrentFsm OBJECT-TYPE
    SYNTAX       CfprMgmtControllerFsmCurrentFsm
    MAX-ACCESS   read-only
    STATUS       current
    DESCRIPTION
        "Cisco Firepower mgmt:ControllerFsm:currentFsm
        managed object property"
    ::= { cfprMgmtControllerFsmEntry 5 }

cfprMgmtControllerFsmDescrData OBJECT-TYPE
    SYNTAX       SnmpAdminString
    MAX-ACCESS   read-only
    STATUS       current
    DESCRIPTION
        "Cisco Firepower mgmt:ControllerFsm:descr managed object property"
    ::= { cfprMgmtControllerFsmEntry 6 }

cfprMgmtControllerFsmFsmStatus OBJECT-TYPE
    SYNTAX       CfprFsmFsmStageStatus
    MAX-ACCESS   read-only
    STATUS       current
    DESCRIPTION
        "Cisco Firepower mgmt:ControllerFsm:fsmStatus managed
        object property"
    ::= { cfprMgmtControllerFsmEntry 7 }

cfprMgmtControllerFsmProgress OBJECT-TYPE
    SYNTAX       Gauge32
    MAX-ACCESS   read-only
    STATUS       current
    DESCRIPTION
        "Cisco Firepower mgmt:ControllerFsm:progress managed
        object property"
    ::= { cfprMgmtControllerFsmEntry 8 }

cfprMgmtControllerFsmRmtErrCode OBJECT-TYPE
    SYNTAX       Gauge32
    MAX-ACCESS   read-only
    STATUS       current
    DESCRIPTION
        "Cisco Firepower mgmt:ControllerFsm:rmtErrCode
        managed object property"
    ::= { cfprMgmtControllerFsmEntry 9 }

cfprMgmtControllerFsmRmtErrDescr OBJECT-TYPE
    SYNTAX       SnmpAdminString
    MAX-ACCESS   read-only
    STATUS       current
    DESCRIPTION
        "Cisco Firepower mgmt:ControllerFsm:rmtErrDescr
        managed object property"
    ::= { cfprMgmtControllerFsmEntry 10 }

cfprMgmtControllerFsmRmtRslt OBJECT-TYPE
    SYNTAX       CfprConditionRemoteInvRslt
    MAX-ACCESS   read-only
    STATUS       current
    DESCRIPTION
        "Cisco Firepower mgmt:ControllerFsm:rmtRslt managed
        object property"
    ::= { cfprMgmtControllerFsmEntry 11 }

cfprMgmtControllerFsmStageTable OBJECT-TYPE
    SYNTAX           SEQUENCE OF CfprMgmtControllerFsmStageEntry
    MAX-ACCESS       not-accessible
    STATUS           current
    DESCRIPTION
        "Cisco Firepower mgmt:ControllerFsmStage managed object table"
    ::= { cfprMgmtObjects 20 }

cfprMgmtControllerFsmStageEntry OBJECT-TYPE
    SYNTAX           CfprMgmtControllerFsmStageEntry
    MAX-ACCESS       not-accessible
    STATUS           current
    DESCRIPTION
        "Entry for the cfprMgmtControllerFsmStageTable table."
    INDEX { cfprMgmtControllerFsmStageInstanceId }
    ::= { cfprMgmtControllerFsmStageTable 1 }

CfprMgmtControllerFsmStageEntry ::= SEQUENCE {
    cfprMgmtControllerFsmStageInstanceId                             CfprManagedObjectId,
    cfprMgmtControllerFsmStageDn                                     CfprManagedObjectDn,
    cfprMgmtControllerFsmStageRn                                     SnmpAdminString,
    cfprMgmtControllerFsmStageDescrData                              SnmpAdminString,
    cfprMgmtControllerFsmStageLastUpdateTime                         DateAndTime,
    cfprMgmtControllerFsmStageName                                   CfprMgmtControllerFsmStageName,
    cfprMgmtControllerFsmStageOrder                                  Gauge32,
    cfprMgmtControllerFsmStageRetry                                  Gauge32,
    cfprMgmtControllerFsmStageStageStatus                            CfprFsmFsmStageStatus
}

cfprMgmtControllerFsmStageInstanceId OBJECT-TYPE
    SYNTAX       CfprManagedObjectId
    MAX-ACCESS   not-accessible
    STATUS       current
    DESCRIPTION
        "Instance identifier of the managed object."
    ::= { cfprMgmtControllerFsmStageEntry 1 }

cfprMgmtControllerFsmStageDn OBJECT-TYPE
    SYNTAX       CfprManagedObjectDn
    MAX-ACCESS   read-only
    STATUS       current
    DESCRIPTION
        "Cisco Firepower mgmt:ControllerFsmStage:dn managed
        object property"
    ::= { cfprMgmtControllerFsmStageEntry 2 }

cfprMgmtControllerFsmStageRn OBJECT-TYPE
    SYNTAX       SnmpAdminString
    MAX-ACCESS   read-only
    STATUS       current
    DESCRIPTION
        "Cisco Firepower mgmt:ControllerFsmStage:rn managed
        object property"
    ::= { cfprMgmtControllerFsmStageEntry 3 }

cfprMgmtControllerFsmStageDescrData OBJECT-TYPE
    SYNTAX       SnmpAdminString
    MAX-ACCESS   read-only
    STATUS       current
    DESCRIPTION
        "Cisco Firepower mgmt:ControllerFsmStage:descr
        managed object property"
    ::= { cfprMgmtControllerFsmStageEntry 4 }

cfprMgmtControllerFsmStageLastUpdateTime OBJECT-TYPE
    SYNTAX       DateAndTime
    MAX-ACCESS   read-only
    STATUS       current
    DESCRIPTION
        "Cisco Firepower mgmt:ControllerFsmStage:lastUpdateTime
        managed object property"
    ::= { cfprMgmtControllerFsmStageEntry 5 }

cfprMgmtControllerFsmStageName OBJECT-TYPE
    SYNTAX       CfprMgmtControllerFsmStageName
    MAX-ACCESS   read-only
    STATUS       current
    DESCRIPTION
        "Cisco Firepower mgmt:ControllerFsmStage:name managed
        object property"
    ::= { cfprMgmtControllerFsmStageEntry 6 }

cfprMgmtControllerFsmStageOrder OBJECT-TYPE
    SYNTAX       Gauge32
    MAX-ACCESS   read-only
    STATUS       current
    DESCRIPTION
        "Cisco Firepower mgmt:ControllerFsmStage:order
        managed object property"
    ::= { cfprMgmtControllerFsmStageEntry 7 }

cfprMgmtControllerFsmStageRetry OBJECT-TYPE
    SYNTAX       Gauge32
    MAX-ACCESS   read-only
    STATUS       current
    DESCRIPTION
        "Cisco Firepower mgmt:ControllerFsmStage:retry
        managed object property"
    ::= { cfprMgmtControllerFsmStageEntry 8 }

cfprMgmtControllerFsmStageStageStatus OBJECT-TYPE
    SYNTAX       CfprFsmFsmStageStatus
    MAX-ACCESS   read-only
    STATUS       current
    DESCRIPTION
        "Cisco Firepower mgmt:ControllerFsmStage:stageStatus
        managed object property"
    ::= { cfprMgmtControllerFsmStageEntry 9 }

cfprMgmtControllerFsmTaskTable OBJECT-TYPE
    SYNTAX           SEQUENCE OF CfprMgmtControllerFsmTaskEntry
    MAX-ACCESS       not-accessible
    STATUS           current
    DESCRIPTION
        "Cisco Firepower mgmt:ControllerFsmTask managed object table"
    ::= { cfprMgmtObjects 21 }

cfprMgmtControllerFsmTaskEntry OBJECT-TYPE
    SYNTAX           CfprMgmtControllerFsmTaskEntry
    MAX-ACCESS       not-accessible
    STATUS           current
    DESCRIPTION
        "Entry for the cfprMgmtControllerFsmTaskTable table."
    INDEX { cfprMgmtControllerFsmTaskInstanceId }
    ::= { cfprMgmtControllerFsmTaskTable 1 }

CfprMgmtControllerFsmTaskEntry ::= SEQUENCE {
    cfprMgmtControllerFsmTaskInstanceId                              CfprManagedObjectId,
    cfprMgmtControllerFsmTaskDn                                      CfprManagedObjectDn,
    cfprMgmtControllerFsmTaskRn                                      SnmpAdminString,
    cfprMgmtControllerFsmTaskCompletion                              CfprFsmCompletion,
    cfprMgmtControllerFsmTaskFlags                                   CfprMgmtControllerFsmTaskFlags,
    cfprMgmtControllerFsmTaskItem                                    CfprMgmtControllerFsmTaskItem,
    cfprMgmtControllerFsmTaskSeqId                                   Gauge32
}

cfprMgmtControllerFsmTaskInstanceId OBJECT-TYPE
    SYNTAX       CfprManagedObjectId
    MAX-ACCESS   not-accessible
    STATUS       current
    DESCRIPTION
        "Instance identifier of the managed object."
    ::= { cfprMgmtControllerFsmTaskEntry 1 }

cfprMgmtControllerFsmTaskDn OBJECT-TYPE
    SYNTAX       CfprManagedObjectDn
    MAX-ACCESS   read-only
    STATUS       current
    DESCRIPTION
        "Cisco Firepower mgmt:ControllerFsmTask:dn managed
        object property"
    ::= { cfprMgmtControllerFsmTaskEntry 2 }

cfprMgmtControllerFsmTaskRn OBJECT-TYPE
    SYNTAX       SnmpAdminString
    MAX-ACCESS   read-only
    STATUS       current
    DESCRIPTION
        "Cisco Firepower mgmt:ControllerFsmTask:rn managed
        object property"
    ::= { cfprMgmtControllerFsmTaskEntry 3 }

cfprMgmtControllerFsmTaskCompletion OBJECT-TYPE
    SYNTAX       CfprFsmCompletion
    MAX-ACCESS   read-only
    STATUS       current
    DESCRIPTION
        "Cisco Firepower mgmt:ControllerFsmTask:completion
        managed object property"
    ::= { cfprMgmtControllerFsmTaskEntry 4 }

cfprMgmtControllerFsmTaskFlags OBJECT-TYPE
    SYNTAX       CfprMgmtControllerFsmTaskFlags
    MAX-ACCESS   read-only
    STATUS       current
    DESCRIPTION
        "Cisco Firepower mgmt:ControllerFsmTask:flags managed
        object property"
    ::= { cfprMgmtControllerFsmTaskEntry 5 }

cfprMgmtControllerFsmTaskItem OBJECT-TYPE
    SYNTAX       CfprMgmtControllerFsmTaskItem
    MAX-ACCESS   read-only
    STATUS       current
    DESCRIPTION
        "Cisco Firepower mgmt:ControllerFsmTask:item managed
        object property"
    ::= { cfprMgmtControllerFsmTaskEntry 6 }

cfprMgmtControllerFsmTaskSeqId OBJECT-TYPE
    SYNTAX       Gauge32
    MAX-ACCESS   read-only
    STATUS       current
    DESCRIPTION
        "Cisco Firepower mgmt:ControllerFsmTask:seqId managed
        object property"
    ::= { cfprMgmtControllerFsmTaskEntry 7 }

cfprMgmtEntityTable OBJECT-TYPE
    SYNTAX           SEQUENCE OF CfprMgmtEntityEntry
    MAX-ACCESS       not-accessible
    STATUS           current
    DESCRIPTION
        "Cisco Firepower mgmt:Entity managed object table"
    ::= { cfprMgmtObjects 22 }

cfprMgmtEntityEntry OBJECT-TYPE
    SYNTAX           CfprMgmtEntityEntry
    MAX-ACCESS       not-accessible
    STATUS           current
    DESCRIPTION
        "Entry for the cfprMgmtEntityTable table."
    INDEX { cfprMgmtEntityInstanceId }
    ::= { cfprMgmtEntityTable 1 }

CfprMgmtEntityEntry ::= SEQUENCE {
    cfprMgmtEntityInstanceId                                         CfprManagedObjectId,
    cfprMgmtEntityDn                                                 CfprManagedObjectDn,
    cfprMgmtEntityRn                                                 SnmpAdminString,
    cfprMgmtEntityChassis1                                           SnmpAdminString,
    cfprMgmtEntityChassis2                                           SnmpAdminString,
    cfprMgmtEntityChassis3                                           SnmpAdminString,
    cfprMgmtEntityChassisDeviceIoState1                              CfprMgmtEntityChassisDeviceIoState1,
    cfprMgmtEntityChassisDeviceIoState2                              CfprMgmtEntityChassisDeviceIoState2,
    cfprMgmtEntityChassisDeviceIoState3                              CfprMgmtEntityChassisDeviceIoState3,
    cfprMgmtEntityHaFailureReason                                    CfprMgmtEntityHaFailureReason,
    cfprMgmtEntityHaReadiness                                        CfprMgmtEntityHaReadiness,
    cfprMgmtEntityHaReady                                            TruthValue,
    cfprMgmtEntityId                                                 CfprNetworkSwitchId,
    cfprMgmtEntityLeadership                                         CfprMgmtEntityLeadership,
    cfprMgmtEntityMgmtServicesState                                  CfprMgmtEntityMgmtServicesState,
    cfprMgmtEntityProblems                                           CfprMgmtEntityProblems,
    cfprMgmtEntitySshAuthKeysCsum                                    SnmpAdminString,
    cfprMgmtEntitySshAuthKeysSize                                    Unsigned64,
    cfprMgmtEntitySshKeyStatus                                       Unsigned64,
    cfprMgmtEntitySshRootPubKeyCsum                                  SnmpAdminString,
    cfprMgmtEntitySshRootPubKeySize                                  Unsigned64,
    cfprMgmtEntityState                                              CfprMgmtEntityState,
    cfprMgmtEntityUmbilicalState                                     CfprMgmtEntityUmbilicalState,
    cfprMgmtEntityVersionMismatch                                    TruthValue
}

cfprMgmtEntityInstanceId OBJECT-TYPE
    SYNTAX       CfprManagedObjectId
    MAX-ACCESS   not-accessible
    STATUS       current
    DESCRIPTION
        "Instance identifier of the managed object."
    ::= { cfprMgmtEntityEntry 1 }

cfprMgmtEntityDn OBJECT-TYPE
    SYNTAX       CfprManagedObjectDn
    MAX-ACCESS   read-only
    STATUS       current
    DESCRIPTION
        "Cisco Firepower mgmt:Entity:dn managed object property"
    ::= { cfprMgmtEntityEntry 2 }

cfprMgmtEntityRn OBJECT-TYPE
    SYNTAX       SnmpAdminString
    MAX-ACCESS   read-only
    STATUS       current
    DESCRIPTION
        "Cisco Firepower mgmt:Entity:rn managed object property"
    ::= { cfprMgmtEntityEntry 3 }

cfprMgmtEntityChassis1 OBJECT-TYPE
    SYNTAX       SnmpAdminString
    MAX-ACCESS   read-only
    STATUS       current
    DESCRIPTION
        "Cisco Firepower mgmt:Entity:chassis1 managed object property"
    ::= { cfprMgmtEntityEntry 4 }

cfprMgmtEntityChassis2 OBJECT-TYPE
    SYNTAX       SnmpAdminString
    MAX-ACCESS   read-only
    STATUS       current
    DESCRIPTION
        "Cisco Firepower mgmt:Entity:chassis2 managed object property"
    ::= { cfprMgmtEntityEntry 5 }

cfprMgmtEntityChassis3 OBJECT-TYPE
    SYNTAX       SnmpAdminString
    MAX-ACCESS   read-only
    STATUS       current
    DESCRIPTION
        "Cisco Firepower mgmt:Entity:chassis3 managed object property"
    ::= { cfprMgmtEntityEntry 6 }

cfprMgmtEntityChassisDeviceIoState1 OBJECT-TYPE
    SYNTAX       CfprMgmtEntityChassisDeviceIoState1
    MAX-ACCESS   read-only
    STATUS       current
    DESCRIPTION
        "Cisco Firepower mgmt:Entity:chassisDeviceIoState1
        managed object property"
    ::= { cfprMgmtEntityEntry 7 }

cfprMgmtEntityChassisDeviceIoState2 OBJECT-TYPE
    SYNTAX       CfprMgmtEntityChassisDeviceIoState2
    MAX-ACCESS   read-only
    STATUS       current
    DESCRIPTION
        "Cisco Firepower mgmt:Entity:chassisDeviceIoState2
        managed object property"
    ::= { cfprMgmtEntityEntry 8 }

cfprMgmtEntityChassisDeviceIoState3 OBJECT-TYPE
    SYNTAX       CfprMgmtEntityChassisDeviceIoState3
    MAX-ACCESS   read-only
    STATUS       current
    DESCRIPTION
        "Cisco Firepower mgmt:Entity:chassisDeviceIoState3
        managed object property"
    ::= { cfprMgmtEntityEntry 9 }

cfprMgmtEntityHaFailureReason OBJECT-TYPE
    SYNTAX       CfprMgmtEntityHaFailureReason
    MAX-ACCESS   read-only
    STATUS       current
    DESCRIPTION
        "Cisco Firepower mgmt:Entity:haFailureReason managed
        object property"
    ::= { cfprMgmtEntityEntry 10 }

cfprMgmtEntityHaReadiness OBJECT-TYPE
    SYNTAX       CfprMgmtEntityHaReadiness
    MAX-ACCESS   read-only
    STATUS       current
    DESCRIPTION
        "Cisco Firepower mgmt:Entity:haReadiness managed object property"
    ::= { cfprMgmtEntityEntry 11 }

cfprMgmtEntityHaReady OBJECT-TYPE
    SYNTAX       TruthValue
    MAX-ACCESS   read-only
    STATUS       current
    DESCRIPTION
        "Cisco Firepower mgmt:Entity:haReady managed object property"
    ::= { cfprMgmtEntityEntry 12 }

cfprMgmtEntityId OBJECT-TYPE
    SYNTAX       CfprNetworkSwitchId
    MAX-ACCESS   read-only
    STATUS       current
    DESCRIPTION
        "Cisco Firepower mgmt:Entity:id managed object property"
    ::= { cfprMgmtEntityEntry 13 }

cfprMgmtEntityLeadership OBJECT-TYPE
    SYNTAX       CfprMgmtEntityLeadership
    MAX-ACCESS   read-only
    STATUS       current
    DESCRIPTION
        "Cisco Firepower mgmt:Entity:leadership managed object property"
    ::= { cfprMgmtEntityEntry 14 }

cfprMgmtEntityMgmtServicesState OBJECT-TYPE
    SYNTAX       CfprMgmtEntityMgmtServicesState
    MAX-ACCESS   read-only
    STATUS       current
    DESCRIPTION
        "Cisco Firepower mgmt:Entity:mgmtServicesState
        managed object property"
    ::= { cfprMgmtEntityEntry 15 }

cfprMgmtEntityProblems OBJECT-TYPE
    SYNTAX       CfprMgmtEntityProblems
    MAX-ACCESS   read-only
    STATUS       current
    DESCRIPTION
        "Cisco Firepower mgmt:Entity:problems managed object property"
    ::= { cfprMgmtEntityEntry 16 }

cfprMgmtEntitySshAuthKeysCsum OBJECT-TYPE
    SYNTAX       SnmpAdminString
    MAX-ACCESS   read-only
    STATUS       current
    DESCRIPTION
        "Cisco Firepower mgmt:Entity:sshAuthKeysCsum managed
        object property"
    ::= { cfprMgmtEntityEntry 17 }

cfprMgmtEntitySshAuthKeysSize OBJECT-TYPE
    SYNTAX       Unsigned64
    MAX-ACCESS   read-only
    STATUS       current
    DESCRIPTION
        "Cisco Firepower mgmt:Entity:sshAuthKeysSize managed
        object property"
    ::= { cfprMgmtEntityEntry 18 }

cfprMgmtEntitySshKeyStatus OBJECT-TYPE
    SYNTAX       Unsigned64
    MAX-ACCESS   read-only
    STATUS       current
    DESCRIPTION
        "Cisco Firepower mgmt:Entity:sshKeyStatus managed object property"
    ::= { cfprMgmtEntityEntry 19 }

cfprMgmtEntitySshRootPubKeyCsum OBJECT-TYPE
    SYNTAX       SnmpAdminString
    MAX-ACCESS   read-only
    STATUS       current
    DESCRIPTION
        "Cisco Firepower mgmt:Entity:sshRootPubKeyCsum
        managed object property"
    ::= { cfprMgmtEntityEntry 20 }

cfprMgmtEntitySshRootPubKeySize OBJECT-TYPE
    SYNTAX       Unsigned64
    MAX-ACCESS   read-only
    STATUS       current
    DESCRIPTION
        "Cisco Firepower mgmt:Entity:sshRootPubKeySize
        managed object property"
    ::= { cfprMgmtEntityEntry 21 }

cfprMgmtEntityState OBJECT-TYPE
    SYNTAX       CfprMgmtEntityState
    MAX-ACCESS   read-only
    STATUS       current
    DESCRIPTION
        "Cisco Firepower mgmt:Entity:state managed object property"
    ::= { cfprMgmtEntityEntry 22 }

cfprMgmtEntityUmbilicalState OBJECT-TYPE
    SYNTAX       CfprMgmtEntityUmbilicalState
    MAX-ACCESS   read-only
    STATUS       current
    DESCRIPTION
        "Cisco Firepower mgmt:Entity:umbilicalState managed
        object property"
    ::= { cfprMgmtEntityEntry 23 }

cfprMgmtEntityVersionMismatch OBJECT-TYPE
    SYNTAX       TruthValue
    MAX-ACCESS   read-only
    STATUS       current
    DESCRIPTION
        "Cisco Firepower mgmt:Entity:versionMismatch managed
        object property"
    ::= { cfprMgmtEntityEntry 24 }

cfprMgmtExportPolicyFsmTable OBJECT-TYPE
    SYNTAX           SEQUENCE OF CfprMgmtExportPolicyFsmEntry
    MAX-ACCESS       not-accessible
    STATUS           current
    DESCRIPTION
        "Cisco Firepower mgmt:ExportPolicyFsm managed object table"
    ::= { cfprMgmtObjects 23 }

cfprMgmtExportPolicyFsmEntry OBJECT-TYPE
    SYNTAX           CfprMgmtExportPolicyFsmEntry
    MAX-ACCESS       not-accessible
    STATUS           current
    DESCRIPTION
        "Entry for the cfprMgmtExportPolicyFsmTable table."
    INDEX { cfprMgmtExportPolicyFsmInstanceId }
    ::= { cfprMgmtExportPolicyFsmTable 1 }

CfprMgmtExportPolicyFsmEntry ::= SEQUENCE {
    cfprMgmtExportPolicyFsmInstanceId                                CfprManagedObjectId,
    cfprMgmtExportPolicyFsmDn                                        CfprManagedObjectDn,
    cfprMgmtExportPolicyFsmRn                                        SnmpAdminString,
    cfprMgmtExportPolicyFsmCompletionTime                            DateAndTime,
    cfprMgmtExportPolicyFsmCurrentFsm                                CfprMgmtExportPolicyFsmCurrentFsm,
    cfprMgmtExportPolicyFsmDescr                                     SnmpAdminString,
    cfprMgmtExportPolicyFsmFsmStatus                                 CfprFsmFsmStageStatus,
    cfprMgmtExportPolicyFsmProgress                                  Gauge32,
    cfprMgmtExportPolicyFsmRmtErrCode                                Gauge32,
    cfprMgmtExportPolicyFsmRmtErrDescr                               SnmpAdminString,
    cfprMgmtExportPolicyFsmRmtRslt                                   CfprConditionRemoteInvRslt
}

cfprMgmtExportPolicyFsmInstanceId OBJECT-TYPE
    SYNTAX       CfprManagedObjectId
    MAX-ACCESS   not-accessible
    STATUS       current
    DESCRIPTION
        "Instance identifier of the managed object."
    ::= { cfprMgmtExportPolicyFsmEntry 1 }

cfprMgmtExportPolicyFsmDn OBJECT-TYPE
    SYNTAX       CfprManagedObjectDn
    MAX-ACCESS   read-only
    STATUS       current
    DESCRIPTION
        "Cisco Firepower mgmt:ExportPolicyFsm:dn managed object property"
    ::= { cfprMgmtExportPolicyFsmEntry 2 }

cfprMgmtExportPolicyFsmRn OBJECT-TYPE
    SYNTAX       SnmpAdminString
    MAX-ACCESS   read-only
    STATUS       current
    DESCRIPTION
        "Cisco Firepower mgmt:ExportPolicyFsm:rn managed object property"
    ::= { cfprMgmtExportPolicyFsmEntry 3 }

cfprMgmtExportPolicyFsmCompletionTime OBJECT-TYPE
    SYNTAX       DateAndTime
    MAX-ACCESS   read-only
    STATUS       current
    DESCRIPTION
        "Cisco Firepower mgmt:ExportPolicyFsm:completionTime
        managed object property"
    ::= { cfprMgmtExportPolicyFsmEntry 4 }

cfprMgmtExportPolicyFsmCurrentFsm OBJECT-TYPE
    SYNTAX       CfprMgmtExportPolicyFsmCurrentFsm
    MAX-ACCESS   read-only
    STATUS       current
    DESCRIPTION
        "Cisco Firepower mgmt:ExportPolicyFsm:currentFsm
        managed object property"
    ::= { cfprMgmtExportPolicyFsmEntry 5 }

cfprMgmtExportPolicyFsmDescr OBJECT-TYPE
    SYNTAX       SnmpAdminString
    MAX-ACCESS   read-only
    STATUS       current
    DESCRIPTION
        "Cisco Firepower mgmt:ExportPolicyFsm:descr managed
        object property"
    ::= { cfprMgmtExportPolicyFsmEntry 6 }

cfprMgmtExportPolicyFsmFsmStatus OBJECT-TYPE
    SYNTAX       CfprFsmFsmStageStatus
    MAX-ACCESS   read-only
    STATUS       current
    DESCRIPTION
        "Cisco Firepower mgmt:ExportPolicyFsm:fsmStatus
        managed object property"
    ::= { cfprMgmtExportPolicyFsmEntry 7 }

cfprMgmtExportPolicyFsmProgress OBJECT-TYPE
    SYNTAX       Gauge32
    MAX-ACCESS   read-only
    STATUS       current
    DESCRIPTION
        "Cisco Firepower mgmt:ExportPolicyFsm:progress
        managed object property"
    ::= { cfprMgmtExportPolicyFsmEntry 8 }

cfprMgmtExportPolicyFsmRmtErrCode OBJECT-TYPE
    SYNTAX       Gauge32
    MAX-ACCESS   read-only
    STATUS       current
    DESCRIPTION
        "Cisco Firepower mgmt:ExportPolicyFsm:rmtErrCode
        managed object property"
    ::= { cfprMgmtExportPolicyFsmEntry 9 }

cfprMgmtExportPolicyFsmRmtErrDescr OBJECT-TYPE
    SYNTAX       SnmpAdminString
    MAX-ACCESS   read-only
    STATUS       current
    DESCRIPTION
        "Cisco Firepower mgmt:ExportPolicyFsm:rmtErrDescr
        managed object property"
    ::= { cfprMgmtExportPolicyFsmEntry 10 }

cfprMgmtExportPolicyFsmRmtRslt OBJECT-TYPE
    SYNTAX       CfprConditionRemoteInvRslt
    MAX-ACCESS   read-only
    STATUS       current
    DESCRIPTION
        "Cisco Firepower mgmt:ExportPolicyFsm:rmtRslt managed
        object property"
    ::= { cfprMgmtExportPolicyFsmEntry 11 }

cfprMgmtExportPolicyFsmStageTable OBJECT-TYPE
    SYNTAX           SEQUENCE OF CfprMgmtExportPolicyFsmStageEntry
    MAX-ACCESS       not-accessible
    STATUS           current
    DESCRIPTION
        "Cisco Firepower mgmt:ExportPolicyFsmStage managed object table"
    ::= { cfprMgmtObjects 24 }

cfprMgmtExportPolicyFsmStageEntry OBJECT-TYPE
    SYNTAX           CfprMgmtExportPolicyFsmStageEntry
    MAX-ACCESS       not-accessible
    STATUS           current
    DESCRIPTION
        "Entry for the cfprMgmtExportPolicyFsmStageTable table."
    INDEX { cfprMgmtExportPolicyFsmStageInstanceId }
    ::= { cfprMgmtExportPolicyFsmStageTable 1 }

CfprMgmtExportPolicyFsmStageEntry ::= SEQUENCE {
    cfprMgmtExportPolicyFsmStageInstanceId                           CfprManagedObjectId,
    cfprMgmtExportPolicyFsmStageDn                                   CfprManagedObjectDn,
    cfprMgmtExportPolicyFsmStageRn                                   SnmpAdminString,
    cfprMgmtExportPolicyFsmStageDescr                                SnmpAdminString,
    cfprMgmtExportPolicyFsmStageLastUpdateTime                       DateAndTime,
    cfprMgmtExportPolicyFsmStageName                                 CfprMgmtExportPolicyFsmStageName,
    cfprMgmtExportPolicyFsmStageOrder                                Gauge32,
    cfprMgmtExportPolicyFsmStageRetry                                Gauge32,
    cfprMgmtExportPolicyFsmStageStageStatus                          CfprFsmFsmStageStatus
}

cfprMgmtExportPolicyFsmStageInstanceId OBJECT-TYPE
    SYNTAX       CfprManagedObjectId
    MAX-ACCESS   not-accessible
    STATUS       current
    DESCRIPTION
        "Instance identifier of the managed object."
    ::= { cfprMgmtExportPolicyFsmStageEntry 1 }

cfprMgmtExportPolicyFsmStageDn OBJECT-TYPE
    SYNTAX       CfprManagedObjectDn
    MAX-ACCESS   read-only
    STATUS       current
    DESCRIPTION
        "Cisco Firepower mgmt:ExportPolicyFsmStage:dn managed
        object property"
    ::= { cfprMgmtExportPolicyFsmStageEntry 2 }

cfprMgmtExportPolicyFsmStageRn OBJECT-TYPE
    SYNTAX       SnmpAdminString
    MAX-ACCESS   read-only
    STATUS       current
    DESCRIPTION
        "Cisco Firepower mgmt:ExportPolicyFsmStage:rn managed
        object property"
    ::= { cfprMgmtExportPolicyFsmStageEntry 3 }

cfprMgmtExportPolicyFsmStageDescr OBJECT-TYPE
    SYNTAX       SnmpAdminString
    MAX-ACCESS   read-only
    STATUS       current
    DESCRIPTION
        "Cisco Firepower mgmt:ExportPolicyFsmStage:descr
        managed object property"
    ::= { cfprMgmtExportPolicyFsmStageEntry 4 }

cfprMgmtExportPolicyFsmStageLastUpdateTime OBJECT-TYPE
    SYNTAX       DateAndTime
    MAX-ACCESS   read-only
    STATUS       current
    DESCRIPTION
        "Cisco Firepower mgmt:ExportPolicyFsmStage:lastUpdateTime
        managed object property"
    ::= { cfprMgmtExportPolicyFsmStageEntry 5 }

cfprMgmtExportPolicyFsmStageName OBJECT-TYPE
    SYNTAX       CfprMgmtExportPolicyFsmStageName
    MAX-ACCESS   read-only
    STATUS       current
    DESCRIPTION
        "Cisco Firepower mgmt:ExportPolicyFsmStage:name
        managed object property"
    ::= { cfprMgmtExportPolicyFsmStageEntry 6 }

cfprMgmtExportPolicyFsmStageOrder OBJECT-TYPE
    SYNTAX       Gauge32
    MAX-ACCESS   read-only
    STATUS       current
    DESCRIPTION
        "Cisco Firepower mgmt:ExportPolicyFsmStage:order
        managed object property"
    ::= { cfprMgmtExportPolicyFsmStageEntry 7 }

cfprMgmtExportPolicyFsmStageRetry OBJECT-TYPE
    SYNTAX       Gauge32
    MAX-ACCESS   read-only
    STATUS       current
    DESCRIPTION
        "Cisco Firepower mgmt:ExportPolicyFsmStage:retry
        managed object property"
    ::= { cfprMgmtExportPolicyFsmStageEntry 8 }

cfprMgmtExportPolicyFsmStageStageStatus OBJECT-TYPE
    SYNTAX       CfprFsmFsmStageStatus
    MAX-ACCESS   read-only
    STATUS       current
    DESCRIPTION
        "Cisco Firepower mgmt:ExportPolicyFsmStage:stageStatus
        managed object property"
    ::= { cfprMgmtExportPolicyFsmStageEntry 9 }

cfprMgmtExportPolicyFsmTaskTable OBJECT-TYPE
    SYNTAX           SEQUENCE OF CfprMgmtExportPolicyFsmTaskEntry
    MAX-ACCESS       not-accessible
    STATUS           current
    DESCRIPTION
        "Cisco Firepower mgmt:ExportPolicyFsmTask managed object table"
    ::= { cfprMgmtObjects 25 }

cfprMgmtExportPolicyFsmTaskEntry OBJECT-TYPE
    SYNTAX           CfprMgmtExportPolicyFsmTaskEntry
    MAX-ACCESS       not-accessible
    STATUS           current
    DESCRIPTION
        "Entry for the cfprMgmtExportPolicyFsmTaskTable table."
    INDEX { cfprMgmtExportPolicyFsmTaskInstanceId }
    ::= { cfprMgmtExportPolicyFsmTaskTable 1 }

CfprMgmtExportPolicyFsmTaskEntry ::= SEQUENCE {
    cfprMgmtExportPolicyFsmTaskInstanceId                            CfprManagedObjectId,
    cfprMgmtExportPolicyFsmTaskDn                                    CfprManagedObjectDn,
    cfprMgmtExportPolicyFsmTaskRn                                    SnmpAdminString,
    cfprMgmtExportPolicyFsmTaskCompletion                            CfprFsmCompletion,
    cfprMgmtExportPolicyFsmTaskFlags                                 CfprFsmFlags,
    cfprMgmtExportPolicyFsmTaskItem                                  CfprMgmtExportPolicyFsmTaskItem,
    cfprMgmtExportPolicyFsmTaskSeqId                                 Gauge32
}

cfprMgmtExportPolicyFsmTaskInstanceId OBJECT-TYPE
    SYNTAX       CfprManagedObjectId
    MAX-ACCESS   not-accessible
    STATUS       current
    DESCRIPTION
        "Instance identifier of the managed object."
    ::= { cfprMgmtExportPolicyFsmTaskEntry 1 }

cfprMgmtExportPolicyFsmTaskDn OBJECT-TYPE
    SYNTAX       CfprManagedObjectDn
    MAX-ACCESS   read-only
    STATUS       current
    DESCRIPTION
        "Cisco Firepower mgmt:ExportPolicyFsmTask:dn managed
        object property"
    ::= { cfprMgmtExportPolicyFsmTaskEntry 2 }

cfprMgmtExportPolicyFsmTaskRn OBJECT-TYPE
    SYNTAX       SnmpAdminString
    MAX-ACCESS   read-only
    STATUS       current
    DESCRIPTION
        "Cisco Firepower mgmt:ExportPolicyFsmTask:rn managed
        object property"
    ::= { cfprMgmtExportPolicyFsmTaskEntry 3 }

cfprMgmtExportPolicyFsmTaskCompletion OBJECT-TYPE
    SYNTAX       CfprFsmCompletion
    MAX-ACCESS   read-only
    STATUS       current
    DESCRIPTION
        "Cisco Firepower mgmt:ExportPolicyFsmTask:completion
        managed object property"
    ::= { cfprMgmtExportPolicyFsmTaskEntry 4 }

cfprMgmtExportPolicyFsmTaskFlags OBJECT-TYPE
    SYNTAX       CfprFsmFlags
    MAX-ACCESS   read-only
    STATUS       current
    DESCRIPTION
        "Cisco Firepower mgmt:ExportPolicyFsmTask:flags
        managed object property"
    ::= { cfprMgmtExportPolicyFsmTaskEntry 5 }

cfprMgmtExportPolicyFsmTaskItem OBJECT-TYPE
    SYNTAX       CfprMgmtExportPolicyFsmTaskItem
    MAX-ACCESS   read-only
    STATUS       current
    DESCRIPTION
        "Cisco Firepower mgmt:ExportPolicyFsmTask:item
        managed object property"
    ::= { cfprMgmtExportPolicyFsmTaskEntry 6 }

cfprMgmtExportPolicyFsmTaskSeqId OBJECT-TYPE
    SYNTAX       Gauge32
    MAX-ACCESS   read-only
    STATUS       current
    DESCRIPTION
        "Cisco Firepower mgmt:ExportPolicyFsmTask:seqId
        managed object property"
    ::= { cfprMgmtExportPolicyFsmTaskEntry 7 }

cfprMgmtIPv6IfAddrTable OBJECT-TYPE
    SYNTAX           SEQUENCE OF CfprMgmtIPv6IfAddrEntry
    MAX-ACCESS       not-accessible
    STATUS           current
    DESCRIPTION
        "Cisco Firepower mgmt:IPv6IfAddr managed object table"
    ::= { cfprMgmtObjects 26 }

cfprMgmtIPv6IfAddrEntry OBJECT-TYPE
    SYNTAX           CfprMgmtIPv6IfAddrEntry
    MAX-ACCESS       not-accessible
    STATUS           current
    DESCRIPTION
        "Entry for the cfprMgmtIPv6IfAddrTable table."
    INDEX { cfprMgmtIPv6IfAddrInstanceId }
    ::= { cfprMgmtIPv6IfAddrTable 1 }

CfprMgmtIPv6IfAddrEntry ::= SEQUENCE {
    cfprMgmtIPv6IfAddrInstanceId                                     CfprManagedObjectId,
    cfprMgmtIPv6IfAddrDn                                             CfprManagedObjectDn,
    cfprMgmtIPv6IfAddrRn                                             SnmpAdminString,
    cfprMgmtIPv6IfAddrAddr                                           InetAddressIPv6,
    cfprMgmtIPv6IfAddrDefGw                                          InetAddressIPv6,
    cfprMgmtIPv6IfAddrFsmDescr                                       SnmpAdminString,
    cfprMgmtIPv6IfAddrFsmPrev                                        SnmpAdminString,
    cfprMgmtIPv6IfAddrFsmProgr                                       Gauge32,
    cfprMgmtIPv6IfAddrFsmRmtInvErrCode                               Gauge32,
    cfprMgmtIPv6IfAddrFsmRmtInvErrDescr                              SnmpAdminString,
    cfprMgmtIPv6IfAddrFsmRmtInvRslt                                  CfprConditionRemoteInvRslt,
    cfprMgmtIPv6IfAddrFsmStageDescr                                  SnmpAdminString,
    cfprMgmtIPv6IfAddrFsmStamp                                       DateAndTime,
    cfprMgmtIPv6IfAddrFsmStatus                                      SnmpAdminString,
    cfprMgmtIPv6IfAddrFsmTry                                         Gauge32,
    cfprMgmtIPv6IfAddrPrefix                                         Gauge32
}

cfprMgmtIPv6IfAddrInstanceId OBJECT-TYPE
    SYNTAX       CfprManagedObjectId
    MAX-ACCESS   not-accessible
    STATUS       current
    DESCRIPTION
        "Instance identifier of the managed object."
    ::= { cfprMgmtIPv6IfAddrEntry 1 }

cfprMgmtIPv6IfAddrDn OBJECT-TYPE
    SYNTAX       CfprManagedObjectDn
    MAX-ACCESS   read-only
    STATUS       current
    DESCRIPTION
        "Cisco Firepower mgmt:IPv6IfAddr:dn managed object property"
    ::= { cfprMgmtIPv6IfAddrEntry 2 }

cfprMgmtIPv6IfAddrRn OBJECT-TYPE
    SYNTAX       SnmpAdminString
    MAX-ACCESS   read-only
    STATUS       current
    DESCRIPTION
        "Cisco Firepower mgmt:IPv6IfAddr:rn managed object property"
    ::= { cfprMgmtIPv6IfAddrEntry 3 }

cfprMgmtIPv6IfAddrAddr OBJECT-TYPE
    SYNTAX       InetAddressIPv6
    MAX-ACCESS   read-only
    STATUS       current
    DESCRIPTION
        "Cisco Firepower mgmt:IPv6IfAddr:addr managed object property"
    ::= { cfprMgmtIPv6IfAddrEntry 4 }

cfprMgmtIPv6IfAddrDefGw OBJECT-TYPE
    SYNTAX       InetAddressIPv6
    MAX-ACCESS   read-only
    STATUS       current
    DESCRIPTION
        "Cisco Firepower mgmt:IPv6IfAddr:defGw managed object property"
    ::= { cfprMgmtIPv6IfAddrEntry 5 }

cfprMgmtIPv6IfAddrFsmDescr OBJECT-TYPE
    SYNTAX       SnmpAdminString
    MAX-ACCESS   read-only
    STATUS       current
    DESCRIPTION
        "Cisco Firepower mgmt:IPv6IfAddr:fsmDescr managed object property"
    ::= { cfprMgmtIPv6IfAddrEntry 6 }

cfprMgmtIPv6IfAddrFsmPrev OBJECT-TYPE
    SYNTAX       SnmpAdminString
    MAX-ACCESS   read-only
    STATUS       current
    DESCRIPTION
        "Cisco Firepower mgmt:IPv6IfAddr:fsmPrev managed object property"
    ::= { cfprMgmtIPv6IfAddrEntry 7 }

cfprMgmtIPv6IfAddrFsmProgr OBJECT-TYPE
    SYNTAX       Gauge32
    MAX-ACCESS   read-only
    STATUS       current
    DESCRIPTION
        "Cisco Firepower mgmt:IPv6IfAddr:fsmProgr managed object property"
    ::= { cfprMgmtIPv6IfAddrEntry 8 }

cfprMgmtIPv6IfAddrFsmRmtInvErrCode OBJECT-TYPE
    SYNTAX       Gauge32
    MAX-ACCESS   read-only
    STATUS       current
    DESCRIPTION
        "Cisco Firepower mgmt:IPv6IfAddr:fsmRmtInvErrCode
        managed object property"
    ::= { cfprMgmtIPv6IfAddrEntry 9 }

cfprMgmtIPv6IfAddrFsmRmtInvErrDescr OBJECT-TYPE
    SYNTAX       SnmpAdminString
    MAX-ACCESS   read-only
    STATUS       current
    DESCRIPTION
        "Cisco Firepower mgmt:IPv6IfAddr:fsmRmtInvErrDescr
        managed object property"
    ::= { cfprMgmtIPv6IfAddrEntry 10 }

cfprMgmtIPv6IfAddrFsmRmtInvRslt OBJECT-TYPE
    SYNTAX       CfprConditionRemoteInvRslt
    MAX-ACCESS   read-only
    STATUS       current
    DESCRIPTION
        "Cisco Firepower mgmt:IPv6IfAddr:fsmRmtInvRslt
        managed object property"
    ::= { cfprMgmtIPv6IfAddrEntry 11 }

cfprMgmtIPv6IfAddrFsmStageDescr OBJECT-TYPE
    SYNTAX       SnmpAdminString
    MAX-ACCESS   read-only
    STATUS       current
    DESCRIPTION
        "Cisco Firepower mgmt:IPv6IfAddr:fsmStageDescr
        managed object property"
    ::= { cfprMgmtIPv6IfAddrEntry 12 }

cfprMgmtIPv6IfAddrFsmStamp OBJECT-TYPE
    SYNTAX       DateAndTime
    MAX-ACCESS   read-only
    STATUS       current
    DESCRIPTION
        "Cisco Firepower mgmt:IPv6IfAddr:fsmStamp managed object property"
    ::= { cfprMgmtIPv6IfAddrEntry 13 }

cfprMgmtIPv6IfAddrFsmStatus OBJECT-TYPE
    SYNTAX       SnmpAdminString
    MAX-ACCESS   read-only
    STATUS       current
    DESCRIPTION
        "Cisco Firepower mgmt:IPv6IfAddr:fsmStatus managed
        object property"
    ::= { cfprMgmtIPv6IfAddrEntry 14 }

cfprMgmtIPv6IfAddrFsmTry OBJECT-TYPE
    SYNTAX       Gauge32
    MAX-ACCESS   read-only
    STATUS       current
    DESCRIPTION
        "Cisco Firepower mgmt:IPv6IfAddr:fsmTry managed object property"
    ::= { cfprMgmtIPv6IfAddrEntry 15 }

cfprMgmtIPv6IfAddrPrefix OBJECT-TYPE
    SYNTAX       Gauge32
    MAX-ACCESS   read-only
    STATUS       current
    DESCRIPTION
        "Cisco Firepower mgmt:IPv6IfAddr:prefix managed object property"
    ::= { cfprMgmtIPv6IfAddrEntry 16 }

cfprMgmtIPv6IfAddrFsmTable OBJECT-TYPE
    SYNTAX           SEQUENCE OF CfprMgmtIPv6IfAddrFsmEntry
    MAX-ACCESS       not-accessible
    STATUS           current
    DESCRIPTION
        "Cisco Firepower mgmt:IPv6IfAddrFsm managed object table"
    ::= { cfprMgmtObjects 27 }

cfprMgmtIPv6IfAddrFsmEntry OBJECT-TYPE
    SYNTAX           CfprMgmtIPv6IfAddrFsmEntry
    MAX-ACCESS       not-accessible
    STATUS           current
    DESCRIPTION
        "Entry for the cfprMgmtIPv6IfAddrFsmTable table."
    INDEX { cfprMgmtIPv6IfAddrFsmInstanceId }
    ::= { cfprMgmtIPv6IfAddrFsmTable 1 }

CfprMgmtIPv6IfAddrFsmEntry ::= SEQUENCE {
    cfprMgmtIPv6IfAddrFsmInstanceId                                  CfprManagedObjectId,
    cfprMgmtIPv6IfAddrFsmDn                                          CfprManagedObjectDn,
    cfprMgmtIPv6IfAddrFsmRn                                          SnmpAdminString,
    cfprMgmtIPv6IfAddrFsmCompletionTime                              DateAndTime,
    cfprMgmtIPv6IfAddrFsmCurrentFsm                                  CfprMgmtIPv6IfAddrFsmCurrentFsm,
    cfprMgmtIPv6IfAddrFsmDescrData                                   SnmpAdminString,
    cfprMgmtIPv6IfAddrFsmFsmStatus                                   CfprFsmFsmStageStatus,
    cfprMgmtIPv6IfAddrFsmProgress                                    Gauge32,
    cfprMgmtIPv6IfAddrFsmRmtErrCode                                  Gauge32,
    cfprMgmtIPv6IfAddrFsmRmtErrDescr                                 SnmpAdminString,
    cfprMgmtIPv6IfAddrFsmRmtRslt                                     CfprConditionRemoteInvRslt
}

cfprMgmtIPv6IfAddrFsmInstanceId OBJECT-TYPE
    SYNTAX       CfprManagedObjectId
    MAX-ACCESS   not-accessible
    STATUS       current
    DESCRIPTION
        "Instance identifier of the managed object."
    ::= { cfprMgmtIPv6IfAddrFsmEntry 1 }

cfprMgmtIPv6IfAddrFsmDn OBJECT-TYPE
    SYNTAX       CfprManagedObjectDn
    MAX-ACCESS   read-only
    STATUS       current
    DESCRIPTION
        "Cisco Firepower mgmt:IPv6IfAddrFsm:dn managed object property"
    ::= { cfprMgmtIPv6IfAddrFsmEntry 2 }

cfprMgmtIPv6IfAddrFsmRn OBJECT-TYPE
    SYNTAX       SnmpAdminString
    MAX-ACCESS   read-only
    STATUS       current
    DESCRIPTION
        "Cisco Firepower mgmt:IPv6IfAddrFsm:rn managed object property"
    ::= { cfprMgmtIPv6IfAddrFsmEntry 3 }

cfprMgmtIPv6IfAddrFsmCompletionTime OBJECT-TYPE
    SYNTAX       DateAndTime
    MAX-ACCESS   read-only
    STATUS       current
    DESCRIPTION
        "Cisco Firepower mgmt:IPv6IfAddrFsm:completionTime
        managed object property"
    ::= { cfprMgmtIPv6IfAddrFsmEntry 4 }

cfprMgmtIPv6IfAddrFsmCurrentFsm OBJECT-TYPE
    SYNTAX       CfprMgmtIPv6IfAddrFsmCurrentFsm
    MAX-ACCESS   read-only
    STATUS       current
    DESCRIPTION
        "Cisco Firepower mgmt:IPv6IfAddrFsm:currentFsm
        managed object property"
    ::= { cfprMgmtIPv6IfAddrFsmEntry 5 }

cfprMgmtIPv6IfAddrFsmDescrData OBJECT-TYPE
    SYNTAX       SnmpAdminString
    MAX-ACCESS   read-only
    STATUS       current
    DESCRIPTION
        "Cisco Firepower mgmt:IPv6IfAddrFsm:descr managed object property"
    ::= { cfprMgmtIPv6IfAddrFsmEntry 6 }

cfprMgmtIPv6IfAddrFsmFsmStatus OBJECT-TYPE
    SYNTAX       CfprFsmFsmStageStatus
    MAX-ACCESS   read-only
    STATUS       current
    DESCRIPTION
        "Cisco Firepower mgmt:IPv6IfAddrFsm:fsmStatus managed
        object property"
    ::= { cfprMgmtIPv6IfAddrFsmEntry 7 }

cfprMgmtIPv6IfAddrFsmProgress OBJECT-TYPE
    SYNTAX       Gauge32
    MAX-ACCESS   read-only
    STATUS       current
    DESCRIPTION
        "Cisco Firepower mgmt:IPv6IfAddrFsm:progress managed
        object property"
    ::= { cfprMgmtIPv6IfAddrFsmEntry 8 }

cfprMgmtIPv6IfAddrFsmRmtErrCode OBJECT-TYPE
    SYNTAX       Gauge32
    MAX-ACCESS   read-only
    STATUS       current
    DESCRIPTION
        "Cisco Firepower mgmt:IPv6IfAddrFsm:rmtErrCode
        managed object property"
    ::= { cfprMgmtIPv6IfAddrFsmEntry 9 }

cfprMgmtIPv6IfAddrFsmRmtErrDescr OBJECT-TYPE
    SYNTAX       SnmpAdminString
    MAX-ACCESS   read-only
    STATUS       current
    DESCRIPTION
        "Cisco Firepower mgmt:IPv6IfAddrFsm:rmtErrDescr
        managed object property"
    ::= { cfprMgmtIPv6IfAddrFsmEntry 10 }

cfprMgmtIPv6IfAddrFsmRmtRslt OBJECT-TYPE
    SYNTAX       CfprConditionRemoteInvRslt
    MAX-ACCESS   read-only
    STATUS       current
    DESCRIPTION
        "Cisco Firepower mgmt:IPv6IfAddrFsm:rmtRslt managed
        object property"
    ::= { cfprMgmtIPv6IfAddrFsmEntry 11 }

cfprMgmtIPv6IfAddrFsmStageTable OBJECT-TYPE
    SYNTAX           SEQUENCE OF CfprMgmtIPv6IfAddrFsmStageEntry
    MAX-ACCESS       not-accessible
    STATUS           current
    DESCRIPTION
        "Cisco Firepower mgmt:IPv6IfAddrFsmStage managed object table"
    ::= { cfprMgmtObjects 28 }

cfprMgmtIPv6IfAddrFsmStageEntry OBJECT-TYPE
    SYNTAX           CfprMgmtIPv6IfAddrFsmStageEntry
    MAX-ACCESS       not-accessible
    STATUS           current
    DESCRIPTION
        "Entry for the cfprMgmtIPv6IfAddrFsmStageTable table."
    INDEX { cfprMgmtIPv6IfAddrFsmStageInstanceId }
    ::= { cfprMgmtIPv6IfAddrFsmStageTable 1 }

CfprMgmtIPv6IfAddrFsmStageEntry ::= SEQUENCE {
    cfprMgmtIPv6IfAddrFsmStageInstanceId                             CfprManagedObjectId,
    cfprMgmtIPv6IfAddrFsmStageDn                                     CfprManagedObjectDn,
    cfprMgmtIPv6IfAddrFsmStageRn                                     SnmpAdminString,
    cfprMgmtIPv6IfAddrFsmStageDescrData                              SnmpAdminString,
    cfprMgmtIPv6IfAddrFsmStageLastUpdateTime                         DateAndTime,
    cfprMgmtIPv6IfAddrFsmStageName                                   CfprMgmtIPv6IfAddrFsmStageName,
    cfprMgmtIPv6IfAddrFsmStageOrder                                  Gauge32,
    cfprMgmtIPv6IfAddrFsmStageRetry                                  Gauge32,
    cfprMgmtIPv6IfAddrFsmStageStageStatus                            CfprFsmFsmStageStatus
}

cfprMgmtIPv6IfAddrFsmStageInstanceId OBJECT-TYPE
    SYNTAX       CfprManagedObjectId
    MAX-ACCESS   not-accessible
    STATUS       current
    DESCRIPTION
        "Instance identifier of the managed object."
    ::= { cfprMgmtIPv6IfAddrFsmStageEntry 1 }

cfprMgmtIPv6IfAddrFsmStageDn OBJECT-TYPE
    SYNTAX       CfprManagedObjectDn
    MAX-ACCESS   read-only
    STATUS       current
    DESCRIPTION
        "Cisco Firepower mgmt:IPv6IfAddrFsmStage:dn managed
        object property"
    ::= { cfprMgmtIPv6IfAddrFsmStageEntry 2 }

cfprMgmtIPv6IfAddrFsmStageRn OBJECT-TYPE
    SYNTAX       SnmpAdminString
    MAX-ACCESS   read-only
    STATUS       current
    DESCRIPTION
        "Cisco Firepower mgmt:IPv6IfAddrFsmStage:rn managed
        object property"
    ::= { cfprMgmtIPv6IfAddrFsmStageEntry 3 }

cfprMgmtIPv6IfAddrFsmStageDescrData OBJECT-TYPE
    SYNTAX       SnmpAdminString
    MAX-ACCESS   read-only
    STATUS       current
    DESCRIPTION
        "Cisco Firepower mgmt:IPv6IfAddrFsmStage:descr
        managed object property"
    ::= { cfprMgmtIPv6IfAddrFsmStageEntry 4 }

cfprMgmtIPv6IfAddrFsmStageLastUpdateTime OBJECT-TYPE
    SYNTAX       DateAndTime
    MAX-ACCESS   read-only
    STATUS       current
    DESCRIPTION
        "Cisco Firepower mgmt:IPv6IfAddrFsmStage:lastUpdateTime
        managed object property"
    ::= { cfprMgmtIPv6IfAddrFsmStageEntry 5 }

cfprMgmtIPv6IfAddrFsmStageName OBJECT-TYPE
    SYNTAX       CfprMgmtIPv6IfAddrFsmStageName
    MAX-ACCESS   read-only
    STATUS       current
    DESCRIPTION
        "Cisco Firepower mgmt:IPv6IfAddrFsmStage:name managed
        object property"
    ::= { cfprMgmtIPv6IfAddrFsmStageEntry 6 }

cfprMgmtIPv6IfAddrFsmStageOrder OBJECT-TYPE
    SYNTAX       Gauge32
    MAX-ACCESS   read-only
    STATUS       current
    DESCRIPTION
        "Cisco Firepower mgmt:IPv6IfAddrFsmStage:order
        managed object property"
    ::= { cfprMgmtIPv6IfAddrFsmStageEntry 7 }

cfprMgmtIPv6IfAddrFsmStageRetry OBJECT-TYPE
    SYNTAX       Gauge32
    MAX-ACCESS   read-only
    STATUS       current
    DESCRIPTION
        "Cisco Firepower mgmt:IPv6IfAddrFsmStage:retry
        managed object property"
    ::= { cfprMgmtIPv6IfAddrFsmStageEntry 8 }

cfprMgmtIPv6IfAddrFsmStageStageStatus OBJECT-TYPE
    SYNTAX       CfprFsmFsmStageStatus
    MAX-ACCESS   read-only
    STATUS       current
    DESCRIPTION
        "Cisco Firepower mgmt:IPv6IfAddrFsmStage:stageStatus
        managed object property"
    ::= { cfprMgmtIPv6IfAddrFsmStageEntry 9 }

cfprMgmtIPv6IfAddrFsmTaskTable OBJECT-TYPE
    SYNTAX           SEQUENCE OF CfprMgmtIPv6IfAddrFsmTaskEntry
    MAX-ACCESS       not-accessible
    STATUS           current
    DESCRIPTION
        "Cisco Firepower mgmt:IPv6IfAddrFsmTask managed object table"
    ::= { cfprMgmtObjects 29 }

cfprMgmtIPv6IfAddrFsmTaskEntry OBJECT-TYPE
    SYNTAX           CfprMgmtIPv6IfAddrFsmTaskEntry
    MAX-ACCESS       not-accessible
    STATUS           current
    DESCRIPTION
        "Entry for the cfprMgmtIPv6IfAddrFsmTaskTable table."
    INDEX { cfprMgmtIPv6IfAddrFsmTaskInstanceId }
    ::= { cfprMgmtIPv6IfAddrFsmTaskTable 1 }

CfprMgmtIPv6IfAddrFsmTaskEntry ::= SEQUENCE {
    cfprMgmtIPv6IfAddrFsmTaskInstanceId                              CfprManagedObjectId,
    cfprMgmtIPv6IfAddrFsmTaskDn                                      CfprManagedObjectDn,
    cfprMgmtIPv6IfAddrFsmTaskRn                                      SnmpAdminString,
    cfprMgmtIPv6IfAddrFsmTaskCompletion                              CfprFsmCompletion,
    cfprMgmtIPv6IfAddrFsmTaskFlags                                   CfprFsmFlags,
    cfprMgmtIPv6IfAddrFsmTaskItem                                    CfprMgmtIPv6IfAddrFsmTaskItem,
    cfprMgmtIPv6IfAddrFsmTaskSeqId                                   Gauge32
}

cfprMgmtIPv6IfAddrFsmTaskInstanceId OBJECT-TYPE
    SYNTAX       CfprManagedObjectId
    MAX-ACCESS   not-accessible
    STATUS       current
    DESCRIPTION
        "Instance identifier of the managed object."
    ::= { cfprMgmtIPv6IfAddrFsmTaskEntry 1 }

cfprMgmtIPv6IfAddrFsmTaskDn OBJECT-TYPE
    SYNTAX       CfprManagedObjectDn
    MAX-ACCESS   read-only
    STATUS       current
    DESCRIPTION
        "Cisco Firepower mgmt:IPv6IfAddrFsmTask:dn managed
        object property"
    ::= { cfprMgmtIPv6IfAddrFsmTaskEntry 2 }

cfprMgmtIPv6IfAddrFsmTaskRn OBJECT-TYPE
    SYNTAX       SnmpAdminString
    MAX-ACCESS   read-only
    STATUS       current
    DESCRIPTION
        "Cisco Firepower mgmt:IPv6IfAddrFsmTask:rn managed
        object property"
    ::= { cfprMgmtIPv6IfAddrFsmTaskEntry 3 }

cfprMgmtIPv6IfAddrFsmTaskCompletion OBJECT-TYPE
    SYNTAX       CfprFsmCompletion
    MAX-ACCESS   read-only
    STATUS       current
    DESCRIPTION
        "Cisco Firepower mgmt:IPv6IfAddrFsmTask:completion
        managed object property"
    ::= { cfprMgmtIPv6IfAddrFsmTaskEntry 4 }

cfprMgmtIPv6IfAddrFsmTaskFlags OBJECT-TYPE
    SYNTAX       CfprFsmFlags
    MAX-ACCESS   read-only
    STATUS       current
    DESCRIPTION
        "Cisco Firepower mgmt:IPv6IfAddrFsmTask:flags managed
        object property"
    ::= { cfprMgmtIPv6IfAddrFsmTaskEntry 5 }

cfprMgmtIPv6IfAddrFsmTaskItem OBJECT-TYPE
    SYNTAX       CfprMgmtIPv6IfAddrFsmTaskItem
    MAX-ACCESS   read-only
    STATUS       current
    DESCRIPTION
        "Cisco Firepower mgmt:IPv6IfAddrFsmTask:item managed
        object property"
    ::= { cfprMgmtIPv6IfAddrFsmTaskEntry 6 }

cfprMgmtIPv6IfAddrFsmTaskSeqId OBJECT-TYPE
    SYNTAX       Gauge32
    MAX-ACCESS   read-only
    STATUS       current
    DESCRIPTION
        "Cisco Firepower mgmt:IPv6IfAddrFsmTask:seqId managed
        object property"
    ::= { cfprMgmtIPv6IfAddrFsmTaskEntry 7 }

cfprMgmtIPv6IfConfigTable OBJECT-TYPE
    SYNTAX           SEQUENCE OF CfprMgmtIPv6IfConfigEntry
    MAX-ACCESS       not-accessible
    STATUS           current
    DESCRIPTION
        "Cisco Firepower mgmt:IPv6IfConfig managed object table"
    ::= { cfprMgmtObjects 30 }

cfprMgmtIPv6IfConfigEntry OBJECT-TYPE
    SYNTAX           CfprMgmtIPv6IfConfigEntry
    MAX-ACCESS       not-accessible
    STATUS           current
    DESCRIPTION
        "Entry for the cfprMgmtIPv6IfConfigTable table."
    INDEX { cfprMgmtIPv6IfConfigInstanceId }
    ::= { cfprMgmtIPv6IfConfigTable 1 }

CfprMgmtIPv6IfConfigEntry ::= SEQUENCE {
    cfprMgmtIPv6IfConfigInstanceId                                   CfprManagedObjectId,
    cfprMgmtIPv6IfConfigDn                                           CfprManagedObjectDn,
    cfprMgmtIPv6IfConfigRn                                           SnmpAdminString
}

cfprMgmtIPv6IfConfigInstanceId OBJECT-TYPE
    SYNTAX       CfprManagedObjectId
    MAX-ACCESS   not-accessible
    STATUS       current
    DESCRIPTION
        "Instance identifier of the managed object."
    ::= { cfprMgmtIPv6IfConfigEntry 1 }

cfprMgmtIPv6IfConfigDn OBJECT-TYPE
    SYNTAX       CfprManagedObjectDn
    MAX-ACCESS   read-only
    STATUS       current
    DESCRIPTION
        "Cisco Firepower mgmt:IPv6IfConfig:dn managed object property"
    ::= { cfprMgmtIPv6IfConfigEntry 2 }

cfprMgmtIPv6IfConfigRn OBJECT-TYPE
    SYNTAX       SnmpAdminString
    MAX-ACCESS   read-only
    STATUS       current
    DESCRIPTION
        "Cisco Firepower mgmt:IPv6IfConfig:rn managed object property"
    ::= { cfprMgmtIPv6IfConfigEntry 3 }

cfprMgmtIfTable OBJECT-TYPE
    SYNTAX           SEQUENCE OF CfprMgmtIfEntry
    MAX-ACCESS       not-accessible
    STATUS           current
    DESCRIPTION
        "Cisco Firepower mgmt:If managed object table"
    ::= { cfprMgmtObjects 31 }

cfprMgmtIfEntry OBJECT-TYPE
    SYNTAX           CfprMgmtIfEntry
    MAX-ACCESS       not-accessible
    STATUS           current
    DESCRIPTION
        "Entry for the cfprMgmtIfTable table."
    INDEX { cfprMgmtIfInstanceId }
    ::= { cfprMgmtIfTable 1 }

CfprMgmtIfEntry ::= SEQUENCE {
    cfprMgmtIfInstanceId                                             CfprManagedObjectId,
    cfprMgmtIfDn                                                     CfprManagedObjectDn,
    cfprMgmtIfRn                                                     SnmpAdminString,
    cfprMgmtIfAccess                                                 CfprMgmtAccess,
    cfprMgmtIfAdminState                                             CfprMgmtAdminState,
    cfprMgmtIfAggrPortId                                             Gauge32,
    cfprMgmtIfChassisId                                              Gauge32,
    cfprMgmtIfDiscovery                                              CfprEtherSatelliteConnectionDisc,
    cfprMgmtIfEpDn                                                   SnmpAdminString,
    cfprMgmtIfExtBroadcast                                           InetAddressIPv4,
    cfprMgmtIfExtGw                                                  InetAddressIPv4,
    cfprMgmtIfExtIp                                                  InetAddressIPv4,
    cfprMgmtIfExtMask                                                InetAddressIPv4,
    cfprMgmtIfFsmDescr                                               SnmpAdminString,
    cfprMgmtIfFsmPrev                                                SnmpAdminString,
    cfprMgmtIfFsmProgr                                               Gauge32,
    cfprMgmtIfFsmRmtInvErrCode                                       Gauge32,
    cfprMgmtIfFsmRmtInvErrDescr                                      SnmpAdminString,
    cfprMgmtIfFsmRmtInvRslt                                          CfprConditionRemoteInvRslt,
    cfprMgmtIfFsmStageDescr                                          SnmpAdminString,
    cfprMgmtIfFsmStamp                                               DateAndTime,
    cfprMgmtIfFsmStatus                                              SnmpAdminString,
    cfprMgmtIfFsmTry                                                 Gauge32,
    cfprMgmtIfId                                                     Gauge32,
    cfprMgmtIfIfRole                                                 CfprNetworkPortRole,
    cfprMgmtIfIfType                                                 CfprNetworkPhysEpIfType,
    cfprMgmtIfIp                                                     InetAddressIPv4,
    cfprMgmtIfLocale                                                 CfprNetworkLocale,
    cfprMgmtIfMac                                                    MacAddress,
    cfprMgmtIfMask                                                   InetAddressIPv4,
    cfprMgmtIfName                                                   SnmpAdminString,
    cfprMgmtIfPeerAggrPortId                                         Gauge32,
    cfprMgmtIfPeerChassisId                                          Gauge32,
    cfprMgmtIfPeerDn                                                 SnmpAdminString,
    cfprMgmtIfPeerPortId                                             Gauge32,
    cfprMgmtIfPeerSlotId                                             Gauge32,
    cfprMgmtIfPortId                                                 Gauge32,
    cfprMgmtIfSlotId                                                 Gauge32,
    cfprMgmtIfStateQual                                              CfprMgmtStateQual,
    cfprMgmtIfSubject                                                CfprMgmtSubject,
    cfprMgmtIfSwitchId                                               CfprNetworkSwitchId,
    cfprMgmtIfTransport                                              CfprNetworkTransport,
    cfprMgmtIfType                                                   CfprNetworkConnectionType,
    cfprMgmtIfVnet                                                   Gauge32
}

cfprMgmtIfInstanceId OBJECT-TYPE
    SYNTAX       CfprManagedObjectId
    MAX-ACCESS   not-accessible
    STATUS       current
    DESCRIPTION
        "Instance identifier of the managed object."
    ::= { cfprMgmtIfEntry 1 }

cfprMgmtIfDn OBJECT-TYPE
    SYNTAX       CfprManagedObjectDn
    MAX-ACCESS   read-only
    STATUS       current
    DESCRIPTION
        "Cisco Firepower mgmt:If:dn managed object property"
    ::= { cfprMgmtIfEntry 2 }

cfprMgmtIfRn OBJECT-TYPE
    SYNTAX       SnmpAdminString
    MAX-ACCESS   read-only
    STATUS       current
    DESCRIPTION
        "Cisco Firepower mgmt:If:rn managed object property"
    ::= { cfprMgmtIfEntry 3 }

cfprMgmtIfAccess OBJECT-TYPE
    SYNTAX       CfprMgmtAccess
    MAX-ACCESS   read-only
    STATUS       current
    DESCRIPTION
        "Cisco Firepower mgmt:If:access managed object property"
    ::= { cfprMgmtIfEntry 4 }

cfprMgmtIfAdminState OBJECT-TYPE
    SYNTAX       CfprMgmtAdminState
    MAX-ACCESS   read-only
    STATUS       current
    DESCRIPTION
        "Cisco Firepower mgmt:If:adminState managed object property"
    ::= { cfprMgmtIfEntry 5 }

cfprMgmtIfAggrPortId OBJECT-TYPE
    SYNTAX       Gauge32
    MAX-ACCESS   read-only
    STATUS       current
    DESCRIPTION
        "Cisco Firepower mgmt:If:aggrPortId managed object property"
    ::= { cfprMgmtIfEntry 6 }

cfprMgmtIfChassisId OBJECT-TYPE
    SYNTAX       Gauge32
    MAX-ACCESS   read-only
    STATUS       current
    DESCRIPTION
        "Cisco Firepower mgmt:If:chassisId managed object property"
    ::= { cfprMgmtIfEntry 7 }

cfprMgmtIfDiscovery OBJECT-TYPE
    SYNTAX       CfprEtherSatelliteConnectionDisc
    MAX-ACCESS   read-only
    STATUS       current
    DESCRIPTION
        "Cisco Firepower mgmt:If:discovery managed object property"
    ::= { cfprMgmtIfEntry 8 }

cfprMgmtIfEpDn OBJECT-TYPE
    SYNTAX       SnmpAdminString
    MAX-ACCESS   read-only
    STATUS       current
    DESCRIPTION
        "Cisco Firepower mgmt:If:epDn managed object property"
    ::= { cfprMgmtIfEntry 9 }

cfprMgmtIfExtBroadcast OBJECT-TYPE
    SYNTAX       InetAddressIPv4
    MAX-ACCESS   read-only
    STATUS       current
    DESCRIPTION
        "Cisco Firepower mgmt:If:extBroadcast managed object property"
    ::= { cfprMgmtIfEntry 10 }

cfprMgmtIfExtGw OBJECT-TYPE
    SYNTAX       InetAddressIPv4
    MAX-ACCESS   read-only
    STATUS       current
    DESCRIPTION
        "Cisco Firepower mgmt:If:extGw managed object property"
    ::= { cfprMgmtIfEntry 11 }

cfprMgmtIfExtIp OBJECT-TYPE
    SYNTAX       InetAddressIPv4
    MAX-ACCESS   read-only
    STATUS       current
    DESCRIPTION
        "Cisco Firepower mgmt:If:extIp managed object property"
    ::= { cfprMgmtIfEntry 12 }

cfprMgmtIfExtMask OBJECT-TYPE
    SYNTAX       InetAddressIPv4
    MAX-ACCESS   read-only
    STATUS       current
    DESCRIPTION
        "Cisco Firepower mgmt:If:extMask managed object property"
    ::= { cfprMgmtIfEntry 13 }

cfprMgmtIfFsmDescr OBJECT-TYPE
    SYNTAX       SnmpAdminString
    MAX-ACCESS   read-only
    STATUS       current
    DESCRIPTION
        "Cisco Firepower mgmt:If:fsmDescr managed object property"
    ::= { cfprMgmtIfEntry 14 }

cfprMgmtIfFsmPrev OBJECT-TYPE
    SYNTAX       SnmpAdminString
    MAX-ACCESS   read-only
    STATUS       current
    DESCRIPTION
        "Cisco Firepower mgmt:If:fsmPrev managed object property"
    ::= { cfprMgmtIfEntry 15 }

cfprMgmtIfFsmProgr OBJECT-TYPE
    SYNTAX       Gauge32
    MAX-ACCESS   read-only
    STATUS       current
    DESCRIPTION
        "Cisco Firepower mgmt:If:fsmProgr managed object property"
    ::= { cfprMgmtIfEntry 16 }

cfprMgmtIfFsmRmtInvErrCode OBJECT-TYPE
    SYNTAX       Gauge32
    MAX-ACCESS   read-only
    STATUS       current
    DESCRIPTION
        "Cisco Firepower mgmt:If:fsmRmtInvErrCode managed object property"
    ::= { cfprMgmtIfEntry 17 }

cfprMgmtIfFsmRmtInvErrDescr OBJECT-TYPE
    SYNTAX       SnmpAdminString
    MAX-ACCESS   read-only
    STATUS       current
    DESCRIPTION
        "Cisco Firepower mgmt:If:fsmRmtInvErrDescr managed
        object property"
    ::= { cfprMgmtIfEntry 18 }

cfprMgmtIfFsmRmtInvRslt OBJECT-TYPE
    SYNTAX       CfprConditionRemoteInvRslt
    MAX-ACCESS   read-only
    STATUS       current
    DESCRIPTION
        "Cisco Firepower mgmt:If:fsmRmtInvRslt managed object property"
    ::= { cfprMgmtIfEntry 19 }

cfprMgmtIfFsmStageDescr OBJECT-TYPE
    SYNTAX       SnmpAdminString
    MAX-ACCESS   read-only
    STATUS       current
    DESCRIPTION
        "Cisco Firepower mgmt:If:fsmStageDescr managed object property"
    ::= { cfprMgmtIfEntry 20 }

cfprMgmtIfFsmStamp OBJECT-TYPE
    SYNTAX       DateAndTime
    MAX-ACCESS   read-only
    STATUS       current
    DESCRIPTION
        "Cisco Firepower mgmt:If:fsmStamp managed object property"
    ::= { cfprMgmtIfEntry 21 }

cfprMgmtIfFsmStatus OBJECT-TYPE
    SYNTAX       SnmpAdminString
    MAX-ACCESS   read-only
    STATUS       current
    DESCRIPTION
        "Cisco Firepower mgmt:If:fsmStatus managed object property"
    ::= { cfprMgmtIfEntry 22 }

cfprMgmtIfFsmTry OBJECT-TYPE
    SYNTAX       Gauge32
    MAX-ACCESS   read-only
    STATUS       current
    DESCRIPTION
        "Cisco Firepower mgmt:If:fsmTry managed object property"
    ::= { cfprMgmtIfEntry 23 }

cfprMgmtIfId OBJECT-TYPE
    SYNTAX       Gauge32
    MAX-ACCESS   read-only
    STATUS       current
    DESCRIPTION
        "Cisco Firepower mgmt:If:id managed object property"
    ::= { cfprMgmtIfEntry 24 }

cfprMgmtIfIfRole OBJECT-TYPE
    SYNTAX       CfprNetworkPortRole
    MAX-ACCESS   read-only
    STATUS       current
    DESCRIPTION
        "Cisco Firepower mgmt:If:ifRole managed object property"
    ::= { cfprMgmtIfEntry 25 }

cfprMgmtIfIfType OBJECT-TYPE
    SYNTAX       CfprNetworkPhysEpIfType
    MAX-ACCESS   read-only
    STATUS       current
    DESCRIPTION
        "Cisco Firepower mgmt:If:ifType managed object property"
    ::= { cfprMgmtIfEntry 26 }

cfprMgmtIfIp OBJECT-TYPE
    SYNTAX       InetAddressIPv4
    MAX-ACCESS   read-only
    STATUS       current
    DESCRIPTION
        "Cisco Firepower mgmt:If:ip managed object property"
    ::= { cfprMgmtIfEntry 27 }

cfprMgmtIfLocale OBJECT-TYPE
    SYNTAX       CfprNetworkLocale
    MAX-ACCESS   read-only
    STATUS       current
    DESCRIPTION
        "Cisco Firepower mgmt:If:locale managed object property"
    ::= { cfprMgmtIfEntry 28 }

cfprMgmtIfMac OBJECT-TYPE
    SYNTAX       MacAddress
    MAX-ACCESS   read-only
    STATUS       current
    DESCRIPTION
        "Cisco Firepower mgmt:If:mac managed object property"
    ::= { cfprMgmtIfEntry 29 }

cfprMgmtIfMask OBJECT-TYPE
    SYNTAX       InetAddressIPv4
    MAX-ACCESS   read-only
    STATUS       current
    DESCRIPTION
        "Cisco Firepower mgmt:If:mask managed object property"
    ::= { cfprMgmtIfEntry 30 }

cfprMgmtIfName OBJECT-TYPE
    SYNTAX       SnmpAdminString
    MAX-ACCESS   read-only
    STATUS       current
    DESCRIPTION
        "Cisco Firepower mgmt:If:name managed object property"
    ::= { cfprMgmtIfEntry 31 }

cfprMgmtIfPeerAggrPortId OBJECT-TYPE
    SYNTAX       Gauge32
    MAX-ACCESS   read-only
    STATUS       current
    DESCRIPTION
        "Cisco Firepower mgmt:If:peerAggrPortId managed object property"
    ::= { cfprMgmtIfEntry 32 }

cfprMgmtIfPeerChassisId OBJECT-TYPE
    SYNTAX       Gauge32
    MAX-ACCESS   read-only
    STATUS       current
    DESCRIPTION
        "Cisco Firepower mgmt:If:peerChassisId managed object property"
    ::= { cfprMgmtIfEntry 33 }

cfprMgmtIfPeerDn OBJECT-TYPE
    SYNTAX       SnmpAdminString
    MAX-ACCESS   read-only
    STATUS       current
    DESCRIPTION
        "Cisco Firepower mgmt:If:peerDn managed object property"
    ::= { cfprMgmtIfEntry 34 }

cfprMgmtIfPeerPortId OBJECT-TYPE
    SYNTAX       Gauge32
    MAX-ACCESS   read-only
    STATUS       current
    DESCRIPTION
        "Cisco Firepower mgmt:If:peerPortId managed object property"
    ::= { cfprMgmtIfEntry 35 }

cfprMgmtIfPeerSlotId OBJECT-TYPE
    SYNTAX       Gauge32
    MAX-ACCESS   read-only
    STATUS       current
    DESCRIPTION
        "Cisco Firepower mgmt:If:peerSlotId managed object property"
    ::= { cfprMgmtIfEntry 36 }

cfprMgmtIfPortId OBJECT-TYPE
    SYNTAX       Gauge32
    MAX-ACCESS   read-only
    STATUS       current
    DESCRIPTION
        "Cisco Firepower mgmt:If:portId managed object property"
    ::= { cfprMgmtIfEntry 37 }

cfprMgmtIfSlotId OBJECT-TYPE
    SYNTAX       Gauge32
    MAX-ACCESS   read-only
    STATUS       current
    DESCRIPTION
        "Cisco Firepower mgmt:If:slotId managed object property"
    ::= { cfprMgmtIfEntry 38 }

cfprMgmtIfStateQual OBJECT-TYPE
    SYNTAX       CfprMgmtStateQual
    MAX-ACCESS   read-only
    STATUS       current
    DESCRIPTION
        "Cisco Firepower mgmt:If:stateQual managed object property"
    ::= { cfprMgmtIfEntry 39 }

cfprMgmtIfSubject OBJECT-TYPE
    SYNTAX       CfprMgmtSubject
    MAX-ACCESS   read-only
    STATUS       current
    DESCRIPTION
        "Cisco Firepower mgmt:If:subject managed object property"
    ::= { cfprMgmtIfEntry 40 }

cfprMgmtIfSwitchId OBJECT-TYPE
    SYNTAX       CfprNetworkSwitchId
    MAX-ACCESS   read-only
    STATUS       current
    DESCRIPTION
        "Cisco Firepower mgmt:If:switchId managed object property"
    ::= { cfprMgmtIfEntry 41 }

cfprMgmtIfTransport OBJECT-TYPE
    SYNTAX       CfprNetworkTransport
    MAX-ACCESS   read-only
    STATUS       current
    DESCRIPTION
        "Cisco Firepower mgmt:If:transport managed object property"
    ::= { cfprMgmtIfEntry 42 }

cfprMgmtIfType OBJECT-TYPE
    SYNTAX       CfprNetworkConnectionType
    MAX-ACCESS   read-only
    STATUS       current
    DESCRIPTION
        "Cisco Firepower mgmt:If:type managed object property"
    ::= { cfprMgmtIfEntry 43 }

cfprMgmtIfVnet OBJECT-TYPE
    SYNTAX       Gauge32
    MAX-ACCESS   read-only
    STATUS       current
    DESCRIPTION
        "Cisco Firepower mgmt:If:vnet managed object property"
    ::= { cfprMgmtIfEntry 44 }

cfprMgmtIfFsmTable OBJECT-TYPE
    SYNTAX           SEQUENCE OF CfprMgmtIfFsmEntry
    MAX-ACCESS       not-accessible
    STATUS           current
    DESCRIPTION
        "Cisco Firepower mgmt:IfFsm managed object table"
    ::= { cfprMgmtObjects 32 }

cfprMgmtIfFsmEntry OBJECT-TYPE
    SYNTAX           CfprMgmtIfFsmEntry
    MAX-ACCESS       not-accessible
    STATUS           current
    DESCRIPTION
        "Entry for the cfprMgmtIfFsmTable table."
    INDEX { cfprMgmtIfFsmInstanceId }
    ::= { cfprMgmtIfFsmTable 1 }

CfprMgmtIfFsmEntry ::= SEQUENCE {
    cfprMgmtIfFsmInstanceId                                          CfprManagedObjectId,
    cfprMgmtIfFsmDn                                                  CfprManagedObjectDn,
    cfprMgmtIfFsmRn                                                  SnmpAdminString,
    cfprMgmtIfFsmCompletionTime                                      DateAndTime,
    cfprMgmtIfFsmCurrentFsm                                          CfprMgmtIfFsmCurrentFsm,
    cfprMgmtIfFsmDescrData                                           SnmpAdminString,
    cfprMgmtIfFsmFsmStatus                                           CfprFsmFsmStageStatus,
    cfprMgmtIfFsmProgress                                            Gauge32,
    cfprMgmtIfFsmRmtErrCode                                          Gauge32,
    cfprMgmtIfFsmRmtErrDescr                                         SnmpAdminString,
    cfprMgmtIfFsmRmtRslt                                             CfprConditionRemoteInvRslt
}

cfprMgmtIfFsmInstanceId OBJECT-TYPE
    SYNTAX       CfprManagedObjectId
    MAX-ACCESS   not-accessible
    STATUS       current
    DESCRIPTION
        "Instance identifier of the managed object."
    ::= { cfprMgmtIfFsmEntry 1 }

cfprMgmtIfFsmDn OBJECT-TYPE
    SYNTAX       CfprManagedObjectDn
    MAX-ACCESS   read-only
    STATUS       current
    DESCRIPTION
        "Cisco Firepower mgmt:IfFsm:dn managed object property"
    ::= { cfprMgmtIfFsmEntry 2 }

cfprMgmtIfFsmRn OBJECT-TYPE
    SYNTAX       SnmpAdminString
    MAX-ACCESS   read-only
    STATUS       current
    DESCRIPTION
        "Cisco Firepower mgmt:IfFsm:rn managed object property"
    ::= { cfprMgmtIfFsmEntry 3 }

cfprMgmtIfFsmCompletionTime OBJECT-TYPE
    SYNTAX       DateAndTime
    MAX-ACCESS   read-only
    STATUS       current
    DESCRIPTION
        "Cisco Firepower mgmt:IfFsm:completionTime managed
        object property"
    ::= { cfprMgmtIfFsmEntry 4 }

cfprMgmtIfFsmCurrentFsm OBJECT-TYPE
    SYNTAX       CfprMgmtIfFsmCurrentFsm
    MAX-ACCESS   read-only
    STATUS       current
    DESCRIPTION
        "Cisco Firepower mgmt:IfFsm:currentFsm managed object property"
    ::= { cfprMgmtIfFsmEntry 5 }

cfprMgmtIfFsmDescrData OBJECT-TYPE
    SYNTAX       SnmpAdminString
    MAX-ACCESS   read-only
    STATUS       current
    DESCRIPTION
        "Cisco Firepower mgmt:IfFsm:descr managed object property"
    ::= { cfprMgmtIfFsmEntry 6 }

cfprMgmtIfFsmFsmStatus OBJECT-TYPE
    SYNTAX       CfprFsmFsmStageStatus
    MAX-ACCESS   read-only
    STATUS       current
    DESCRIPTION
        "Cisco Firepower mgmt:IfFsm:fsmStatus managed object property"
    ::= { cfprMgmtIfFsmEntry 7 }

cfprMgmtIfFsmProgress OBJECT-TYPE
    SYNTAX       Gauge32
    MAX-ACCESS   read-only
    STATUS       current
    DESCRIPTION
        "Cisco Firepower mgmt:IfFsm:progress managed object property"
    ::= { cfprMgmtIfFsmEntry 8 }

cfprMgmtIfFsmRmtErrCode OBJECT-TYPE
    SYNTAX       Gauge32
    MAX-ACCESS   read-only
    STATUS       current
    DESCRIPTION
        "Cisco Firepower mgmt:IfFsm:rmtErrCode managed object property"
    ::= { cfprMgmtIfFsmEntry 9 }

cfprMgmtIfFsmRmtErrDescr OBJECT-TYPE
    SYNTAX       SnmpAdminString
    MAX-ACCESS   read-only
    STATUS       current
    DESCRIPTION
        "Cisco Firepower mgmt:IfFsm:rmtErrDescr managed object property"
    ::= { cfprMgmtIfFsmEntry 10 }

cfprMgmtIfFsmRmtRslt OBJECT-TYPE
    SYNTAX       CfprConditionRemoteInvRslt
    MAX-ACCESS   read-only
    STATUS       current
    DESCRIPTION
        "Cisco Firepower mgmt:IfFsm:rmtRslt managed object property"
    ::= { cfprMgmtIfFsmEntry 11 }

cfprMgmtIfFsmStageTable OBJECT-TYPE
    SYNTAX           SEQUENCE OF CfprMgmtIfFsmStageEntry
    MAX-ACCESS       not-accessible
    STATUS           current
    DESCRIPTION
        "Cisco Firepower mgmt:IfFsmStage managed object table"
    ::= { cfprMgmtObjects 33 }

cfprMgmtIfFsmStageEntry OBJECT-TYPE
    SYNTAX           CfprMgmtIfFsmStageEntry
    MAX-ACCESS       not-accessible
    STATUS           current
    DESCRIPTION
        "Entry for the cfprMgmtIfFsmStageTable table."
    INDEX { cfprMgmtIfFsmStageInstanceId }
    ::= { cfprMgmtIfFsmStageTable 1 }

CfprMgmtIfFsmStageEntry ::= SEQUENCE {
    cfprMgmtIfFsmStageInstanceId                                     CfprManagedObjectId,
    cfprMgmtIfFsmStageDn                                             CfprManagedObjectDn,
    cfprMgmtIfFsmStageRn                                             SnmpAdminString,
    cfprMgmtIfFsmStageDescrData                                      SnmpAdminString,
    cfprMgmtIfFsmStageLastUpdateTime                                 DateAndTime,
    cfprMgmtIfFsmStageName                                           CfprMgmtIfFsmStageName,
    cfprMgmtIfFsmStageOrder                                          Gauge32,
    cfprMgmtIfFsmStageRetry                                          Gauge32,
    cfprMgmtIfFsmStageStageStatus                                    CfprFsmFsmStageStatus
}

cfprMgmtIfFsmStageInstanceId OBJECT-TYPE
    SYNTAX       CfprManagedObjectId
    MAX-ACCESS   not-accessible
    STATUS       current
    DESCRIPTION
        "Instance identifier of the managed object."
    ::= { cfprMgmtIfFsmStageEntry 1 }

cfprMgmtIfFsmStageDn OBJECT-TYPE
    SYNTAX       CfprManagedObjectDn
    MAX-ACCESS   read-only
    STATUS       current
    DESCRIPTION
        "Cisco Firepower mgmt:IfFsmStage:dn managed object property"
    ::= { cfprMgmtIfFsmStageEntry 2 }

cfprMgmtIfFsmStageRn OBJECT-TYPE
    SYNTAX       SnmpAdminString
    MAX-ACCESS   read-only
    STATUS       current
    DESCRIPTION
        "Cisco Firepower mgmt:IfFsmStage:rn managed object property"
    ::= { cfprMgmtIfFsmStageEntry 3 }

cfprMgmtIfFsmStageDescrData OBJECT-TYPE
    SYNTAX       SnmpAdminString
    MAX-ACCESS   read-only
    STATUS       current
    DESCRIPTION
        "Cisco Firepower mgmt:IfFsmStage:descr managed object property"
    ::= { cfprMgmtIfFsmStageEntry 4 }

cfprMgmtIfFsmStageLastUpdateTime OBJECT-TYPE
    SYNTAX       DateAndTime
    MAX-ACCESS   read-only
    STATUS       current
    DESCRIPTION
        "Cisco Firepower mgmt:IfFsmStage:lastUpdateTime
        managed object property"
    ::= { cfprMgmtIfFsmStageEntry 5 }

cfprMgmtIfFsmStageName OBJECT-TYPE
    SYNTAX       CfprMgmtIfFsmStageName
    MAX-ACCESS   read-only
    STATUS       current
    DESCRIPTION
        "Cisco Firepower mgmt:IfFsmStage:name managed object property"
    ::= { cfprMgmtIfFsmStageEntry 6 }

cfprMgmtIfFsmStageOrder OBJECT-TYPE
    SYNTAX       Gauge32
    MAX-ACCESS   read-only
    STATUS       current
    DESCRIPTION
        "Cisco Firepower mgmt:IfFsmStage:order managed object property"
    ::= { cfprMgmtIfFsmStageEntry 7 }

cfprMgmtIfFsmStageRetry OBJECT-TYPE
    SYNTAX       Gauge32
    MAX-ACCESS   read-only
    STATUS       current
    DESCRIPTION
        "Cisco Firepower mgmt:IfFsmStage:retry managed object property"
    ::= { cfprMgmtIfFsmStageEntry 8 }

cfprMgmtIfFsmStageStageStatus OBJECT-TYPE
    SYNTAX       CfprFsmFsmStageStatus
    MAX-ACCESS   read-only
    STATUS       current
    DESCRIPTION
        "Cisco Firepower mgmt:IfFsmStage:stageStatus managed
        object property"
    ::= { cfprMgmtIfFsmStageEntry 9 }

cfprMgmtIfFsmTaskTable OBJECT-TYPE
    SYNTAX           SEQUENCE OF CfprMgmtIfFsmTaskEntry
    MAX-ACCESS       not-accessible
    STATUS           current
    DESCRIPTION
        "Cisco Firepower mgmt:IfFsmTask managed object table"
    ::= { cfprMgmtObjects 34 }

cfprMgmtIfFsmTaskEntry OBJECT-TYPE
    SYNTAX           CfprMgmtIfFsmTaskEntry
    MAX-ACCESS       not-accessible
    STATUS           current
    DESCRIPTION
        "Entry for the cfprMgmtIfFsmTaskTable table."
    INDEX { cfprMgmtIfFsmTaskInstanceId }
    ::= { cfprMgmtIfFsmTaskTable 1 }

CfprMgmtIfFsmTaskEntry ::= SEQUENCE {
    cfprMgmtIfFsmTaskInstanceId                                      CfprManagedObjectId,
    cfprMgmtIfFsmTaskDn                                              CfprManagedObjectDn,
    cfprMgmtIfFsmTaskRn                                              SnmpAdminString,
    cfprMgmtIfFsmTaskCompletion                                      CfprFsmCompletion,
    cfprMgmtIfFsmTaskFlags                                           CfprFsmFlags,
    cfprMgmtIfFsmTaskItem                                            CfprMgmtIfFsmTaskItem,
    cfprMgmtIfFsmTaskSeqId                                           Gauge32
}

cfprMgmtIfFsmTaskInstanceId OBJECT-TYPE
    SYNTAX       CfprManagedObjectId
    MAX-ACCESS   not-accessible
    STATUS       current
    DESCRIPTION
        "Instance identifier of the managed object."
    ::= { cfprMgmtIfFsmTaskEntry 1 }

cfprMgmtIfFsmTaskDn OBJECT-TYPE
    SYNTAX       CfprManagedObjectDn
    MAX-ACCESS   read-only
    STATUS       current
    DESCRIPTION
        "Cisco Firepower mgmt:IfFsmTask:dn managed object property"
    ::= { cfprMgmtIfFsmTaskEntry 2 }

cfprMgmtIfFsmTaskRn OBJECT-TYPE
    SYNTAX       SnmpAdminString
    MAX-ACCESS   read-only
    STATUS       current
    DESCRIPTION
        "Cisco Firepower mgmt:IfFsmTask:rn managed object property"
    ::= { cfprMgmtIfFsmTaskEntry 3 }

cfprMgmtIfFsmTaskCompletion OBJECT-TYPE
    SYNTAX       CfprFsmCompletion
    MAX-ACCESS   read-only
    STATUS       current
    DESCRIPTION
        "Cisco Firepower mgmt:IfFsmTask:completion managed
        object property"
    ::= { cfprMgmtIfFsmTaskEntry 4 }

cfprMgmtIfFsmTaskFlags OBJECT-TYPE
    SYNTAX       CfprFsmFlags
    MAX-ACCESS   read-only
    STATUS       current
    DESCRIPTION
        "Cisco Firepower mgmt:IfFsmTask:flags managed object property"
    ::= { cfprMgmtIfFsmTaskEntry 5 }

cfprMgmtIfFsmTaskItem OBJECT-TYPE
    SYNTAX       CfprMgmtIfFsmTaskItem
    MAX-ACCESS   read-only
    STATUS       current
    DESCRIPTION
        "Cisco Firepower mgmt:IfFsmTask:item managed object property"
    ::= { cfprMgmtIfFsmTaskEntry 6 }

cfprMgmtIfFsmTaskSeqId OBJECT-TYPE
    SYNTAX       Gauge32
    MAX-ACCESS   read-only
    STATUS       current
    DESCRIPTION
        "Cisco Firepower mgmt:IfFsmTask:seqId managed object property"
    ::= { cfprMgmtIfFsmTaskEntry 7 }

cfprMgmtImportConfigInfoTable OBJECT-TYPE
    SYNTAX           SEQUENCE OF CfprMgmtImportConfigInfoEntry
    MAX-ACCESS       not-accessible
    STATUS           current
    DESCRIPTION
        "Cisco Firepower mgmt:ImportConfigInfo managed object table"
    ::= { cfprMgmtObjects 45 }

cfprMgmtImportConfigInfoEntry OBJECT-TYPE
    SYNTAX           CfprMgmtImportConfigInfoEntry
    MAX-ACCESS       not-accessible
    STATUS           current
    DESCRIPTION
        "Entry for the cfprMgmtImportConfigInfoTable table."
    INDEX { cfprMgmtImportConfigInfoInstanceId }
    ::= { cfprMgmtImportConfigInfoTable 1 }

CfprMgmtImportConfigInfoEntry ::= SEQUENCE {
    cfprMgmtImportConfigInfoInstanceId                               CfprManagedObjectId,
    cfprMgmtImportConfigInfoDn                                       CfprManagedObjectDn,
    cfprMgmtImportConfigInfoRn                                       SnmpAdminString,
    cfprMgmtImportConfigInfoImportDate                               DateAndTime
}

cfprMgmtImportConfigInfoInstanceId OBJECT-TYPE
    SYNTAX       CfprManagedObjectId
    MAX-ACCESS   not-accessible
    STATUS       current
    DESCRIPTION
        "Instance identifier of the managed object."
    ::= { cfprMgmtImportConfigInfoEntry 1 }

cfprMgmtImportConfigInfoDn OBJECT-TYPE
    SYNTAX       CfprManagedObjectDn
    MAX-ACCESS   read-only
    STATUS       current
    DESCRIPTION
        "Cisco Firepower mgmt:ImportConfigInfo:dn managed object property"
    ::= { cfprMgmtImportConfigInfoEntry 2 }

cfprMgmtImportConfigInfoRn OBJECT-TYPE
    SYNTAX       SnmpAdminString
    MAX-ACCESS   read-only
    STATUS       current
    DESCRIPTION
        "Cisco Firepower mgmt:ImportConfigInfo:rn managed object property"
    ::= { cfprMgmtImportConfigInfoEntry 3 }

cfprMgmtImportConfigInfoImportDate OBJECT-TYPE
    SYNTAX       DateAndTime
    MAX-ACCESS   read-only
    STATUS       current
    DESCRIPTION
        "Cisco Firepower mgmt:ImportConfigInfo:importDate
        managed object property"
    ::= { cfprMgmtImportConfigInfoEntry 4 }

cfprMgmtImporterTable OBJECT-TYPE
    SYNTAX           SEQUENCE OF CfprMgmtImporterEntry
    MAX-ACCESS       not-accessible
    STATUS           current
    DESCRIPTION
        "Cisco Firepower mgmt:Importer managed object table"
    ::= { cfprMgmtObjects 35 }

cfprMgmtImporterEntry OBJECT-TYPE
    SYNTAX           CfprMgmtImporterEntry
    MAX-ACCESS       not-accessible
    STATUS           current
    DESCRIPTION
        "Entry for the cfprMgmtImporterTable table."
    INDEX { cfprMgmtImporterInstanceId }
    ::= { cfprMgmtImporterTable 1 }

CfprMgmtImporterEntry ::= SEQUENCE {
    cfprMgmtImporterInstanceId                                       CfprManagedObjectId,
    cfprMgmtImporterDn                                               CfprManagedObjectDn,
    cfprMgmtImporterRn                                               SnmpAdminString,
    cfprMgmtImporterAction                                           CfprMgmtImportAction,
    cfprMgmtImporterAdminState                                       CfprCommClientAdminState,
    cfprMgmtImporterDescr                                            SnmpAdminString,
    cfprMgmtImporterFsmDescr                                         SnmpAdminString,
    cfprMgmtImporterFsmPrev                                          SnmpAdminString,
    cfprMgmtImporterFsmProgr                                         Gauge32,
    cfprMgmtImporterFsmRmtInvErrCode                                 Gauge32,
    cfprMgmtImporterFsmRmtInvErrDescr                                SnmpAdminString,
    cfprMgmtImporterFsmRmtInvRslt                                    CfprConditionRemoteInvRslt,
    cfprMgmtImporterFsmStageDescr                                    SnmpAdminString,
    cfprMgmtImporterFsmStamp                                         DateAndTime,
    cfprMgmtImporterFsmStatus                                        SnmpAdminString,
    cfprMgmtImporterFsmTry                                           Gauge32,
    cfprMgmtImporterHostname                                         SnmpAdminString,
    cfprMgmtImporterIntId                                            SnmpAdminString,
    cfprMgmtImporterName                                             SnmpAdminString,
    cfprMgmtImporterOperStatus                                       CfprMgmtImportStatus,
    cfprMgmtImporterPolicyLevel                                      Gauge32,
    cfprMgmtImporterPolicyOwner                                      CfprPolicyPolicyOwner,
    cfprMgmtImporterPostAction                                       CfprMgmtImporterPostAction,
    cfprMgmtImporterProto                                            CfprMgmtImporterProto,
    cfprMgmtImporterPwd                                              SnmpAdminString,
    cfprMgmtImporterRemoteFile                                       SnmpAdminString,
    cfprMgmtImporterUser                                             SnmpAdminString,
    cfprMgmtImporterApplyingBreakoutCfg                              TruthValue,
    cfprMgmtImporterPort                                             Gauge32,
    cfprMgmtImporterErrMsg                                           SnmpAdminString
}

cfprMgmtImporterInstanceId OBJECT-TYPE
    SYNTAX       CfprManagedObjectId
    MAX-ACCESS   not-accessible
    STATUS       current
    DESCRIPTION
        "Instance identifier of the managed object."
    ::= { cfprMgmtImporterEntry 1 }

cfprMgmtImporterDn OBJECT-TYPE
    SYNTAX       CfprManagedObjectDn
    MAX-ACCESS   read-only
    STATUS       current
    DESCRIPTION
        "Cisco Firepower mgmt:Importer:dn managed object property"
    ::= { cfprMgmtImporterEntry 2 }

cfprMgmtImporterRn OBJECT-TYPE
    SYNTAX       SnmpAdminString
    MAX-ACCESS   read-only
    STATUS       current
    DESCRIPTION
        "Cisco Firepower mgmt:Importer:rn managed object property"
    ::= { cfprMgmtImporterEntry 3 }

cfprMgmtImporterAction OBJECT-TYPE
    SYNTAX       CfprMgmtImportAction
    MAX-ACCESS   read-only
    STATUS       current
    DESCRIPTION
        "Cisco Firepower mgmt:Importer:action managed object property"
    ::= { cfprMgmtImporterEntry 4 }

cfprMgmtImporterAdminState OBJECT-TYPE
    SYNTAX       CfprCommClientAdminState
    MAX-ACCESS   read-only
    STATUS       current
    DESCRIPTION
        "Cisco Firepower mgmt:Importer:adminState managed object property"
    ::= { cfprMgmtImporterEntry 5 }

cfprMgmtImporterDescr OBJECT-TYPE
    SYNTAX       SnmpAdminString
    MAX-ACCESS   read-only
    STATUS       current
    DESCRIPTION
        "Cisco Firepower mgmt:Importer:descr managed object property"
    ::= { cfprMgmtImporterEntry 6 }

cfprMgmtImporterFsmDescr OBJECT-TYPE
    SYNTAX       SnmpAdminString
    MAX-ACCESS   read-only
    STATUS       current
    DESCRIPTION
        "Cisco Firepower mgmt:Importer:fsmDescr managed object property"
    ::= { cfprMgmtImporterEntry 7 }

cfprMgmtImporterFsmPrev OBJECT-TYPE
    SYNTAX       SnmpAdminString
    MAX-ACCESS   read-only
    STATUS       current
    DESCRIPTION
        "Cisco Firepower mgmt:Importer:fsmPrev managed object property"
    ::= { cfprMgmtImporterEntry 8 }

cfprMgmtImporterFsmProgr OBJECT-TYPE
    SYNTAX       Gauge32
    MAX-ACCESS   read-only
    STATUS       current
    DESCRIPTION
        "Cisco Firepower mgmt:Importer:fsmProgr managed object property"
    ::= { cfprMgmtImporterEntry 9 }

cfprMgmtImporterFsmRmtInvErrCode OBJECT-TYPE
    SYNTAX       Gauge32
    MAX-ACCESS   read-only
    STATUS       current
    DESCRIPTION
        "Cisco Firepower mgmt:Importer:fsmRmtInvErrCode
        managed object property"
    ::= { cfprMgmtImporterEntry 10 }

cfprMgmtImporterFsmRmtInvErrDescr OBJECT-TYPE
    SYNTAX       SnmpAdminString
    MAX-ACCESS   read-only
    STATUS       current
    DESCRIPTION
        "Cisco Firepower mgmt:Importer:fsmRmtInvErrDescr
        managed object property"
    ::= { cfprMgmtImporterEntry 11 }

cfprMgmtImporterFsmRmtInvRslt OBJECT-TYPE
    SYNTAX       CfprConditionRemoteInvRslt
    MAX-ACCESS   read-only
    STATUS       current
    DESCRIPTION
        "Cisco Firepower mgmt:Importer:fsmRmtInvRslt managed
        object property"
    ::= { cfprMgmtImporterEntry 12 }

cfprMgmtImporterFsmStageDescr OBJECT-TYPE
    SYNTAX       SnmpAdminString
    MAX-ACCESS   read-only
    STATUS       current
    DESCRIPTION
        "Cisco Firepower mgmt:Importer:fsmStageDescr managed
        object property"
    ::= { cfprMgmtImporterEntry 13 }

cfprMgmtImporterFsmStamp OBJECT-TYPE
    SYNTAX       DateAndTime
    MAX-ACCESS   read-only
    STATUS       current
    DESCRIPTION
        "Cisco Firepower mgmt:Importer:fsmStamp managed object property"
    ::= { cfprMgmtImporterEntry 14 }

cfprMgmtImporterFsmStatus OBJECT-TYPE
    SYNTAX       SnmpAdminString
    MAX-ACCESS   read-only
    STATUS       current
    DESCRIPTION
        "Cisco Firepower mgmt:Importer:fsmStatus managed object property"
    ::= { cfprMgmtImporterEntry 15 }

cfprMgmtImporterFsmTry OBJECT-TYPE
    SYNTAX       Gauge32
    MAX-ACCESS   read-only
    STATUS       current
    DESCRIPTION
        "Cisco Firepower mgmt:Importer:fsmTry managed object property"
    ::= { cfprMgmtImporterEntry 16 }

cfprMgmtImporterHostname OBJECT-TYPE
    SYNTAX       SnmpAdminString
    MAX-ACCESS   read-only
    STATUS       current
    DESCRIPTION
        "Cisco Firepower mgmt:Importer:hostname managed object property"
    ::= { cfprMgmtImporterEntry 17 }

cfprMgmtImporterIntId OBJECT-TYPE
    SYNTAX       SnmpAdminString
    MAX-ACCESS   read-only
    STATUS       current
    DESCRIPTION
        "Cisco Firepower mgmt:Importer:intId managed object property"
    ::= { cfprMgmtImporterEntry 18 }

cfprMgmtImporterName OBJECT-TYPE
    SYNTAX       SnmpAdminString
    MAX-ACCESS   read-only
    STATUS       current
    DESCRIPTION
        "Cisco Firepower mgmt:Importer:name managed object property"
    ::= { cfprMgmtImporterEntry 19 }

cfprMgmtImporterOperStatus OBJECT-TYPE
    SYNTAX       CfprMgmtImportStatus
    MAX-ACCESS   read-only
    STATUS       current
    DESCRIPTION
        "Cisco Firepower mgmt:Importer:operStatus managed object property"
    ::= { cfprMgmtImporterEntry 20 }

cfprMgmtImporterPolicyLevel OBJECT-TYPE
    SYNTAX       Gauge32
    MAX-ACCESS   read-only
    STATUS       current
    DESCRIPTION
        "Cisco Firepower mgmt:Importer:policyLevel managed
        object property"
    ::= { cfprMgmtImporterEntry 21 }

cfprMgmtImporterPolicyOwner OBJECT-TYPE
    SYNTAX       CfprPolicyPolicyOwner
    MAX-ACCESS   read-only
    STATUS       current
    DESCRIPTION
        "Cisco Firepower mgmt:Importer:policyOwner managed
        object property"
    ::= { cfprMgmtImporterEntry 22 }

cfprMgmtImporterPostAction OBJECT-TYPE
    SYNTAX       CfprMgmtImporterPostAction
    MAX-ACCESS   read-only
    STATUS       current
    DESCRIPTION
        "Cisco Firepower mgmt:Importer:postAction managed object property"
    ::= { cfprMgmtImporterEntry 23 }

cfprMgmtImporterProto OBJECT-TYPE
    SYNTAX       CfprMgmtImporterProto
    MAX-ACCESS   read-only
    STATUS       current
    DESCRIPTION
        "Cisco Firepower mgmt:Importer:proto managed object property"
    ::= { cfprMgmtImporterEntry 24 }

cfprMgmtImporterPwd OBJECT-TYPE
    SYNTAX       SnmpAdminString
    MAX-ACCESS   read-only
    STATUS       current
    DESCRIPTION
        "Cisco Firepower mgmt:Importer:pwd managed object property"
    ::= { cfprMgmtImporterEntry 25 }

cfprMgmtImporterRemoteFile OBJECT-TYPE
    SYNTAX       SnmpAdminString
    MAX-ACCESS   read-only
    STATUS       current
    DESCRIPTION
        "Cisco Firepower mgmt:Importer:remoteFile managed object property"
    ::= { cfprMgmtImporterEntry 26 }

cfprMgmtImporterUser OBJECT-TYPE
    SYNTAX       SnmpAdminString
    MAX-ACCESS   read-only
    STATUS       current
    DESCRIPTION
        "Cisco Firepower mgmt:Importer:user managed object property"
    ::= { cfprMgmtImporterEntry 27 }

cfprMgmtImporterApplyingBreakoutCfg OBJECT-TYPE
    SYNTAX       TruthValue
    MAX-ACCESS   read-only
    STATUS       current
    DESCRIPTION
        "Cisco Firepower mgmt:Importer:applyingBreakoutCfg
        managed object property"
    ::= { cfprMgmtImporterEntry 28 }

cfprMgmtImporterPort OBJECT-TYPE
    SYNTAX       Gauge32
    MAX-ACCESS   read-only
    STATUS       current
    DESCRIPTION
        "Cisco Firepower mgmt:Importer:port managed object property"
    ::= { cfprMgmtImporterEntry 29 }

cfprMgmtImporterErrMsg OBJECT-TYPE
    SYNTAX       SnmpAdminString
    MAX-ACCESS   read-only
    STATUS       current
    DESCRIPTION
        "Cisco Firepower mgmt:Importer:errMsg managed object property"
    ::= { cfprMgmtImporterEntry 30 }

cfprMgmtImporterFsmTable OBJECT-TYPE
    SYNTAX           SEQUENCE OF CfprMgmtImporterFsmEntry
    MAX-ACCESS       not-accessible
    STATUS           current
    DESCRIPTION
        "Cisco Firepower mgmt:ImporterFsm managed object table"
    ::= { cfprMgmtObjects 36 }

cfprMgmtImporterFsmEntry OBJECT-TYPE
    SYNTAX           CfprMgmtImporterFsmEntry
    MAX-ACCESS       not-accessible
    STATUS           current
    DESCRIPTION
        "Entry for the cfprMgmtImporterFsmTable table."
    INDEX { cfprMgmtImporterFsmInstanceId }
    ::= { cfprMgmtImporterFsmTable 1 }

CfprMgmtImporterFsmEntry ::= SEQUENCE {
    cfprMgmtImporterFsmInstanceId                                    CfprManagedObjectId,
    cfprMgmtImporterFsmDn                                            CfprManagedObjectDn,
    cfprMgmtImporterFsmRn                                            SnmpAdminString,
    cfprMgmtImporterFsmCompletionTime                                DateAndTime,
    cfprMgmtImporterFsmCurrentFsm                                    CfprMgmtImporterFsmCurrentFsm,
    cfprMgmtImporterFsmDescrData                                     SnmpAdminString,
    cfprMgmtImporterFsmFsmStatus                                     CfprFsmFsmStageStatus,
    cfprMgmtImporterFsmProgress                                      Gauge32,
    cfprMgmtImporterFsmRmtErrCode                                    Gauge32,
    cfprMgmtImporterFsmRmtErrDescr                                   SnmpAdminString,
    cfprMgmtImporterFsmRmtRslt                                       CfprConditionRemoteInvRslt
}

cfprMgmtImporterFsmInstanceId OBJECT-TYPE
    SYNTAX       CfprManagedObjectId
    MAX-ACCESS   not-accessible
    STATUS       current
    DESCRIPTION
        "Instance identifier of the managed object."
    ::= { cfprMgmtImporterFsmEntry 1 }

cfprMgmtImporterFsmDn OBJECT-TYPE
    SYNTAX       CfprManagedObjectDn
    MAX-ACCESS   read-only
    STATUS       current
    DESCRIPTION
        "Cisco Firepower mgmt:ImporterFsm:dn managed object property"
    ::= { cfprMgmtImporterFsmEntry 2 }

cfprMgmtImporterFsmRn OBJECT-TYPE
    SYNTAX       SnmpAdminString
    MAX-ACCESS   read-only
    STATUS       current
    DESCRIPTION
        "Cisco Firepower mgmt:ImporterFsm:rn managed object property"
    ::= { cfprMgmtImporterFsmEntry 3 }

cfprMgmtImporterFsmCompletionTime OBJECT-TYPE
    SYNTAX       DateAndTime
    MAX-ACCESS   read-only
    STATUS       current
    DESCRIPTION
        "Cisco Firepower mgmt:ImporterFsm:completionTime
        managed object property"
    ::= { cfprMgmtImporterFsmEntry 4 }

cfprMgmtImporterFsmCurrentFsm OBJECT-TYPE
    SYNTAX       CfprMgmtImporterFsmCurrentFsm
    MAX-ACCESS   read-only
    STATUS       current
    DESCRIPTION
        "Cisco Firepower mgmt:ImporterFsm:currentFsm managed
        object property"
    ::= { cfprMgmtImporterFsmEntry 5 }

cfprMgmtImporterFsmDescrData OBJECT-TYPE
    SYNTAX       SnmpAdminString
    MAX-ACCESS   read-only
    STATUS       current
    DESCRIPTION
        "Cisco Firepower mgmt:ImporterFsm:descr managed object property"
    ::= { cfprMgmtImporterFsmEntry 6 }

cfprMgmtImporterFsmFsmStatus OBJECT-TYPE
    SYNTAX       CfprFsmFsmStageStatus
    MAX-ACCESS   read-only
    STATUS       current
    DESCRIPTION
        "Cisco Firepower mgmt:ImporterFsm:fsmStatus managed
        object property"
    ::= { cfprMgmtImporterFsmEntry 7 }

cfprMgmtImporterFsmProgress OBJECT-TYPE
    SYNTAX       Gauge32
    MAX-ACCESS   read-only
    STATUS       current
    DESCRIPTION
        "Cisco Firepower mgmt:ImporterFsm:progress managed
        object property"
    ::= { cfprMgmtImporterFsmEntry 8 }

cfprMgmtImporterFsmRmtErrCode OBJECT-TYPE
    SYNTAX       Gauge32
    MAX-ACCESS   read-only
    STATUS       current
    DESCRIPTION
        "Cisco Firepower mgmt:ImporterFsm:rmtErrCode managed
        object property"
    ::= { cfprMgmtImporterFsmEntry 9 }

cfprMgmtImporterFsmRmtErrDescr OBJECT-TYPE
    SYNTAX       SnmpAdminString
    MAX-ACCESS   read-only
    STATUS       current
    DESCRIPTION
        "Cisco Firepower mgmt:ImporterFsm:rmtErrDescr managed
        object property"
    ::= { cfprMgmtImporterFsmEntry 10 }

cfprMgmtImporterFsmRmtRslt OBJECT-TYPE
    SYNTAX       CfprConditionRemoteInvRslt
    MAX-ACCESS   read-only
    STATUS       current
    DESCRIPTION
        "Cisco Firepower mgmt:ImporterFsm:rmtRslt managed object property"
    ::= { cfprMgmtImporterFsmEntry 11 }

cfprMgmtImporterFsmStageTable OBJECT-TYPE
    SYNTAX           SEQUENCE OF CfprMgmtImporterFsmStageEntry
    MAX-ACCESS       not-accessible
    STATUS           current
    DESCRIPTION
        "Cisco Firepower mgmt:ImporterFsmStage managed object table"
    ::= { cfprMgmtObjects 37 }

cfprMgmtImporterFsmStageEntry OBJECT-TYPE
    SYNTAX           CfprMgmtImporterFsmStageEntry
    MAX-ACCESS       not-accessible
    STATUS           current
    DESCRIPTION
        "Entry for the cfprMgmtImporterFsmStageTable table."
    INDEX { cfprMgmtImporterFsmStageInstanceId }
    ::= { cfprMgmtImporterFsmStageTable 1 }

CfprMgmtImporterFsmStageEntry ::= SEQUENCE {
    cfprMgmtImporterFsmStageInstanceId                               CfprManagedObjectId,
    cfprMgmtImporterFsmStageDn                                       CfprManagedObjectDn,
    cfprMgmtImporterFsmStageRn                                       SnmpAdminString,
    cfprMgmtImporterFsmStageDescrData                                SnmpAdminString,
    cfprMgmtImporterFsmStageLastUpdateTime                           DateAndTime,
    cfprMgmtImporterFsmStageName                                     CfprMgmtImporterFsmStageName,
    cfprMgmtImporterFsmStageOrder                                    Gauge32,
    cfprMgmtImporterFsmStageRetry                                    Gauge32,
    cfprMgmtImporterFsmStageStageStatus                              CfprFsmFsmStageStatus
}

cfprMgmtImporterFsmStageInstanceId OBJECT-TYPE
    SYNTAX       CfprManagedObjectId
    MAX-ACCESS   not-accessible
    STATUS       current
    DESCRIPTION
        "Instance identifier of the managed object."
    ::= { cfprMgmtImporterFsmStageEntry 1 }

cfprMgmtImporterFsmStageDn OBJECT-TYPE
    SYNTAX       CfprManagedObjectDn
    MAX-ACCESS   read-only
    STATUS       current
    DESCRIPTION
        "Cisco Firepower mgmt:ImporterFsmStage:dn managed object property"
    ::= { cfprMgmtImporterFsmStageEntry 2 }

cfprMgmtImporterFsmStageRn OBJECT-TYPE
    SYNTAX       SnmpAdminString
    MAX-ACCESS   read-only
    STATUS       current
    DESCRIPTION
        "Cisco Firepower mgmt:ImporterFsmStage:rn managed object property"
    ::= { cfprMgmtImporterFsmStageEntry 3 }

cfprMgmtImporterFsmStageDescrData OBJECT-TYPE
    SYNTAX       SnmpAdminString
    MAX-ACCESS   read-only
    STATUS       current
    DESCRIPTION
        "Cisco Firepower mgmt:ImporterFsmStage:descr managed
        object property"
    ::= { cfprMgmtImporterFsmStageEntry 4 }

cfprMgmtImporterFsmStageLastUpdateTime OBJECT-TYPE
    SYNTAX       DateAndTime
    MAX-ACCESS   read-only
    STATUS       current
    DESCRIPTION
        "Cisco Firepower mgmt:ImporterFsmStage:lastUpdateTime
        managed object property"
    ::= { cfprMgmtImporterFsmStageEntry 5 }

cfprMgmtImporterFsmStageName OBJECT-TYPE
    SYNTAX       CfprMgmtImporterFsmStageName
    MAX-ACCESS   read-only
    STATUS       current
    DESCRIPTION
        "Cisco Firepower mgmt:ImporterFsmStage:name managed
        object property"
    ::= { cfprMgmtImporterFsmStageEntry 6 }

cfprMgmtImporterFsmStageOrder OBJECT-TYPE
    SYNTAX       Gauge32
    MAX-ACCESS   read-only
    STATUS       current
    DESCRIPTION
        "Cisco Firepower mgmt:ImporterFsmStage:order managed
        object property"
    ::= { cfprMgmtImporterFsmStageEntry 7 }

cfprMgmtImporterFsmStageRetry OBJECT-TYPE
    SYNTAX       Gauge32
    MAX-ACCESS   read-only
    STATUS       current
    DESCRIPTION
        "Cisco Firepower mgmt:ImporterFsmStage:retry managed
        object property"
    ::= { cfprMgmtImporterFsmStageEntry 8 }

cfprMgmtImporterFsmStageStageStatus OBJECT-TYPE
    SYNTAX       CfprFsmFsmStageStatus
    MAX-ACCESS   read-only
    STATUS       current
    DESCRIPTION
        "Cisco Firepower mgmt:ImporterFsmStage:stageStatus
        managed object property"
    ::= { cfprMgmtImporterFsmStageEntry 9 }

cfprMgmtImporterFsmTaskTable OBJECT-TYPE
    SYNTAX           SEQUENCE OF CfprMgmtImporterFsmTaskEntry
    MAX-ACCESS       not-accessible
    STATUS           current
    DESCRIPTION
        "Cisco Firepower mgmt:ImporterFsmTask managed object table"
    ::= { cfprMgmtObjects 38 }

cfprMgmtImporterFsmTaskEntry OBJECT-TYPE
    SYNTAX           CfprMgmtImporterFsmTaskEntry
    MAX-ACCESS       not-accessible
    STATUS           current
    DESCRIPTION
        "Entry for the cfprMgmtImporterFsmTaskTable table."
    INDEX { cfprMgmtImporterFsmTaskInstanceId }
    ::= { cfprMgmtImporterFsmTaskTable 1 }

CfprMgmtImporterFsmTaskEntry ::= SEQUENCE {
    cfprMgmtImporterFsmTaskInstanceId                                CfprManagedObjectId,
    cfprMgmtImporterFsmTaskDn                                        CfprManagedObjectDn,
    cfprMgmtImporterFsmTaskRn                                        SnmpAdminString,
    cfprMgmtImporterFsmTaskCompletion                                CfprFsmCompletion,
    cfprMgmtImporterFsmTaskFlags                                     CfprFsmFlags,
    cfprMgmtImporterFsmTaskItem                                      CfprMgmtImporterFsmTaskItem,
    cfprMgmtImporterFsmTaskSeqId                                     Gauge32
}

cfprMgmtImporterFsmTaskInstanceId OBJECT-TYPE
    SYNTAX       CfprManagedObjectId
    MAX-ACCESS   not-accessible
    STATUS       current
    DESCRIPTION
        "Instance identifier of the managed object."
    ::= { cfprMgmtImporterFsmTaskEntry 1 }

cfprMgmtImporterFsmTaskDn OBJECT-TYPE
    SYNTAX       CfprManagedObjectDn
    MAX-ACCESS   read-only
    STATUS       current
    DESCRIPTION
        "Cisco Firepower mgmt:ImporterFsmTask:dn managed object property"
    ::= { cfprMgmtImporterFsmTaskEntry 2 }

cfprMgmtImporterFsmTaskRn OBJECT-TYPE
    SYNTAX       SnmpAdminString
    MAX-ACCESS   read-only
    STATUS       current
    DESCRIPTION
        "Cisco Firepower mgmt:ImporterFsmTask:rn managed object property"
    ::= { cfprMgmtImporterFsmTaskEntry 3 }

cfprMgmtImporterFsmTaskCompletion OBJECT-TYPE
    SYNTAX       CfprFsmCompletion
    MAX-ACCESS   read-only
    STATUS       current
    DESCRIPTION
        "Cisco Firepower mgmt:ImporterFsmTask:completion
        managed object property"
    ::= { cfprMgmtImporterFsmTaskEntry 4 }

cfprMgmtImporterFsmTaskFlags OBJECT-TYPE
    SYNTAX       CfprFsmFlags
    MAX-ACCESS   read-only
    STATUS       current
    DESCRIPTION
        "Cisco Firepower mgmt:ImporterFsmTask:flags managed
        object property"
    ::= { cfprMgmtImporterFsmTaskEntry 5 }

cfprMgmtImporterFsmTaskItem OBJECT-TYPE
    SYNTAX       CfprMgmtImporterFsmTaskItem
    MAX-ACCESS   read-only
    STATUS       current
    DESCRIPTION
        "Cisco Firepower mgmt:ImporterFsmTask:item managed
        object property"
    ::= { cfprMgmtImporterFsmTaskEntry 6 }

cfprMgmtImporterFsmTaskSeqId OBJECT-TYPE
    SYNTAX       Gauge32
    MAX-ACCESS   read-only
    STATUS       current
    DESCRIPTION
        "Cisco Firepower mgmt:ImporterFsmTask:seqId managed
        object property"
    ::= { cfprMgmtImporterFsmTaskEntry 7 }

cfprMgmtInbandProfileTable OBJECT-TYPE
    SYNTAX           SEQUENCE OF CfprMgmtInbandProfileEntry
    MAX-ACCESS       not-accessible
    STATUS           current
    DESCRIPTION
        "Cisco Firepower mgmt:InbandProfile managed object table"
    ::= { cfprMgmtObjects 39 }

cfprMgmtInbandProfileEntry OBJECT-TYPE
    SYNTAX           CfprMgmtInbandProfileEntry
    MAX-ACCESS       not-accessible
    STATUS           current
    DESCRIPTION
        "Entry for the cfprMgmtInbandProfileTable table."
    INDEX { cfprMgmtInbandProfileInstanceId }
    ::= { cfprMgmtInbandProfileTable 1 }

CfprMgmtInbandProfileEntry ::= SEQUENCE {
    cfprMgmtInbandProfileInstanceId                                  CfprManagedObjectId,
    cfprMgmtInbandProfileDn                                          CfprManagedObjectDn,
    cfprMgmtInbandProfileRn                                          SnmpAdminString,
    cfprMgmtInbandProfileDefaultVlanName                             SnmpAdminString,
    cfprMgmtInbandProfileName                                        SnmpAdminString,
    cfprMgmtInbandProfilePoolName                                    SnmpAdminString
}

cfprMgmtInbandProfileInstanceId OBJECT-TYPE
    SYNTAX       CfprManagedObjectId
    MAX-ACCESS   not-accessible
    STATUS       current
    DESCRIPTION
        "Instance identifier of the managed object."
    ::= { cfprMgmtInbandProfileEntry 1 }

cfprMgmtInbandProfileDn OBJECT-TYPE
    SYNTAX       CfprManagedObjectDn
    MAX-ACCESS   read-only
    STATUS       current
    DESCRIPTION
        "Cisco Firepower mgmt:InbandProfile:dn managed object property"
    ::= { cfprMgmtInbandProfileEntry 2 }

cfprMgmtInbandProfileRn OBJECT-TYPE
    SYNTAX       SnmpAdminString
    MAX-ACCESS   read-only
    STATUS       current
    DESCRIPTION
        "Cisco Firepower mgmt:InbandProfile:rn managed object property"
    ::= { cfprMgmtInbandProfileEntry 3 }

cfprMgmtInbandProfileDefaultVlanName OBJECT-TYPE
    SYNTAX       SnmpAdminString
    MAX-ACCESS   read-only
    STATUS       current
    DESCRIPTION
        "Cisco Firepower mgmt:InbandProfile:defaultVlanName
        managed object property"
    ::= { cfprMgmtInbandProfileEntry 4 }

cfprMgmtInbandProfileName OBJECT-TYPE
    SYNTAX       SnmpAdminString
    MAX-ACCESS   read-only
    STATUS       current
    DESCRIPTION
        "Cisco Firepower mgmt:InbandProfile:name managed object property"
    ::= { cfprMgmtInbandProfileEntry 5 }

cfprMgmtInbandProfilePoolName OBJECT-TYPE
    SYNTAX       SnmpAdminString
    MAX-ACCESS   read-only
    STATUS       current
    DESCRIPTION
        "Cisco Firepower mgmt:InbandProfile:poolName managed
        object property"
    ::= { cfprMgmtInbandProfileEntry 6 }

cfprMgmtIntAuthPolicyTable OBJECT-TYPE
    SYNTAX           SEQUENCE OF CfprMgmtIntAuthPolicyEntry
    MAX-ACCESS       not-accessible
    STATUS           current
    DESCRIPTION
        "Cisco Firepower mgmt:IntAuthPolicy managed object table"
    ::= { cfprMgmtObjects 40 }

cfprMgmtIntAuthPolicyEntry OBJECT-TYPE
    SYNTAX           CfprMgmtIntAuthPolicyEntry
    MAX-ACCESS       not-accessible
    STATUS           current
    DESCRIPTION
        "Entry for the cfprMgmtIntAuthPolicyTable table."
    INDEX { cfprMgmtIntAuthPolicyInstanceId }
    ::= { cfprMgmtIntAuthPolicyTable 1 }

CfprMgmtIntAuthPolicyEntry ::= SEQUENCE {
    cfprMgmtIntAuthPolicyInstanceId                                  CfprManagedObjectId,
    cfprMgmtIntAuthPolicyDn                                          CfprManagedObjectDn,
    cfprMgmtIntAuthPolicyRn                                          SnmpAdminString,
    cfprMgmtIntAuthPolicyMethod                                      CfprMgmtIntAuthPolicyMethod,
    cfprMgmtIntAuthPolicyName                                        SnmpAdminString,
    cfprMgmtIntAuthPolicyPwd                                         SnmpAdminString
}

cfprMgmtIntAuthPolicyInstanceId OBJECT-TYPE
    SYNTAX       CfprManagedObjectId
    MAX-ACCESS   not-accessible
    STATUS       current
    DESCRIPTION
        "Instance identifier of the managed object."
    ::= { cfprMgmtIntAuthPolicyEntry 1 }

cfprMgmtIntAuthPolicyDn OBJECT-TYPE
    SYNTAX       CfprManagedObjectDn
    MAX-ACCESS   read-only
    STATUS       current
    DESCRIPTION
        "Cisco Firepower mgmt:IntAuthPolicy:dn managed object property"
    ::= { cfprMgmtIntAuthPolicyEntry 2 }

cfprMgmtIntAuthPolicyRn OBJECT-TYPE
    SYNTAX       SnmpAdminString
    MAX-ACCESS   read-only
    STATUS       current
    DESCRIPTION
        "Cisco Firepower mgmt:IntAuthPolicy:rn managed object property"
    ::= { cfprMgmtIntAuthPolicyEntry 3 }

cfprMgmtIntAuthPolicyMethod OBJECT-TYPE
    SYNTAX       CfprMgmtIntAuthPolicyMethod
    MAX-ACCESS   read-only
    STATUS       current
    DESCRIPTION
        "Cisco Firepower mgmt:IntAuthPolicy:method managed
        object property"
    ::= { cfprMgmtIntAuthPolicyEntry 4 }

cfprMgmtIntAuthPolicyName OBJECT-TYPE
    SYNTAX       SnmpAdminString
    MAX-ACCESS   read-only
    STATUS       current
    DESCRIPTION
        "Cisco Firepower mgmt:IntAuthPolicy:name managed object property"
    ::= { cfprMgmtIntAuthPolicyEntry 5 }

cfprMgmtIntAuthPolicyPwd OBJECT-TYPE
    SYNTAX       SnmpAdminString
    MAX-ACCESS   read-only
    STATUS       current
    DESCRIPTION
        "Cisco Firepower mgmt:IntAuthPolicy:pwd managed object property"
    ::= { cfprMgmtIntAuthPolicyEntry 6 }

cfprMgmtInterfaceTable OBJECT-TYPE
    SYNTAX           SEQUENCE OF CfprMgmtInterfaceEntry
    MAX-ACCESS       not-accessible
    STATUS           current
    DESCRIPTION
        "Cisco Firepower mgmt:Interface managed object table"
    ::= { cfprMgmtObjects 41 }

cfprMgmtInterfaceEntry OBJECT-TYPE
    SYNTAX           CfprMgmtInterfaceEntry
    MAX-ACCESS       not-accessible
    STATUS           current
    DESCRIPTION
        "Entry for the cfprMgmtInterfaceTable table."
    INDEX { cfprMgmtInterfaceInstanceId }
    ::= { cfprMgmtInterfaceTable 1 }

CfprMgmtInterfaceEntry ::= SEQUENCE {
    cfprMgmtInterfaceInstanceId                                      CfprManagedObjectId,
    cfprMgmtInterfaceDn                                              CfprManagedObjectDn,
    cfprMgmtInterfaceRn                                              SnmpAdminString,
    cfprMgmtInterfaceConfigMessage                                   SnmpAdminString,
    cfprMgmtInterfaceConfigState                                     CfprMgmtConfigState,
    cfprMgmtInterfaceIpV4State                                       CfprVnicExternalMgmtIPMode,
    cfprMgmtInterfaceIpV6State                                       CfprVnicExternalMgmtIPMode,
    cfprMgmtInterfaceIsDefaultDerived                                TruthValue,
    cfprMgmtInterfaceMode                                            CfprMgmtMode,
    cfprMgmtInterfaceOperState                                       CfprMgmtOperState
}

cfprMgmtInterfaceInstanceId OBJECT-TYPE
    SYNTAX       CfprManagedObjectId
    MAX-ACCESS   not-accessible
    STATUS       current
    DESCRIPTION
        "Instance identifier of the managed object."
    ::= { cfprMgmtInterfaceEntry 1 }

cfprMgmtInterfaceDn OBJECT-TYPE
    SYNTAX       CfprManagedObjectDn
    MAX-ACCESS   read-only
    STATUS       current
    DESCRIPTION
        "Cisco Firepower mgmt:Interface:dn managed object property"
    ::= { cfprMgmtInterfaceEntry 2 }

cfprMgmtInterfaceRn OBJECT-TYPE
    SYNTAX       SnmpAdminString
    MAX-ACCESS   read-only
    STATUS       current
    DESCRIPTION
        "Cisco Firepower mgmt:Interface:rn managed object property"
    ::= { cfprMgmtInterfaceEntry 3 }

cfprMgmtInterfaceConfigMessage OBJECT-TYPE
    SYNTAX       SnmpAdminString
    MAX-ACCESS   read-only
    STATUS       current
    DESCRIPTION
        "Cisco Firepower mgmt:Interface:configMessage managed
        object property"
    ::= { cfprMgmtInterfaceEntry 4 }

cfprMgmtInterfaceConfigState OBJECT-TYPE
    SYNTAX       CfprMgmtConfigState
    MAX-ACCESS   read-only
    STATUS       current
    DESCRIPTION
        "Cisco Firepower mgmt:Interface:configState managed
        object property"
    ::= { cfprMgmtInterfaceEntry 5 }

cfprMgmtInterfaceIpV4State OBJECT-TYPE
    SYNTAX       CfprVnicExternalMgmtIPMode
    MAX-ACCESS   read-only
    STATUS       current
    DESCRIPTION
        "Cisco Firepower mgmt:Interface:ipV4State managed object property"
    ::= { cfprMgmtInterfaceEntry 6 }

cfprMgmtInterfaceIpV6State OBJECT-TYPE
    SYNTAX       CfprVnicExternalMgmtIPMode
    MAX-ACCESS   read-only
    STATUS       current
    DESCRIPTION
        "Cisco Firepower mgmt:Interface:ipV6State managed object property"
    ::= { cfprMgmtInterfaceEntry 7 }

cfprMgmtInterfaceIsDefaultDerived OBJECT-TYPE
    SYNTAX       TruthValue
    MAX-ACCESS   read-only
    STATUS       current
    DESCRIPTION
        "Cisco Firepower mgmt:Interface:isDefaultDerived
        managed object property"
    ::= { cfprMgmtInterfaceEntry 8 }

cfprMgmtInterfaceMode OBJECT-TYPE
    SYNTAX       CfprMgmtMode
    MAX-ACCESS   read-only
    STATUS       current
    DESCRIPTION
        "Cisco Firepower mgmt:Interface:mode managed object property"
    ::= { cfprMgmtInterfaceEntry 9 }

cfprMgmtInterfaceOperState OBJECT-TYPE
    SYNTAX       CfprMgmtOperState
    MAX-ACCESS   read-only
    STATUS       current
    DESCRIPTION
        "Cisco Firepower mgmt:Interface:operState managed object property"
    ::= { cfprMgmtInterfaceEntry 10 }

cfprMgmtPmonEntryTable OBJECT-TYPE
    SYNTAX           SEQUENCE OF CfprMgmtPmonEntryEntry
    MAX-ACCESS       not-accessible
    STATUS           current
    DESCRIPTION
        "Cisco Firepower mgmt:PmonEntry managed object table"
    ::= { cfprMgmtObjects 42 }

cfprMgmtPmonEntryEntry OBJECT-TYPE
    SYNTAX           CfprMgmtPmonEntryEntry
    MAX-ACCESS       not-accessible
    STATUS           current
    DESCRIPTION
        "Entry for the cfprMgmtPmonEntryTable table."
    INDEX { cfprMgmtPmonEntryInstanceId }
    ::= { cfprMgmtPmonEntryTable 1 }

CfprMgmtPmonEntryEntry ::= SEQUENCE {
    cfprMgmtPmonEntryInstanceId                                      CfprManagedObjectId,
    cfprMgmtPmonEntryDn                                              CfprManagedObjectDn,
    cfprMgmtPmonEntryRn                                              SnmpAdminString,
    cfprMgmtPmonEntryExitSignal                                      Gauge32,
    cfprMgmtPmonEntryFullPathname                                    SnmpAdminString,
    cfprMgmtPmonEntryHeapSize                                        Unsigned64,
    cfprMgmtPmonEntryHeapSize16Gb                                    Unsigned64,
    cfprMgmtPmonEntryLastExitCode                                    Gauge32,
    cfprMgmtPmonEntryMaxRetries                                      Gauge32,
    cfprMgmtPmonEntryName                                            SnmpAdminString,
    cfprMgmtPmonEntryRetries                                         Gauge32,
    cfprMgmtPmonEntrySpuriousRetries                                 Gauge32,
    cfprMgmtPmonEntryState                                           CfprMgmtPmonEntryState,
    cfprMgmtPmonEntrySwitchId                                        CfprNetworkSwitchId,
    cfprMgmtPmonEntryWorkingDirectory                                SnmpAdminString
}

cfprMgmtPmonEntryInstanceId OBJECT-TYPE
    SYNTAX       CfprManagedObjectId
    MAX-ACCESS   not-accessible
    STATUS       current
    DESCRIPTION
        "Instance identifier of the managed object."
    ::= { cfprMgmtPmonEntryEntry 1 }

cfprMgmtPmonEntryDn OBJECT-TYPE
    SYNTAX       CfprManagedObjectDn
    MAX-ACCESS   read-only
    STATUS       current
    DESCRIPTION
        "Cisco Firepower mgmt:PmonEntry:dn managed object property"
    ::= { cfprMgmtPmonEntryEntry 2 }

cfprMgmtPmonEntryRn OBJECT-TYPE
    SYNTAX       SnmpAdminString
    MAX-ACCESS   read-only
    STATUS       current
    DESCRIPTION
        "Cisco Firepower mgmt:PmonEntry:rn managed object property"
    ::= { cfprMgmtPmonEntryEntry 3 }

cfprMgmtPmonEntryExitSignal OBJECT-TYPE
    SYNTAX       Gauge32
    MAX-ACCESS   read-only
    STATUS       current
    DESCRIPTION
        "Cisco Firepower mgmt:PmonEntry:exitSignal managed
        object property"
    ::= { cfprMgmtPmonEntryEntry 4 }

cfprMgmtPmonEntryFullPathname OBJECT-TYPE
    SYNTAX       SnmpAdminString
    MAX-ACCESS   read-only
    STATUS       current
    DESCRIPTION
        "Cisco Firepower mgmt:PmonEntry:fullPathname managed
        object property"
    ::= { cfprMgmtPmonEntryEntry 5 }

cfprMgmtPmonEntryHeapSize OBJECT-TYPE
    SYNTAX       Unsigned64
    MAX-ACCESS   read-only
    STATUS       current
    DESCRIPTION
        "Cisco Firepower mgmt:PmonEntry:heapSize managed object property"
    ::= { cfprMgmtPmonEntryEntry 6 }

cfprMgmtPmonEntryHeapSize16Gb OBJECT-TYPE
    SYNTAX       Unsigned64
    MAX-ACCESS   read-only
    STATUS       current
    DESCRIPTION
        "Cisco Firepower mgmt:PmonEntry:heapSize16Gb managed
        object property"
    ::= { cfprMgmtPmonEntryEntry 7 }

cfprMgmtPmonEntryLastExitCode OBJECT-TYPE
    SYNTAX       Gauge32
    MAX-ACCESS   read-only
    STATUS       current
    DESCRIPTION
        "Cisco Firepower mgmt:PmonEntry:lastExitCode managed
        object property"
    ::= { cfprMgmtPmonEntryEntry 8 }

cfprMgmtPmonEntryMaxRetries OBJECT-TYPE
    SYNTAX       Gauge32
    MAX-ACCESS   read-only
    STATUS       current
    DESCRIPTION
        "Cisco Firepower mgmt:PmonEntry:maxRetries managed
        object property"
    ::= { cfprMgmtPmonEntryEntry 9 }

cfprMgmtPmonEntryName OBJECT-TYPE
    SYNTAX       SnmpAdminString
    MAX-ACCESS   read-only
    STATUS       current
    DESCRIPTION
        "Cisco Firepower mgmt:PmonEntry:name managed object property"
    ::= { cfprMgmtPmonEntryEntry 10 }

cfprMgmtPmonEntryRetries OBJECT-TYPE
    SYNTAX       Gauge32
    MAX-ACCESS   read-only
    STATUS       current
    DESCRIPTION
        "Cisco Firepower mgmt:PmonEntry:retries managed object property"
    ::= { cfprMgmtPmonEntryEntry 11 }

cfprMgmtPmonEntrySpuriousRetries OBJECT-TYPE
    SYNTAX       Gauge32
    MAX-ACCESS   read-only
    STATUS       current
    DESCRIPTION
        "Cisco Firepower mgmt:PmonEntry:spuriousRetries
        managed object property"
    ::= { cfprMgmtPmonEntryEntry 12 }

cfprMgmtPmonEntryState OBJECT-TYPE
    SYNTAX       CfprMgmtPmonEntryState
    MAX-ACCESS   read-only
    STATUS       current
    DESCRIPTION
        "Cisco Firepower mgmt:PmonEntry:state managed object property"
    ::= { cfprMgmtPmonEntryEntry 13 }

cfprMgmtPmonEntrySwitchId OBJECT-TYPE
    SYNTAX       CfprNetworkSwitchId
    MAX-ACCESS   read-only
    STATUS       current
    DESCRIPTION
        "Cisco Firepower mgmt:PmonEntry:switchId managed object property"
    ::= { cfprMgmtPmonEntryEntry 14 }

cfprMgmtPmonEntryWorkingDirectory OBJECT-TYPE
    SYNTAX       SnmpAdminString
    MAX-ACCESS   read-only
    STATUS       current
    DESCRIPTION
        "Cisco Firepower mgmt:PmonEntry:workingDirectory
        managed object property"
    ::= { cfprMgmtPmonEntryEntry 15 }

cfprMgmtProfDerivedInterfaceTable OBJECT-TYPE
    SYNTAX           SEQUENCE OF CfprMgmtProfDerivedInterfaceEntry
    MAX-ACCESS       not-accessible
    STATUS           current
    DESCRIPTION
        "Cisco Firepower mgmt:ProfDerivedInterface managed object table"
    ::= { cfprMgmtObjects 43 }

cfprMgmtProfDerivedInterfaceEntry OBJECT-TYPE
    SYNTAX           CfprMgmtProfDerivedInterfaceEntry
    MAX-ACCESS       not-accessible
    STATUS           current
    DESCRIPTION
        "Entry for the cfprMgmtProfDerivedInterfaceTable table."
    INDEX { cfprMgmtProfDerivedInterfaceInstanceId }
    ::= { cfprMgmtProfDerivedInterfaceTable 1 }

CfprMgmtProfDerivedInterfaceEntry ::= SEQUENCE {
    cfprMgmtProfDerivedInterfaceInstanceId                           CfprManagedObjectId,
    cfprMgmtProfDerivedInterfaceDn                                   CfprManagedObjectDn,
    cfprMgmtProfDerivedInterfaceRn                                   SnmpAdminString,
    cfprMgmtProfDerivedInterfaceConfigMessage                        SnmpAdminString,
    cfprMgmtProfDerivedInterfaceConfigState                          CfprMgmtConfigState,
    cfprMgmtProfDerivedInterfaceIpV4State                            CfprVnicExternalMgmtIPMode,
    cfprMgmtProfDerivedInterfaceIpV6State                            CfprVnicExternalMgmtIPMode,
    cfprMgmtProfDerivedInterfaceMode                                 CfprMgmtMode,
    cfprMgmtProfDerivedInterfaceOperState                            CfprMgmtOperState
}

cfprMgmtProfDerivedInterfaceInstanceId OBJECT-TYPE
    SYNTAX       CfprManagedObjectId
    MAX-ACCESS   not-accessible
    STATUS       current
    DESCRIPTION
        "Instance identifier of the managed object."
    ::= { cfprMgmtProfDerivedInterfaceEntry 1 }

cfprMgmtProfDerivedInterfaceDn OBJECT-TYPE
    SYNTAX       CfprManagedObjectDn
    MAX-ACCESS   read-only
    STATUS       current
    DESCRIPTION
        "Cisco Firepower mgmt:ProfDerivedInterface:dn managed
        object property"
    ::= { cfprMgmtProfDerivedInterfaceEntry 2 }

cfprMgmtProfDerivedInterfaceRn OBJECT-TYPE
    SYNTAX       SnmpAdminString
    MAX-ACCESS   read-only
    STATUS       current
    DESCRIPTION
        "Cisco Firepower mgmt:ProfDerivedInterface:rn managed
        object property"
    ::= { cfprMgmtProfDerivedInterfaceEntry 3 }

cfprMgmtProfDerivedInterfaceConfigMessage OBJECT-TYPE
    SYNTAX       SnmpAdminString
    MAX-ACCESS   read-only
    STATUS       current
    DESCRIPTION
        "Cisco Firepower mgmt:ProfDerivedInterface:configMessage
        managed object property"
    ::= { cfprMgmtProfDerivedInterfaceEntry 4 }

cfprMgmtProfDerivedInterfaceConfigState OBJECT-TYPE
    SYNTAX       CfprMgmtConfigState
    MAX-ACCESS   read-only
    STATUS       current
    DESCRIPTION
        "Cisco Firepower mgmt:ProfDerivedInterface:configState
        managed object property"
    ::= { cfprMgmtProfDerivedInterfaceEntry 5 }

cfprMgmtProfDerivedInterfaceIpV4State OBJECT-TYPE
    SYNTAX       CfprVnicExternalMgmtIPMode
    MAX-ACCESS   read-only
    STATUS       current
    DESCRIPTION
        "Cisco Firepower mgmt:ProfDerivedInterface:ipV4State
        managed object property"
    ::= { cfprMgmtProfDerivedInterfaceEntry 6 }

cfprMgmtProfDerivedInterfaceIpV6State OBJECT-TYPE
    SYNTAX       CfprVnicExternalMgmtIPMode
    MAX-ACCESS   read-only
    STATUS       current
    DESCRIPTION
        "Cisco Firepower mgmt:ProfDerivedInterface:ipV6State
        managed object property"
    ::= { cfprMgmtProfDerivedInterfaceEntry 7 }

cfprMgmtProfDerivedInterfaceMode OBJECT-TYPE
    SYNTAX       CfprMgmtMode
    MAX-ACCESS   read-only
    STATUS       current
    DESCRIPTION
        "Cisco Firepower mgmt:ProfDerivedInterface:mode
        managed object property"
    ::= { cfprMgmtProfDerivedInterfaceEntry 8 }

cfprMgmtProfDerivedInterfaceOperState OBJECT-TYPE
    SYNTAX       CfprMgmtOperState
    MAX-ACCESS   read-only
    STATUS       current
    DESCRIPTION
        "Cisco Firepower mgmt:ProfDerivedInterface:operState
        managed object property"
    ::= { cfprMgmtProfDerivedInterfaceEntry 9 }

cfprMgmtVnetTable OBJECT-TYPE
    SYNTAX           SEQUENCE OF CfprMgmtVnetEntry
    MAX-ACCESS       not-accessible
    STATUS           current
    DESCRIPTION
        "Cisco Firepower mgmt:Vnet managed object table"
    ::= { cfprMgmtObjects 44 }

cfprMgmtVnetEntry OBJECT-TYPE
    SYNTAX           CfprMgmtVnetEntry
    MAX-ACCESS       not-accessible
    STATUS           current
    DESCRIPTION
        "Entry for the cfprMgmtVnetTable table."
    INDEX { cfprMgmtVnetInstanceId }
    ::= { cfprMgmtVnetTable 1 }

CfprMgmtVnetEntry ::= SEQUENCE {
    cfprMgmtVnetInstanceId                                           CfprManagedObjectId,
    cfprMgmtVnetDn                                                   CfprManagedObjectDn,
    cfprMgmtVnetRn                                                   SnmpAdminString,
    cfprMgmtVnetConfigState                                          CfprMgmtConfigState,
    cfprMgmtVnetId                                                   Gauge32,
    cfprMgmtVnetName                                                 SnmpAdminString
}

cfprMgmtVnetInstanceId OBJECT-TYPE
    SYNTAX       CfprManagedObjectId
    MAX-ACCESS   not-accessible
    STATUS       current
    DESCRIPTION
        "Instance identifier of the managed object."
    ::= { cfprMgmtVnetEntry 1 }

cfprMgmtVnetDn OBJECT-TYPE
    SYNTAX       CfprManagedObjectDn
    MAX-ACCESS   read-only
    STATUS       current
    DESCRIPTION
        "Cisco Firepower mgmt:Vnet:dn managed object property"
    ::= { cfprMgmtVnetEntry 2 }

cfprMgmtVnetRn OBJECT-TYPE
    SYNTAX       SnmpAdminString
    MAX-ACCESS   read-only
    STATUS       current
    DESCRIPTION
        "Cisco Firepower mgmt:Vnet:rn managed object property"
    ::= { cfprMgmtVnetEntry 3 }

cfprMgmtVnetConfigState OBJECT-TYPE
    SYNTAX       CfprMgmtConfigState
    MAX-ACCESS   read-only
    STATUS       current
    DESCRIPTION
        "Cisco Firepower mgmt:Vnet:configState managed object property"
    ::= { cfprMgmtVnetEntry 4 }

cfprMgmtVnetId OBJECT-TYPE
    SYNTAX       Gauge32
    MAX-ACCESS   read-only
    STATUS       current
    DESCRIPTION
        "Cisco Firepower mgmt:Vnet:id managed object property"
    ::= { cfprMgmtVnetEntry 5 }

cfprMgmtVnetName OBJECT-TYPE
    SYNTAX       SnmpAdminString
    MAX-ACCESS   read-only
    STATUS       current
    DESCRIPTION
        "Cisco Firepower mgmt:Vnet:name managed object property"
    ::= { cfprMgmtVnetEntry 6 }

END

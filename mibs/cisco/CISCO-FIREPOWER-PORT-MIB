-- *********************************************************************
-- CISCO-FIREPOWER-PORT-MIB.my
-- 
-- MIB representation of the Cisco Firepower
-- PORT management information model package
-- 
-- Created March 2020 by Charles Bullis
-- 
-- Copyright (c) 2005-2020 Cisco Systems, Inc. All rights reserved.
-- 
-- *********************************************************************

CISCO-FIREPOWER-PORT-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerMIBObjects,
    CfprManagedObjectId,
    CfprManagedObjectDn
        FROM CISCO-FIREPOWER-MIB
    CfprConditionRemoteInvRslt,
    CfprFsmCompletion,
    CfprFsmFlags,
    CfprFsmFsmStageStatus,
    CfprLicenseState,
    CfprNetworkConnectionType,
    CfprNetworkLocale,
    CfprNetworkPortRole,
    CfprNetworkPortType,
    CfprNetworkSwitchId,
    CfprNetworkTransport,
    CfprPortGroupType,
    CfprPortPIoFsmCurrentFsm,
    CfprPortPIoFsmStageName,
    CfprPortPIoFsmTaskItem,
    CfprPortSubGroupConfigState,
    CfprPortSubGroupSlotId,
    CfprPortTrust
        FROM CISCO-FIREPOWER-TC-MIB;

cfprPortObjects MODULE-IDENTITY
    LAST-UPDATED    "202003100000Z"
    ORGANIZATION    "Cisco Systems Inc."
    CONTACT-INFO
        "Cisco Systems
        Customer Service
        
        Postal: 170 W Tasman Drive
        San Jose, CA  95134
        USA
        
        Tel: +1 800 553-NETS
        
        E-mail: firepower-mibs@cisco.com"
    DESCRIPTION
        "MIB representation of the Cisco Firepower
        PORT management information model package"
    ::= { ciscoFirepowerMIBObjects 63 }

cfprPortDomainEpTable OBJECT-TYPE
    SYNTAX           SEQUENCE OF CfprPortDomainEpEntry
    MAX-ACCESS       not-accessible
    STATUS           current
    DESCRIPTION
        "Cisco Firepower port:DomainEp managed object table"
    ::= { cfprPortObjects 1 }

cfprPortDomainEpEntry OBJECT-TYPE
    SYNTAX           CfprPortDomainEpEntry
    MAX-ACCESS       not-accessible
    STATUS           current
    DESCRIPTION
        "Entry for the cfprPortDomainEpTable table."
    INDEX { cfprPortDomainEpInstanceId }
    ::= { cfprPortDomainEpTable 1 }

CfprPortDomainEpEntry ::= SEQUENCE {
    cfprPortDomainEpInstanceId                                       CfprManagedObjectId,
    cfprPortDomainEpDn                                               CfprManagedObjectDn,
    cfprPortDomainEpRn                                               SnmpAdminString,
    cfprPortDomainEpEpDn                                             SnmpAdminString,
    cfprPortDomainEpIfRole                                           CfprNetworkPortRole,
    cfprPortDomainEpIfType                                           CfprNetworkPortType,
    cfprPortDomainEpLocale                                           CfprNetworkLocale,
    cfprPortDomainEpName                                             SnmpAdminString,
    cfprPortDomainEpPeerDn                                           SnmpAdminString,
    cfprPortDomainEpTransport                                        CfprNetworkTransport,
    cfprPortDomainEpType                                             CfprNetworkConnectionType
}

cfprPortDomainEpInstanceId OBJECT-TYPE
    SYNTAX       CfprManagedObjectId
    MAX-ACCESS   not-accessible
    STATUS       current
    DESCRIPTION
        "Instance identifier of the managed object."
    ::= { cfprPortDomainEpEntry 1 }

cfprPortDomainEpDn OBJECT-TYPE
    SYNTAX       CfprManagedObjectDn
    MAX-ACCESS   read-only
    STATUS       current
    DESCRIPTION
        "Cisco Firepower port:DomainEp:dn managed object property"
    ::= { cfprPortDomainEpEntry 2 }

cfprPortDomainEpRn OBJECT-TYPE
    SYNTAX       SnmpAdminString
    MAX-ACCESS   read-only
    STATUS       current
    DESCRIPTION
        "Cisco Firepower port:DomainEp:rn managed object property"
    ::= { cfprPortDomainEpEntry 3 }

cfprPortDomainEpEpDn OBJECT-TYPE
    SYNTAX       SnmpAdminString
    MAX-ACCESS   read-only
    STATUS       current
    DESCRIPTION
        "Cisco Firepower port:DomainEp:epDn managed object property"
    ::= { cfprPortDomainEpEntry 4 }

cfprPortDomainEpIfRole OBJECT-TYPE
    SYNTAX       CfprNetworkPortRole
    MAX-ACCESS   read-only
    STATUS       current
    DESCRIPTION
        "Cisco Firepower port:DomainEp:ifRole managed object property"
    ::= { cfprPortDomainEpEntry 5 }

cfprPortDomainEpIfType OBJECT-TYPE
    SYNTAX       CfprNetworkPortType
    MAX-ACCESS   read-only
    STATUS       current
    DESCRIPTION
        "Cisco Firepower port:DomainEp:ifType managed object property"
    ::= { cfprPortDomainEpEntry 6 }

cfprPortDomainEpLocale OBJECT-TYPE
    SYNTAX       CfprNetworkLocale
    MAX-ACCESS   read-only
    STATUS       current
    DESCRIPTION
        "Cisco Firepower port:DomainEp:locale managed object property"
    ::= { cfprPortDomainEpEntry 7 }

cfprPortDomainEpName OBJECT-TYPE
    SYNTAX       SnmpAdminString
    MAX-ACCESS   read-only
    STATUS       current
    DESCRIPTION
        "Cisco Firepower port:DomainEp:name managed object property"
    ::= { cfprPortDomainEpEntry 8 }

cfprPortDomainEpPeerDn OBJECT-TYPE
    SYNTAX       SnmpAdminString
    MAX-ACCESS   read-only
    STATUS       current
    DESCRIPTION
        "Cisco Firepower port:DomainEp:peerDn managed object property"
    ::= { cfprPortDomainEpEntry 9 }

cfprPortDomainEpTransport OBJECT-TYPE
    SYNTAX       CfprNetworkTransport
    MAX-ACCESS   read-only
    STATUS       current
    DESCRIPTION
        "Cisco Firepower port:DomainEp:transport managed object property"
    ::= { cfprPortDomainEpEntry 10 }

cfprPortDomainEpType OBJECT-TYPE
    SYNTAX       CfprNetworkConnectionType
    MAX-ACCESS   read-only
    STATUS       current
    DESCRIPTION
        "Cisco Firepower port:DomainEp:type managed object property"
    ::= { cfprPortDomainEpEntry 11 }

cfprPortGroupTable OBJECT-TYPE
    SYNTAX           SEQUENCE OF CfprPortGroupEntry
    MAX-ACCESS       not-accessible
    STATUS           current
    DESCRIPTION
        "Cisco Firepower port:Group managed object table"
    ::= { cfprPortObjects 2 }

cfprPortGroupEntry OBJECT-TYPE
    SYNTAX           CfprPortGroupEntry
    MAX-ACCESS       not-accessible
    STATUS           current
    DESCRIPTION
        "Entry for the cfprPortGroupTable table."
    INDEX { cfprPortGroupInstanceId }
    ::= { cfprPortGroupTable 1 }

CfprPortGroupEntry ::= SEQUENCE {
    cfprPortGroupInstanceId                                          CfprManagedObjectId,
    cfprPortGroupDn                                                  CfprManagedObjectDn,
    cfprPortGroupRn                                                  SnmpAdminString,
    cfprPortGroupLocale                                              CfprNetworkLocale,
    cfprPortGroupName                                                SnmpAdminString,
    cfprPortGroupTransport                                           CfprNetworkTransport,
    cfprPortGroupType                                                CfprPortGroupType
}

cfprPortGroupInstanceId OBJECT-TYPE
    SYNTAX       CfprManagedObjectId
    MAX-ACCESS   not-accessible
    STATUS       current
    DESCRIPTION
        "Instance identifier of the managed object."
    ::= { cfprPortGroupEntry 1 }

cfprPortGroupDn OBJECT-TYPE
    SYNTAX       CfprManagedObjectDn
    MAX-ACCESS   read-only
    STATUS       current
    DESCRIPTION
        "Cisco Firepower port:Group:dn managed object property"
    ::= { cfprPortGroupEntry 2 }

cfprPortGroupRn OBJECT-TYPE
    SYNTAX       SnmpAdminString
    MAX-ACCESS   read-only
    STATUS       current
    DESCRIPTION
        "Cisco Firepower port:Group:rn managed object property"
    ::= { cfprPortGroupEntry 3 }

cfprPortGroupLocale OBJECT-TYPE
    SYNTAX       CfprNetworkLocale
    MAX-ACCESS   read-only
    STATUS       current
    DESCRIPTION
        "Cisco Firepower port:Group:locale managed object property"
    ::= { cfprPortGroupEntry 4 }

cfprPortGroupName OBJECT-TYPE
    SYNTAX       SnmpAdminString
    MAX-ACCESS   read-only
    STATUS       current
    DESCRIPTION
        "Cisco Firepower port:Group:name managed object property"
    ::= { cfprPortGroupEntry 5 }

cfprPortGroupTransport OBJECT-TYPE
    SYNTAX       CfprNetworkTransport
    MAX-ACCESS   read-only
    STATUS       current
    DESCRIPTION
        "Cisco Firepower port:Group:transport managed object property"
    ::= { cfprPortGroupEntry 6 }

cfprPortGroupType OBJECT-TYPE
    SYNTAX       CfprPortGroupType
    MAX-ACCESS   read-only
    STATUS       current
    DESCRIPTION
        "Cisco Firepower port:Group:type managed object property"
    ::= { cfprPortGroupEntry 7 }

cfprPortPIoFsmTable OBJECT-TYPE
    SYNTAX           SEQUENCE OF CfprPortPIoFsmEntry
    MAX-ACCESS       not-accessible
    STATUS           current
    DESCRIPTION
        "Cisco Firepower port:PIoFsm managed object table"
    ::= { cfprPortObjects 3 }

cfprPortPIoFsmEntry OBJECT-TYPE
    SYNTAX           CfprPortPIoFsmEntry
    MAX-ACCESS       not-accessible
    STATUS           current
    DESCRIPTION
        "Entry for the cfprPortPIoFsmTable table."
    INDEX { cfprPortPIoFsmInstanceId }
    ::= { cfprPortPIoFsmTable 1 }

CfprPortPIoFsmEntry ::= SEQUENCE {
    cfprPortPIoFsmInstanceId                                         CfprManagedObjectId,
    cfprPortPIoFsmDn                                                 CfprManagedObjectDn,
    cfprPortPIoFsmRn                                                 SnmpAdminString,
    cfprPortPIoFsmCompletionTime                                     DateAndTime,
    cfprPortPIoFsmCurrentFsm                                         CfprPortPIoFsmCurrentFsm,
    cfprPortPIoFsmDescr                                              SnmpAdminString,
    cfprPortPIoFsmFsmStatus                                          CfprFsmFsmStageStatus,
    cfprPortPIoFsmProgress                                           Gauge32,
    cfprPortPIoFsmRmtErrCode                                         Gauge32,
    cfprPortPIoFsmRmtErrDescr                                        SnmpAdminString,
    cfprPortPIoFsmRmtRslt                                            CfprConditionRemoteInvRslt
}

cfprPortPIoFsmInstanceId OBJECT-TYPE
    SYNTAX       CfprManagedObjectId
    MAX-ACCESS   not-accessible
    STATUS       current
    DESCRIPTION
        "Instance identifier of the managed object."
    ::= { cfprPortPIoFsmEntry 1 }

cfprPortPIoFsmDn OBJECT-TYPE
    SYNTAX       CfprManagedObjectDn
    MAX-ACCESS   read-only
    STATUS       current
    DESCRIPTION
        "Cisco Firepower port:PIoFsm:dn managed object property"
    ::= { cfprPortPIoFsmEntry 2 }

cfprPortPIoFsmRn OBJECT-TYPE
    SYNTAX       SnmpAdminString
    MAX-ACCESS   read-only
    STATUS       current
    DESCRIPTION
        "Cisco Firepower port:PIoFsm:rn managed object property"
    ::= { cfprPortPIoFsmEntry 3 }

cfprPortPIoFsmCompletionTime OBJECT-TYPE
    SYNTAX       DateAndTime
    MAX-ACCESS   read-only
    STATUS       current
    DESCRIPTION
        "Cisco Firepower port:PIoFsm:completionTime managed
        object property"
    ::= { cfprPortPIoFsmEntry 4 }

cfprPortPIoFsmCurrentFsm OBJECT-TYPE
    SYNTAX       CfprPortPIoFsmCurrentFsm
    MAX-ACCESS   read-only
    STATUS       current
    DESCRIPTION
        "Cisco Firepower port:PIoFsm:currentFsm managed object property"
    ::= { cfprPortPIoFsmEntry 5 }

cfprPortPIoFsmDescr OBJECT-TYPE
    SYNTAX       SnmpAdminString
    MAX-ACCESS   read-only
    STATUS       current
    DESCRIPTION
        "Cisco Firepower port:PIoFsm:descr managed object property"
    ::= { cfprPortPIoFsmEntry 6 }

cfprPortPIoFsmFsmStatus OBJECT-TYPE
    SYNTAX       CfprFsmFsmStageStatus
    MAX-ACCESS   read-only
    STATUS       current
    DESCRIPTION
        "Cisco Firepower port:PIoFsm:fsmStatus managed object property"
    ::= { cfprPortPIoFsmEntry 7 }

cfprPortPIoFsmProgress OBJECT-TYPE
    SYNTAX       Gauge32
    MAX-ACCESS   read-only
    STATUS       current
    DESCRIPTION
        "Cisco Firepower port:PIoFsm:progress managed object property"
    ::= { cfprPortPIoFsmEntry 8 }

cfprPortPIoFsmRmtErrCode OBJECT-TYPE
    SYNTAX       Gauge32
    MAX-ACCESS   read-only
    STATUS       current
    DESCRIPTION
        "Cisco Firepower port:PIoFsm:rmtErrCode managed object property"
    ::= { cfprPortPIoFsmEntry 9 }

cfprPortPIoFsmRmtErrDescr OBJECT-TYPE
    SYNTAX       SnmpAdminString
    MAX-ACCESS   read-only
    STATUS       current
    DESCRIPTION
        "Cisco Firepower port:PIoFsm:rmtErrDescr managed object property"
    ::= { cfprPortPIoFsmEntry 10 }

cfprPortPIoFsmRmtRslt OBJECT-TYPE
    SYNTAX       CfprConditionRemoteInvRslt
    MAX-ACCESS   read-only
    STATUS       current
    DESCRIPTION
        "Cisco Firepower port:PIoFsm:rmtRslt managed object property"
    ::= { cfprPortPIoFsmEntry 11 }

cfprPortPIoFsmStageTable OBJECT-TYPE
    SYNTAX           SEQUENCE OF CfprPortPIoFsmStageEntry
    MAX-ACCESS       not-accessible
    STATUS           current
    DESCRIPTION
        "Cisco Firepower port:PIoFsmStage managed object table"
    ::= { cfprPortObjects 4 }

cfprPortPIoFsmStageEntry OBJECT-TYPE
    SYNTAX           CfprPortPIoFsmStageEntry
    MAX-ACCESS       not-accessible
    STATUS           current
    DESCRIPTION
        "Entry for the cfprPortPIoFsmStageTable table."
    INDEX { cfprPortPIoFsmStageInstanceId }
    ::= { cfprPortPIoFsmStageTable 1 }

CfprPortPIoFsmStageEntry ::= SEQUENCE {
    cfprPortPIoFsmStageInstanceId                                    CfprManagedObjectId,
    cfprPortPIoFsmStageDn                                            CfprManagedObjectDn,
    cfprPortPIoFsmStageRn                                            SnmpAdminString,
    cfprPortPIoFsmStageDescr                                         SnmpAdminString,
    cfprPortPIoFsmStageLastUpdateTime                                DateAndTime,
    cfprPortPIoFsmStageName                                          CfprPortPIoFsmStageName,
    cfprPortPIoFsmStageOrder                                         Gauge32,
    cfprPortPIoFsmStageRetry                                         Gauge32,
    cfprPortPIoFsmStageStageStatus                                   CfprFsmFsmStageStatus
}

cfprPortPIoFsmStageInstanceId OBJECT-TYPE
    SYNTAX       CfprManagedObjectId
    MAX-ACCESS   not-accessible
    STATUS       current
    DESCRIPTION
        "Instance identifier of the managed object."
    ::= { cfprPortPIoFsmStageEntry 1 }

cfprPortPIoFsmStageDn OBJECT-TYPE
    SYNTAX       CfprManagedObjectDn
    MAX-ACCESS   read-only
    STATUS       current
    DESCRIPTION
        "Cisco Firepower port:PIoFsmStage:dn managed object property"
    ::= { cfprPortPIoFsmStageEntry 2 }

cfprPortPIoFsmStageRn OBJECT-TYPE
    SYNTAX       SnmpAdminString
    MAX-ACCESS   read-only
    STATUS       current
    DESCRIPTION
        "Cisco Firepower port:PIoFsmStage:rn managed object property"
    ::= { cfprPortPIoFsmStageEntry 3 }

cfprPortPIoFsmStageDescr OBJECT-TYPE
    SYNTAX       SnmpAdminString
    MAX-ACCESS   read-only
    STATUS       current
    DESCRIPTION
        "Cisco Firepower port:PIoFsmStage:descr managed object property"
    ::= { cfprPortPIoFsmStageEntry 4 }

cfprPortPIoFsmStageLastUpdateTime OBJECT-TYPE
    SYNTAX       DateAndTime
    MAX-ACCESS   read-only
    STATUS       current
    DESCRIPTION
        "Cisco Firepower port:PIoFsmStage:lastUpdateTime
        managed object property"
    ::= { cfprPortPIoFsmStageEntry 5 }

cfprPortPIoFsmStageName OBJECT-TYPE
    SYNTAX       CfprPortPIoFsmStageName
    MAX-ACCESS   read-only
    STATUS       current
    DESCRIPTION
        "Cisco Firepower port:PIoFsmStage:name managed object property"
    ::= { cfprPortPIoFsmStageEntry 6 }

cfprPortPIoFsmStageOrder OBJECT-TYPE
    SYNTAX       Gauge32
    MAX-ACCESS   read-only
    STATUS       current
    DESCRIPTION
        "Cisco Firepower port:PIoFsmStage:order managed object property"
    ::= { cfprPortPIoFsmStageEntry 7 }

cfprPortPIoFsmStageRetry OBJECT-TYPE
    SYNTAX       Gauge32
    MAX-ACCESS   read-only
    STATUS       current
    DESCRIPTION
        "Cisco Firepower port:PIoFsmStage:retry managed object property"
    ::= { cfprPortPIoFsmStageEntry 8 }

cfprPortPIoFsmStageStageStatus OBJECT-TYPE
    SYNTAX       CfprFsmFsmStageStatus
    MAX-ACCESS   read-only
    STATUS       current
    DESCRIPTION
        "Cisco Firepower port:PIoFsmStage:stageStatus managed
        object property"
    ::= { cfprPortPIoFsmStageEntry 9 }

cfprPortPIoFsmTaskTable OBJECT-TYPE
    SYNTAX           SEQUENCE OF CfprPortPIoFsmTaskEntry
    MAX-ACCESS       not-accessible
    STATUS           current
    DESCRIPTION
        "Cisco Firepower port:PIoFsmTask managed object table"
    ::= { cfprPortObjects 5 }

cfprPortPIoFsmTaskEntry OBJECT-TYPE
    SYNTAX           CfprPortPIoFsmTaskEntry
    MAX-ACCESS       not-accessible
    STATUS           current
    DESCRIPTION
        "Entry for the cfprPortPIoFsmTaskTable table."
    INDEX { cfprPortPIoFsmTaskInstanceId }
    ::= { cfprPortPIoFsmTaskTable 1 }

CfprPortPIoFsmTaskEntry ::= SEQUENCE {
    cfprPortPIoFsmTaskInstanceId                                     CfprManagedObjectId,
    cfprPortPIoFsmTaskDn                                             CfprManagedObjectDn,
    cfprPortPIoFsmTaskRn                                             SnmpAdminString,
    cfprPortPIoFsmTaskCompletion                                     CfprFsmCompletion,
    cfprPortPIoFsmTaskFlags                                          CfprFsmFlags,
    cfprPortPIoFsmTaskItem                                           CfprPortPIoFsmTaskItem,
    cfprPortPIoFsmTaskSeqId                                          Gauge32
}

cfprPortPIoFsmTaskInstanceId OBJECT-TYPE
    SYNTAX       CfprManagedObjectId
    MAX-ACCESS   not-accessible
    STATUS       current
    DESCRIPTION
        "Instance identifier of the managed object."
    ::= { cfprPortPIoFsmTaskEntry 1 }

cfprPortPIoFsmTaskDn OBJECT-TYPE
    SYNTAX       CfprManagedObjectDn
    MAX-ACCESS   read-only
    STATUS       current
    DESCRIPTION
        "Cisco Firepower port:PIoFsmTask:dn managed object property"
    ::= { cfprPortPIoFsmTaskEntry 2 }

cfprPortPIoFsmTaskRn OBJECT-TYPE
    SYNTAX       SnmpAdminString
    MAX-ACCESS   read-only
    STATUS       current
    DESCRIPTION
        "Cisco Firepower port:PIoFsmTask:rn managed object property"
    ::= { cfprPortPIoFsmTaskEntry 3 }

cfprPortPIoFsmTaskCompletion OBJECT-TYPE
    SYNTAX       CfprFsmCompletion
    MAX-ACCESS   read-only
    STATUS       current
    DESCRIPTION
        "Cisco Firepower port:PIoFsmTask:completion managed
        object property"
    ::= { cfprPortPIoFsmTaskEntry 4 }

cfprPortPIoFsmTaskFlags OBJECT-TYPE
    SYNTAX       CfprFsmFlags
    MAX-ACCESS   read-only
    STATUS       current
    DESCRIPTION
        "Cisco Firepower port:PIoFsmTask:flags managed object property"
    ::= { cfprPortPIoFsmTaskEntry 5 }

cfprPortPIoFsmTaskItem OBJECT-TYPE
    SYNTAX       CfprPortPIoFsmTaskItem
    MAX-ACCESS   read-only
    STATUS       current
    DESCRIPTION
        "Cisco Firepower port:PIoFsmTask:item managed object property"
    ::= { cfprPortPIoFsmTaskEntry 6 }

cfprPortPIoFsmTaskSeqId OBJECT-TYPE
    SYNTAX       Gauge32
    MAX-ACCESS   read-only
    STATUS       current
    DESCRIPTION
        "Cisco Firepower port:PIoFsmTask:seqId managed object property"
    ::= { cfprPortPIoFsmTaskEntry 7 }

cfprPortSubGroupTable OBJECT-TYPE
    SYNTAX           SEQUENCE OF CfprPortSubGroupEntry
    MAX-ACCESS       not-accessible
    STATUS           current
    DESCRIPTION
        "Cisco Firepower port:SubGroup managed object table"
    ::= { cfprPortObjects 6 }

cfprPortSubGroupEntry OBJECT-TYPE
    SYNTAX           CfprPortSubGroupEntry
    MAX-ACCESS       not-accessible
    STATUS           current
    DESCRIPTION
        "Entry for the cfprPortSubGroupTable table."
    INDEX { cfprPortSubGroupInstanceId }
    ::= { cfprPortSubGroupTable 1 }

CfprPortSubGroupEntry ::= SEQUENCE {
    cfprPortSubGroupInstanceId                                       CfprManagedObjectId,
    cfprPortSubGroupDn                                               CfprManagedObjectDn,
    cfprPortSubGroupRn                                               SnmpAdminString,
    cfprPortSubGroupAggrPortId                                       Gauge32,
    cfprPortSubGroupConfigState                                      CfprPortSubGroupConfigState,
    cfprPortSubGroupLicGP                                            Unsigned64,
    cfprPortSubGroupLicState                                         CfprLicenseState,
    cfprPortSubGroupLocale                                           CfprNetworkLocale,
    cfprPortSubGroupName                                             SnmpAdminString,
    cfprPortSubGroupSlotId                                           CfprPortSubGroupSlotId,
    cfprPortSubGroupSwitchId                                         CfprNetworkSwitchId,
    cfprPortSubGroupTransport                                        CfprNetworkTransport,
    cfprPortSubGroupType                                             CfprNetworkConnectionType
}

cfprPortSubGroupInstanceId OBJECT-TYPE
    SYNTAX       CfprManagedObjectId
    MAX-ACCESS   not-accessible
    STATUS       current
    DESCRIPTION
        "Instance identifier of the managed object."
    ::= { cfprPortSubGroupEntry 1 }

cfprPortSubGroupDn OBJECT-TYPE
    SYNTAX       CfprManagedObjectDn
    MAX-ACCESS   read-only
    STATUS       current
    DESCRIPTION
        "Cisco Firepower port:SubGroup:dn managed object property"
    ::= { cfprPortSubGroupEntry 2 }

cfprPortSubGroupRn OBJECT-TYPE
    SYNTAX       SnmpAdminString
    MAX-ACCESS   read-only
    STATUS       current
    DESCRIPTION
        "Cisco Firepower port:SubGroup:rn managed object property"
    ::= { cfprPortSubGroupEntry 3 }

cfprPortSubGroupAggrPortId OBJECT-TYPE
    SYNTAX       Gauge32
    MAX-ACCESS   read-only
    STATUS       current
    DESCRIPTION
        "Cisco Firepower port:SubGroup:aggrPortId managed object property"
    ::= { cfprPortSubGroupEntry 4 }

cfprPortSubGroupConfigState OBJECT-TYPE
    SYNTAX       CfprPortSubGroupConfigState
    MAX-ACCESS   read-only
    STATUS       current
    DESCRIPTION
        "Cisco Firepower port:SubGroup:configState managed
        object property"
    ::= { cfprPortSubGroupEntry 5 }

cfprPortSubGroupLicGP OBJECT-TYPE
    SYNTAX       Unsigned64
    MAX-ACCESS   read-only
    STATUS       current
    DESCRIPTION
        "Cisco Firepower port:SubGroup:licGP managed object property"
    ::= { cfprPortSubGroupEntry 6 }

cfprPortSubGroupLicState OBJECT-TYPE
    SYNTAX       CfprLicenseState
    MAX-ACCESS   read-only
    STATUS       current
    DESCRIPTION
        "Cisco Firepower port:SubGroup:licState managed object property"
    ::= { cfprPortSubGroupEntry 7 }

cfprPortSubGroupLocale OBJECT-TYPE
    SYNTAX       CfprNetworkLocale
    MAX-ACCESS   read-only
    STATUS       current
    DESCRIPTION
        "Cisco Firepower port:SubGroup:locale managed object property"
    ::= { cfprPortSubGroupEntry 8 }

cfprPortSubGroupName OBJECT-TYPE
    SYNTAX       SnmpAdminString
    MAX-ACCESS   read-only
    STATUS       current
    DESCRIPTION
        "Cisco Firepower port:SubGroup:name managed object property"
    ::= { cfprPortSubGroupEntry 9 }

cfprPortSubGroupSlotId OBJECT-TYPE
    SYNTAX       CfprPortSubGroupSlotId
    MAX-ACCESS   read-only
    STATUS       current
    DESCRIPTION
        "Cisco Firepower port:SubGroup:slotId managed object property"
    ::= { cfprPortSubGroupEntry 10 }

cfprPortSubGroupSwitchId OBJECT-TYPE
    SYNTAX       CfprNetworkSwitchId
    MAX-ACCESS   read-only
    STATUS       current
    DESCRIPTION
        "Cisco Firepower port:SubGroup:switchId managed object property"
    ::= { cfprPortSubGroupEntry 11 }

cfprPortSubGroupTransport OBJECT-TYPE
    SYNTAX       CfprNetworkTransport
    MAX-ACCESS   read-only
    STATUS       current
    DESCRIPTION
        "Cisco Firepower port:SubGroup:transport managed object property"
    ::= { cfprPortSubGroupEntry 12 }

cfprPortSubGroupType OBJECT-TYPE
    SYNTAX       CfprNetworkConnectionType
    MAX-ACCESS   read-only
    STATUS       current
    DESCRIPTION
        "Cisco Firepower port:SubGroup:type managed object property"
    ::= { cfprPortSubGroupEntry 13 }

cfprPortTrustModeTable OBJECT-TYPE
    SYNTAX           SEQUENCE OF CfprPortTrustModeEntry
    MAX-ACCESS       not-accessible
    STATUS           current
    DESCRIPTION
        "Cisco Firepower port:TrustMode managed object table"
    ::= { cfprPortObjects 7 }

cfprPortTrustModeEntry OBJECT-TYPE
    SYNTAX           CfprPortTrustModeEntry
    MAX-ACCESS       not-accessible
    STATUS           current
    DESCRIPTION
        "Entry for the cfprPortTrustModeTable table."
    INDEX { cfprPortTrustModeInstanceId }
    ::= { cfprPortTrustModeTable 1 }

CfprPortTrustModeEntry ::= SEQUENCE {
    cfprPortTrustModeInstanceId                                      CfprManagedObjectId,
    cfprPortTrustModeDn                                              CfprManagedObjectDn,
    cfprPortTrustModeRn                                              SnmpAdminString,
    cfprPortTrustModeState                                           CfprPortTrust
}

cfprPortTrustModeInstanceId OBJECT-TYPE
    SYNTAX       CfprManagedObjectId
    MAX-ACCESS   not-accessible
    STATUS       current
    DESCRIPTION
        "Instance identifier of the managed object."
    ::= { cfprPortTrustModeEntry 1 }

cfprPortTrustModeDn OBJECT-TYPE
    SYNTAX       CfprManagedObjectDn
    MAX-ACCESS   read-only
    STATUS       current
    DESCRIPTION
        "Cisco Firepower port:TrustMode:dn managed object property"
    ::= { cfprPortTrustModeEntry 2 }

cfprPortTrustModeRn OBJECT-TYPE
    SYNTAX       SnmpAdminString
    MAX-ACCESS   read-only
    STATUS       current
    DESCRIPTION
        "Cisco Firepower port:TrustMode:rn managed object property"
    ::= { cfprPortTrustModeEntry 3 }

cfprPortTrustModeState OBJECT-TYPE
    SYNTAX       CfprPortTrust
    MAX-ACCESS   read-only
    STATUS       current
    DESCRIPTION
        "Cisco Firepower port:TrustMode:state managed object property"
    ::= { cfprPortTrustModeEntry 4 }

END

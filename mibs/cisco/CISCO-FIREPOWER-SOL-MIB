-- *********************************************************************
-- CISCO-FIREPOWER-SOL-MIB.my
-- 
-- MIB representation of the Cisco Firepower
-- SOL management information model package
-- 
-- Created March 2020 by Charles Bullis
-- 
-- Copyright (c) 2005-2020 Cisco Systems, Inc. All rights reserved.
-- 
-- *********************************************************************

CISCO-FIREPOWER-SOL-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerMIBObjects,
    CfprManagedObjectId,
    CfprManagedObjectDn
        FROM CISCO-FIREPOWER-MIB
    CfprPolicyPolicyOwner,
    CfprSolAdminState,
    CfprSolSpeed
        FROM CISCO-FIREPOWER-TC-MIB;

cfprSolObjects MODULE-IDENTITY
    LAST-UPDATED    "202003100000Z"
    ORGANIZATION    "Cisco Systems Inc."
    CONTACT-INFO
        "Cisco Systems
        Customer Service
        
        Postal: 170 W Tasman Drive
        San Jose, CA  95134
        USA
        
        Tel: +1 800 553-NETS
        
        E-mail: firepower-mibs@cisco.com"
    DESCRIPTION
        "MIB representation of the Cisco Firepower
        SOL management information model package"
    ::= { ciscoFirepowerMIBObjects 72 }

cfprSolConfigTable OBJECT-TYPE
    SYNTAX           SEQUENCE OF CfprSolConfigEntry
    MAX-ACCESS       not-accessible
    STATUS           current
    DESCRIPTION
        "Cisco Firepower sol:Config managed object table"
    ::= { cfprSolObjects 1 }

cfprSolConfigEntry OBJECT-TYPE
    SYNTAX           CfprSolConfigEntry
    MAX-ACCESS       not-accessible
    STATUS           current
    DESCRIPTION
        "Entry for the cfprSolConfigTable table."
    INDEX { cfprSolConfigInstanceId }
    ::= { cfprSolConfigTable 1 }

CfprSolConfigEntry ::= SEQUENCE {
    cfprSolConfigInstanceId                                          CfprManagedObjectId,
    cfprSolConfigDn                                                  CfprManagedObjectDn,
    cfprSolConfigRn                                                  SnmpAdminString,
    cfprSolConfigAdminState                                          CfprSolAdminState,
    cfprSolConfigDescr                                               SnmpAdminString,
    cfprSolConfigIntId                                               SnmpAdminString,
    cfprSolConfigName                                                SnmpAdminString,
    cfprSolConfigPolicyLevel                                         Gauge32,
    cfprSolConfigPolicyOwner                                         CfprPolicyPolicyOwner,
    cfprSolConfigSpeed                                               CfprSolSpeed
}

cfprSolConfigInstanceId OBJECT-TYPE
    SYNTAX       CfprManagedObjectId
    MAX-ACCESS   not-accessible
    STATUS       current
    DESCRIPTION
        "Instance identifier of the managed object."
    ::= { cfprSolConfigEntry 1 }

cfprSolConfigDn OBJECT-TYPE
    SYNTAX       CfprManagedObjectDn
    MAX-ACCESS   read-only
    STATUS       current
    DESCRIPTION
        "Cisco Firepower sol:Config:dn managed object property"
    ::= { cfprSolConfigEntry 2 }

cfprSolConfigRn OBJECT-TYPE
    SYNTAX       SnmpAdminString
    MAX-ACCESS   read-only
    STATUS       current
    DESCRIPTION
        "Cisco Firepower sol:Config:rn managed object property"
    ::= { cfprSolConfigEntry 3 }

cfprSolConfigAdminState OBJECT-TYPE
    SYNTAX       CfprSolAdminState
    MAX-ACCESS   read-only
    STATUS       current
    DESCRIPTION
        "Cisco Firepower sol:Config:adminState managed object property"
    ::= { cfprSolConfigEntry 4 }

cfprSolConfigDescr OBJECT-TYPE
    SYNTAX       SnmpAdminString
    MAX-ACCESS   read-only
    STATUS       current
    DESCRIPTION
        "Cisco Firepower sol:Config:descr managed object property"
    ::= { cfprSolConfigEntry 5 }

cfprSolConfigIntId OBJECT-TYPE
    SYNTAX       SnmpAdminString
    MAX-ACCESS   read-only
    STATUS       current
    DESCRIPTION
        "Cisco Firepower sol:Config:intId managed object property"
    ::= { cfprSolConfigEntry 6 }

cfprSolConfigName OBJECT-TYPE
    SYNTAX       SnmpAdminString
    MAX-ACCESS   read-only
    STATUS       current
    DESCRIPTION
        "Cisco Firepower sol:Config:name managed object property"
    ::= { cfprSolConfigEntry 7 }

cfprSolConfigPolicyLevel OBJECT-TYPE
    SYNTAX       Gauge32
    MAX-ACCESS   read-only
    STATUS       current
    DESCRIPTION
        "Cisco Firepower sol:Config:policyLevel managed object property"
    ::= { cfprSolConfigEntry 8 }

cfprSolConfigPolicyOwner OBJECT-TYPE
    SYNTAX       CfprPolicyPolicyOwner
    MAX-ACCESS   read-only
    STATUS       current
    DESCRIPTION
        "Cisco Firepower sol:Config:policyOwner managed object property"
    ::= { cfprSolConfigEntry 9 }

cfprSolConfigSpeed OBJECT-TYPE
    SYNTAX       CfprSolSpeed
    MAX-ACCESS   read-only
    STATUS       current
    DESCRIPTION
        "Cisco Firepower sol:Config:speed managed object property"
    ::= { cfprSolConfigEntry 10 }

cfprSolIfTable OBJECT-TYPE
    SYNTAX           SEQUENCE OF CfprSolIfEntry
    MAX-ACCESS       not-accessible
    STATUS           current
    DESCRIPTION
        "Cisco Firepower sol:If managed object table"
    ::= { cfprSolObjects 2 }

cfprSolIfEntry OBJECT-TYPE
    SYNTAX           CfprSolIfEntry
    MAX-ACCESS       not-accessible
    STATUS           current
    DESCRIPTION
        "Entry for the cfprSolIfTable table."
    INDEX { cfprSolIfInstanceId }
    ::= { cfprSolIfTable 1 }

CfprSolIfEntry ::= SEQUENCE {
    cfprSolIfInstanceId                                              CfprManagedObjectId,
    cfprSolIfDn                                                      CfprManagedObjectDn,
    cfprSolIfRn                                                      SnmpAdminString,
    cfprSolIfAdminState                                              CfprSolAdminState,
    cfprSolIfDescr                                                   SnmpAdminString,
    cfprSolIfIntId                                                   SnmpAdminString,
    cfprSolIfName                                                    SnmpAdminString,
    cfprSolIfPolicyLevel                                             Gauge32,
    cfprSolIfPolicyOwner                                             CfprPolicyPolicyOwner,
    cfprSolIfSpeed                                                   CfprSolSpeed
}

cfprSolIfInstanceId OBJECT-TYPE
    SYNTAX       CfprManagedObjectId
    MAX-ACCESS   not-accessible
    STATUS       current
    DESCRIPTION
        "Instance identifier of the managed object."
    ::= { cfprSolIfEntry 1 }

cfprSolIfDn OBJECT-TYPE
    SYNTAX       CfprManagedObjectDn
    MAX-ACCESS   read-only
    STATUS       current
    DESCRIPTION
        "Cisco Firepower sol:If:dn managed object property"
    ::= { cfprSolIfEntry 2 }

cfprSolIfRn OBJECT-TYPE
    SYNTAX       SnmpAdminString
    MAX-ACCESS   read-only
    STATUS       current
    DESCRIPTION
        "Cisco Firepower sol:If:rn managed object property"
    ::= { cfprSolIfEntry 3 }

cfprSolIfAdminState OBJECT-TYPE
    SYNTAX       CfprSolAdminState
    MAX-ACCESS   read-only
    STATUS       current
    DESCRIPTION
        "Cisco Firepower sol:If:adminState managed object property"
    ::= { cfprSolIfEntry 4 }

cfprSolIfDescr OBJECT-TYPE
    SYNTAX       SnmpAdminString
    MAX-ACCESS   read-only
    STATUS       current
    DESCRIPTION
        "Cisco Firepower sol:If:descr managed object property"
    ::= { cfprSolIfEntry 5 }

cfprSolIfIntId OBJECT-TYPE
    SYNTAX       SnmpAdminString
    MAX-ACCESS   read-only
    STATUS       current
    DESCRIPTION
        "Cisco Firepower sol:If:intId managed object property"
    ::= { cfprSolIfEntry 6 }

cfprSolIfName OBJECT-TYPE
    SYNTAX       SnmpAdminString
    MAX-ACCESS   read-only
    STATUS       current
    DESCRIPTION
        "Cisco Firepower sol:If:name managed object property"
    ::= { cfprSolIfEntry 7 }

cfprSolIfPolicyLevel OBJECT-TYPE
    SYNTAX       Gauge32
    MAX-ACCESS   read-only
    STATUS       current
    DESCRIPTION
        "Cisco Firepower sol:If:policyLevel managed object property"
    ::= { cfprSolIfEntry 8 }

cfprSolIfPolicyOwner OBJECT-TYPE
    SYNTAX       CfprPolicyPolicyOwner
    MAX-ACCESS   read-only
    STATUS       current
    DESCRIPTION
        "Cisco Firepower sol:If:policyOwner managed object property"
    ::= { cfprSolIfEntry 9 }

cfprSolIfSpeed OBJECT-TYPE
    SYNTAX       CfprSolSpeed
    MAX-ACCESS   read-only
    STATUS       current
    DESCRIPTION
        "Cisco Firepower sol:If:speed managed object property"
    ::= { cfprSolIfEntry 10 }

cfprSolPolicyTable OBJECT-TYPE
    SYNTAX           SEQUENCE OF CfprSolPolicyEntry
    MAX-ACCESS       not-accessible
    STATUS           current
    DESCRIPTION
        "Cisco Firepower sol:Policy managed object table"
    ::= { cfprSolObjects 3 }

cfprSolPolicyEntry OBJECT-TYPE
    SYNTAX           CfprSolPolicyEntry
    MAX-ACCESS       not-accessible
    STATUS           current
    DESCRIPTION
        "Entry for the cfprSolPolicyTable table."
    INDEX { cfprSolPolicyInstanceId }
    ::= { cfprSolPolicyTable 1 }

CfprSolPolicyEntry ::= SEQUENCE {
    cfprSolPolicyInstanceId                                          CfprManagedObjectId,
    cfprSolPolicyDn                                                  CfprManagedObjectDn,
    cfprSolPolicyRn                                                  SnmpAdminString,
    cfprSolPolicyAdminState                                          CfprSolAdminState,
    cfprSolPolicyDescr                                               SnmpAdminString,
    cfprSolPolicyIntId                                               SnmpAdminString,
    cfprSolPolicyName                                                SnmpAdminString,
    cfprSolPolicyPolicyLevel                                         Gauge32,
    cfprSolPolicyPolicyOwner                                         CfprPolicyPolicyOwner,
    cfprSolPolicySpeed                                               CfprSolSpeed
}

cfprSolPolicyInstanceId OBJECT-TYPE
    SYNTAX       CfprManagedObjectId
    MAX-ACCESS   not-accessible
    STATUS       current
    DESCRIPTION
        "Instance identifier of the managed object."
    ::= { cfprSolPolicyEntry 1 }

cfprSolPolicyDn OBJECT-TYPE
    SYNTAX       CfprManagedObjectDn
    MAX-ACCESS   read-only
    STATUS       current
    DESCRIPTION
        "Cisco Firepower sol:Policy:dn managed object property"
    ::= { cfprSolPolicyEntry 2 }

cfprSolPolicyRn OBJECT-TYPE
    SYNTAX       SnmpAdminString
    MAX-ACCESS   read-only
    STATUS       current
    DESCRIPTION
        "Cisco Firepower sol:Policy:rn managed object property"
    ::= { cfprSolPolicyEntry 3 }

cfprSolPolicyAdminState OBJECT-TYPE
    SYNTAX       CfprSolAdminState
    MAX-ACCESS   read-only
    STATUS       current
    DESCRIPTION
        "Cisco Firepower sol:Policy:adminState managed object property"
    ::= { cfprSolPolicyEntry 4 }

cfprSolPolicyDescr OBJECT-TYPE
    SYNTAX       SnmpAdminString
    MAX-ACCESS   read-only
    STATUS       current
    DESCRIPTION
        "Cisco Firepower sol:Policy:descr managed object property"
    ::= { cfprSolPolicyEntry 5 }

cfprSolPolicyIntId OBJECT-TYPE
    SYNTAX       SnmpAdminString
    MAX-ACCESS   read-only
    STATUS       current
    DESCRIPTION
        "Cisco Firepower sol:Policy:intId managed object property"
    ::= { cfprSolPolicyEntry 6 }

cfprSolPolicyName OBJECT-TYPE
    SYNTAX       SnmpAdminString
    MAX-ACCESS   read-only
    STATUS       current
    DESCRIPTION
        "Cisco Firepower sol:Policy:name managed object property"
    ::= { cfprSolPolicyEntry 7 }

cfprSolPolicyPolicyLevel OBJECT-TYPE
    SYNTAX       Gauge32
    MAX-ACCESS   read-only
    STATUS       current
    DESCRIPTION
        "Cisco Firepower sol:Policy:policyLevel managed object property"
    ::= { cfprSolPolicyEntry 8 }

cfprSolPolicyPolicyOwner OBJECT-TYPE
    SYNTAX       CfprPolicyPolicyOwner
    MAX-ACCESS   read-only
    STATUS       current
    DESCRIPTION
        "Cisco Firepower sol:Policy:policyOwner managed object property"
    ::= { cfprSolPolicyEntry 9 }

cfprSolPolicySpeed OBJECT-TYPE
    SYNTAX       CfprSolSpeed
    MAX-ACCESS   read-only
    STATUS       current
    DESCRIPTION
        "Cisco Firepower sol:Policy:speed managed object property"
    ::= { cfprSolPolicyEntry 10 }

END

-- *********************************************************************
-- CISCO-FIREPOWER-VNIC-MIB.my
-- 
-- MIB representation of the Cisco Firepower
-- VNIC management information model package
-- 
-- Created March 2020 by Charles Bullis
-- 
-- Copyright (c) 2005-2020 Cisco Systems, Inc. All rights reserved.
-- 
-- *********************************************************************

CISCO-FIREPOWER-VNIC-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerMIBObjects,
    CfprManagedObjectId,
    CfprManagedObjectDn
        FROM CISCO-FIREPOWER-MIB
    CfprConditionRemoteInvRslt,
    CfprDpsecForgedTransmit,
    CfprFabricHostPortId,
    CfprFabricSSAPortType,
    CfprFabricVlanSharingType,
    CfprFsmCompletion,
    CfprFsmFlags,
    CfprFsmFsmStageStatus,
    CfprLsConfigState,
    CfprNetworkSwitchId,
    CfprNwctrlAdminState,
    CfprNwctrlLinkFailAction,
    CfprNwctrlRegistrationMode,
    CfprPolicyPolicyOwner,
    CfprVmMgmtPlane,
    CfprVnicAEtherIfType,
    CfprVnicAFcIfType,
    CfprVnicAIpcIfType,
    CfprVnicAScsiIfType,
    CfprVnicAppRole,
    CfprVnicConfigIssues,
    CfprVnicConnectionOwner,
    CfprVnicConnectionType,
    CfprVnicDefBehType,
    CfprVnicDefaultAction,
    CfprVnicDynamicConReqProtection,
    CfprVnicEtherBaseSwitchId,
    CfprVnicEtherType,
    CfprVnicExternalMgmtIPMode,
    CfprVnicFcBasePersBind,
    CfprVnicFcBaseType,
    CfprVnicFcNodeOwner,
    CfprVnicHostNwIOPerfPref,
    CfprVnicIPv4DnsPref,
    CfprVnicIScsiIfDefType,
    CfprVnicIScsiNodeOwner,
    CfprVnicIfOperState,
    CfprVnicInstantiation,
    CfprVnicIpcType,
    CfprVnicL2IfSwitchId,
    CfprVnicLanConnTemplSwitchId,
    CfprVnicLunId,
    CfprVnicPortProfileType,
    CfprVnicProfileConfigQualifier,
    CfprVnicProfileSetFsmCurrentFsm,
    CfprVnicProfileSetFsmStageName,
    CfprVnicProfileSetFsmTaskItem,
    CfprVnicSanConnTemplTarget,
    CfprVnicScsiType,
    CfprVnicTemplateTarget,
    CfprVnicTemplateType,
    CfprVnicVhbaBehPolicyType,
    CfprVnicVirtualizationPreferenceType,
    CfprVnicVnicBehPolicyType,
    CfprVnicVnicBootDev,
    CfprVnicVnicOperHostPort
        FROM CISCO-FIREPOWER-TC-MIB;

cfprVnicObjects MODULE-IDENTITY
    LAST-UPDATED    "202003100000Z"
    ORGANIZATION    "Cisco Systems Inc."
    CONTACT-INFO
        "Cisco Systems
        Customer Service
        
        Postal: 170 W Tasman Drive
        San Jose, CA  95134
        USA
        
        Tel: +1 800 553-NETS
        
        E-mail: firepower-mibs@cisco.com"
    DESCRIPTION
        "MIB representation of the Cisco Firepower
        VNIC management information model package"
    ::= { ciscoFirepowerMIBObjects 83 }

cfprVnicBootIpPolicyTable OBJECT-TYPE
    SYNTAX           SEQUENCE OF CfprVnicBootIpPolicyEntry
    MAX-ACCESS       not-accessible
    STATUS           current
    DESCRIPTION
        "Cisco Firepower vnic:BootIpPolicy managed object table"
    ::= { cfprVnicObjects 1 }

cfprVnicBootIpPolicyEntry OBJECT-TYPE
    SYNTAX           CfprVnicBootIpPolicyEntry
    MAX-ACCESS       not-accessible
    STATUS           current
    DESCRIPTION
        "Entry for the cfprVnicBootIpPolicyTable table."
    INDEX { cfprVnicBootIpPolicyInstanceId }
    ::= { cfprVnicBootIpPolicyTable 1 }

CfprVnicBootIpPolicyEntry ::= SEQUENCE {
    cfprVnicBootIpPolicyInstanceId                                   CfprManagedObjectId,
    cfprVnicBootIpPolicyDn                                           CfprManagedObjectDn,
    cfprVnicBootIpPolicyRn                                           SnmpAdminString,
    cfprVnicBootIpPolicyDescr                                        SnmpAdminString,
    cfprVnicBootIpPolicyIntId                                        SnmpAdminString,
    cfprVnicBootIpPolicyName                                         SnmpAdminString,
    cfprVnicBootIpPolicyPolicyLevel                                  Gauge32,
    cfprVnicBootIpPolicyPolicyOwner                                  CfprPolicyPolicyOwner,
    cfprVnicBootIpPolicyPoolName                                     SnmpAdminString
}

cfprVnicBootIpPolicyInstanceId OBJECT-TYPE
    SYNTAX       CfprManagedObjectId
    MAX-ACCESS   not-accessible
    STATUS       current
    DESCRIPTION
        "Instance identifier of the managed object."
    ::= { cfprVnicBootIpPolicyEntry 1 }

cfprVnicBootIpPolicyDn OBJECT-TYPE
    SYNTAX       CfprManagedObjectDn
    MAX-ACCESS   read-only
    STATUS       current
    DESCRIPTION
        "Cisco Firepower vnic:BootIpPolicy:dn managed object property"
    ::= { cfprVnicBootIpPolicyEntry 2 }

cfprVnicBootIpPolicyRn OBJECT-TYPE
    SYNTAX       SnmpAdminString
    MAX-ACCESS   read-only
    STATUS       current
    DESCRIPTION
        "Cisco Firepower vnic:BootIpPolicy:rn managed object property"
    ::= { cfprVnicBootIpPolicyEntry 3 }

cfprVnicBootIpPolicyDescr OBJECT-TYPE
    SYNTAX       SnmpAdminString
    MAX-ACCESS   read-only
    STATUS       current
    DESCRIPTION
        "Cisco Firepower vnic:BootIpPolicy:descr managed object property"
    ::= { cfprVnicBootIpPolicyEntry 4 }

cfprVnicBootIpPolicyIntId OBJECT-TYPE
    SYNTAX       SnmpAdminString
    MAX-ACCESS   read-only
    STATUS       current
    DESCRIPTION
        "Cisco Firepower vnic:BootIpPolicy:intId managed object property"
    ::= { cfprVnicBootIpPolicyEntry 5 }

cfprVnicBootIpPolicyName OBJECT-TYPE
    SYNTAX       SnmpAdminString
    MAX-ACCESS   read-only
    STATUS       current
    DESCRIPTION
        "Cisco Firepower vnic:BootIpPolicy:name managed object property"
    ::= { cfprVnicBootIpPolicyEntry 6 }

cfprVnicBootIpPolicyPolicyLevel OBJECT-TYPE
    SYNTAX       Gauge32
    MAX-ACCESS   read-only
    STATUS       current
    DESCRIPTION
        "Cisco Firepower vnic:BootIpPolicy:policyLevel
        managed object property"
    ::= { cfprVnicBootIpPolicyEntry 7 }

cfprVnicBootIpPolicyPolicyOwner OBJECT-TYPE
    SYNTAX       CfprPolicyPolicyOwner
    MAX-ACCESS   read-only
    STATUS       current
    DESCRIPTION
        "Cisco Firepower vnic:BootIpPolicy:policyOwner
        managed object property"
    ::= { cfprVnicBootIpPolicyEntry 8 }

cfprVnicBootIpPolicyPoolName OBJECT-TYPE
    SYNTAX       SnmpAdminString
    MAX-ACCESS   read-only
    STATUS       current
    DESCRIPTION
        "Cisco Firepower vnic:BootIpPolicy:poolName managed
        object property"
    ::= { cfprVnicBootIpPolicyEntry 9 }

cfprVnicBootTargetTable OBJECT-TYPE
    SYNTAX           SEQUENCE OF CfprVnicBootTargetEntry
    MAX-ACCESS       not-accessible
    STATUS           current
    DESCRIPTION
        "Cisco Firepower vnic:BootTarget managed object table"
    ::= { cfprVnicObjects 2 }

cfprVnicBootTargetEntry OBJECT-TYPE
    SYNTAX           CfprVnicBootTargetEntry
    MAX-ACCESS       not-accessible
    STATUS           current
    DESCRIPTION
        "Entry for the cfprVnicBootTargetTable table."
    INDEX { cfprVnicBootTargetInstanceId }
    ::= { cfprVnicBootTargetTable 1 }

CfprVnicBootTargetEntry ::= SEQUENCE {
    cfprVnicBootTargetInstanceId                                     CfprManagedObjectId,
    cfprVnicBootTargetDn                                             CfprManagedObjectDn,
    cfprVnicBootTargetRn                                             SnmpAdminString,
    cfprVnicBootTargetLun                                            SnmpAdminString,
    cfprVnicBootTargetWwn                                            Unsigned64
}

cfprVnicBootTargetInstanceId OBJECT-TYPE
    SYNTAX       CfprManagedObjectId
    MAX-ACCESS   not-accessible
    STATUS       current
    DESCRIPTION
        "Instance identifier of the managed object."
    ::= { cfprVnicBootTargetEntry 1 }

cfprVnicBootTargetDn OBJECT-TYPE
    SYNTAX       CfprManagedObjectDn
    MAX-ACCESS   read-only
    STATUS       current
    DESCRIPTION
        "Cisco Firepower vnic:BootTarget:dn managed object property"
    ::= { cfprVnicBootTargetEntry 2 }

cfprVnicBootTargetRn OBJECT-TYPE
    SYNTAX       SnmpAdminString
    MAX-ACCESS   read-only
    STATUS       current
    DESCRIPTION
        "Cisco Firepower vnic:BootTarget:rn managed object property"
    ::= { cfprVnicBootTargetEntry 3 }

cfprVnicBootTargetLun OBJECT-TYPE
    SYNTAX       SnmpAdminString
    MAX-ACCESS   read-only
    STATUS       current
    DESCRIPTION
        "Cisco Firepower vnic:BootTarget:lun managed object property"
    ::= { cfprVnicBootTargetEntry 4 }

cfprVnicBootTargetWwn OBJECT-TYPE
    SYNTAX       Unsigned64
    MAX-ACCESS   read-only
    STATUS       current
    DESCRIPTION
        "Cisco Firepower vnic:BootTarget:wwn managed object property"
    ::= { cfprVnicBootTargetEntry 5 }

cfprVnicConnDefTable OBJECT-TYPE
    SYNTAX           SEQUENCE OF CfprVnicConnDefEntry
    MAX-ACCESS       not-accessible
    STATUS           current
    DESCRIPTION
        "Cisco Firepower vnic:ConnDef managed object table"
    ::= { cfprVnicObjects 3 }

cfprVnicConnDefEntry OBJECT-TYPE
    SYNTAX           CfprVnicConnDefEntry
    MAX-ACCESS       not-accessible
    STATUS           current
    DESCRIPTION
        "Entry for the cfprVnicConnDefTable table."
    INDEX { cfprVnicConnDefInstanceId }
    ::= { cfprVnicConnDefTable 1 }

CfprVnicConnDefEntry ::= SEQUENCE {
    cfprVnicConnDefInstanceId                                        CfprManagedObjectId,
    cfprVnicConnDefDn                                                CfprManagedObjectDn,
    cfprVnicConnDefRn                                                SnmpAdminString,
    cfprVnicConnDefFltAggr                                           Unsigned64,
    cfprVnicConnDefLanConnPolicyName                                 SnmpAdminString,
    cfprVnicConnDefOperLanConnPolicyName                             SnmpAdminString,
    cfprVnicConnDefOperSanConnPolicyName                             SnmpAdminString,
    cfprVnicConnDefSanConnPolicyName                                 SnmpAdminString
}

cfprVnicConnDefInstanceId OBJECT-TYPE
    SYNTAX       CfprManagedObjectId
    MAX-ACCESS   not-accessible
    STATUS       current
    DESCRIPTION
        "Instance identifier of the managed object."
    ::= { cfprVnicConnDefEntry 1 }

cfprVnicConnDefDn OBJECT-TYPE
    SYNTAX       CfprManagedObjectDn
    MAX-ACCESS   read-only
    STATUS       current
    DESCRIPTION
        "Cisco Firepower vnic:ConnDef:dn managed object property"
    ::= { cfprVnicConnDefEntry 2 }

cfprVnicConnDefRn OBJECT-TYPE
    SYNTAX       SnmpAdminString
    MAX-ACCESS   read-only
    STATUS       current
    DESCRIPTION
        "Cisco Firepower vnic:ConnDef:rn managed object property"
    ::= { cfprVnicConnDefEntry 3 }

cfprVnicConnDefFltAggr OBJECT-TYPE
    SYNTAX       Unsigned64
    MAX-ACCESS   read-only
    STATUS       current
    DESCRIPTION
        "Cisco Firepower vnic:ConnDef:fltAggr managed object property"
    ::= { cfprVnicConnDefEntry 4 }

cfprVnicConnDefLanConnPolicyName OBJECT-TYPE
    SYNTAX       SnmpAdminString
    MAX-ACCESS   read-only
    STATUS       current
    DESCRIPTION
        "Cisco Firepower vnic:ConnDef:lanConnPolicyName
        managed object property"
    ::= { cfprVnicConnDefEntry 5 }

cfprVnicConnDefOperLanConnPolicyName OBJECT-TYPE
    SYNTAX       SnmpAdminString
    MAX-ACCESS   read-only
    STATUS       current
    DESCRIPTION
        "Cisco Firepower vnic:ConnDef:operLanConnPolicyName
        managed object property"
    ::= { cfprVnicConnDefEntry 6 }

cfprVnicConnDefOperSanConnPolicyName OBJECT-TYPE
    SYNTAX       SnmpAdminString
    MAX-ACCESS   read-only
    STATUS       current
    DESCRIPTION
        "Cisco Firepower vnic:ConnDef:operSanConnPolicyName
        managed object property"
    ::= { cfprVnicConnDefEntry 7 }

cfprVnicConnDefSanConnPolicyName OBJECT-TYPE
    SYNTAX       SnmpAdminString
    MAX-ACCESS   read-only
    STATUS       current
    DESCRIPTION
        "Cisco Firepower vnic:ConnDef:sanConnPolicyName
        managed object property"
    ::= { cfprVnicConnDefEntry 8 }

cfprVnicDefBehTable OBJECT-TYPE
    SYNTAX           SEQUENCE OF CfprVnicDefBehEntry
    MAX-ACCESS       not-accessible
    STATUS           current
    DESCRIPTION
        "Cisco Firepower vnic:DefBeh managed object table"
    ::= { cfprVnicObjects 4 }

cfprVnicDefBehEntry OBJECT-TYPE
    SYNTAX           CfprVnicDefBehEntry
    MAX-ACCESS       not-accessible
    STATUS           current
    DESCRIPTION
        "Entry for the cfprVnicDefBehTable table."
    INDEX { cfprVnicDefBehInstanceId }
    ::= { cfprVnicDefBehTable 1 }

CfprVnicDefBehEntry ::= SEQUENCE {
    cfprVnicDefBehInstanceId                                         CfprManagedObjectId,
    cfprVnicDefBehDn                                                 CfprManagedObjectDn,
    cfprVnicDefBehRn                                                 SnmpAdminString,
    cfprVnicDefBehAction                                             CfprVnicDefaultAction,
    cfprVnicDefBehDescr                                              SnmpAdminString,
    cfprVnicDefBehIntId                                              SnmpAdminString,
    cfprVnicDefBehName                                               SnmpAdminString,
    cfprVnicDefBehNwTemplName                                        SnmpAdminString,
    cfprVnicDefBehPolicyLevel                                        Gauge32,
    cfprVnicDefBehPolicyOwner                                        CfprPolicyPolicyOwner,
    cfprVnicDefBehType                                               CfprVnicDefBehType
}

cfprVnicDefBehInstanceId OBJECT-TYPE
    SYNTAX       CfprManagedObjectId
    MAX-ACCESS   not-accessible
    STATUS       current
    DESCRIPTION
        "Instance identifier of the managed object."
    ::= { cfprVnicDefBehEntry 1 }

cfprVnicDefBehDn OBJECT-TYPE
    SYNTAX       CfprManagedObjectDn
    MAX-ACCESS   read-only
    STATUS       current
    DESCRIPTION
        "Cisco Firepower vnic:DefBeh:dn managed object property"
    ::= { cfprVnicDefBehEntry 2 }

cfprVnicDefBehRn OBJECT-TYPE
    SYNTAX       SnmpAdminString
    MAX-ACCESS   read-only
    STATUS       current
    DESCRIPTION
        "Cisco Firepower vnic:DefBeh:rn managed object property"
    ::= { cfprVnicDefBehEntry 3 }

cfprVnicDefBehAction OBJECT-TYPE
    SYNTAX       CfprVnicDefaultAction
    MAX-ACCESS   read-only
    STATUS       current
    DESCRIPTION
        "Cisco Firepower vnic:DefBeh:action managed object property"
    ::= { cfprVnicDefBehEntry 4 }

cfprVnicDefBehDescr OBJECT-TYPE
    SYNTAX       SnmpAdminString
    MAX-ACCESS   read-only
    STATUS       current
    DESCRIPTION
        "Cisco Firepower vnic:DefBeh:descr managed object property"
    ::= { cfprVnicDefBehEntry 5 }

cfprVnicDefBehIntId OBJECT-TYPE
    SYNTAX       SnmpAdminString
    MAX-ACCESS   read-only
    STATUS       current
    DESCRIPTION
        "Cisco Firepower vnic:DefBeh:intId managed object property"
    ::= { cfprVnicDefBehEntry 6 }

cfprVnicDefBehName OBJECT-TYPE
    SYNTAX       SnmpAdminString
    MAX-ACCESS   read-only
    STATUS       current
    DESCRIPTION
        "Cisco Firepower vnic:DefBeh:name managed object property"
    ::= { cfprVnicDefBehEntry 7 }

cfprVnicDefBehNwTemplName OBJECT-TYPE
    SYNTAX       SnmpAdminString
    MAX-ACCESS   read-only
    STATUS       current
    DESCRIPTION
        "Cisco Firepower vnic:DefBeh:nwTemplName managed object property"
    ::= { cfprVnicDefBehEntry 8 }

cfprVnicDefBehPolicyLevel OBJECT-TYPE
    SYNTAX       Gauge32
    MAX-ACCESS   read-only
    STATUS       current
    DESCRIPTION
        "Cisco Firepower vnic:DefBeh:policyLevel managed object property"
    ::= { cfprVnicDefBehEntry 9 }

cfprVnicDefBehPolicyOwner OBJECT-TYPE
    SYNTAX       CfprPolicyPolicyOwner
    MAX-ACCESS   read-only
    STATUS       current
    DESCRIPTION
        "Cisco Firepower vnic:DefBeh:policyOwner managed object property"
    ::= { cfprVnicDefBehEntry 10 }

cfprVnicDefBehType OBJECT-TYPE
    SYNTAX       CfprVnicDefBehType
    MAX-ACCESS   read-only
    STATUS       current
    DESCRIPTION
        "Cisco Firepower vnic:DefBeh:type managed object property"
    ::= { cfprVnicDefBehEntry 11 }

cfprVnicDynamicConTable OBJECT-TYPE
    SYNTAX           SEQUENCE OF CfprVnicDynamicConEntry
    MAX-ACCESS       not-accessible
    STATUS           current
    DESCRIPTION
        "Cisco Firepower vnic:DynamicCon managed object table"
    ::= { cfprVnicObjects 5 }

cfprVnicDynamicConEntry OBJECT-TYPE
    SYNTAX           CfprVnicDynamicConEntry
    MAX-ACCESS       not-accessible
    STATUS           current
    DESCRIPTION
        "Entry for the cfprVnicDynamicConTable table."
    INDEX { cfprVnicDynamicConInstanceId }
    ::= { cfprVnicDynamicConTable 1 }

CfprVnicDynamicConEntry ::= SEQUENCE {
    cfprVnicDynamicConInstanceId                                     CfprManagedObjectId,
    cfprVnicDynamicConDn                                             CfprManagedObjectDn,
    cfprVnicDynamicConRn                                             SnmpAdminString,
    cfprVnicDynamicConAdaptorProfileName                             SnmpAdminString,
    cfprVnicDynamicConDescr                                          SnmpAdminString,
    cfprVnicDynamicConDynamicEth                                     Gauge32,
    cfprVnicDynamicConIntId                                          SnmpAdminString,
    cfprVnicDynamicConMtu                                            Gauge32,
    cfprVnicDynamicConName                                           SnmpAdminString,
    cfprVnicDynamicConNamingPrefix                                   SnmpAdminString,
    cfprVnicDynamicConPolicyLevel                                    Gauge32,
    cfprVnicDynamicConPolicyOwner                                    CfprPolicyPolicyOwner,
    cfprVnicDynamicConProtection                                     CfprVnicDynamicConReqProtection
}

cfprVnicDynamicConInstanceId OBJECT-TYPE
    SYNTAX       CfprManagedObjectId
    MAX-ACCESS   not-accessible
    STATUS       current
    DESCRIPTION
        "Instance identifier of the managed object."
    ::= { cfprVnicDynamicConEntry 1 }

cfprVnicDynamicConDn OBJECT-TYPE
    SYNTAX       CfprManagedObjectDn
    MAX-ACCESS   read-only
    STATUS       current
    DESCRIPTION
        "Cisco Firepower vnic:DynamicCon:dn managed object property"
    ::= { cfprVnicDynamicConEntry 2 }

cfprVnicDynamicConRn OBJECT-TYPE
    SYNTAX       SnmpAdminString
    MAX-ACCESS   read-only
    STATUS       current
    DESCRIPTION
        "Cisco Firepower vnic:DynamicCon:rn managed object property"
    ::= { cfprVnicDynamicConEntry 3 }

cfprVnicDynamicConAdaptorProfileName OBJECT-TYPE
    SYNTAX       SnmpAdminString
    MAX-ACCESS   read-only
    STATUS       current
    DESCRIPTION
        "Cisco Firepower vnic:DynamicCon:adaptorProfileName
        managed object property"
    ::= { cfprVnicDynamicConEntry 4 }

cfprVnicDynamicConDescr OBJECT-TYPE
    SYNTAX       SnmpAdminString
    MAX-ACCESS   read-only
    STATUS       current
    DESCRIPTION
        "Cisco Firepower vnic:DynamicCon:descr managed object property"
    ::= { cfprVnicDynamicConEntry 5 }

cfprVnicDynamicConDynamicEth OBJECT-TYPE
    SYNTAX       Gauge32
    MAX-ACCESS   read-only
    STATUS       current
    DESCRIPTION
        "Cisco Firepower vnic:DynamicCon:dynamicEth managed
        object property"
    ::= { cfprVnicDynamicConEntry 6 }

cfprVnicDynamicConIntId OBJECT-TYPE
    SYNTAX       SnmpAdminString
    MAX-ACCESS   read-only
    STATUS       current
    DESCRIPTION
        "Cisco Firepower vnic:DynamicCon:intId managed object property"
    ::= { cfprVnicDynamicConEntry 7 }

cfprVnicDynamicConMtu OBJECT-TYPE
    SYNTAX       Gauge32
    MAX-ACCESS   read-only
    STATUS       current
    DESCRIPTION
        "Cisco Firepower vnic:DynamicCon:mtu managed object property"
    ::= { cfprVnicDynamicConEntry 8 }

cfprVnicDynamicConName OBJECT-TYPE
    SYNTAX       SnmpAdminString
    MAX-ACCESS   read-only
    STATUS       current
    DESCRIPTION
        "Cisco Firepower vnic:DynamicCon:name managed object property"
    ::= { cfprVnicDynamicConEntry 9 }

cfprVnicDynamicConNamingPrefix OBJECT-TYPE
    SYNTAX       SnmpAdminString
    MAX-ACCESS   read-only
    STATUS       current
    DESCRIPTION
        "Cisco Firepower vnic:DynamicCon:namingPrefix managed
        object property"
    ::= { cfprVnicDynamicConEntry 10 }

cfprVnicDynamicConPolicyLevel OBJECT-TYPE
    SYNTAX       Gauge32
    MAX-ACCESS   read-only
    STATUS       current
    DESCRIPTION
        "Cisco Firepower vnic:DynamicCon:policyLevel managed
        object property"
    ::= { cfprVnicDynamicConEntry 11 }

cfprVnicDynamicConPolicyOwner OBJECT-TYPE
    SYNTAX       CfprPolicyPolicyOwner
    MAX-ACCESS   read-only
    STATUS       current
    DESCRIPTION
        "Cisco Firepower vnic:DynamicCon:policyOwner managed
        object property"
    ::= { cfprVnicDynamicConEntry 12 }

cfprVnicDynamicConProtection OBJECT-TYPE
    SYNTAX       CfprVnicDynamicConReqProtection
    MAX-ACCESS   read-only
    STATUS       current
    DESCRIPTION
        "Cisco Firepower vnic:DynamicCon:protection managed
        object property"
    ::= { cfprVnicDynamicConEntry 13 }

cfprVnicDynamicConPolicyTable OBJECT-TYPE
    SYNTAX           SEQUENCE OF CfprVnicDynamicConPolicyEntry
    MAX-ACCESS       not-accessible
    STATUS           current
    DESCRIPTION
        "Cisco Firepower vnic:DynamicConPolicy managed object table"
    ::= { cfprVnicObjects 6 }

cfprVnicDynamicConPolicyEntry OBJECT-TYPE
    SYNTAX           CfprVnicDynamicConPolicyEntry
    MAX-ACCESS       not-accessible
    STATUS           current
    DESCRIPTION
        "Entry for the cfprVnicDynamicConPolicyTable table."
    INDEX { cfprVnicDynamicConPolicyInstanceId }
    ::= { cfprVnicDynamicConPolicyTable 1 }

CfprVnicDynamicConPolicyEntry ::= SEQUENCE {
    cfprVnicDynamicConPolicyInstanceId                               CfprManagedObjectId,
    cfprVnicDynamicConPolicyDn                                       CfprManagedObjectDn,
    cfprVnicDynamicConPolicyRn                                       SnmpAdminString,
    cfprVnicDynamicConPolicyAdaptorProfileName                       SnmpAdminString,
    cfprVnicDynamicConPolicyDescr                                    SnmpAdminString,
    cfprVnicDynamicConPolicyDynamicEth                               Gauge32,
    cfprVnicDynamicConPolicyIntId                                    SnmpAdminString,
    cfprVnicDynamicConPolicyMtu                                      Gauge32,
    cfprVnicDynamicConPolicyName                                     SnmpAdminString,
    cfprVnicDynamicConPolicyNamingPrefix                             SnmpAdminString,
    cfprVnicDynamicConPolicyPolicyLevel                              Gauge32,
    cfprVnicDynamicConPolicyPolicyOwner                              CfprPolicyPolicyOwner,
    cfprVnicDynamicConPolicyProtection                               CfprVnicDynamicConReqProtection
}

cfprVnicDynamicConPolicyInstanceId OBJECT-TYPE
    SYNTAX       CfprManagedObjectId
    MAX-ACCESS   not-accessible
    STATUS       current
    DESCRIPTION
        "Instance identifier of the managed object."
    ::= { cfprVnicDynamicConPolicyEntry 1 }

cfprVnicDynamicConPolicyDn OBJECT-TYPE
    SYNTAX       CfprManagedObjectDn
    MAX-ACCESS   read-only
    STATUS       current
    DESCRIPTION
        "Cisco Firepower vnic:DynamicConPolicy:dn managed object property"
    ::= { cfprVnicDynamicConPolicyEntry 2 }

cfprVnicDynamicConPolicyRn OBJECT-TYPE
    SYNTAX       SnmpAdminString
    MAX-ACCESS   read-only
    STATUS       current
    DESCRIPTION
        "Cisco Firepower vnic:DynamicConPolicy:rn managed object property"
    ::= { cfprVnicDynamicConPolicyEntry 3 }

cfprVnicDynamicConPolicyAdaptorProfileName OBJECT-TYPE
    SYNTAX       SnmpAdminString
    MAX-ACCESS   read-only
    STATUS       current
    DESCRIPTION
        "Cisco Firepower vnic:DynamicConPolicy:adaptorProfileName
        managed object property"
    ::= { cfprVnicDynamicConPolicyEntry 4 }

cfprVnicDynamicConPolicyDescr OBJECT-TYPE
    SYNTAX       SnmpAdminString
    MAX-ACCESS   read-only
    STATUS       current
    DESCRIPTION
        "Cisco Firepower vnic:DynamicConPolicy:descr managed
        object property"
    ::= { cfprVnicDynamicConPolicyEntry 5 }

cfprVnicDynamicConPolicyDynamicEth OBJECT-TYPE
    SYNTAX       Gauge32
    MAX-ACCESS   read-only
    STATUS       current
    DESCRIPTION
        "Cisco Firepower vnic:DynamicConPolicy:dynamicEth
        managed object property"
    ::= { cfprVnicDynamicConPolicyEntry 6 }

cfprVnicDynamicConPolicyIntId OBJECT-TYPE
    SYNTAX       SnmpAdminString
    MAX-ACCESS   read-only
    STATUS       current
    DESCRIPTION
        "Cisco Firepower vnic:DynamicConPolicy:intId managed
        object property"
    ::= { cfprVnicDynamicConPolicyEntry 7 }

cfprVnicDynamicConPolicyMtu OBJECT-TYPE
    SYNTAX       Gauge32
    MAX-ACCESS   read-only
    STATUS       current
    DESCRIPTION
        "Cisco Firepower vnic:DynamicConPolicy:mtu managed
        object property"
    ::= { cfprVnicDynamicConPolicyEntry 8 }

cfprVnicDynamicConPolicyName OBJECT-TYPE
    SYNTAX       SnmpAdminString
    MAX-ACCESS   read-only
    STATUS       current
    DESCRIPTION
        "Cisco Firepower vnic:DynamicConPolicy:name managed
        object property"
    ::= { cfprVnicDynamicConPolicyEntry 9 }

cfprVnicDynamicConPolicyNamingPrefix OBJECT-TYPE
    SYNTAX       SnmpAdminString
    MAX-ACCESS   read-only
    STATUS       current
    DESCRIPTION
        "Cisco Firepower vnic:DynamicConPolicy:namingPrefix
        managed object property"
    ::= { cfprVnicDynamicConPolicyEntry 10 }

cfprVnicDynamicConPolicyPolicyLevel OBJECT-TYPE
    SYNTAX       Gauge32
    MAX-ACCESS   read-only
    STATUS       current
    DESCRIPTION
        "Cisco Firepower vnic:DynamicConPolicy:policyLevel
        managed object property"
    ::= { cfprVnicDynamicConPolicyEntry 11 }

cfprVnicDynamicConPolicyPolicyOwner OBJECT-TYPE
    SYNTAX       CfprPolicyPolicyOwner
    MAX-ACCESS   read-only
    STATUS       current
    DESCRIPTION
        "Cisco Firepower vnic:DynamicConPolicy:policyOwner
        managed object property"
    ::= { cfprVnicDynamicConPolicyEntry 12 }

cfprVnicDynamicConPolicyProtection OBJECT-TYPE
    SYNTAX       CfprVnicDynamicConReqProtection
    MAX-ACCESS   read-only
    STATUS       current
    DESCRIPTION
        "Cisco Firepower vnic:DynamicConPolicy:protection
        managed object property"
    ::= { cfprVnicDynamicConPolicyEntry 13 }

cfprVnicDynamicConPolicyRefTable OBJECT-TYPE
    SYNTAX           SEQUENCE OF CfprVnicDynamicConPolicyRefEntry
    MAX-ACCESS       not-accessible
    STATUS           current
    DESCRIPTION
        "Cisco Firepower vnic:DynamicConPolicyRef managed object table"
    ::= { cfprVnicObjects 7 }

cfprVnicDynamicConPolicyRefEntry OBJECT-TYPE
    SYNTAX           CfprVnicDynamicConPolicyRefEntry
    MAX-ACCESS       not-accessible
    STATUS           current
    DESCRIPTION
        "Entry for the cfprVnicDynamicConPolicyRefTable table."
    INDEX { cfprVnicDynamicConPolicyRefInstanceId }
    ::= { cfprVnicDynamicConPolicyRefTable 1 }

CfprVnicDynamicConPolicyRefEntry ::= SEQUENCE {
    cfprVnicDynamicConPolicyRefInstanceId                            CfprManagedObjectId,
    cfprVnicDynamicConPolicyRefDn                                    CfprManagedObjectDn,
    cfprVnicDynamicConPolicyRefRn                                    SnmpAdminString,
    cfprVnicDynamicConPolicyRefConPolicyName                         SnmpAdminString,
    cfprVnicDynamicConPolicyRefOperConPolicyName                     SnmpAdminString
}

cfprVnicDynamicConPolicyRefInstanceId OBJECT-TYPE
    SYNTAX       CfprManagedObjectId
    MAX-ACCESS   not-accessible
    STATUS       current
    DESCRIPTION
        "Instance identifier of the managed object."
    ::= { cfprVnicDynamicConPolicyRefEntry 1 }

cfprVnicDynamicConPolicyRefDn OBJECT-TYPE
    SYNTAX       CfprManagedObjectDn
    MAX-ACCESS   read-only
    STATUS       current
    DESCRIPTION
        "Cisco Firepower vnic:DynamicConPolicyRef:dn managed
        object property"
    ::= { cfprVnicDynamicConPolicyRefEntry 2 }

cfprVnicDynamicConPolicyRefRn OBJECT-TYPE
    SYNTAX       SnmpAdminString
    MAX-ACCESS   read-only
    STATUS       current
    DESCRIPTION
        "Cisco Firepower vnic:DynamicConPolicyRef:rn managed
        object property"
    ::= { cfprVnicDynamicConPolicyRefEntry 3 }

cfprVnicDynamicConPolicyRefConPolicyName OBJECT-TYPE
    SYNTAX       SnmpAdminString
    MAX-ACCESS   read-only
    STATUS       current
    DESCRIPTION
        "Cisco Firepower vnic:DynamicConPolicyRef:conPolicyName
        managed object property"
    ::= { cfprVnicDynamicConPolicyRefEntry 4 }

cfprVnicDynamicConPolicyRefOperConPolicyName OBJECT-TYPE
    SYNTAX       SnmpAdminString
    MAX-ACCESS   read-only
    STATUS       current
    DESCRIPTION
        "Cisco Firepower vnic:DynamicConPolicyRef:operConPolicyName
        managed object property"
    ::= { cfprVnicDynamicConPolicyRefEntry 5 }

cfprVnicDynamicIdUniverseTable OBJECT-TYPE
    SYNTAX           SEQUENCE OF CfprVnicDynamicIdUniverseEntry
    MAX-ACCESS       not-accessible
    STATUS           current
    DESCRIPTION
        "Cisco Firepower vnic:DynamicIdUniverse managed object table"
    ::= { cfprVnicObjects 8 }

cfprVnicDynamicIdUniverseEntry OBJECT-TYPE
    SYNTAX           CfprVnicDynamicIdUniverseEntry
    MAX-ACCESS       not-accessible
    STATUS           current
    DESCRIPTION
        "Entry for the cfprVnicDynamicIdUniverseTable table."
    INDEX { cfprVnicDynamicIdUniverseInstanceId }
    ::= { cfprVnicDynamicIdUniverseTable 1 }

CfprVnicDynamicIdUniverseEntry ::= SEQUENCE {
    cfprVnicDynamicIdUniverseInstanceId                              CfprManagedObjectId,
    cfprVnicDynamicIdUniverseDn                                      CfprManagedObjectDn,
    cfprVnicDynamicIdUniverseRn                                      SnmpAdminString,
    cfprVnicDynamicIdUniverseDescr                                   SnmpAdminString,
    cfprVnicDynamicIdUniverseIntId                                   SnmpAdminString,
    cfprVnicDynamicIdUniverseName                                    SnmpAdminString,
    cfprVnicDynamicIdUniversePolicyLevel                             Gauge32,
    cfprVnicDynamicIdUniversePolicyOwner                             CfprPolicyPolicyOwner
}

cfprVnicDynamicIdUniverseInstanceId OBJECT-TYPE
    SYNTAX       CfprManagedObjectId
    MAX-ACCESS   not-accessible
    STATUS       current
    DESCRIPTION
        "Instance identifier of the managed object."
    ::= { cfprVnicDynamicIdUniverseEntry 1 }

cfprVnicDynamicIdUniverseDn OBJECT-TYPE
    SYNTAX       CfprManagedObjectDn
    MAX-ACCESS   read-only
    STATUS       current
    DESCRIPTION
        "Cisco Firepower vnic:DynamicIdUniverse:dn managed
        object property"
    ::= { cfprVnicDynamicIdUniverseEntry 2 }

cfprVnicDynamicIdUniverseRn OBJECT-TYPE
    SYNTAX       SnmpAdminString
    MAX-ACCESS   read-only
    STATUS       current
    DESCRIPTION
        "Cisco Firepower vnic:DynamicIdUniverse:rn managed
        object property"
    ::= { cfprVnicDynamicIdUniverseEntry 3 }

cfprVnicDynamicIdUniverseDescr OBJECT-TYPE
    SYNTAX       SnmpAdminString
    MAX-ACCESS   read-only
    STATUS       current
    DESCRIPTION
        "Cisco Firepower vnic:DynamicIdUniverse:descr managed
        object property"
    ::= { cfprVnicDynamicIdUniverseEntry 4 }

cfprVnicDynamicIdUniverseIntId OBJECT-TYPE
    SYNTAX       SnmpAdminString
    MAX-ACCESS   read-only
    STATUS       current
    DESCRIPTION
        "Cisco Firepower vnic:DynamicIdUniverse:intId managed
        object property"
    ::= { cfprVnicDynamicIdUniverseEntry 5 }

cfprVnicDynamicIdUniverseName OBJECT-TYPE
    SYNTAX       SnmpAdminString
    MAX-ACCESS   read-only
    STATUS       current
    DESCRIPTION
        "Cisco Firepower vnic:DynamicIdUniverse:name managed
        object property"
    ::= { cfprVnicDynamicIdUniverseEntry 6 }

cfprVnicDynamicIdUniversePolicyLevel OBJECT-TYPE
    SYNTAX       Gauge32
    MAX-ACCESS   read-only
    STATUS       current
    DESCRIPTION
        "Cisco Firepower vnic:DynamicIdUniverse:policyLevel
        managed object property"
    ::= { cfprVnicDynamicIdUniverseEntry 7 }

cfprVnicDynamicIdUniversePolicyOwner OBJECT-TYPE
    SYNTAX       CfprPolicyPolicyOwner
    MAX-ACCESS   read-only
    STATUS       current
    DESCRIPTION
        "Cisco Firepower vnic:DynamicIdUniverse:policyOwner
        managed object property"
    ::= { cfprVnicDynamicIdUniverseEntry 8 }

cfprVnicDynamicProviderTable OBJECT-TYPE
    SYNTAX           SEQUENCE OF CfprVnicDynamicProviderEntry
    MAX-ACCESS       not-accessible
    STATUS           current
    DESCRIPTION
        "Cisco Firepower vnic:DynamicProvider managed object table"
    ::= { cfprVnicObjects 9 }

cfprVnicDynamicProviderEntry OBJECT-TYPE
    SYNTAX           CfprVnicDynamicProviderEntry
    MAX-ACCESS       not-accessible
    STATUS           current
    DESCRIPTION
        "Entry for the cfprVnicDynamicProviderTable table."
    INDEX { cfprVnicDynamicProviderInstanceId }
    ::= { cfprVnicDynamicProviderTable 1 }

CfprVnicDynamicProviderEntry ::= SEQUENCE {
    cfprVnicDynamicProviderInstanceId                                CfprManagedObjectId,
    cfprVnicDynamicProviderDn                                        CfprManagedObjectDn,
    cfprVnicDynamicProviderRn                                        SnmpAdminString,
    cfprVnicDynamicProviderName                                      SnmpAdminString
}

cfprVnicDynamicProviderInstanceId OBJECT-TYPE
    SYNTAX       CfprManagedObjectId
    MAX-ACCESS   not-accessible
    STATUS       current
    DESCRIPTION
        "Instance identifier of the managed object."
    ::= { cfprVnicDynamicProviderEntry 1 }

cfprVnicDynamicProviderDn OBJECT-TYPE
    SYNTAX       CfprManagedObjectDn
    MAX-ACCESS   read-only
    STATUS       current
    DESCRIPTION
        "Cisco Firepower vnic:DynamicProvider:dn managed object property"
    ::= { cfprVnicDynamicProviderEntry 2 }

cfprVnicDynamicProviderRn OBJECT-TYPE
    SYNTAX       SnmpAdminString
    MAX-ACCESS   read-only
    STATUS       current
    DESCRIPTION
        "Cisco Firepower vnic:DynamicProvider:rn managed object property"
    ::= { cfprVnicDynamicProviderEntry 3 }

cfprVnicDynamicProviderName OBJECT-TYPE
    SYNTAX       SnmpAdminString
    MAX-ACCESS   read-only
    STATUS       current
    DESCRIPTION
        "Cisco Firepower vnic:DynamicProvider:name managed
        object property"
    ::= { cfprVnicDynamicProviderEntry 4 }

cfprVnicDynamicProviderEpTable OBJECT-TYPE
    SYNTAX           SEQUENCE OF CfprVnicDynamicProviderEpEntry
    MAX-ACCESS       not-accessible
    STATUS           current
    DESCRIPTION
        "Cisco Firepower vnic:DynamicProviderEp managed object table"
    ::= { cfprVnicObjects 10 }

cfprVnicDynamicProviderEpEntry OBJECT-TYPE
    SYNTAX           CfprVnicDynamicProviderEpEntry
    MAX-ACCESS       not-accessible
    STATUS           current
    DESCRIPTION
        "Entry for the cfprVnicDynamicProviderEpTable table."
    INDEX { cfprVnicDynamicProviderEpInstanceId }
    ::= { cfprVnicDynamicProviderEpTable 1 }

CfprVnicDynamicProviderEpEntry ::= SEQUENCE {
    cfprVnicDynamicProviderEpInstanceId                              CfprManagedObjectId,
    cfprVnicDynamicProviderEpDn                                      CfprManagedObjectDn,
    cfprVnicDynamicProviderEpRn                                      SnmpAdminString,
    cfprVnicDynamicProviderEpChassisId                               Gauge32,
    cfprVnicDynamicProviderEpPortId                                  Gauge32,
    cfprVnicDynamicProviderEpSlotId                                  Gauge32,
    cfprVnicDynamicProviderEpSwitchId                                CfprNetworkSwitchId
}

cfprVnicDynamicProviderEpInstanceId OBJECT-TYPE
    SYNTAX       CfprManagedObjectId
    MAX-ACCESS   not-accessible
    STATUS       current
    DESCRIPTION
        "Instance identifier of the managed object."
    ::= { cfprVnicDynamicProviderEpEntry 1 }

cfprVnicDynamicProviderEpDn OBJECT-TYPE
    SYNTAX       CfprManagedObjectDn
    MAX-ACCESS   read-only
    STATUS       current
    DESCRIPTION
        "Cisco Firepower vnic:DynamicProviderEp:dn managed
        object property"
    ::= { cfprVnicDynamicProviderEpEntry 2 }

cfprVnicDynamicProviderEpRn OBJECT-TYPE
    SYNTAX       SnmpAdminString
    MAX-ACCESS   read-only
    STATUS       current
    DESCRIPTION
        "Cisco Firepower vnic:DynamicProviderEp:rn managed
        object property"
    ::= { cfprVnicDynamicProviderEpEntry 3 }

cfprVnicDynamicProviderEpChassisId OBJECT-TYPE
    SYNTAX       Gauge32
    MAX-ACCESS   read-only
    STATUS       current
    DESCRIPTION
        "Cisco Firepower vnic:DynamicProviderEp:chassisId
        managed object property"
    ::= { cfprVnicDynamicProviderEpEntry 4 }

cfprVnicDynamicProviderEpPortId OBJECT-TYPE
    SYNTAX       Gauge32
    MAX-ACCESS   read-only
    STATUS       current
    DESCRIPTION
        "Cisco Firepower vnic:DynamicProviderEp:portId
        managed object property"
    ::= { cfprVnicDynamicProviderEpEntry 5 }

cfprVnicDynamicProviderEpSlotId OBJECT-TYPE
    SYNTAX       Gauge32
    MAX-ACCESS   read-only
    STATUS       current
    DESCRIPTION
        "Cisco Firepower vnic:DynamicProviderEp:slotId
        managed object property"
    ::= { cfprVnicDynamicProviderEpEntry 6 }

cfprVnicDynamicProviderEpSwitchId OBJECT-TYPE
    SYNTAX       CfprNetworkSwitchId
    MAX-ACCESS   read-only
    STATUS       current
    DESCRIPTION
        "Cisco Firepower vnic:DynamicProviderEp:switchId
        managed object property"
    ::= { cfprVnicDynamicProviderEpEntry 7 }

cfprVnicEthLifTable OBJECT-TYPE
    SYNTAX           SEQUENCE OF CfprVnicEthLifEntry
    MAX-ACCESS       not-accessible
    STATUS           current
    DESCRIPTION
        "Cisco Firepower vnic:EthLif managed object table"
    ::= { cfprVnicObjects 11 }

cfprVnicEthLifEntry OBJECT-TYPE
    SYNTAX           CfprVnicEthLifEntry
    MAX-ACCESS       not-accessible
    STATUS           current
    DESCRIPTION
        "Entry for the cfprVnicEthLifTable table."
    INDEX { cfprVnicEthLifInstanceId }
    ::= { cfprVnicEthLifTable 1 }

CfprVnicEthLifEntry ::= SEQUENCE {
    cfprVnicEthLifInstanceId                                         CfprManagedObjectId,
    cfprVnicEthLifDn                                                 CfprManagedObjectDn,
    cfprVnicEthLifRn                                                 SnmpAdminString,
    cfprVnicEthLifAddr                                               MacAddress,
    cfprVnicEthLifName                                               SnmpAdminString,
    cfprVnicEthLifNicDn                                              SnmpAdminString,
    cfprVnicEthLifOwner                                              CfprVnicConnectionOwner,
    cfprVnicEthLifSwitchId                                           CfprNetworkSwitchId,
    cfprVnicEthLifType                                               CfprVnicConnectionType,
    cfprVnicEthLifVnicDn                                             SnmpAdminString
}

cfprVnicEthLifInstanceId OBJECT-TYPE
    SYNTAX       CfprManagedObjectId
    MAX-ACCESS   not-accessible
    STATUS       current
    DESCRIPTION
        "Instance identifier of the managed object."
    ::= { cfprVnicEthLifEntry 1 }

cfprVnicEthLifDn OBJECT-TYPE
    SYNTAX       CfprManagedObjectDn
    MAX-ACCESS   read-only
    STATUS       current
    DESCRIPTION
        "Cisco Firepower vnic:EthLif:dn managed object property"
    ::= { cfprVnicEthLifEntry 2 }

cfprVnicEthLifRn OBJECT-TYPE
    SYNTAX       SnmpAdminString
    MAX-ACCESS   read-only
    STATUS       current
    DESCRIPTION
        "Cisco Firepower vnic:EthLif:rn managed object property"
    ::= { cfprVnicEthLifEntry 3 }

cfprVnicEthLifAddr OBJECT-TYPE
    SYNTAX       MacAddress
    MAX-ACCESS   read-only
    STATUS       current
    DESCRIPTION
        "Cisco Firepower vnic:EthLif:addr managed object property"
    ::= { cfprVnicEthLifEntry 4 }

cfprVnicEthLifName OBJECT-TYPE
    SYNTAX       SnmpAdminString
    MAX-ACCESS   read-only
    STATUS       current
    DESCRIPTION
        "Cisco Firepower vnic:EthLif:name managed object property"
    ::= { cfprVnicEthLifEntry 5 }

cfprVnicEthLifNicDn OBJECT-TYPE
    SYNTAX       SnmpAdminString
    MAX-ACCESS   read-only
    STATUS       current
    DESCRIPTION
        "Cisco Firepower vnic:EthLif:nicDn managed object property"
    ::= { cfprVnicEthLifEntry 6 }

cfprVnicEthLifOwner OBJECT-TYPE
    SYNTAX       CfprVnicConnectionOwner
    MAX-ACCESS   read-only
    STATUS       current
    DESCRIPTION
        "Cisco Firepower vnic:EthLif:owner managed object property"
    ::= { cfprVnicEthLifEntry 7 }

cfprVnicEthLifSwitchId OBJECT-TYPE
    SYNTAX       CfprNetworkSwitchId
    MAX-ACCESS   read-only
    STATUS       current
    DESCRIPTION
        "Cisco Firepower vnic:EthLif:switchId managed object property"
    ::= { cfprVnicEthLifEntry 8 }

cfprVnicEthLifType OBJECT-TYPE
    SYNTAX       CfprVnicConnectionType
    MAX-ACCESS   read-only
    STATUS       current
    DESCRIPTION
        "Cisco Firepower vnic:EthLif:type managed object property"
    ::= { cfprVnicEthLifEntry 9 }

cfprVnicEthLifVnicDn OBJECT-TYPE
    SYNTAX       SnmpAdminString
    MAX-ACCESS   read-only
    STATUS       current
    DESCRIPTION
        "Cisco Firepower vnic:EthLif:vnicDn managed object property"
    ::= { cfprVnicEthLifEntry 10 }

cfprVnicEtherTable OBJECT-TYPE
    SYNTAX           SEQUENCE OF CfprVnicEtherEntry
    MAX-ACCESS       not-accessible
    STATUS           current
    DESCRIPTION
        "Cisco Firepower vnic:Ether managed object table"
    ::= { cfprVnicObjects 12 }

cfprVnicEtherEntry OBJECT-TYPE
    SYNTAX           CfprVnicEtherEntry
    MAX-ACCESS       not-accessible
    STATUS           current
    DESCRIPTION
        "Entry for the cfprVnicEtherTable table."
    INDEX { cfprVnicEtherInstanceId }
    ::= { cfprVnicEtherTable 1 }

CfprVnicEtherEntry ::= SEQUENCE {
    cfprVnicEtherInstanceId                                          CfprManagedObjectId,
    cfprVnicEtherDn                                                  CfprManagedObjectDn,
    cfprVnicEtherRn                                                  SnmpAdminString,
    cfprVnicEtherAdaptorProfileName                                  SnmpAdminString,
    cfprVnicEtherAddr                                                MacAddress,
    cfprVnicEtherAdminHostPort                                       CfprFabricHostPortId,
    cfprVnicEtherAdminVcon                                           SnmpAdminString,
    cfprVnicEtherAppInstId                                           SnmpAdminString,
    cfprVnicEtherAppRole                                             CfprVnicAppRole,
    cfprVnicEtherBootDev                                             CfprVnicVnicBootDev,
    cfprVnicEtherConfigQualifier                                     CfprVnicConfigIssues,
    cfprVnicEtherConfigState                                         CfprLsConfigState,
    cfprVnicEtherDynamicId                                           Gauge32,
    cfprVnicEtherEquipmentDn                                         SnmpAdminString,
    cfprVnicEtherFltAggr                                             Unsigned64,
    cfprVnicEtherIdentPoolName                                       SnmpAdminString,
    cfprVnicEtherInstType                                            CfprVnicInstantiation,
    cfprVnicEtherIsAllocated                                         TruthValue,
    cfprVnicEtherMtu                                                 Gauge32,
    cfprVnicEtherName                                                SnmpAdminString,
    cfprVnicEtherNwCtrlPolicyName                                    SnmpAdminString,
    cfprVnicEtherNwTemplName                                         SnmpAdminString,
    cfprVnicEtherOperAdaptorProfileName                              SnmpAdminString,
    cfprVnicEtherOperHostPort                                        CfprVnicVnicOperHostPort,
    cfprVnicEtherOperIdentPoolName                                   SnmpAdminString,
    cfprVnicEtherOperNwCtrlPolicyName                                SnmpAdminString,
    cfprVnicEtherOperNwTemplName                                     SnmpAdminString,
    cfprVnicEtherOperOrder                                           Gauge32,
    cfprVnicEtherOperPinToGroupName                                  SnmpAdminString,
    cfprVnicEtherOperQosPolicyName                                   SnmpAdminString,
    cfprVnicEtherOperSpeed                                           Gauge32,
    cfprVnicEtherOperStatsPolicyName                                 SnmpAdminString,
    cfprVnicEtherOperVcon                                            SnmpAdminString,
    cfprVnicEtherOrder                                               Gauge32,
    cfprVnicEtherOwner                                               CfprVnicConnectionOwner,
    cfprVnicEtherPfDn                                                SnmpAdminString,
    cfprVnicEtherPinToGroupName                                      SnmpAdminString,
    cfprVnicEtherQosPolicyName                                       SnmpAdminString,
    cfprVnicEtherStatsPolicyName                                     SnmpAdminString,
    cfprVnicEtherSwitchId                                            CfprVnicEtherBaseSwitchId,
    cfprVnicEtherType                                                CfprVnicEtherType,
    cfprVnicEtherVirtualizationPreference                            CfprVnicVirtualizationPreferenceType,
    cfprVnicEtherPortType                                            CfprFabricSSAPortType
}

cfprVnicEtherInstanceId OBJECT-TYPE
    SYNTAX       CfprManagedObjectId
    MAX-ACCESS   not-accessible
    STATUS       current
    DESCRIPTION
        "Instance identifier of the managed object."
    ::= { cfprVnicEtherEntry 1 }

cfprVnicEtherDn OBJECT-TYPE
    SYNTAX       CfprManagedObjectDn
    MAX-ACCESS   read-only
    STATUS       current
    DESCRIPTION
        "Cisco Firepower vnic:Ether:dn managed object property"
    ::= { cfprVnicEtherEntry 2 }

cfprVnicEtherRn OBJECT-TYPE
    SYNTAX       SnmpAdminString
    MAX-ACCESS   read-only
    STATUS       current
    DESCRIPTION
        "Cisco Firepower vnic:Ether:rn managed object property"
    ::= { cfprVnicEtherEntry 3 }

cfprVnicEtherAdaptorProfileName OBJECT-TYPE
    SYNTAX       SnmpAdminString
    MAX-ACCESS   read-only
    STATUS       current
    DESCRIPTION
        "Cisco Firepower vnic:Ether:adaptorProfileName
        managed object property"
    ::= { cfprVnicEtherEntry 4 }

cfprVnicEtherAddr OBJECT-TYPE
    SYNTAX       MacAddress
    MAX-ACCESS   read-only
    STATUS       current
    DESCRIPTION
        "Cisco Firepower vnic:Ether:addr managed object property"
    ::= { cfprVnicEtherEntry 5 }

cfprVnicEtherAdminHostPort OBJECT-TYPE
    SYNTAX       CfprFabricHostPortId
    MAX-ACCESS   read-only
    STATUS       current
    DESCRIPTION
        "Cisco Firepower vnic:Ether:adminHostPort managed object property"
    ::= { cfprVnicEtherEntry 6 }

cfprVnicEtherAdminVcon OBJECT-TYPE
    SYNTAX       SnmpAdminString
    MAX-ACCESS   read-only
    STATUS       current
    DESCRIPTION
        "Cisco Firepower vnic:Ether:adminVcon managed object property"
    ::= { cfprVnicEtherEntry 7 }

cfprVnicEtherAppInstId OBJECT-TYPE
    SYNTAX       SnmpAdminString
    MAX-ACCESS   read-only
    STATUS       current
    DESCRIPTION
        "Cisco Firepower vnic:Ether:appInstId managed object property"
    ::= { cfprVnicEtherEntry 8 }

cfprVnicEtherAppRole OBJECT-TYPE
    SYNTAX       CfprVnicAppRole
    MAX-ACCESS   read-only
    STATUS       current
    DESCRIPTION
        "Cisco Firepower vnic:Ether:appRole managed object property"
    ::= { cfprVnicEtherEntry 9 }

cfprVnicEtherBootDev OBJECT-TYPE
    SYNTAX       CfprVnicVnicBootDev
    MAX-ACCESS   read-only
    STATUS       current
    DESCRIPTION
        "Cisco Firepower vnic:Ether:bootDev managed object property"
    ::= { cfprVnicEtherEntry 10 }

cfprVnicEtherConfigQualifier OBJECT-TYPE
    SYNTAX       CfprVnicConfigIssues
    MAX-ACCESS   read-only
    STATUS       current
    DESCRIPTION
        "Cisco Firepower vnic:Ether:configQualifier managed
        object property"
    ::= { cfprVnicEtherEntry 11 }

cfprVnicEtherConfigState OBJECT-TYPE
    SYNTAX       CfprLsConfigState
    MAX-ACCESS   read-only
    STATUS       current
    DESCRIPTION
        "Cisco Firepower vnic:Ether:configState managed object property"
    ::= { cfprVnicEtherEntry 12 }

cfprVnicEtherDynamicId OBJECT-TYPE
    SYNTAX       Gauge32
    MAX-ACCESS   read-only
    STATUS       current
    DESCRIPTION
        "Cisco Firepower vnic:Ether:dynamicId managed object property"
    ::= { cfprVnicEtherEntry 13 }

cfprVnicEtherEquipmentDn OBJECT-TYPE
    SYNTAX       SnmpAdminString
    MAX-ACCESS   read-only
    STATUS       current
    DESCRIPTION
        "Cisco Firepower vnic:Ether:equipmentDn managed object property"
    ::= { cfprVnicEtherEntry 14 }

cfprVnicEtherFltAggr OBJECT-TYPE
    SYNTAX       Unsigned64
    MAX-ACCESS   read-only
    STATUS       current
    DESCRIPTION
        "Cisco Firepower vnic:Ether:fltAggr managed object property"
    ::= { cfprVnicEtherEntry 15 }

cfprVnicEtherIdentPoolName OBJECT-TYPE
    SYNTAX       SnmpAdminString
    MAX-ACCESS   read-only
    STATUS       current
    DESCRIPTION
        "Cisco Firepower vnic:Ether:identPoolName managed object property"
    ::= { cfprVnicEtherEntry 16 }

cfprVnicEtherInstType OBJECT-TYPE
    SYNTAX       CfprVnicInstantiation
    MAX-ACCESS   read-only
    STATUS       current
    DESCRIPTION
        "Cisco Firepower vnic:Ether:instType managed object property"
    ::= { cfprVnicEtherEntry 17 }

cfprVnicEtherIsAllocated OBJECT-TYPE
    SYNTAX       TruthValue
    MAX-ACCESS   read-only
    STATUS       current
    DESCRIPTION
        "Cisco Firepower vnic:Ether:isAllocated managed object property"
    ::= { cfprVnicEtherEntry 18 }

cfprVnicEtherMtu OBJECT-TYPE
    SYNTAX       Gauge32
    MAX-ACCESS   read-only
    STATUS       current
    DESCRIPTION
        "Cisco Firepower vnic:Ether:mtu managed object property"
    ::= { cfprVnicEtherEntry 19 }

cfprVnicEtherName OBJECT-TYPE
    SYNTAX       SnmpAdminString
    MAX-ACCESS   read-only
    STATUS       current
    DESCRIPTION
        "Cisco Firepower vnic:Ether:name managed object property"
    ::= { cfprVnicEtherEntry 20 }

cfprVnicEtherNwCtrlPolicyName OBJECT-TYPE
    SYNTAX       SnmpAdminString
    MAX-ACCESS   read-only
    STATUS       current
    DESCRIPTION
        "Cisco Firepower vnic:Ether:nwCtrlPolicyName managed
        object property"
    ::= { cfprVnicEtherEntry 21 }

cfprVnicEtherNwTemplName OBJECT-TYPE
    SYNTAX       SnmpAdminString
    MAX-ACCESS   read-only
    STATUS       current
    DESCRIPTION
        "Cisco Firepower vnic:Ether:nwTemplName managed object property"
    ::= { cfprVnicEtherEntry 22 }

cfprVnicEtherOperAdaptorProfileName OBJECT-TYPE
    SYNTAX       SnmpAdminString
    MAX-ACCESS   read-only
    STATUS       current
    DESCRIPTION
        "Cisco Firepower vnic:Ether:operAdaptorProfileName
        managed object property"
    ::= { cfprVnicEtherEntry 23 }

cfprVnicEtherOperHostPort OBJECT-TYPE
    SYNTAX       CfprVnicVnicOperHostPort
    MAX-ACCESS   read-only
    STATUS       current
    DESCRIPTION
        "Cisco Firepower vnic:Ether:operHostPort managed object property"
    ::= { cfprVnicEtherEntry 24 }

cfprVnicEtherOperIdentPoolName OBJECT-TYPE
    SYNTAX       SnmpAdminString
    MAX-ACCESS   read-only
    STATUS       current
    DESCRIPTION
        "Cisco Firepower vnic:Ether:operIdentPoolName managed
        object property"
    ::= { cfprVnicEtherEntry 25 }

cfprVnicEtherOperNwCtrlPolicyName OBJECT-TYPE
    SYNTAX       SnmpAdminString
    MAX-ACCESS   read-only
    STATUS       current
    DESCRIPTION
        "Cisco Firepower vnic:Ether:operNwCtrlPolicyName
        managed object property"
    ::= { cfprVnicEtherEntry 26 }

cfprVnicEtherOperNwTemplName OBJECT-TYPE
    SYNTAX       SnmpAdminString
    MAX-ACCESS   read-only
    STATUS       current
    DESCRIPTION
        "Cisco Firepower vnic:Ether:operNwTemplName managed
        object property"
    ::= { cfprVnicEtherEntry 27 }

cfprVnicEtherOperOrder OBJECT-TYPE
    SYNTAX       Gauge32
    MAX-ACCESS   read-only
    STATUS       current
    DESCRIPTION
        "Cisco Firepower vnic:Ether:operOrder managed object property"
    ::= { cfprVnicEtherEntry 28 }

cfprVnicEtherOperPinToGroupName OBJECT-TYPE
    SYNTAX       SnmpAdminString
    MAX-ACCESS   read-only
    STATUS       current
    DESCRIPTION
        "Cisco Firepower vnic:Ether:operPinToGroupName
        managed object property"
    ::= { cfprVnicEtherEntry 29 }

cfprVnicEtherOperQosPolicyName OBJECT-TYPE
    SYNTAX       SnmpAdminString
    MAX-ACCESS   read-only
    STATUS       current
    DESCRIPTION
        "Cisco Firepower vnic:Ether:operQosPolicyName managed
        object property"
    ::= { cfprVnicEtherEntry 30 }

cfprVnicEtherOperSpeed OBJECT-TYPE
    SYNTAX       Gauge32
    MAX-ACCESS   read-only
    STATUS       current
    DESCRIPTION
        "Cisco Firepower vnic:Ether:operSpeed managed object property"
    ::= { cfprVnicEtherEntry 31 }

cfprVnicEtherOperStatsPolicyName OBJECT-TYPE
    SYNTAX       SnmpAdminString
    MAX-ACCESS   read-only
    STATUS       current
    DESCRIPTION
        "Cisco Firepower vnic:Ether:operStatsPolicyName
        managed object property"
    ::= { cfprVnicEtherEntry 32 }

cfprVnicEtherOperVcon OBJECT-TYPE
    SYNTAX       SnmpAdminString
    MAX-ACCESS   read-only
    STATUS       current
    DESCRIPTION
        "Cisco Firepower vnic:Ether:operVcon managed object property"
    ::= { cfprVnicEtherEntry 33 }

cfprVnicEtherOrder OBJECT-TYPE
    SYNTAX       Gauge32
    MAX-ACCESS   read-only
    STATUS       current
    DESCRIPTION
        "Cisco Firepower vnic:Ether:order managed object property"
    ::= { cfprVnicEtherEntry 34 }

cfprVnicEtherOwner OBJECT-TYPE
    SYNTAX       CfprVnicConnectionOwner
    MAX-ACCESS   read-only
    STATUS       current
    DESCRIPTION
        "Cisco Firepower vnic:Ether:owner managed object property"
    ::= { cfprVnicEtherEntry 35 }

cfprVnicEtherPfDn OBJECT-TYPE
    SYNTAX       SnmpAdminString
    MAX-ACCESS   read-only
    STATUS       current
    DESCRIPTION
        "Cisco Firepower vnic:Ether:pfDn managed object property"
    ::= { cfprVnicEtherEntry 36 }

cfprVnicEtherPinToGroupName OBJECT-TYPE
    SYNTAX       SnmpAdminString
    MAX-ACCESS   read-only
    STATUS       current
    DESCRIPTION
        "Cisco Firepower vnic:Ether:pinToGroupName managed
        object property"
    ::= { cfprVnicEtherEntry 37 }

cfprVnicEtherQosPolicyName OBJECT-TYPE
    SYNTAX       SnmpAdminString
    MAX-ACCESS   read-only
    STATUS       current
    DESCRIPTION
        "Cisco Firepower vnic:Ether:qosPolicyName managed object property"
    ::= { cfprVnicEtherEntry 38 }

cfprVnicEtherStatsPolicyName OBJECT-TYPE
    SYNTAX       SnmpAdminString
    MAX-ACCESS   read-only
    STATUS       current
    DESCRIPTION
        "Cisco Firepower vnic:Ether:statsPolicyName managed
        object property"
    ::= { cfprVnicEtherEntry 39 }

cfprVnicEtherSwitchId OBJECT-TYPE
    SYNTAX       CfprVnicEtherBaseSwitchId
    MAX-ACCESS   read-only
    STATUS       current
    DESCRIPTION
        "Cisco Firepower vnic:Ether:switchId managed object property"
    ::= { cfprVnicEtherEntry 40 }

cfprVnicEtherType OBJECT-TYPE
    SYNTAX       CfprVnicEtherType
    MAX-ACCESS   read-only
    STATUS       current
    DESCRIPTION
        "Cisco Firepower vnic:Ether:type managed object property"
    ::= { cfprVnicEtherEntry 41 }

cfprVnicEtherVirtualizationPreference OBJECT-TYPE
    SYNTAX       CfprVnicVirtualizationPreferenceType
    MAX-ACCESS   read-only
    STATUS       current
    DESCRIPTION
        "Cisco Firepower vnic:Ether:virtualizationPreference
        managed object property"
    ::= { cfprVnicEtherEntry 42 }

cfprVnicEtherPortType OBJECT-TYPE
    SYNTAX       CfprFabricSSAPortType
    MAX-ACCESS   read-only
    STATUS       current
    DESCRIPTION
        "Cisco Firepower vnic:Ether:portType managed object property"
    ::= { cfprVnicEtherEntry 43 }

cfprVnicEtherIfTable OBJECT-TYPE
    SYNTAX           SEQUENCE OF CfprVnicEtherIfEntry
    MAX-ACCESS       not-accessible
    STATUS           current
    DESCRIPTION
        "Cisco Firepower vnic:EtherIf managed object table"
    ::= { cfprVnicObjects 13 }

cfprVnicEtherIfEntry OBJECT-TYPE
    SYNTAX           CfprVnicEtherIfEntry
    MAX-ACCESS       not-accessible
    STATUS           current
    DESCRIPTION
        "Entry for the cfprVnicEtherIfTable table."
    INDEX { cfprVnicEtherIfInstanceId }
    ::= { cfprVnicEtherIfTable 1 }

CfprVnicEtherIfEntry ::= SEQUENCE {
    cfprVnicEtherIfInstanceId                                        CfprManagedObjectId,
    cfprVnicEtherIfDn                                                CfprManagedObjectDn,
    cfprVnicEtherIfRn                                                SnmpAdminString,
    cfprVnicEtherIfAddr                                              MacAddress,
    cfprVnicEtherIfConfigQualifier                                   CfprVnicConfigIssues,
    cfprVnicEtherIfDefaultNet                                        TruthValue,
    cfprVnicEtherIfFltAggr                                           Unsigned64,
    cfprVnicEtherIfName                                              SnmpAdminString,
    cfprVnicEtherIfOperState                                         CfprVnicIfOperState,
    cfprVnicEtherIfOperVnetDn                                        SnmpAdminString,
    cfprVnicEtherIfOperVnetName                                      SnmpAdminString,
    cfprVnicEtherIfOwner                                             CfprVnicConnectionOwner,
    cfprVnicEtherIfPubNwId                                           Gauge32,
    cfprVnicEtherIfSharing                                           CfprFabricVlanSharingType,
    cfprVnicEtherIfSwitchId                                          CfprVnicL2IfSwitchId,
    cfprVnicEtherIfType                                              CfprVnicAEtherIfType,
    cfprVnicEtherIfVnet                                              Gauge32
}

cfprVnicEtherIfInstanceId OBJECT-TYPE
    SYNTAX       CfprManagedObjectId
    MAX-ACCESS   not-accessible
    STATUS       current
    DESCRIPTION
        "Instance identifier of the managed object."
    ::= { cfprVnicEtherIfEntry 1 }

cfprVnicEtherIfDn OBJECT-TYPE
    SYNTAX       CfprManagedObjectDn
    MAX-ACCESS   read-only
    STATUS       current
    DESCRIPTION
        "Cisco Firepower vnic:EtherIf:dn managed object property"
    ::= { cfprVnicEtherIfEntry 2 }

cfprVnicEtherIfRn OBJECT-TYPE
    SYNTAX       SnmpAdminString
    MAX-ACCESS   read-only
    STATUS       current
    DESCRIPTION
        "Cisco Firepower vnic:EtherIf:rn managed object property"
    ::= { cfprVnicEtherIfEntry 3 }

cfprVnicEtherIfAddr OBJECT-TYPE
    SYNTAX       MacAddress
    MAX-ACCESS   read-only
    STATUS       current
    DESCRIPTION
        "Cisco Firepower vnic:EtherIf:addr managed object property"
    ::= { cfprVnicEtherIfEntry 4 }

cfprVnicEtherIfConfigQualifier OBJECT-TYPE
    SYNTAX       CfprVnicConfigIssues
    MAX-ACCESS   read-only
    STATUS       current
    DESCRIPTION
        "Cisco Firepower vnic:EtherIf:configQualifier managed
        object property"
    ::= { cfprVnicEtherIfEntry 5 }

cfprVnicEtherIfDefaultNet OBJECT-TYPE
    SYNTAX       TruthValue
    MAX-ACCESS   read-only
    STATUS       current
    DESCRIPTION
        "Cisco Firepower vnic:EtherIf:defaultNet managed object property"
    ::= { cfprVnicEtherIfEntry 6 }

cfprVnicEtherIfFltAggr OBJECT-TYPE
    SYNTAX       Unsigned64
    MAX-ACCESS   read-only
    STATUS       current
    DESCRIPTION
        "Cisco Firepower vnic:EtherIf:fltAggr managed object property"
    ::= { cfprVnicEtherIfEntry 7 }

cfprVnicEtherIfName OBJECT-TYPE
    SYNTAX       SnmpAdminString
    MAX-ACCESS   read-only
    STATUS       current
    DESCRIPTION
        "Cisco Firepower vnic:EtherIf:name managed object property"
    ::= { cfprVnicEtherIfEntry 8 }

cfprVnicEtherIfOperState OBJECT-TYPE
    SYNTAX       CfprVnicIfOperState
    MAX-ACCESS   read-only
    STATUS       current
    DESCRIPTION
        "Cisco Firepower vnic:EtherIf:operState managed object property"
    ::= { cfprVnicEtherIfEntry 9 }

cfprVnicEtherIfOperVnetDn OBJECT-TYPE
    SYNTAX       SnmpAdminString
    MAX-ACCESS   read-only
    STATUS       current
    DESCRIPTION
        "Cisco Firepower vnic:EtherIf:operVnetDn managed object property"
    ::= { cfprVnicEtherIfEntry 10 }

cfprVnicEtherIfOperVnetName OBJECT-TYPE
    SYNTAX       SnmpAdminString
    MAX-ACCESS   read-only
    STATUS       current
    DESCRIPTION
        "Cisco Firepower vnic:EtherIf:operVnetName managed
        object property"
    ::= { cfprVnicEtherIfEntry 11 }

cfprVnicEtherIfOwner OBJECT-TYPE
    SYNTAX       CfprVnicConnectionOwner
    MAX-ACCESS   read-only
    STATUS       current
    DESCRIPTION
        "Cisco Firepower vnic:EtherIf:owner managed object property"
    ::= { cfprVnicEtherIfEntry 12 }

cfprVnicEtherIfPubNwId OBJECT-TYPE
    SYNTAX       Gauge32
    MAX-ACCESS   read-only
    STATUS       current
    DESCRIPTION
        "Cisco Firepower vnic:EtherIf:pubNwId managed object property"
    ::= { cfprVnicEtherIfEntry 13 }

cfprVnicEtherIfSharing OBJECT-TYPE
    SYNTAX       CfprFabricVlanSharingType
    MAX-ACCESS   read-only
    STATUS       current
    DESCRIPTION
        "Cisco Firepower vnic:EtherIf:sharing managed object property"
    ::= { cfprVnicEtherIfEntry 14 }

cfprVnicEtherIfSwitchId OBJECT-TYPE
    SYNTAX       CfprVnicL2IfSwitchId
    MAX-ACCESS   read-only
    STATUS       current
    DESCRIPTION
        "Cisco Firepower vnic:EtherIf:switchId managed object property"
    ::= { cfprVnicEtherIfEntry 15 }

cfprVnicEtherIfType OBJECT-TYPE
    SYNTAX       CfprVnicAEtherIfType
    MAX-ACCESS   read-only
    STATUS       current
    DESCRIPTION
        "Cisco Firepower vnic:EtherIf:type managed object property"
    ::= { cfprVnicEtherIfEntry 16 }

cfprVnicEtherIfVnet OBJECT-TYPE
    SYNTAX       Gauge32
    MAX-ACCESS   read-only
    STATUS       current
    DESCRIPTION
        "Cisco Firepower vnic:EtherIf:vnet managed object property"
    ::= { cfprVnicEtherIfEntry 17 }

cfprVnicFcTable OBJECT-TYPE
    SYNTAX           SEQUENCE OF CfprVnicFcEntry
    MAX-ACCESS       not-accessible
    STATUS           current
    DESCRIPTION
        "Cisco Firepower vnic:Fc managed object table"
    ::= { cfprVnicObjects 14 }

cfprVnicFcEntry OBJECT-TYPE
    SYNTAX           CfprVnicFcEntry
    MAX-ACCESS       not-accessible
    STATUS           current
    DESCRIPTION
        "Entry for the cfprVnicFcTable table."
    INDEX { cfprVnicFcInstanceId }
    ::= { cfprVnicFcTable 1 }

CfprVnicFcEntry ::= SEQUENCE {
    cfprVnicFcInstanceId                                             CfprManagedObjectId,
    cfprVnicFcDn                                                     CfprManagedObjectDn,
    cfprVnicFcRn                                                     SnmpAdminString,
    cfprVnicFcAdaptorProfileName                                     SnmpAdminString,
    cfprVnicFcAddr                                                   Unsigned64,
    cfprVnicFcAdminHostPort                                          CfprFabricHostPortId,
    cfprVnicFcAdminVcon                                              SnmpAdminString,
    cfprVnicFcAppRole                                                CfprVnicAppRole,
    cfprVnicFcBootDev                                                CfprVnicVnicBootDev,
    cfprVnicFcConfigQualifier                                        CfprVnicConfigIssues,
    cfprVnicFcConfigState                                            CfprLsConfigState,
    cfprVnicFcEquipmentDn                                            SnmpAdminString,
    cfprVnicFcFltAggr                                                Unsigned64,
    cfprVnicFcIdentPoolName                                          SnmpAdminString,
    cfprVnicFcInstType                                               CfprVnicInstantiation,
    cfprVnicFcMaxDataFieldSize                                       Gauge32,
    cfprVnicFcName                                                   SnmpAdminString,
    cfprVnicFcNodeAddr                                               Unsigned64,
    cfprVnicFcNwTemplName                                            SnmpAdminString,
    cfprVnicFcOperAdaptorProfileName                                 SnmpAdminString,
    cfprVnicFcOperHostPort                                           CfprVnicVnicOperHostPort,
    cfprVnicFcOperIdentPoolName                                      SnmpAdminString,
    cfprVnicFcOperNwTemplName                                        SnmpAdminString,
    cfprVnicFcOperOrder                                              Gauge32,
    cfprVnicFcOperPinToGroupName                                     SnmpAdminString,
    cfprVnicFcOperQosPolicyName                                      SnmpAdminString,
    cfprVnicFcOperSpeed                                              Gauge32,
    cfprVnicFcOperStatsPolicyName                                    SnmpAdminString,
    cfprVnicFcOperVcon                                               SnmpAdminString,
    cfprVnicFcOrder                                                  Gauge32,
    cfprVnicFcOwner                                                  CfprVnicConnectionOwner,
    cfprVnicFcPersBind                                               CfprVnicFcBasePersBind,
    cfprVnicFcPersBindClear                                          TruthValue,
    cfprVnicFcPinToGroupName                                         SnmpAdminString,
    cfprVnicFcQosPolicyName                                          SnmpAdminString,
    cfprVnicFcStatsPolicyName                                        SnmpAdminString,
    cfprVnicFcSwitchId                                               CfprNetworkSwitchId,
    cfprVnicFcType                                                   CfprVnicFcBaseType
}

cfprVnicFcInstanceId OBJECT-TYPE
    SYNTAX       CfprManagedObjectId
    MAX-ACCESS   not-accessible
    STATUS       current
    DESCRIPTION
        "Instance identifier of the managed object."
    ::= { cfprVnicFcEntry 1 }

cfprVnicFcDn OBJECT-TYPE
    SYNTAX       CfprManagedObjectDn
    MAX-ACCESS   read-only
    STATUS       current
    DESCRIPTION
        "Cisco Firepower vnic:Fc:dn managed object property"
    ::= { cfprVnicFcEntry 2 }

cfprVnicFcRn OBJECT-TYPE
    SYNTAX       SnmpAdminString
    MAX-ACCESS   read-only
    STATUS       current
    DESCRIPTION
        "Cisco Firepower vnic:Fc:rn managed object property"
    ::= { cfprVnicFcEntry 3 }

cfprVnicFcAdaptorProfileName OBJECT-TYPE
    SYNTAX       SnmpAdminString
    MAX-ACCESS   read-only
    STATUS       current
    DESCRIPTION
        "Cisco Firepower vnic:Fc:adaptorProfileName managed
        object property"
    ::= { cfprVnicFcEntry 4 }

cfprVnicFcAddr OBJECT-TYPE
    SYNTAX       Unsigned64
    MAX-ACCESS   read-only
    STATUS       current
    DESCRIPTION
        "Cisco Firepower vnic:Fc:addr managed object property"
    ::= { cfprVnicFcEntry 5 }

cfprVnicFcAdminHostPort OBJECT-TYPE
    SYNTAX       CfprFabricHostPortId
    MAX-ACCESS   read-only
    STATUS       current
    DESCRIPTION
        "Cisco Firepower vnic:Fc:adminHostPort managed object property"
    ::= { cfprVnicFcEntry 6 }

cfprVnicFcAdminVcon OBJECT-TYPE
    SYNTAX       SnmpAdminString
    MAX-ACCESS   read-only
    STATUS       current
    DESCRIPTION
        "Cisco Firepower vnic:Fc:adminVcon managed object property"
    ::= { cfprVnicFcEntry 7 }

cfprVnicFcAppRole OBJECT-TYPE
    SYNTAX       CfprVnicAppRole
    MAX-ACCESS   read-only
    STATUS       current
    DESCRIPTION
        "Cisco Firepower vnic:Fc:appRole managed object property"
    ::= { cfprVnicFcEntry 8 }

cfprVnicFcBootDev OBJECT-TYPE
    SYNTAX       CfprVnicVnicBootDev
    MAX-ACCESS   read-only
    STATUS       current
    DESCRIPTION
        "Cisco Firepower vnic:Fc:bootDev managed object property"
    ::= { cfprVnicFcEntry 9 }

cfprVnicFcConfigQualifier OBJECT-TYPE
    SYNTAX       CfprVnicConfigIssues
    MAX-ACCESS   read-only
    STATUS       current
    DESCRIPTION
        "Cisco Firepower vnic:Fc:configQualifier managed object property"
    ::= { cfprVnicFcEntry 10 }

cfprVnicFcConfigState OBJECT-TYPE
    SYNTAX       CfprLsConfigState
    MAX-ACCESS   read-only
    STATUS       current
    DESCRIPTION
        "Cisco Firepower vnic:Fc:configState managed object property"
    ::= { cfprVnicFcEntry 11 }

cfprVnicFcEquipmentDn OBJECT-TYPE
    SYNTAX       SnmpAdminString
    MAX-ACCESS   read-only
    STATUS       current
    DESCRIPTION
        "Cisco Firepower vnic:Fc:equipmentDn managed object property"
    ::= { cfprVnicFcEntry 12 }

cfprVnicFcFltAggr OBJECT-TYPE
    SYNTAX       Unsigned64
    MAX-ACCESS   read-only
    STATUS       current
    DESCRIPTION
        "Cisco Firepower vnic:Fc:fltAggr managed object property"
    ::= { cfprVnicFcEntry 13 }

cfprVnicFcIdentPoolName OBJECT-TYPE
    SYNTAX       SnmpAdminString
    MAX-ACCESS   read-only
    STATUS       current
    DESCRIPTION
        "Cisco Firepower vnic:Fc:identPoolName managed object property"
    ::= { cfprVnicFcEntry 14 }

cfprVnicFcInstType OBJECT-TYPE
    SYNTAX       CfprVnicInstantiation
    MAX-ACCESS   read-only
    STATUS       current
    DESCRIPTION
        "Cisco Firepower vnic:Fc:instType managed object property"
    ::= { cfprVnicFcEntry 15 }

cfprVnicFcMaxDataFieldSize OBJECT-TYPE
    SYNTAX       Gauge32
    MAX-ACCESS   read-only
    STATUS       current
    DESCRIPTION
        "Cisco Firepower vnic:Fc:maxDataFieldSize managed object property"
    ::= { cfprVnicFcEntry 16 }

cfprVnicFcName OBJECT-TYPE
    SYNTAX       SnmpAdminString
    MAX-ACCESS   read-only
    STATUS       current
    DESCRIPTION
        "Cisco Firepower vnic:Fc:name managed object property"
    ::= { cfprVnicFcEntry 17 }

cfprVnicFcNodeAddr OBJECT-TYPE
    SYNTAX       Unsigned64
    MAX-ACCESS   read-only
    STATUS       current
    DESCRIPTION
        "Cisco Firepower vnic:Fc:nodeAddr managed object property"
    ::= { cfprVnicFcEntry 18 }

cfprVnicFcNwTemplName OBJECT-TYPE
    SYNTAX       SnmpAdminString
    MAX-ACCESS   read-only
    STATUS       current
    DESCRIPTION
        "Cisco Firepower vnic:Fc:nwTemplName managed object property"
    ::= { cfprVnicFcEntry 19 }

cfprVnicFcOperAdaptorProfileName OBJECT-TYPE
    SYNTAX       SnmpAdminString
    MAX-ACCESS   read-only
    STATUS       current
    DESCRIPTION
        "Cisco Firepower vnic:Fc:operAdaptorProfileName
        managed object property"
    ::= { cfprVnicFcEntry 20 }

cfprVnicFcOperHostPort OBJECT-TYPE
    SYNTAX       CfprVnicVnicOperHostPort
    MAX-ACCESS   read-only
    STATUS       current
    DESCRIPTION
        "Cisco Firepower vnic:Fc:operHostPort managed object property"
    ::= { cfprVnicFcEntry 21 }

cfprVnicFcOperIdentPoolName OBJECT-TYPE
    SYNTAX       SnmpAdminString
    MAX-ACCESS   read-only
    STATUS       current
    DESCRIPTION
        "Cisco Firepower vnic:Fc:operIdentPoolName managed
        object property"
    ::= { cfprVnicFcEntry 22 }

cfprVnicFcOperNwTemplName OBJECT-TYPE
    SYNTAX       SnmpAdminString
    MAX-ACCESS   read-only
    STATUS       current
    DESCRIPTION
        "Cisco Firepower vnic:Fc:operNwTemplName managed object property"
    ::= { cfprVnicFcEntry 23 }

cfprVnicFcOperOrder OBJECT-TYPE
    SYNTAX       Gauge32
    MAX-ACCESS   read-only
    STATUS       current
    DESCRIPTION
        "Cisco Firepower vnic:Fc:operOrder managed object property"
    ::= { cfprVnicFcEntry 24 }

cfprVnicFcOperPinToGroupName OBJECT-TYPE
    SYNTAX       SnmpAdminString
    MAX-ACCESS   read-only
    STATUS       current
    DESCRIPTION
        "Cisco Firepower vnic:Fc:operPinToGroupName managed
        object property"
    ::= { cfprVnicFcEntry 25 }

cfprVnicFcOperQosPolicyName OBJECT-TYPE
    SYNTAX       SnmpAdminString
    MAX-ACCESS   read-only
    STATUS       current
    DESCRIPTION
        "Cisco Firepower vnic:Fc:operQosPolicyName managed
        object property"
    ::= { cfprVnicFcEntry 26 }

cfprVnicFcOperSpeed OBJECT-TYPE
    SYNTAX       Gauge32
    MAX-ACCESS   read-only
    STATUS       current
    DESCRIPTION
        "Cisco Firepower vnic:Fc:operSpeed managed object property"
    ::= { cfprVnicFcEntry 27 }

cfprVnicFcOperStatsPolicyName OBJECT-TYPE
    SYNTAX       SnmpAdminString
    MAX-ACCESS   read-only
    STATUS       current
    DESCRIPTION
        "Cisco Firepower vnic:Fc:operStatsPolicyName managed
        object property"
    ::= { cfprVnicFcEntry 28 }

cfprVnicFcOperVcon OBJECT-TYPE
    SYNTAX       SnmpAdminString
    MAX-ACCESS   read-only
    STATUS       current
    DESCRIPTION
        "Cisco Firepower vnic:Fc:operVcon managed object property"
    ::= { cfprVnicFcEntry 29 }

cfprVnicFcOrder OBJECT-TYPE
    SYNTAX       Gauge32
    MAX-ACCESS   read-only
    STATUS       current
    DESCRIPTION
        "Cisco Firepower vnic:Fc:order managed object property"
    ::= { cfprVnicFcEntry 30 }

cfprVnicFcOwner OBJECT-TYPE
    SYNTAX       CfprVnicConnectionOwner
    MAX-ACCESS   read-only
    STATUS       current
    DESCRIPTION
        "Cisco Firepower vnic:Fc:owner managed object property"
    ::= { cfprVnicFcEntry 31 }

cfprVnicFcPersBind OBJECT-TYPE
    SYNTAX       CfprVnicFcBasePersBind
    MAX-ACCESS   read-only
    STATUS       current
    DESCRIPTION
        "Cisco Firepower vnic:Fc:persBind managed object property"
    ::= { cfprVnicFcEntry 32 }

cfprVnicFcPersBindClear OBJECT-TYPE
    SYNTAX       TruthValue
    MAX-ACCESS   read-only
    STATUS       current
    DESCRIPTION
        "Cisco Firepower vnic:Fc:persBindClear managed object property"
    ::= { cfprVnicFcEntry 33 }

cfprVnicFcPinToGroupName OBJECT-TYPE
    SYNTAX       SnmpAdminString
    MAX-ACCESS   read-only
    STATUS       current
    DESCRIPTION
        "Cisco Firepower vnic:Fc:pinToGroupName managed object property"
    ::= { cfprVnicFcEntry 34 }

cfprVnicFcQosPolicyName OBJECT-TYPE
    SYNTAX       SnmpAdminString
    MAX-ACCESS   read-only
    STATUS       current
    DESCRIPTION
        "Cisco Firepower vnic:Fc:qosPolicyName managed object property"
    ::= { cfprVnicFcEntry 35 }

cfprVnicFcStatsPolicyName OBJECT-TYPE
    SYNTAX       SnmpAdminString
    MAX-ACCESS   read-only
    STATUS       current
    DESCRIPTION
        "Cisco Firepower vnic:Fc:statsPolicyName managed object property"
    ::= { cfprVnicFcEntry 36 }

cfprVnicFcSwitchId OBJECT-TYPE
    SYNTAX       CfprNetworkSwitchId
    MAX-ACCESS   read-only
    STATUS       current
    DESCRIPTION
        "Cisco Firepower vnic:Fc:switchId managed object property"
    ::= { cfprVnicFcEntry 37 }

cfprVnicFcType OBJECT-TYPE
    SYNTAX       CfprVnicFcBaseType
    MAX-ACCESS   read-only
    STATUS       current
    DESCRIPTION
        "Cisco Firepower vnic:Fc:type managed object property"
    ::= { cfprVnicFcEntry 38 }

cfprVnicFcGroupDefTable OBJECT-TYPE
    SYNTAX           SEQUENCE OF CfprVnicFcGroupDefEntry
    MAX-ACCESS       not-accessible
    STATUS           current
    DESCRIPTION
        "Cisco Firepower vnic:FcGroupDef managed object table"
    ::= { cfprVnicObjects 15 }

cfprVnicFcGroupDefEntry OBJECT-TYPE
    SYNTAX           CfprVnicFcGroupDefEntry
    MAX-ACCESS       not-accessible
    STATUS           current
    DESCRIPTION
        "Entry for the cfprVnicFcGroupDefTable table."
    INDEX { cfprVnicFcGroupDefInstanceId }
    ::= { cfprVnicFcGroupDefTable 1 }

CfprVnicFcGroupDefEntry ::= SEQUENCE {
    cfprVnicFcGroupDefInstanceId                                     CfprManagedObjectId,
    cfprVnicFcGroupDefDn                                             CfprManagedObjectDn,
    cfprVnicFcGroupDefRn                                             SnmpAdminString,
    cfprVnicFcGroupDefAdaptorProfileName                             SnmpAdminString,
    cfprVnicFcGroupDefDescr                                          SnmpAdminString,
    cfprVnicFcGroupDefIdentPoolName                                  SnmpAdminString,
    cfprVnicFcGroupDefIntId                                          SnmpAdminString,
    cfprVnicFcGroupDefMaxDataFieldSize                               Gauge32,
    cfprVnicFcGroupDefName                                           SnmpAdminString,
    cfprVnicFcGroupDefNwTemplName                                    SnmpAdminString,
    cfprVnicFcGroupDefOperStatsPolicyName                            SnmpAdminString,
    cfprVnicFcGroupDefOperStorageConnPolicyName                      SnmpAdminString,
    cfprVnicFcGroupDefPolicyLevel                                    Gauge32,
    cfprVnicFcGroupDefPolicyOwner                                    CfprPolicyPolicyOwner,
    cfprVnicFcGroupDefQosPolicyName                                  SnmpAdminString,
    cfprVnicFcGroupDefStatsPolicyName                                SnmpAdminString,
    cfprVnicFcGroupDefStorageConnPolicyName                          SnmpAdminString
}

cfprVnicFcGroupDefInstanceId OBJECT-TYPE
    SYNTAX       CfprManagedObjectId
    MAX-ACCESS   not-accessible
    STATUS       current
    DESCRIPTION
        "Instance identifier of the managed object."
    ::= { cfprVnicFcGroupDefEntry 1 }

cfprVnicFcGroupDefDn OBJECT-TYPE
    SYNTAX       CfprManagedObjectDn
    MAX-ACCESS   read-only
    STATUS       current
    DESCRIPTION
        "Cisco Firepower vnic:FcGroupDef:dn managed object property"
    ::= { cfprVnicFcGroupDefEntry 2 }

cfprVnicFcGroupDefRn OBJECT-TYPE
    SYNTAX       SnmpAdminString
    MAX-ACCESS   read-only
    STATUS       current
    DESCRIPTION
        "Cisco Firepower vnic:FcGroupDef:rn managed object property"
    ::= { cfprVnicFcGroupDefEntry 3 }

cfprVnicFcGroupDefAdaptorProfileName OBJECT-TYPE
    SYNTAX       SnmpAdminString
    MAX-ACCESS   read-only
    STATUS       current
    DESCRIPTION
        "Cisco Firepower vnic:FcGroupDef:adaptorProfileName
        managed object property"
    ::= { cfprVnicFcGroupDefEntry 4 }

cfprVnicFcGroupDefDescr OBJECT-TYPE
    SYNTAX       SnmpAdminString
    MAX-ACCESS   read-only
    STATUS       current
    DESCRIPTION
        "Cisco Firepower vnic:FcGroupDef:descr managed object property"
    ::= { cfprVnicFcGroupDefEntry 5 }

cfprVnicFcGroupDefIdentPoolName OBJECT-TYPE
    SYNTAX       SnmpAdminString
    MAX-ACCESS   read-only
    STATUS       current
    DESCRIPTION
        "Cisco Firepower vnic:FcGroupDef:identPoolName
        managed object property"
    ::= { cfprVnicFcGroupDefEntry 6 }

cfprVnicFcGroupDefIntId OBJECT-TYPE
    SYNTAX       SnmpAdminString
    MAX-ACCESS   read-only
    STATUS       current
    DESCRIPTION
        "Cisco Firepower vnic:FcGroupDef:intId managed object property"
    ::= { cfprVnicFcGroupDefEntry 7 }

cfprVnicFcGroupDefMaxDataFieldSize OBJECT-TYPE
    SYNTAX       Gauge32
    MAX-ACCESS   read-only
    STATUS       current
    DESCRIPTION
        "Cisco Firepower vnic:FcGroupDef:maxDataFieldSize
        managed object property"
    ::= { cfprVnicFcGroupDefEntry 8 }

cfprVnicFcGroupDefName OBJECT-TYPE
    SYNTAX       SnmpAdminString
    MAX-ACCESS   read-only
    STATUS       current
    DESCRIPTION
        "Cisco Firepower vnic:FcGroupDef:name managed object property"
    ::= { cfprVnicFcGroupDefEntry 9 }

cfprVnicFcGroupDefNwTemplName OBJECT-TYPE
    SYNTAX       SnmpAdminString
    MAX-ACCESS   read-only
    STATUS       current
    DESCRIPTION
        "Cisco Firepower vnic:FcGroupDef:nwTemplName managed
        object property"
    ::= { cfprVnicFcGroupDefEntry 10 }

cfprVnicFcGroupDefOperStatsPolicyName OBJECT-TYPE
    SYNTAX       SnmpAdminString
    MAX-ACCESS   read-only
    STATUS       current
    DESCRIPTION
        "Cisco Firepower vnic:FcGroupDef:operStatsPolicyName
        managed object property"
    ::= { cfprVnicFcGroupDefEntry 11 }

cfprVnicFcGroupDefOperStorageConnPolicyName OBJECT-TYPE
    SYNTAX       SnmpAdminString
    MAX-ACCESS   read-only
    STATUS       current
    DESCRIPTION
        "Cisco Firepower vnic:FcGroupDef:operStorageConnPolicyName
        managed object property"
    ::= { cfprVnicFcGroupDefEntry 12 }

cfprVnicFcGroupDefPolicyLevel OBJECT-TYPE
    SYNTAX       Gauge32
    MAX-ACCESS   read-only
    STATUS       current
    DESCRIPTION
        "Cisco Firepower vnic:FcGroupDef:policyLevel managed
        object property"
    ::= { cfprVnicFcGroupDefEntry 13 }

cfprVnicFcGroupDefPolicyOwner OBJECT-TYPE
    SYNTAX       CfprPolicyPolicyOwner
    MAX-ACCESS   read-only
    STATUS       current
    DESCRIPTION
        "Cisco Firepower vnic:FcGroupDef:policyOwner managed
        object property"
    ::= { cfprVnicFcGroupDefEntry 14 }

cfprVnicFcGroupDefQosPolicyName OBJECT-TYPE
    SYNTAX       SnmpAdminString
    MAX-ACCESS   read-only
    STATUS       current
    DESCRIPTION
        "Cisco Firepower vnic:FcGroupDef:qosPolicyName
        managed object property"
    ::= { cfprVnicFcGroupDefEntry 15 }

cfprVnicFcGroupDefStatsPolicyName OBJECT-TYPE
    SYNTAX       SnmpAdminString
    MAX-ACCESS   read-only
    STATUS       current
    DESCRIPTION
        "Cisco Firepower vnic:FcGroupDef:statsPolicyName
        managed object property"
    ::= { cfprVnicFcGroupDefEntry 16 }

cfprVnicFcGroupDefStorageConnPolicyName OBJECT-TYPE
    SYNTAX       SnmpAdminString
    MAX-ACCESS   read-only
    STATUS       current
    DESCRIPTION
        "Cisco Firepower vnic:FcGroupDef:storageConnPolicyName
        managed object property"
    ::= { cfprVnicFcGroupDefEntry 17 }

cfprVnicFcGroupTemplTable OBJECT-TYPE
    SYNTAX           SEQUENCE OF CfprVnicFcGroupTemplEntry
    MAX-ACCESS       not-accessible
    STATUS           current
    DESCRIPTION
        "Cisco Firepower vnic:FcGroupTempl managed object table"
    ::= { cfprVnicObjects 16 }

cfprVnicFcGroupTemplEntry OBJECT-TYPE
    SYNTAX           CfprVnicFcGroupTemplEntry
    MAX-ACCESS       not-accessible
    STATUS           current
    DESCRIPTION
        "Entry for the cfprVnicFcGroupTemplTable table."
    INDEX { cfprVnicFcGroupTemplInstanceId }
    ::= { cfprVnicFcGroupTemplTable 1 }

CfprVnicFcGroupTemplEntry ::= SEQUENCE {
    cfprVnicFcGroupTemplInstanceId                                   CfprManagedObjectId,
    cfprVnicFcGroupTemplDn                                           CfprManagedObjectDn,
    cfprVnicFcGroupTemplRn                                           SnmpAdminString,
    cfprVnicFcGroupTemplAdaptorProfileName                           SnmpAdminString,
    cfprVnicFcGroupTemplDescr                                        SnmpAdminString,
    cfprVnicFcGroupTemplIdentPoolName                                SnmpAdminString,
    cfprVnicFcGroupTemplIntId                                        SnmpAdminString,
    cfprVnicFcGroupTemplMaxDataFieldSize                             Gauge32,
    cfprVnicFcGroupTemplName                                         SnmpAdminString,
    cfprVnicFcGroupTemplNwTemplName                                  SnmpAdminString,
    cfprVnicFcGroupTemplOperStatsPolicyName                          SnmpAdminString,
    cfprVnicFcGroupTemplOperStorageConnPolicyName                    SnmpAdminString,
    cfprVnicFcGroupTemplPolicyLevel                                  Gauge32,
    cfprVnicFcGroupTemplPolicyOwner                                  CfprPolicyPolicyOwner,
    cfprVnicFcGroupTemplQosPolicyName                                SnmpAdminString,
    cfprVnicFcGroupTemplStatsPolicyName                              SnmpAdminString,
    cfprVnicFcGroupTemplStorageConnPolicyName                        SnmpAdminString,
    cfprVnicFcGroupTemplTemplType                                    CfprVnicTemplateType
}

cfprVnicFcGroupTemplInstanceId OBJECT-TYPE
    SYNTAX       CfprManagedObjectId
    MAX-ACCESS   not-accessible
    STATUS       current
    DESCRIPTION
        "Instance identifier of the managed object."
    ::= { cfprVnicFcGroupTemplEntry 1 }

cfprVnicFcGroupTemplDn OBJECT-TYPE
    SYNTAX       CfprManagedObjectDn
    MAX-ACCESS   read-only
    STATUS       current
    DESCRIPTION
        "Cisco Firepower vnic:FcGroupTempl:dn managed object property"
    ::= { cfprVnicFcGroupTemplEntry 2 }

cfprVnicFcGroupTemplRn OBJECT-TYPE
    SYNTAX       SnmpAdminString
    MAX-ACCESS   read-only
    STATUS       current
    DESCRIPTION
        "Cisco Firepower vnic:FcGroupTempl:rn managed object property"
    ::= { cfprVnicFcGroupTemplEntry 3 }

cfprVnicFcGroupTemplAdaptorProfileName OBJECT-TYPE
    SYNTAX       SnmpAdminString
    MAX-ACCESS   read-only
    STATUS       current
    DESCRIPTION
        "Cisco Firepower vnic:FcGroupTempl:adaptorProfileName
        managed object property"
    ::= { cfprVnicFcGroupTemplEntry 4 }

cfprVnicFcGroupTemplDescr OBJECT-TYPE
    SYNTAX       SnmpAdminString
    MAX-ACCESS   read-only
    STATUS       current
    DESCRIPTION
        "Cisco Firepower vnic:FcGroupTempl:descr managed object property"
    ::= { cfprVnicFcGroupTemplEntry 5 }

cfprVnicFcGroupTemplIdentPoolName OBJECT-TYPE
    SYNTAX       SnmpAdminString
    MAX-ACCESS   read-only
    STATUS       current
    DESCRIPTION
        "Cisco Firepower vnic:FcGroupTempl:identPoolName
        managed object property"
    ::= { cfprVnicFcGroupTemplEntry 6 }

cfprVnicFcGroupTemplIntId OBJECT-TYPE
    SYNTAX       SnmpAdminString
    MAX-ACCESS   read-only
    STATUS       current
    DESCRIPTION
        "Cisco Firepower vnic:FcGroupTempl:intId managed object property"
    ::= { cfprVnicFcGroupTemplEntry 7 }

cfprVnicFcGroupTemplMaxDataFieldSize OBJECT-TYPE
    SYNTAX       Gauge32
    MAX-ACCESS   read-only
    STATUS       current
    DESCRIPTION
        "Cisco Firepower vnic:FcGroupTempl:maxDataFieldSize
        managed object property"
    ::= { cfprVnicFcGroupTemplEntry 8 }

cfprVnicFcGroupTemplName OBJECT-TYPE
    SYNTAX       SnmpAdminString
    MAX-ACCESS   read-only
    STATUS       current
    DESCRIPTION
        "Cisco Firepower vnic:FcGroupTempl:name managed object property"
    ::= { cfprVnicFcGroupTemplEntry 9 }

cfprVnicFcGroupTemplNwTemplName OBJECT-TYPE
    SYNTAX       SnmpAdminString
    MAX-ACCESS   read-only
    STATUS       current
    DESCRIPTION
        "Cisco Firepower vnic:FcGroupTempl:nwTemplName
        managed object property"
    ::= { cfprVnicFcGroupTemplEntry 10 }

cfprVnicFcGroupTemplOperStatsPolicyName OBJECT-TYPE
    SYNTAX       SnmpAdminString
    MAX-ACCESS   read-only
    STATUS       current
    DESCRIPTION
        "Cisco Firepower vnic:FcGroupTempl:operStatsPolicyName
        managed object property"
    ::= { cfprVnicFcGroupTemplEntry 11 }

cfprVnicFcGroupTemplOperStorageConnPolicyName OBJECT-TYPE
    SYNTAX       SnmpAdminString
    MAX-ACCESS   read-only
    STATUS       current
    DESCRIPTION
        "Cisco Firepower vnic:FcGroupTempl:operStorageConnPolicyName
        managed object property"
    ::= { cfprVnicFcGroupTemplEntry 12 }

cfprVnicFcGroupTemplPolicyLevel OBJECT-TYPE
    SYNTAX       Gauge32
    MAX-ACCESS   read-only
    STATUS       current
    DESCRIPTION
        "Cisco Firepower vnic:FcGroupTempl:policyLevel
        managed object property"
    ::= { cfprVnicFcGroupTemplEntry 13 }

cfprVnicFcGroupTemplPolicyOwner OBJECT-TYPE
    SYNTAX       CfprPolicyPolicyOwner
    MAX-ACCESS   read-only
    STATUS       current
    DESCRIPTION
        "Cisco Firepower vnic:FcGroupTempl:policyOwner
        managed object property"
    ::= { cfprVnicFcGroupTemplEntry 14 }

cfprVnicFcGroupTemplQosPolicyName OBJECT-TYPE
    SYNTAX       SnmpAdminString
    MAX-ACCESS   read-only
    STATUS       current
    DESCRIPTION
        "Cisco Firepower vnic:FcGroupTempl:qosPolicyName
        managed object property"
    ::= { cfprVnicFcGroupTemplEntry 15 }

cfprVnicFcGroupTemplStatsPolicyName OBJECT-TYPE
    SYNTAX       SnmpAdminString
    MAX-ACCESS   read-only
    STATUS       current
    DESCRIPTION
        "Cisco Firepower vnic:FcGroupTempl:statsPolicyName
        managed object property"
    ::= { cfprVnicFcGroupTemplEntry 16 }

cfprVnicFcGroupTemplStorageConnPolicyName OBJECT-TYPE
    SYNTAX       SnmpAdminString
    MAX-ACCESS   read-only
    STATUS       current
    DESCRIPTION
        "Cisco Firepower vnic:FcGroupTempl:storageConnPolicyName
        managed object property"
    ::= { cfprVnicFcGroupTemplEntry 17 }

cfprVnicFcGroupTemplTemplType OBJECT-TYPE
    SYNTAX       CfprVnicTemplateType
    MAX-ACCESS   read-only
    STATUS       current
    DESCRIPTION
        "Cisco Firepower vnic:FcGroupTempl:templType managed
        object property"
    ::= { cfprVnicFcGroupTemplEntry 18 }

cfprVnicFcIfTable OBJECT-TYPE
    SYNTAX           SEQUENCE OF CfprVnicFcIfEntry
    MAX-ACCESS       not-accessible
    STATUS           current
    DESCRIPTION
        "Cisco Firepower vnic:FcIf managed object table"
    ::= { cfprVnicObjects 17 }

cfprVnicFcIfEntry OBJECT-TYPE
    SYNTAX           CfprVnicFcIfEntry
    MAX-ACCESS       not-accessible
    STATUS           current
    DESCRIPTION
        "Entry for the cfprVnicFcIfTable table."
    INDEX { cfprVnicFcIfInstanceId }
    ::= { cfprVnicFcIfTable 1 }

CfprVnicFcIfEntry ::= SEQUENCE {
    cfprVnicFcIfInstanceId                                           CfprManagedObjectId,
    cfprVnicFcIfDn                                                   CfprManagedObjectDn,
    cfprVnicFcIfRn                                                   SnmpAdminString,
    cfprVnicFcIfConfigQualifier                                      CfprVnicConfigIssues,
    cfprVnicFcIfInitiator                                            Unsigned64,
    cfprVnicFcIfName                                                 SnmpAdminString,
    cfprVnicFcIfOperState                                            CfprVnicIfOperState,
    cfprVnicFcIfOperVnetDn                                           SnmpAdminString,
    cfprVnicFcIfOperVnetName                                         SnmpAdminString,
    cfprVnicFcIfOwner                                                CfprVnicConnectionOwner,
    cfprVnicFcIfPubNwId                                              Gauge32,
    cfprVnicFcIfSharing                                              CfprFabricVlanSharingType,
    cfprVnicFcIfSwitchId                                             CfprVnicL2IfSwitchId,
    cfprVnicFcIfType                                                 CfprVnicAFcIfType,
    cfprVnicFcIfVnet                                                 Gauge32
}

cfprVnicFcIfInstanceId OBJECT-TYPE
    SYNTAX       CfprManagedObjectId
    MAX-ACCESS   not-accessible
    STATUS       current
    DESCRIPTION
        "Instance identifier of the managed object."
    ::= { cfprVnicFcIfEntry 1 }

cfprVnicFcIfDn OBJECT-TYPE
    SYNTAX       CfprManagedObjectDn
    MAX-ACCESS   read-only
    STATUS       current
    DESCRIPTION
        "Cisco Firepower vnic:FcIf:dn managed object property"
    ::= { cfprVnicFcIfEntry 2 }

cfprVnicFcIfRn OBJECT-TYPE
    SYNTAX       SnmpAdminString
    MAX-ACCESS   read-only
    STATUS       current
    DESCRIPTION
        "Cisco Firepower vnic:FcIf:rn managed object property"
    ::= { cfprVnicFcIfEntry 3 }

cfprVnicFcIfConfigQualifier OBJECT-TYPE
    SYNTAX       CfprVnicConfigIssues
    MAX-ACCESS   read-only
    STATUS       current
    DESCRIPTION
        "Cisco Firepower vnic:FcIf:configQualifier managed
        object property"
    ::= { cfprVnicFcIfEntry 4 }

cfprVnicFcIfInitiator OBJECT-TYPE
    SYNTAX       Unsigned64
    MAX-ACCESS   read-only
    STATUS       current
    DESCRIPTION
        "Cisco Firepower vnic:FcIf:initiator managed object property"
    ::= { cfprVnicFcIfEntry 5 }

cfprVnicFcIfName OBJECT-TYPE
    SYNTAX       SnmpAdminString
    MAX-ACCESS   read-only
    STATUS       current
    DESCRIPTION
        "Cisco Firepower vnic:FcIf:name managed object property"
    ::= { cfprVnicFcIfEntry 6 }

cfprVnicFcIfOperState OBJECT-TYPE
    SYNTAX       CfprVnicIfOperState
    MAX-ACCESS   read-only
    STATUS       current
    DESCRIPTION
        "Cisco Firepower vnic:FcIf:operState managed object property"
    ::= { cfprVnicFcIfEntry 7 }

cfprVnicFcIfOperVnetDn OBJECT-TYPE
    SYNTAX       SnmpAdminString
    MAX-ACCESS   read-only
    STATUS       current
    DESCRIPTION
        "Cisco Firepower vnic:FcIf:operVnetDn managed object property"
    ::= { cfprVnicFcIfEntry 8 }

cfprVnicFcIfOperVnetName OBJECT-TYPE
    SYNTAX       SnmpAdminString
    MAX-ACCESS   read-only
    STATUS       current
    DESCRIPTION
        "Cisco Firepower vnic:FcIf:operVnetName managed object property"
    ::= { cfprVnicFcIfEntry 9 }

cfprVnicFcIfOwner OBJECT-TYPE
    SYNTAX       CfprVnicConnectionOwner
    MAX-ACCESS   read-only
    STATUS       current
    DESCRIPTION
        "Cisco Firepower vnic:FcIf:owner managed object property"
    ::= { cfprVnicFcIfEntry 10 }

cfprVnicFcIfPubNwId OBJECT-TYPE
    SYNTAX       Gauge32
    MAX-ACCESS   read-only
    STATUS       current
    DESCRIPTION
        "Cisco Firepower vnic:FcIf:pubNwId managed object property"
    ::= { cfprVnicFcIfEntry 11 }

cfprVnicFcIfSharing OBJECT-TYPE
    SYNTAX       CfprFabricVlanSharingType
    MAX-ACCESS   read-only
    STATUS       current
    DESCRIPTION
        "Cisco Firepower vnic:FcIf:sharing managed object property"
    ::= { cfprVnicFcIfEntry 12 }

cfprVnicFcIfSwitchId OBJECT-TYPE
    SYNTAX       CfprVnicL2IfSwitchId
    MAX-ACCESS   read-only
    STATUS       current
    DESCRIPTION
        "Cisco Firepower vnic:FcIf:switchId managed object property"
    ::= { cfprVnicFcIfEntry 13 }

cfprVnicFcIfType OBJECT-TYPE
    SYNTAX       CfprVnicAFcIfType
    MAX-ACCESS   read-only
    STATUS       current
    DESCRIPTION
        "Cisco Firepower vnic:FcIf:type managed object property"
    ::= { cfprVnicFcIfEntry 14 }

cfprVnicFcIfVnet OBJECT-TYPE
    SYNTAX       Gauge32
    MAX-ACCESS   read-only
    STATUS       current
    DESCRIPTION
        "Cisco Firepower vnic:FcIf:vnet managed object property"
    ::= { cfprVnicFcIfEntry 15 }

cfprVnicFcLifTable OBJECT-TYPE
    SYNTAX           SEQUENCE OF CfprVnicFcLifEntry
    MAX-ACCESS       not-accessible
    STATUS           current
    DESCRIPTION
        "Cisco Firepower vnic:FcLif managed object table"
    ::= { cfprVnicObjects 18 }

cfprVnicFcLifEntry OBJECT-TYPE
    SYNTAX           CfprVnicFcLifEntry
    MAX-ACCESS       not-accessible
    STATUS           current
    DESCRIPTION
        "Entry for the cfprVnicFcLifTable table."
    INDEX { cfprVnicFcLifInstanceId }
    ::= { cfprVnicFcLifTable 1 }

CfprVnicFcLifEntry ::= SEQUENCE {
    cfprVnicFcLifInstanceId                                          CfprManagedObjectId,
    cfprVnicFcLifDn                                                  CfprManagedObjectDn,
    cfprVnicFcLifRn                                                  SnmpAdminString,
    cfprVnicFcLifAddr                                                Unsigned64,
    cfprVnicFcLifName                                                SnmpAdminString,
    cfprVnicFcLifNicDn                                               SnmpAdminString,
    cfprVnicFcLifOwner                                               CfprVnicConnectionOwner,
    cfprVnicFcLifSwitchId                                            CfprNetworkSwitchId,
    cfprVnicFcLifType                                                CfprVnicConnectionType,
    cfprVnicFcLifVnicDn                                              SnmpAdminString
}

cfprVnicFcLifInstanceId OBJECT-TYPE
    SYNTAX       CfprManagedObjectId
    MAX-ACCESS   not-accessible
    STATUS       current
    DESCRIPTION
        "Instance identifier of the managed object."
    ::= { cfprVnicFcLifEntry 1 }

cfprVnicFcLifDn OBJECT-TYPE
    SYNTAX       CfprManagedObjectDn
    MAX-ACCESS   read-only
    STATUS       current
    DESCRIPTION
        "Cisco Firepower vnic:FcLif:dn managed object property"
    ::= { cfprVnicFcLifEntry 2 }

cfprVnicFcLifRn OBJECT-TYPE
    SYNTAX       SnmpAdminString
    MAX-ACCESS   read-only
    STATUS       current
    DESCRIPTION
        "Cisco Firepower vnic:FcLif:rn managed object property"
    ::= { cfprVnicFcLifEntry 3 }

cfprVnicFcLifAddr OBJECT-TYPE
    SYNTAX       Unsigned64
    MAX-ACCESS   read-only
    STATUS       current
    DESCRIPTION
        "Cisco Firepower vnic:FcLif:addr managed object property"
    ::= { cfprVnicFcLifEntry 4 }

cfprVnicFcLifName OBJECT-TYPE
    SYNTAX       SnmpAdminString
    MAX-ACCESS   read-only
    STATUS       current
    DESCRIPTION
        "Cisco Firepower vnic:FcLif:name managed object property"
    ::= { cfprVnicFcLifEntry 5 }

cfprVnicFcLifNicDn OBJECT-TYPE
    SYNTAX       SnmpAdminString
    MAX-ACCESS   read-only
    STATUS       current
    DESCRIPTION
        "Cisco Firepower vnic:FcLif:nicDn managed object property"
    ::= { cfprVnicFcLifEntry 6 }

cfprVnicFcLifOwner OBJECT-TYPE
    SYNTAX       CfprVnicConnectionOwner
    MAX-ACCESS   read-only
    STATUS       current
    DESCRIPTION
        "Cisco Firepower vnic:FcLif:owner managed object property"
    ::= { cfprVnicFcLifEntry 7 }

cfprVnicFcLifSwitchId OBJECT-TYPE
    SYNTAX       CfprNetworkSwitchId
    MAX-ACCESS   read-only
    STATUS       current
    DESCRIPTION
        "Cisco Firepower vnic:FcLif:switchId managed object property"
    ::= { cfprVnicFcLifEntry 8 }

cfprVnicFcLifType OBJECT-TYPE
    SYNTAX       CfprVnicConnectionType
    MAX-ACCESS   read-only
    STATUS       current
    DESCRIPTION
        "Cisco Firepower vnic:FcLif:type managed object property"
    ::= { cfprVnicFcLifEntry 9 }

cfprVnicFcLifVnicDn OBJECT-TYPE
    SYNTAX       SnmpAdminString
    MAX-ACCESS   read-only
    STATUS       current
    DESCRIPTION
        "Cisco Firepower vnic:FcLif:vnicDn managed object property"
    ::= { cfprVnicFcLifEntry 10 }

cfprVnicFcNodeTable OBJECT-TYPE
    SYNTAX           SEQUENCE OF CfprVnicFcNodeEntry
    MAX-ACCESS       not-accessible
    STATUS           current
    DESCRIPTION
        "Cisco Firepower vnic:FcNode managed object table"
    ::= { cfprVnicObjects 19 }

cfprVnicFcNodeEntry OBJECT-TYPE
    SYNTAX           CfprVnicFcNodeEntry
    MAX-ACCESS       not-accessible
    STATUS           current
    DESCRIPTION
        "Entry for the cfprVnicFcNodeTable table."
    INDEX { cfprVnicFcNodeInstanceId }
    ::= { cfprVnicFcNodeTable 1 }

CfprVnicFcNodeEntry ::= SEQUENCE {
    cfprVnicFcNodeInstanceId                                         CfprManagedObjectId,
    cfprVnicFcNodeDn                                                 CfprManagedObjectDn,
    cfprVnicFcNodeRn                                                 SnmpAdminString,
    cfprVnicFcNodeAddrData                                           Unsigned64,
    cfprVnicFcNodeFltAggr                                            Unsigned64,
    cfprVnicFcNodeIdentPoolName                                      SnmpAdminString,
    cfprVnicFcNodeMaxDerivableWWPN                                   Gauge32,
    cfprVnicFcNodeOperIdentPoolName                                  SnmpAdminString,
    cfprVnicFcNodeOwner                                              CfprVnicFcNodeOwner
}

cfprVnicFcNodeInstanceId OBJECT-TYPE
    SYNTAX       CfprManagedObjectId
    MAX-ACCESS   not-accessible
    STATUS       current
    DESCRIPTION
        "Instance identifier of the managed object."
    ::= { cfprVnicFcNodeEntry 1 }

cfprVnicFcNodeDn OBJECT-TYPE
    SYNTAX       CfprManagedObjectDn
    MAX-ACCESS   read-only
    STATUS       current
    DESCRIPTION
        "Cisco Firepower vnic:FcNode:dn managed object property"
    ::= { cfprVnicFcNodeEntry 2 }

cfprVnicFcNodeRn OBJECT-TYPE
    SYNTAX       SnmpAdminString
    MAX-ACCESS   read-only
    STATUS       current
    DESCRIPTION
        "Cisco Firepower vnic:FcNode:rn managed object property"
    ::= { cfprVnicFcNodeEntry 3 }

cfprVnicFcNodeAddrData OBJECT-TYPE
    SYNTAX       Unsigned64
    MAX-ACCESS   read-only
    STATUS       current
    DESCRIPTION
        "Cisco Firepower vnic:FcNode:addr managed object property"
    ::= { cfprVnicFcNodeEntry 4 }

cfprVnicFcNodeFltAggr OBJECT-TYPE
    SYNTAX       Unsigned64
    MAX-ACCESS   read-only
    STATUS       current
    DESCRIPTION
        "Cisco Firepower vnic:FcNode:fltAggr managed object property"
    ::= { cfprVnicFcNodeEntry 5 }

cfprVnicFcNodeIdentPoolName OBJECT-TYPE
    SYNTAX       SnmpAdminString
    MAX-ACCESS   read-only
    STATUS       current
    DESCRIPTION
        "Cisco Firepower vnic:FcNode:identPoolName managed
        object property"
    ::= { cfprVnicFcNodeEntry 6 }

cfprVnicFcNodeMaxDerivableWWPN OBJECT-TYPE
    SYNTAX       Gauge32
    MAX-ACCESS   read-only
    STATUS       current
    DESCRIPTION
        "Cisco Firepower vnic:FcNode:maxDerivableWWPN managed
        object property"
    ::= { cfprVnicFcNodeEntry 7 }

cfprVnicFcNodeOperIdentPoolName OBJECT-TYPE
    SYNTAX       SnmpAdminString
    MAX-ACCESS   read-only
    STATUS       current
    DESCRIPTION
        "Cisco Firepower vnic:FcNode:operIdentPoolName
        managed object property"
    ::= { cfprVnicFcNodeEntry 8 }

cfprVnicFcNodeOwner OBJECT-TYPE
    SYNTAX       CfprVnicFcNodeOwner
    MAX-ACCESS   read-only
    STATUS       current
    DESCRIPTION
        "Cisco Firepower vnic:FcNode:owner managed object property"
    ::= { cfprVnicFcNodeEntry 9 }

cfprVnicFcOEIfTable OBJECT-TYPE
    SYNTAX           SEQUENCE OF CfprVnicFcOEIfEntry
    MAX-ACCESS       not-accessible
    STATUS           current
    DESCRIPTION
        "Cisco Firepower vnic:FcOEIf managed object table"
    ::= { cfprVnicObjects 20 }

cfprVnicFcOEIfEntry OBJECT-TYPE
    SYNTAX           CfprVnicFcOEIfEntry
    MAX-ACCESS       not-accessible
    STATUS           current
    DESCRIPTION
        "Entry for the cfprVnicFcOEIfTable table."
    INDEX { cfprVnicFcOEIfInstanceId }
    ::= { cfprVnicFcOEIfTable 1 }

CfprVnicFcOEIfEntry ::= SEQUENCE {
    cfprVnicFcOEIfInstanceId                                         CfprManagedObjectId,
    cfprVnicFcOEIfDn                                                 CfprManagedObjectDn,
    cfprVnicFcOEIfRn                                                 SnmpAdminString,
    cfprVnicFcOEIfConfigQualifier                                    CfprVnicConfigIssues,
    cfprVnicFcOEIfInitiator                                          Unsigned64,
    cfprVnicFcOEIfName                                               SnmpAdminString,
    cfprVnicFcOEIfOperState                                          CfprVnicIfOperState,
    cfprVnicFcOEIfOperVnetDn                                         SnmpAdminString,
    cfprVnicFcOEIfOperVnetName                                       SnmpAdminString,
    cfprVnicFcOEIfOwner                                              CfprVnicConnectionOwner,
    cfprVnicFcOEIfPubNwId                                            Gauge32,
    cfprVnicFcOEIfSharing                                            CfprFabricVlanSharingType,
    cfprVnicFcOEIfSwitchId                                           CfprVnicL2IfSwitchId,
    cfprVnicFcOEIfType                                               CfprVnicAFcIfType,
    cfprVnicFcOEIfVnet                                               Gauge32
}

cfprVnicFcOEIfInstanceId OBJECT-TYPE
    SYNTAX       CfprManagedObjectId
    MAX-ACCESS   not-accessible
    STATUS       current
    DESCRIPTION
        "Instance identifier of the managed object."
    ::= { cfprVnicFcOEIfEntry 1 }

cfprVnicFcOEIfDn OBJECT-TYPE
    SYNTAX       CfprManagedObjectDn
    MAX-ACCESS   read-only
    STATUS       current
    DESCRIPTION
        "Cisco Firepower vnic:FcOEIf:dn managed object property"
    ::= { cfprVnicFcOEIfEntry 2 }

cfprVnicFcOEIfRn OBJECT-TYPE
    SYNTAX       SnmpAdminString
    MAX-ACCESS   read-only
    STATUS       current
    DESCRIPTION
        "Cisco Firepower vnic:FcOEIf:rn managed object property"
    ::= { cfprVnicFcOEIfEntry 3 }

cfprVnicFcOEIfConfigQualifier OBJECT-TYPE
    SYNTAX       CfprVnicConfigIssues
    MAX-ACCESS   read-only
    STATUS       current
    DESCRIPTION
        "Cisco Firepower vnic:FcOEIf:configQualifier managed
        object property"
    ::= { cfprVnicFcOEIfEntry 4 }

cfprVnicFcOEIfInitiator OBJECT-TYPE
    SYNTAX       Unsigned64
    MAX-ACCESS   read-only
    STATUS       current
    DESCRIPTION
        "Cisco Firepower vnic:FcOEIf:initiator managed object property"
    ::= { cfprVnicFcOEIfEntry 5 }

cfprVnicFcOEIfName OBJECT-TYPE
    SYNTAX       SnmpAdminString
    MAX-ACCESS   read-only
    STATUS       current
    DESCRIPTION
        "Cisco Firepower vnic:FcOEIf:name managed object property"
    ::= { cfprVnicFcOEIfEntry 6 }

cfprVnicFcOEIfOperState OBJECT-TYPE
    SYNTAX       CfprVnicIfOperState
    MAX-ACCESS   read-only
    STATUS       current
    DESCRIPTION
        "Cisco Firepower vnic:FcOEIf:operState managed object property"
    ::= { cfprVnicFcOEIfEntry 7 }

cfprVnicFcOEIfOperVnetDn OBJECT-TYPE
    SYNTAX       SnmpAdminString
    MAX-ACCESS   read-only
    STATUS       current
    DESCRIPTION
        "Cisco Firepower vnic:FcOEIf:operVnetDn managed object property"
    ::= { cfprVnicFcOEIfEntry 8 }

cfprVnicFcOEIfOperVnetName OBJECT-TYPE
    SYNTAX       SnmpAdminString
    MAX-ACCESS   read-only
    STATUS       current
    DESCRIPTION
        "Cisco Firepower vnic:FcOEIf:operVnetName managed object property"
    ::= { cfprVnicFcOEIfEntry 9 }

cfprVnicFcOEIfOwner OBJECT-TYPE
    SYNTAX       CfprVnicConnectionOwner
    MAX-ACCESS   read-only
    STATUS       current
    DESCRIPTION
        "Cisco Firepower vnic:FcOEIf:owner managed object property"
    ::= { cfprVnicFcOEIfEntry 10 }

cfprVnicFcOEIfPubNwId OBJECT-TYPE
    SYNTAX       Gauge32
    MAX-ACCESS   read-only
    STATUS       current
    DESCRIPTION
        "Cisco Firepower vnic:FcOEIf:pubNwId managed object property"
    ::= { cfprVnicFcOEIfEntry 11 }

cfprVnicFcOEIfSharing OBJECT-TYPE
    SYNTAX       CfprFabricVlanSharingType
    MAX-ACCESS   read-only
    STATUS       current
    DESCRIPTION
        "Cisco Firepower vnic:FcOEIf:sharing managed object property"
    ::= { cfprVnicFcOEIfEntry 12 }

cfprVnicFcOEIfSwitchId OBJECT-TYPE
    SYNTAX       CfprVnicL2IfSwitchId
    MAX-ACCESS   read-only
    STATUS       current
    DESCRIPTION
        "Cisco Firepower vnic:FcOEIf:switchId managed object property"
    ::= { cfprVnicFcOEIfEntry 13 }

cfprVnicFcOEIfType OBJECT-TYPE
    SYNTAX       CfprVnicAFcIfType
    MAX-ACCESS   read-only
    STATUS       current
    DESCRIPTION
        "Cisco Firepower vnic:FcOEIf:type managed object property"
    ::= { cfprVnicFcOEIfEntry 14 }

cfprVnicFcOEIfVnet OBJECT-TYPE
    SYNTAX       Gauge32
    MAX-ACCESS   read-only
    STATUS       current
    DESCRIPTION
        "Cisco Firepower vnic:FcOEIf:vnet managed object property"
    ::= { cfprVnicFcOEIfEntry 15 }

cfprVnicIPv4DhcpTable OBJECT-TYPE
    SYNTAX           SEQUENCE OF CfprVnicIPv4DhcpEntry
    MAX-ACCESS       not-accessible
    STATUS           current
    DESCRIPTION
        "Cisco Firepower vnic:IPv4Dhcp managed object table"
    ::= { cfprVnicObjects 21 }

cfprVnicIPv4DhcpEntry OBJECT-TYPE
    SYNTAX           CfprVnicIPv4DhcpEntry
    MAX-ACCESS       not-accessible
    STATUS           current
    DESCRIPTION
        "Entry for the cfprVnicIPv4DhcpTable table."
    INDEX { cfprVnicIPv4DhcpInstanceId }
    ::= { cfprVnicIPv4DhcpTable 1 }

CfprVnicIPv4DhcpEntry ::= SEQUENCE {
    cfprVnicIPv4DhcpInstanceId                                       CfprManagedObjectId,
    cfprVnicIPv4DhcpDn                                               CfprManagedObjectDn,
    cfprVnicIPv4DhcpRn                                               SnmpAdminString,
    cfprVnicIPv4DhcpAddr                                             InetAddressIPv4,
    cfprVnicIPv4DhcpDefGw                                            InetAddressIPv4,
    cfprVnicIPv4DhcpSubnet                                           InetAddressIPv4
}

cfprVnicIPv4DhcpInstanceId OBJECT-TYPE
    SYNTAX       CfprManagedObjectId
    MAX-ACCESS   not-accessible
    STATUS       current
    DESCRIPTION
        "Instance identifier of the managed object."
    ::= { cfprVnicIPv4DhcpEntry 1 }

cfprVnicIPv4DhcpDn OBJECT-TYPE
    SYNTAX       CfprManagedObjectDn
    MAX-ACCESS   read-only
    STATUS       current
    DESCRIPTION
        "Cisco Firepower vnic:IPv4Dhcp:dn managed object property"
    ::= { cfprVnicIPv4DhcpEntry 2 }

cfprVnicIPv4DhcpRn OBJECT-TYPE
    SYNTAX       SnmpAdminString
    MAX-ACCESS   read-only
    STATUS       current
    DESCRIPTION
        "Cisco Firepower vnic:IPv4Dhcp:rn managed object property"
    ::= { cfprVnicIPv4DhcpEntry 3 }

cfprVnicIPv4DhcpAddr OBJECT-TYPE
    SYNTAX       InetAddressIPv4
    MAX-ACCESS   read-only
    STATUS       current
    DESCRIPTION
        "Cisco Firepower vnic:IPv4Dhcp:addr managed object property"
    ::= { cfprVnicIPv4DhcpEntry 4 }

cfprVnicIPv4DhcpDefGw OBJECT-TYPE
    SYNTAX       InetAddressIPv4
    MAX-ACCESS   read-only
    STATUS       current
    DESCRIPTION
        "Cisco Firepower vnic:IPv4Dhcp:defGw managed object property"
    ::= { cfprVnicIPv4DhcpEntry 5 }

cfprVnicIPv4DhcpSubnet OBJECT-TYPE
    SYNTAX       InetAddressIPv4
    MAX-ACCESS   read-only
    STATUS       current
    DESCRIPTION
        "Cisco Firepower vnic:IPv4Dhcp:subnet managed object property"
    ::= { cfprVnicIPv4DhcpEntry 6 }

cfprVnicIPv4DnsTable OBJECT-TYPE
    SYNTAX           SEQUENCE OF CfprVnicIPv4DnsEntry
    MAX-ACCESS       not-accessible
    STATUS           current
    DESCRIPTION
        "Cisco Firepower vnic:IPv4Dns managed object table"
    ::= { cfprVnicObjects 22 }

cfprVnicIPv4DnsEntry OBJECT-TYPE
    SYNTAX           CfprVnicIPv4DnsEntry
    MAX-ACCESS       not-accessible
    STATUS           current
    DESCRIPTION
        "Entry for the cfprVnicIPv4DnsTable table."
    INDEX { cfprVnicIPv4DnsInstanceId }
    ::= { cfprVnicIPv4DnsTable 1 }

CfprVnicIPv4DnsEntry ::= SEQUENCE {
    cfprVnicIPv4DnsInstanceId                                        CfprManagedObjectId,
    cfprVnicIPv4DnsDn                                                CfprManagedObjectDn,
    cfprVnicIPv4DnsRn                                                SnmpAdminString,
    cfprVnicIPv4DnsAddr                                              InetAddressIPv4,
    cfprVnicIPv4DnsDefGw                                             InetAddressIPv4,
    cfprVnicIPv4DnsPref                                              CfprVnicIPv4DnsPref,
    cfprVnicIPv4DnsSubnet                                            InetAddressIPv4
}

cfprVnicIPv4DnsInstanceId OBJECT-TYPE
    SYNTAX       CfprManagedObjectId
    MAX-ACCESS   not-accessible
    STATUS       current
    DESCRIPTION
        "Instance identifier of the managed object."
    ::= { cfprVnicIPv4DnsEntry 1 }

cfprVnicIPv4DnsDn OBJECT-TYPE
    SYNTAX       CfprManagedObjectDn
    MAX-ACCESS   read-only
    STATUS       current
    DESCRIPTION
        "Cisco Firepower vnic:IPv4Dns:dn managed object property"
    ::= { cfprVnicIPv4DnsEntry 2 }

cfprVnicIPv4DnsRn OBJECT-TYPE
    SYNTAX       SnmpAdminString
    MAX-ACCESS   read-only
    STATUS       current
    DESCRIPTION
        "Cisco Firepower vnic:IPv4Dns:rn managed object property"
    ::= { cfprVnicIPv4DnsEntry 3 }

cfprVnicIPv4DnsAddr OBJECT-TYPE
    SYNTAX       InetAddressIPv4
    MAX-ACCESS   read-only
    STATUS       current
    DESCRIPTION
        "Cisco Firepower vnic:IPv4Dns:addr managed object property"
    ::= { cfprVnicIPv4DnsEntry 4 }

cfprVnicIPv4DnsDefGw OBJECT-TYPE
    SYNTAX       InetAddressIPv4
    MAX-ACCESS   read-only
    STATUS       current
    DESCRIPTION
        "Cisco Firepower vnic:IPv4Dns:defGw managed object property"
    ::= { cfprVnicIPv4DnsEntry 5 }

cfprVnicIPv4DnsPref OBJECT-TYPE
    SYNTAX       CfprVnicIPv4DnsPref
    MAX-ACCESS   read-only
    STATUS       current
    DESCRIPTION
        "Cisco Firepower vnic:IPv4Dns:pref managed object property"
    ::= { cfprVnicIPv4DnsEntry 6 }

cfprVnicIPv4DnsSubnet OBJECT-TYPE
    SYNTAX       InetAddressIPv4
    MAX-ACCESS   read-only
    STATUS       current
    DESCRIPTION
        "Cisco Firepower vnic:IPv4Dns:subnet managed object property"
    ::= { cfprVnicIPv4DnsEntry 7 }

cfprVnicIPv4IfTable OBJECT-TYPE
    SYNTAX           SEQUENCE OF CfprVnicIPv4IfEntry
    MAX-ACCESS       not-accessible
    STATUS           current
    DESCRIPTION
        "Cisco Firepower vnic:IPv4If managed object table"
    ::= { cfprVnicObjects 23 }

cfprVnicIPv4IfEntry OBJECT-TYPE
    SYNTAX           CfprVnicIPv4IfEntry
    MAX-ACCESS       not-accessible
    STATUS           current
    DESCRIPTION
        "Entry for the cfprVnicIPv4IfTable table."
    INDEX { cfprVnicIPv4IfInstanceId }
    ::= { cfprVnicIPv4IfTable 1 }

CfprVnicIPv4IfEntry ::= SEQUENCE {
    cfprVnicIPv4IfInstanceId                                         CfprManagedObjectId,
    cfprVnicIPv4IfDn                                                 CfprManagedObjectDn,
    cfprVnicIPv4IfRn                                                 SnmpAdminString,
    cfprVnicIPv4IfAddr                                               InetAddressIPv4,
    cfprVnicIPv4IfConfigQualifier                                    CfprVnicConfigIssues,
    cfprVnicIPv4IfName                                               SnmpAdminString,
    cfprVnicIPv4IfOperState                                          CfprVnicIfOperState,
    cfprVnicIPv4IfOperVnetDn                                         SnmpAdminString,
    cfprVnicIPv4IfOperVnetName                                       SnmpAdminString,
    cfprVnicIPv4IfOwner                                              CfprVnicConnectionOwner,
    cfprVnicIPv4IfPubNwId                                            Gauge32,
    cfprVnicIPv4IfSharing                                            CfprFabricVlanSharingType,
    cfprVnicIPv4IfSwitchId                                           CfprNetworkSwitchId,
    cfprVnicIPv4IfType                                               CfprVnicConnectionType,
    cfprVnicIPv4IfVnet                                               Gauge32
}

cfprVnicIPv4IfInstanceId OBJECT-TYPE
    SYNTAX       CfprManagedObjectId
    MAX-ACCESS   not-accessible
    STATUS       current
    DESCRIPTION
        "Instance identifier of the managed object."
    ::= { cfprVnicIPv4IfEntry 1 }

cfprVnicIPv4IfDn OBJECT-TYPE
    SYNTAX       CfprManagedObjectDn
    MAX-ACCESS   read-only
    STATUS       current
    DESCRIPTION
        "Cisco Firepower vnic:IPv4If:dn managed object property"
    ::= { cfprVnicIPv4IfEntry 2 }

cfprVnicIPv4IfRn OBJECT-TYPE
    SYNTAX       SnmpAdminString
    MAX-ACCESS   read-only
    STATUS       current
    DESCRIPTION
        "Cisco Firepower vnic:IPv4If:rn managed object property"
    ::= { cfprVnicIPv4IfEntry 3 }

cfprVnicIPv4IfAddr OBJECT-TYPE
    SYNTAX       InetAddressIPv4
    MAX-ACCESS   read-only
    STATUS       current
    DESCRIPTION
        "Cisco Firepower vnic:IPv4If:addr managed object property"
    ::= { cfprVnicIPv4IfEntry 4 }

cfprVnicIPv4IfConfigQualifier OBJECT-TYPE
    SYNTAX       CfprVnicConfigIssues
    MAX-ACCESS   read-only
    STATUS       current
    DESCRIPTION
        "Cisco Firepower vnic:IPv4If:configQualifier managed
        object property"
    ::= { cfprVnicIPv4IfEntry 5 }

cfprVnicIPv4IfName OBJECT-TYPE
    SYNTAX       SnmpAdminString
    MAX-ACCESS   read-only
    STATUS       current
    DESCRIPTION
        "Cisco Firepower vnic:IPv4If:name managed object property"
    ::= { cfprVnicIPv4IfEntry 6 }

cfprVnicIPv4IfOperState OBJECT-TYPE
    SYNTAX       CfprVnicIfOperState
    MAX-ACCESS   read-only
    STATUS       current
    DESCRIPTION
        "Cisco Firepower vnic:IPv4If:operState managed object property"
    ::= { cfprVnicIPv4IfEntry 7 }

cfprVnicIPv4IfOperVnetDn OBJECT-TYPE
    SYNTAX       SnmpAdminString
    MAX-ACCESS   read-only
    STATUS       current
    DESCRIPTION
        "Cisco Firepower vnic:IPv4If:operVnetDn managed object property"
    ::= { cfprVnicIPv4IfEntry 8 }

cfprVnicIPv4IfOperVnetName OBJECT-TYPE
    SYNTAX       SnmpAdminString
    MAX-ACCESS   read-only
    STATUS       current
    DESCRIPTION
        "Cisco Firepower vnic:IPv4If:operVnetName managed object property"
    ::= { cfprVnicIPv4IfEntry 9 }

cfprVnicIPv4IfOwner OBJECT-TYPE
    SYNTAX       CfprVnicConnectionOwner
    MAX-ACCESS   read-only
    STATUS       current
    DESCRIPTION
        "Cisco Firepower vnic:IPv4If:owner managed object property"
    ::= { cfprVnicIPv4IfEntry 10 }

cfprVnicIPv4IfPubNwId OBJECT-TYPE
    SYNTAX       Gauge32
    MAX-ACCESS   read-only
    STATUS       current
    DESCRIPTION
        "Cisco Firepower vnic:IPv4If:pubNwId managed object property"
    ::= { cfprVnicIPv4IfEntry 11 }

cfprVnicIPv4IfSharing OBJECT-TYPE
    SYNTAX       CfprFabricVlanSharingType
    MAX-ACCESS   read-only
    STATUS       current
    DESCRIPTION
        "Cisco Firepower vnic:IPv4If:sharing managed object property"
    ::= { cfprVnicIPv4IfEntry 12 }

cfprVnicIPv4IfSwitchId OBJECT-TYPE
    SYNTAX       CfprNetworkSwitchId
    MAX-ACCESS   read-only
    STATUS       current
    DESCRIPTION
        "Cisco Firepower vnic:IPv4If:switchId managed object property"
    ::= { cfprVnicIPv4IfEntry 13 }

cfprVnicIPv4IfType OBJECT-TYPE
    SYNTAX       CfprVnicConnectionType
    MAX-ACCESS   read-only
    STATUS       current
    DESCRIPTION
        "Cisco Firepower vnic:IPv4If:type managed object property"
    ::= { cfprVnicIPv4IfEntry 14 }

cfprVnicIPv4IfVnet OBJECT-TYPE
    SYNTAX       Gauge32
    MAX-ACCESS   read-only
    STATUS       current
    DESCRIPTION
        "Cisco Firepower vnic:IPv4If:vnet managed object property"
    ::= { cfprVnicIPv4IfEntry 15 }

cfprVnicIPv4IscsiAddrTable OBJECT-TYPE
    SYNTAX           SEQUENCE OF CfprVnicIPv4IscsiAddrEntry
    MAX-ACCESS       not-accessible
    STATUS           current
    DESCRIPTION
        "Cisco Firepower vnic:IPv4IscsiAddr managed object table"
    ::= { cfprVnicObjects 24 }

cfprVnicIPv4IscsiAddrEntry OBJECT-TYPE
    SYNTAX           CfprVnicIPv4IscsiAddrEntry
    MAX-ACCESS       not-accessible
    STATUS           current
    DESCRIPTION
        "Entry for the cfprVnicIPv4IscsiAddrTable table."
    INDEX { cfprVnicIPv4IscsiAddrInstanceId }
    ::= { cfprVnicIPv4IscsiAddrTable 1 }

CfprVnicIPv4IscsiAddrEntry ::= SEQUENCE {
    cfprVnicIPv4IscsiAddrInstanceId                                  CfprManagedObjectId,
    cfprVnicIPv4IscsiAddrDn                                          CfprManagedObjectDn,
    cfprVnicIPv4IscsiAddrRn                                          SnmpAdminString,
    cfprVnicIPv4IscsiAddrAddr                                        InetAddressIPv4,
    cfprVnicIPv4IscsiAddrDefGw                                       InetAddressIPv4,
    cfprVnicIPv4IscsiAddrPrimDns                                     InetAddressIPv4,
    cfprVnicIPv4IscsiAddrSecDns                                      InetAddressIPv4,
    cfprVnicIPv4IscsiAddrSubnet                                      InetAddressIPv4
}

cfprVnicIPv4IscsiAddrInstanceId OBJECT-TYPE
    SYNTAX       CfprManagedObjectId
    MAX-ACCESS   not-accessible
    STATUS       current
    DESCRIPTION
        "Instance identifier of the managed object."
    ::= { cfprVnicIPv4IscsiAddrEntry 1 }

cfprVnicIPv4IscsiAddrDn OBJECT-TYPE
    SYNTAX       CfprManagedObjectDn
    MAX-ACCESS   read-only
    STATUS       current
    DESCRIPTION
        "Cisco Firepower vnic:IPv4IscsiAddr:dn managed object property"
    ::= { cfprVnicIPv4IscsiAddrEntry 2 }

cfprVnicIPv4IscsiAddrRn OBJECT-TYPE
    SYNTAX       SnmpAdminString
    MAX-ACCESS   read-only
    STATUS       current
    DESCRIPTION
        "Cisco Firepower vnic:IPv4IscsiAddr:rn managed object property"
    ::= { cfprVnicIPv4IscsiAddrEntry 3 }

cfprVnicIPv4IscsiAddrAddr OBJECT-TYPE
    SYNTAX       InetAddressIPv4
    MAX-ACCESS   read-only
    STATUS       current
    DESCRIPTION
        "Cisco Firepower vnic:IPv4IscsiAddr:addr managed object property"
    ::= { cfprVnicIPv4IscsiAddrEntry 4 }

cfprVnicIPv4IscsiAddrDefGw OBJECT-TYPE
    SYNTAX       InetAddressIPv4
    MAX-ACCESS   read-only
    STATUS       current
    DESCRIPTION
        "Cisco Firepower vnic:IPv4IscsiAddr:defGw managed object property"
    ::= { cfprVnicIPv4IscsiAddrEntry 5 }

cfprVnicIPv4IscsiAddrPrimDns OBJECT-TYPE
    SYNTAX       InetAddressIPv4
    MAX-ACCESS   read-only
    STATUS       current
    DESCRIPTION
        "Cisco Firepower vnic:IPv4IscsiAddr:primDns managed
        object property"
    ::= { cfprVnicIPv4IscsiAddrEntry 6 }

cfprVnicIPv4IscsiAddrSecDns OBJECT-TYPE
    SYNTAX       InetAddressIPv4
    MAX-ACCESS   read-only
    STATUS       current
    DESCRIPTION
        "Cisco Firepower vnic:IPv4IscsiAddr:secDns managed
        object property"
    ::= { cfprVnicIPv4IscsiAddrEntry 7 }

cfprVnicIPv4IscsiAddrSubnet OBJECT-TYPE
    SYNTAX       InetAddressIPv4
    MAX-ACCESS   read-only
    STATUS       current
    DESCRIPTION
        "Cisco Firepower vnic:IPv4IscsiAddr:subnet managed
        object property"
    ::= { cfprVnicIPv4IscsiAddrEntry 8 }

cfprVnicIPv4PooledIscsiAddrTable OBJECT-TYPE
    SYNTAX           SEQUENCE OF CfprVnicIPv4PooledIscsiAddrEntry
    MAX-ACCESS       not-accessible
    STATUS           current
    DESCRIPTION
        "Cisco Firepower vnic:IPv4PooledIscsiAddr managed object table"
    ::= { cfprVnicObjects 25 }

cfprVnicIPv4PooledIscsiAddrEntry OBJECT-TYPE
    SYNTAX           CfprVnicIPv4PooledIscsiAddrEntry
    MAX-ACCESS       not-accessible
    STATUS           current
    DESCRIPTION
        "Entry for the cfprVnicIPv4PooledIscsiAddrTable table."
    INDEX { cfprVnicIPv4PooledIscsiAddrInstanceId }
    ::= { cfprVnicIPv4PooledIscsiAddrTable 1 }

CfprVnicIPv4PooledIscsiAddrEntry ::= SEQUENCE {
    cfprVnicIPv4PooledIscsiAddrInstanceId                            CfprManagedObjectId,
    cfprVnicIPv4PooledIscsiAddrDn                                    CfprManagedObjectDn,
    cfprVnicIPv4PooledIscsiAddrRn                                    SnmpAdminString,
    cfprVnicIPv4PooledIscsiAddrAddr                                  InetAddressIPv4,
    cfprVnicIPv4PooledIscsiAddrDefGw                                 InetAddressIPv4,
    cfprVnicIPv4PooledIscsiAddrIdentPoolName                         SnmpAdminString,
    cfprVnicIPv4PooledIscsiAddrOperIdentPoolName                     SnmpAdminString,
    cfprVnicIPv4PooledIscsiAddrPrimDns                               InetAddressIPv4,
    cfprVnicIPv4PooledIscsiAddrSecDns                                InetAddressIPv4,
    cfprVnicIPv4PooledIscsiAddrSubnet                                InetAddressIPv4
}

cfprVnicIPv4PooledIscsiAddrInstanceId OBJECT-TYPE
    SYNTAX       CfprManagedObjectId
    MAX-ACCESS   not-accessible
    STATUS       current
    DESCRIPTION
        "Instance identifier of the managed object."
    ::= { cfprVnicIPv4PooledIscsiAddrEntry 1 }

cfprVnicIPv4PooledIscsiAddrDn OBJECT-TYPE
    SYNTAX       CfprManagedObjectDn
    MAX-ACCESS   read-only
    STATUS       current
    DESCRIPTION
        "Cisco Firepower vnic:IPv4PooledIscsiAddr:dn managed
        object property"
    ::= { cfprVnicIPv4PooledIscsiAddrEntry 2 }

cfprVnicIPv4PooledIscsiAddrRn OBJECT-TYPE
    SYNTAX       SnmpAdminString
    MAX-ACCESS   read-only
    STATUS       current
    DESCRIPTION
        "Cisco Firepower vnic:IPv4PooledIscsiAddr:rn managed
        object property"
    ::= { cfprVnicIPv4PooledIscsiAddrEntry 3 }

cfprVnicIPv4PooledIscsiAddrAddr OBJECT-TYPE
    SYNTAX       InetAddressIPv4
    MAX-ACCESS   read-only
    STATUS       current
    DESCRIPTION
        "Cisco Firepower vnic:IPv4PooledIscsiAddr:addr
        managed object property"
    ::= { cfprVnicIPv4PooledIscsiAddrEntry 4 }

cfprVnicIPv4PooledIscsiAddrDefGw OBJECT-TYPE
    SYNTAX       InetAddressIPv4
    MAX-ACCESS   read-only
    STATUS       current
    DESCRIPTION
        "Cisco Firepower vnic:IPv4PooledIscsiAddr:defGw
        managed object property"
    ::= { cfprVnicIPv4PooledIscsiAddrEntry 5 }

cfprVnicIPv4PooledIscsiAddrIdentPoolName OBJECT-TYPE
    SYNTAX       SnmpAdminString
    MAX-ACCESS   read-only
    STATUS       current
    DESCRIPTION
        "Cisco Firepower vnic:IPv4PooledIscsiAddr:identPoolName
        managed object property"
    ::= { cfprVnicIPv4PooledIscsiAddrEntry 6 }

cfprVnicIPv4PooledIscsiAddrOperIdentPoolName OBJECT-TYPE
    SYNTAX       SnmpAdminString
    MAX-ACCESS   read-only
    STATUS       current
    DESCRIPTION
        "Cisco Firepower vnic:IPv4PooledIscsiAddr:operIdentPoolName
        managed object property"
    ::= { cfprVnicIPv4PooledIscsiAddrEntry 7 }

cfprVnicIPv4PooledIscsiAddrPrimDns OBJECT-TYPE
    SYNTAX       InetAddressIPv4
    MAX-ACCESS   read-only
    STATUS       current
    DESCRIPTION
        "Cisco Firepower vnic:IPv4PooledIscsiAddr:primDns
        managed object property"
    ::= { cfprVnicIPv4PooledIscsiAddrEntry 8 }

cfprVnicIPv4PooledIscsiAddrSecDns OBJECT-TYPE
    SYNTAX       InetAddressIPv4
    MAX-ACCESS   read-only
    STATUS       current
    DESCRIPTION
        "Cisco Firepower vnic:IPv4PooledIscsiAddr:secDns
        managed object property"
    ::= { cfprVnicIPv4PooledIscsiAddrEntry 9 }

cfprVnicIPv4PooledIscsiAddrSubnet OBJECT-TYPE
    SYNTAX       InetAddressIPv4
    MAX-ACCESS   read-only
    STATUS       current
    DESCRIPTION
        "Cisco Firepower vnic:IPv4PooledIscsiAddr:subnet
        managed object property"
    ::= { cfprVnicIPv4PooledIscsiAddrEntry 10 }

cfprVnicIPv4StaticRouteTable OBJECT-TYPE
    SYNTAX           SEQUENCE OF CfprVnicIPv4StaticRouteEntry
    MAX-ACCESS       not-accessible
    STATUS           current
    DESCRIPTION
        "Cisco Firepower vnic:IPv4StaticRoute managed object table"
    ::= { cfprVnicObjects 26 }

cfprVnicIPv4StaticRouteEntry OBJECT-TYPE
    SYNTAX           CfprVnicIPv4StaticRouteEntry
    MAX-ACCESS       not-accessible
    STATUS           current
    DESCRIPTION
        "Entry for the cfprVnicIPv4StaticRouteTable table."
    INDEX { cfprVnicIPv4StaticRouteInstanceId }
    ::= { cfprVnicIPv4StaticRouteTable 1 }

CfprVnicIPv4StaticRouteEntry ::= SEQUENCE {
    cfprVnicIPv4StaticRouteInstanceId                                CfprManagedObjectId,
    cfprVnicIPv4StaticRouteDn                                        CfprManagedObjectDn,
    cfprVnicIPv4StaticRouteRn                                        SnmpAdminString,
    cfprVnicIPv4StaticRouteAddr                                      InetAddressIPv4,
    cfprVnicIPv4StaticRouteDefGw                                     InetAddressIPv4,
    cfprVnicIPv4StaticRouteGwAddr                                    InetAddressIPv4,
    cfprVnicIPv4StaticRouteGwSubnet                                  InetAddressIPv4,
    cfprVnicIPv4StaticRouteSubnet                                    InetAddressIPv4
}

cfprVnicIPv4StaticRouteInstanceId OBJECT-TYPE
    SYNTAX       CfprManagedObjectId
    MAX-ACCESS   not-accessible
    STATUS       current
    DESCRIPTION
        "Instance identifier of the managed object."
    ::= { cfprVnicIPv4StaticRouteEntry 1 }

cfprVnicIPv4StaticRouteDn OBJECT-TYPE
    SYNTAX       CfprManagedObjectDn
    MAX-ACCESS   read-only
    STATUS       current
    DESCRIPTION
        "Cisco Firepower vnic:IPv4StaticRoute:dn managed object property"
    ::= { cfprVnicIPv4StaticRouteEntry 2 }

cfprVnicIPv4StaticRouteRn OBJECT-TYPE
    SYNTAX       SnmpAdminString
    MAX-ACCESS   read-only
    STATUS       current
    DESCRIPTION
        "Cisco Firepower vnic:IPv4StaticRoute:rn managed object property"
    ::= { cfprVnicIPv4StaticRouteEntry 3 }

cfprVnicIPv4StaticRouteAddr OBJECT-TYPE
    SYNTAX       InetAddressIPv4
    MAX-ACCESS   read-only
    STATUS       current
    DESCRIPTION
        "Cisco Firepower vnic:IPv4StaticRoute:addr managed
        object property"
    ::= { cfprVnicIPv4StaticRouteEntry 4 }

cfprVnicIPv4StaticRouteDefGw OBJECT-TYPE
    SYNTAX       InetAddressIPv4
    MAX-ACCESS   read-only
    STATUS       current
    DESCRIPTION
        "Cisco Firepower vnic:IPv4StaticRoute:defGw managed
        object property"
    ::= { cfprVnicIPv4StaticRouteEntry 5 }

cfprVnicIPv4StaticRouteGwAddr OBJECT-TYPE
    SYNTAX       InetAddressIPv4
    MAX-ACCESS   read-only
    STATUS       current
    DESCRIPTION
        "Cisco Firepower vnic:IPv4StaticRoute:gwAddr managed
        object property"
    ::= { cfprVnicIPv4StaticRouteEntry 6 }

cfprVnicIPv4StaticRouteGwSubnet OBJECT-TYPE
    SYNTAX       InetAddressIPv4
    MAX-ACCESS   read-only
    STATUS       current
    DESCRIPTION
        "Cisco Firepower vnic:IPv4StaticRoute:gwSubnet
        managed object property"
    ::= { cfprVnicIPv4StaticRouteEntry 7 }

cfprVnicIPv4StaticRouteSubnet OBJECT-TYPE
    SYNTAX       InetAddressIPv4
    MAX-ACCESS   read-only
    STATUS       current
    DESCRIPTION
        "Cisco Firepower vnic:IPv4StaticRoute:subnet managed
        object property"
    ::= { cfprVnicIPv4StaticRouteEntry 8 }

cfprVnicIScsiTable OBJECT-TYPE
    SYNTAX           SEQUENCE OF CfprVnicIScsiEntry
    MAX-ACCESS       not-accessible
    STATUS           current
    DESCRIPTION
        "Cisco Firepower vnic:IScsi managed object table"
    ::= { cfprVnicObjects 27 }

cfprVnicIScsiEntry OBJECT-TYPE
    SYNTAX           CfprVnicIScsiEntry
    MAX-ACCESS       not-accessible
    STATUS           current
    DESCRIPTION
        "Entry for the cfprVnicIScsiTable table."
    INDEX { cfprVnicIScsiInstanceId }
    ::= { cfprVnicIScsiTable 1 }

CfprVnicIScsiEntry ::= SEQUENCE {
    cfprVnicIScsiInstanceId                                          CfprManagedObjectId,
    cfprVnicIScsiDn                                                  CfprManagedObjectDn,
    cfprVnicIScsiRn                                                  SnmpAdminString,
    cfprVnicIScsiAdaptorProfileName                                  SnmpAdminString,
    cfprVnicIScsiAddr                                                MacAddress,
    cfprVnicIScsiAdminHostPort                                       CfprFabricHostPortId,
    cfprVnicIScsiAdminVcon                                           SnmpAdminString,
    cfprVnicIScsiAppRole                                             CfprVnicAppRole,
    cfprVnicIScsiAuthProfileName                                     SnmpAdminString,
    cfprVnicIScsiBootDev                                             CfprVnicVnicBootDev,
    cfprVnicIScsiConfigQualifier                                     CfprVnicConfigIssues,
    cfprVnicIScsiConfigState                                         CfprLsConfigState,
    cfprVnicIScsiEquipmentDn                                         SnmpAdminString,
    cfprVnicIScsiEthEpDn                                             SnmpAdminString,
    cfprVnicIScsiExtIPState                                          CfprVnicExternalMgmtIPMode,
    cfprVnicIScsiFltAggr                                             Unsigned64,
    cfprVnicIScsiIdentPoolName                                       SnmpAdminString,
    cfprVnicIScsiInitNameSuffix                                      SnmpAdminString,
    cfprVnicIScsiInitiatorName                                       SnmpAdminString,
    cfprVnicIScsiInstType                                            CfprVnicInstantiation,
    cfprVnicIScsiIqnIdentPoolName                                    SnmpAdminString,
    cfprVnicIScsiName                                                SnmpAdminString,
    cfprVnicIScsiNwTemplName                                         SnmpAdminString,
    cfprVnicIScsiOperAdaptorProfileName                              SnmpAdminString,
    cfprVnicIScsiOperAuthProfileName                                 SnmpAdminString,
    cfprVnicIScsiOperHostPort                                        CfprVnicVnicOperHostPort,
    cfprVnicIScsiOperIdentPoolName                                   SnmpAdminString,
    cfprVnicIScsiOperIqnIdentPoolName                                SnmpAdminString,
    cfprVnicIScsiOperOrder                                           Gauge32,
    cfprVnicIScsiOperSpeed                                           Gauge32,
    cfprVnicIScsiOperStatsPolicyName                                 SnmpAdminString,
    cfprVnicIScsiOperVcon                                            SnmpAdminString,
    cfprVnicIScsiOrder                                               Gauge32,
    cfprVnicIScsiOwner                                               CfprVnicConnectionOwner,
    cfprVnicIScsiPinToGroupName                                      SnmpAdminString,
    cfprVnicIScsiQosPolicyName                                       SnmpAdminString,
    cfprVnicIScsiStatsPolicyName                                     SnmpAdminString,
    cfprVnicIScsiSwitchId                                            CfprNetworkSwitchId,
    cfprVnicIScsiType                                                CfprVnicConnectionType,
    cfprVnicIScsiVnicDefType                                         CfprVnicIScsiIfDefType,
    cfprVnicIScsiVnicName                                            SnmpAdminString
}

cfprVnicIScsiInstanceId OBJECT-TYPE
    SYNTAX       CfprManagedObjectId
    MAX-ACCESS   not-accessible
    STATUS       current
    DESCRIPTION
        "Instance identifier of the managed object."
    ::= { cfprVnicIScsiEntry 1 }

cfprVnicIScsiDn OBJECT-TYPE
    SYNTAX       CfprManagedObjectDn
    MAX-ACCESS   read-only
    STATUS       current
    DESCRIPTION
        "Cisco Firepower vnic:IScsi:dn managed object property"
    ::= { cfprVnicIScsiEntry 2 }

cfprVnicIScsiRn OBJECT-TYPE
    SYNTAX       SnmpAdminString
    MAX-ACCESS   read-only
    STATUS       current
    DESCRIPTION
        "Cisco Firepower vnic:IScsi:rn managed object property"
    ::= { cfprVnicIScsiEntry 3 }

cfprVnicIScsiAdaptorProfileName OBJECT-TYPE
    SYNTAX       SnmpAdminString
    MAX-ACCESS   read-only
    STATUS       current
    DESCRIPTION
        "Cisco Firepower vnic:IScsi:adaptorProfileName
        managed object property"
    ::= { cfprVnicIScsiEntry 4 }

cfprVnicIScsiAddr OBJECT-TYPE
    SYNTAX       MacAddress
    MAX-ACCESS   read-only
    STATUS       current
    DESCRIPTION
        "Cisco Firepower vnic:IScsi:addr managed object property"
    ::= { cfprVnicIScsiEntry 5 }

cfprVnicIScsiAdminHostPort OBJECT-TYPE
    SYNTAX       CfprFabricHostPortId
    MAX-ACCESS   read-only
    STATUS       current
    DESCRIPTION
        "Cisco Firepower vnic:IScsi:adminHostPort managed object property"
    ::= { cfprVnicIScsiEntry 6 }

cfprVnicIScsiAdminVcon OBJECT-TYPE
    SYNTAX       SnmpAdminString
    MAX-ACCESS   read-only
    STATUS       current
    DESCRIPTION
        "Cisco Firepower vnic:IScsi:adminVcon managed object property"
    ::= { cfprVnicIScsiEntry 7 }

cfprVnicIScsiAppRole OBJECT-TYPE
    SYNTAX       CfprVnicAppRole
    MAX-ACCESS   read-only
    STATUS       current
    DESCRIPTION
        "Cisco Firepower vnic:IScsi:appRole managed object property"
    ::= { cfprVnicIScsiEntry 8 }

cfprVnicIScsiAuthProfileName OBJECT-TYPE
    SYNTAX       SnmpAdminString
    MAX-ACCESS   read-only
    STATUS       current
    DESCRIPTION
        "Cisco Firepower vnic:IScsi:authProfileName managed
        object property"
    ::= { cfprVnicIScsiEntry 9 }

cfprVnicIScsiBootDev OBJECT-TYPE
    SYNTAX       CfprVnicVnicBootDev
    MAX-ACCESS   read-only
    STATUS       current
    DESCRIPTION
        "Cisco Firepower vnic:IScsi:bootDev managed object property"
    ::= { cfprVnicIScsiEntry 10 }

cfprVnicIScsiConfigQualifier OBJECT-TYPE
    SYNTAX       CfprVnicConfigIssues
    MAX-ACCESS   read-only
    STATUS       current
    DESCRIPTION
        "Cisco Firepower vnic:IScsi:configQualifier managed
        object property"
    ::= { cfprVnicIScsiEntry 11 }

cfprVnicIScsiConfigState OBJECT-TYPE
    SYNTAX       CfprLsConfigState
    MAX-ACCESS   read-only
    STATUS       current
    DESCRIPTION
        "Cisco Firepower vnic:IScsi:configState managed object property"
    ::= { cfprVnicIScsiEntry 12 }

cfprVnicIScsiEquipmentDn OBJECT-TYPE
    SYNTAX       SnmpAdminString
    MAX-ACCESS   read-only
    STATUS       current
    DESCRIPTION
        "Cisco Firepower vnic:IScsi:equipmentDn managed object property"
    ::= { cfprVnicIScsiEntry 13 }

cfprVnicIScsiEthEpDn OBJECT-TYPE
    SYNTAX       SnmpAdminString
    MAX-ACCESS   read-only
    STATUS       current
    DESCRIPTION
        "Cisco Firepower vnic:IScsi:ethEpDn managed object property"
    ::= { cfprVnicIScsiEntry 14 }

cfprVnicIScsiExtIPState OBJECT-TYPE
    SYNTAX       CfprVnicExternalMgmtIPMode
    MAX-ACCESS   read-only
    STATUS       current
    DESCRIPTION
        "Cisco Firepower vnic:IScsi:extIPState managed object property"
    ::= { cfprVnicIScsiEntry 15 }

cfprVnicIScsiFltAggr OBJECT-TYPE
    SYNTAX       Unsigned64
    MAX-ACCESS   read-only
    STATUS       current
    DESCRIPTION
        "Cisco Firepower vnic:IScsi:fltAggr managed object property"
    ::= { cfprVnicIScsiEntry 16 }

cfprVnicIScsiIdentPoolName OBJECT-TYPE
    SYNTAX       SnmpAdminString
    MAX-ACCESS   read-only
    STATUS       current
    DESCRIPTION
        "Cisco Firepower vnic:IScsi:identPoolName managed object property"
    ::= { cfprVnicIScsiEntry 17 }

cfprVnicIScsiInitNameSuffix OBJECT-TYPE
    SYNTAX       SnmpAdminString
    MAX-ACCESS   read-only
    STATUS       current
    DESCRIPTION
        "Cisco Firepower vnic:IScsi:initNameSuffix managed
        object property"
    ::= { cfprVnicIScsiEntry 18 }

cfprVnicIScsiInitiatorName OBJECT-TYPE
    SYNTAX       SnmpAdminString
    MAX-ACCESS   read-only
    STATUS       current
    DESCRIPTION
        "Cisco Firepower vnic:IScsi:initiatorName managed object property"
    ::= { cfprVnicIScsiEntry 19 }

cfprVnicIScsiInstType OBJECT-TYPE
    SYNTAX       CfprVnicInstantiation
    MAX-ACCESS   read-only
    STATUS       current
    DESCRIPTION
        "Cisco Firepower vnic:IScsi:instType managed object property"
    ::= { cfprVnicIScsiEntry 20 }

cfprVnicIScsiIqnIdentPoolName OBJECT-TYPE
    SYNTAX       SnmpAdminString
    MAX-ACCESS   read-only
    STATUS       current
    DESCRIPTION
        "Cisco Firepower vnic:IScsi:iqnIdentPoolName managed
        object property"
    ::= { cfprVnicIScsiEntry 21 }

cfprVnicIScsiName OBJECT-TYPE
    SYNTAX       SnmpAdminString
    MAX-ACCESS   read-only
    STATUS       current
    DESCRIPTION
        "Cisco Firepower vnic:IScsi:name managed object property"
    ::= { cfprVnicIScsiEntry 22 }

cfprVnicIScsiNwTemplName OBJECT-TYPE
    SYNTAX       SnmpAdminString
    MAX-ACCESS   read-only
    STATUS       current
    DESCRIPTION
        "Cisco Firepower vnic:IScsi:nwTemplName managed object property"
    ::= { cfprVnicIScsiEntry 23 }

cfprVnicIScsiOperAdaptorProfileName OBJECT-TYPE
    SYNTAX       SnmpAdminString
    MAX-ACCESS   read-only
    STATUS       current
    DESCRIPTION
        "Cisco Firepower vnic:IScsi:operAdaptorProfileName
        managed object property"
    ::= { cfprVnicIScsiEntry 24 }

cfprVnicIScsiOperAuthProfileName OBJECT-TYPE
    SYNTAX       SnmpAdminString
    MAX-ACCESS   read-only
    STATUS       current
    DESCRIPTION
        "Cisco Firepower vnic:IScsi:operAuthProfileName
        managed object property"
    ::= { cfprVnicIScsiEntry 25 }

cfprVnicIScsiOperHostPort OBJECT-TYPE
    SYNTAX       CfprVnicVnicOperHostPort
    MAX-ACCESS   read-only
    STATUS       current
    DESCRIPTION
        "Cisco Firepower vnic:IScsi:operHostPort managed object property"
    ::= { cfprVnicIScsiEntry 26 }

cfprVnicIScsiOperIdentPoolName OBJECT-TYPE
    SYNTAX       SnmpAdminString
    MAX-ACCESS   read-only
    STATUS       current
    DESCRIPTION
        "Cisco Firepower vnic:IScsi:operIdentPoolName managed
        object property"
    ::= { cfprVnicIScsiEntry 27 }

cfprVnicIScsiOperIqnIdentPoolName OBJECT-TYPE
    SYNTAX       SnmpAdminString
    MAX-ACCESS   read-only
    STATUS       current
    DESCRIPTION
        "Cisco Firepower vnic:IScsi:operIqnIdentPoolName
        managed object property"
    ::= { cfprVnicIScsiEntry 28 }

cfprVnicIScsiOperOrder OBJECT-TYPE
    SYNTAX       Gauge32
    MAX-ACCESS   read-only
    STATUS       current
    DESCRIPTION
        "Cisco Firepower vnic:IScsi:operOrder managed object property"
    ::= { cfprVnicIScsiEntry 29 }

cfprVnicIScsiOperSpeed OBJECT-TYPE
    SYNTAX       Gauge32
    MAX-ACCESS   read-only
    STATUS       current
    DESCRIPTION
        "Cisco Firepower vnic:IScsi:operSpeed managed object property"
    ::= { cfprVnicIScsiEntry 30 }

cfprVnicIScsiOperStatsPolicyName OBJECT-TYPE
    SYNTAX       SnmpAdminString
    MAX-ACCESS   read-only
    STATUS       current
    DESCRIPTION
        "Cisco Firepower vnic:IScsi:operStatsPolicyName
        managed object property"
    ::= { cfprVnicIScsiEntry 31 }

cfprVnicIScsiOperVcon OBJECT-TYPE
    SYNTAX       SnmpAdminString
    MAX-ACCESS   read-only
    STATUS       current
    DESCRIPTION
        "Cisco Firepower vnic:IScsi:operVcon managed object property"
    ::= { cfprVnicIScsiEntry 32 }

cfprVnicIScsiOrder OBJECT-TYPE
    SYNTAX       Gauge32
    MAX-ACCESS   read-only
    STATUS       current
    DESCRIPTION
        "Cisco Firepower vnic:IScsi:order managed object property"
    ::= { cfprVnicIScsiEntry 33 }

cfprVnicIScsiOwner OBJECT-TYPE
    SYNTAX       CfprVnicConnectionOwner
    MAX-ACCESS   read-only
    STATUS       current
    DESCRIPTION
        "Cisco Firepower vnic:IScsi:owner managed object property"
    ::= { cfprVnicIScsiEntry 34 }

cfprVnicIScsiPinToGroupName OBJECT-TYPE
    SYNTAX       SnmpAdminString
    MAX-ACCESS   read-only
    STATUS       current
    DESCRIPTION
        "Cisco Firepower vnic:IScsi:pinToGroupName managed
        object property"
    ::= { cfprVnicIScsiEntry 35 }

cfprVnicIScsiQosPolicyName OBJECT-TYPE
    SYNTAX       SnmpAdminString
    MAX-ACCESS   read-only
    STATUS       current
    DESCRIPTION
        "Cisco Firepower vnic:IScsi:qosPolicyName managed object property"
    ::= { cfprVnicIScsiEntry 36 }

cfprVnicIScsiStatsPolicyName OBJECT-TYPE
    SYNTAX       SnmpAdminString
    MAX-ACCESS   read-only
    STATUS       current
    DESCRIPTION
        "Cisco Firepower vnic:IScsi:statsPolicyName managed
        object property"
    ::= { cfprVnicIScsiEntry 37 }

cfprVnicIScsiSwitchId OBJECT-TYPE
    SYNTAX       CfprNetworkSwitchId
    MAX-ACCESS   read-only
    STATUS       current
    DESCRIPTION
        "Cisco Firepower vnic:IScsi:switchId managed object property"
    ::= { cfprVnicIScsiEntry 38 }

cfprVnicIScsiType OBJECT-TYPE
    SYNTAX       CfprVnicConnectionType
    MAX-ACCESS   read-only
    STATUS       current
    DESCRIPTION
        "Cisco Firepower vnic:IScsi:type managed object property"
    ::= { cfprVnicIScsiEntry 39 }

cfprVnicIScsiVnicDefType OBJECT-TYPE
    SYNTAX       CfprVnicIScsiIfDefType
    MAX-ACCESS   read-only
    STATUS       current
    DESCRIPTION
        "Cisco Firepower vnic:IScsi:vnicDefType managed object property"
    ::= { cfprVnicIScsiEntry 40 }

cfprVnicIScsiVnicName OBJECT-TYPE
    SYNTAX       SnmpAdminString
    MAX-ACCESS   read-only
    STATUS       current
    DESCRIPTION
        "Cisco Firepower vnic:IScsi:vnicName managed object property"
    ::= { cfprVnicIScsiEntry 41 }

cfprVnicIScsiAutoTargetIfTable OBJECT-TYPE
    SYNTAX           SEQUENCE OF CfprVnicIScsiAutoTargetIfEntry
    MAX-ACCESS       not-accessible
    STATUS           current
    DESCRIPTION
        "Cisco Firepower vnic:IScsiAutoTargetIf managed object table"
    ::= { cfprVnicObjects 28 }

cfprVnicIScsiAutoTargetIfEntry OBJECT-TYPE
    SYNTAX           CfprVnicIScsiAutoTargetIfEntry
    MAX-ACCESS       not-accessible
    STATUS           current
    DESCRIPTION
        "Entry for the cfprVnicIScsiAutoTargetIfTable table."
    INDEX { cfprVnicIScsiAutoTargetIfInstanceId }
    ::= { cfprVnicIScsiAutoTargetIfTable 1 }

CfprVnicIScsiAutoTargetIfEntry ::= SEQUENCE {
    cfprVnicIScsiAutoTargetIfInstanceId                              CfprManagedObjectId,
    cfprVnicIScsiAutoTargetIfDn                                      CfprManagedObjectDn,
    cfprVnicIScsiAutoTargetIfRn                                      SnmpAdminString,
    cfprVnicIScsiAutoTargetIfDhcpVendorId                            SnmpAdminString
}

cfprVnicIScsiAutoTargetIfInstanceId OBJECT-TYPE
    SYNTAX       CfprManagedObjectId
    MAX-ACCESS   not-accessible
    STATUS       current
    DESCRIPTION
        "Instance identifier of the managed object."
    ::= { cfprVnicIScsiAutoTargetIfEntry 1 }

cfprVnicIScsiAutoTargetIfDn OBJECT-TYPE
    SYNTAX       CfprManagedObjectDn
    MAX-ACCESS   read-only
    STATUS       current
    DESCRIPTION
        "Cisco Firepower vnic:IScsiAutoTargetIf:dn managed
        object property"
    ::= { cfprVnicIScsiAutoTargetIfEntry 2 }

cfprVnicIScsiAutoTargetIfRn OBJECT-TYPE
    SYNTAX       SnmpAdminString
    MAX-ACCESS   read-only
    STATUS       current
    DESCRIPTION
        "Cisco Firepower vnic:IScsiAutoTargetIf:rn managed
        object property"
    ::= { cfprVnicIScsiAutoTargetIfEntry 3 }

cfprVnicIScsiAutoTargetIfDhcpVendorId OBJECT-TYPE
    SYNTAX       SnmpAdminString
    MAX-ACCESS   read-only
    STATUS       current
    DESCRIPTION
        "Cisco Firepower vnic:IScsiAutoTargetIf:dhcpVendorId
        managed object property"
    ::= { cfprVnicIScsiAutoTargetIfEntry 4 }

cfprVnicIScsiBootParamsTable OBJECT-TYPE
    SYNTAX           SEQUENCE OF CfprVnicIScsiBootParamsEntry
    MAX-ACCESS       not-accessible
    STATUS           current
    DESCRIPTION
        "Cisco Firepower vnic:IScsiBootParams managed object table"
    ::= { cfprVnicObjects 29 }

cfprVnicIScsiBootParamsEntry OBJECT-TYPE
    SYNTAX           CfprVnicIScsiBootParamsEntry
    MAX-ACCESS       not-accessible
    STATUS           current
    DESCRIPTION
        "Entry for the cfprVnicIScsiBootParamsTable table."
    INDEX { cfprVnicIScsiBootParamsInstanceId }
    ::= { cfprVnicIScsiBootParamsTable 1 }

CfprVnicIScsiBootParamsEntry ::= SEQUENCE {
    cfprVnicIScsiBootParamsInstanceId                                CfprManagedObjectId,
    cfprVnicIScsiBootParamsDn                                        CfprManagedObjectDn,
    cfprVnicIScsiBootParamsRn                                        SnmpAdminString,
    cfprVnicIScsiBootParamsDescr                                     SnmpAdminString,
    cfprVnicIScsiBootParamsIntId                                     SnmpAdminString,
    cfprVnicIScsiBootParamsName                                      SnmpAdminString,
    cfprVnicIScsiBootParamsPolicyLevel                               Gauge32,
    cfprVnicIScsiBootParamsPolicyOwner                               CfprPolicyPolicyOwner
}

cfprVnicIScsiBootParamsInstanceId OBJECT-TYPE
    SYNTAX       CfprManagedObjectId
    MAX-ACCESS   not-accessible
    STATUS       current
    DESCRIPTION
        "Instance identifier of the managed object."
    ::= { cfprVnicIScsiBootParamsEntry 1 }

cfprVnicIScsiBootParamsDn OBJECT-TYPE
    SYNTAX       CfprManagedObjectDn
    MAX-ACCESS   read-only
    STATUS       current
    DESCRIPTION
        "Cisco Firepower vnic:IScsiBootParams:dn managed object property"
    ::= { cfprVnicIScsiBootParamsEntry 2 }

cfprVnicIScsiBootParamsRn OBJECT-TYPE
    SYNTAX       SnmpAdminString
    MAX-ACCESS   read-only
    STATUS       current
    DESCRIPTION
        "Cisco Firepower vnic:IScsiBootParams:rn managed object property"
    ::= { cfprVnicIScsiBootParamsEntry 3 }

cfprVnicIScsiBootParamsDescr OBJECT-TYPE
    SYNTAX       SnmpAdminString
    MAX-ACCESS   read-only
    STATUS       current
    DESCRIPTION
        "Cisco Firepower vnic:IScsiBootParams:descr managed
        object property"
    ::= { cfprVnicIScsiBootParamsEntry 4 }

cfprVnicIScsiBootParamsIntId OBJECT-TYPE
    SYNTAX       SnmpAdminString
    MAX-ACCESS   read-only
    STATUS       current
    DESCRIPTION
        "Cisco Firepower vnic:IScsiBootParams:intId managed
        object property"
    ::= { cfprVnicIScsiBootParamsEntry 5 }

cfprVnicIScsiBootParamsName OBJECT-TYPE
    SYNTAX       SnmpAdminString
    MAX-ACCESS   read-only
    STATUS       current
    DESCRIPTION
        "Cisco Firepower vnic:IScsiBootParams:name managed
        object property"
    ::= { cfprVnicIScsiBootParamsEntry 6 }

cfprVnicIScsiBootParamsPolicyLevel OBJECT-TYPE
    SYNTAX       Gauge32
    MAX-ACCESS   read-only
    STATUS       current
    DESCRIPTION
        "Cisco Firepower vnic:IScsiBootParams:policyLevel
        managed object property"
    ::= { cfprVnicIScsiBootParamsEntry 7 }

cfprVnicIScsiBootParamsPolicyOwner OBJECT-TYPE
    SYNTAX       CfprPolicyPolicyOwner
    MAX-ACCESS   read-only
    STATUS       current
    DESCRIPTION
        "Cisco Firepower vnic:IScsiBootParams:policyOwner
        managed object property"
    ::= { cfprVnicIScsiBootParamsEntry 8 }

cfprVnicIScsiBootVnicTable OBJECT-TYPE
    SYNTAX           SEQUENCE OF CfprVnicIScsiBootVnicEntry
    MAX-ACCESS       not-accessible
    STATUS           current
    DESCRIPTION
        "Cisco Firepower vnic:IScsiBootVnic managed object table"
    ::= { cfprVnicObjects 30 }

cfprVnicIScsiBootVnicEntry OBJECT-TYPE
    SYNTAX           CfprVnicIScsiBootVnicEntry
    MAX-ACCESS       not-accessible
    STATUS           current
    DESCRIPTION
        "Entry for the cfprVnicIScsiBootVnicTable table."
    INDEX { cfprVnicIScsiBootVnicInstanceId }
    ::= { cfprVnicIScsiBootVnicTable 1 }

CfprVnicIScsiBootVnicEntry ::= SEQUENCE {
    cfprVnicIScsiBootVnicInstanceId                                  CfprManagedObjectId,
    cfprVnicIScsiBootVnicDn                                          CfprManagedObjectDn,
    cfprVnicIScsiBootVnicRn                                          SnmpAdminString,
    cfprVnicIScsiBootVnicAuthProfileName                             SnmpAdminString,
    cfprVnicIScsiBootVnicDescr                                       SnmpAdminString,
    cfprVnicIScsiBootVnicInitiatorName                               SnmpAdminString,
    cfprVnicIScsiBootVnicIntId                                       SnmpAdminString,
    cfprVnicIScsiBootVnicIqnIdentPoolName                            SnmpAdminString,
    cfprVnicIScsiBootVnicName                                        SnmpAdminString,
    cfprVnicIScsiBootVnicOperAuthProfileName                         SnmpAdminString,
    cfprVnicIScsiBootVnicOperIqnIdentPoolName                        SnmpAdminString,
    cfprVnicIScsiBootVnicPolicyLevel                                 Gauge32,
    cfprVnicIScsiBootVnicPolicyOwner                                 CfprPolicyPolicyOwner
}

cfprVnicIScsiBootVnicInstanceId OBJECT-TYPE
    SYNTAX       CfprManagedObjectId
    MAX-ACCESS   not-accessible
    STATUS       current
    DESCRIPTION
        "Instance identifier of the managed object."
    ::= { cfprVnicIScsiBootVnicEntry 1 }

cfprVnicIScsiBootVnicDn OBJECT-TYPE
    SYNTAX       CfprManagedObjectDn
    MAX-ACCESS   read-only
    STATUS       current
    DESCRIPTION
        "Cisco Firepower vnic:IScsiBootVnic:dn managed object property"
    ::= { cfprVnicIScsiBootVnicEntry 2 }

cfprVnicIScsiBootVnicRn OBJECT-TYPE
    SYNTAX       SnmpAdminString
    MAX-ACCESS   read-only
    STATUS       current
    DESCRIPTION
        "Cisco Firepower vnic:IScsiBootVnic:rn managed object property"
    ::= { cfprVnicIScsiBootVnicEntry 3 }

cfprVnicIScsiBootVnicAuthProfileName OBJECT-TYPE
    SYNTAX       SnmpAdminString
    MAX-ACCESS   read-only
    STATUS       current
    DESCRIPTION
        "Cisco Firepower vnic:IScsiBootVnic:authProfileName
        managed object property"
    ::= { cfprVnicIScsiBootVnicEntry 4 }

cfprVnicIScsiBootVnicDescr OBJECT-TYPE
    SYNTAX       SnmpAdminString
    MAX-ACCESS   read-only
    STATUS       current
    DESCRIPTION
        "Cisco Firepower vnic:IScsiBootVnic:descr managed object property"
    ::= { cfprVnicIScsiBootVnicEntry 5 }

cfprVnicIScsiBootVnicInitiatorName OBJECT-TYPE
    SYNTAX       SnmpAdminString
    MAX-ACCESS   read-only
    STATUS       current
    DESCRIPTION
        "Cisco Firepower vnic:IScsiBootVnic:initiatorName
        managed object property"
    ::= { cfprVnicIScsiBootVnicEntry 6 }

cfprVnicIScsiBootVnicIntId OBJECT-TYPE
    SYNTAX       SnmpAdminString
    MAX-ACCESS   read-only
    STATUS       current
    DESCRIPTION
        "Cisco Firepower vnic:IScsiBootVnic:intId managed object property"
    ::= { cfprVnicIScsiBootVnicEntry 7 }

cfprVnicIScsiBootVnicIqnIdentPoolName OBJECT-TYPE
    SYNTAX       SnmpAdminString
    MAX-ACCESS   read-only
    STATUS       current
    DESCRIPTION
        "Cisco Firepower vnic:IScsiBootVnic:iqnIdentPoolName
        managed object property"
    ::= { cfprVnicIScsiBootVnicEntry 8 }

cfprVnicIScsiBootVnicName OBJECT-TYPE
    SYNTAX       SnmpAdminString
    MAX-ACCESS   read-only
    STATUS       current
    DESCRIPTION
        "Cisco Firepower vnic:IScsiBootVnic:name managed object property"
    ::= { cfprVnicIScsiBootVnicEntry 9 }

cfprVnicIScsiBootVnicOperAuthProfileName OBJECT-TYPE
    SYNTAX       SnmpAdminString
    MAX-ACCESS   read-only
    STATUS       current
    DESCRIPTION
        "Cisco Firepower vnic:IScsiBootVnic:operAuthProfileName
        managed object property"
    ::= { cfprVnicIScsiBootVnicEntry 10 }

cfprVnicIScsiBootVnicOperIqnIdentPoolName OBJECT-TYPE
    SYNTAX       SnmpAdminString
    MAX-ACCESS   read-only
    STATUS       current
    DESCRIPTION
        "Cisco Firepower vnic:IScsiBootVnic:operIqnIdentPoolName
        managed object property"
    ::= { cfprVnicIScsiBootVnicEntry 11 }

cfprVnicIScsiBootVnicPolicyLevel OBJECT-TYPE
    SYNTAX       Gauge32
    MAX-ACCESS   read-only
    STATUS       current
    DESCRIPTION
        "Cisco Firepower vnic:IScsiBootVnic:policyLevel
        managed object property"
    ::= { cfprVnicIScsiBootVnicEntry 12 }

cfprVnicIScsiBootVnicPolicyOwner OBJECT-TYPE
    SYNTAX       CfprPolicyPolicyOwner
    MAX-ACCESS   read-only
    STATUS       current
    DESCRIPTION
        "Cisco Firepower vnic:IScsiBootVnic:policyOwner
        managed object property"
    ::= { cfprVnicIScsiBootVnicEntry 13 }

cfprVnicIScsiLCPTable OBJECT-TYPE
    SYNTAX           SEQUENCE OF CfprVnicIScsiLCPEntry
    MAX-ACCESS       not-accessible
    STATUS           current
    DESCRIPTION
        "Cisco Firepower vnic:IScsiLCP managed object table"
    ::= { cfprVnicObjects 31 }

cfprVnicIScsiLCPEntry OBJECT-TYPE
    SYNTAX           CfprVnicIScsiLCPEntry
    MAX-ACCESS       not-accessible
    STATUS           current
    DESCRIPTION
        "Entry for the cfprVnicIScsiLCPTable table."
    INDEX { cfprVnicIScsiLCPInstanceId }
    ::= { cfprVnicIScsiLCPTable 1 }

CfprVnicIScsiLCPEntry ::= SEQUENCE {
    cfprVnicIScsiLCPInstanceId                                       CfprManagedObjectId,
    cfprVnicIScsiLCPDn                                               CfprManagedObjectDn,
    cfprVnicIScsiLCPRn                                               SnmpAdminString,
    cfprVnicIScsiLCPAdaptorProfileName                               SnmpAdminString,
    cfprVnicIScsiLCPAddr                                             MacAddress,
    cfprVnicIScsiLCPAdminHostPort                                    CfprFabricHostPortId,
    cfprVnicIScsiLCPAdminVcon                                        SnmpAdminString,
    cfprVnicIScsiLCPAppRole                                          CfprVnicAppRole,
    cfprVnicIScsiLCPBootDev                                          CfprVnicVnicBootDev,
    cfprVnicIScsiLCPConfigQualifier                                  CfprVnicConfigIssues,
    cfprVnicIScsiLCPConfigState                                      CfprLsConfigState,
    cfprVnicIScsiLCPEquipmentDn                                      SnmpAdminString,
    cfprVnicIScsiLCPFltAggr                                          Unsigned64,
    cfprVnicIScsiLCPIdentPoolName                                    SnmpAdminString,
    cfprVnicIScsiLCPInstType                                         CfprVnicInstantiation,
    cfprVnicIScsiLCPName                                             SnmpAdminString,
    cfprVnicIScsiLCPNwTemplName                                      SnmpAdminString,
    cfprVnicIScsiLCPOperAdaptorProfileName                           SnmpAdminString,
    cfprVnicIScsiLCPOperHostPort                                     CfprVnicVnicOperHostPort,
    cfprVnicIScsiLCPOperIdentPoolName                                SnmpAdminString,
    cfprVnicIScsiLCPOperOrder                                        Gauge32,
    cfprVnicIScsiLCPOperSpeed                                        Gauge32,
    cfprVnicIScsiLCPOperStatsPolicyName                              SnmpAdminString,
    cfprVnicIScsiLCPOperVcon                                         SnmpAdminString,
    cfprVnicIScsiLCPOrder                                            Gauge32,
    cfprVnicIScsiLCPOwner                                            CfprVnicConnectionOwner,
    cfprVnicIScsiLCPPinToGroupName                                   SnmpAdminString,
    cfprVnicIScsiLCPQosPolicyName                                    SnmpAdminString,
    cfprVnicIScsiLCPStatsPolicyName                                  SnmpAdminString,
    cfprVnicIScsiLCPSwitchId                                         CfprNetworkSwitchId,
    cfprVnicIScsiLCPType                                             CfprVnicConnectionType,
    cfprVnicIScsiLCPVnicName                                         SnmpAdminString
}

cfprVnicIScsiLCPInstanceId OBJECT-TYPE
    SYNTAX       CfprManagedObjectId
    MAX-ACCESS   not-accessible
    STATUS       current
    DESCRIPTION
        "Instance identifier of the managed object."
    ::= { cfprVnicIScsiLCPEntry 1 }

cfprVnicIScsiLCPDn OBJECT-TYPE
    SYNTAX       CfprManagedObjectDn
    MAX-ACCESS   read-only
    STATUS       current
    DESCRIPTION
        "Cisco Firepower vnic:IScsiLCP:dn managed object property"
    ::= { cfprVnicIScsiLCPEntry 2 }

cfprVnicIScsiLCPRn OBJECT-TYPE
    SYNTAX       SnmpAdminString
    MAX-ACCESS   read-only
    STATUS       current
    DESCRIPTION
        "Cisco Firepower vnic:IScsiLCP:rn managed object property"
    ::= { cfprVnicIScsiLCPEntry 3 }

cfprVnicIScsiLCPAdaptorProfileName OBJECT-TYPE
    SYNTAX       SnmpAdminString
    MAX-ACCESS   read-only
    STATUS       current
    DESCRIPTION
        "Cisco Firepower vnic:IScsiLCP:adaptorProfileName
        managed object property"
    ::= { cfprVnicIScsiLCPEntry 4 }

cfprVnicIScsiLCPAddr OBJECT-TYPE
    SYNTAX       MacAddress
    MAX-ACCESS   read-only
    STATUS       current
    DESCRIPTION
        "Cisco Firepower vnic:IScsiLCP:addr managed object property"
    ::= { cfprVnicIScsiLCPEntry 5 }

cfprVnicIScsiLCPAdminHostPort OBJECT-TYPE
    SYNTAX       CfprFabricHostPortId
    MAX-ACCESS   read-only
    STATUS       current
    DESCRIPTION
        "Cisco Firepower vnic:IScsiLCP:adminHostPort managed
        object property"
    ::= { cfprVnicIScsiLCPEntry 6 }

cfprVnicIScsiLCPAdminVcon OBJECT-TYPE
    SYNTAX       SnmpAdminString
    MAX-ACCESS   read-only
    STATUS       current
    DESCRIPTION
        "Cisco Firepower vnic:IScsiLCP:adminVcon managed object property"
    ::= { cfprVnicIScsiLCPEntry 7 }

cfprVnicIScsiLCPAppRole OBJECT-TYPE
    SYNTAX       CfprVnicAppRole
    MAX-ACCESS   read-only
    STATUS       current
    DESCRIPTION
        "Cisco Firepower vnic:IScsiLCP:appRole managed object property"
    ::= { cfprVnicIScsiLCPEntry 8 }

cfprVnicIScsiLCPBootDev OBJECT-TYPE
    SYNTAX       CfprVnicVnicBootDev
    MAX-ACCESS   read-only
    STATUS       current
    DESCRIPTION
        "Cisco Firepower vnic:IScsiLCP:bootDev managed object property"
    ::= { cfprVnicIScsiLCPEntry 9 }

cfprVnicIScsiLCPConfigQualifier OBJECT-TYPE
    SYNTAX       CfprVnicConfigIssues
    MAX-ACCESS   read-only
    STATUS       current
    DESCRIPTION
        "Cisco Firepower vnic:IScsiLCP:configQualifier
        managed object property"
    ::= { cfprVnicIScsiLCPEntry 10 }

cfprVnicIScsiLCPConfigState OBJECT-TYPE
    SYNTAX       CfprLsConfigState
    MAX-ACCESS   read-only
    STATUS       current
    DESCRIPTION
        "Cisco Firepower vnic:IScsiLCP:configState managed
        object property"
    ::= { cfprVnicIScsiLCPEntry 11 }

cfprVnicIScsiLCPEquipmentDn OBJECT-TYPE
    SYNTAX       SnmpAdminString
    MAX-ACCESS   read-only
    STATUS       current
    DESCRIPTION
        "Cisco Firepower vnic:IScsiLCP:equipmentDn managed
        object property"
    ::= { cfprVnicIScsiLCPEntry 12 }

cfprVnicIScsiLCPFltAggr OBJECT-TYPE
    SYNTAX       Unsigned64
    MAX-ACCESS   read-only
    STATUS       current
    DESCRIPTION
        "Cisco Firepower vnic:IScsiLCP:fltAggr managed object property"
    ::= { cfprVnicIScsiLCPEntry 13 }

cfprVnicIScsiLCPIdentPoolName OBJECT-TYPE
    SYNTAX       SnmpAdminString
    MAX-ACCESS   read-only
    STATUS       current
    DESCRIPTION
        "Cisco Firepower vnic:IScsiLCP:identPoolName managed
        object property"
    ::= { cfprVnicIScsiLCPEntry 14 }

cfprVnicIScsiLCPInstType OBJECT-TYPE
    SYNTAX       CfprVnicInstantiation
    MAX-ACCESS   read-only
    STATUS       current
    DESCRIPTION
        "Cisco Firepower vnic:IScsiLCP:instType managed object property"
    ::= { cfprVnicIScsiLCPEntry 15 }

cfprVnicIScsiLCPName OBJECT-TYPE
    SYNTAX       SnmpAdminString
    MAX-ACCESS   read-only
    STATUS       current
    DESCRIPTION
        "Cisco Firepower vnic:IScsiLCP:name managed object property"
    ::= { cfprVnicIScsiLCPEntry 16 }

cfprVnicIScsiLCPNwTemplName OBJECT-TYPE
    SYNTAX       SnmpAdminString
    MAX-ACCESS   read-only
    STATUS       current
    DESCRIPTION
        "Cisco Firepower vnic:IScsiLCP:nwTemplName managed
        object property"
    ::= { cfprVnicIScsiLCPEntry 17 }

cfprVnicIScsiLCPOperAdaptorProfileName OBJECT-TYPE
    SYNTAX       SnmpAdminString
    MAX-ACCESS   read-only
    STATUS       current
    DESCRIPTION
        "Cisco Firepower vnic:IScsiLCP:operAdaptorProfileName
        managed object property"
    ::= { cfprVnicIScsiLCPEntry 18 }

cfprVnicIScsiLCPOperHostPort OBJECT-TYPE
    SYNTAX       CfprVnicVnicOperHostPort
    MAX-ACCESS   read-only
    STATUS       current
    DESCRIPTION
        "Cisco Firepower vnic:IScsiLCP:operHostPort managed
        object property"
    ::= { cfprVnicIScsiLCPEntry 19 }

cfprVnicIScsiLCPOperIdentPoolName OBJECT-TYPE
    SYNTAX       SnmpAdminString
    MAX-ACCESS   read-only
    STATUS       current
    DESCRIPTION
        "Cisco Firepower vnic:IScsiLCP:operIdentPoolName
        managed object property"
    ::= { cfprVnicIScsiLCPEntry 20 }

cfprVnicIScsiLCPOperOrder OBJECT-TYPE
    SYNTAX       Gauge32
    MAX-ACCESS   read-only
    STATUS       current
    DESCRIPTION
        "Cisco Firepower vnic:IScsiLCP:operOrder managed object property"
    ::= { cfprVnicIScsiLCPEntry 21 }

cfprVnicIScsiLCPOperSpeed OBJECT-TYPE
    SYNTAX       Gauge32
    MAX-ACCESS   read-only
    STATUS       current
    DESCRIPTION
        "Cisco Firepower vnic:IScsiLCP:operSpeed managed object property"
    ::= { cfprVnicIScsiLCPEntry 22 }

cfprVnicIScsiLCPOperStatsPolicyName OBJECT-TYPE
    SYNTAX       SnmpAdminString
    MAX-ACCESS   read-only
    STATUS       current
    DESCRIPTION
        "Cisco Firepower vnic:IScsiLCP:operStatsPolicyName
        managed object property"
    ::= { cfprVnicIScsiLCPEntry 23 }

cfprVnicIScsiLCPOperVcon OBJECT-TYPE
    SYNTAX       SnmpAdminString
    MAX-ACCESS   read-only
    STATUS       current
    DESCRIPTION
        "Cisco Firepower vnic:IScsiLCP:operVcon managed object property"
    ::= { cfprVnicIScsiLCPEntry 24 }

cfprVnicIScsiLCPOrder OBJECT-TYPE
    SYNTAX       Gauge32
    MAX-ACCESS   read-only
    STATUS       current
    DESCRIPTION
        "Cisco Firepower vnic:IScsiLCP:order managed object property"
    ::= { cfprVnicIScsiLCPEntry 25 }

cfprVnicIScsiLCPOwner OBJECT-TYPE
    SYNTAX       CfprVnicConnectionOwner
    MAX-ACCESS   read-only
    STATUS       current
    DESCRIPTION
        "Cisco Firepower vnic:IScsiLCP:owner managed object property"
    ::= { cfprVnicIScsiLCPEntry 26 }

cfprVnicIScsiLCPPinToGroupName OBJECT-TYPE
    SYNTAX       SnmpAdminString
    MAX-ACCESS   read-only
    STATUS       current
    DESCRIPTION
        "Cisco Firepower vnic:IScsiLCP:pinToGroupName managed
        object property"
    ::= { cfprVnicIScsiLCPEntry 27 }

cfprVnicIScsiLCPQosPolicyName OBJECT-TYPE
    SYNTAX       SnmpAdminString
    MAX-ACCESS   read-only
    STATUS       current
    DESCRIPTION
        "Cisco Firepower vnic:IScsiLCP:qosPolicyName managed
        object property"
    ::= { cfprVnicIScsiLCPEntry 28 }

cfprVnicIScsiLCPStatsPolicyName OBJECT-TYPE
    SYNTAX       SnmpAdminString
    MAX-ACCESS   read-only
    STATUS       current
    DESCRIPTION
        "Cisco Firepower vnic:IScsiLCP:statsPolicyName
        managed object property"
    ::= { cfprVnicIScsiLCPEntry 29 }

cfprVnicIScsiLCPSwitchId OBJECT-TYPE
    SYNTAX       CfprNetworkSwitchId
    MAX-ACCESS   read-only
    STATUS       current
    DESCRIPTION
        "Cisco Firepower vnic:IScsiLCP:switchId managed object property"
    ::= { cfprVnicIScsiLCPEntry 30 }

cfprVnicIScsiLCPType OBJECT-TYPE
    SYNTAX       CfprVnicConnectionType
    MAX-ACCESS   read-only
    STATUS       current
    DESCRIPTION
        "Cisco Firepower vnic:IScsiLCP:type managed object property"
    ::= { cfprVnicIScsiLCPEntry 31 }

cfprVnicIScsiLCPVnicName OBJECT-TYPE
    SYNTAX       SnmpAdminString
    MAX-ACCESS   read-only
    STATUS       current
    DESCRIPTION
        "Cisco Firepower vnic:IScsiLCP:vnicName managed object property"
    ::= { cfprVnicIScsiLCPEntry 32 }

cfprVnicIScsiNodeTable OBJECT-TYPE
    SYNTAX           SEQUENCE OF CfprVnicIScsiNodeEntry
    MAX-ACCESS       not-accessible
    STATUS           current
    DESCRIPTION
        "Cisco Firepower vnic:IScsiNode managed object table"
    ::= { cfprVnicObjects 32 }

cfprVnicIScsiNodeEntry OBJECT-TYPE
    SYNTAX           CfprVnicIScsiNodeEntry
    MAX-ACCESS       not-accessible
    STATUS           current
    DESCRIPTION
        "Entry for the cfprVnicIScsiNodeTable table."
    INDEX { cfprVnicIScsiNodeInstanceId }
    ::= { cfprVnicIScsiNodeTable 1 }

CfprVnicIScsiNodeEntry ::= SEQUENCE {
    cfprVnicIScsiNodeInstanceId                                      CfprManagedObjectId,
    cfprVnicIScsiNodeDn                                              CfprManagedObjectDn,
    cfprVnicIScsiNodeRn                                              SnmpAdminString,
    cfprVnicIScsiNodeFltAggr                                         Unsigned64,
    cfprVnicIScsiNodeInitNameSuffix                                  SnmpAdminString,
    cfprVnicIScsiNodeInitiatorName                                   SnmpAdminString,
    cfprVnicIScsiNodeIqnIdentPoolName                                SnmpAdminString,
    cfprVnicIScsiNodeOperIqnIdentPoolName                            SnmpAdminString,
    cfprVnicIScsiNodeOwner                                           CfprVnicIScsiNodeOwner
}

cfprVnicIScsiNodeInstanceId OBJECT-TYPE
    SYNTAX       CfprManagedObjectId
    MAX-ACCESS   not-accessible
    STATUS       current
    DESCRIPTION
        "Instance identifier of the managed object."
    ::= { cfprVnicIScsiNodeEntry 1 }

cfprVnicIScsiNodeDn OBJECT-TYPE
    SYNTAX       CfprManagedObjectDn
    MAX-ACCESS   read-only
    STATUS       current
    DESCRIPTION
        "Cisco Firepower vnic:IScsiNode:dn managed object property"
    ::= { cfprVnicIScsiNodeEntry 2 }

cfprVnicIScsiNodeRn OBJECT-TYPE
    SYNTAX       SnmpAdminString
    MAX-ACCESS   read-only
    STATUS       current
    DESCRIPTION
        "Cisco Firepower vnic:IScsiNode:rn managed object property"
    ::= { cfprVnicIScsiNodeEntry 3 }

cfprVnicIScsiNodeFltAggr OBJECT-TYPE
    SYNTAX       Unsigned64
    MAX-ACCESS   read-only
    STATUS       current
    DESCRIPTION
        "Cisco Firepower vnic:IScsiNode:fltAggr managed object property"
    ::= { cfprVnicIScsiNodeEntry 4 }

cfprVnicIScsiNodeInitNameSuffix OBJECT-TYPE
    SYNTAX       SnmpAdminString
    MAX-ACCESS   read-only
    STATUS       current
    DESCRIPTION
        "Cisco Firepower vnic:IScsiNode:initNameSuffix
        managed object property"
    ::= { cfprVnicIScsiNodeEntry 5 }

cfprVnicIScsiNodeInitiatorName OBJECT-TYPE
    SYNTAX       SnmpAdminString
    MAX-ACCESS   read-only
    STATUS       current
    DESCRIPTION
        "Cisco Firepower vnic:IScsiNode:initiatorName managed
        object property"
    ::= { cfprVnicIScsiNodeEntry 6 }

cfprVnicIScsiNodeIqnIdentPoolName OBJECT-TYPE
    SYNTAX       SnmpAdminString
    MAX-ACCESS   read-only
    STATUS       current
    DESCRIPTION
        "Cisco Firepower vnic:IScsiNode:iqnIdentPoolName
        managed object property"
    ::= { cfprVnicIScsiNodeEntry 7 }

cfprVnicIScsiNodeOperIqnIdentPoolName OBJECT-TYPE
    SYNTAX       SnmpAdminString
    MAX-ACCESS   read-only
    STATUS       current
    DESCRIPTION
        "Cisco Firepower vnic:IScsiNode:operIqnIdentPoolName
        managed object property"
    ::= { cfprVnicIScsiNodeEntry 8 }

cfprVnicIScsiNodeOwner OBJECT-TYPE
    SYNTAX       CfprVnicIScsiNodeOwner
    MAX-ACCESS   read-only
    STATUS       current
    DESCRIPTION
        "Cisco Firepower vnic:IScsiNode:owner managed object property"
    ::= { cfprVnicIScsiNodeEntry 9 }

cfprVnicIScsiStaticTargetIfTable OBJECT-TYPE
    SYNTAX           SEQUENCE OF CfprVnicIScsiStaticTargetIfEntry
    MAX-ACCESS       not-accessible
    STATUS           current
    DESCRIPTION
        "Cisco Firepower vnic:IScsiStaticTargetIf managed object table"
    ::= { cfprVnicObjects 33 }

cfprVnicIScsiStaticTargetIfEntry OBJECT-TYPE
    SYNTAX           CfprVnicIScsiStaticTargetIfEntry
    MAX-ACCESS       not-accessible
    STATUS           current
    DESCRIPTION
        "Entry for the cfprVnicIScsiStaticTargetIfTable table."
    INDEX { cfprVnicIScsiStaticTargetIfInstanceId }
    ::= { cfprVnicIScsiStaticTargetIfTable 1 }

CfprVnicIScsiStaticTargetIfEntry ::= SEQUENCE {
    cfprVnicIScsiStaticTargetIfInstanceId                            CfprManagedObjectId,
    cfprVnicIScsiStaticTargetIfDn                                    CfprManagedObjectDn,
    cfprVnicIScsiStaticTargetIfRn                                    SnmpAdminString,
    cfprVnicIScsiStaticTargetIfAuthProfileName                       SnmpAdminString,
    cfprVnicIScsiStaticTargetIfIpAddress                             InetAddressIPv4,
    cfprVnicIScsiStaticTargetIfName                                  SnmpAdminString,
    cfprVnicIScsiStaticTargetIfOperAuthProfileName                   SnmpAdminString,
    cfprVnicIScsiStaticTargetIfPort                                  Gauge32,
    cfprVnicIScsiStaticTargetIfPriority                              Gauge32
}

cfprVnicIScsiStaticTargetIfInstanceId OBJECT-TYPE
    SYNTAX       CfprManagedObjectId
    MAX-ACCESS   not-accessible
    STATUS       current
    DESCRIPTION
        "Instance identifier of the managed object."
    ::= { cfprVnicIScsiStaticTargetIfEntry 1 }

cfprVnicIScsiStaticTargetIfDn OBJECT-TYPE
    SYNTAX       CfprManagedObjectDn
    MAX-ACCESS   read-only
    STATUS       current
    DESCRIPTION
        "Cisco Firepower vnic:IScsiStaticTargetIf:dn managed
        object property"
    ::= { cfprVnicIScsiStaticTargetIfEntry 2 }

cfprVnicIScsiStaticTargetIfRn OBJECT-TYPE
    SYNTAX       SnmpAdminString
    MAX-ACCESS   read-only
    STATUS       current
    DESCRIPTION
        "Cisco Firepower vnic:IScsiStaticTargetIf:rn managed
        object property"
    ::= { cfprVnicIScsiStaticTargetIfEntry 3 }

cfprVnicIScsiStaticTargetIfAuthProfileName OBJECT-TYPE
    SYNTAX       SnmpAdminString
    MAX-ACCESS   read-only
    STATUS       current
    DESCRIPTION
        "Cisco Firepower vnic:IScsiStaticTargetIf:authProfileName
        managed object property"
    ::= { cfprVnicIScsiStaticTargetIfEntry 4 }

cfprVnicIScsiStaticTargetIfIpAddress OBJECT-TYPE
    SYNTAX       InetAddressIPv4
    MAX-ACCESS   read-only
    STATUS       current
    DESCRIPTION
        "Cisco Firepower vnic:IScsiStaticTargetIf:ipAddress
        managed object property"
    ::= { cfprVnicIScsiStaticTargetIfEntry 5 }

cfprVnicIScsiStaticTargetIfName OBJECT-TYPE
    SYNTAX       SnmpAdminString
    MAX-ACCESS   read-only
    STATUS       current
    DESCRIPTION
        "Cisco Firepower vnic:IScsiStaticTargetIf:name
        managed object property"
    ::= { cfprVnicIScsiStaticTargetIfEntry 6 }

cfprVnicIScsiStaticTargetIfOperAuthProfileName OBJECT-TYPE
    SYNTAX       SnmpAdminString
    MAX-ACCESS   read-only
    STATUS       current
    DESCRIPTION
        "Cisco Firepower vnic:IScsiStaticTargetIf:operAuthProfileName
        managed object property"
    ::= { cfprVnicIScsiStaticTargetIfEntry 7 }

cfprVnicIScsiStaticTargetIfPort OBJECT-TYPE
    SYNTAX       Gauge32
    MAX-ACCESS   read-only
    STATUS       current
    DESCRIPTION
        "Cisco Firepower vnic:IScsiStaticTargetIf:port
        managed object property"
    ::= { cfprVnicIScsiStaticTargetIfEntry 8 }

cfprVnicIScsiStaticTargetIfPriority OBJECT-TYPE
    SYNTAX       Gauge32
    MAX-ACCESS   read-only
    STATUS       current
    DESCRIPTION
        "Cisco Firepower vnic:IScsiStaticTargetIf:priority
        managed object property"
    ::= { cfprVnicIScsiStaticTargetIfEntry 9 }

cfprVnicInternalProfileTable OBJECT-TYPE
    SYNTAX           SEQUENCE OF CfprVnicInternalProfileEntry
    MAX-ACCESS       not-accessible
    STATUS           current
    DESCRIPTION
        "Cisco Firepower vnic:InternalProfile managed object table"
    ::= { cfprVnicObjects 34 }

cfprVnicInternalProfileEntry OBJECT-TYPE
    SYNTAX           CfprVnicInternalProfileEntry
    MAX-ACCESS       not-accessible
    STATUS           current
    DESCRIPTION
        "Entry for the cfprVnicInternalProfileTable table."
    INDEX { cfprVnicInternalProfileInstanceId }
    ::= { cfprVnicInternalProfileTable 1 }

CfprVnicInternalProfileEntry ::= SEQUENCE {
    cfprVnicInternalProfileInstanceId                                CfprManagedObjectId,
    cfprVnicInternalProfileDn                                        CfprManagedObjectDn,
    cfprVnicInternalProfileRn                                        SnmpAdminString,
    cfprVnicInternalProfileDescr                                     SnmpAdminString,
    cfprVnicInternalProfileIntId                                     SnmpAdminString,
    cfprVnicInternalProfileMaxPorts                                  Gauge32,
    cfprVnicInternalProfileName                                      SnmpAdminString,
    cfprVnicInternalProfilePolicyLevel                               Gauge32,
    cfprVnicInternalProfilePolicyOwner                               CfprPolicyPolicyOwner
}

cfprVnicInternalProfileInstanceId OBJECT-TYPE
    SYNTAX       CfprManagedObjectId
    MAX-ACCESS   not-accessible
    STATUS       current
    DESCRIPTION
        "Instance identifier of the managed object."
    ::= { cfprVnicInternalProfileEntry 1 }

cfprVnicInternalProfileDn OBJECT-TYPE
    SYNTAX       CfprManagedObjectDn
    MAX-ACCESS   read-only
    STATUS       current
    DESCRIPTION
        "Cisco Firepower vnic:InternalProfile:dn managed object property"
    ::= { cfprVnicInternalProfileEntry 2 }

cfprVnicInternalProfileRn OBJECT-TYPE
    SYNTAX       SnmpAdminString
    MAX-ACCESS   read-only
    STATUS       current
    DESCRIPTION
        "Cisco Firepower vnic:InternalProfile:rn managed object property"
    ::= { cfprVnicInternalProfileEntry 3 }

cfprVnicInternalProfileDescr OBJECT-TYPE
    SYNTAX       SnmpAdminString
    MAX-ACCESS   read-only
    STATUS       current
    DESCRIPTION
        "Cisco Firepower vnic:InternalProfile:descr managed
        object property"
    ::= { cfprVnicInternalProfileEntry 4 }

cfprVnicInternalProfileIntId OBJECT-TYPE
    SYNTAX       SnmpAdminString
    MAX-ACCESS   read-only
    STATUS       current
    DESCRIPTION
        "Cisco Firepower vnic:InternalProfile:intId managed
        object property"
    ::= { cfprVnicInternalProfileEntry 5 }

cfprVnicInternalProfileMaxPorts OBJECT-TYPE
    SYNTAX       Gauge32
    MAX-ACCESS   read-only
    STATUS       current
    DESCRIPTION
        "Cisco Firepower vnic:InternalProfile:maxPorts
        managed object property"
    ::= { cfprVnicInternalProfileEntry 6 }

cfprVnicInternalProfileName OBJECT-TYPE
    SYNTAX       SnmpAdminString
    MAX-ACCESS   read-only
    STATUS       current
    DESCRIPTION
        "Cisco Firepower vnic:InternalProfile:name managed
        object property"
    ::= { cfprVnicInternalProfileEntry 7 }

cfprVnicInternalProfilePolicyLevel OBJECT-TYPE
    SYNTAX       Gauge32
    MAX-ACCESS   read-only
    STATUS       current
    DESCRIPTION
        "Cisco Firepower vnic:InternalProfile:policyLevel
        managed object property"
    ::= { cfprVnicInternalProfileEntry 8 }

cfprVnicInternalProfilePolicyOwner OBJECT-TYPE
    SYNTAX       CfprPolicyPolicyOwner
    MAX-ACCESS   read-only
    STATUS       current
    DESCRIPTION
        "Cisco Firepower vnic:InternalProfile:policyOwner
        managed object property"
    ::= { cfprVnicInternalProfileEntry 9 }

cfprVnicIpV4HistoryTable OBJECT-TYPE
    SYNTAX           SEQUENCE OF CfprVnicIpV4HistoryEntry
    MAX-ACCESS       not-accessible
    STATUS           current
    DESCRIPTION
        "Cisco Firepower vnic:IpV4History managed object table"
    ::= { cfprVnicObjects 35 }

cfprVnicIpV4HistoryEntry OBJECT-TYPE
    SYNTAX           CfprVnicIpV4HistoryEntry
    MAX-ACCESS       not-accessible
    STATUS           current
    DESCRIPTION
        "Entry for the cfprVnicIpV4HistoryTable table."
    INDEX { cfprVnicIpV4HistoryInstanceId }
    ::= { cfprVnicIpV4HistoryTable 1 }

CfprVnicIpV4HistoryEntry ::= SEQUENCE {
    cfprVnicIpV4HistoryInstanceId                                    CfprManagedObjectId,
    cfprVnicIpV4HistoryDn                                            CfprManagedObjectDn,
    cfprVnicIpV4HistoryRn                                            SnmpAdminString,
    cfprVnicIpV4HistoryOldIpV4Addr                                   InetAddressIPv4
}

cfprVnicIpV4HistoryInstanceId OBJECT-TYPE
    SYNTAX       CfprManagedObjectId
    MAX-ACCESS   not-accessible
    STATUS       current
    DESCRIPTION
        "Instance identifier of the managed object."
    ::= { cfprVnicIpV4HistoryEntry 1 }

cfprVnicIpV4HistoryDn OBJECT-TYPE
    SYNTAX       CfprManagedObjectDn
    MAX-ACCESS   read-only
    STATUS       current
    DESCRIPTION
        "Cisco Firepower vnic:IpV4History:dn managed object property"
    ::= { cfprVnicIpV4HistoryEntry 2 }

cfprVnicIpV4HistoryRn OBJECT-TYPE
    SYNTAX       SnmpAdminString
    MAX-ACCESS   read-only
    STATUS       current
    DESCRIPTION
        "Cisco Firepower vnic:IpV4History:rn managed object property"
    ::= { cfprVnicIpV4HistoryEntry 3 }

cfprVnicIpV4HistoryOldIpV4Addr OBJECT-TYPE
    SYNTAX       InetAddressIPv4
    MAX-ACCESS   read-only
    STATUS       current
    DESCRIPTION
        "Cisco Firepower vnic:IpV4History:oldIpV4Addr managed
        object property"
    ::= { cfprVnicIpV4HistoryEntry 4 }

cfprVnicIpV4MgmtPooledAddrTable OBJECT-TYPE
    SYNTAX           SEQUENCE OF CfprVnicIpV4MgmtPooledAddrEntry
    MAX-ACCESS       not-accessible
    STATUS           current
    DESCRIPTION
        "Cisco Firepower vnic:IpV4MgmtPooledAddr managed object table"
    ::= { cfprVnicObjects 36 }

cfprVnicIpV4MgmtPooledAddrEntry OBJECT-TYPE
    SYNTAX           CfprVnicIpV4MgmtPooledAddrEntry
    MAX-ACCESS       not-accessible
    STATUS           current
    DESCRIPTION
        "Entry for the cfprVnicIpV4MgmtPooledAddrTable table."
    INDEX { cfprVnicIpV4MgmtPooledAddrInstanceId }
    ::= { cfprVnicIpV4MgmtPooledAddrTable 1 }

CfprVnicIpV4MgmtPooledAddrEntry ::= SEQUENCE {
    cfprVnicIpV4MgmtPooledAddrInstanceId                             CfprManagedObjectId,
    cfprVnicIpV4MgmtPooledAddrDn                                     CfprManagedObjectDn,
    cfprVnicIpV4MgmtPooledAddrRn                                     SnmpAdminString,
    cfprVnicIpV4MgmtPooledAddrAddr                                   InetAddressIPv4,
    cfprVnicIpV4MgmtPooledAddrDefGw                                  InetAddressIPv4,
    cfprVnicIpV4MgmtPooledAddrName                                   SnmpAdminString,
    cfprVnicIpV4MgmtPooledAddrOperName                               SnmpAdminString,
    cfprVnicIpV4MgmtPooledAddrPrimDns                                InetAddressIPv4,
    cfprVnicIpV4MgmtPooledAddrSecDns                                 InetAddressIPv4,
    cfprVnicIpV4MgmtPooledAddrSubnet                                 InetAddressIPv4
}

cfprVnicIpV4MgmtPooledAddrInstanceId OBJECT-TYPE
    SYNTAX       CfprManagedObjectId
    MAX-ACCESS   not-accessible
    STATUS       current
    DESCRIPTION
        "Instance identifier of the managed object."
    ::= { cfprVnicIpV4MgmtPooledAddrEntry 1 }

cfprVnicIpV4MgmtPooledAddrDn OBJECT-TYPE
    SYNTAX       CfprManagedObjectDn
    MAX-ACCESS   read-only
    STATUS       current
    DESCRIPTION
        "Cisco Firepower vnic:IpV4MgmtPooledAddr:dn managed
        object property"
    ::= { cfprVnicIpV4MgmtPooledAddrEntry 2 }

cfprVnicIpV4MgmtPooledAddrRn OBJECT-TYPE
    SYNTAX       SnmpAdminString
    MAX-ACCESS   read-only
    STATUS       current
    DESCRIPTION
        "Cisco Firepower vnic:IpV4MgmtPooledAddr:rn managed
        object property"
    ::= { cfprVnicIpV4MgmtPooledAddrEntry 3 }

cfprVnicIpV4MgmtPooledAddrAddr OBJECT-TYPE
    SYNTAX       InetAddressIPv4
    MAX-ACCESS   read-only
    STATUS       current
    DESCRIPTION
        "Cisco Firepower vnic:IpV4MgmtPooledAddr:addr managed
        object property"
    ::= { cfprVnicIpV4MgmtPooledAddrEntry 4 }

cfprVnicIpV4MgmtPooledAddrDefGw OBJECT-TYPE
    SYNTAX       InetAddressIPv4
    MAX-ACCESS   read-only
    STATUS       current
    DESCRIPTION
        "Cisco Firepower vnic:IpV4MgmtPooledAddr:defGw
        managed object property"
    ::= { cfprVnicIpV4MgmtPooledAddrEntry 5 }

cfprVnicIpV4MgmtPooledAddrName OBJECT-TYPE
    SYNTAX       SnmpAdminString
    MAX-ACCESS   read-only
    STATUS       current
    DESCRIPTION
        "Cisco Firepower vnic:IpV4MgmtPooledAddr:name managed
        object property"
    ::= { cfprVnicIpV4MgmtPooledAddrEntry 6 }

cfprVnicIpV4MgmtPooledAddrOperName OBJECT-TYPE
    SYNTAX       SnmpAdminString
    MAX-ACCESS   read-only
    STATUS       current
    DESCRIPTION
        "Cisco Firepower vnic:IpV4MgmtPooledAddr:operName
        managed object property"
    ::= { cfprVnicIpV4MgmtPooledAddrEntry 7 }

cfprVnicIpV4MgmtPooledAddrPrimDns OBJECT-TYPE
    SYNTAX       InetAddressIPv4
    MAX-ACCESS   read-only
    STATUS       current
    DESCRIPTION
        "Cisco Firepower vnic:IpV4MgmtPooledAddr:primDns
        managed object property"
    ::= { cfprVnicIpV4MgmtPooledAddrEntry 8 }

cfprVnicIpV4MgmtPooledAddrSecDns OBJECT-TYPE
    SYNTAX       InetAddressIPv4
    MAX-ACCESS   read-only
    STATUS       current
    DESCRIPTION
        "Cisco Firepower vnic:IpV4MgmtPooledAddr:secDns
        managed object property"
    ::= { cfprVnicIpV4MgmtPooledAddrEntry 9 }

cfprVnicIpV4MgmtPooledAddrSubnet OBJECT-TYPE
    SYNTAX       InetAddressIPv4
    MAX-ACCESS   read-only
    STATUS       current
    DESCRIPTION
        "Cisco Firepower vnic:IpV4MgmtPooledAddr:subnet
        managed object property"
    ::= { cfprVnicIpV4MgmtPooledAddrEntry 10 }

cfprVnicIpV4PooledAddrTable OBJECT-TYPE
    SYNTAX           SEQUENCE OF CfprVnicIpV4PooledAddrEntry
    MAX-ACCESS       not-accessible
    STATUS           current
    DESCRIPTION
        "Cisco Firepower vnic:IpV4PooledAddr managed object table"
    ::= { cfprVnicObjects 37 }

cfprVnicIpV4PooledAddrEntry OBJECT-TYPE
    SYNTAX           CfprVnicIpV4PooledAddrEntry
    MAX-ACCESS       not-accessible
    STATUS           current
    DESCRIPTION
        "Entry for the cfprVnicIpV4PooledAddrTable table."
    INDEX { cfprVnicIpV4PooledAddrInstanceId }
    ::= { cfprVnicIpV4PooledAddrTable 1 }

CfprVnicIpV4PooledAddrEntry ::= SEQUENCE {
    cfprVnicIpV4PooledAddrInstanceId                                 CfprManagedObjectId,
    cfprVnicIpV4PooledAddrDn                                         CfprManagedObjectDn,
    cfprVnicIpV4PooledAddrRn                                         SnmpAdminString,
    cfprVnicIpV4PooledAddrAddr                                       InetAddressIPv4,
    cfprVnicIpV4PooledAddrDefGw                                      InetAddressIPv4,
    cfprVnicIpV4PooledAddrName                                       SnmpAdminString,
    cfprVnicIpV4PooledAddrOperName                                   SnmpAdminString,
    cfprVnicIpV4PooledAddrPrimDns                                    InetAddressIPv4,
    cfprVnicIpV4PooledAddrSecDns                                     InetAddressIPv4,
    cfprVnicIpV4PooledAddrSubnet                                     InetAddressIPv4
}

cfprVnicIpV4PooledAddrInstanceId OBJECT-TYPE
    SYNTAX       CfprManagedObjectId
    MAX-ACCESS   not-accessible
    STATUS       current
    DESCRIPTION
        "Instance identifier of the managed object."
    ::= { cfprVnicIpV4PooledAddrEntry 1 }

cfprVnicIpV4PooledAddrDn OBJECT-TYPE
    SYNTAX       CfprManagedObjectDn
    MAX-ACCESS   read-only
    STATUS       current
    DESCRIPTION
        "Cisco Firepower vnic:IpV4PooledAddr:dn managed object property"
    ::= { cfprVnicIpV4PooledAddrEntry 2 }

cfprVnicIpV4PooledAddrRn OBJECT-TYPE
    SYNTAX       SnmpAdminString
    MAX-ACCESS   read-only
    STATUS       current
    DESCRIPTION
        "Cisco Firepower vnic:IpV4PooledAddr:rn managed object property"
    ::= { cfprVnicIpV4PooledAddrEntry 3 }

cfprVnicIpV4PooledAddrAddr OBJECT-TYPE
    SYNTAX       InetAddressIPv4
    MAX-ACCESS   read-only
    STATUS       current
    DESCRIPTION
        "Cisco Firepower vnic:IpV4PooledAddr:addr managed object property"
    ::= { cfprVnicIpV4PooledAddrEntry 4 }

cfprVnicIpV4PooledAddrDefGw OBJECT-TYPE
    SYNTAX       InetAddressIPv4
    MAX-ACCESS   read-only
    STATUS       current
    DESCRIPTION
        "Cisco Firepower vnic:IpV4PooledAddr:defGw managed
        object property"
    ::= { cfprVnicIpV4PooledAddrEntry 5 }

cfprVnicIpV4PooledAddrName OBJECT-TYPE
    SYNTAX       SnmpAdminString
    MAX-ACCESS   read-only
    STATUS       current
    DESCRIPTION
        "Cisco Firepower vnic:IpV4PooledAddr:name managed object property"
    ::= { cfprVnicIpV4PooledAddrEntry 6 }

cfprVnicIpV4PooledAddrOperName OBJECT-TYPE
    SYNTAX       SnmpAdminString
    MAX-ACCESS   read-only
    STATUS       current
    DESCRIPTION
        "Cisco Firepower vnic:IpV4PooledAddr:operName managed
        object property"
    ::= { cfprVnicIpV4PooledAddrEntry 7 }

cfprVnicIpV4PooledAddrPrimDns OBJECT-TYPE
    SYNTAX       InetAddressIPv4
    MAX-ACCESS   read-only
    STATUS       current
    DESCRIPTION
        "Cisco Firepower vnic:IpV4PooledAddr:primDns managed
        object property"
    ::= { cfprVnicIpV4PooledAddrEntry 8 }

cfprVnicIpV4PooledAddrSecDns OBJECT-TYPE
    SYNTAX       InetAddressIPv4
    MAX-ACCESS   read-only
    STATUS       current
    DESCRIPTION
        "Cisco Firepower vnic:IpV4PooledAddr:secDns managed
        object property"
    ::= { cfprVnicIpV4PooledAddrEntry 9 }

cfprVnicIpV4PooledAddrSubnet OBJECT-TYPE
    SYNTAX       InetAddressIPv4
    MAX-ACCESS   read-only
    STATUS       current
    DESCRIPTION
        "Cisco Firepower vnic:IpV4PooledAddr:subnet managed
        object property"
    ::= { cfprVnicIpV4PooledAddrEntry 10 }

cfprVnicIpV4ProfDerivedAddrTable OBJECT-TYPE
    SYNTAX           SEQUENCE OF CfprVnicIpV4ProfDerivedAddrEntry
    MAX-ACCESS       not-accessible
    STATUS           current
    DESCRIPTION
        "Cisco Firepower vnic:IpV4ProfDerivedAddr managed object table"
    ::= { cfprVnicObjects 38 }

cfprVnicIpV4ProfDerivedAddrEntry OBJECT-TYPE
    SYNTAX           CfprVnicIpV4ProfDerivedAddrEntry
    MAX-ACCESS       not-accessible
    STATUS           current
    DESCRIPTION
        "Entry for the cfprVnicIpV4ProfDerivedAddrTable table."
    INDEX { cfprVnicIpV4ProfDerivedAddrInstanceId }
    ::= { cfprVnicIpV4ProfDerivedAddrTable 1 }

CfprVnicIpV4ProfDerivedAddrEntry ::= SEQUENCE {
    cfprVnicIpV4ProfDerivedAddrInstanceId                            CfprManagedObjectId,
    cfprVnicIpV4ProfDerivedAddrDn                                    CfprManagedObjectDn,
    cfprVnicIpV4ProfDerivedAddrRn                                    SnmpAdminString,
    cfprVnicIpV4ProfDerivedAddrAddr                                  InetAddressIPv4,
    cfprVnicIpV4ProfDerivedAddrDefGw                                 InetAddressIPv4,
    cfprVnicIpV4ProfDerivedAddrSubnet                                InetAddressIPv4
}

cfprVnicIpV4ProfDerivedAddrInstanceId OBJECT-TYPE
    SYNTAX       CfprManagedObjectId
    MAX-ACCESS   not-accessible
    STATUS       current
    DESCRIPTION
        "Instance identifier of the managed object."
    ::= { cfprVnicIpV4ProfDerivedAddrEntry 1 }

cfprVnicIpV4ProfDerivedAddrDn OBJECT-TYPE
    SYNTAX       CfprManagedObjectDn
    MAX-ACCESS   read-only
    STATUS       current
    DESCRIPTION
        "Cisco Firepower vnic:IpV4ProfDerivedAddr:dn managed
        object property"
    ::= { cfprVnicIpV4ProfDerivedAddrEntry 2 }

cfprVnicIpV4ProfDerivedAddrRn OBJECT-TYPE
    SYNTAX       SnmpAdminString
    MAX-ACCESS   read-only
    STATUS       current
    DESCRIPTION
        "Cisco Firepower vnic:IpV4ProfDerivedAddr:rn managed
        object property"
    ::= { cfprVnicIpV4ProfDerivedAddrEntry 3 }

cfprVnicIpV4ProfDerivedAddrAddr OBJECT-TYPE
    SYNTAX       InetAddressIPv4
    MAX-ACCESS   read-only
    STATUS       current
    DESCRIPTION
        "Cisco Firepower vnic:IpV4ProfDerivedAddr:addr
        managed object property"
    ::= { cfprVnicIpV4ProfDerivedAddrEntry 4 }

cfprVnicIpV4ProfDerivedAddrDefGw OBJECT-TYPE
    SYNTAX       InetAddressIPv4
    MAX-ACCESS   read-only
    STATUS       current
    DESCRIPTION
        "Cisco Firepower vnic:IpV4ProfDerivedAddr:defGw
        managed object property"
    ::= { cfprVnicIpV4ProfDerivedAddrEntry 5 }

cfprVnicIpV4ProfDerivedAddrSubnet OBJECT-TYPE
    SYNTAX       InetAddressIPv4
    MAX-ACCESS   read-only
    STATUS       current
    DESCRIPTION
        "Cisco Firepower vnic:IpV4ProfDerivedAddr:subnet
        managed object property"
    ::= { cfprVnicIpV4ProfDerivedAddrEntry 6 }

cfprVnicIpV4StaticAddrTable OBJECT-TYPE
    SYNTAX           SEQUENCE OF CfprVnicIpV4StaticAddrEntry
    MAX-ACCESS       not-accessible
    STATUS           current
    DESCRIPTION
        "Cisco Firepower vnic:IpV4StaticAddr managed object table"
    ::= { cfprVnicObjects 39 }

cfprVnicIpV4StaticAddrEntry OBJECT-TYPE
    SYNTAX           CfprVnicIpV4StaticAddrEntry
    MAX-ACCESS       not-accessible
    STATUS           current
    DESCRIPTION
        "Entry for the cfprVnicIpV4StaticAddrTable table."
    INDEX { cfprVnicIpV4StaticAddrInstanceId }
    ::= { cfprVnicIpV4StaticAddrTable 1 }

CfprVnicIpV4StaticAddrEntry ::= SEQUENCE {
    cfprVnicIpV4StaticAddrInstanceId                                 CfprManagedObjectId,
    cfprVnicIpV4StaticAddrDn                                         CfprManagedObjectDn,
    cfprVnicIpV4StaticAddrRn                                         SnmpAdminString,
    cfprVnicIpV4StaticAddrAddr                                       InetAddressIPv4,
    cfprVnicIpV4StaticAddrDefGw                                      InetAddressIPv4,
    cfprVnicIpV4StaticAddrPrimDns                                    InetAddressIPv4,
    cfprVnicIpV4StaticAddrSecDns                                     InetAddressIPv4,
    cfprVnicIpV4StaticAddrSubnet                                     InetAddressIPv4
}

cfprVnicIpV4StaticAddrInstanceId OBJECT-TYPE
    SYNTAX       CfprManagedObjectId
    MAX-ACCESS   not-accessible
    STATUS       current
    DESCRIPTION
        "Instance identifier of the managed object."
    ::= { cfprVnicIpV4StaticAddrEntry 1 }

cfprVnicIpV4StaticAddrDn OBJECT-TYPE
    SYNTAX       CfprManagedObjectDn
    MAX-ACCESS   read-only
    STATUS       current
    DESCRIPTION
        "Cisco Firepower vnic:IpV4StaticAddr:dn managed object property"
    ::= { cfprVnicIpV4StaticAddrEntry 2 }

cfprVnicIpV4StaticAddrRn OBJECT-TYPE
    SYNTAX       SnmpAdminString
    MAX-ACCESS   read-only
    STATUS       current
    DESCRIPTION
        "Cisco Firepower vnic:IpV4StaticAddr:rn managed object property"
    ::= { cfprVnicIpV4StaticAddrEntry 3 }

cfprVnicIpV4StaticAddrAddr OBJECT-TYPE
    SYNTAX       InetAddressIPv4
    MAX-ACCESS   read-only
    STATUS       current
    DESCRIPTION
        "Cisco Firepower vnic:IpV4StaticAddr:addr managed object property"
    ::= { cfprVnicIpV4StaticAddrEntry 4 }

cfprVnicIpV4StaticAddrDefGw OBJECT-TYPE
    SYNTAX       InetAddressIPv4
    MAX-ACCESS   read-only
    STATUS       current
    DESCRIPTION
        "Cisco Firepower vnic:IpV4StaticAddr:defGw managed
        object property"
    ::= { cfprVnicIpV4StaticAddrEntry 5 }

cfprVnicIpV4StaticAddrPrimDns OBJECT-TYPE
    SYNTAX       InetAddressIPv4
    MAX-ACCESS   read-only
    STATUS       current
    DESCRIPTION
        "Cisco Firepower vnic:IpV4StaticAddr:primDns managed
        object property"
    ::= { cfprVnicIpV4StaticAddrEntry 6 }

cfprVnicIpV4StaticAddrSecDns OBJECT-TYPE
    SYNTAX       InetAddressIPv4
    MAX-ACCESS   read-only
    STATUS       current
    DESCRIPTION
        "Cisco Firepower vnic:IpV4StaticAddr:secDns managed
        object property"
    ::= { cfprVnicIpV4StaticAddrEntry 7 }

cfprVnicIpV4StaticAddrSubnet OBJECT-TYPE
    SYNTAX       InetAddressIPv4
    MAX-ACCESS   read-only
    STATUS       current
    DESCRIPTION
        "Cisco Firepower vnic:IpV4StaticAddr:subnet managed
        object property"
    ::= { cfprVnicIpV4StaticAddrEntry 8 }

cfprVnicIpV6HistoryTable OBJECT-TYPE
    SYNTAX           SEQUENCE OF CfprVnicIpV6HistoryEntry
    MAX-ACCESS       not-accessible
    STATUS           current
    DESCRIPTION
        "Cisco Firepower vnic:IpV6History managed object table"
    ::= { cfprVnicObjects 40 }

cfprVnicIpV6HistoryEntry OBJECT-TYPE
    SYNTAX           CfprVnicIpV6HistoryEntry
    MAX-ACCESS       not-accessible
    STATUS           current
    DESCRIPTION
        "Entry for the cfprVnicIpV6HistoryTable table."
    INDEX { cfprVnicIpV6HistoryInstanceId }
    ::= { cfprVnicIpV6HistoryTable 1 }

CfprVnicIpV6HistoryEntry ::= SEQUENCE {
    cfprVnicIpV6HistoryInstanceId                                    CfprManagedObjectId,
    cfprVnicIpV6HistoryDn                                            CfprManagedObjectDn,
    cfprVnicIpV6HistoryRn                                            SnmpAdminString,
    cfprVnicIpV6HistoryOldIpV6Addr                                   InetAddressIPv6
}

cfprVnicIpV6HistoryInstanceId OBJECT-TYPE
    SYNTAX       CfprManagedObjectId
    MAX-ACCESS   not-accessible
    STATUS       current
    DESCRIPTION
        "Instance identifier of the managed object."
    ::= { cfprVnicIpV6HistoryEntry 1 }

cfprVnicIpV6HistoryDn OBJECT-TYPE
    SYNTAX       CfprManagedObjectDn
    MAX-ACCESS   read-only
    STATUS       current
    DESCRIPTION
        "Cisco Firepower vnic:IpV6History:dn managed object property"
    ::= { cfprVnicIpV6HistoryEntry 2 }

cfprVnicIpV6HistoryRn OBJECT-TYPE
    SYNTAX       SnmpAdminString
    MAX-ACCESS   read-only
    STATUS       current
    DESCRIPTION
        "Cisco Firepower vnic:IpV6History:rn managed object property"
    ::= { cfprVnicIpV6HistoryEntry 3 }

cfprVnicIpV6HistoryOldIpV6Addr OBJECT-TYPE
    SYNTAX       InetAddressIPv6
    MAX-ACCESS   read-only
    STATUS       current
    DESCRIPTION
        "Cisco Firepower vnic:IpV6History:oldIpV6Addr managed
        object property"
    ::= { cfprVnicIpV6HistoryEntry 4 }

cfprVnicIpV6MgmtPooledAddrTable OBJECT-TYPE
    SYNTAX           SEQUENCE OF CfprVnicIpV6MgmtPooledAddrEntry
    MAX-ACCESS       not-accessible
    STATUS           current
    DESCRIPTION
        "Cisco Firepower vnic:IpV6MgmtPooledAddr managed object table"
    ::= { cfprVnicObjects 41 }

cfprVnicIpV6MgmtPooledAddrEntry OBJECT-TYPE
    SYNTAX           CfprVnicIpV6MgmtPooledAddrEntry
    MAX-ACCESS       not-accessible
    STATUS           current
    DESCRIPTION
        "Entry for the cfprVnicIpV6MgmtPooledAddrTable table."
    INDEX { cfprVnicIpV6MgmtPooledAddrInstanceId }
    ::= { cfprVnicIpV6MgmtPooledAddrTable 1 }

CfprVnicIpV6MgmtPooledAddrEntry ::= SEQUENCE {
    cfprVnicIpV6MgmtPooledAddrInstanceId                             CfprManagedObjectId,
    cfprVnicIpV6MgmtPooledAddrDn                                     CfprManagedObjectDn,
    cfprVnicIpV6MgmtPooledAddrRn                                     SnmpAdminString,
    cfprVnicIpV6MgmtPooledAddrAddr                                   InetAddressIPv6,
    cfprVnicIpV6MgmtPooledAddrDefGw                                  InetAddressIPv6,
    cfprVnicIpV6MgmtPooledAddrName                                   SnmpAdminString,
    cfprVnicIpV6MgmtPooledAddrOperName                               SnmpAdminString,
    cfprVnicIpV6MgmtPooledAddrPrefix                                 Gauge32,
    cfprVnicIpV6MgmtPooledAddrPrimDns                                InetAddressIPv6,
    cfprVnicIpV6MgmtPooledAddrSecDns                                 InetAddressIPv6
}

cfprVnicIpV6MgmtPooledAddrInstanceId OBJECT-TYPE
    SYNTAX       CfprManagedObjectId
    MAX-ACCESS   not-accessible
    STATUS       current
    DESCRIPTION
        "Instance identifier of the managed object."
    ::= { cfprVnicIpV6MgmtPooledAddrEntry 1 }

cfprVnicIpV6MgmtPooledAddrDn OBJECT-TYPE
    SYNTAX       CfprManagedObjectDn
    MAX-ACCESS   read-only
    STATUS       current
    DESCRIPTION
        "Cisco Firepower vnic:IpV6MgmtPooledAddr:dn managed
        object property"
    ::= { cfprVnicIpV6MgmtPooledAddrEntry 2 }

cfprVnicIpV6MgmtPooledAddrRn OBJECT-TYPE
    SYNTAX       SnmpAdminString
    MAX-ACCESS   read-only
    STATUS       current
    DESCRIPTION
        "Cisco Firepower vnic:IpV6MgmtPooledAddr:rn managed
        object property"
    ::= { cfprVnicIpV6MgmtPooledAddrEntry 3 }

cfprVnicIpV6MgmtPooledAddrAddr OBJECT-TYPE
    SYNTAX       InetAddressIPv6
    MAX-ACCESS   read-only
    STATUS       current
    DESCRIPTION
        "Cisco Firepower vnic:IpV6MgmtPooledAddr:addr managed
        object property"
    ::= { cfprVnicIpV6MgmtPooledAddrEntry 4 }

cfprVnicIpV6MgmtPooledAddrDefGw OBJECT-TYPE
    SYNTAX       InetAddressIPv6
    MAX-ACCESS   read-only
    STATUS       current
    DESCRIPTION
        "Cisco Firepower vnic:IpV6MgmtPooledAddr:defGw
        managed object property"
    ::= { cfprVnicIpV6MgmtPooledAddrEntry 5 }

cfprVnicIpV6MgmtPooledAddrName OBJECT-TYPE
    SYNTAX       SnmpAdminString
    MAX-ACCESS   read-only
    STATUS       current
    DESCRIPTION
        "Cisco Firepower vnic:IpV6MgmtPooledAddr:name managed
        object property"
    ::= { cfprVnicIpV6MgmtPooledAddrEntry 6 }

cfprVnicIpV6MgmtPooledAddrOperName OBJECT-TYPE
    SYNTAX       SnmpAdminString
    MAX-ACCESS   read-only
    STATUS       current
    DESCRIPTION
        "Cisco Firepower vnic:IpV6MgmtPooledAddr:operName
        managed object property"
    ::= { cfprVnicIpV6MgmtPooledAddrEntry 7 }

cfprVnicIpV6MgmtPooledAddrPrefix OBJECT-TYPE
    SYNTAX       Gauge32
    MAX-ACCESS   read-only
    STATUS       current
    DESCRIPTION
        "Cisco Firepower vnic:IpV6MgmtPooledAddr:prefix
        managed object property"
    ::= { cfprVnicIpV6MgmtPooledAddrEntry 8 }

cfprVnicIpV6MgmtPooledAddrPrimDns OBJECT-TYPE
    SYNTAX       InetAddressIPv6
    MAX-ACCESS   read-only
    STATUS       current
    DESCRIPTION
        "Cisco Firepower vnic:IpV6MgmtPooledAddr:primDns
        managed object property"
    ::= { cfprVnicIpV6MgmtPooledAddrEntry 9 }

cfprVnicIpV6MgmtPooledAddrSecDns OBJECT-TYPE
    SYNTAX       InetAddressIPv6
    MAX-ACCESS   read-only
    STATUS       current
    DESCRIPTION
        "Cisco Firepower vnic:IpV6MgmtPooledAddr:secDns
        managed object property"
    ::= { cfprVnicIpV6MgmtPooledAddrEntry 10 }

cfprVnicIpV6StaticAddrTable OBJECT-TYPE
    SYNTAX           SEQUENCE OF CfprVnicIpV6StaticAddrEntry
    MAX-ACCESS       not-accessible
    STATUS           current
    DESCRIPTION
        "Cisco Firepower vnic:IpV6StaticAddr managed object table"
    ::= { cfprVnicObjects 42 }

cfprVnicIpV6StaticAddrEntry OBJECT-TYPE
    SYNTAX           CfprVnicIpV6StaticAddrEntry
    MAX-ACCESS       not-accessible
    STATUS           current
    DESCRIPTION
        "Entry for the cfprVnicIpV6StaticAddrTable table."
    INDEX { cfprVnicIpV6StaticAddrInstanceId }
    ::= { cfprVnicIpV6StaticAddrTable 1 }

CfprVnicIpV6StaticAddrEntry ::= SEQUENCE {
    cfprVnicIpV6StaticAddrInstanceId                                 CfprManagedObjectId,
    cfprVnicIpV6StaticAddrDn                                         CfprManagedObjectDn,
    cfprVnicIpV6StaticAddrRn                                         SnmpAdminString,
    cfprVnicIpV6StaticAddrAddr                                       InetAddressIPv6,
    cfprVnicIpV6StaticAddrDefGw                                      InetAddressIPv6,
    cfprVnicIpV6StaticAddrPrefix                                     Gauge32,
    cfprVnicIpV6StaticAddrPrimDns                                    InetAddressIPv6,
    cfprVnicIpV6StaticAddrSecDns                                     InetAddressIPv6
}

cfprVnicIpV6StaticAddrInstanceId OBJECT-TYPE
    SYNTAX       CfprManagedObjectId
    MAX-ACCESS   not-accessible
    STATUS       current
    DESCRIPTION
        "Instance identifier of the managed object."
    ::= { cfprVnicIpV6StaticAddrEntry 1 }

cfprVnicIpV6StaticAddrDn OBJECT-TYPE
    SYNTAX       CfprManagedObjectDn
    MAX-ACCESS   read-only
    STATUS       current
    DESCRIPTION
        "Cisco Firepower vnic:IpV6StaticAddr:dn managed object property"
    ::= { cfprVnicIpV6StaticAddrEntry 2 }

cfprVnicIpV6StaticAddrRn OBJECT-TYPE
    SYNTAX       SnmpAdminString
    MAX-ACCESS   read-only
    STATUS       current
    DESCRIPTION
        "Cisco Firepower vnic:IpV6StaticAddr:rn managed object property"
    ::= { cfprVnicIpV6StaticAddrEntry 3 }

cfprVnicIpV6StaticAddrAddr OBJECT-TYPE
    SYNTAX       InetAddressIPv6
    MAX-ACCESS   read-only
    STATUS       current
    DESCRIPTION
        "Cisco Firepower vnic:IpV6StaticAddr:addr managed object property"
    ::= { cfprVnicIpV6StaticAddrEntry 4 }

cfprVnicIpV6StaticAddrDefGw OBJECT-TYPE
    SYNTAX       InetAddressIPv6
    MAX-ACCESS   read-only
    STATUS       current
    DESCRIPTION
        "Cisco Firepower vnic:IpV6StaticAddr:defGw managed
        object property"
    ::= { cfprVnicIpV6StaticAddrEntry 5 }

cfprVnicIpV6StaticAddrPrefix OBJECT-TYPE
    SYNTAX       Gauge32
    MAX-ACCESS   read-only
    STATUS       current
    DESCRIPTION
        "Cisco Firepower vnic:IpV6StaticAddr:prefix managed
        object property"
    ::= { cfprVnicIpV6StaticAddrEntry 6 }

cfprVnicIpV6StaticAddrPrimDns OBJECT-TYPE
    SYNTAX       InetAddressIPv6
    MAX-ACCESS   read-only
    STATUS       current
    DESCRIPTION
        "Cisco Firepower vnic:IpV6StaticAddr:primDns managed
        object property"
    ::= { cfprVnicIpV6StaticAddrEntry 7 }

cfprVnicIpV6StaticAddrSecDns OBJECT-TYPE
    SYNTAX       InetAddressIPv6
    MAX-ACCESS   read-only
    STATUS       current
    DESCRIPTION
        "Cisco Firepower vnic:IpV6StaticAddr:secDns managed
        object property"
    ::= { cfprVnicIpV6StaticAddrEntry 8 }

cfprVnicIpcTable OBJECT-TYPE
    SYNTAX           SEQUENCE OF CfprVnicIpcEntry
    MAX-ACCESS       not-accessible
    STATUS           current
    DESCRIPTION
        "Cisco Firepower vnic:Ipc managed object table"
    ::= { cfprVnicObjects 43 }

cfprVnicIpcEntry OBJECT-TYPE
    SYNTAX           CfprVnicIpcEntry
    MAX-ACCESS       not-accessible
    STATUS           current
    DESCRIPTION
        "Entry for the cfprVnicIpcTable table."
    INDEX { cfprVnicIpcInstanceId }
    ::= { cfprVnicIpcTable 1 }

CfprVnicIpcEntry ::= SEQUENCE {
    cfprVnicIpcInstanceId                                            CfprManagedObjectId,
    cfprVnicIpcDn                                                    CfprManagedObjectDn,
    cfprVnicIpcRn                                                    SnmpAdminString,
    cfprVnicIpcAdaptorProfileName                                    SnmpAdminString,
    cfprVnicIpcAddr                                                  MacAddress,
    cfprVnicIpcAdminHostPort                                         CfprFabricHostPortId,
    cfprVnicIpcAdminVcon                                             SnmpAdminString,
    cfprVnicIpcAppRole                                               CfprVnicAppRole,
    cfprVnicIpcBootDev                                               CfprVnicVnicBootDev,
    cfprVnicIpcConfigQualifier                                       CfprVnicConfigIssues,
    cfprVnicIpcConfigState                                           CfprLsConfigState,
    cfprVnicIpcEquipmentDn                                           SnmpAdminString,
    cfprVnicIpcIdentPoolName                                         SnmpAdminString,
    cfprVnicIpcInstType                                              CfprVnicInstantiation,
    cfprVnicIpcMtu                                                   Gauge32,
    cfprVnicIpcName                                                  SnmpAdminString,
    cfprVnicIpcNwCtrlPolicyName                                      SnmpAdminString,
    cfprVnicIpcNwTemplName                                           SnmpAdminString,
    cfprVnicIpcOperAdaptorProfileName                                SnmpAdminString,
    cfprVnicIpcOperHostPort                                          CfprVnicVnicOperHostPort,
    cfprVnicIpcOperIdentPoolName                                     SnmpAdminString,
    cfprVnicIpcOperNwCtrlPolicyName                                  SnmpAdminString,
    cfprVnicIpcOperNwTemplName                                       SnmpAdminString,
    cfprVnicIpcOperOrder                                             Gauge32,
    cfprVnicIpcOperPinToGroupName                                    SnmpAdminString,
    cfprVnicIpcOperQosPolicyName                                     SnmpAdminString,
    cfprVnicIpcOperSpeed                                             Gauge32,
    cfprVnicIpcOperStatsPolicyName                                   SnmpAdminString,
    cfprVnicIpcOperVcon                                              SnmpAdminString,
    cfprVnicIpcOrder                                                 Gauge32,
    cfprVnicIpcOwner                                                 CfprVnicConnectionOwner,
    cfprVnicIpcPinToGroupName                                        SnmpAdminString,
    cfprVnicIpcQosPolicyName                                         SnmpAdminString,
    cfprVnicIpcStatsPolicyName                                       SnmpAdminString,
    cfprVnicIpcSwitchId                                              CfprVnicEtherBaseSwitchId,
    cfprVnicIpcType                                                  CfprVnicIpcType
}

cfprVnicIpcInstanceId OBJECT-TYPE
    SYNTAX       CfprManagedObjectId
    MAX-ACCESS   not-accessible
    STATUS       current
    DESCRIPTION
        "Instance identifier of the managed object."
    ::= { cfprVnicIpcEntry 1 }

cfprVnicIpcDn OBJECT-TYPE
    SYNTAX       CfprManagedObjectDn
    MAX-ACCESS   read-only
    STATUS       current
    DESCRIPTION
        "Cisco Firepower vnic:Ipc:dn managed object property"
    ::= { cfprVnicIpcEntry 2 }

cfprVnicIpcRn OBJECT-TYPE
    SYNTAX       SnmpAdminString
    MAX-ACCESS   read-only
    STATUS       current
    DESCRIPTION
        "Cisco Firepower vnic:Ipc:rn managed object property"
    ::= { cfprVnicIpcEntry 3 }

cfprVnicIpcAdaptorProfileName OBJECT-TYPE
    SYNTAX       SnmpAdminString
    MAX-ACCESS   read-only
    STATUS       current
    DESCRIPTION
        "Cisco Firepower vnic:Ipc:adaptorProfileName managed
        object property"
    ::= { cfprVnicIpcEntry 4 }

cfprVnicIpcAddr OBJECT-TYPE
    SYNTAX       MacAddress
    MAX-ACCESS   read-only
    STATUS       current
    DESCRIPTION
        "Cisco Firepower vnic:Ipc:addr managed object property"
    ::= { cfprVnicIpcEntry 5 }

cfprVnicIpcAdminHostPort OBJECT-TYPE
    SYNTAX       CfprFabricHostPortId
    MAX-ACCESS   read-only
    STATUS       current
    DESCRIPTION
        "Cisco Firepower vnic:Ipc:adminHostPort managed object property"
    ::= { cfprVnicIpcEntry 6 }

cfprVnicIpcAdminVcon OBJECT-TYPE
    SYNTAX       SnmpAdminString
    MAX-ACCESS   read-only
    STATUS       current
    DESCRIPTION
        "Cisco Firepower vnic:Ipc:adminVcon managed object property"
    ::= { cfprVnicIpcEntry 7 }

cfprVnicIpcAppRole OBJECT-TYPE
    SYNTAX       CfprVnicAppRole
    MAX-ACCESS   read-only
    STATUS       current
    DESCRIPTION
        "Cisco Firepower vnic:Ipc:appRole managed object property"
    ::= { cfprVnicIpcEntry 8 }

cfprVnicIpcBootDev OBJECT-TYPE
    SYNTAX       CfprVnicVnicBootDev
    MAX-ACCESS   read-only
    STATUS       current
    DESCRIPTION
        "Cisco Firepower vnic:Ipc:bootDev managed object property"
    ::= { cfprVnicIpcEntry 9 }

cfprVnicIpcConfigQualifier OBJECT-TYPE
    SYNTAX       CfprVnicConfigIssues
    MAX-ACCESS   read-only
    STATUS       current
    DESCRIPTION
        "Cisco Firepower vnic:Ipc:configQualifier managed object property"
    ::= { cfprVnicIpcEntry 10 }

cfprVnicIpcConfigState OBJECT-TYPE
    SYNTAX       CfprLsConfigState
    MAX-ACCESS   read-only
    STATUS       current
    DESCRIPTION
        "Cisco Firepower vnic:Ipc:configState managed object property"
    ::= { cfprVnicIpcEntry 11 }

cfprVnicIpcEquipmentDn OBJECT-TYPE
    SYNTAX       SnmpAdminString
    MAX-ACCESS   read-only
    STATUS       current
    DESCRIPTION
        "Cisco Firepower vnic:Ipc:equipmentDn managed object property"
    ::= { cfprVnicIpcEntry 12 }

cfprVnicIpcIdentPoolName OBJECT-TYPE
    SYNTAX       SnmpAdminString
    MAX-ACCESS   read-only
    STATUS       current
    DESCRIPTION
        "Cisco Firepower vnic:Ipc:identPoolName managed object property"
    ::= { cfprVnicIpcEntry 13 }

cfprVnicIpcInstType OBJECT-TYPE
    SYNTAX       CfprVnicInstantiation
    MAX-ACCESS   read-only
    STATUS       current
    DESCRIPTION
        "Cisco Firepower vnic:Ipc:instType managed object property"
    ::= { cfprVnicIpcEntry 14 }

cfprVnicIpcMtu OBJECT-TYPE
    SYNTAX       Gauge32
    MAX-ACCESS   read-only
    STATUS       current
    DESCRIPTION
        "Cisco Firepower vnic:Ipc:mtu managed object property"
    ::= { cfprVnicIpcEntry 15 }

cfprVnicIpcName OBJECT-TYPE
    SYNTAX       SnmpAdminString
    MAX-ACCESS   read-only
    STATUS       current
    DESCRIPTION
        "Cisco Firepower vnic:Ipc:name managed object property"
    ::= { cfprVnicIpcEntry 16 }

cfprVnicIpcNwCtrlPolicyName OBJECT-TYPE
    SYNTAX       SnmpAdminString
    MAX-ACCESS   read-only
    STATUS       current
    DESCRIPTION
        "Cisco Firepower vnic:Ipc:nwCtrlPolicyName managed
        object property"
    ::= { cfprVnicIpcEntry 17 }

cfprVnicIpcNwTemplName OBJECT-TYPE
    SYNTAX       SnmpAdminString
    MAX-ACCESS   read-only
    STATUS       current
    DESCRIPTION
        "Cisco Firepower vnic:Ipc:nwTemplName managed object property"
    ::= { cfprVnicIpcEntry 18 }

cfprVnicIpcOperAdaptorProfileName OBJECT-TYPE
    SYNTAX       SnmpAdminString
    MAX-ACCESS   read-only
    STATUS       current
    DESCRIPTION
        "Cisco Firepower vnic:Ipc:operAdaptorProfileName
        managed object property"
    ::= { cfprVnicIpcEntry 19 }

cfprVnicIpcOperHostPort OBJECT-TYPE
    SYNTAX       CfprVnicVnicOperHostPort
    MAX-ACCESS   read-only
    STATUS       current
    DESCRIPTION
        "Cisco Firepower vnic:Ipc:operHostPort managed object property"
    ::= { cfprVnicIpcEntry 20 }

cfprVnicIpcOperIdentPoolName OBJECT-TYPE
    SYNTAX       SnmpAdminString
    MAX-ACCESS   read-only
    STATUS       current
    DESCRIPTION
        "Cisco Firepower vnic:Ipc:operIdentPoolName managed
        object property"
    ::= { cfprVnicIpcEntry 21 }

cfprVnicIpcOperNwCtrlPolicyName OBJECT-TYPE
    SYNTAX       SnmpAdminString
    MAX-ACCESS   read-only
    STATUS       current
    DESCRIPTION
        "Cisco Firepower vnic:Ipc:operNwCtrlPolicyName
        managed object property"
    ::= { cfprVnicIpcEntry 22 }

cfprVnicIpcOperNwTemplName OBJECT-TYPE
    SYNTAX       SnmpAdminString
    MAX-ACCESS   read-only
    STATUS       current
    DESCRIPTION
        "Cisco Firepower vnic:Ipc:operNwTemplName managed object property"
    ::= { cfprVnicIpcEntry 23 }

cfprVnicIpcOperOrder OBJECT-TYPE
    SYNTAX       Gauge32
    MAX-ACCESS   read-only
    STATUS       current
    DESCRIPTION
        "Cisco Firepower vnic:Ipc:operOrder managed object property"
    ::= { cfprVnicIpcEntry 24 }

cfprVnicIpcOperPinToGroupName OBJECT-TYPE
    SYNTAX       SnmpAdminString
    MAX-ACCESS   read-only
    STATUS       current
    DESCRIPTION
        "Cisco Firepower vnic:Ipc:operPinToGroupName managed
        object property"
    ::= { cfprVnicIpcEntry 25 }

cfprVnicIpcOperQosPolicyName OBJECT-TYPE
    SYNTAX       SnmpAdminString
    MAX-ACCESS   read-only
    STATUS       current
    DESCRIPTION
        "Cisco Firepower vnic:Ipc:operQosPolicyName managed
        object property"
    ::= { cfprVnicIpcEntry 26 }

cfprVnicIpcOperSpeed OBJECT-TYPE
    SYNTAX       Gauge32
    MAX-ACCESS   read-only
    STATUS       current
    DESCRIPTION
        "Cisco Firepower vnic:Ipc:operSpeed managed object property"
    ::= { cfprVnicIpcEntry 27 }

cfprVnicIpcOperStatsPolicyName OBJECT-TYPE
    SYNTAX       SnmpAdminString
    MAX-ACCESS   read-only
    STATUS       current
    DESCRIPTION
        "Cisco Firepower vnic:Ipc:operStatsPolicyName managed
        object property"
    ::= { cfprVnicIpcEntry 28 }

cfprVnicIpcOperVcon OBJECT-TYPE
    SYNTAX       SnmpAdminString
    MAX-ACCESS   read-only
    STATUS       current
    DESCRIPTION
        "Cisco Firepower vnic:Ipc:operVcon managed object property"
    ::= { cfprVnicIpcEntry 29 }

cfprVnicIpcOrder OBJECT-TYPE
    SYNTAX       Gauge32
    MAX-ACCESS   read-only
    STATUS       current
    DESCRIPTION
        "Cisco Firepower vnic:Ipc:order managed object property"
    ::= { cfprVnicIpcEntry 30 }

cfprVnicIpcOwner OBJECT-TYPE
    SYNTAX       CfprVnicConnectionOwner
    MAX-ACCESS   read-only
    STATUS       current
    DESCRIPTION
        "Cisco Firepower vnic:Ipc:owner managed object property"
    ::= { cfprVnicIpcEntry 31 }

cfprVnicIpcPinToGroupName OBJECT-TYPE
    SYNTAX       SnmpAdminString
    MAX-ACCESS   read-only
    STATUS       current
    DESCRIPTION
        "Cisco Firepower vnic:Ipc:pinToGroupName managed object property"
    ::= { cfprVnicIpcEntry 32 }

cfprVnicIpcQosPolicyName OBJECT-TYPE
    SYNTAX       SnmpAdminString
    MAX-ACCESS   read-only
    STATUS       current
    DESCRIPTION
        "Cisco Firepower vnic:Ipc:qosPolicyName managed object property"
    ::= { cfprVnicIpcEntry 33 }

cfprVnicIpcStatsPolicyName OBJECT-TYPE
    SYNTAX       SnmpAdminString
    MAX-ACCESS   read-only
    STATUS       current
    DESCRIPTION
        "Cisco Firepower vnic:Ipc:statsPolicyName managed object property"
    ::= { cfprVnicIpcEntry 34 }

cfprVnicIpcSwitchId OBJECT-TYPE
    SYNTAX       CfprVnicEtherBaseSwitchId
    MAX-ACCESS   read-only
    STATUS       current
    DESCRIPTION
        "Cisco Firepower vnic:Ipc:switchId managed object property"
    ::= { cfprVnicIpcEntry 35 }

cfprVnicIpcType OBJECT-TYPE
    SYNTAX       CfprVnicIpcType
    MAX-ACCESS   read-only
    STATUS       current
    DESCRIPTION
        "Cisco Firepower vnic:Ipc:type managed object property"
    ::= { cfprVnicIpcEntry 36 }

cfprVnicIpcIfTable OBJECT-TYPE
    SYNTAX           SEQUENCE OF CfprVnicIpcIfEntry
    MAX-ACCESS       not-accessible
    STATUS           current
    DESCRIPTION
        "Cisco Firepower vnic:IpcIf managed object table"
    ::= { cfprVnicObjects 44 }

cfprVnicIpcIfEntry OBJECT-TYPE
    SYNTAX           CfprVnicIpcIfEntry
    MAX-ACCESS       not-accessible
    STATUS           current
    DESCRIPTION
        "Entry for the cfprVnicIpcIfTable table."
    INDEX { cfprVnicIpcIfInstanceId }
    ::= { cfprVnicIpcIfTable 1 }

CfprVnicIpcIfEntry ::= SEQUENCE {
    cfprVnicIpcIfInstanceId                                          CfprManagedObjectId,
    cfprVnicIpcIfDn                                                  CfprManagedObjectDn,
    cfprVnicIpcIfRn                                                  SnmpAdminString,
    cfprVnicIpcIfAddr                                                MacAddress,
    cfprVnicIpcIfConfigQualifier                                     CfprVnicConfigIssues,
    cfprVnicIpcIfDefaultNet                                          TruthValue,
    cfprVnicIpcIfName                                                SnmpAdminString,
    cfprVnicIpcIfOperState                                           CfprVnicIfOperState,
    cfprVnicIpcIfOperVnetDn                                          SnmpAdminString,
    cfprVnicIpcIfOperVnetName                                        SnmpAdminString,
    cfprVnicIpcIfOwner                                               CfprVnicConnectionOwner,
    cfprVnicIpcIfPubNwId                                             Gauge32,
    cfprVnicIpcIfSharing                                             CfprFabricVlanSharingType,
    cfprVnicIpcIfSwitchId                                            CfprVnicL2IfSwitchId,
    cfprVnicIpcIfType                                                CfprVnicAIpcIfType,
    cfprVnicIpcIfVnet                                                Gauge32
}

cfprVnicIpcIfInstanceId OBJECT-TYPE
    SYNTAX       CfprManagedObjectId
    MAX-ACCESS   not-accessible
    STATUS       current
    DESCRIPTION
        "Instance identifier of the managed object."
    ::= { cfprVnicIpcIfEntry 1 }

cfprVnicIpcIfDn OBJECT-TYPE
    SYNTAX       CfprManagedObjectDn
    MAX-ACCESS   read-only
    STATUS       current
    DESCRIPTION
        "Cisco Firepower vnic:IpcIf:dn managed object property"
    ::= { cfprVnicIpcIfEntry 2 }

cfprVnicIpcIfRn OBJECT-TYPE
    SYNTAX       SnmpAdminString
    MAX-ACCESS   read-only
    STATUS       current
    DESCRIPTION
        "Cisco Firepower vnic:IpcIf:rn managed object property"
    ::= { cfprVnicIpcIfEntry 3 }

cfprVnicIpcIfAddr OBJECT-TYPE
    SYNTAX       MacAddress
    MAX-ACCESS   read-only
    STATUS       current
    DESCRIPTION
        "Cisco Firepower vnic:IpcIf:addr managed object property"
    ::= { cfprVnicIpcIfEntry 4 }

cfprVnicIpcIfConfigQualifier OBJECT-TYPE
    SYNTAX       CfprVnicConfigIssues
    MAX-ACCESS   read-only
    STATUS       current
    DESCRIPTION
        "Cisco Firepower vnic:IpcIf:configQualifier managed
        object property"
    ::= { cfprVnicIpcIfEntry 5 }

cfprVnicIpcIfDefaultNet OBJECT-TYPE
    SYNTAX       TruthValue
    MAX-ACCESS   read-only
    STATUS       current
    DESCRIPTION
        "Cisco Firepower vnic:IpcIf:defaultNet managed object property"
    ::= { cfprVnicIpcIfEntry 6 }

cfprVnicIpcIfName OBJECT-TYPE
    SYNTAX       SnmpAdminString
    MAX-ACCESS   read-only
    STATUS       current
    DESCRIPTION
        "Cisco Firepower vnic:IpcIf:name managed object property"
    ::= { cfprVnicIpcIfEntry 7 }

cfprVnicIpcIfOperState OBJECT-TYPE
    SYNTAX       CfprVnicIfOperState
    MAX-ACCESS   read-only
    STATUS       current
    DESCRIPTION
        "Cisco Firepower vnic:IpcIf:operState managed object property"
    ::= { cfprVnicIpcIfEntry 8 }

cfprVnicIpcIfOperVnetDn OBJECT-TYPE
    SYNTAX       SnmpAdminString
    MAX-ACCESS   read-only
    STATUS       current
    DESCRIPTION
        "Cisco Firepower vnic:IpcIf:operVnetDn managed object property"
    ::= { cfprVnicIpcIfEntry 9 }

cfprVnicIpcIfOperVnetName OBJECT-TYPE
    SYNTAX       SnmpAdminString
    MAX-ACCESS   read-only
    STATUS       current
    DESCRIPTION
        "Cisco Firepower vnic:IpcIf:operVnetName managed object property"
    ::= { cfprVnicIpcIfEntry 10 }

cfprVnicIpcIfOwner OBJECT-TYPE
    SYNTAX       CfprVnicConnectionOwner
    MAX-ACCESS   read-only
    STATUS       current
    DESCRIPTION
        "Cisco Firepower vnic:IpcIf:owner managed object property"
    ::= { cfprVnicIpcIfEntry 11 }

cfprVnicIpcIfPubNwId OBJECT-TYPE
    SYNTAX       Gauge32
    MAX-ACCESS   read-only
    STATUS       current
    DESCRIPTION
        "Cisco Firepower vnic:IpcIf:pubNwId managed object property"
    ::= { cfprVnicIpcIfEntry 12 }

cfprVnicIpcIfSharing OBJECT-TYPE
    SYNTAX       CfprFabricVlanSharingType
    MAX-ACCESS   read-only
    STATUS       current
    DESCRIPTION
        "Cisco Firepower vnic:IpcIf:sharing managed object property"
    ::= { cfprVnicIpcIfEntry 13 }

cfprVnicIpcIfSwitchId OBJECT-TYPE
    SYNTAX       CfprVnicL2IfSwitchId
    MAX-ACCESS   read-only
    STATUS       current
    DESCRIPTION
        "Cisco Firepower vnic:IpcIf:switchId managed object property"
    ::= { cfprVnicIpcIfEntry 14 }

cfprVnicIpcIfType OBJECT-TYPE
    SYNTAX       CfprVnicAIpcIfType
    MAX-ACCESS   read-only
    STATUS       current
    DESCRIPTION
        "Cisco Firepower vnic:IpcIf:type managed object property"
    ::= { cfprVnicIpcIfEntry 15 }

cfprVnicIpcIfVnet OBJECT-TYPE
    SYNTAX       Gauge32
    MAX-ACCESS   read-only
    STATUS       current
    DESCRIPTION
        "Cisco Firepower vnic:IpcIf:vnet managed object property"
    ::= { cfprVnicIpcIfEntry 16 }

cfprVnicIqnHistoryTable OBJECT-TYPE
    SYNTAX           SEQUENCE OF CfprVnicIqnHistoryEntry
    MAX-ACCESS       not-accessible
    STATUS           current
    DESCRIPTION
        "Cisco Firepower vnic:IqnHistory managed object table"
    ::= { cfprVnicObjects 45 }

cfprVnicIqnHistoryEntry OBJECT-TYPE
    SYNTAX           CfprVnicIqnHistoryEntry
    MAX-ACCESS       not-accessible
    STATUS           current
    DESCRIPTION
        "Entry for the cfprVnicIqnHistoryTable table."
    INDEX { cfprVnicIqnHistoryInstanceId }
    ::= { cfprVnicIqnHistoryTable 1 }

CfprVnicIqnHistoryEntry ::= SEQUENCE {
    cfprVnicIqnHistoryInstanceId                                     CfprManagedObjectId,
    cfprVnicIqnHistoryDn                                             CfprManagedObjectDn,
    cfprVnicIqnHistoryRn                                             SnmpAdminString,
    cfprVnicIqnHistoryOldInitiatorName                               SnmpAdminString
}

cfprVnicIqnHistoryInstanceId OBJECT-TYPE
    SYNTAX       CfprManagedObjectId
    MAX-ACCESS   not-accessible
    STATUS       current
    DESCRIPTION
        "Instance identifier of the managed object."
    ::= { cfprVnicIqnHistoryEntry 1 }

cfprVnicIqnHistoryDn OBJECT-TYPE
    SYNTAX       CfprManagedObjectDn
    MAX-ACCESS   read-only
    STATUS       current
    DESCRIPTION
        "Cisco Firepower vnic:IqnHistory:dn managed object property"
    ::= { cfprVnicIqnHistoryEntry 2 }

cfprVnicIqnHistoryRn OBJECT-TYPE
    SYNTAX       SnmpAdminString
    MAX-ACCESS   read-only
    STATUS       current
    DESCRIPTION
        "Cisco Firepower vnic:IqnHistory:rn managed object property"
    ::= { cfprVnicIqnHistoryEntry 3 }

cfprVnicIqnHistoryOldInitiatorName OBJECT-TYPE
    SYNTAX       SnmpAdminString
    MAX-ACCESS   read-only
    STATUS       current
    DESCRIPTION
        "Cisco Firepower vnic:IqnHistory:oldInitiatorName
        managed object property"
    ::= { cfprVnicIqnHistoryEntry 4 }

cfprVnicLanConnPolicyTable OBJECT-TYPE
    SYNTAX           SEQUENCE OF CfprVnicLanConnPolicyEntry
    MAX-ACCESS       not-accessible
    STATUS           current
    DESCRIPTION
        "Cisco Firepower vnic:LanConnPolicy managed object table"
    ::= { cfprVnicObjects 46 }

cfprVnicLanConnPolicyEntry OBJECT-TYPE
    SYNTAX           CfprVnicLanConnPolicyEntry
    MAX-ACCESS       not-accessible
    STATUS           current
    DESCRIPTION
        "Entry for the cfprVnicLanConnPolicyTable table."
    INDEX { cfprVnicLanConnPolicyInstanceId }
    ::= { cfprVnicLanConnPolicyTable 1 }

CfprVnicLanConnPolicyEntry ::= SEQUENCE {
    cfprVnicLanConnPolicyInstanceId                                  CfprManagedObjectId,
    cfprVnicLanConnPolicyDn                                          CfprManagedObjectDn,
    cfprVnicLanConnPolicyRn                                          SnmpAdminString,
    cfprVnicLanConnPolicyDescr                                       SnmpAdminString,
    cfprVnicLanConnPolicyFltAggr                                     Unsigned64,
    cfprVnicLanConnPolicyIntId                                       SnmpAdminString,
    cfprVnicLanConnPolicyName                                        SnmpAdminString,
    cfprVnicLanConnPolicyPolicyLevel                                 Gauge32,
    cfprVnicLanConnPolicyPolicyOwner                                 CfprPolicyPolicyOwner
}

cfprVnicLanConnPolicyInstanceId OBJECT-TYPE
    SYNTAX       CfprManagedObjectId
    MAX-ACCESS   not-accessible
    STATUS       current
    DESCRIPTION
        "Instance identifier of the managed object."
    ::= { cfprVnicLanConnPolicyEntry 1 }

cfprVnicLanConnPolicyDn OBJECT-TYPE
    SYNTAX       CfprManagedObjectDn
    MAX-ACCESS   read-only
    STATUS       current
    DESCRIPTION
        "Cisco Firepower vnic:LanConnPolicy:dn managed object property"
    ::= { cfprVnicLanConnPolicyEntry 2 }

cfprVnicLanConnPolicyRn OBJECT-TYPE
    SYNTAX       SnmpAdminString
    MAX-ACCESS   read-only
    STATUS       current
    DESCRIPTION
        "Cisco Firepower vnic:LanConnPolicy:rn managed object property"
    ::= { cfprVnicLanConnPolicyEntry 3 }

cfprVnicLanConnPolicyDescr OBJECT-TYPE
    SYNTAX       SnmpAdminString
    MAX-ACCESS   read-only
    STATUS       current
    DESCRIPTION
        "Cisco Firepower vnic:LanConnPolicy:descr managed object property"
    ::= { cfprVnicLanConnPolicyEntry 4 }

cfprVnicLanConnPolicyFltAggr OBJECT-TYPE
    SYNTAX       Unsigned64
    MAX-ACCESS   read-only
    STATUS       current
    DESCRIPTION
        "Cisco Firepower vnic:LanConnPolicy:fltAggr managed
        object property"
    ::= { cfprVnicLanConnPolicyEntry 5 }

cfprVnicLanConnPolicyIntId OBJECT-TYPE
    SYNTAX       SnmpAdminString
    MAX-ACCESS   read-only
    STATUS       current
    DESCRIPTION
        "Cisco Firepower vnic:LanConnPolicy:intId managed object property"
    ::= { cfprVnicLanConnPolicyEntry 6 }

cfprVnicLanConnPolicyName OBJECT-TYPE
    SYNTAX       SnmpAdminString
    MAX-ACCESS   read-only
    STATUS       current
    DESCRIPTION
        "Cisco Firepower vnic:LanConnPolicy:name managed object property"
    ::= { cfprVnicLanConnPolicyEntry 7 }

cfprVnicLanConnPolicyPolicyLevel OBJECT-TYPE
    SYNTAX       Gauge32
    MAX-ACCESS   read-only
    STATUS       current
    DESCRIPTION
        "Cisco Firepower vnic:LanConnPolicy:policyLevel
        managed object property"
    ::= { cfprVnicLanConnPolicyEntry 8 }

cfprVnicLanConnPolicyPolicyOwner OBJECT-TYPE
    SYNTAX       CfprPolicyPolicyOwner
    MAX-ACCESS   read-only
    STATUS       current
    DESCRIPTION
        "Cisco Firepower vnic:LanConnPolicy:policyOwner
        managed object property"
    ::= { cfprVnicLanConnPolicyEntry 9 }

cfprVnicLanConnTemplTable OBJECT-TYPE
    SYNTAX           SEQUENCE OF CfprVnicLanConnTemplEntry
    MAX-ACCESS       not-accessible
    STATUS           current
    DESCRIPTION
        "Cisco Firepower vnic:LanConnTempl managed object table"
    ::= { cfprVnicObjects 47 }

cfprVnicLanConnTemplEntry OBJECT-TYPE
    SYNTAX           CfprVnicLanConnTemplEntry
    MAX-ACCESS       not-accessible
    STATUS           current
    DESCRIPTION
        "Entry for the cfprVnicLanConnTemplTable table."
    INDEX { cfprVnicLanConnTemplInstanceId }
    ::= { cfprVnicLanConnTemplTable 1 }

CfprVnicLanConnTemplEntry ::= SEQUENCE {
    cfprVnicLanConnTemplInstanceId                                   CfprManagedObjectId,
    cfprVnicLanConnTemplDn                                           CfprManagedObjectDn,
    cfprVnicLanConnTemplRn                                           SnmpAdminString,
    cfprVnicLanConnTemplDescr                                        SnmpAdminString,
    cfprVnicLanConnTemplIdentPoolName                                SnmpAdminString,
    cfprVnicLanConnTemplIntId                                        SnmpAdminString,
    cfprVnicLanConnTemplMtu                                          Gauge32,
    cfprVnicLanConnTemplName                                         SnmpAdminString,
    cfprVnicLanConnTemplNwCtrlPolicyName                             SnmpAdminString,
    cfprVnicLanConnTemplOperIdentPoolName                            SnmpAdminString,
    cfprVnicLanConnTemplOperNwCtrlPolicyName                         SnmpAdminString,
    cfprVnicLanConnTemplOperQosPolicyName                            SnmpAdminString,
    cfprVnicLanConnTemplOperStatsPolicyName                          SnmpAdminString,
    cfprVnicLanConnTemplPinToGroupName                               SnmpAdminString,
    cfprVnicLanConnTemplPolicyLevel                                  Gauge32,
    cfprVnicLanConnTemplPolicyOwner                                  CfprPolicyPolicyOwner,
    cfprVnicLanConnTemplQosPolicyName                                SnmpAdminString,
    cfprVnicLanConnTemplStatsPolicyName                              SnmpAdminString,
    cfprVnicLanConnTemplSwitchId                                     CfprVnicLanConnTemplSwitchId,
    cfprVnicLanConnTemplTarget                                       CfprVnicTemplateTarget,
    cfprVnicLanConnTemplTemplType                                    CfprVnicTemplateType
}

cfprVnicLanConnTemplInstanceId OBJECT-TYPE
    SYNTAX       CfprManagedObjectId
    MAX-ACCESS   not-accessible
    STATUS       current
    DESCRIPTION
        "Instance identifier of the managed object."
    ::= { cfprVnicLanConnTemplEntry 1 }

cfprVnicLanConnTemplDn OBJECT-TYPE
    SYNTAX       CfprManagedObjectDn
    MAX-ACCESS   read-only
    STATUS       current
    DESCRIPTION
        "Cisco Firepower vnic:LanConnTempl:dn managed object property"
    ::= { cfprVnicLanConnTemplEntry 2 }

cfprVnicLanConnTemplRn OBJECT-TYPE
    SYNTAX       SnmpAdminString
    MAX-ACCESS   read-only
    STATUS       current
    DESCRIPTION
        "Cisco Firepower vnic:LanConnTempl:rn managed object property"
    ::= { cfprVnicLanConnTemplEntry 3 }

cfprVnicLanConnTemplDescr OBJECT-TYPE
    SYNTAX       SnmpAdminString
    MAX-ACCESS   read-only
    STATUS       current
    DESCRIPTION
        "Cisco Firepower vnic:LanConnTempl:descr managed object property"
    ::= { cfprVnicLanConnTemplEntry 4 }

cfprVnicLanConnTemplIdentPoolName OBJECT-TYPE
    SYNTAX       SnmpAdminString
    MAX-ACCESS   read-only
    STATUS       current
    DESCRIPTION
        "Cisco Firepower vnic:LanConnTempl:identPoolName
        managed object property"
    ::= { cfprVnicLanConnTemplEntry 5 }

cfprVnicLanConnTemplIntId OBJECT-TYPE
    SYNTAX       SnmpAdminString
    MAX-ACCESS   read-only
    STATUS       current
    DESCRIPTION
        "Cisco Firepower vnic:LanConnTempl:intId managed object property"
    ::= { cfprVnicLanConnTemplEntry 6 }

cfprVnicLanConnTemplMtu OBJECT-TYPE
    SYNTAX       Gauge32
    MAX-ACCESS   read-only
    STATUS       current
    DESCRIPTION
        "Cisco Firepower vnic:LanConnTempl:mtu managed object property"
    ::= { cfprVnicLanConnTemplEntry 7 }

cfprVnicLanConnTemplName OBJECT-TYPE
    SYNTAX       SnmpAdminString
    MAX-ACCESS   read-only
    STATUS       current
    DESCRIPTION
        "Cisco Firepower vnic:LanConnTempl:name managed object property"
    ::= { cfprVnicLanConnTemplEntry 8 }

cfprVnicLanConnTemplNwCtrlPolicyName OBJECT-TYPE
    SYNTAX       SnmpAdminString
    MAX-ACCESS   read-only
    STATUS       current
    DESCRIPTION
        "Cisco Firepower vnic:LanConnTempl:nwCtrlPolicyName
        managed object property"
    ::= { cfprVnicLanConnTemplEntry 9 }

cfprVnicLanConnTemplOperIdentPoolName OBJECT-TYPE
    SYNTAX       SnmpAdminString
    MAX-ACCESS   read-only
    STATUS       current
    DESCRIPTION
        "Cisco Firepower vnic:LanConnTempl:operIdentPoolName
        managed object property"
    ::= { cfprVnicLanConnTemplEntry 10 }

cfprVnicLanConnTemplOperNwCtrlPolicyName OBJECT-TYPE
    SYNTAX       SnmpAdminString
    MAX-ACCESS   read-only
    STATUS       current
    DESCRIPTION
        "Cisco Firepower vnic:LanConnTempl:operNwCtrlPolicyName
        managed object property"
    ::= { cfprVnicLanConnTemplEntry 11 }

cfprVnicLanConnTemplOperQosPolicyName OBJECT-TYPE
    SYNTAX       SnmpAdminString
    MAX-ACCESS   read-only
    STATUS       current
    DESCRIPTION
        "Cisco Firepower vnic:LanConnTempl:operQosPolicyName
        managed object property"
    ::= { cfprVnicLanConnTemplEntry 12 }

cfprVnicLanConnTemplOperStatsPolicyName OBJECT-TYPE
    SYNTAX       SnmpAdminString
    MAX-ACCESS   read-only
    STATUS       current
    DESCRIPTION
        "Cisco Firepower vnic:LanConnTempl:operStatsPolicyName
        managed object property"
    ::= { cfprVnicLanConnTemplEntry 13 }

cfprVnicLanConnTemplPinToGroupName OBJECT-TYPE
    SYNTAX       SnmpAdminString
    MAX-ACCESS   read-only
    STATUS       current
    DESCRIPTION
        "Cisco Firepower vnic:LanConnTempl:pinToGroupName
        managed object property"
    ::= { cfprVnicLanConnTemplEntry 14 }

cfprVnicLanConnTemplPolicyLevel OBJECT-TYPE
    SYNTAX       Gauge32
    MAX-ACCESS   read-only
    STATUS       current
    DESCRIPTION
        "Cisco Firepower vnic:LanConnTempl:policyLevel
        managed object property"
    ::= { cfprVnicLanConnTemplEntry 15 }

cfprVnicLanConnTemplPolicyOwner OBJECT-TYPE
    SYNTAX       CfprPolicyPolicyOwner
    MAX-ACCESS   read-only
    STATUS       current
    DESCRIPTION
        "Cisco Firepower vnic:LanConnTempl:policyOwner
        managed object property"
    ::= { cfprVnicLanConnTemplEntry 16 }

cfprVnicLanConnTemplQosPolicyName OBJECT-TYPE
    SYNTAX       SnmpAdminString
    MAX-ACCESS   read-only
    STATUS       current
    DESCRIPTION
        "Cisco Firepower vnic:LanConnTempl:qosPolicyName
        managed object property"
    ::= { cfprVnicLanConnTemplEntry 17 }

cfprVnicLanConnTemplStatsPolicyName OBJECT-TYPE
    SYNTAX       SnmpAdminString
    MAX-ACCESS   read-only
    STATUS       current
    DESCRIPTION
        "Cisco Firepower vnic:LanConnTempl:statsPolicyName
        managed object property"
    ::= { cfprVnicLanConnTemplEntry 18 }

cfprVnicLanConnTemplSwitchId OBJECT-TYPE
    SYNTAX       CfprVnicLanConnTemplSwitchId
    MAX-ACCESS   read-only
    STATUS       current
    DESCRIPTION
        "Cisco Firepower vnic:LanConnTempl:switchId managed
        object property"
    ::= { cfprVnicLanConnTemplEntry 19 }

cfprVnicLanConnTemplTarget OBJECT-TYPE
    SYNTAX       CfprVnicTemplateTarget
    MAX-ACCESS   read-only
    STATUS       current
    DESCRIPTION
        "Cisco Firepower vnic:LanConnTempl:target managed object property"
    ::= { cfprVnicLanConnTemplEntry 20 }

cfprVnicLanConnTemplTemplType OBJECT-TYPE
    SYNTAX       CfprVnicTemplateType
    MAX-ACCESS   read-only
    STATUS       current
    DESCRIPTION
        "Cisco Firepower vnic:LanConnTempl:templType managed
        object property"
    ::= { cfprVnicLanConnTemplEntry 21 }

cfprVnicLifVlanTable OBJECT-TYPE
    SYNTAX           SEQUENCE OF CfprVnicLifVlanEntry
    MAX-ACCESS       not-accessible
    STATUS           current
    DESCRIPTION
        "Cisco Firepower vnic:LifVlan managed object table"
    ::= { cfprVnicObjects 48 }

cfprVnicLifVlanEntry OBJECT-TYPE
    SYNTAX           CfprVnicLifVlanEntry
    MAX-ACCESS       not-accessible
    STATUS           current
    DESCRIPTION
        "Entry for the cfprVnicLifVlanTable table."
    INDEX { cfprVnicLifVlanInstanceId }
    ::= { cfprVnicLifVlanTable 1 }

CfprVnicLifVlanEntry ::= SEQUENCE {
    cfprVnicLifVlanInstanceId                                        CfprManagedObjectId,
    cfprVnicLifVlanDn                                                CfprManagedObjectDn,
    cfprVnicLifVlanRn                                                SnmpAdminString,
    cfprVnicLifVlanAddr                                              MacAddress,
    cfprVnicLifVlanConfigQualifier                                   CfprVnicConfigIssues,
    cfprVnicLifVlanDefaultNet                                        TruthValue,
    cfprVnicLifVlanName                                              SnmpAdminString,
    cfprVnicLifVlanOperState                                         CfprVnicIfOperState,
    cfprVnicLifVlanOperVnetDn                                        SnmpAdminString,
    cfprVnicLifVlanOperVnetName                                      SnmpAdminString,
    cfprVnicLifVlanOwner                                             CfprVnicConnectionOwner,
    cfprVnicLifVlanPubNwId                                           Gauge32,
    cfprVnicLifVlanSharing                                           CfprFabricVlanSharingType,
    cfprVnicLifVlanSwitchId                                          CfprVnicL2IfSwitchId,
    cfprVnicLifVlanType                                              CfprVnicAEtherIfType,
    cfprVnicLifVlanVnet                                              Gauge32
}

cfprVnicLifVlanInstanceId OBJECT-TYPE
    SYNTAX       CfprManagedObjectId
    MAX-ACCESS   not-accessible
    STATUS       current
    DESCRIPTION
        "Instance identifier of the managed object."
    ::= { cfprVnicLifVlanEntry 1 }

cfprVnicLifVlanDn OBJECT-TYPE
    SYNTAX       CfprManagedObjectDn
    MAX-ACCESS   read-only
    STATUS       current
    DESCRIPTION
        "Cisco Firepower vnic:LifVlan:dn managed object property"
    ::= { cfprVnicLifVlanEntry 2 }

cfprVnicLifVlanRn OBJECT-TYPE
    SYNTAX       SnmpAdminString
    MAX-ACCESS   read-only
    STATUS       current
    DESCRIPTION
        "Cisco Firepower vnic:LifVlan:rn managed object property"
    ::= { cfprVnicLifVlanEntry 3 }

cfprVnicLifVlanAddr OBJECT-TYPE
    SYNTAX       MacAddress
    MAX-ACCESS   read-only
    STATUS       current
    DESCRIPTION
        "Cisco Firepower vnic:LifVlan:addr managed object property"
    ::= { cfprVnicLifVlanEntry 4 }

cfprVnicLifVlanConfigQualifier OBJECT-TYPE
    SYNTAX       CfprVnicConfigIssues
    MAX-ACCESS   read-only
    STATUS       current
    DESCRIPTION
        "Cisco Firepower vnic:LifVlan:configQualifier managed
        object property"
    ::= { cfprVnicLifVlanEntry 5 }

cfprVnicLifVlanDefaultNet OBJECT-TYPE
    SYNTAX       TruthValue
    MAX-ACCESS   read-only
    STATUS       current
    DESCRIPTION
        "Cisco Firepower vnic:LifVlan:defaultNet managed object property"
    ::= { cfprVnicLifVlanEntry 6 }

cfprVnicLifVlanName OBJECT-TYPE
    SYNTAX       SnmpAdminString
    MAX-ACCESS   read-only
    STATUS       current
    DESCRIPTION
        "Cisco Firepower vnic:LifVlan:name managed object property"
    ::= { cfprVnicLifVlanEntry 7 }

cfprVnicLifVlanOperState OBJECT-TYPE
    SYNTAX       CfprVnicIfOperState
    MAX-ACCESS   read-only
    STATUS       current
    DESCRIPTION
        "Cisco Firepower vnic:LifVlan:operState managed object property"
    ::= { cfprVnicLifVlanEntry 8 }

cfprVnicLifVlanOperVnetDn OBJECT-TYPE
    SYNTAX       SnmpAdminString
    MAX-ACCESS   read-only
    STATUS       current
    DESCRIPTION
        "Cisco Firepower vnic:LifVlan:operVnetDn managed object property"
    ::= { cfprVnicLifVlanEntry 9 }

cfprVnicLifVlanOperVnetName OBJECT-TYPE
    SYNTAX       SnmpAdminString
    MAX-ACCESS   read-only
    STATUS       current
    DESCRIPTION
        "Cisco Firepower vnic:LifVlan:operVnetName managed
        object property"
    ::= { cfprVnicLifVlanEntry 10 }

cfprVnicLifVlanOwner OBJECT-TYPE
    SYNTAX       CfprVnicConnectionOwner
    MAX-ACCESS   read-only
    STATUS       current
    DESCRIPTION
        "Cisco Firepower vnic:LifVlan:owner managed object property"
    ::= { cfprVnicLifVlanEntry 11 }

cfprVnicLifVlanPubNwId OBJECT-TYPE
    SYNTAX       Gauge32
    MAX-ACCESS   read-only
    STATUS       current
    DESCRIPTION
        "Cisco Firepower vnic:LifVlan:pubNwId managed object property"
    ::= { cfprVnicLifVlanEntry 12 }

cfprVnicLifVlanSharing OBJECT-TYPE
    SYNTAX       CfprFabricVlanSharingType
    MAX-ACCESS   read-only
    STATUS       current
    DESCRIPTION
        "Cisco Firepower vnic:LifVlan:sharing managed object property"
    ::= { cfprVnicLifVlanEntry 13 }

cfprVnicLifVlanSwitchId OBJECT-TYPE
    SYNTAX       CfprVnicL2IfSwitchId
    MAX-ACCESS   read-only
    STATUS       current
    DESCRIPTION
        "Cisco Firepower vnic:LifVlan:switchId managed object property"
    ::= { cfprVnicLifVlanEntry 14 }

cfprVnicLifVlanType OBJECT-TYPE
    SYNTAX       CfprVnicAEtherIfType
    MAX-ACCESS   read-only
    STATUS       current
    DESCRIPTION
        "Cisco Firepower vnic:LifVlan:type managed object property"
    ::= { cfprVnicLifVlanEntry 15 }

cfprVnicLifVlanVnet OBJECT-TYPE
    SYNTAX       Gauge32
    MAX-ACCESS   read-only
    STATUS       current
    DESCRIPTION
        "Cisco Firepower vnic:LifVlan:vnet managed object property"
    ::= { cfprVnicLifVlanEntry 16 }

cfprVnicLifVsanTable OBJECT-TYPE
    SYNTAX           SEQUENCE OF CfprVnicLifVsanEntry
    MAX-ACCESS       not-accessible
    STATUS           current
    DESCRIPTION
        "Cisco Firepower vnic:LifVsan managed object table"
    ::= { cfprVnicObjects 49 }

cfprVnicLifVsanEntry OBJECT-TYPE
    SYNTAX           CfprVnicLifVsanEntry
    MAX-ACCESS       not-accessible
    STATUS           current
    DESCRIPTION
        "Entry for the cfprVnicLifVsanTable table."
    INDEX { cfprVnicLifVsanInstanceId }
    ::= { cfprVnicLifVsanTable 1 }

CfprVnicLifVsanEntry ::= SEQUENCE {
    cfprVnicLifVsanInstanceId                                        CfprManagedObjectId,
    cfprVnicLifVsanDn                                                CfprManagedObjectDn,
    cfprVnicLifVsanRn                                                SnmpAdminString,
    cfprVnicLifVsanConfigQualifier                                   CfprVnicConfigIssues,
    cfprVnicLifVsanInitiator                                         Unsigned64,
    cfprVnicLifVsanName                                              SnmpAdminString,
    cfprVnicLifVsanOperState                                         CfprVnicIfOperState,
    cfprVnicLifVsanOperVnetDn                                        SnmpAdminString,
    cfprVnicLifVsanOperVnetName                                      SnmpAdminString,
    cfprVnicLifVsanOwner                                             CfprVnicConnectionOwner,
    cfprVnicLifVsanPubNwId                                           Gauge32,
    cfprVnicLifVsanSharing                                           CfprFabricVlanSharingType,
    cfprVnicLifVsanSwitchId                                          CfprVnicL2IfSwitchId,
    cfprVnicLifVsanType                                              CfprVnicAFcIfType,
    cfprVnicLifVsanVnet                                              Gauge32
}

cfprVnicLifVsanInstanceId OBJECT-TYPE
    SYNTAX       CfprManagedObjectId
    MAX-ACCESS   not-accessible
    STATUS       current
    DESCRIPTION
        "Instance identifier of the managed object."
    ::= { cfprVnicLifVsanEntry 1 }

cfprVnicLifVsanDn OBJECT-TYPE
    SYNTAX       CfprManagedObjectDn
    MAX-ACCESS   read-only
    STATUS       current
    DESCRIPTION
        "Cisco Firepower vnic:LifVsan:dn managed object property"
    ::= { cfprVnicLifVsanEntry 2 }

cfprVnicLifVsanRn OBJECT-TYPE
    SYNTAX       SnmpAdminString
    MAX-ACCESS   read-only
    STATUS       current
    DESCRIPTION
        "Cisco Firepower vnic:LifVsan:rn managed object property"
    ::= { cfprVnicLifVsanEntry 3 }

cfprVnicLifVsanConfigQualifier OBJECT-TYPE
    SYNTAX       CfprVnicConfigIssues
    MAX-ACCESS   read-only
    STATUS       current
    DESCRIPTION
        "Cisco Firepower vnic:LifVsan:configQualifier managed
        object property"
    ::= { cfprVnicLifVsanEntry 4 }

cfprVnicLifVsanInitiator OBJECT-TYPE
    SYNTAX       Unsigned64
    MAX-ACCESS   read-only
    STATUS       current
    DESCRIPTION
        "Cisco Firepower vnic:LifVsan:initiator managed object property"
    ::= { cfprVnicLifVsanEntry 5 }

cfprVnicLifVsanName OBJECT-TYPE
    SYNTAX       SnmpAdminString
    MAX-ACCESS   read-only
    STATUS       current
    DESCRIPTION
        "Cisco Firepower vnic:LifVsan:name managed object property"
    ::= { cfprVnicLifVsanEntry 6 }

cfprVnicLifVsanOperState OBJECT-TYPE
    SYNTAX       CfprVnicIfOperState
    MAX-ACCESS   read-only
    STATUS       current
    DESCRIPTION
        "Cisco Firepower vnic:LifVsan:operState managed object property"
    ::= { cfprVnicLifVsanEntry 7 }

cfprVnicLifVsanOperVnetDn OBJECT-TYPE
    SYNTAX       SnmpAdminString
    MAX-ACCESS   read-only
    STATUS       current
    DESCRIPTION
        "Cisco Firepower vnic:LifVsan:operVnetDn managed object property"
    ::= { cfprVnicLifVsanEntry 8 }

cfprVnicLifVsanOperVnetName OBJECT-TYPE
    SYNTAX       SnmpAdminString
    MAX-ACCESS   read-only
    STATUS       current
    DESCRIPTION
        "Cisco Firepower vnic:LifVsan:operVnetName managed
        object property"
    ::= { cfprVnicLifVsanEntry 9 }

cfprVnicLifVsanOwner OBJECT-TYPE
    SYNTAX       CfprVnicConnectionOwner
    MAX-ACCESS   read-only
    STATUS       current
    DESCRIPTION
        "Cisco Firepower vnic:LifVsan:owner managed object property"
    ::= { cfprVnicLifVsanEntry 10 }

cfprVnicLifVsanPubNwId OBJECT-TYPE
    SYNTAX       Gauge32
    MAX-ACCESS   read-only
    STATUS       current
    DESCRIPTION
        "Cisco Firepower vnic:LifVsan:pubNwId managed object property"
    ::= { cfprVnicLifVsanEntry 11 }

cfprVnicLifVsanSharing OBJECT-TYPE
    SYNTAX       CfprFabricVlanSharingType
    MAX-ACCESS   read-only
    STATUS       current
    DESCRIPTION
        "Cisco Firepower vnic:LifVsan:sharing managed object property"
    ::= { cfprVnicLifVsanEntry 12 }

cfprVnicLifVsanSwitchId OBJECT-TYPE
    SYNTAX       CfprVnicL2IfSwitchId
    MAX-ACCESS   read-only
    STATUS       current
    DESCRIPTION
        "Cisco Firepower vnic:LifVsan:switchId managed object property"
    ::= { cfprVnicLifVsanEntry 13 }

cfprVnicLifVsanType OBJECT-TYPE
    SYNTAX       CfprVnicAFcIfType
    MAX-ACCESS   read-only
    STATUS       current
    DESCRIPTION
        "Cisco Firepower vnic:LifVsan:type managed object property"
    ::= { cfprVnicLifVsanEntry 14 }

cfprVnicLifVsanVnet OBJECT-TYPE
    SYNTAX       Gauge32
    MAX-ACCESS   read-only
    STATUS       current
    DESCRIPTION
        "Cisco Firepower vnic:LifVsan:vnet managed object property"
    ::= { cfprVnicLifVsanEntry 15 }

cfprVnicLunTable OBJECT-TYPE
    SYNTAX           SEQUENCE OF CfprVnicLunEntry
    MAX-ACCESS       not-accessible
    STATUS           current
    DESCRIPTION
        "Cisco Firepower vnic:Lun managed object table"
    ::= { cfprVnicObjects 50 }

cfprVnicLunEntry OBJECT-TYPE
    SYNTAX           CfprVnicLunEntry
    MAX-ACCESS       not-accessible
    STATUS           current
    DESCRIPTION
        "Entry for the cfprVnicLunTable table."
    INDEX { cfprVnicLunInstanceId }
    ::= { cfprVnicLunTable 1 }

CfprVnicLunEntry ::= SEQUENCE {
    cfprVnicLunInstanceId                                            CfprManagedObjectId,
    cfprVnicLunDn                                                    CfprManagedObjectDn,
    cfprVnicLunRn                                                    SnmpAdminString,
    cfprVnicLunBootable                                              TruthValue,
    cfprVnicLunId                                                    CfprVnicLunId
}

cfprVnicLunInstanceId OBJECT-TYPE
    SYNTAX       CfprManagedObjectId
    MAX-ACCESS   not-accessible
    STATUS       current
    DESCRIPTION
        "Instance identifier of the managed object."
    ::= { cfprVnicLunEntry 1 }

cfprVnicLunDn OBJECT-TYPE
    SYNTAX       CfprManagedObjectDn
    MAX-ACCESS   read-only
    STATUS       current
    DESCRIPTION
        "Cisco Firepower vnic:Lun:dn managed object property"
    ::= { cfprVnicLunEntry 2 }

cfprVnicLunRn OBJECT-TYPE
    SYNTAX       SnmpAdminString
    MAX-ACCESS   read-only
    STATUS       current
    DESCRIPTION
        "Cisco Firepower vnic:Lun:rn managed object property"
    ::= { cfprVnicLunEntry 3 }

cfprVnicLunBootable OBJECT-TYPE
    SYNTAX       TruthValue
    MAX-ACCESS   read-only
    STATUS       current
    DESCRIPTION
        "Cisco Firepower vnic:Lun:bootable managed object property"
    ::= { cfprVnicLunEntry 4 }

cfprVnicLunId OBJECT-TYPE
    SYNTAX       CfprVnicLunId
    MAX-ACCESS   read-only
    STATUS       current
    DESCRIPTION
        "Cisco Firepower vnic:Lun:id managed object property"
    ::= { cfprVnicLunEntry 5 }

cfprVnicMacHistoryTable OBJECT-TYPE
    SYNTAX           SEQUENCE OF CfprVnicMacHistoryEntry
    MAX-ACCESS       not-accessible
    STATUS           current
    DESCRIPTION
        "Cisco Firepower vnic:MacHistory managed object table"
    ::= { cfprVnicObjects 51 }

cfprVnicMacHistoryEntry OBJECT-TYPE
    SYNTAX           CfprVnicMacHistoryEntry
    MAX-ACCESS       not-accessible
    STATUS           current
    DESCRIPTION
        "Entry for the cfprVnicMacHistoryTable table."
    INDEX { cfprVnicMacHistoryInstanceId }
    ::= { cfprVnicMacHistoryTable 1 }

CfprVnicMacHistoryEntry ::= SEQUENCE {
    cfprVnicMacHistoryInstanceId                                     CfprManagedObjectId,
    cfprVnicMacHistoryDn                                             CfprManagedObjectDn,
    cfprVnicMacHistoryRn                                             SnmpAdminString,
    cfprVnicMacHistoryOldaddr                                        MacAddress
}

cfprVnicMacHistoryInstanceId OBJECT-TYPE
    SYNTAX       CfprManagedObjectId
    MAX-ACCESS   not-accessible
    STATUS       current
    DESCRIPTION
        "Instance identifier of the managed object."
    ::= { cfprVnicMacHistoryEntry 1 }

cfprVnicMacHistoryDn OBJECT-TYPE
    SYNTAX       CfprManagedObjectDn
    MAX-ACCESS   read-only
    STATUS       current
    DESCRIPTION
        "Cisco Firepower vnic:MacHistory:dn managed object property"
    ::= { cfprVnicMacHistoryEntry 2 }

cfprVnicMacHistoryRn OBJECT-TYPE
    SYNTAX       SnmpAdminString
    MAX-ACCESS   read-only
    STATUS       current
    DESCRIPTION
        "Cisco Firepower vnic:MacHistory:rn managed object property"
    ::= { cfprVnicMacHistoryEntry 3 }

cfprVnicMacHistoryOldaddr OBJECT-TYPE
    SYNTAX       MacAddress
    MAX-ACCESS   read-only
    STATUS       current
    DESCRIPTION
        "Cisco Firepower vnic:MacHistory:oldaddr managed object property"
    ::= { cfprVnicMacHistoryEntry 4 }

cfprVnicOProfileAliasTable OBJECT-TYPE
    SYNTAX           SEQUENCE OF CfprVnicOProfileAliasEntry
    MAX-ACCESS       not-accessible
    STATUS           current
    DESCRIPTION
        "Cisco Firepower vnic:OProfileAlias managed object table"
    ::= { cfprVnicObjects 52 }

cfprVnicOProfileAliasEntry OBJECT-TYPE
    SYNTAX           CfprVnicOProfileAliasEntry
    MAX-ACCESS       not-accessible
    STATUS           current
    DESCRIPTION
        "Entry for the cfprVnicOProfileAliasTable table."
    INDEX { cfprVnicOProfileAliasInstanceId }
    ::= { cfprVnicOProfileAliasTable 1 }

CfprVnicOProfileAliasEntry ::= SEQUENCE {
    cfprVnicOProfileAliasInstanceId                                  CfprManagedObjectId,
    cfprVnicOProfileAliasDn                                          CfprManagedObjectDn,
    cfprVnicOProfileAliasRn                                          SnmpAdminString,
    cfprVnicOProfileAliasAlias                                       SnmpAdminString,
    cfprVnicOProfileAliasMgmtPlane                                   CfprVmMgmtPlane,
    cfprVnicOProfileAliasVSwitchId                                   SnmpAdminString,
    cfprVnicOProfileAliasVSwitchName                                 SnmpAdminString
}

cfprVnicOProfileAliasInstanceId OBJECT-TYPE
    SYNTAX       CfprManagedObjectId
    MAX-ACCESS   not-accessible
    STATUS       current
    DESCRIPTION
        "Instance identifier of the managed object."
    ::= { cfprVnicOProfileAliasEntry 1 }

cfprVnicOProfileAliasDn OBJECT-TYPE
    SYNTAX       CfprManagedObjectDn
    MAX-ACCESS   read-only
    STATUS       current
    DESCRIPTION
        "Cisco Firepower vnic:OProfileAlias:dn managed object property"
    ::= { cfprVnicOProfileAliasEntry 2 }

cfprVnicOProfileAliasRn OBJECT-TYPE
    SYNTAX       SnmpAdminString
    MAX-ACCESS   read-only
    STATUS       current
    DESCRIPTION
        "Cisco Firepower vnic:OProfileAlias:rn managed object property"
    ::= { cfprVnicOProfileAliasEntry 3 }

cfprVnicOProfileAliasAlias OBJECT-TYPE
    SYNTAX       SnmpAdminString
    MAX-ACCESS   read-only
    STATUS       current
    DESCRIPTION
        "Cisco Firepower vnic:OProfileAlias:alias managed object property"
    ::= { cfprVnicOProfileAliasEntry 4 }

cfprVnicOProfileAliasMgmtPlane OBJECT-TYPE
    SYNTAX       CfprVmMgmtPlane
    MAX-ACCESS   read-only
    STATUS       current
    DESCRIPTION
        "Cisco Firepower vnic:OProfileAlias:mgmtPlane managed
        object property"
    ::= { cfprVnicOProfileAliasEntry 5 }

cfprVnicOProfileAliasVSwitchId OBJECT-TYPE
    SYNTAX       SnmpAdminString
    MAX-ACCESS   read-only
    STATUS       current
    DESCRIPTION
        "Cisco Firepower vnic:OProfileAlias:vSwitchId managed
        object property"
    ::= { cfprVnicOProfileAliasEntry 6 }

cfprVnicOProfileAliasVSwitchName OBJECT-TYPE
    SYNTAX       SnmpAdminString
    MAX-ACCESS   read-only
    STATUS       current
    DESCRIPTION
        "Cisco Firepower vnic:OProfileAlias:vSwitchName
        managed object property"
    ::= { cfprVnicOProfileAliasEntry 7 }

cfprVnicProfileTable OBJECT-TYPE
    SYNTAX           SEQUENCE OF CfprVnicProfileEntry
    MAX-ACCESS       not-accessible
    STATUS           current
    DESCRIPTION
        "Cisco Firepower vnic:Profile managed object table"
    ::= { cfprVnicObjects 53 }

cfprVnicProfileEntry OBJECT-TYPE
    SYNTAX           CfprVnicProfileEntry
    MAX-ACCESS       not-accessible
    STATUS           current
    DESCRIPTION
        "Entry for the cfprVnicProfileTable table."
    INDEX { cfprVnicProfileInstanceId }
    ::= { cfprVnicProfileTable 1 }

CfprVnicProfileEntry ::= SEQUENCE {
    cfprVnicProfileInstanceId                                        CfprManagedObjectId,
    cfprVnicProfileDn                                                CfprManagedObjectDn,
    cfprVnicProfileRn                                                SnmpAdminString,
    cfprVnicProfileCdp                                               CfprNwctrlAdminState,
    cfprVnicProfileConfigQualifier                                   CfprVnicProfileConfigQualifier,
    cfprVnicProfileCos                                               Gauge32,
    cfprVnicProfileDescr                                             SnmpAdminString,
    cfprVnicProfileForgeMac                                          CfprDpsecForgedTransmit,
    cfprVnicProfileHostNwIOPerf                                      CfprVnicHostNwIOPerfPref,
    cfprVnicProfileIntId                                             SnmpAdminString,
    cfprVnicProfileMacRegisterMode                                   CfprNwctrlRegistrationMode,
    cfprVnicProfileMaxPorts                                          Gauge32,
    cfprVnicProfileName                                              SnmpAdminString,
    cfprVnicProfileNwCtrlPolicyName                                  SnmpAdminString,
    cfprVnicProfileOperNwCtrlPolicyName                              SnmpAdminString,
    cfprVnicProfileOperQosPolicyName                                 SnmpAdminString,
    cfprVnicProfilePinToGroupName                                    SnmpAdminString,
    cfprVnicProfilePolicyLevel                                       Gauge32,
    cfprVnicProfilePolicyOwner                                       CfprPolicyPolicyOwner,
    cfprVnicProfilePortProfileUuid                                   SnmpAdminString,
    cfprVnicProfilePrimaryVlanId                                     Gauge32,
    cfprVnicProfileQosPolicyDn                                       SnmpAdminString,
    cfprVnicProfileQosPolicyId                                       SnmpAdminString,
    cfprVnicProfileQosPolicyName                                     SnmpAdminString,
    cfprVnicProfileSwABorderAggrPort                                 Gauge32,
    cfprVnicProfileSwABorderPort                                     Gauge32,
    cfprVnicProfileSwABorderSlot                                     Gauge32,
    cfprVnicProfileSwBBorderAggrPort                                 Gauge32,
    cfprVnicProfileSwBBorderPort                                     Gauge32,
    cfprVnicProfileSwBBorderSlot                                     Gauge32,
    cfprVnicProfileType                                              CfprVnicPortProfileType,
    cfprVnicProfileUplinkFailAction                                  CfprNwctrlLinkFailAction
}

cfprVnicProfileInstanceId OBJECT-TYPE
    SYNTAX       CfprManagedObjectId
    MAX-ACCESS   not-accessible
    STATUS       current
    DESCRIPTION
        "Instance identifier of the managed object."
    ::= { cfprVnicProfileEntry 1 }

cfprVnicProfileDn OBJECT-TYPE
    SYNTAX       CfprManagedObjectDn
    MAX-ACCESS   read-only
    STATUS       current
    DESCRIPTION
        "Cisco Firepower vnic:Profile:dn managed object property"
    ::= { cfprVnicProfileEntry 2 }

cfprVnicProfileRn OBJECT-TYPE
    SYNTAX       SnmpAdminString
    MAX-ACCESS   read-only
    STATUS       current
    DESCRIPTION
        "Cisco Firepower vnic:Profile:rn managed object property"
    ::= { cfprVnicProfileEntry 3 }

cfprVnicProfileCdp OBJECT-TYPE
    SYNTAX       CfprNwctrlAdminState
    MAX-ACCESS   read-only
    STATUS       current
    DESCRIPTION
        "Cisco Firepower vnic:Profile:cdp managed object property"
    ::= { cfprVnicProfileEntry 4 }

cfprVnicProfileConfigQualifier OBJECT-TYPE
    SYNTAX       CfprVnicProfileConfigQualifier
    MAX-ACCESS   read-only
    STATUS       current
    DESCRIPTION
        "Cisco Firepower vnic:Profile:configQualifier managed
        object property"
    ::= { cfprVnicProfileEntry 5 }

cfprVnicProfileCos OBJECT-TYPE
    SYNTAX       Gauge32
    MAX-ACCESS   read-only
    STATUS       current
    DESCRIPTION
        "Cisco Firepower vnic:Profile:cos managed object property"
    ::= { cfprVnicProfileEntry 6 }

cfprVnicProfileDescr OBJECT-TYPE
    SYNTAX       SnmpAdminString
    MAX-ACCESS   read-only
    STATUS       current
    DESCRIPTION
        "Cisco Firepower vnic:Profile:descr managed object property"
    ::= { cfprVnicProfileEntry 7 }

cfprVnicProfileForgeMac OBJECT-TYPE
    SYNTAX       CfprDpsecForgedTransmit
    MAX-ACCESS   read-only
    STATUS       current
    DESCRIPTION
        "Cisco Firepower vnic:Profile:forgeMac managed object property"
    ::= { cfprVnicProfileEntry 8 }

cfprVnicProfileHostNwIOPerf OBJECT-TYPE
    SYNTAX       CfprVnicHostNwIOPerfPref
    MAX-ACCESS   read-only
    STATUS       current
    DESCRIPTION
        "Cisco Firepower vnic:Profile:hostNwIOPerf managed
        object property"
    ::= { cfprVnicProfileEntry 9 }

cfprVnicProfileIntId OBJECT-TYPE
    SYNTAX       SnmpAdminString
    MAX-ACCESS   read-only
    STATUS       current
    DESCRIPTION
        "Cisco Firepower vnic:Profile:intId managed object property"
    ::= { cfprVnicProfileEntry 10 }

cfprVnicProfileMacRegisterMode OBJECT-TYPE
    SYNTAX       CfprNwctrlRegistrationMode
    MAX-ACCESS   read-only
    STATUS       current
    DESCRIPTION
        "Cisco Firepower vnic:Profile:macRegisterMode managed
        object property"
    ::= { cfprVnicProfileEntry 11 }

cfprVnicProfileMaxPorts OBJECT-TYPE
    SYNTAX       Gauge32
    MAX-ACCESS   read-only
    STATUS       current
    DESCRIPTION
        "Cisco Firepower vnic:Profile:maxPorts managed object property"
    ::= { cfprVnicProfileEntry 12 }

cfprVnicProfileName OBJECT-TYPE
    SYNTAX       SnmpAdminString
    MAX-ACCESS   read-only
    STATUS       current
    DESCRIPTION
        "Cisco Firepower vnic:Profile:name managed object property"
    ::= { cfprVnicProfileEntry 13 }

cfprVnicProfileNwCtrlPolicyName OBJECT-TYPE
    SYNTAX       SnmpAdminString
    MAX-ACCESS   read-only
    STATUS       current
    DESCRIPTION
        "Cisco Firepower vnic:Profile:nwCtrlPolicyName
        managed object property"
    ::= { cfprVnicProfileEntry 14 }

cfprVnicProfileOperNwCtrlPolicyName OBJECT-TYPE
    SYNTAX       SnmpAdminString
    MAX-ACCESS   read-only
    STATUS       current
    DESCRIPTION
        "Cisco Firepower vnic:Profile:operNwCtrlPolicyName
        managed object property"
    ::= { cfprVnicProfileEntry 15 }

cfprVnicProfileOperQosPolicyName OBJECT-TYPE
    SYNTAX       SnmpAdminString
    MAX-ACCESS   read-only
    STATUS       current
    DESCRIPTION
        "Cisco Firepower vnic:Profile:operQosPolicyName
        managed object property"
    ::= { cfprVnicProfileEntry 16 }

cfprVnicProfilePinToGroupName OBJECT-TYPE
    SYNTAX       SnmpAdminString
    MAX-ACCESS   read-only
    STATUS       current
    DESCRIPTION
        "Cisco Firepower vnic:Profile:pinToGroupName managed
        object property"
    ::= { cfprVnicProfileEntry 17 }

cfprVnicProfilePolicyLevel OBJECT-TYPE
    SYNTAX       Gauge32
    MAX-ACCESS   read-only
    STATUS       current
    DESCRIPTION
        "Cisco Firepower vnic:Profile:policyLevel managed object property"
    ::= { cfprVnicProfileEntry 18 }

cfprVnicProfilePolicyOwner OBJECT-TYPE
    SYNTAX       CfprPolicyPolicyOwner
    MAX-ACCESS   read-only
    STATUS       current
    DESCRIPTION
        "Cisco Firepower vnic:Profile:policyOwner managed object property"
    ::= { cfprVnicProfileEntry 19 }

cfprVnicProfilePortProfileUuid OBJECT-TYPE
    SYNTAX       SnmpAdminString
    MAX-ACCESS   read-only
    STATUS       current
    DESCRIPTION
        "Cisco Firepower vnic:Profile:portProfileUuid managed
        object property"
    ::= { cfprVnicProfileEntry 20 }

cfprVnicProfilePrimaryVlanId OBJECT-TYPE
    SYNTAX       Gauge32
    MAX-ACCESS   read-only
    STATUS       current
    DESCRIPTION
        "Cisco Firepower vnic:Profile:primaryVlanId managed
        object property"
    ::= { cfprVnicProfileEntry 21 }

cfprVnicProfileQosPolicyDn OBJECT-TYPE
    SYNTAX       SnmpAdminString
    MAX-ACCESS   read-only
    STATUS       current
    DESCRIPTION
        "Cisco Firepower vnic:Profile:qosPolicyDn managed object property"
    ::= { cfprVnicProfileEntry 22 }

cfprVnicProfileQosPolicyId OBJECT-TYPE
    SYNTAX       SnmpAdminString
    MAX-ACCESS   read-only
    STATUS       current
    DESCRIPTION
        "Cisco Firepower vnic:Profile:qosPolicyId managed object property"
    ::= { cfprVnicProfileEntry 23 }

cfprVnicProfileQosPolicyName OBJECT-TYPE
    SYNTAX       SnmpAdminString
    MAX-ACCESS   read-only
    STATUS       current
    DESCRIPTION
        "Cisco Firepower vnic:Profile:qosPolicyName managed
        object property"
    ::= { cfprVnicProfileEntry 24 }

cfprVnicProfileSwABorderAggrPort OBJECT-TYPE
    SYNTAX       Gauge32
    MAX-ACCESS   read-only
    STATUS       current
    DESCRIPTION
        "Cisco Firepower vnic:Profile:swABorderAggrPort
        managed object property"
    ::= { cfprVnicProfileEntry 25 }

cfprVnicProfileSwABorderPort OBJECT-TYPE
    SYNTAX       Gauge32
    MAX-ACCESS   read-only
    STATUS       current
    DESCRIPTION
        "Cisco Firepower vnic:Profile:swABorderPort managed
        object property"
    ::= { cfprVnicProfileEntry 26 }

cfprVnicProfileSwABorderSlot OBJECT-TYPE
    SYNTAX       Gauge32
    MAX-ACCESS   read-only
    STATUS       current
    DESCRIPTION
        "Cisco Firepower vnic:Profile:swABorderSlot managed
        object property"
    ::= { cfprVnicProfileEntry 27 }

cfprVnicProfileSwBBorderAggrPort OBJECT-TYPE
    SYNTAX       Gauge32
    MAX-ACCESS   read-only
    STATUS       current
    DESCRIPTION
        "Cisco Firepower vnic:Profile:swBBorderAggrPort
        managed object property"
    ::= { cfprVnicProfileEntry 28 }

cfprVnicProfileSwBBorderPort OBJECT-TYPE
    SYNTAX       Gauge32
    MAX-ACCESS   read-only
    STATUS       current
    DESCRIPTION
        "Cisco Firepower vnic:Profile:swBBorderPort managed
        object property"
    ::= { cfprVnicProfileEntry 29 }

cfprVnicProfileSwBBorderSlot OBJECT-TYPE
    SYNTAX       Gauge32
    MAX-ACCESS   read-only
    STATUS       current
    DESCRIPTION
        "Cisco Firepower vnic:Profile:swBBorderSlot managed
        object property"
    ::= { cfprVnicProfileEntry 30 }

cfprVnicProfileType OBJECT-TYPE
    SYNTAX       CfprVnicPortProfileType
    MAX-ACCESS   read-only
    STATUS       current
    DESCRIPTION
        "Cisco Firepower vnic:Profile:type managed object property"
    ::= { cfprVnicProfileEntry 31 }

cfprVnicProfileUplinkFailAction OBJECT-TYPE
    SYNTAX       CfprNwctrlLinkFailAction
    MAX-ACCESS   read-only
    STATUS       current
    DESCRIPTION
        "Cisco Firepower vnic:Profile:uplinkFailAction
        managed object property"
    ::= { cfprVnicProfileEntry 32 }

cfprVnicProfileAliasTable OBJECT-TYPE
    SYNTAX           SEQUENCE OF CfprVnicProfileAliasEntry
    MAX-ACCESS       not-accessible
    STATUS           current
    DESCRIPTION
        "Cisco Firepower vnic:ProfileAlias managed object table"
    ::= { cfprVnicObjects 54 }

cfprVnicProfileAliasEntry OBJECT-TYPE
    SYNTAX           CfprVnicProfileAliasEntry
    MAX-ACCESS       not-accessible
    STATUS           current
    DESCRIPTION
        "Entry for the cfprVnicProfileAliasTable table."
    INDEX { cfprVnicProfileAliasInstanceId }
    ::= { cfprVnicProfileAliasTable 1 }

CfprVnicProfileAliasEntry ::= SEQUENCE {
    cfprVnicProfileAliasInstanceId                                   CfprManagedObjectId,
    cfprVnicProfileAliasDn                                           CfprManagedObjectDn,
    cfprVnicProfileAliasRn                                           SnmpAdminString,
    cfprVnicProfileAliasAlias                                        SnmpAdminString,
    cfprVnicProfileAliasSwUuid                                       SnmpAdminString
}

cfprVnicProfileAliasInstanceId OBJECT-TYPE
    SYNTAX       CfprManagedObjectId
    MAX-ACCESS   not-accessible
    STATUS       current
    DESCRIPTION
        "Instance identifier of the managed object."
    ::= { cfprVnicProfileAliasEntry 1 }

cfprVnicProfileAliasDn OBJECT-TYPE
    SYNTAX       CfprManagedObjectDn
    MAX-ACCESS   read-only
    STATUS       current
    DESCRIPTION
        "Cisco Firepower vnic:ProfileAlias:dn managed object property"
    ::= { cfprVnicProfileAliasEntry 2 }

cfprVnicProfileAliasRn OBJECT-TYPE
    SYNTAX       SnmpAdminString
    MAX-ACCESS   read-only
    STATUS       current
    DESCRIPTION
        "Cisco Firepower vnic:ProfileAlias:rn managed object property"
    ::= { cfprVnicProfileAliasEntry 3 }

cfprVnicProfileAliasAlias OBJECT-TYPE
    SYNTAX       SnmpAdminString
    MAX-ACCESS   read-only
    STATUS       current
    DESCRIPTION
        "Cisco Firepower vnic:ProfileAlias:alias managed object property"
    ::= { cfprVnicProfileAliasEntry 4 }

cfprVnicProfileAliasSwUuid OBJECT-TYPE
    SYNTAX       SnmpAdminString
    MAX-ACCESS   read-only
    STATUS       current
    DESCRIPTION
        "Cisco Firepower vnic:ProfileAlias:swUuid managed object property"
    ::= { cfprVnicProfileAliasEntry 5 }

cfprVnicProfileRefTable OBJECT-TYPE
    SYNTAX           SEQUENCE OF CfprVnicProfileRefEntry
    MAX-ACCESS       not-accessible
    STATUS           current
    DESCRIPTION
        "Cisco Firepower vnic:ProfileRef managed object table"
    ::= { cfprVnicObjects 55 }

cfprVnicProfileRefEntry OBJECT-TYPE
    SYNTAX           CfprVnicProfileRefEntry
    MAX-ACCESS       not-accessible
    STATUS           current
    DESCRIPTION
        "Entry for the cfprVnicProfileRefTable table."
    INDEX { cfprVnicProfileRefInstanceId }
    ::= { cfprVnicProfileRefTable 1 }

CfprVnicProfileRefEntry ::= SEQUENCE {
    cfprVnicProfileRefInstanceId                                     CfprManagedObjectId,
    cfprVnicProfileRefDn                                             CfprManagedObjectDn,
    cfprVnicProfileRefRn                                             SnmpAdminString,
    cfprVnicProfileRefName                                           SnmpAdminString,
    cfprVnicProfileRefSourceDn                                       SnmpAdminString
}

cfprVnicProfileRefInstanceId OBJECT-TYPE
    SYNTAX       CfprManagedObjectId
    MAX-ACCESS   not-accessible
    STATUS       current
    DESCRIPTION
        "Instance identifier of the managed object."
    ::= { cfprVnicProfileRefEntry 1 }

cfprVnicProfileRefDn OBJECT-TYPE
    SYNTAX       CfprManagedObjectDn
    MAX-ACCESS   read-only
    STATUS       current
    DESCRIPTION
        "Cisco Firepower vnic:ProfileRef:dn managed object property"
    ::= { cfprVnicProfileRefEntry 2 }

cfprVnicProfileRefRn OBJECT-TYPE
    SYNTAX       SnmpAdminString
    MAX-ACCESS   read-only
    STATUS       current
    DESCRIPTION
        "Cisco Firepower vnic:ProfileRef:rn managed object property"
    ::= { cfprVnicProfileRefEntry 3 }

cfprVnicProfileRefName OBJECT-TYPE
    SYNTAX       SnmpAdminString
    MAX-ACCESS   read-only
    STATUS       current
    DESCRIPTION
        "Cisco Firepower vnic:ProfileRef:name managed object property"
    ::= { cfprVnicProfileRefEntry 4 }

cfprVnicProfileRefSourceDn OBJECT-TYPE
    SYNTAX       SnmpAdminString
    MAX-ACCESS   read-only
    STATUS       current
    DESCRIPTION
        "Cisco Firepower vnic:ProfileRef:sourceDn managed object property"
    ::= { cfprVnicProfileRefEntry 5 }

cfprVnicProfileSetTable OBJECT-TYPE
    SYNTAX           SEQUENCE OF CfprVnicProfileSetEntry
    MAX-ACCESS       not-accessible
    STATUS           current
    DESCRIPTION
        "Cisco Firepower vnic:ProfileSet managed object table"
    ::= { cfprVnicObjects 56 }

cfprVnicProfileSetEntry OBJECT-TYPE
    SYNTAX           CfprVnicProfileSetEntry
    MAX-ACCESS       not-accessible
    STATUS           current
    DESCRIPTION
        "Entry for the cfprVnicProfileSetTable table."
    INDEX { cfprVnicProfileSetInstanceId }
    ::= { cfprVnicProfileSetTable 1 }

CfprVnicProfileSetEntry ::= SEQUENCE {
    cfprVnicProfileSetInstanceId                                     CfprManagedObjectId,
    cfprVnicProfileSetDn                                             CfprManagedObjectDn,
    cfprVnicProfileSetRn                                             SnmpAdminString,
    cfprVnicProfileSetFltAggr                                        Unsigned64,
    cfprVnicProfileSetFsmDescr                                       SnmpAdminString,
    cfprVnicProfileSetFsmPrev                                        SnmpAdminString,
    cfprVnicProfileSetFsmProgr                                       Gauge32,
    cfprVnicProfileSetFsmRmtInvErrCode                               Gauge32,
    cfprVnicProfileSetFsmRmtInvErrDescr                              SnmpAdminString,
    cfprVnicProfileSetFsmRmtInvRslt                                  CfprConditionRemoteInvRslt,
    cfprVnicProfileSetFsmStageDescr                                  SnmpAdminString,
    cfprVnicProfileSetFsmStamp                                       DateAndTime,
    cfprVnicProfileSetFsmStatus                                      SnmpAdminString,
    cfprVnicProfileSetFsmTry                                         Gauge32,
    cfprVnicProfileSetGenNum                                         Gauge32
}

cfprVnicProfileSetInstanceId OBJECT-TYPE
    SYNTAX       CfprManagedObjectId
    MAX-ACCESS   not-accessible
    STATUS       current
    DESCRIPTION
        "Instance identifier of the managed object."
    ::= { cfprVnicProfileSetEntry 1 }

cfprVnicProfileSetDn OBJECT-TYPE
    SYNTAX       CfprManagedObjectDn
    MAX-ACCESS   read-only
    STATUS       current
    DESCRIPTION
        "Cisco Firepower vnic:ProfileSet:dn managed object property"
    ::= { cfprVnicProfileSetEntry 2 }

cfprVnicProfileSetRn OBJECT-TYPE
    SYNTAX       SnmpAdminString
    MAX-ACCESS   read-only
    STATUS       current
    DESCRIPTION
        "Cisco Firepower vnic:ProfileSet:rn managed object property"
    ::= { cfprVnicProfileSetEntry 3 }

cfprVnicProfileSetFltAggr OBJECT-TYPE
    SYNTAX       Unsigned64
    MAX-ACCESS   read-only
    STATUS       current
    DESCRIPTION
        "Cisco Firepower vnic:ProfileSet:fltAggr managed object property"
    ::= { cfprVnicProfileSetEntry 4 }

cfprVnicProfileSetFsmDescr OBJECT-TYPE
    SYNTAX       SnmpAdminString
    MAX-ACCESS   read-only
    STATUS       current
    DESCRIPTION
        "Cisco Firepower vnic:ProfileSet:fsmDescr managed object property"
    ::= { cfprVnicProfileSetEntry 5 }

cfprVnicProfileSetFsmPrev OBJECT-TYPE
    SYNTAX       SnmpAdminString
    MAX-ACCESS   read-only
    STATUS       current
    DESCRIPTION
        "Cisco Firepower vnic:ProfileSet:fsmPrev managed object property"
    ::= { cfprVnicProfileSetEntry 6 }

cfprVnicProfileSetFsmProgr OBJECT-TYPE
    SYNTAX       Gauge32
    MAX-ACCESS   read-only
    STATUS       current
    DESCRIPTION
        "Cisco Firepower vnic:ProfileSet:fsmProgr managed object property"
    ::= { cfprVnicProfileSetEntry 7 }

cfprVnicProfileSetFsmRmtInvErrCode OBJECT-TYPE
    SYNTAX       Gauge32
    MAX-ACCESS   read-only
    STATUS       current
    DESCRIPTION
        "Cisco Firepower vnic:ProfileSet:fsmRmtInvErrCode
        managed object property"
    ::= { cfprVnicProfileSetEntry 8 }

cfprVnicProfileSetFsmRmtInvErrDescr OBJECT-TYPE
    SYNTAX       SnmpAdminString
    MAX-ACCESS   read-only
    STATUS       current
    DESCRIPTION
        "Cisco Firepower vnic:ProfileSet:fsmRmtInvErrDescr
        managed object property"
    ::= { cfprVnicProfileSetEntry 9 }

cfprVnicProfileSetFsmRmtInvRslt OBJECT-TYPE
    SYNTAX       CfprConditionRemoteInvRslt
    MAX-ACCESS   read-only
    STATUS       current
    DESCRIPTION
        "Cisco Firepower vnic:ProfileSet:fsmRmtInvRslt
        managed object property"
    ::= { cfprVnicProfileSetEntry 10 }

cfprVnicProfileSetFsmStageDescr OBJECT-TYPE
    SYNTAX       SnmpAdminString
    MAX-ACCESS   read-only
    STATUS       current
    DESCRIPTION
        "Cisco Firepower vnic:ProfileSet:fsmStageDescr
        managed object property"
    ::= { cfprVnicProfileSetEntry 11 }

cfprVnicProfileSetFsmStamp OBJECT-TYPE
    SYNTAX       DateAndTime
    MAX-ACCESS   read-only
    STATUS       current
    DESCRIPTION
        "Cisco Firepower vnic:ProfileSet:fsmStamp managed object property"
    ::= { cfprVnicProfileSetEntry 12 }

cfprVnicProfileSetFsmStatus OBJECT-TYPE
    SYNTAX       SnmpAdminString
    MAX-ACCESS   read-only
    STATUS       current
    DESCRIPTION
        "Cisco Firepower vnic:ProfileSet:fsmStatus managed
        object property"
    ::= { cfprVnicProfileSetEntry 13 }

cfprVnicProfileSetFsmTry OBJECT-TYPE
    SYNTAX       Gauge32
    MAX-ACCESS   read-only
    STATUS       current
    DESCRIPTION
        "Cisco Firepower vnic:ProfileSet:fsmTry managed object property"
    ::= { cfprVnicProfileSetEntry 14 }

cfprVnicProfileSetGenNum OBJECT-TYPE
    SYNTAX       Gauge32
    MAX-ACCESS   read-only
    STATUS       current
    DESCRIPTION
        "Cisco Firepower vnic:ProfileSet:genNum managed object property"
    ::= { cfprVnicProfileSetEntry 15 }

cfprVnicProfileSetFsmTable OBJECT-TYPE
    SYNTAX           SEQUENCE OF CfprVnicProfileSetFsmEntry
    MAX-ACCESS       not-accessible
    STATUS           current
    DESCRIPTION
        "Cisco Firepower vnic:ProfileSetFsm managed object table"
    ::= { cfprVnicObjects 57 }

cfprVnicProfileSetFsmEntry OBJECT-TYPE
    SYNTAX           CfprVnicProfileSetFsmEntry
    MAX-ACCESS       not-accessible
    STATUS           current
    DESCRIPTION
        "Entry for the cfprVnicProfileSetFsmTable table."
    INDEX { cfprVnicProfileSetFsmInstanceId }
    ::= { cfprVnicProfileSetFsmTable 1 }

CfprVnicProfileSetFsmEntry ::= SEQUENCE {
    cfprVnicProfileSetFsmInstanceId                                  CfprManagedObjectId,
    cfprVnicProfileSetFsmDn                                          CfprManagedObjectDn,
    cfprVnicProfileSetFsmRn                                          SnmpAdminString,
    cfprVnicProfileSetFsmCompletionTime                              DateAndTime,
    cfprVnicProfileSetFsmCurrentFsm                                  CfprVnicProfileSetFsmCurrentFsm,
    cfprVnicProfileSetFsmDescrData                                   SnmpAdminString,
    cfprVnicProfileSetFsmFsmStatus                                   CfprFsmFsmStageStatus,
    cfprVnicProfileSetFsmProgress                                    Gauge32,
    cfprVnicProfileSetFsmRmtErrCode                                  Gauge32,
    cfprVnicProfileSetFsmRmtErrDescr                                 SnmpAdminString,
    cfprVnicProfileSetFsmRmtRslt                                     CfprConditionRemoteInvRslt
}

cfprVnicProfileSetFsmInstanceId OBJECT-TYPE
    SYNTAX       CfprManagedObjectId
    MAX-ACCESS   not-accessible
    STATUS       current
    DESCRIPTION
        "Instance identifier of the managed object."
    ::= { cfprVnicProfileSetFsmEntry 1 }

cfprVnicProfileSetFsmDn OBJECT-TYPE
    SYNTAX       CfprManagedObjectDn
    MAX-ACCESS   read-only
    STATUS       current
    DESCRIPTION
        "Cisco Firepower vnic:ProfileSetFsm:dn managed object property"
    ::= { cfprVnicProfileSetFsmEntry 2 }

cfprVnicProfileSetFsmRn OBJECT-TYPE
    SYNTAX       SnmpAdminString
    MAX-ACCESS   read-only
    STATUS       current
    DESCRIPTION
        "Cisco Firepower vnic:ProfileSetFsm:rn managed object property"
    ::= { cfprVnicProfileSetFsmEntry 3 }

cfprVnicProfileSetFsmCompletionTime OBJECT-TYPE
    SYNTAX       DateAndTime
    MAX-ACCESS   read-only
    STATUS       current
    DESCRIPTION
        "Cisco Firepower vnic:ProfileSetFsm:completionTime
        managed object property"
    ::= { cfprVnicProfileSetFsmEntry 4 }

cfprVnicProfileSetFsmCurrentFsm OBJECT-TYPE
    SYNTAX       CfprVnicProfileSetFsmCurrentFsm
    MAX-ACCESS   read-only
    STATUS       current
    DESCRIPTION
        "Cisco Firepower vnic:ProfileSetFsm:currentFsm
        managed object property"
    ::= { cfprVnicProfileSetFsmEntry 5 }

cfprVnicProfileSetFsmDescrData OBJECT-TYPE
    SYNTAX       SnmpAdminString
    MAX-ACCESS   read-only
    STATUS       current
    DESCRIPTION
        "Cisco Firepower vnic:ProfileSetFsm:descr managed object property"
    ::= { cfprVnicProfileSetFsmEntry 6 }

cfprVnicProfileSetFsmFsmStatus OBJECT-TYPE
    SYNTAX       CfprFsmFsmStageStatus
    MAX-ACCESS   read-only
    STATUS       current
    DESCRIPTION
        "Cisco Firepower vnic:ProfileSetFsm:fsmStatus managed
        object property"
    ::= { cfprVnicProfileSetFsmEntry 7 }

cfprVnicProfileSetFsmProgress OBJECT-TYPE
    SYNTAX       Gauge32
    MAX-ACCESS   read-only
    STATUS       current
    DESCRIPTION
        "Cisco Firepower vnic:ProfileSetFsm:progress managed
        object property"
    ::= { cfprVnicProfileSetFsmEntry 8 }

cfprVnicProfileSetFsmRmtErrCode OBJECT-TYPE
    SYNTAX       Gauge32
    MAX-ACCESS   read-only
    STATUS       current
    DESCRIPTION
        "Cisco Firepower vnic:ProfileSetFsm:rmtErrCode
        managed object property"
    ::= { cfprVnicProfileSetFsmEntry 9 }

cfprVnicProfileSetFsmRmtErrDescr OBJECT-TYPE
    SYNTAX       SnmpAdminString
    MAX-ACCESS   read-only
    STATUS       current
    DESCRIPTION
        "Cisco Firepower vnic:ProfileSetFsm:rmtErrDescr
        managed object property"
    ::= { cfprVnicProfileSetFsmEntry 10 }

cfprVnicProfileSetFsmRmtRslt OBJECT-TYPE
    SYNTAX       CfprConditionRemoteInvRslt
    MAX-ACCESS   read-only
    STATUS       current
    DESCRIPTION
        "Cisco Firepower vnic:ProfileSetFsm:rmtRslt managed
        object property"
    ::= { cfprVnicProfileSetFsmEntry 11 }

cfprVnicProfileSetFsmStageTable OBJECT-TYPE
    SYNTAX           SEQUENCE OF CfprVnicProfileSetFsmStageEntry
    MAX-ACCESS       not-accessible
    STATUS           current
    DESCRIPTION
        "Cisco Firepower vnic:ProfileSetFsmStage managed object table"
    ::= { cfprVnicObjects 58 }

cfprVnicProfileSetFsmStageEntry OBJECT-TYPE
    SYNTAX           CfprVnicProfileSetFsmStageEntry
    MAX-ACCESS       not-accessible
    STATUS           current
    DESCRIPTION
        "Entry for the cfprVnicProfileSetFsmStageTable table."
    INDEX { cfprVnicProfileSetFsmStageInstanceId }
    ::= { cfprVnicProfileSetFsmStageTable 1 }

CfprVnicProfileSetFsmStageEntry ::= SEQUENCE {
    cfprVnicProfileSetFsmStageInstanceId                             CfprManagedObjectId,
    cfprVnicProfileSetFsmStageDn                                     CfprManagedObjectDn,
    cfprVnicProfileSetFsmStageRn                                     SnmpAdminString,
    cfprVnicProfileSetFsmStageDescrData                              SnmpAdminString,
    cfprVnicProfileSetFsmStageLastUpdateTime                         DateAndTime,
    cfprVnicProfileSetFsmStageName                                   CfprVnicProfileSetFsmStageName,
    cfprVnicProfileSetFsmStageOrder                                  Gauge32,
    cfprVnicProfileSetFsmStageRetry                                  Gauge32,
    cfprVnicProfileSetFsmStageStageStatus                            CfprFsmFsmStageStatus
}

cfprVnicProfileSetFsmStageInstanceId OBJECT-TYPE
    SYNTAX       CfprManagedObjectId
    MAX-ACCESS   not-accessible
    STATUS       current
    DESCRIPTION
        "Instance identifier of the managed object."
    ::= { cfprVnicProfileSetFsmStageEntry 1 }

cfprVnicProfileSetFsmStageDn OBJECT-TYPE
    SYNTAX       CfprManagedObjectDn
    MAX-ACCESS   read-only
    STATUS       current
    DESCRIPTION
        "Cisco Firepower vnic:ProfileSetFsmStage:dn managed
        object property"
    ::= { cfprVnicProfileSetFsmStageEntry 2 }

cfprVnicProfileSetFsmStageRn OBJECT-TYPE
    SYNTAX       SnmpAdminString
    MAX-ACCESS   read-only
    STATUS       current
    DESCRIPTION
        "Cisco Firepower vnic:ProfileSetFsmStage:rn managed
        object property"
    ::= { cfprVnicProfileSetFsmStageEntry 3 }

cfprVnicProfileSetFsmStageDescrData OBJECT-TYPE
    SYNTAX       SnmpAdminString
    MAX-ACCESS   read-only
    STATUS       current
    DESCRIPTION
        "Cisco Firepower vnic:ProfileSetFsmStage:descr
        managed object property"
    ::= { cfprVnicProfileSetFsmStageEntry 4 }

cfprVnicProfileSetFsmStageLastUpdateTime OBJECT-TYPE
    SYNTAX       DateAndTime
    MAX-ACCESS   read-only
    STATUS       current
    DESCRIPTION
        "Cisco Firepower vnic:ProfileSetFsmStage:lastUpdateTime
        managed object property"
    ::= { cfprVnicProfileSetFsmStageEntry 5 }

cfprVnicProfileSetFsmStageName OBJECT-TYPE
    SYNTAX       CfprVnicProfileSetFsmStageName
    MAX-ACCESS   read-only
    STATUS       current
    DESCRIPTION
        "Cisco Firepower vnic:ProfileSetFsmStage:name managed
        object property"
    ::= { cfprVnicProfileSetFsmStageEntry 6 }

cfprVnicProfileSetFsmStageOrder OBJECT-TYPE
    SYNTAX       Gauge32
    MAX-ACCESS   read-only
    STATUS       current
    DESCRIPTION
        "Cisco Firepower vnic:ProfileSetFsmStage:order
        managed object property"
    ::= { cfprVnicProfileSetFsmStageEntry 7 }

cfprVnicProfileSetFsmStageRetry OBJECT-TYPE
    SYNTAX       Gauge32
    MAX-ACCESS   read-only
    STATUS       current
    DESCRIPTION
        "Cisco Firepower vnic:ProfileSetFsmStage:retry
        managed object property"
    ::= { cfprVnicProfileSetFsmStageEntry 8 }

cfprVnicProfileSetFsmStageStageStatus OBJECT-TYPE
    SYNTAX       CfprFsmFsmStageStatus
    MAX-ACCESS   read-only
    STATUS       current
    DESCRIPTION
        "Cisco Firepower vnic:ProfileSetFsmStage:stageStatus
        managed object property"
    ::= { cfprVnicProfileSetFsmStageEntry 9 }

cfprVnicProfileSetFsmTaskTable OBJECT-TYPE
    SYNTAX           SEQUENCE OF CfprVnicProfileSetFsmTaskEntry
    MAX-ACCESS       not-accessible
    STATUS           current
    DESCRIPTION
        "Cisco Firepower vnic:ProfileSetFsmTask managed object table"
    ::= { cfprVnicObjects 59 }

cfprVnicProfileSetFsmTaskEntry OBJECT-TYPE
    SYNTAX           CfprVnicProfileSetFsmTaskEntry
    MAX-ACCESS       not-accessible
    STATUS           current
    DESCRIPTION
        "Entry for the cfprVnicProfileSetFsmTaskTable table."
    INDEX { cfprVnicProfileSetFsmTaskInstanceId }
    ::= { cfprVnicProfileSetFsmTaskTable 1 }

CfprVnicProfileSetFsmTaskEntry ::= SEQUENCE {
    cfprVnicProfileSetFsmTaskInstanceId                              CfprManagedObjectId,
    cfprVnicProfileSetFsmTaskDn                                      CfprManagedObjectDn,
    cfprVnicProfileSetFsmTaskRn                                      SnmpAdminString,
    cfprVnicProfileSetFsmTaskCompletion                              CfprFsmCompletion,
    cfprVnicProfileSetFsmTaskFlags                                   CfprFsmFlags,
    cfprVnicProfileSetFsmTaskItem                                    CfprVnicProfileSetFsmTaskItem,
    cfprVnicProfileSetFsmTaskSeqId                                   Gauge32
}

cfprVnicProfileSetFsmTaskInstanceId OBJECT-TYPE
    SYNTAX       CfprManagedObjectId
    MAX-ACCESS   not-accessible
    STATUS       current
    DESCRIPTION
        "Instance identifier of the managed object."
    ::= { cfprVnicProfileSetFsmTaskEntry 1 }

cfprVnicProfileSetFsmTaskDn OBJECT-TYPE
    SYNTAX       CfprManagedObjectDn
    MAX-ACCESS   read-only
    STATUS       current
    DESCRIPTION
        "Cisco Firepower vnic:ProfileSetFsmTask:dn managed
        object property"
    ::= { cfprVnicProfileSetFsmTaskEntry 2 }

cfprVnicProfileSetFsmTaskRn OBJECT-TYPE
    SYNTAX       SnmpAdminString
    MAX-ACCESS   read-only
    STATUS       current
    DESCRIPTION
        "Cisco Firepower vnic:ProfileSetFsmTask:rn managed
        object property"
    ::= { cfprVnicProfileSetFsmTaskEntry 3 }

cfprVnicProfileSetFsmTaskCompletion OBJECT-TYPE
    SYNTAX       CfprFsmCompletion
    MAX-ACCESS   read-only
    STATUS       current
    DESCRIPTION
        "Cisco Firepower vnic:ProfileSetFsmTask:completion
        managed object property"
    ::= { cfprVnicProfileSetFsmTaskEntry 4 }

cfprVnicProfileSetFsmTaskFlags OBJECT-TYPE
    SYNTAX       CfprFsmFlags
    MAX-ACCESS   read-only
    STATUS       current
    DESCRIPTION
        "Cisco Firepower vnic:ProfileSetFsmTask:flags managed
        object property"
    ::= { cfprVnicProfileSetFsmTaskEntry 5 }

cfprVnicProfileSetFsmTaskItem OBJECT-TYPE
    SYNTAX       CfprVnicProfileSetFsmTaskItem
    MAX-ACCESS   read-only
    STATUS       current
    DESCRIPTION
        "Cisco Firepower vnic:ProfileSetFsmTask:item managed
        object property"
    ::= { cfprVnicProfileSetFsmTaskEntry 6 }

cfprVnicProfileSetFsmTaskSeqId OBJECT-TYPE
    SYNTAX       Gauge32
    MAX-ACCESS   read-only
    STATUS       current
    DESCRIPTION
        "Cisco Firepower vnic:ProfileSetFsmTask:seqId managed
        object property"
    ::= { cfprVnicProfileSetFsmTaskEntry 7 }

cfprVnicRackServerDiscoveryProfileTable OBJECT-TYPE
    SYNTAX           SEQUENCE OF CfprVnicRackServerDiscoveryProfileEntry
    MAX-ACCESS       not-accessible
    STATUS           current
    DESCRIPTION
        "Cisco Firepower vnic:RackServerDiscoveryProfile
        managed object table"
    ::= { cfprVnicObjects 60 }

cfprVnicRackServerDiscoveryProfileEntry OBJECT-TYPE
    SYNTAX           CfprVnicRackServerDiscoveryProfileEntry
    MAX-ACCESS       not-accessible
    STATUS           current
    DESCRIPTION
        "Entry for the cfprVnicRackServerDiscoveryProfileTable table."
    INDEX { cfprVnicRackServerDiscoveryProfileInstanceId }
    ::= { cfprVnicRackServerDiscoveryProfileTable 1 }

CfprVnicRackServerDiscoveryProfileEntry ::= SEQUENCE {
    cfprVnicRackServerDiscoveryProfileInstanceId                     CfprManagedObjectId,
    cfprVnicRackServerDiscoveryProfileDn                             CfprManagedObjectDn,
    cfprVnicRackServerDiscoveryProfileRn                             SnmpAdminString,
    cfprVnicRackServerDiscoveryProfileDescr                          SnmpAdminString,
    cfprVnicRackServerDiscoveryProfileIntId                          SnmpAdminString,
    cfprVnicRackServerDiscoveryProfileMaxPorts                       Gauge32,
    cfprVnicRackServerDiscoveryProfileName                           SnmpAdminString,
    cfprVnicRackServerDiscoveryProfilePolicyLevel                    Gauge32,
    cfprVnicRackServerDiscoveryProfilePolicyOwner                    CfprPolicyPolicyOwner
}

cfprVnicRackServerDiscoveryProfileInstanceId OBJECT-TYPE
    SYNTAX       CfprManagedObjectId
    MAX-ACCESS   not-accessible
    STATUS       current
    DESCRIPTION
        "Instance identifier of the managed object."
    ::= { cfprVnicRackServerDiscoveryProfileEntry 1 }

cfprVnicRackServerDiscoveryProfileDn OBJECT-TYPE
    SYNTAX       CfprManagedObjectDn
    MAX-ACCESS   read-only
    STATUS       current
    DESCRIPTION
        "Cisco Firepower vnic:RackServerDiscoveryProfile:dn
        managed object property"
    ::= { cfprVnicRackServerDiscoveryProfileEntry 2 }

cfprVnicRackServerDiscoveryProfileRn OBJECT-TYPE
    SYNTAX       SnmpAdminString
    MAX-ACCESS   read-only
    STATUS       current
    DESCRIPTION
        "Cisco Firepower vnic:RackServerDiscoveryProfile:rn
        managed object property"
    ::= { cfprVnicRackServerDiscoveryProfileEntry 3 }

cfprVnicRackServerDiscoveryProfileDescr OBJECT-TYPE
    SYNTAX       SnmpAdminString
    MAX-ACCESS   read-only
    STATUS       current
    DESCRIPTION
        "Cisco Firepower vnic:RackServerDiscoveryProfile:descr
        managed object property"
    ::= { cfprVnicRackServerDiscoveryProfileEntry 4 }

cfprVnicRackServerDiscoveryProfileIntId OBJECT-TYPE
    SYNTAX       SnmpAdminString
    MAX-ACCESS   read-only
    STATUS       current
    DESCRIPTION
        "Cisco Firepower vnic:RackServerDiscoveryProfile:intId
        managed object property"
    ::= { cfprVnicRackServerDiscoveryProfileEntry 5 }

cfprVnicRackServerDiscoveryProfileMaxPorts OBJECT-TYPE
    SYNTAX       Gauge32
    MAX-ACCESS   read-only
    STATUS       current
    DESCRIPTION
        "Cisco Firepower vnic:RackServerDiscoveryProfile:maxPorts
        managed object property"
    ::= { cfprVnicRackServerDiscoveryProfileEntry 6 }

cfprVnicRackServerDiscoveryProfileName OBJECT-TYPE
    SYNTAX       SnmpAdminString
    MAX-ACCESS   read-only
    STATUS       current
    DESCRIPTION
        "Cisco Firepower vnic:RackServerDiscoveryProfile:name
        managed object property"
    ::= { cfprVnicRackServerDiscoveryProfileEntry 7 }

cfprVnicRackServerDiscoveryProfilePolicyLevel OBJECT-TYPE
    SYNTAX       Gauge32
    MAX-ACCESS   read-only
    STATUS       current
    DESCRIPTION
        "Cisco Firepower vnic:RackServerDiscoveryProfile:policyLevel
        managed object property"
    ::= { cfprVnicRackServerDiscoveryProfileEntry 8 }

cfprVnicRackServerDiscoveryProfilePolicyOwner OBJECT-TYPE
    SYNTAX       CfprPolicyPolicyOwner
    MAX-ACCESS   read-only
    STATUS       current
    DESCRIPTION
        "Cisco Firepower vnic:RackServerDiscoveryProfile:policyOwner
        managed object property"
    ::= { cfprVnicRackServerDiscoveryProfileEntry 9 }

cfprVnicSanConnPolicyTable OBJECT-TYPE
    SYNTAX           SEQUENCE OF CfprVnicSanConnPolicyEntry
    MAX-ACCESS       not-accessible
    STATUS           current
    DESCRIPTION
        "Cisco Firepower vnic:SanConnPolicy managed object table"
    ::= { cfprVnicObjects 61 }

cfprVnicSanConnPolicyEntry OBJECT-TYPE
    SYNTAX           CfprVnicSanConnPolicyEntry
    MAX-ACCESS       not-accessible
    STATUS           current
    DESCRIPTION
        "Entry for the cfprVnicSanConnPolicyTable table."
    INDEX { cfprVnicSanConnPolicyInstanceId }
    ::= { cfprVnicSanConnPolicyTable 1 }

CfprVnicSanConnPolicyEntry ::= SEQUENCE {
    cfprVnicSanConnPolicyInstanceId                                  CfprManagedObjectId,
    cfprVnicSanConnPolicyDn                                          CfprManagedObjectDn,
    cfprVnicSanConnPolicyRn                                          SnmpAdminString,
    cfprVnicSanConnPolicyDescr                                       SnmpAdminString,
    cfprVnicSanConnPolicyFltAggr                                     Unsigned64,
    cfprVnicSanConnPolicyIntId                                       SnmpAdminString,
    cfprVnicSanConnPolicyName                                        SnmpAdminString,
    cfprVnicSanConnPolicyPolicyLevel                                 Gauge32,
    cfprVnicSanConnPolicyPolicyOwner                                 CfprPolicyPolicyOwner
}

cfprVnicSanConnPolicyInstanceId OBJECT-TYPE
    SYNTAX       CfprManagedObjectId
    MAX-ACCESS   not-accessible
    STATUS       current
    DESCRIPTION
        "Instance identifier of the managed object."
    ::= { cfprVnicSanConnPolicyEntry 1 }

cfprVnicSanConnPolicyDn OBJECT-TYPE
    SYNTAX       CfprManagedObjectDn
    MAX-ACCESS   read-only
    STATUS       current
    DESCRIPTION
        "Cisco Firepower vnic:SanConnPolicy:dn managed object property"
    ::= { cfprVnicSanConnPolicyEntry 2 }

cfprVnicSanConnPolicyRn OBJECT-TYPE
    SYNTAX       SnmpAdminString
    MAX-ACCESS   read-only
    STATUS       current
    DESCRIPTION
        "Cisco Firepower vnic:SanConnPolicy:rn managed object property"
    ::= { cfprVnicSanConnPolicyEntry 3 }

cfprVnicSanConnPolicyDescr OBJECT-TYPE
    SYNTAX       SnmpAdminString
    MAX-ACCESS   read-only
    STATUS       current
    DESCRIPTION
        "Cisco Firepower vnic:SanConnPolicy:descr managed object property"
    ::= { cfprVnicSanConnPolicyEntry 4 }

cfprVnicSanConnPolicyFltAggr OBJECT-TYPE
    SYNTAX       Unsigned64
    MAX-ACCESS   read-only
    STATUS       current
    DESCRIPTION
        "Cisco Firepower vnic:SanConnPolicy:fltAggr managed
        object property"
    ::= { cfprVnicSanConnPolicyEntry 5 }

cfprVnicSanConnPolicyIntId OBJECT-TYPE
    SYNTAX       SnmpAdminString
    MAX-ACCESS   read-only
    STATUS       current
    DESCRIPTION
        "Cisco Firepower vnic:SanConnPolicy:intId managed object property"
    ::= { cfprVnicSanConnPolicyEntry 6 }

cfprVnicSanConnPolicyName OBJECT-TYPE
    SYNTAX       SnmpAdminString
    MAX-ACCESS   read-only
    STATUS       current
    DESCRIPTION
        "Cisco Firepower vnic:SanConnPolicy:name managed object property"
    ::= { cfprVnicSanConnPolicyEntry 7 }

cfprVnicSanConnPolicyPolicyLevel OBJECT-TYPE
    SYNTAX       Gauge32
    MAX-ACCESS   read-only
    STATUS       current
    DESCRIPTION
        "Cisco Firepower vnic:SanConnPolicy:policyLevel
        managed object property"
    ::= { cfprVnicSanConnPolicyEntry 8 }

cfprVnicSanConnPolicyPolicyOwner OBJECT-TYPE
    SYNTAX       CfprPolicyPolicyOwner
    MAX-ACCESS   read-only
    STATUS       current
    DESCRIPTION
        "Cisco Firepower vnic:SanConnPolicy:policyOwner
        managed object property"
    ::= { cfprVnicSanConnPolicyEntry 9 }

cfprVnicSanConnTemplTable OBJECT-TYPE
    SYNTAX           SEQUENCE OF CfprVnicSanConnTemplEntry
    MAX-ACCESS       not-accessible
    STATUS           current
    DESCRIPTION
        "Cisco Firepower vnic:SanConnTempl managed object table"
    ::= { cfprVnicObjects 62 }

cfprVnicSanConnTemplEntry OBJECT-TYPE
    SYNTAX           CfprVnicSanConnTemplEntry
    MAX-ACCESS       not-accessible
    STATUS           current
    DESCRIPTION
        "Entry for the cfprVnicSanConnTemplTable table."
    INDEX { cfprVnicSanConnTemplInstanceId }
    ::= { cfprVnicSanConnTemplTable 1 }

CfprVnicSanConnTemplEntry ::= SEQUENCE {
    cfprVnicSanConnTemplInstanceId                                   CfprManagedObjectId,
    cfprVnicSanConnTemplDn                                           CfprManagedObjectDn,
    cfprVnicSanConnTemplRn                                           SnmpAdminString,
    cfprVnicSanConnTemplDescr                                        SnmpAdminString,
    cfprVnicSanConnTemplIdentPoolName                                SnmpAdminString,
    cfprVnicSanConnTemplIntId                                        SnmpAdminString,
    cfprVnicSanConnTemplMaxDataFieldSize                             Gauge32,
    cfprVnicSanConnTemplName                                         SnmpAdminString,
    cfprVnicSanConnTemplNwCtrlPolicyName                             SnmpAdminString,
    cfprVnicSanConnTemplOperIdentPoolName                            SnmpAdminString,
    cfprVnicSanConnTemplOperQosPolicyName                            SnmpAdminString,
    cfprVnicSanConnTemplOperStatsPolicyName                          SnmpAdminString,
    cfprVnicSanConnTemplPinToGroupName                               SnmpAdminString,
    cfprVnicSanConnTemplPolicyLevel                                  Gauge32,
    cfprVnicSanConnTemplPolicyOwner                                  CfprPolicyPolicyOwner,
    cfprVnicSanConnTemplQosPolicyName                                SnmpAdminString,
    cfprVnicSanConnTemplStatsPolicyName                              SnmpAdminString,
    cfprVnicSanConnTemplSwitchId                                     CfprNetworkSwitchId,
    cfprVnicSanConnTemplTarget                                       CfprVnicSanConnTemplTarget,
    cfprVnicSanConnTemplTemplType                                    CfprVnicTemplateType
}

cfprVnicSanConnTemplInstanceId OBJECT-TYPE
    SYNTAX       CfprManagedObjectId
    MAX-ACCESS   not-accessible
    STATUS       current
    DESCRIPTION
        "Instance identifier of the managed object."
    ::= { cfprVnicSanConnTemplEntry 1 }

cfprVnicSanConnTemplDn OBJECT-TYPE
    SYNTAX       CfprManagedObjectDn
    MAX-ACCESS   read-only
    STATUS       current
    DESCRIPTION
        "Cisco Firepower vnic:SanConnTempl:dn managed object property"
    ::= { cfprVnicSanConnTemplEntry 2 }

cfprVnicSanConnTemplRn OBJECT-TYPE
    SYNTAX       SnmpAdminString
    MAX-ACCESS   read-only
    STATUS       current
    DESCRIPTION
        "Cisco Firepower vnic:SanConnTempl:rn managed object property"
    ::= { cfprVnicSanConnTemplEntry 3 }

cfprVnicSanConnTemplDescr OBJECT-TYPE
    SYNTAX       SnmpAdminString
    MAX-ACCESS   read-only
    STATUS       current
    DESCRIPTION
        "Cisco Firepower vnic:SanConnTempl:descr managed object property"
    ::= { cfprVnicSanConnTemplEntry 4 }

cfprVnicSanConnTemplIdentPoolName OBJECT-TYPE
    SYNTAX       SnmpAdminString
    MAX-ACCESS   read-only
    STATUS       current
    DESCRIPTION
        "Cisco Firepower vnic:SanConnTempl:identPoolName
        managed object property"
    ::= { cfprVnicSanConnTemplEntry 5 }

cfprVnicSanConnTemplIntId OBJECT-TYPE
    SYNTAX       SnmpAdminString
    MAX-ACCESS   read-only
    STATUS       current
    DESCRIPTION
        "Cisco Firepower vnic:SanConnTempl:intId managed object property"
    ::= { cfprVnicSanConnTemplEntry 6 }

cfprVnicSanConnTemplMaxDataFieldSize OBJECT-TYPE
    SYNTAX       Gauge32
    MAX-ACCESS   read-only
    STATUS       current
    DESCRIPTION
        "Cisco Firepower vnic:SanConnTempl:maxDataFieldSize
        managed object property"
    ::= { cfprVnicSanConnTemplEntry 7 }

cfprVnicSanConnTemplName OBJECT-TYPE
    SYNTAX       SnmpAdminString
    MAX-ACCESS   read-only
    STATUS       current
    DESCRIPTION
        "Cisco Firepower vnic:SanConnTempl:name managed object property"
    ::= { cfprVnicSanConnTemplEntry 8 }

cfprVnicSanConnTemplNwCtrlPolicyName OBJECT-TYPE
    SYNTAX       SnmpAdminString
    MAX-ACCESS   read-only
    STATUS       current
    DESCRIPTION
        "Cisco Firepower vnic:SanConnTempl:nwCtrlPolicyName
        managed object property"
    ::= { cfprVnicSanConnTemplEntry 9 }

cfprVnicSanConnTemplOperIdentPoolName OBJECT-TYPE
    SYNTAX       SnmpAdminString
    MAX-ACCESS   read-only
    STATUS       current
    DESCRIPTION
        "Cisco Firepower vnic:SanConnTempl:operIdentPoolName
        managed object property"
    ::= { cfprVnicSanConnTemplEntry 10 }

cfprVnicSanConnTemplOperQosPolicyName OBJECT-TYPE
    SYNTAX       SnmpAdminString
    MAX-ACCESS   read-only
    STATUS       current
    DESCRIPTION
        "Cisco Firepower vnic:SanConnTempl:operQosPolicyName
        managed object property"
    ::= { cfprVnicSanConnTemplEntry 11 }

cfprVnicSanConnTemplOperStatsPolicyName OBJECT-TYPE
    SYNTAX       SnmpAdminString
    MAX-ACCESS   read-only
    STATUS       current
    DESCRIPTION
        "Cisco Firepower vnic:SanConnTempl:operStatsPolicyName
        managed object property"
    ::= { cfprVnicSanConnTemplEntry 12 }

cfprVnicSanConnTemplPinToGroupName OBJECT-TYPE
    SYNTAX       SnmpAdminString
    MAX-ACCESS   read-only
    STATUS       current
    DESCRIPTION
        "Cisco Firepower vnic:SanConnTempl:pinToGroupName
        managed object property"
    ::= { cfprVnicSanConnTemplEntry 13 }

cfprVnicSanConnTemplPolicyLevel OBJECT-TYPE
    SYNTAX       Gauge32
    MAX-ACCESS   read-only
    STATUS       current
    DESCRIPTION
        "Cisco Firepower vnic:SanConnTempl:policyLevel
        managed object property"
    ::= { cfprVnicSanConnTemplEntry 14 }

cfprVnicSanConnTemplPolicyOwner OBJECT-TYPE
    SYNTAX       CfprPolicyPolicyOwner
    MAX-ACCESS   read-only
    STATUS       current
    DESCRIPTION
        "Cisco Firepower vnic:SanConnTempl:policyOwner
        managed object property"
    ::= { cfprVnicSanConnTemplEntry 15 }

cfprVnicSanConnTemplQosPolicyName OBJECT-TYPE
    SYNTAX       SnmpAdminString
    MAX-ACCESS   read-only
    STATUS       current
    DESCRIPTION
        "Cisco Firepower vnic:SanConnTempl:qosPolicyName
        managed object property"
    ::= { cfprVnicSanConnTemplEntry 16 }

cfprVnicSanConnTemplStatsPolicyName OBJECT-TYPE
    SYNTAX       SnmpAdminString
    MAX-ACCESS   read-only
    STATUS       current
    DESCRIPTION
        "Cisco Firepower vnic:SanConnTempl:statsPolicyName
        managed object property"
    ::= { cfprVnicSanConnTemplEntry 17 }

cfprVnicSanConnTemplSwitchId OBJECT-TYPE
    SYNTAX       CfprNetworkSwitchId
    MAX-ACCESS   read-only
    STATUS       current
    DESCRIPTION
        "Cisco Firepower vnic:SanConnTempl:switchId managed
        object property"
    ::= { cfprVnicSanConnTemplEntry 18 }

cfprVnicSanConnTemplTarget OBJECT-TYPE
    SYNTAX       CfprVnicSanConnTemplTarget
    MAX-ACCESS   read-only
    STATUS       current
    DESCRIPTION
        "Cisco Firepower vnic:SanConnTempl:target managed object property"
    ::= { cfprVnicSanConnTemplEntry 19 }

cfprVnicSanConnTemplTemplType OBJECT-TYPE
    SYNTAX       CfprVnicTemplateType
    MAX-ACCESS   read-only
    STATUS       current
    DESCRIPTION
        "Cisco Firepower vnic:SanConnTempl:templType managed
        object property"
    ::= { cfprVnicSanConnTemplEntry 20 }

cfprVnicScsiTable OBJECT-TYPE
    SYNTAX           SEQUENCE OF CfprVnicScsiEntry
    MAX-ACCESS       not-accessible
    STATUS           current
    DESCRIPTION
        "Cisco Firepower vnic:Scsi managed object table"
    ::= { cfprVnicObjects 63 }

cfprVnicScsiEntry OBJECT-TYPE
    SYNTAX           CfprVnicScsiEntry
    MAX-ACCESS       not-accessible
    STATUS           current
    DESCRIPTION
        "Entry for the cfprVnicScsiTable table."
    INDEX { cfprVnicScsiInstanceId }
    ::= { cfprVnicScsiTable 1 }

CfprVnicScsiEntry ::= SEQUENCE {
    cfprVnicScsiInstanceId                                           CfprManagedObjectId,
    cfprVnicScsiDn                                                   CfprManagedObjectDn,
    cfprVnicScsiRn                                                   SnmpAdminString,
    cfprVnicScsiAdaptorProfileName                                   SnmpAdminString,
    cfprVnicScsiAdminHostPort                                        CfprFabricHostPortId,
    cfprVnicScsiAdminVcon                                            SnmpAdminString,
    cfprVnicScsiAppRole                                              CfprVnicAppRole,
    cfprVnicScsiBootDev                                              CfprVnicVnicBootDev,
    cfprVnicScsiConfigQualifier                                      CfprVnicConfigIssues,
    cfprVnicScsiConfigState                                          CfprLsConfigState,
    cfprVnicScsiEquipmentDn                                          SnmpAdminString,
    cfprVnicScsiIdentPoolName                                        SnmpAdminString,
    cfprVnicScsiInstType                                             CfprVnicInstantiation,
    cfprVnicScsiName                                                 SnmpAdminString,
    cfprVnicScsiNwTemplName                                          SnmpAdminString,
    cfprVnicScsiOperHostPort                                         CfprVnicVnicOperHostPort,
    cfprVnicScsiOperOrder                                            Gauge32,
    cfprVnicScsiOperSpeed                                            Gauge32,
    cfprVnicScsiOperStatsPolicyName                                  SnmpAdminString,
    cfprVnicScsiOperVcon                                             SnmpAdminString,
    cfprVnicScsiOrder                                                Gauge32,
    cfprVnicScsiOwner                                                CfprVnicConnectionOwner,
    cfprVnicScsiPinToGroupName                                       SnmpAdminString,
    cfprVnicScsiQosPolicyName                                        SnmpAdminString,
    cfprVnicScsiStatsPolicyName                                      SnmpAdminString,
    cfprVnicScsiSwitchId                                             CfprNetworkSwitchId,
    cfprVnicScsiType                                                 CfprVnicScsiType
}

cfprVnicScsiInstanceId OBJECT-TYPE
    SYNTAX       CfprManagedObjectId
    MAX-ACCESS   not-accessible
    STATUS       current
    DESCRIPTION
        "Instance identifier of the managed object."
    ::= { cfprVnicScsiEntry 1 }

cfprVnicScsiDn OBJECT-TYPE
    SYNTAX       CfprManagedObjectDn
    MAX-ACCESS   read-only
    STATUS       current
    DESCRIPTION
        "Cisco Firepower vnic:Scsi:dn managed object property"
    ::= { cfprVnicScsiEntry 2 }

cfprVnicScsiRn OBJECT-TYPE
    SYNTAX       SnmpAdminString
    MAX-ACCESS   read-only
    STATUS       current
    DESCRIPTION
        "Cisco Firepower vnic:Scsi:rn managed object property"
    ::= { cfprVnicScsiEntry 3 }

cfprVnicScsiAdaptorProfileName OBJECT-TYPE
    SYNTAX       SnmpAdminString
    MAX-ACCESS   read-only
    STATUS       current
    DESCRIPTION
        "Cisco Firepower vnic:Scsi:adaptorProfileName managed
        object property"
    ::= { cfprVnicScsiEntry 4 }

cfprVnicScsiAdminHostPort OBJECT-TYPE
    SYNTAX       CfprFabricHostPortId
    MAX-ACCESS   read-only
    STATUS       current
    DESCRIPTION
        "Cisco Firepower vnic:Scsi:adminHostPort managed object property"
    ::= { cfprVnicScsiEntry 5 }

cfprVnicScsiAdminVcon OBJECT-TYPE
    SYNTAX       SnmpAdminString
    MAX-ACCESS   read-only
    STATUS       current
    DESCRIPTION
        "Cisco Firepower vnic:Scsi:adminVcon managed object property"
    ::= { cfprVnicScsiEntry 6 }

cfprVnicScsiAppRole OBJECT-TYPE
    SYNTAX       CfprVnicAppRole
    MAX-ACCESS   read-only
    STATUS       current
    DESCRIPTION
        "Cisco Firepower vnic:Scsi:appRole managed object property"
    ::= { cfprVnicScsiEntry 7 }

cfprVnicScsiBootDev OBJECT-TYPE
    SYNTAX       CfprVnicVnicBootDev
    MAX-ACCESS   read-only
    STATUS       current
    DESCRIPTION
        "Cisco Firepower vnic:Scsi:bootDev managed object property"
    ::= { cfprVnicScsiEntry 8 }

cfprVnicScsiConfigQualifier OBJECT-TYPE
    SYNTAX       CfprVnicConfigIssues
    MAX-ACCESS   read-only
    STATUS       current
    DESCRIPTION
        "Cisco Firepower vnic:Scsi:configQualifier managed
        object property"
    ::= { cfprVnicScsiEntry 9 }

cfprVnicScsiConfigState OBJECT-TYPE
    SYNTAX       CfprLsConfigState
    MAX-ACCESS   read-only
    STATUS       current
    DESCRIPTION
        "Cisco Firepower vnic:Scsi:configState managed object property"
    ::= { cfprVnicScsiEntry 10 }

cfprVnicScsiEquipmentDn OBJECT-TYPE
    SYNTAX       SnmpAdminString
    MAX-ACCESS   read-only
    STATUS       current
    DESCRIPTION
        "Cisco Firepower vnic:Scsi:equipmentDn managed object property"
    ::= { cfprVnicScsiEntry 11 }

cfprVnicScsiIdentPoolName OBJECT-TYPE
    SYNTAX       SnmpAdminString
    MAX-ACCESS   read-only
    STATUS       current
    DESCRIPTION
        "Cisco Firepower vnic:Scsi:identPoolName managed object property"
    ::= { cfprVnicScsiEntry 12 }

cfprVnicScsiInstType OBJECT-TYPE
    SYNTAX       CfprVnicInstantiation
    MAX-ACCESS   read-only
    STATUS       current
    DESCRIPTION
        "Cisco Firepower vnic:Scsi:instType managed object property"
    ::= { cfprVnicScsiEntry 13 }

cfprVnicScsiName OBJECT-TYPE
    SYNTAX       SnmpAdminString
    MAX-ACCESS   read-only
    STATUS       current
    DESCRIPTION
        "Cisco Firepower vnic:Scsi:name managed object property"
    ::= { cfprVnicScsiEntry 14 }

cfprVnicScsiNwTemplName OBJECT-TYPE
    SYNTAX       SnmpAdminString
    MAX-ACCESS   read-only
    STATUS       current
    DESCRIPTION
        "Cisco Firepower vnic:Scsi:nwTemplName managed object property"
    ::= { cfprVnicScsiEntry 15 }

cfprVnicScsiOperHostPort OBJECT-TYPE
    SYNTAX       CfprVnicVnicOperHostPort
    MAX-ACCESS   read-only
    STATUS       current
    DESCRIPTION
        "Cisco Firepower vnic:Scsi:operHostPort managed object property"
    ::= { cfprVnicScsiEntry 16 }

cfprVnicScsiOperOrder OBJECT-TYPE
    SYNTAX       Gauge32
    MAX-ACCESS   read-only
    STATUS       current
    DESCRIPTION
        "Cisco Firepower vnic:Scsi:operOrder managed object property"
    ::= { cfprVnicScsiEntry 17 }

cfprVnicScsiOperSpeed OBJECT-TYPE
    SYNTAX       Gauge32
    MAX-ACCESS   read-only
    STATUS       current
    DESCRIPTION
        "Cisco Firepower vnic:Scsi:operSpeed managed object property"
    ::= { cfprVnicScsiEntry 18 }

cfprVnicScsiOperStatsPolicyName OBJECT-TYPE
    SYNTAX       SnmpAdminString
    MAX-ACCESS   read-only
    STATUS       current
    DESCRIPTION
        "Cisco Firepower vnic:Scsi:operStatsPolicyName
        managed object property"
    ::= { cfprVnicScsiEntry 19 }

cfprVnicScsiOperVcon OBJECT-TYPE
    SYNTAX       SnmpAdminString
    MAX-ACCESS   read-only
    STATUS       current
    DESCRIPTION
        "Cisco Firepower vnic:Scsi:operVcon managed object property"
    ::= { cfprVnicScsiEntry 20 }

cfprVnicScsiOrder OBJECT-TYPE
    SYNTAX       Gauge32
    MAX-ACCESS   read-only
    STATUS       current
    DESCRIPTION
        "Cisco Firepower vnic:Scsi:order managed object property"
    ::= { cfprVnicScsiEntry 21 }

cfprVnicScsiOwner OBJECT-TYPE
    SYNTAX       CfprVnicConnectionOwner
    MAX-ACCESS   read-only
    STATUS       current
    DESCRIPTION
        "Cisco Firepower vnic:Scsi:owner managed object property"
    ::= { cfprVnicScsiEntry 22 }

cfprVnicScsiPinToGroupName OBJECT-TYPE
    SYNTAX       SnmpAdminString
    MAX-ACCESS   read-only
    STATUS       current
    DESCRIPTION
        "Cisco Firepower vnic:Scsi:pinToGroupName managed object property"
    ::= { cfprVnicScsiEntry 23 }

cfprVnicScsiQosPolicyName OBJECT-TYPE
    SYNTAX       SnmpAdminString
    MAX-ACCESS   read-only
    STATUS       current
    DESCRIPTION
        "Cisco Firepower vnic:Scsi:qosPolicyName managed object property"
    ::= { cfprVnicScsiEntry 24 }

cfprVnicScsiStatsPolicyName OBJECT-TYPE
    SYNTAX       SnmpAdminString
    MAX-ACCESS   read-only
    STATUS       current
    DESCRIPTION
        "Cisco Firepower vnic:Scsi:statsPolicyName managed
        object property"
    ::= { cfprVnicScsiEntry 25 }

cfprVnicScsiSwitchId OBJECT-TYPE
    SYNTAX       CfprNetworkSwitchId
    MAX-ACCESS   read-only
    STATUS       current
    DESCRIPTION
        "Cisco Firepower vnic:Scsi:switchId managed object property"
    ::= { cfprVnicScsiEntry 26 }

cfprVnicScsiType OBJECT-TYPE
    SYNTAX       CfprVnicScsiType
    MAX-ACCESS   read-only
    STATUS       current
    DESCRIPTION
        "Cisco Firepower vnic:Scsi:type managed object property"
    ::= { cfprVnicScsiEntry 27 }

cfprVnicScsiIfTable OBJECT-TYPE
    SYNTAX           SEQUENCE OF CfprVnicScsiIfEntry
    MAX-ACCESS       not-accessible
    STATUS           current
    DESCRIPTION
        "Cisco Firepower vnic:ScsiIf managed object table"
    ::= { cfprVnicObjects 64 }

cfprVnicScsiIfEntry OBJECT-TYPE
    SYNTAX           CfprVnicScsiIfEntry
    MAX-ACCESS       not-accessible
    STATUS           current
    DESCRIPTION
        "Entry for the cfprVnicScsiIfTable table."
    INDEX { cfprVnicScsiIfInstanceId }
    ::= { cfprVnicScsiIfTable 1 }

CfprVnicScsiIfEntry ::= SEQUENCE {
    cfprVnicScsiIfInstanceId                                         CfprManagedObjectId,
    cfprVnicScsiIfDn                                                 CfprManagedObjectDn,
    cfprVnicScsiIfRn                                                 SnmpAdminString,
    cfprVnicScsiIfAddr                                               Unsigned64,
    cfprVnicScsiIfConfigQualifier                                    CfprVnicConfigIssues,
    cfprVnicScsiIfName                                               SnmpAdminString,
    cfprVnicScsiIfOperState                                          CfprVnicIfOperState,
    cfprVnicScsiIfOperVnetDn                                         SnmpAdminString,
    cfprVnicScsiIfOperVnetName                                       SnmpAdminString,
    cfprVnicScsiIfOwner                                              CfprVnicConnectionOwner,
    cfprVnicScsiIfPubNwId                                            Gauge32,
    cfprVnicScsiIfSharing                                            CfprFabricVlanSharingType,
    cfprVnicScsiIfSwitchId                                           CfprNetworkSwitchId,
    cfprVnicScsiIfType                                               CfprVnicAScsiIfType,
    cfprVnicScsiIfVnet                                               Gauge32
}

cfprVnicScsiIfInstanceId OBJECT-TYPE
    SYNTAX       CfprManagedObjectId
    MAX-ACCESS   not-accessible
    STATUS       current
    DESCRIPTION
        "Instance identifier of the managed object."
    ::= { cfprVnicScsiIfEntry 1 }

cfprVnicScsiIfDn OBJECT-TYPE
    SYNTAX       CfprManagedObjectDn
    MAX-ACCESS   read-only
    STATUS       current
    DESCRIPTION
        "Cisco Firepower vnic:ScsiIf:dn managed object property"
    ::= { cfprVnicScsiIfEntry 2 }

cfprVnicScsiIfRn OBJECT-TYPE
    SYNTAX       SnmpAdminString
    MAX-ACCESS   read-only
    STATUS       current
    DESCRIPTION
        "Cisco Firepower vnic:ScsiIf:rn managed object property"
    ::= { cfprVnicScsiIfEntry 3 }

cfprVnicScsiIfAddr OBJECT-TYPE
    SYNTAX       Unsigned64
    MAX-ACCESS   read-only
    STATUS       current
    DESCRIPTION
        "Cisco Firepower vnic:ScsiIf:addr managed object property"
    ::= { cfprVnicScsiIfEntry 4 }

cfprVnicScsiIfConfigQualifier OBJECT-TYPE
    SYNTAX       CfprVnicConfigIssues
    MAX-ACCESS   read-only
    STATUS       current
    DESCRIPTION
        "Cisco Firepower vnic:ScsiIf:configQualifier managed
        object property"
    ::= { cfprVnicScsiIfEntry 5 }

cfprVnicScsiIfName OBJECT-TYPE
    SYNTAX       SnmpAdminString
    MAX-ACCESS   read-only
    STATUS       current
    DESCRIPTION
        "Cisco Firepower vnic:ScsiIf:name managed object property"
    ::= { cfprVnicScsiIfEntry 6 }

cfprVnicScsiIfOperState OBJECT-TYPE
    SYNTAX       CfprVnicIfOperState
    MAX-ACCESS   read-only
    STATUS       current
    DESCRIPTION
        "Cisco Firepower vnic:ScsiIf:operState managed object property"
    ::= { cfprVnicScsiIfEntry 7 }

cfprVnicScsiIfOperVnetDn OBJECT-TYPE
    SYNTAX       SnmpAdminString
    MAX-ACCESS   read-only
    STATUS       current
    DESCRIPTION
        "Cisco Firepower vnic:ScsiIf:operVnetDn managed object property"
    ::= { cfprVnicScsiIfEntry 8 }

cfprVnicScsiIfOperVnetName OBJECT-TYPE
    SYNTAX       SnmpAdminString
    MAX-ACCESS   read-only
    STATUS       current
    DESCRIPTION
        "Cisco Firepower vnic:ScsiIf:operVnetName managed object property"
    ::= { cfprVnicScsiIfEntry 9 }

cfprVnicScsiIfOwner OBJECT-TYPE
    SYNTAX       CfprVnicConnectionOwner
    MAX-ACCESS   read-only
    STATUS       current
    DESCRIPTION
        "Cisco Firepower vnic:ScsiIf:owner managed object property"
    ::= { cfprVnicScsiIfEntry 10 }

cfprVnicScsiIfPubNwId OBJECT-TYPE
    SYNTAX       Gauge32
    MAX-ACCESS   read-only
    STATUS       current
    DESCRIPTION
        "Cisco Firepower vnic:ScsiIf:pubNwId managed object property"
    ::= { cfprVnicScsiIfEntry 11 }

cfprVnicScsiIfSharing OBJECT-TYPE
    SYNTAX       CfprFabricVlanSharingType
    MAX-ACCESS   read-only
    STATUS       current
    DESCRIPTION
        "Cisco Firepower vnic:ScsiIf:sharing managed object property"
    ::= { cfprVnicScsiIfEntry 12 }

cfprVnicScsiIfSwitchId OBJECT-TYPE
    SYNTAX       CfprNetworkSwitchId
    MAX-ACCESS   read-only
    STATUS       current
    DESCRIPTION
        "Cisco Firepower vnic:ScsiIf:switchId managed object property"
    ::= { cfprVnicScsiIfEntry 13 }

cfprVnicScsiIfType OBJECT-TYPE
    SYNTAX       CfprVnicAScsiIfType
    MAX-ACCESS   read-only
    STATUS       current
    DESCRIPTION
        "Cisco Firepower vnic:ScsiIf:type managed object property"
    ::= { cfprVnicScsiIfEntry 14 }

cfprVnicScsiIfVnet OBJECT-TYPE
    SYNTAX       Gauge32
    MAX-ACCESS   read-only
    STATUS       current
    DESCRIPTION
        "Cisco Firepower vnic:ScsiIf:vnet managed object property"
    ::= { cfprVnicScsiIfEntry 15 }

cfprVnicUsnicConPolicyTable OBJECT-TYPE
    SYNTAX           SEQUENCE OF CfprVnicUsnicConPolicyEntry
    MAX-ACCESS       not-accessible
    STATUS           current
    DESCRIPTION
        "Cisco Firepower vnic:UsnicConPolicy managed object table"
    ::= { cfprVnicObjects 65 }

cfprVnicUsnicConPolicyEntry OBJECT-TYPE
    SYNTAX           CfprVnicUsnicConPolicyEntry
    MAX-ACCESS       not-accessible
    STATUS           current
    DESCRIPTION
        "Entry for the cfprVnicUsnicConPolicyTable table."
    INDEX { cfprVnicUsnicConPolicyInstanceId }
    ::= { cfprVnicUsnicConPolicyTable 1 }

CfprVnicUsnicConPolicyEntry ::= SEQUENCE {
    cfprVnicUsnicConPolicyInstanceId                                 CfprManagedObjectId,
    cfprVnicUsnicConPolicyDn                                         CfprManagedObjectDn,
    cfprVnicUsnicConPolicyRn                                         SnmpAdminString,
    cfprVnicUsnicConPolicyAdaptorProfileName                         SnmpAdminString,
    cfprVnicUsnicConPolicyDescr                                      SnmpAdminString,
    cfprVnicUsnicConPolicyIntId                                      SnmpAdminString,
    cfprVnicUsnicConPolicyName                                       SnmpAdminString,
    cfprVnicUsnicConPolicyPolicyLevel                                Gauge32,
    cfprVnicUsnicConPolicyPolicyOwner                                CfprPolicyPolicyOwner,
    cfprVnicUsnicConPolicyUsnicCount                                 Gauge32
}

cfprVnicUsnicConPolicyInstanceId OBJECT-TYPE
    SYNTAX       CfprManagedObjectId
    MAX-ACCESS   not-accessible
    STATUS       current
    DESCRIPTION
        "Instance identifier of the managed object."
    ::= { cfprVnicUsnicConPolicyEntry 1 }

cfprVnicUsnicConPolicyDn OBJECT-TYPE
    SYNTAX       CfprManagedObjectDn
    MAX-ACCESS   read-only
    STATUS       current
    DESCRIPTION
        "Cisco Firepower vnic:UsnicConPolicy:dn managed object property"
    ::= { cfprVnicUsnicConPolicyEntry 2 }

cfprVnicUsnicConPolicyRn OBJECT-TYPE
    SYNTAX       SnmpAdminString
    MAX-ACCESS   read-only
    STATUS       current
    DESCRIPTION
        "Cisco Firepower vnic:UsnicConPolicy:rn managed object property"
    ::= { cfprVnicUsnicConPolicyEntry 3 }

cfprVnicUsnicConPolicyAdaptorProfileName OBJECT-TYPE
    SYNTAX       SnmpAdminString
    MAX-ACCESS   read-only
    STATUS       current
    DESCRIPTION
        "Cisco Firepower vnic:UsnicConPolicy:adaptorProfileName
        managed object property"
    ::= { cfprVnicUsnicConPolicyEntry 4 }

cfprVnicUsnicConPolicyDescr OBJECT-TYPE
    SYNTAX       SnmpAdminString
    MAX-ACCESS   read-only
    STATUS       current
    DESCRIPTION
        "Cisco Firepower vnic:UsnicConPolicy:descr managed
        object property"
    ::= { cfprVnicUsnicConPolicyEntry 5 }

cfprVnicUsnicConPolicyIntId OBJECT-TYPE
    SYNTAX       SnmpAdminString
    MAX-ACCESS   read-only
    STATUS       current
    DESCRIPTION
        "Cisco Firepower vnic:UsnicConPolicy:intId managed
        object property"
    ::= { cfprVnicUsnicConPolicyEntry 6 }

cfprVnicUsnicConPolicyName OBJECT-TYPE
    SYNTAX       SnmpAdminString
    MAX-ACCESS   read-only
    STATUS       current
    DESCRIPTION
        "Cisco Firepower vnic:UsnicConPolicy:name managed object property"
    ::= { cfprVnicUsnicConPolicyEntry 7 }

cfprVnicUsnicConPolicyPolicyLevel OBJECT-TYPE
    SYNTAX       Gauge32
    MAX-ACCESS   read-only
    STATUS       current
    DESCRIPTION
        "Cisco Firepower vnic:UsnicConPolicy:policyLevel
        managed object property"
    ::= { cfprVnicUsnicConPolicyEntry 8 }

cfprVnicUsnicConPolicyPolicyOwner OBJECT-TYPE
    SYNTAX       CfprPolicyPolicyOwner
    MAX-ACCESS   read-only
    STATUS       current
    DESCRIPTION
        "Cisco Firepower vnic:UsnicConPolicy:policyOwner
        managed object property"
    ::= { cfprVnicUsnicConPolicyEntry 9 }

cfprVnicUsnicConPolicyUsnicCount OBJECT-TYPE
    SYNTAX       Gauge32
    MAX-ACCESS   read-only
    STATUS       current
    DESCRIPTION
        "Cisco Firepower vnic:UsnicConPolicy:usnicCount
        managed object property"
    ::= { cfprVnicUsnicConPolicyEntry 10 }

cfprVnicUsnicConPolicyRefTable OBJECT-TYPE
    SYNTAX           SEQUENCE OF CfprVnicUsnicConPolicyRefEntry
    MAX-ACCESS       not-accessible
    STATUS           current
    DESCRIPTION
        "Cisco Firepower vnic:UsnicConPolicyRef managed object table"
    ::= { cfprVnicObjects 66 }

cfprVnicUsnicConPolicyRefEntry OBJECT-TYPE
    SYNTAX           CfprVnicUsnicConPolicyRefEntry
    MAX-ACCESS       not-accessible
    STATUS           current
    DESCRIPTION
        "Entry for the cfprVnicUsnicConPolicyRefTable table."
    INDEX { cfprVnicUsnicConPolicyRefInstanceId }
    ::= { cfprVnicUsnicConPolicyRefTable 1 }

CfprVnicUsnicConPolicyRefEntry ::= SEQUENCE {
    cfprVnicUsnicConPolicyRefInstanceId                              CfprManagedObjectId,
    cfprVnicUsnicConPolicyRefDn                                      CfprManagedObjectDn,
    cfprVnicUsnicConPolicyRefRn                                      SnmpAdminString,
    cfprVnicUsnicConPolicyRefConPolicyName                           SnmpAdminString,
    cfprVnicUsnicConPolicyRefOperConPolicyName                       SnmpAdminString
}

cfprVnicUsnicConPolicyRefInstanceId OBJECT-TYPE
    SYNTAX       CfprManagedObjectId
    MAX-ACCESS   not-accessible
    STATUS       current
    DESCRIPTION
        "Instance identifier of the managed object."
    ::= { cfprVnicUsnicConPolicyRefEntry 1 }

cfprVnicUsnicConPolicyRefDn OBJECT-TYPE
    SYNTAX       CfprManagedObjectDn
    MAX-ACCESS   read-only
    STATUS       current
    DESCRIPTION
        "Cisco Firepower vnic:UsnicConPolicyRef:dn managed
        object property"
    ::= { cfprVnicUsnicConPolicyRefEntry 2 }

cfprVnicUsnicConPolicyRefRn OBJECT-TYPE
    SYNTAX       SnmpAdminString
    MAX-ACCESS   read-only
    STATUS       current
    DESCRIPTION
        "Cisco Firepower vnic:UsnicConPolicyRef:rn managed
        object property"
    ::= { cfprVnicUsnicConPolicyRefEntry 3 }

cfprVnicUsnicConPolicyRefConPolicyName OBJECT-TYPE
    SYNTAX       SnmpAdminString
    MAX-ACCESS   read-only
    STATUS       current
    DESCRIPTION
        "Cisco Firepower vnic:UsnicConPolicyRef:conPolicyName
        managed object property"
    ::= { cfprVnicUsnicConPolicyRefEntry 4 }

cfprVnicUsnicConPolicyRefOperConPolicyName OBJECT-TYPE
    SYNTAX       SnmpAdminString
    MAX-ACCESS   read-only
    STATUS       current
    DESCRIPTION
        "Cisco Firepower vnic:UsnicConPolicyRef:operConPolicyName
        managed object property"
    ::= { cfprVnicUsnicConPolicyRefEntry 5 }

cfprVnicVhbaBehPolicyTable OBJECT-TYPE
    SYNTAX           SEQUENCE OF CfprVnicVhbaBehPolicyEntry
    MAX-ACCESS       not-accessible
    STATUS           current
    DESCRIPTION
        "Cisco Firepower vnic:VhbaBehPolicy managed object table"
    ::= { cfprVnicObjects 67 }

cfprVnicVhbaBehPolicyEntry OBJECT-TYPE
    SYNTAX           CfprVnicVhbaBehPolicyEntry
    MAX-ACCESS       not-accessible
    STATUS           current
    DESCRIPTION
        "Entry for the cfprVnicVhbaBehPolicyTable table."
    INDEX { cfprVnicVhbaBehPolicyInstanceId }
    ::= { cfprVnicVhbaBehPolicyTable 1 }

CfprVnicVhbaBehPolicyEntry ::= SEQUENCE {
    cfprVnicVhbaBehPolicyInstanceId                                  CfprManagedObjectId,
    cfprVnicVhbaBehPolicyDn                                          CfprManagedObjectDn,
    cfprVnicVhbaBehPolicyRn                                          SnmpAdminString,
    cfprVnicVhbaBehPolicyAction                                      CfprVnicDefaultAction,
    cfprVnicVhbaBehPolicyDescr                                       SnmpAdminString,
    cfprVnicVhbaBehPolicyIntId                                       SnmpAdminString,
    cfprVnicVhbaBehPolicyName                                        SnmpAdminString,
    cfprVnicVhbaBehPolicyNwTemplName                                 SnmpAdminString,
    cfprVnicVhbaBehPolicyPolicyLevel                                 Gauge32,
    cfprVnicVhbaBehPolicyPolicyOwner                                 CfprPolicyPolicyOwner,
    cfprVnicVhbaBehPolicyType                                        CfprVnicVhbaBehPolicyType
}

cfprVnicVhbaBehPolicyInstanceId OBJECT-TYPE
    SYNTAX       CfprManagedObjectId
    MAX-ACCESS   not-accessible
    STATUS       current
    DESCRIPTION
        "Instance identifier of the managed object."
    ::= { cfprVnicVhbaBehPolicyEntry 1 }

cfprVnicVhbaBehPolicyDn OBJECT-TYPE
    SYNTAX       CfprManagedObjectDn
    MAX-ACCESS   read-only
    STATUS       current
    DESCRIPTION
        "Cisco Firepower vnic:VhbaBehPolicy:dn managed object property"
    ::= { cfprVnicVhbaBehPolicyEntry 2 }

cfprVnicVhbaBehPolicyRn OBJECT-TYPE
    SYNTAX       SnmpAdminString
    MAX-ACCESS   read-only
    STATUS       current
    DESCRIPTION
        "Cisco Firepower vnic:VhbaBehPolicy:rn managed object property"
    ::= { cfprVnicVhbaBehPolicyEntry 3 }

cfprVnicVhbaBehPolicyAction OBJECT-TYPE
    SYNTAX       CfprVnicDefaultAction
    MAX-ACCESS   read-only
    STATUS       current
    DESCRIPTION
        "Cisco Firepower vnic:VhbaBehPolicy:action managed
        object property"
    ::= { cfprVnicVhbaBehPolicyEntry 4 }

cfprVnicVhbaBehPolicyDescr OBJECT-TYPE
    SYNTAX       SnmpAdminString
    MAX-ACCESS   read-only
    STATUS       current
    DESCRIPTION
        "Cisco Firepower vnic:VhbaBehPolicy:descr managed object property"
    ::= { cfprVnicVhbaBehPolicyEntry 5 }

cfprVnicVhbaBehPolicyIntId OBJECT-TYPE
    SYNTAX       SnmpAdminString
    MAX-ACCESS   read-only
    STATUS       current
    DESCRIPTION
        "Cisco Firepower vnic:VhbaBehPolicy:intId managed object property"
    ::= { cfprVnicVhbaBehPolicyEntry 6 }

cfprVnicVhbaBehPolicyName OBJECT-TYPE
    SYNTAX       SnmpAdminString
    MAX-ACCESS   read-only
    STATUS       current
    DESCRIPTION
        "Cisco Firepower vnic:VhbaBehPolicy:name managed object property"
    ::= { cfprVnicVhbaBehPolicyEntry 7 }

cfprVnicVhbaBehPolicyNwTemplName OBJECT-TYPE
    SYNTAX       SnmpAdminString
    MAX-ACCESS   read-only
    STATUS       current
    DESCRIPTION
        "Cisco Firepower vnic:VhbaBehPolicy:nwTemplName
        managed object property"
    ::= { cfprVnicVhbaBehPolicyEntry 8 }

cfprVnicVhbaBehPolicyPolicyLevel OBJECT-TYPE
    SYNTAX       Gauge32
    MAX-ACCESS   read-only
    STATUS       current
    DESCRIPTION
        "Cisco Firepower vnic:VhbaBehPolicy:policyLevel
        managed object property"
    ::= { cfprVnicVhbaBehPolicyEntry 9 }

cfprVnicVhbaBehPolicyPolicyOwner OBJECT-TYPE
    SYNTAX       CfprPolicyPolicyOwner
    MAX-ACCESS   read-only
    STATUS       current
    DESCRIPTION
        "Cisco Firepower vnic:VhbaBehPolicy:policyOwner
        managed object property"
    ::= { cfprVnicVhbaBehPolicyEntry 10 }

cfprVnicVhbaBehPolicyType OBJECT-TYPE
    SYNTAX       CfprVnicVhbaBehPolicyType
    MAX-ACCESS   read-only
    STATUS       current
    DESCRIPTION
        "Cisco Firepower vnic:VhbaBehPolicy:type managed object property"
    ::= { cfprVnicVhbaBehPolicyEntry 11 }

cfprVnicVlanTable OBJECT-TYPE
    SYNTAX           SEQUENCE OF CfprVnicVlanEntry
    MAX-ACCESS       not-accessible
    STATUS           current
    DESCRIPTION
        "Cisco Firepower vnic:Vlan managed object table"
    ::= { cfprVnicObjects 68 }

cfprVnicVlanEntry OBJECT-TYPE
    SYNTAX           CfprVnicVlanEntry
    MAX-ACCESS       not-accessible
    STATUS           current
    DESCRIPTION
        "Entry for the cfprVnicVlanTable table."
    INDEX { cfprVnicVlanInstanceId }
    ::= { cfprVnicVlanTable 1 }

CfprVnicVlanEntry ::= SEQUENCE {
    cfprVnicVlanInstanceId                                           CfprManagedObjectId,
    cfprVnicVlanDn                                                   CfprManagedObjectDn,
    cfprVnicVlanRn                                                   SnmpAdminString,
    cfprVnicVlanConfigQualifier                                      CfprVnicConfigIssues,
    cfprVnicVlanFltAggr                                              Unsigned64,
    cfprVnicVlanName                                                 SnmpAdminString,
    cfprVnicVlanOperState                                            CfprVnicIfOperState,
    cfprVnicVlanOperVnetDn                                           SnmpAdminString,
    cfprVnicVlanOperVnetName                                         SnmpAdminString,
    cfprVnicVlanOwner                                                CfprVnicConnectionOwner,
    cfprVnicVlanPubNwId                                              Gauge32,
    cfprVnicVlanSharing                                              CfprFabricVlanSharingType,
    cfprVnicVlanSwitchId                                             CfprNetworkSwitchId,
    cfprVnicVlanType                                                 CfprVnicConnectionType,
    cfprVnicVlanVlanName                                             SnmpAdminString,
    cfprVnicVlanVnet                                                 Gauge32
}

cfprVnicVlanInstanceId OBJECT-TYPE
    SYNTAX       CfprManagedObjectId
    MAX-ACCESS   not-accessible
    STATUS       current
    DESCRIPTION
        "Instance identifier of the managed object."
    ::= { cfprVnicVlanEntry 1 }

cfprVnicVlanDn OBJECT-TYPE
    SYNTAX       CfprManagedObjectDn
    MAX-ACCESS   read-only
    STATUS       current
    DESCRIPTION
        "Cisco Firepower vnic:Vlan:dn managed object property"
    ::= { cfprVnicVlanEntry 2 }

cfprVnicVlanRn OBJECT-TYPE
    SYNTAX       SnmpAdminString
    MAX-ACCESS   read-only
    STATUS       current
    DESCRIPTION
        "Cisco Firepower vnic:Vlan:rn managed object property"
    ::= { cfprVnicVlanEntry 3 }

cfprVnicVlanConfigQualifier OBJECT-TYPE
    SYNTAX       CfprVnicConfigIssues
    MAX-ACCESS   read-only
    STATUS       current
    DESCRIPTION
        "Cisco Firepower vnic:Vlan:configQualifier managed
        object property"
    ::= { cfprVnicVlanEntry 4 }

cfprVnicVlanFltAggr OBJECT-TYPE
    SYNTAX       Unsigned64
    MAX-ACCESS   read-only
    STATUS       current
    DESCRIPTION
        "Cisco Firepower vnic:Vlan:fltAggr managed object property"
    ::= { cfprVnicVlanEntry 5 }

cfprVnicVlanName OBJECT-TYPE
    SYNTAX       SnmpAdminString
    MAX-ACCESS   read-only
    STATUS       current
    DESCRIPTION
        "Cisco Firepower vnic:Vlan:name managed object property"
    ::= { cfprVnicVlanEntry 6 }

cfprVnicVlanOperState OBJECT-TYPE
    SYNTAX       CfprVnicIfOperState
    MAX-ACCESS   read-only
    STATUS       current
    DESCRIPTION
        "Cisco Firepower vnic:Vlan:operState managed object property"
    ::= { cfprVnicVlanEntry 7 }

cfprVnicVlanOperVnetDn OBJECT-TYPE
    SYNTAX       SnmpAdminString
    MAX-ACCESS   read-only
    STATUS       current
    DESCRIPTION
        "Cisco Firepower vnic:Vlan:operVnetDn managed object property"
    ::= { cfprVnicVlanEntry 8 }

cfprVnicVlanOperVnetName OBJECT-TYPE
    SYNTAX       SnmpAdminString
    MAX-ACCESS   read-only
    STATUS       current
    DESCRIPTION
        "Cisco Firepower vnic:Vlan:operVnetName managed object property"
    ::= { cfprVnicVlanEntry 9 }

cfprVnicVlanOwner OBJECT-TYPE
    SYNTAX       CfprVnicConnectionOwner
    MAX-ACCESS   read-only
    STATUS       current
    DESCRIPTION
        "Cisco Firepower vnic:Vlan:owner managed object property"
    ::= { cfprVnicVlanEntry 10 }

cfprVnicVlanPubNwId OBJECT-TYPE
    SYNTAX       Gauge32
    MAX-ACCESS   read-only
    STATUS       current
    DESCRIPTION
        "Cisco Firepower vnic:Vlan:pubNwId managed object property"
    ::= { cfprVnicVlanEntry 11 }

cfprVnicVlanSharing OBJECT-TYPE
    SYNTAX       CfprFabricVlanSharingType
    MAX-ACCESS   read-only
    STATUS       current
    DESCRIPTION
        "Cisco Firepower vnic:Vlan:sharing managed object property"
    ::= { cfprVnicVlanEntry 12 }

cfprVnicVlanSwitchId OBJECT-TYPE
    SYNTAX       CfprNetworkSwitchId
    MAX-ACCESS   read-only
    STATUS       current
    DESCRIPTION
        "Cisco Firepower vnic:Vlan:switchId managed object property"
    ::= { cfprVnicVlanEntry 13 }

cfprVnicVlanType OBJECT-TYPE
    SYNTAX       CfprVnicConnectionType
    MAX-ACCESS   read-only
    STATUS       current
    DESCRIPTION
        "Cisco Firepower vnic:Vlan:type managed object property"
    ::= { cfprVnicVlanEntry 14 }

cfprVnicVlanVlanName OBJECT-TYPE
    SYNTAX       SnmpAdminString
    MAX-ACCESS   read-only
    STATUS       current
    DESCRIPTION
        "Cisco Firepower vnic:Vlan:vlanName managed object property"
    ::= { cfprVnicVlanEntry 15 }

cfprVnicVlanVnet OBJECT-TYPE
    SYNTAX       Gauge32
    MAX-ACCESS   read-only
    STATUS       current
    DESCRIPTION
        "Cisco Firepower vnic:Vlan:vnet managed object property"
    ::= { cfprVnicVlanEntry 16 }

cfprVnicVmqConPolicyTable OBJECT-TYPE
    SYNTAX           SEQUENCE OF CfprVnicVmqConPolicyEntry
    MAX-ACCESS       not-accessible
    STATUS           current
    DESCRIPTION
        "Cisco Firepower vnic:VmqConPolicy managed object table"
    ::= { cfprVnicObjects 69 }

cfprVnicVmqConPolicyEntry OBJECT-TYPE
    SYNTAX           CfprVnicVmqConPolicyEntry
    MAX-ACCESS       not-accessible
    STATUS           current
    DESCRIPTION
        "Entry for the cfprVnicVmqConPolicyTable table."
    INDEX { cfprVnicVmqConPolicyInstanceId }
    ::= { cfprVnicVmqConPolicyTable 1 }

CfprVnicVmqConPolicyEntry ::= SEQUENCE {
    cfprVnicVmqConPolicyInstanceId                                   CfprManagedObjectId,
    cfprVnicVmqConPolicyDn                                           CfprManagedObjectDn,
    cfprVnicVmqConPolicyRn                                           SnmpAdminString,
    cfprVnicVmqConPolicyDescr                                        SnmpAdminString,
    cfprVnicVmqConPolicyIntId                                        SnmpAdminString,
    cfprVnicVmqConPolicyIntrCount                                    Gauge32,
    cfprVnicVmqConPolicyName                                         SnmpAdminString,
    cfprVnicVmqConPolicyPolicyLevel                                  Gauge32,
    cfprVnicVmqConPolicyPolicyOwner                                  CfprPolicyPolicyOwner,
    cfprVnicVmqConPolicyVmqCount                                     Gauge32
}

cfprVnicVmqConPolicyInstanceId OBJECT-TYPE
    SYNTAX       CfprManagedObjectId
    MAX-ACCESS   not-accessible
    STATUS       current
    DESCRIPTION
        "Instance identifier of the managed object."
    ::= { cfprVnicVmqConPolicyEntry 1 }

cfprVnicVmqConPolicyDn OBJECT-TYPE
    SYNTAX       CfprManagedObjectDn
    MAX-ACCESS   read-only
    STATUS       current
    DESCRIPTION
        "Cisco Firepower vnic:VmqConPolicy:dn managed object property"
    ::= { cfprVnicVmqConPolicyEntry 2 }

cfprVnicVmqConPolicyRn OBJECT-TYPE
    SYNTAX       SnmpAdminString
    MAX-ACCESS   read-only
    STATUS       current
    DESCRIPTION
        "Cisco Firepower vnic:VmqConPolicy:rn managed object property"
    ::= { cfprVnicVmqConPolicyEntry 3 }

cfprVnicVmqConPolicyDescr OBJECT-TYPE
    SYNTAX       SnmpAdminString
    MAX-ACCESS   read-only
    STATUS       current
    DESCRIPTION
        "Cisco Firepower vnic:VmqConPolicy:descr managed object property"
    ::= { cfprVnicVmqConPolicyEntry 4 }

cfprVnicVmqConPolicyIntId OBJECT-TYPE
    SYNTAX       SnmpAdminString
    MAX-ACCESS   read-only
    STATUS       current
    DESCRIPTION
        "Cisco Firepower vnic:VmqConPolicy:intId managed object property"
    ::= { cfprVnicVmqConPolicyEntry 5 }

cfprVnicVmqConPolicyIntrCount OBJECT-TYPE
    SYNTAX       Gauge32
    MAX-ACCESS   read-only
    STATUS       current
    DESCRIPTION
        "Cisco Firepower vnic:VmqConPolicy:intrCount managed
        object property"
    ::= { cfprVnicVmqConPolicyEntry 6 }

cfprVnicVmqConPolicyName OBJECT-TYPE
    SYNTAX       SnmpAdminString
    MAX-ACCESS   read-only
    STATUS       current
    DESCRIPTION
        "Cisco Firepower vnic:VmqConPolicy:name managed object property"
    ::= { cfprVnicVmqConPolicyEntry 7 }

cfprVnicVmqConPolicyPolicyLevel OBJECT-TYPE
    SYNTAX       Gauge32
    MAX-ACCESS   read-only
    STATUS       current
    DESCRIPTION
        "Cisco Firepower vnic:VmqConPolicy:policyLevel
        managed object property"
    ::= { cfprVnicVmqConPolicyEntry 8 }

cfprVnicVmqConPolicyPolicyOwner OBJECT-TYPE
    SYNTAX       CfprPolicyPolicyOwner
    MAX-ACCESS   read-only
    STATUS       current
    DESCRIPTION
        "Cisco Firepower vnic:VmqConPolicy:policyOwner
        managed object property"
    ::= { cfprVnicVmqConPolicyEntry 9 }

cfprVnicVmqConPolicyVmqCount OBJECT-TYPE
    SYNTAX       Gauge32
    MAX-ACCESS   read-only
    STATUS       current
    DESCRIPTION
        "Cisco Firepower vnic:VmqConPolicy:vmqCount managed
        object property"
    ::= { cfprVnicVmqConPolicyEntry 10 }

cfprVnicVmqConPolicyRefTable OBJECT-TYPE
    SYNTAX           SEQUENCE OF CfprVnicVmqConPolicyRefEntry
    MAX-ACCESS       not-accessible
    STATUS           current
    DESCRIPTION
        "Cisco Firepower vnic:VmqConPolicyRef managed object table"
    ::= { cfprVnicObjects 70 }

cfprVnicVmqConPolicyRefEntry OBJECT-TYPE
    SYNTAX           CfprVnicVmqConPolicyRefEntry
    MAX-ACCESS       not-accessible
    STATUS           current
    DESCRIPTION
        "Entry for the cfprVnicVmqConPolicyRefTable table."
    INDEX { cfprVnicVmqConPolicyRefInstanceId }
    ::= { cfprVnicVmqConPolicyRefTable 1 }

CfprVnicVmqConPolicyRefEntry ::= SEQUENCE {
    cfprVnicVmqConPolicyRefInstanceId                                CfprManagedObjectId,
    cfprVnicVmqConPolicyRefDn                                        CfprManagedObjectDn,
    cfprVnicVmqConPolicyRefRn                                        SnmpAdminString,
    cfprVnicVmqConPolicyRefConPolicyName                             SnmpAdminString,
    cfprVnicVmqConPolicyRefOperConPolicyName                         SnmpAdminString
}

cfprVnicVmqConPolicyRefInstanceId OBJECT-TYPE
    SYNTAX       CfprManagedObjectId
    MAX-ACCESS   not-accessible
    STATUS       current
    DESCRIPTION
        "Instance identifier of the managed object."
    ::= { cfprVnicVmqConPolicyRefEntry 1 }

cfprVnicVmqConPolicyRefDn OBJECT-TYPE
    SYNTAX       CfprManagedObjectDn
    MAX-ACCESS   read-only
    STATUS       current
    DESCRIPTION
        "Cisco Firepower vnic:VmqConPolicyRef:dn managed object property"
    ::= { cfprVnicVmqConPolicyRefEntry 2 }

cfprVnicVmqConPolicyRefRn OBJECT-TYPE
    SYNTAX       SnmpAdminString
    MAX-ACCESS   read-only
    STATUS       current
    DESCRIPTION
        "Cisco Firepower vnic:VmqConPolicyRef:rn managed object property"
    ::= { cfprVnicVmqConPolicyRefEntry 3 }

cfprVnicVmqConPolicyRefConPolicyName OBJECT-TYPE
    SYNTAX       SnmpAdminString
    MAX-ACCESS   read-only
    STATUS       current
    DESCRIPTION
        "Cisco Firepower vnic:VmqConPolicyRef:conPolicyName
        managed object property"
    ::= { cfprVnicVmqConPolicyRefEntry 4 }

cfprVnicVmqConPolicyRefOperConPolicyName OBJECT-TYPE
    SYNTAX       SnmpAdminString
    MAX-ACCESS   read-only
    STATUS       current
    DESCRIPTION
        "Cisco Firepower vnic:VmqConPolicyRef:operConPolicyName
        managed object property"
    ::= { cfprVnicVmqConPolicyRefEntry 5 }

cfprVnicVnicBehPolicyTable OBJECT-TYPE
    SYNTAX           SEQUENCE OF CfprVnicVnicBehPolicyEntry
    MAX-ACCESS       not-accessible
    STATUS           current
    DESCRIPTION
        "Cisco Firepower vnic:VnicBehPolicy managed object table"
    ::= { cfprVnicObjects 71 }

cfprVnicVnicBehPolicyEntry OBJECT-TYPE
    SYNTAX           CfprVnicVnicBehPolicyEntry
    MAX-ACCESS       not-accessible
    STATUS           current
    DESCRIPTION
        "Entry for the cfprVnicVnicBehPolicyTable table."
    INDEX { cfprVnicVnicBehPolicyInstanceId }
    ::= { cfprVnicVnicBehPolicyTable 1 }

CfprVnicVnicBehPolicyEntry ::= SEQUENCE {
    cfprVnicVnicBehPolicyInstanceId                                  CfprManagedObjectId,
    cfprVnicVnicBehPolicyDn                                          CfprManagedObjectDn,
    cfprVnicVnicBehPolicyRn                                          SnmpAdminString,
    cfprVnicVnicBehPolicyAction                                      CfprVnicDefaultAction,
    cfprVnicVnicBehPolicyDescr                                       SnmpAdminString,
    cfprVnicVnicBehPolicyIntId                                       SnmpAdminString,
    cfprVnicVnicBehPolicyName                                        SnmpAdminString,
    cfprVnicVnicBehPolicyNwTemplName                                 SnmpAdminString,
    cfprVnicVnicBehPolicyPolicyLevel                                 Gauge32,
    cfprVnicVnicBehPolicyPolicyOwner                                 CfprPolicyPolicyOwner,
    cfprVnicVnicBehPolicyType                                        CfprVnicVnicBehPolicyType
}

cfprVnicVnicBehPolicyInstanceId OBJECT-TYPE
    SYNTAX       CfprManagedObjectId
    MAX-ACCESS   not-accessible
    STATUS       current
    DESCRIPTION
        "Instance identifier of the managed object."
    ::= { cfprVnicVnicBehPolicyEntry 1 }

cfprVnicVnicBehPolicyDn OBJECT-TYPE
    SYNTAX       CfprManagedObjectDn
    MAX-ACCESS   read-only
    STATUS       current
    DESCRIPTION
        "Cisco Firepower vnic:VnicBehPolicy:dn managed object property"
    ::= { cfprVnicVnicBehPolicyEntry 2 }

cfprVnicVnicBehPolicyRn OBJECT-TYPE
    SYNTAX       SnmpAdminString
    MAX-ACCESS   read-only
    STATUS       current
    DESCRIPTION
        "Cisco Firepower vnic:VnicBehPolicy:rn managed object property"
    ::= { cfprVnicVnicBehPolicyEntry 3 }

cfprVnicVnicBehPolicyAction OBJECT-TYPE
    SYNTAX       CfprVnicDefaultAction
    MAX-ACCESS   read-only
    STATUS       current
    DESCRIPTION
        "Cisco Firepower vnic:VnicBehPolicy:action managed
        object property"
    ::= { cfprVnicVnicBehPolicyEntry 4 }

cfprVnicVnicBehPolicyDescr OBJECT-TYPE
    SYNTAX       SnmpAdminString
    MAX-ACCESS   read-only
    STATUS       current
    DESCRIPTION
        "Cisco Firepower vnic:VnicBehPolicy:descr managed object property"
    ::= { cfprVnicVnicBehPolicyEntry 5 }

cfprVnicVnicBehPolicyIntId OBJECT-TYPE
    SYNTAX       SnmpAdminString
    MAX-ACCESS   read-only
    STATUS       current
    DESCRIPTION
        "Cisco Firepower vnic:VnicBehPolicy:intId managed object property"
    ::= { cfprVnicVnicBehPolicyEntry 6 }

cfprVnicVnicBehPolicyName OBJECT-TYPE
    SYNTAX       SnmpAdminString
    MAX-ACCESS   read-only
    STATUS       current
    DESCRIPTION
        "Cisco Firepower vnic:VnicBehPolicy:name managed object property"
    ::= { cfprVnicVnicBehPolicyEntry 7 }

cfprVnicVnicBehPolicyNwTemplName OBJECT-TYPE
    SYNTAX       SnmpAdminString
    MAX-ACCESS   read-only
    STATUS       current
    DESCRIPTION
        "Cisco Firepower vnic:VnicBehPolicy:nwTemplName
        managed object property"
    ::= { cfprVnicVnicBehPolicyEntry 8 }

cfprVnicVnicBehPolicyPolicyLevel OBJECT-TYPE
    SYNTAX       Gauge32
    MAX-ACCESS   read-only
    STATUS       current
    DESCRIPTION
        "Cisco Firepower vnic:VnicBehPolicy:policyLevel
        managed object property"
    ::= { cfprVnicVnicBehPolicyEntry 9 }

cfprVnicVnicBehPolicyPolicyOwner OBJECT-TYPE
    SYNTAX       CfprPolicyPolicyOwner
    MAX-ACCESS   read-only
    STATUS       current
    DESCRIPTION
        "Cisco Firepower vnic:VnicBehPolicy:policyOwner
        managed object property"
    ::= { cfprVnicVnicBehPolicyEntry 10 }

cfprVnicVnicBehPolicyType OBJECT-TYPE
    SYNTAX       CfprVnicVnicBehPolicyType
    MAX-ACCESS   read-only
    STATUS       current
    DESCRIPTION
        "Cisco Firepower vnic:VnicBehPolicy:type managed object property"
    ::= { cfprVnicVnicBehPolicyEntry 11 }

cfprVnicWwnnHistoryTable OBJECT-TYPE
    SYNTAX           SEQUENCE OF CfprVnicWwnnHistoryEntry
    MAX-ACCESS       not-accessible
    STATUS           current
    DESCRIPTION
        "Cisco Firepower vnic:WwnnHistory managed object table"
    ::= { cfprVnicObjects 72 }

cfprVnicWwnnHistoryEntry OBJECT-TYPE
    SYNTAX           CfprVnicWwnnHistoryEntry
    MAX-ACCESS       not-accessible
    STATUS           current
    DESCRIPTION
        "Entry for the cfprVnicWwnnHistoryTable table."
    INDEX { cfprVnicWwnnHistoryInstanceId }
    ::= { cfprVnicWwnnHistoryTable 1 }

CfprVnicWwnnHistoryEntry ::= SEQUENCE {
    cfprVnicWwnnHistoryInstanceId                                    CfprManagedObjectId,
    cfprVnicWwnnHistoryDn                                            CfprManagedObjectDn,
    cfprVnicWwnnHistoryRn                                            SnmpAdminString,
    cfprVnicWwnnHistoryOldwwnn                                       Unsigned64
}

cfprVnicWwnnHistoryInstanceId OBJECT-TYPE
    SYNTAX       CfprManagedObjectId
    MAX-ACCESS   not-accessible
    STATUS       current
    DESCRIPTION
        "Instance identifier of the managed object."
    ::= { cfprVnicWwnnHistoryEntry 1 }

cfprVnicWwnnHistoryDn OBJECT-TYPE
    SYNTAX       CfprManagedObjectDn
    MAX-ACCESS   read-only
    STATUS       current
    DESCRIPTION
        "Cisco Firepower vnic:WwnnHistory:dn managed object property"
    ::= { cfprVnicWwnnHistoryEntry 2 }

cfprVnicWwnnHistoryRn OBJECT-TYPE
    SYNTAX       SnmpAdminString
    MAX-ACCESS   read-only
    STATUS       current
    DESCRIPTION
        "Cisco Firepower vnic:WwnnHistory:rn managed object property"
    ::= { cfprVnicWwnnHistoryEntry 3 }

cfprVnicWwnnHistoryOldwwnn OBJECT-TYPE
    SYNTAX       Unsigned64
    MAX-ACCESS   read-only
    STATUS       current
    DESCRIPTION
        "Cisco Firepower vnic:WwnnHistory:oldwwnn managed object property"
    ::= { cfprVnicWwnnHistoryEntry 4 }

cfprVnicWwpnHistoryTable OBJECT-TYPE
    SYNTAX           SEQUENCE OF CfprVnicWwpnHistoryEntry
    MAX-ACCESS       not-accessible
    STATUS           current
    DESCRIPTION
        "Cisco Firepower vnic:WwpnHistory managed object table"
    ::= { cfprVnicObjects 73 }

cfprVnicWwpnHistoryEntry OBJECT-TYPE
    SYNTAX           CfprVnicWwpnHistoryEntry
    MAX-ACCESS       not-accessible
    STATUS           current
    DESCRIPTION
        "Entry for the cfprVnicWwpnHistoryTable table."
    INDEX { cfprVnicWwpnHistoryInstanceId }
    ::= { cfprVnicWwpnHistoryTable 1 }

CfprVnicWwpnHistoryEntry ::= SEQUENCE {
    cfprVnicWwpnHistoryInstanceId                                    CfprManagedObjectId,
    cfprVnicWwpnHistoryDn                                            CfprManagedObjectDn,
    cfprVnicWwpnHistoryRn                                            SnmpAdminString,
    cfprVnicWwpnHistoryOldaddr                                       Unsigned64
}

cfprVnicWwpnHistoryInstanceId OBJECT-TYPE
    SYNTAX       CfprManagedObjectId
    MAX-ACCESS   not-accessible
    STATUS       current
    DESCRIPTION
        "Instance identifier of the managed object."
    ::= { cfprVnicWwpnHistoryEntry 1 }

cfprVnicWwpnHistoryDn OBJECT-TYPE
    SYNTAX       CfprManagedObjectDn
    MAX-ACCESS   read-only
    STATUS       current
    DESCRIPTION
        "Cisco Firepower vnic:WwpnHistory:dn managed object property"
    ::= { cfprVnicWwpnHistoryEntry 2 }

cfprVnicWwpnHistoryRn OBJECT-TYPE
    SYNTAX       SnmpAdminString
    MAX-ACCESS   read-only
    STATUS       current
    DESCRIPTION
        "Cisco Firepower vnic:WwpnHistory:rn managed object property"
    ::= { cfprVnicWwpnHistoryEntry 3 }

cfprVnicWwpnHistoryOldaddr OBJECT-TYPE
    SYNTAX       Unsigned64
    MAX-ACCESS   read-only
    STATUS       current
    DESCRIPTION
        "Cisco Firepower vnic:WwpnHistory:oldaddr managed object property"
    ::= { cfprVnicWwpnHistoryEntry 4 }

END

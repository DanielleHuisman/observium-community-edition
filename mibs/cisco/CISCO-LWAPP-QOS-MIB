-- *******************************************************************
-- CISCO-LWAPP-QOS-MIB.my
-- November 2011 Gayathri
--   
-- Copyright (c) 2011-2013, 2018, 2021, 2023 by Cisco Systems, Inc.
-- All rights reserved.
-- *******************************************************************

CISCO-LWAPP-QOS-MIB DEFINITIONS ::= BEGIN

IMPORTS
    MODULE-IDENTITY,
    OBJECT-TYPE,
    NOTIFICATION-TYPE,
    Unsigned32,
    Counter32,
    Gauge32,
    IpAddress
        FROM SNMPv2-SMI
    MODULE-COMPLIANCE,
    OBJECT-GROUP,
    NOTIFICATION-GROUP
        FROM SNMPv2-CONF
    TruthValue,
    TEXTUAL-CONVENTION,
    TimeStamp,
    MacAddress,
    DisplayString,
    StorageType,
    RowStatus
        FROM SNMPv2-TC
    SnmpAdminString
        FROM SNMP-FRAMEWORK-MIB
    InetAddressType,
    InetAddress
        FROM INET-ADDRESS-MIB
    TimeIntervalSec,
    CiscoURLStringOrEmpty
        FROM CISCO-TC
    cldcClientMacAddress
        FROM CISCO-LWAPP-DOT11-CLIENT-MIB
    cLApSysMacAddress,
    cLApDot11IfSlotId,
    cLApName,
    cLApDot11IfType,
    cLApDot11IfEntry
        FROM CISCO-LWAPP-AP-MIB
    cLWlanIndex,
    cLWlanConfigEntry
        FROM CISCO-LWAPP-WLAN-MIB
    Percent
        FROM CISCO-QOS-PIB-MIB
    ciscoMgmt
        FROM CISCO-SMI;


-- ********************************************************************
-- *  MODULE IDENTITY
-- ********************************************************************

ciscoLwappQosMIB MODULE-IDENTITY
    LAST-UPDATED    "201302270000Z"
    ORGANIZATION    "Cisco Systems Inc."
    CONTACT-INFO
            "Cisco Systems,
            Customer Service
            Postal: 170 West Tasman Drive
            San Jose, CA  95134
            USA
            Tel: +1 800 553-NETS

            Email: cs-wnbu-snmp@cisco.com"
    DESCRIPTION
        "This MIB is intended to be implemented on all those
        devices operating as Central controllers, that
        terminate the Light Weight Access Point Protocol
        tunnel from Cisco Light-weight LWAPP Access Points.

        Information provided by this MIB is used to study
        the quality of service in the voice and video traffic
        on the WLAN.

        The relationship between CC and the LWAPP APs
        can be depicted as follows:

              +......+     +......+     +......+
              +      +     +      +     +      +
              +  CC  +     +  CC  +     +  CC  +
              +      +     +      +     +      +
              +......+     +......+     +......+
                ..            .             .
                ..            .             .
               .  .            .             .
              .    .            .             .
             .      .            .             .
            .        .            .             .
        +......+ +......+     +......+      +......+
        +      + +      +     +      +      +      +
        +  AP  + +  AP  +     +  AP  +      +  AP  +
        +      + +      +     +      +      +      +
        +......+ +......+     +......+      +......+
                   .              .             .
                 .  .              .             .
                .    .              .             .
               .      .              .             .
              .        .              .             .
           +......+ +......+     +......+      +......+
           +      + +      +     +      +      +      +
           +  MN  + +  MN  +     +  MN  +      +  MN  +
           +      + +      +     +      +      +      +
           +......+ +......+     +......+      +......+


        The LWAPP tunnel exists between the controller and
        the APs.  The MNs communicate with the APs through
        the protocol defined by the 802.11 standard.

        LWAPP APs, upon bootup, discover and join one of the
        controllers and the controller pushes the configuration,
        that includes the WLAN parameters, to the LWAPP APs.
        The APs then encapsulate all the 802.11 frames from
        wireless clients inside LWAPP frames and forward
        the LWAPP frames to the controller.

                           GLOSSARY

        Access Point ( AP )

        An entity that contains an 802.11 medium access
        control ( MAC ) and physical layer ( PHY ) interface
        and provides access to the distribution services via
        the wireless medium for associated clients.  

        LWAPP APs encapsulate all the 802.11 frames in
        LWAPP frames and sends them to the controller to which
        it is logically connected.

        Gratuitous Probe Response (GPR)

        The Gratuitous Probe Response feature aids in conserving
        battery power of WLAN-enabled cell phones by providing
        a high rate packet on the order of tens of milliseconds
        such that these kind of phones can wake up and wait at
        predefined intervals, to reduce battery power.  The 
        GPR packet is transmitted from the AP at a predefined
        time interval.


        Light Weight Access Point Protocol ( LWAPP )

        This is a generic protocol that defines the 
        communication between the Access Points and the
        Central Controller. 

        Mobile Node ( MN )

        A roaming 802.11 wireless device in a wireless
        network associated with an access point. Mobile Node 
        and client are used interchangeably. 

        TU

        A measurement of time in units of 1024 microseconds.

        User Priority ( UP )

        Specifies a the priority rules in QOS for handling user 
        priority.

        EDCA (Enhanced distributed channel access)

        As defined in 802.11e standard, Enhanced distributed
        channel access(EDCA) parameter set element is used 
        by the AP to establish policy, to change policy when
        accepting new clients, or to adapt to changes in 
        offered load. 

        RRC (Resource Reservation Control)

        Wireless LAN Controller will periodically send this message to 
        AP in order to collect various radio and client statistics, which
        will be feed in to RRC algorithm. This message will be sent per access
        class (i.e. 802.11 band) at the time of admission and re-RRC calculations. 

        REFERENCE

        [1] Wireless LAN Medium Access Control ( MAC ) and
        Physical Layer ( PHY ) Specifications

        [2] Draft-obara-capwap-lwapp-00.txt, IETF Light 
        Weight Access Point Protocol"
    REVISION        "201803080000Z"
    DESCRIPTION
        "Added cLGlobalAirTimeAllocation."
    REVISION        "201302270000Z"
    DESCRIPTION
        "Added the following groups:
        ciscoLwappQosMediaClientGroup,
        ciscoLwappQosMediaStreamConfigGroup,
        ciscoLwappPreferredCallConfigGroup,
        ciscoLwappQosDot11aConfigGroupSup3,
        ciscoLwappQosDot11bConfigGroupSup3,
        ciscoLwappQosDot11MediaNotifGroup
        Deprecated ciscoLwappQosMIBComplianceRev2 and 
        replaced it with ciscoLwappQosMIBComplianceRev3."
    REVISION        "201007210000Z"
    DESCRIPTION
        "Added the following groups:
        ciscoLwappQosMIBComplianceRev2, 
        ciscoLwappQosDot11aConfigGroupSup2, 
        ciscoLwappQosDot11bConfigGroupSup2, 
        ciscoLwappQosDot11SipCacStatsGroup, 
        ciscoLwappQosDot11SipConfigGroup, 
        ciscoLwappQosDot11VoiceStatsGroup, 
        ciscoLwappQosDot11VoiceConfigGroup, 
        ciscoLwappQosConfigGroup,
        ciscoLwappQosDot11VoiceNotifGroup 

        Deprecated ciscoLwappQosMIBComplianceRev1 and 
        replaced it with ciscoLwappQosMIBComplianceRev2."
    REVISION        "200701070000Z"
    DESCRIPTION
        "Added ciscoLwappQosDot11aConfigGroupSup1 and
        ciscoLwappQosDot11bConfigGroupSup1 objects."
    REVISION        "200604130000Z"
    DESCRIPTION
        "Initial version of this MIB module."
    ::= { ciscoMgmt 524 }


ciscoLwappQosMIBNotifs  OBJECT IDENTIFIER
    ::= { ciscoLwappQosMIB 0 }

ciscoLwappQosMIBObjects  OBJECT IDENTIFIER
    ::= { ciscoLwappQosMIB 1 }

ciscoLwappQosMIBConform  OBJECT IDENTIFIER
    ::= { ciscoLwappQosMIB 2 }

cLQd11aCACConfig  OBJECT IDENTIFIER
    ::= { ciscoLwappQosMIBObjects 1 }

cLQd11bCACConfig  OBJECT IDENTIFIER
    ::= { ciscoLwappQosMIBObjects 2 }

cLQd11GprConfig  OBJECT IDENTIFIER
    ::= { ciscoLwappQosMIBObjects 3 }

cLQd11CACStats  OBJECT IDENTIFIER
    ::= { ciscoLwappQosMIBObjects 4 }

cLQEntConfConfig  OBJECT IDENTIFIER
    ::= { ciscoLwappQosMIBObjects 5 }

cLQd11VoiceStats  OBJECT IDENTIFIER
    ::= { ciscoLwappQosMIBObjects 6 }

cLQVoiceWlanConfig  OBJECT IDENTIFIER
    ::= { ciscoLwappQosMIBObjects 7 }

cLQVoiceClient  OBJECT IDENTIFIER
    ::= { ciscoLwappQosMIBObjects 8 }

cLQMediaClient  OBJECT IDENTIFIER
    ::= { ciscoLwappQosMIBObjects 9 }

cLQd11SipCacConfig  OBJECT IDENTIFIER
    ::= { ciscoLwappQosMIBObjects 10 }

cLQMediaStreamConfig  OBJECT IDENTIFIER
    ::= { ciscoLwappQosMIBObjects 11 }

cLQPreferredCallConfig  OBJECT IDENTIFIER
    ::= { ciscoLwappQosMIBObjects 12 }

cLQConfigObjects  OBJECT IDENTIFIER
    ::= { ciscoLwappQosMIBObjects 13 }

cLQoSProfileConfig  OBJECT IDENTIFIER
    ::= { ciscoLwappQosMIBObjects 14 }

cLQoSSipSnoopingConfig  OBJECT IDENTIFIER
    ::= { ciscoLwappQosMIBObjects 15 }

cLQoSAirTimeFairness  OBJECT IDENTIFIER
    ::= { ciscoLwappQosMIBObjects 16 }

cLQd11axCACConfig  OBJECT IDENTIFIER	
    ::= { ciscoLwappQosMIBObjects 21 }

cLQCacThreshold OBJECT IDENTIFIER
    ::= { ciscoLwappQosMIBObjects 22 }

cLQCacStats OBJECT IDENTIFIER
    ::= { ciscoLwappQosMIBObjects 23 }

CiscoLwappDot11aPhyRates ::= TEXTUAL-CONVENTION
    STATUS          current
    DESCRIPTION
        "This texual convention denotes the physical rates supported by
        a 802.11a radio. The rates are indicated in Mbps."
    SYNTAX          INTEGER  {
                        six(6), -- 6 Mbps
                        nine(9), -- 9 Mbps
                        twelve(12), -- 12 Mbps
                        eighteen(18), -- 18 Mbps
                        twentyFour(24), -- 24 Mbps
                        thirtySix(36), -- 36 Mbps
                        fortyEight(48), -- 48 Mbps
                        fiftyFour(54), -- 54 Mbps
                        sixtyFive(65), -- 65 Mbps
                        seventyTwoPointTwo(72), -- 72 Mbps
                        oneThirty(130), -- 130 Mbps
                        oneThirtyfive(135), -- 135 Mbps
                        oneFortyFourPointFour(144), -- 144 Mbps
                        oneFifty(150), -- 150 Mbps
                        twoSeventy(270), -- 270 Mbps
                        threeHundred(300) -- 300 Mbps                        
                    }

CiscoLwappDot11bPhyRates ::= TEXTUAL-CONVENTION
    STATUS          current
    DESCRIPTION
        "This texual convention denotes the physical rates supported by
        a 802.11b radio. The rates are indicated in Mbps."
    SYNTAX          INTEGER  {
                        one(1), -- 1 Mbps
                        two(2), -- 2 Mbps
                        fivePointFive(5), -- 5.5 Mbps
                        six(6), -- 6 Mbps
                        nine(9), -- 9 Mbps
                        eleven(11), -- 11 Mbps
                        twelve(12), -- 12 Mbps
                        eighteen(18), -- 18 Mbps
                        twentyFour(24), -- 24 Mbps
                        thirtySix(36), -- 36 Mbps
                        fortyEight(48), -- 48 Mbps
                        fiftyFour(54), -- 54 Mbps
                        sixtyFive(65), -- 65 Mbps
                        seventyTwoPointTwo(72), -- 72 Mbps
                        oneThirty(130), -- 130 Mbps
                        oneThirtyFive(135), -- 135 Mbps
                        oneFortyFourPointFour(144), -- 144.4 Mbps
                        oneFifty(150), -- 150 Mbps
                        twoSeventy(270), -- 270 Mbps
                        threeHundred(300) -- 300  Mbps                        
                    }

-- ********************************************************************
-- *    Configuration for Call Admission Control parameters
-- *    for VOICE traffic in 802.11ax interfaces in the controller
-- ********************************************************************

cLQd11axVoiceAdmCtrlSupport OBJECT-TYPE
    SYNTAX          TruthValue
    MAX-ACCESS      read-write
    STATUS          current
    DESCRIPTION
        "This object is used to enable or disable admission
        control for voice traffic flowing through the 802.11ax 
        interfaces in the controller.

        When set to 'true', controller will reserve and manage 
        max-bandwidth (cLQd11axVoiceMaxAdmBandwidth) 
        and roaming-bandwidth
        (cLQd11axVoiceMaxRoamBandwidth) as per user 
        configured values.

        When disabled, admission control will not be enforced. 
        This may delay voice traffic depending on load on
        the WLAN."
    DEFVAL          { true } 
    ::= { cLQd11axCACConfig 1 }

cLQd11axVoiceMaxAdmBandwidth OBJECT-TYPE
    SYNTAX          Unsigned32 (0..100)
    UNITS           "Percent"
    MAX-ACCESS      read-write
    STATUS          current
    DESCRIPTION
        "This object denotes the maximum bandwidth
        that can be allocated by controller for voice
        traffic when admission control is enabled for
        for 802.11ax interfaces in the controller.

        Please note that the write operation on this
        object will be successful only if the 802.11ax
        network is not operational and the total
        value populated for this object for all the
        admission control attributes (voice, video)
        together does not exceed 100%." 
    ::= { cLQd11axCACConfig 2 }

cLQd11axVoiceMaxRoamBandwidth OBJECT-TYPE
    SYNTAX          Unsigned32 (0..100)
    UNITS           "Percent"
    MAX-ACCESS      read-write
    STATUS          current
    DESCRIPTION
        "This object represents the bandwidth relative
        to the maximum allocated bandwidth indicated by
        cLQd11axVoiceMaxAdmBandwidth, that can be 
        allocated to roaming clients for voice traffic,
        when admission control is enabled for 802.11ax
        interfaces in the controller.

        Please note that the write operation on this
        object will be successful only if the 802.11ax
        network is disabled and not operational.  The
        value configured through this object takes
        effect when the 802.11ax network is enabled."
    DEFVAL          { 0 } 
    ::= { cLQd11axCACConfig 3 }

-- ********************************************************************
-- *    Configuration for Call Admission Control parameters
-- *    for VIDEO traffic in 802.11ax interfaces in the controller
-- ********************************************************************

cLQd11axVideoAdmCtrlSupport OBJECT-TYPE
    SYNTAX          TruthValue
    MAX-ACCESS      read-write
    STATUS          current
    DESCRIPTION
        "This object is used to enable or disable admission
        control for video traffic flowing through the 802.11ax 
        interfaces in the controller.

        When set to 'true', controller will reserve and manage 
        max-bandwidth (cLQd11axVideoMaxAdmBandwidth) 
        and roaming-bandwidth
        (cLQd11axVideoMaxRoamBandwidth) as per user  
        configured values.

        When disabled, admission control will not be enforced. 
        This may delay video traffic depending on load on
        the WLAN."
    DEFVAL          { true } 
    ::= { cLQd11axCACConfig 4 }

cLQd11axVideoMaxAdmBandwidth OBJECT-TYPE
    SYNTAX          Unsigned32 (0..100)
    UNITS           "Percent"
    MAX-ACCESS      read-write
    STATUS          current
    DESCRIPTION
        "This object denotes the maximum bandwidth
        that can be allocated by controller for video traffic
        when admission control is enabled for 802.11ax 
        interfaces in the controller.  When set to 0, all
        available bandwidth in 802.11ax interfaces can be
        allocated to video traffic.

        Please note that the write operation on this
        object will be successful only if the 802.11ax
        network is not operational and the total
        value populated for this object for all the
        admission control attributes (voice, video)
        together does not exceed 100%."
    DEFVAL          { 0 } 
    ::= { cLQd11axCACConfig 5 }

cLQd11axVideoMaxRoamBandwidth OBJECT-TYPE
    SYNTAX          Unsigned32 (0..100)
    UNITS           "Percent"
    MAX-ACCESS      read-write
    STATUS          current
    DESCRIPTION
        "This object represents the bandwidth relative
        to the maximum allocated bandwidth indicated by
        cLQd11aVideoMaxAdmBandwidth, that can be 
        allocated to roaming clients for video traffic,
        when admission control is enabled for 802.11ax
        interfaces in the controller.

        Please note that the write operation on this
        object will be successful only if the 802.11ax
        network is disabled and not operational.  The
        value configured through this object takes effect 
        when the 802.11ax network is enabled and 
        operational."
    DEFVAL          { 0 } 
    ::= { cLQd11axCACConfig 6 }

cLQd11axEdcaProfile OBJECT-TYPE
    SYNTAX          INTEGER  {
                        wmmDefault(1),
                        svpVoice(2),
                        optimizedVoice(3),
                        optimizedVideoVoice(4),
                        customVoice(5),
                        fastlaneEdca(6),
                        iotLowLatency(7)
                    }
    MAX-ACCESS      read-write
    STATUS          current
    DESCRIPTION
        "This object specifies the EDCA profile to be used
        in EDCA Parameter set element. 
           wmmDefault     - WMM default standard parameters.
           svpVoice       - Spectralink voice priority 
                             parameters.
           optimizedVoice      - parameters for voice optimization.
           optimizedVideoVoice - parameters for video and voice
                                   optimization.
           customVoice     - parameters for voice custom.
           fastlaneEdca    - parameter for fastlane.
           iotLowLatency   - parameters for low latency.
           "
    ::= { cLQd11axCACConfig 7 }

cLQd11axVoiceCtrl OBJECT-TYPE
    SYNTAX          INTEGER  {
                        loadBased(1),
                        static(2)
                    }
    MAX-ACCESS      read-write
    STATUS          current
    DESCRIPTION
        "This object specifies the parameters that
        can be modified, when admission control is enabled.
            loadBased - controller will reserve and manage
                        max-bandwidth and roaming-bandwidth
                        based on the load on the WLAN. 
            static    - controller will reserve and
                        manage max-bandwidth 
                        (cLQd11axVoiceMaxAdmBandwidth)
                        and roaming-bandwidth
                        (cLQd11axVoiceMaxRoamBandwidth) 
                        as per user configured values.
         When ACM is disabled, admission control will not 
         be enforced. This may delay voice traffic depending 
         on the traffic on the WLAN."
    DEFVAL          { loadBased } 
    ::= { cLQd11axCACConfig 8 }

cLQd11axExpeditedBw OBJECT-TYPE
    SYNTAX          TruthValue
    MAX-ACCESS      read-write
    STATUS          current
    DESCRIPTION
        "This object specifies if expedited BW feature is
        enabled or not.
        A value of 'true' will ensure that the APs advertise
        the expedited BW support in their beacons and 
        association responses.
        A value of 'false' will ensure that the APs do not
        advertise the expedited BW support in their beacons 
        and association responses." 
    ::= { cLQd11axCACConfig 9 }

-- ********************************************************************
-- *    Configuration of SIP CAC support on dot11ax radio band.
-- ********************************************************************

cLQd11axSipCacSupportEnable OBJECT-TYPE
    SYNTAX          TruthValue
    MAX-ACCESS      read-write
    STATUS          current
    DESCRIPTION
        "This object specifies whether SIP CAC is enabled.

        A value of 'true' enables SIP CAC on dot11a radio band. 
        A value of 'false' disables SIP CAC on dot11a radio band." 
    ::= { cLQd11axCACConfig 10 }

-- ********************************************************************
-- *    Configuration for Call Admission Control parameters
-- *    for mc2uc in 802.11ax interfaces in the controller
-- ********************************************************************

cLQd11axMcastDirectEnable OBJECT-TYPE
    SYNTAX          TruthValue
    MAX-ACCESS      read-write
    STATUS          current
    DESCRIPTION
        "This object specifies the decision flag to allow multicast direct
        stream on radio." 
    ::= { cLQd11axCACConfig 11 }

cLQd11axBestEffortAdmission OBJECT-TYPE
    SYNTAX          TruthValue
    MAX-ACCESS      read-write
    STATUS          current
    DESCRIPTION
        "This object specifies whether to admit a media stream in best
        effort queue." 
    ::= { cLQd11axCACConfig 12 }

cLQd11axRedirectBestEffort OBJECT-TYPE
    SYNTAX          TruthValue
    MAX-ACCESS      read-write
    STATUS          current
    DESCRIPTION
        "This object specifies whether a unicast or multicast only video
        stream can be redirected to best effort." 
    ::= { cLQd11axCACConfig 13 }

cLQd11axRadioMaxStreams OBJECT-TYPE
    SYNTAX          Unsigned32
    MAX-ACCESS      read-write
    STATUS          current
    DESCRIPTION
        "This object specifies the maximum number of allowed streams per
        radio for a 802.11ax band." 
    ::= { cLQd11axCACConfig 14 }

cLQd11axMaxMediaATPercent OBJECT-TYPE
    SYNTAX          INTEGER (0..100)
    UNITS           "Percent"
    MAX-ACCESS      read-write
    STATUS          current
    DESCRIPTION
        "This object specifies the maximum allowed bandwidth for media
        traffic." 
    ::= { cLQd11axCACConfig 15 }

cLQd11axMinPhyRate OBJECT-TYPE
    SYNTAX          CiscoLwappDot11aPhyRates
    MAX-ACCESS      read-write
    STATUS          current
    DESCRIPTION
        "This object specifies the minimum physical rate that should be
        enabled by a client to successfully join a media stream." 
    ::= { cLQd11axCACConfig 16 }

cLQd11axClientMaxStreams OBJECT-TYPE
    SYNTAX          Unsigned32 (0..20)
    MAX-ACCESS      read-write
    STATUS          current
    DESCRIPTION
        "This object specifies the maximum number of allowed streams per
        client for a 802.11ax band." 
    ::= { cLQd11axCACConfig 17 }

-- ********************************************************************
-- *    Configuration for Call Admission Control parameters
-- *    for VOICE traffic in 802.11a interfaces in the controller
-- ********************************************************************

cLQd11aVoiceAdmCtrlSupport OBJECT-TYPE
    SYNTAX          TruthValue
    MAX-ACCESS      read-write
    STATUS          current
    DESCRIPTION
        "This object is used to enable or disable admission
        control for voice traffic flowing through the 802.11a 
        interfaces in the controller.

        When set to 'true', controller will reserve and manage 
        max-bandwidth (cLQd11aVoiceMaxAdmBandwidth) 
        and roaming-bandwidth
        (cLQd11aVoiceMaxRoamBandwidth) as per user 
        configured values.

        When disabled, admission control will not be enforced. 
        This may delay voice traffic depending on load on
        the WLAN."
    DEFVAL          { true } 
    ::= { cLQd11aCACConfig 1 }

cLQd11aVoiceMaxAdmBandwidth OBJECT-TYPE
    SYNTAX          Unsigned32 (0..100)
    UNITS           "Percent"
    MAX-ACCESS      read-write
    STATUS          current
    DESCRIPTION
        "This object denotes the maximum bandwidth
        that can be allocated by controller for voice
        traffic when admission control is enabled for
        for 802.11a interfaces in the controller.

        Please note that the write operation on this
        object will be successful only if the 802.11a
        network is not operational and the total
        value populated for this object for all the
        admission control attributes (voice, video)
        together does not exceed 100%." 
    ::= { cLQd11aCACConfig 2 }

cLQd11aVoiceMaxRoamBandwidth OBJECT-TYPE
    SYNTAX          Unsigned32 (0..100)
    UNITS           "Percent"
    MAX-ACCESS      read-write
    STATUS          current
    DESCRIPTION
        "This object represents the bandwidth relative
        to the maximum allocated bandwidth indicated by
        cLQd11aVoiceMaxAdmBandwidth, that can be 
        allocated to roaming clients for voice traffic,
        when admission control is enabled for 802.11a
        interfaces in the controller.

        Please note that the write operation on this
        object will be successful only if the 802.11a
        network is disabled and not operational.  The
        value configured through this object takes
        effect when the 802.11a network is enabled."
    DEFVAL          { 0 } 
    ::= { cLQd11aCACConfig 3 }

-- ********************************************************************
-- *    Configuration for Call Admission Control parameters
-- *    for VIDEO traffic in 802.11a interfaces in the controller
-- ********************************************************************

cLQd11aVideoAdmCtrlSupport OBJECT-TYPE
    SYNTAX          TruthValue
    MAX-ACCESS      read-write
    STATUS          current
    DESCRIPTION
        "This object is used to enable or disable admission
        control for video traffic flowing through the 802.11a 
        interfaces in the controller.

        When set to 'true', controller will reserve and manage 
        max-bandwidth (cLQd11aVideoMaxAdmBandwidth) 
        and roaming-bandwidth
        (cLQd11aVideoMaxRoamBandwidth) as per user  
        configured values.

        When disabled, admission control will not be enforced. 
        This may delay video traffic depending on load on
        the WLAN."
    DEFVAL          { true } 
    ::= { cLQd11aCACConfig 4 }

cLQd11aVideoMaxAdmBandwidth OBJECT-TYPE
    SYNTAX          Unsigned32 (0..100)
    UNITS           "Percent"
    MAX-ACCESS      read-write
    STATUS          current
    DESCRIPTION
        "This object denotes the maximum bandwidth
        that can be allocated by controller for video traffic
        when admission control is enabled for 802.11a 
        interfaces in the controller.  When set to 0, all
        available bandwidth in 802.11a interfaces can be
        allocated to video traffic.

        Please note that the write operation on this
        object will be successful only if the 802.11a
        network is not operational and the total
        value populated for this object for all the
        admission control attributes (voice, video)
        together does not exceed 100%."
    DEFVAL          { 0 } 
    ::= { cLQd11aCACConfig 5 }

cLQd11aVideoMaxRoamBandwidth OBJECT-TYPE
    SYNTAX          Unsigned32 (0..100)
    UNITS           "Percent"
    MAX-ACCESS      read-write
    STATUS          current
    DESCRIPTION
        "This object represents the bandwidth relative
        to the maximum allocated bandwidth indicated by
        cLQd11aVideoMaxAdmBandwidth, that can be 
        allocated to roaming clients for video traffic,
        when admission control is enabled for 802.11a
        interfaces in the controller.

        Please note that the write operation on this
        object will be successful only if the 802.11a
        network is disabled and not operational.  The
        value configured through this object takes effect 
        when the 802.11a network is enabled and 
        operational."
    DEFVAL          { 0 } 
    ::= { cLQd11aCACConfig 6 }

-- ********************************************************************
-- *    Configuration of GPR (Gratuitous Probe Response) probe interval
-- *    for all 802.11a interfaces in the controller
-- ********************************************************************

cLQd11aGprProbeInterval OBJECT-TYPE
    SYNTAX          Unsigned32 (10..100)
    UNITS           "TU"
    MAX-ACCESS      read-write
    STATUS          current
    DESCRIPTION
        "This object specifies the  GPR probe interval
        period to be used by all 802.11a interfaces in the 
        controller. The radios are advertising any 
        WLAN with GPR support enabled.

        Please note that the write operation on this
        object will be successful only if the 802.11a
        network is not operational.  The value configured
        through this object takes effect when the 802.11a
        network is enabled and operational."
    DEFVAL          { 10 } 
    ::= { cLQd11aCACConfig 7 }

cLQd11aVoiceCtrl OBJECT-TYPE
    SYNTAX          INTEGER  {
                        loadBased(1),
                        static(2)
                    }
    MAX-ACCESS      read-write
    STATUS          current
    DESCRIPTION
        "This object specifies the parameters that
        can be modified, when admission control is enabled.
            loadBased - controller will reserve and manage
                        max-bandwidth and roaming-bandwidth
                        based on the load on the WLAN. 
            static    - controller will reserve and
                        manage max-bandwidth 
                        (cLQd11aVoiceMaxAdmBandwidth)
                        and roaming-bandwidth
                        (cLQd11aVoiceMaxRoamBandwidth) 
                        as per user configured values.
         When ACM is disabled, admission control will not 
         be enforced. This may delay voice traffic depending 
         on the traffic on the WLAN."
    DEFVAL          { loadBased } 
    ::= { cLQd11aCACConfig 8 }

cLQd11aExpeditedBw OBJECT-TYPE
    SYNTAX          TruthValue
    MAX-ACCESS      read-write
    STATUS          current
    DESCRIPTION
        "This object specifies if expedited BW feature is
        enabled or not.
        A value of 'true' will ensure that the APs advertise
        the expedited BW support in their beacons and 
        association responses.
        A value of 'false' will ensure that the APs do not
        advertise the expedited BW support in their beacons 
        and association responses." 
    ::= { cLQd11aCACConfig 9 }

cLQd11aEdcaProfile OBJECT-TYPE
    SYNTAX          INTEGER  {
                        wmmDefault(1),
                        svpVoice(2),
                        optimizedVoice(3),
                        optimizedVideoVoice(4),
                        customVoice(5),
                        fastlaneEdca(6),
                        iotLowLatency(7)
                    }
    MAX-ACCESS      read-write
    STATUS          current
    DESCRIPTION
        "This object specifies the EDCA profile to be used
        in EDCA Parameter set element. 
           wmmDefault     - WMM default standard parameters.
           svpVoice       - Spectralink voice priority 
                             parameters.
           optimizedVoice      - parameters for voice optimization.
           optimizedVideoVoice - parameters for video and voice
                                   optimization.
           customVoice     - parameters for voice custom.
           fastlaneEdca    - parameter for fastlane.
           iotLowLatency   - parameters for low latency."
    ::= { cLQd11aCACConfig 10 }

cLQd11aMacOptimization OBJECT-TYPE
    SYNTAX          TruthValue
    MAX-ACCESS      read-write
    STATUS          current
    DESCRIPTION
        "This object specifies MAC enhancements for voice,
        resulting in improvement in number of voice calls
        serviced per access point.
        A value of 'true' enables MAC optimization. 
        A value of 'false' disables MAC optimization." 
    ::= { cLQd11aCACConfig 11 }

cLQd11aMaxCallLimit OBJECT-TYPE
    SYNTAX          Unsigned32
    MAX-ACCESS      read-write
    STATUS          deprecated
    DESCRIPTION
        "This object specifies the maximum number of CAC Voice Calls
        allowed on dot11a radio band.
        Value of zero denotes no limit. No replacement object." 
    ::= { cLQd11aCACConfig 12 }

-- ********************************************************************
-- *    Configuration for Call Admission Control parameters
-- *    for mc2uc in 802.11a interfaces in the controller
-- ********************************************************************

cLQd11aMcastDirectEnable OBJECT-TYPE
    SYNTAX          TruthValue
    MAX-ACCESS      read-write
    STATUS          current
    DESCRIPTION
        "This object specifies the decision flag to allow multicast direct
        stream on radio." 
    ::= { cLQd11aCACConfig 13 }

cLQd11aBestEffortAdmission OBJECT-TYPE
    SYNTAX          TruthValue
    MAX-ACCESS      read-write
    STATUS          current
    DESCRIPTION
        "This object specifies whether to admit a media stream in best
        effort queue." 
    ::= { cLQd11aCACConfig 14 }

cLQd11aRedirectBestEffort OBJECT-TYPE
    SYNTAX          TruthValue
    MAX-ACCESS      read-write
    STATUS          current
    DESCRIPTION
        "This object specifies whether a unicast or multicast only video
        stream can be redirected to best effort." 
    ::= { cLQd11aCACConfig 15 }

cLQd11aRadioMaxStreams OBJECT-TYPE
    SYNTAX          Unsigned32
    MAX-ACCESS      read-write
    STATUS          current
    DESCRIPTION
        "This object specifies the maximum number of allowed streams per
        radio for a 802.11a band." 
    ::= { cLQd11aCACConfig 16 }

cLQd11aMaxVideoATPercent OBJECT-TYPE
    SYNTAX          INTEGER (0..85)
    UNITS           "Percent"
    MAX-ACCESS      read-write
    STATUS          current
    DESCRIPTION
        "This object specifies the maximum allowed bandwidth for video
        traffic." 
    ::= { cLQd11aCACConfig 17 }

cLQd11aMaxVoiceATPercent OBJECT-TYPE
    SYNTAX          INTEGER (0..85)
    UNITS           "Percent"
    MAX-ACCESS      read-write
    STATUS          current
    DESCRIPTION
        "This object specifies the maximum allowed bandwidth for voice
        traffic." 
    ::= { cLQd11aCACConfig 18 }

cLQd11aMaxMediaATPercent OBJECT-TYPE
    SYNTAX          INTEGER (0..100)
    UNITS           "Percent"
    MAX-ACCESS      read-write
    STATUS          current
    DESCRIPTION
        "This object specifies the maximum allowed bandwidth for media
        traffic." 
    ::= { cLQd11aCACConfig 19 }

cLQd11aMinPhyRate OBJECT-TYPE
    SYNTAX          CiscoLwappDot11aPhyRates
    MAX-ACCESS      read-write
    STATUS          current
    DESCRIPTION
        "This object specifies the minimum physical rate that should be
        enabled by a client to successfully join a media stream." 
    ::= { cLQd11aCACConfig 20 }

cLQd11aClientMaxStreams OBJECT-TYPE
    SYNTAX          Unsigned32 (0..20)
    MAX-ACCESS      read-write
    STATUS          current
    DESCRIPTION
        "This object specifies the maximum number of allowed streams per
        client for a 802.11a band." 
    ::= { cLQd11aCACConfig 21 }

-- ********************************************************************
-- *    Configuration of SIP CAC support on dot11a radio band.
-- ********************************************************************

cLQd11aSipCacSupportEnable OBJECT-TYPE
    SYNTAX          TruthValue
    MAX-ACCESS      read-write
    STATUS          current
    DESCRIPTION
        "This object specifies whether SIP CAC is enabled.

        A value of 'true' enables SIP CAC on dot11a radio band. 
        A value of 'true' disables SIP CAC on dot11a radio band." 
    ::= { cLQd11aCACConfig 22 }

-- ********************************************************************
-- *    Configuration for  Call Admission Control parameters
-- *    for VOICE traffic in 802.11b/g interfaces in the controller
-- ********************************************************************

cLQd11bVoiceAdmCtrlSupport OBJECT-TYPE
    SYNTAX          TruthValue
    MAX-ACCESS      read-write
    STATUS          current
    DESCRIPTION
        "This object is used to enable or disable admission
        control for voice traffic flowing through the 
        802.11b/g interfaces in the controller.

        When set to 'true', controller will reserve and manage
        max-bandwidth (cLQd11bVoiceMaxAdmBandwidth)
        and roaming-bandwidth
        (cLQd11bVoiceMaxRoamingBandwidth) as per user
        configured values.

        When disabled, admission control will not be enforced. 
        This may delay voice traffic depending on load on the 
        WLAN."
    DEFVAL          { true } 
    ::= { cLQd11bCACConfig 1 }

cLQd11bVoiceMaxAdmBandwidth OBJECT-TYPE
    SYNTAX          Unsigned32 (0..100)
    UNITS           "Percent"
    MAX-ACCESS      read-write
    STATUS          current
    DESCRIPTION
        "This object denotes the maximum bandwidth that
        can be allocated by controller for voice traffic 
        when admission control is enabled for 802.11b/g
        interfaces in the controller.

        Please note that the write operation on this
        object will be successful only if the 802.11b/g
        network is not operational and the total
        value populated for this object for all the
        admission control attributes (voice, video)
        together does not exceed 100%." 
    ::= { cLQd11bCACConfig 2 }

cLQd11bVoiceMaxRoamBandwidth OBJECT-TYPE
    SYNTAX          Unsigned32 (0..100)
    UNITS           "Percent"
    MAX-ACCESS      read-write
    STATUS          current
    DESCRIPTION
        "This object represents the bandwidth relative
        to the maximum allocated bandwidth indicated by
        cLQd11bVoiceMaxAdmBandwidth, that can be 
        allocated to roaming clients for voice traffic,
        when admission control is enabled for 802.11b
        interfaces in the controller.

        Please note that the write operation on this
        object will be successful only if the 802.11b/g
        network is not operational.  The value configured
        through this object takes effect when the 802.11b/g
        network is enabled and operational."
    DEFVAL          { 0 } 
    ::= { cLQd11bCACConfig 3 }

-- ********************************************************************
-- *    Configuration for Call Admission Control parameters
-- *    for VIDEO traffic in 802.11b/g interfaces in the controller
-- ********************************************************************

cLQd11bVideoAdmCtrlSupport OBJECT-TYPE
    SYNTAX          TruthValue
    MAX-ACCESS      read-write
    STATUS          current
    DESCRIPTION
        "This object is used to enable or disable admission
        control for video traffic flowing through the 
        802.11b/g interfaces in the controller.

        When set to 'true', controller will reserve and manage
        max-bandwidth (cLQd11bVideoMaxAdmBandwidth) 
        and roaming-bandwidth
        (cLQd11bVideoMaxRoamBandwidth) as per user 
        configured values.

        When disabled, admission control will not be enforced. 
        This may delay video traffic depending on load on the 
        WLAN."
    DEFVAL          { true } 
    ::= { cLQd11bCACConfig 4 }

cLQd11bVideoMaxAdmBandwidth OBJECT-TYPE
    SYNTAX          Unsigned32 (0..100)
    UNITS           "Percent"
    MAX-ACCESS      read-write
    STATUS          current
    DESCRIPTION
        "This object denotes the maximum bandwidth that
        can be allocated by controller for video traffic when
        admission control is enabled for 802.11b/g interfaces 
        in the controller.  When set to 0, all available
        bandwidth in 802.11b/g interfaces can be allocated
        to video traffic.

        Please note that the write operation on this
        object will be successful only if the 802.11b/g
        network is not operational and the total
        value populated for this object for all the
        admission control attributes (voice, video)
        together does not exceed 100%."
    DEFVAL          { 0 } 
    ::= { cLQd11bCACConfig 5 }

cLQd11bVideoMaxRoamBandwidth OBJECT-TYPE
    SYNTAX          Unsigned32 (0..100)
    UNITS           "Percent"
    MAX-ACCESS      read-write
    STATUS          current
    DESCRIPTION
        "This objects represents the bandwidth relative
        to the maximum allocated bandwidth indicated by
        cLQd11bVideoMaxAdmBandwidth, that can be 
        allocated to roaming clients for video traffic,
        when admission control is enabled for 802.11b
        interfaces in the controller.

        Please note that the write operation on this
        object will be successful only if the 802.11b/g
        network is not operational.  The value configured
        through this object takes effect when the 802.11b/g
        network is enabled and operational."
    DEFVAL          { 0 } 
    ::= { cLQd11bCACConfig 6 }

-- ********************************************************************
-- *    Configuration of GPR (Gratuitous Probe Response) probe interval
-- *    for all 802.11b/g interfaces in the controller
-- ********************************************************************

cLQd11bGprProbeInterval OBJECT-TYPE
    SYNTAX          Unsigned32 (10..100)
    UNITS           "TU"
    MAX-ACCESS      read-write
    STATUS          current
    DESCRIPTION
        "This object is used to set GPR probe interval
        period to be used by all 802.11b/g interfaces in the
        controller, when the radios are advertising any
        WLAN with GPR support enabled.

        Please note that the write operation on this
        object will be successful only if the 802.11b/g
        network is not operational.  The value configured
        through this object takes effect when the 802.11b/g
        network is enabled."
    DEFVAL          { 10 } 
    ::= { cLQd11bCACConfig 7 }

cLQd11bVoiceCtrl OBJECT-TYPE
    SYNTAX          INTEGER  {
                        loadBased(1),
                        static(2)
                    }
    MAX-ACCESS      read-write
    STATUS          current
    DESCRIPTION
        "When admission control is enabled these parameters
        can be modified.
            loadBased - controller will reserve and manage
                        max-bandwidth and roaming-bandwidth
                        based on the load on the WLAN.
            static    - controller will reserve and
                        manage max-bandwidth
                        (cLQd11bVoiceMaxAdmBandwidth)
                        and roaming-bandwidth
                        (cLQd11bVoiceMaxRoamBandwidth)
                        as per user configured values.
         When ACM is disabled, admission control will not
         be enforced. This may delay voice traffic depending
         on the traffic on the WLAN."
    DEFVAL          { loadBased } 
    ::= { cLQd11bCACConfig 8 }

cLQd11bExpeditedBw OBJECT-TYPE
    SYNTAX          TruthValue
    MAX-ACCESS      read-write
    STATUS          current
    DESCRIPTION
        "This object specifies if expedited BW feature is
        enabled or not.
        A value of 'true' will ensure that the APs advertise
        the expedited BW support in their beacons and
        association responses.
        A value of 'false' will ensure that the APs do not
        advertise the expedited BW support in their beacons
        and association responses."
    ::= { cLQd11bCACConfig 9 }

cLQd11bEdcaProfile OBJECT-TYPE
    SYNTAX          INTEGER  {
                        wmmDefault(1),
                        svpVoice(2),
                        optimizedVoice(3),
                        optimizedVideoVoice(4),
                        customVoice(5),
                        fastlaneEdca(6),
                        iotLowLatency(7)

                    }
    MAX-ACCESS      read-write
    STATUS          current
    DESCRIPTION
        "This object represents the EDCA profile to be used
        in EDCA Parameter set element. See glossary for EDCA.
           wmmDefault     - WMM default standard parameters.
           svpVoice       - Spectralink voice priority
                             parameters.
           optimizedVoice - paramters for voice optimization.
           optimizedVideoVoice - parameters for video and voice
                                   optimization.
           customVoice    - parameters for voice custom.
           fastlaneEdca   - parameter for fastlane.
           iotLowLatency  - parameters for low latency."
    ::= { cLQd11bCACConfig 10 }

cLQd11bMacOptimization OBJECT-TYPE
    SYNTAX          TruthValue
    MAX-ACCESS      read-write
    STATUS          current
    DESCRIPTION
        "This object represents MAC enhancements for voice,
        resulting in improvement in number of voice calls
        serviced per access point.
        A value of 'true' enables MAC optimization.
        A value of 'false' disabled MAC optimization."
 
    ::= { cLQd11bCACConfig 11 }

cLQd11bMaxCallLimit OBJECT-TYPE
    SYNTAX          Unsigned32
    MAX-ACCESS      read-write
    STATUS          deprecated
    DESCRIPTION
        "This object represents the max number of CAC Voice Calls
        allowed on dot11b radio band.
        Value of zero denotes no limit.
        This mib is deprecated  since this configuration is
        no longer supported by the controller." 
    ::= { cLQd11bCACConfig 12 }

-- ********************************************************************
-- *    Configuration for Call Admission Control parameters
-- *    for mc2uc in 802.11b interfaces in the controller
-- ********************************************************************

cLQd11bMcastDirectEnable OBJECT-TYPE
    SYNTAX          TruthValue
    MAX-ACCESS      read-write
    STATUS          current
    DESCRIPTION
        "This object specifies the decision flag to allow multicast
        direct stream on radio. This overrides Resource Reservation
        Control status." 
    ::= { cLQd11bCACConfig 13 }

cLQd11bBestEffortAdmission OBJECT-TYPE
    SYNTAX          TruthValue
    MAX-ACCESS      read-write
    STATUS          current
    DESCRIPTION
        "This object specifies whether to admit a media stream in best
        effort queue." 
    ::= { cLQd11bCACConfig 14 }

cLQd11bRedirectBestEffort OBJECT-TYPE
    SYNTAX          TruthValue
    MAX-ACCESS      read-write
    STATUS          current
    DESCRIPTION
        "This object specifies whether a unicast or multicast only video
        stream can be redirected to best effort." 
    ::= { cLQd11bCACConfig 15 }

cLQd11bRadioMaxStreams OBJECT-TYPE
    SYNTAX          Unsigned32 (0..20)
    MAX-ACCESS      read-write
    STATUS          current
    DESCRIPTION
        "This object specifies the maximum number of allowed streams per
        radio for a 802.11b band." 
    ::= { cLQd11bCACConfig 16 }

cLQd11bMaxVideoATPercent OBJECT-TYPE
    SYNTAX          INTEGER (0..85)
    UNITS           "Percent"
    MAX-ACCESS      read-write
    STATUS          current
    DESCRIPTION
        "This object denotes the maximum allowed bandwidth for video
        traffic." 
    ::= { cLQd11bCACConfig 17 }

cLQd11bMaxVoiceATPercent OBJECT-TYPE
    SYNTAX          INTEGER (0..85)
    UNITS           "Percent"
    MAX-ACCESS      read-write
    STATUS          current
    DESCRIPTION
        "This object denotes the maximum allowed bandwidth for voice
        traffic." 
    ::= { cLQd11bCACConfig 18 }

cLQd11bMaxMediaATPercent OBJECT-TYPE
    SYNTAX          INTEGER (0..100)
    UNITS           "Percent"
    MAX-ACCESS      read-write
    STATUS          current
    DESCRIPTION
        "This object specifies the maximum allowed bandwidth for media
        traffic." 
    ::= { cLQd11bCACConfig 19 }

cLQd11bMinPhyRate OBJECT-TYPE
    SYNTAX          CiscoLwappDot11bPhyRates
    MAX-ACCESS      read-write
    STATUS          current
    DESCRIPTION
        "This object specifies the minimum physical rate
        that should be enabled by a client to successfully join a media
        stream." 
    ::= { cLQd11bCACConfig 20 }

cLQd11bClientMaxStreams OBJECT-TYPE
    SYNTAX          Unsigned32 (0..20)
    MAX-ACCESS      read-write
    STATUS          current
    DESCRIPTION
        "This object specifies the maximum number of allowed streams per
        client for a 802.11b band."
    DEFVAL          { 0 } 
    ::= { cLQd11bCACConfig 21 }

-- ********************************************************************
-- *    Configuration of SIP CAC support on dot11b radio band.
-- ********************************************************************

cLQd11bSipCacSupportEnable OBJECT-TYPE
    SYNTAX          TruthValue
    MAX-ACCESS      read-write
    STATUS          current
    DESCRIPTION
        "This object specifies whether SIP CAC is enabled.

        A value of 'true' enables SIP CAC on dot11b radio band. 
        A value of 'false' disables SIP CAC on dot11b radio band"
    DEFVAL          { false } 
    ::= { cLQd11bCACConfig 22 }
-- ********************************************************************
-- Table to represent (Gratuitous Probe Response) GPR
-- parameters per each WLAN.
-- ********************************************************************

cLQd11GprTable OBJECT-TYPE
    SYNTAX          SEQUENCE OF CLQd11GprEntry 
    MAX-ACCESS      not-accessible
    STATUS          current
    DESCRIPTION
        "This table populates the GPR configuration on the
        WLANs configured on this controller.  

        There exists a row in this table for each WLAN
        configured through cLWlanConfigTable.  A row is added
        is to this table by the agent when a WLAN is created
        by the user through an explicit management action
        initiated from a network management station.
        Similarly a row gets deleted automatically when the
        user deletes the particular WLAN."
    ::= { cLQd11GprConfig 1 }

cLQd11GprEntry OBJECT-TYPE
    SYNTAX          CLQd11GprEntry
    MAX-ACCESS      not-accessible
    STATUS          current
    DESCRIPTION
        "Each entry represents a conceptual row in
        cLQd11GprTable and corresponds to the
        GPR configuration on a WLAN."
    AUGMENTS           { cLWlanConfigEntry  } 
    ::= { cLQd11GprTable 1 }

CLQd11GprEntry ::= SEQUENCE {
        cLQd11GprSupport TruthValue
}

cLQd11GprSupport OBJECT-TYPE
    SYNTAX          TruthValue
    MAX-ACCESS      read-write
    STATUS          current
    DESCRIPTION
        "If 'true', then the corresponding radios that
        advertise this WLAN, will send Gratuitous Probe 
        Response.  If 'false', then the corresponding radios 
        that advertise this WLAN, will not send Gratuitous 
        Probe Response."
    DEFVAL          { false } 
    ::= { cLQd11GprEntry 1 }
 

-- ********************************************************************
-- *  CALL admission control statistics
-- ********************************************************************

cLQd11CACStatsTable OBJECT-TYPE
    SYNTAX          SEQUENCE OF CLQd11CACStatsEntry 
    MAX-ACCESS      not-accessible
    STATUS          current
    DESCRIPTION
        "This table populates the call admission control
        metrics collected by observing the voice or video
        traffic on the dot11 interface of a particular
        AP. 

        There exists a row in this table for each row
        corresponding to a dot11 interface found in
        cLApDot11IfTable.  A row corresponding to a
        dot11 interface is added when an AP joins the
        controller.  The row gets deleted when the AP
        dissociates from the controller."
    ::= { cLQd11CACStats 1 }

cLQd11CACStatsEntry OBJECT-TYPE
    SYNTAX          CLQd11CACStatsEntry
    MAX-ACCESS      not-accessible
    STATUS          current
    DESCRIPTION
        "Each entry represents a conceptual row in
        CLQd11CACStatsTable and corresponds to the 
        admission control statistics for a particular
        dot11 interface."
    AUGMENTS           { cLApDot11IfEntry  } 
    ::= { cLQd11CACStatsTable 1 }

CLQd11CACStatsEntry ::= SEQUENCE {
        cLQd11CacVoiceBwInUse                    Gauge32,
        cLQd11CacVideoBwInUse                    Gauge32,
        cLQd11CacVoiceCallsInProgress            Gauge32,
        cLQd11CacRoamVoiceCallsInProg            Gauge32,
        cLQd11CacTotalVoiceCallsAP               Counter32,
        cLQd11CacTotalRoamCallsAP                Counter32,
        cLQd11CacVoiceCallsRejectedAP            Counter32,
        cLQd11CacRoamCallsRejectedAP             Counter32,
        cLQd11CacRejCallsInsufBw                 Counter32,
        cLQd11CacRejCallsBadParams               Counter32,
        cLQd11CacRejCallsPhyRate                 Counter32,
        cLQd11CacRejCallsQosPolicy               Counter32,
        cLQd11SipCacNonRoamCallsInProgress       Gauge32,
        cLQd11SipCacRoamCallsInProg              Gauge32,
        cLQd11SipCacTotalNonRoamCallsAP          Counter32,
        cLQd11SipCacTotalRoamCallsAP             Counter32,
        cLQd11SipCacNonRoamCallsRejectedInSuffBw Counter32,
        cLQd11SipCacRoamCallsRejectedInSuffBw    Counter32,
        cLQd11SipCacNonRoamCallsRejectedMaxLimit Counter32,
        cLQd11SipCacRoamCallsRejectedMaxLimit    Counter32,
        cLQd11SipCacRejCallsQosPolicy            Counter32,
        cLQd11SipCacPreferredCallsReceived       Counter32,
        cLQd11SipCacPreferredCallsAccepted       Counter32
}

cLQd11CacVoiceBwInUse OBJECT-TYPE
    SYNTAX          Gauge32 (0..100)
    UNITS           "Percent"
    MAX-ACCESS      read-only
    STATUS          current
    DESCRIPTION
        "This object indicates the voice bandwidth in use
        as a percentage of the bandwidth configured through
        cLQd11aVoiceMaxAdmBandwidth or
        cLQd11bVoiceMaxAdmBandwidth, depending on the type
        of this dot11 interface." 
    ::= { cLQd11CACStatsEntry 1 }

cLQd11CacVideoBwInUse OBJECT-TYPE
    SYNTAX          Gauge32 (0..100)
    UNITS           "Percent"
    MAX-ACCESS      read-only
    STATUS          current
    DESCRIPTION
        "This object indicates the video bandwidth in use
        as a percentage of the bandwidth configured through
        cLQd11aVideoMaxAdmBandwidth or
        cLQd11bVideoMaxAdmBandwidth, depending on the type
        of this dot11 interface." 
    ::= { cLQd11CACStatsEntry 2 }

cLQd11CacVoiceCallsInProgress OBJECT-TYPE
    SYNTAX          Gauge32
    MAX-ACCESS      read-only
    STATUS          current
    DESCRIPTION
        "This object indicates the count of the number of
        voice calls currently in progress on this dot11
        interface." 
    ::= { cLQd11CACStatsEntry 3 }

cLQd11CacRoamVoiceCallsInProg OBJECT-TYPE
    SYNTAX          Gauge32
    MAX-ACCESS      read-only
    STATUS          current
    DESCRIPTION
        "This object indicates the count of the number of
        voice calls initiated from roaming clients
        currently in progress on this dot11 interface." 
    ::= { cLQd11CACStatsEntry 4 }

cLQd11CacTotalVoiceCallsAP OBJECT-TYPE
    SYNTAX          Counter32
    MAX-ACCESS      read-only
    STATUS          current
    DESCRIPTION
        "This object indicates the count of the number of
        voice calls observed on this dot11 interface
        ever since this AP has joined the controller." 
    ::= { cLQd11CACStatsEntry 5 }

cLQd11CacTotalRoamCallsAP OBJECT-TYPE
    SYNTAX          Counter32
    MAX-ACCESS      read-only
    STATUS          current
    DESCRIPTION
        "This object indicates the count of the number of
        voice and video calls initiated from roaming clients
        observed on this dot11 interface ever since
        this AP has joined the controller." 
    ::= { cLQd11CACStatsEntry 6 }

cLQd11CacVoiceCallsRejectedAP OBJECT-TYPE
    SYNTAX          Counter32
    MAX-ACCESS      read-only
    STATUS          current
    DESCRIPTION
        "This object indicates the count of the number of
        voice calls observed as rejected on this dot11
        interface, ever since this AP has joined the
        controller." 
    ::= { cLQd11CACStatsEntry 7 }

cLQd11CacRoamCallsRejectedAP OBJECT-TYPE
    SYNTAX          Counter32
    MAX-ACCESS      read-only
    STATUS          current
    DESCRIPTION
        "This object indicates the count of the number of
        voice and video calls initiated from roaming
        clients observed as rejected on this dot11
        interface, ever since this AP has joined the
        controller." 
    ::= { cLQd11CACStatsEntry 8 }

cLQd11CacRejCallsInsufBw OBJECT-TYPE
    SYNTAX          Counter32
    MAX-ACCESS      read-only
    STATUS          current
    DESCRIPTION
        "This object indicates the count of the number of
        calls observed as rejected on this dot11
        interface due to insufficient bandwidth, ever
        since this AP has joined the controller." 
    ::= { cLQd11CACStatsEntry 9 }

cLQd11CacRejCallsBadParams OBJECT-TYPE
    SYNTAX          Counter32
    MAX-ACCESS      read-only
    STATUS          current
    DESCRIPTION
        "This object indicates the count of the number of
        calls observed as rejected on this dot11
        interface due to mismatch in call parameters, ever
        since this AP has joined the controller." 
    ::= { cLQd11CACStatsEntry 10 }

cLQd11CacRejCallsPhyRate OBJECT-TYPE
    SYNTAX          Counter32
    MAX-ACCESS      read-only
    STATUS          current
    DESCRIPTION
        "This object indicates the count of the number of
        calls observed as rejected on this dot11
        interface due to mismatch in 802.11 data rates,
        ever since this AP has joined the controller." 
    ::= { cLQd11CACStatsEntry 11 }

cLQd11CacRejCallsQosPolicy OBJECT-TYPE
    SYNTAX          Counter32
    MAX-ACCESS      read-only
    STATUS          current
    DESCRIPTION
        "This object indicates the count of the number of
        calls observed as rejected on this dot11
        interface due to restrictions imposed by QOS
        policies, ever since this AP has joined the
        controller." 
    ::= { cLQd11CACStatsEntry 12 }

cLQd11SipCacNonRoamCallsInProgress OBJECT-TYPE
    SYNTAX          Gauge32
    MAX-ACCESS      read-only
    STATUS          current
    DESCRIPTION
        "This object indicates the number of non-roaming SIP calls
        currently in progress on this dot11 interface." 
    ::= { cLQd11CACStatsEntry 13 }

cLQd11SipCacRoamCallsInProg OBJECT-TYPE
    SYNTAX          Gauge32
    MAX-ACCESS      read-only
    STATUS          current
    DESCRIPTION
        "This object indicates the number of SIP calls initiated
        from roaming clients currently in progress on this 
        dot11 interface." 
    ::= { cLQd11CACStatsEntry 14 }

cLQd11SipCacTotalNonRoamCallsAP OBJECT-TYPE
    SYNTAX          Counter32
    MAX-ACCESS      read-only
    STATUS          current
    DESCRIPTION
        "This object indicates the number of non-roaming SIP calls
        observed on this dot11 interface since this AP has joined 
        the controller." 
    ::= { cLQd11CACStatsEntry 15 }

cLQd11SipCacTotalRoamCallsAP OBJECT-TYPE
    SYNTAX          Counter32
    MAX-ACCESS      read-only
    STATUS          current
    DESCRIPTION
        "This object indicates the number of SIP calls initiated
        from roaming clients observed on this dot11 interface ever 
        this AP has joined the controller." 
    ::= { cLQd11CACStatsEntry 16 }

cLQd11SipCacNonRoamCallsRejectedInSuffBw OBJECT-TYPE
    SYNTAX          Counter32
    MAX-ACCESS      read-only
    STATUS          current
    DESCRIPTION
        "This object indicates the number of non-roaming SIP calls
        observed as rejected on this dot11 interface due to insufficient
        bandwidth, since this AP has joined the controller." 
    ::= { cLQd11CACStatsEntry 17 }

cLQd11SipCacRoamCallsRejectedInSuffBw OBJECT-TYPE
    SYNTAX          Counter32
    MAX-ACCESS      read-only
    STATUS          current
    DESCRIPTION
        "This object indicates the number of SIP calls initiated
        from roaming clients observed as rejected on this dot11
        interface due to insufficient bandwidth, since this AP has 
        joined the controller." 
    ::= { cLQd11CACStatsEntry 18 }

cLQd11SipCacNonRoamCallsRejectedMaxLimit OBJECT-TYPE
    SYNTAX          Counter32
    MAX-ACCESS      read-only
    STATUS          current
    DESCRIPTION
        "This object indicates the number of non-roaming SIP calls
        observed as rejected on this dot11 interface due to maximum 
        limit exceeded, since this AP has joined the controller." 
    ::= { cLQd11CACStatsEntry 19 }

cLQd11SipCacRoamCallsRejectedMaxLimit OBJECT-TYPE
    SYNTAX          Counter32
    MAX-ACCESS      read-only
    STATUS          current
    DESCRIPTION
        "This object indicates the number of roaming SIP calls observed
        as rejected on this dot11 interface due to maximum limit 
        exceeded, since this AP has joined the controller." 
    ::= { cLQd11CACStatsEntry 20 }

cLQd11SipCacRejCallsQosPolicy OBJECT-TYPE
    SYNTAX          Counter32
    MAX-ACCESS      read-only
    STATUS          current
    DESCRIPTION
        "This object indicates the number of SIP calls observed as
        rejected on this dot11 interface due to restrictions imposed 
        by QOS policies, ever since this AP has joined the controller." 
    ::= { cLQd11CACStatsEntry 21 }

cLQd11SipCacPreferredCallsReceived OBJECT-TYPE
    SYNTAX          Counter32
    MAX-ACCESS      read-only
    STATUS          current
    DESCRIPTION
        "This object indicates the number of
        preferred calls observed as received on this dot11
        interface due to restrictions imposed by QOS
        policies, ever since this AP has joined the
        controller." 
    ::= { cLQd11CACStatsEntry 22 }

cLQd11SipCacPreferredCallsAccepted OBJECT-TYPE
    SYNTAX          Counter32
    MAX-ACCESS      read-only
    STATUS          current
    DESCRIPTION
        "This object indicates the number of
        preferred calls observed as accepted on this dot11
        interface due to restrictions imposed by QOS
        policies, ever since this AP has joined the
        controller." 
    ::= { cLQd11CACStatsEntry 23 }
 

-- ********************************************************************
-- *    Voice stats per radio
-- ********************************************************************

cLQd11VoiceStatsTable OBJECT-TYPE
    SYNTAX          SEQUENCE OF CLQd11VoiceStatsEntry 
    MAX-ACCESS      not-accessible
    STATUS          current
    DESCRIPTION
        "This table represents the voice statistics
        calculated for each radio on an AP.
        An entry is automatically added by the controller
        when a voice call is successfully placed. 
        Entry is deleted when AP disassociates the 
        Controller."
    ::= { cLQd11VoiceStats 1 }

cLQd11VoiceStatsEntry OBJECT-TYPE
    SYNTAX          CLQd11VoiceStatsEntry
    MAX-ACCESS      not-accessible
    STATUS          current
    DESCRIPTION
        "Each entry in this table provides voice related statistics for
        each radio on an AP. 
        Entries are removed when the AP disassociates the controller."
    INDEX           {
                        cLApSysMacAddress,
                        cLApDot11IfSlotId
                    } 
    ::= { cLQd11VoiceStatsTable 1 }

CLQd11VoiceStatsEntry ::= SEQUENCE {
        cLQd11VoiceCallCounts        Counter32,
        cLQd11CacVoiceCallTimePeriod TimeIntervalSec
}

cLQd11VoiceCallCounts OBJECT-TYPE
    SYNTAX          Counter32
    UNITS           "calls"
    MAX-ACCESS      read-only
    STATUS          current
    DESCRIPTION
        "This object indicates cumulative number of successful
        VOIP calls placed using this radio." 
    ::= { cLQd11VoiceStatsEntry 1 }

cLQd11CacVoiceCallTimePeriod OBJECT-TYPE
    SYNTAX          TimeIntervalSec
    UNITS           "seconds"
    MAX-ACCESS      read-only
    STATUS          current
    DESCRIPTION
        "This object indicates cumulative call proceed time
        in seconds." 
    ::= { cLQd11VoiceStatsEntry 2 }
 
-- ********************************************************************
-- *    Client table - voice related objects
-- ********************************************************************

cLQVoiceClientTable OBJECT-TYPE
    SYNTAX          SEQUENCE OF CLQVoiceClientEntry 
    MAX-ACCESS      not-accessible
    STATUS          current
    DESCRIPTION
        "This table contains voice related client properties.

        There exists a row in this table for each associated
        voice clients.  
        A row is added to this table by the 
        agent when a voice client gets associated.
        Similarly, a row gets deleted automatically when the
        voice client gets disassociated."
    ::= { cLQVoiceClient 1 }

cLQVoiceClientEntry OBJECT-TYPE
    SYNTAX          CLQVoiceClientEntry
    MAX-ACCESS      not-accessible
    STATUS          current
    DESCRIPTION
        "An entry containing voice call management information for a
        particular client."
    INDEX           { cldcClientMacAddress } 
    ::= { cLQVoiceClientTable 1 }

CLQVoiceClientEntry ::= SEQUENCE {
        cLQVoiceClientCallingNumber             SnmpAdminString,
        cLQVoiceClientLastCalledNumber          SnmpAdminString,
        cLQVoiceClientLastCallFailureReasonCode INTEGER
}

cLQVoiceClientCallingNumber OBJECT-TYPE
    SYNTAX          SnmpAdminString
    MAX-ACCESS      read-only
    STATUS          current
    DESCRIPTION
        "This object indicates calling number of this
        voice client" 
    ::= { cLQVoiceClientEntry 1 }

cLQVoiceClientLastCalledNumber OBJECT-TYPE
    SYNTAX          SnmpAdminString
    MAX-ACCESS      read-only
    STATUS          current
    DESCRIPTION
        "This object indicates last called number from this
        voice client" 
    ::= { cLQVoiceClientEntry 2 }

cLQVoiceClientLastCallFailureReasonCode OBJECT-TYPE
    SYNTAX          INTEGER  {
                        unknown(1),
                        normalFailure(2),
                        roamFailure(3),
                        maxLimitExceeded(4),
                        sipPrefCallNoBw(5),
                        badRequest(400),
                        unathorized(401),
                        paymentRequired(402),
                        forbidden(403),
                        notFound(404),
                        methodNotallowed(405),
                        notAcceptable(406),
                        proxyAuthenticationRequired(407),
                        requestTimeout(408),
                        conflict(409),
                        gone(410),
                        lengthRequired(411),
                        requestEntityTooLarge(413),
                        requestURITooLarge(414),
                        unsupportedMdediaType(415),
                        badExtension(420),
                        temporarilyNotAvailable(480),
                        callLegDoesNotExist(481),
                        loopDetected(482),
                        tooManyHops(483),
                        addressIncomplete(484),
                        ambiguous(485),
                        busy(486),
                        internalServerError(500),
                        notImplemented(501),
                        badGateway(502),
                        serviceUnavailable(503),
                        serverTimeout(504),
                        versionNotSupported(505),
                        busyEverywhere(600),
                        decline(603),
                        doesNotExistAnywhere(604),
                        sessionNotAcceptable(606)
                    }
    MAX-ACCESS      read-only
    STATUS          current
    DESCRIPTION
        "This object represents last VOIP failue reason code
        of this voice client.
        These reason codes are taken from SIP standards.

        unknown               - Unknown error

        normalFailure         - Call failed for insufficient bandwidth 


        roamFailure           - SIP call failed during roaming

        maxLimitExceeded      - Maximum SIP call permissible limit 
        was exceeded.

        sipPrefCallNoBw       - No bandwidth available for SIP preferred
        calls.

        badRequest            - The request could not be understood 
        due to malformed syntax.

        unathorized           - The request requires user 
        authentication.

        paymentRequired       - Reserved for future.

        forbidden             - The server understood the request, 
        but is refusing to fulfill it.

        notFound              - The server has definitive information
        that the user does not exist at the domain specified in the 
        Request-URI.

        methodNotallowed      - The method specified in the 
        Request-Line is understood, but not allowed for the address 
        identified by the Request-URI.

        notAcceptable         - The resource identified by the request 
        is only capable of generating response entities that have 
        content characteristics not acceptable according to the Accept
        header field sent in the request.

        proxyAuthenticationRequired - This code is similar to 401 
        (Unauthorized), but indicates that the client MUST first 
        authenticate itself with the proxy.  

        requestTimeout        - The server could not produce a 
        response within a suitable amount of time, for example, 
        if it could not determine the location of the user in time.

        conflict              - This is used to indicate that the 
        request could not be completed due to a conflict with the 
        current state of the resource.

        gone                  - The requested resource is no longer 
        available at the server and no forwarding address is known.

        lengthRequired        -  The server is refusing to process a 
        request because the request entity-body is larger than the 
        server is willing or able to process.

        requestEntityTooLarge - The server is refusing to process a 
        request because the request entity-body is larger than the 
        server is willing or able to process.

        requestURITooLarge    - The server is refusing to service the
        request because the Request-URI is longer than the server is 
        willing to interpret.

        unsupportedMediaType - The server is refusing to service the 
        request because the message body of the request is in a format 
        not supported by the server for the requested method.

        badExtension          - The server did not understand the 
        protocol extension specified in a Proxy-Require  or Require 
        header field.

        temporarilyNotAvailable - The callee's end system was contacted

        successfully but the callee is currently unavailable.

        callLegDoesNotExist   - This status indicates that the UAS 
        received a request that does not match any existing dialog 
        or transaction.

        loopDetected          - The server has detected a loop.

        tooManyHops           - The server received a request that 
        contains a Max-Forwards header field with the value zero.

        addressIncomplete     - The server received a request with a 
        Request-URI that was incomplete.

        ambiguous             - The Request-URI was ambiguous.

        busy                  - The callee's end system was contacted 
        successfully, but the callee is currently not willing or able 
        to take additional calls at this end system. 

        internalServerError   - The server encountered an unexpected 
        condition that prevented it from fulfilling the request.

        notImplemented        - The server does not support the 
        functionality required to fulfill the request. 

        badGateway            - The server, while acting as a gateway 
        or proxy, received an invalid response from the downstream 
        server it accessed in attempting to fulfill the request.

        serviceUnavailable    - The server is temporarily unable to 
        process the request due to a temporary overloading or 
        maintenance of the server.

        serverTimeout         - The server did not receive a timely 
        response from an external server it accessed in attempting to 
        process the request.

        versionNotSupported    - The server does not support, or 
        refuses to support, the SIP protocol version that was used 
        in the request. 

        busyEverywhere        - The callee's end system was contacted 
        successfully but the callee is busy and does not wish to take 
        the call at this time. 

        decline               - The callee's machine was successfully 
        contacted but the user explicitly does not wish to or cannot 
        participate.

        doesNotExistAnywhere  - The server has authoritative 
        information that the user indicated in the Request-URI 
        does not exist anywhere.

        sessionNotAcceptable         - The user's agent was contacted 
        successfully but some aspects of the session description 
        such as the requested media, bandwidth, or addressing 
        style were not acceptable." 
    ::= { cLQVoiceClientEntry 3 }
 

-- ********************************************************************
-- *    Client table - Media related objects
-- ********************************************************************

cLQMediaClientTable OBJECT-TYPE
    SYNTAX          SEQUENCE OF CLQMediaClientEntry 
    MAX-ACCESS      not-accessible
    STATUS          current
    DESCRIPTION
        "This table represents media related client
        properties.
        There exists a row in this table for each associated-
        media clients.  A row is added to this table by the
        agent when a client gets associated.
        Similarly a row gets deleted automatically when the
        client gets disassociated."
    ::= { cLQMediaClient 1 }

cLQMediaClientEntry OBJECT-TYPE
    SYNTAX          CLQMediaClientEntry
    MAX-ACCESS      not-accessible
    STATUS          current
    DESCRIPTION
        "Each entry represents a conceptual row in
        cLQMediaClientTable and corresponds to media
        properties of client. There exists a row in this table for each
        client associating to a media stream."
    INDEX           {
                        cLQMStreamName,
                        cLQVMediaClientDestIpAddrType,
                        cLQVMediaClientDestIpAddr,
                        cldcClientMacAddress
                    } 
    ::= { cLQMediaClientTable 1 }

CLQMediaClientEntry ::= SEQUENCE {
        cLQVMediaClientDestIpAddrType InetAddressType,
        cLQVMediaClientDestIpAddr     InetAddress,
        cLQVMediaClientSrcIpAddrType  InetAddressType,
        cLQVMediaClientSrcIpAddr      InetAddress,
        cLQVMediaClientApMacAddress   MacAddress,
        cLQVMediaClientWlanIndex      Unsigned32,
        cLQVMediaClientRadioType      INTEGER,
        cLQVMediaClientQos            INTEGER,
        cLQVMediaClientDecision       INTEGER
}

cLQVMediaClientDestIpAddrType OBJECT-TYPE
    SYNTAX          InetAddressType
    MAX-ACCESS      not-accessible
    STATUS          current
    DESCRIPTION
        "This object indicates the type of address specified by the
        corresponding instance of cLQVMediaClientDestIpAddr." 
    ::= { cLQMediaClientEntry 1 }

cLQVMediaClientDestIpAddr OBJECT-TYPE
    SYNTAX          InetAddress
    MAX-ACCESS      not-accessible
    STATUS          current
    DESCRIPTION
        "This object indicates the destination multicast IP address of
        the associated client." 
    ::= { cLQMediaClientEntry 2 }

cLQVMediaClientSrcIpAddrType OBJECT-TYPE
    SYNTAX          InetAddressType
    MAX-ACCESS      read-only
    STATUS          current
    DESCRIPTION
        "This object indicates the type of address specified by the
        corresponding instance of cLQVMediaClientSrcIpAddr." 
    ::= { cLQMediaClientEntry 3 }

cLQVMediaClientSrcIpAddr OBJECT-TYPE
    SYNTAX          InetAddress
    MAX-ACCESS      read-only
    STATUS          current
    DESCRIPTION
        "This object specifies the source multicast IP address of
        the associated client." 
    ::= { cLQMediaClientEntry 4 }

cLQVMediaClientApMacAddress OBJECT-TYPE
    SYNTAX          MacAddress
    MAX-ACCESS      read-only
    STATUS          current
    DESCRIPTION
        "This object indicates the MAC address of the
        AP, the client gets associated during the streaming." 
    ::= { cLQMediaClientEntry 5 }

cLQVMediaClientWlanIndex OBJECT-TYPE
    SYNTAX          Unsigned32
    MAX-ACCESS      read-only
    STATUS          current
    DESCRIPTION
        "This object indicates the wlan SSID the client uses for
        associating to the AP on the controller. The value 513-517
        indicates wired clients." 
    ::= { cLQMediaClientEntry 6 }

cLQVMediaClientRadioType OBJECT-TYPE
    SYNTAX          INTEGER  {
                        radio80211bg(1),
                        radio80211a(2)
                    }
    MAX-ACCESS      read-only
    STATUS          current
    DESCRIPTION
        "This object indicates the type of radio used by the associated
        client." 
    ::= { cLQMediaClientEntry 7 }

cLQVMediaClientQos OBJECT-TYPE
    SYNTAX          INTEGER  {
                        bestEffort(1),
                        background(2),
                        undefined(3),
                        excellentEffort(4),
                        ctrlLoad(5),
                        video(6),
                        voice(7),
                        network(8)
                    }
    MAX-ACCESS      read-only
    STATUS          current
    DESCRIPTION
        "This object indicates the QOS policy enforced by the associated
        client.

        bestEffort - media stream clients associated to the stream 
        identified by stream name are scheduled to a best effort queue.

        background - media stream clients associated to the stream 
        identified by stream name are scheduled to a background queue.

        undefined - media stream clients associated to the stream 
        identified by stream name are scheduled to a undefined queue.

        excellentEffort - media stream clients associated to the stream 
        identified by stream name are scheduled to a execellent effort queue.

        ctrlLoad - media stream clients associated to the stream 
        identified by stream name are scheduled to a control load queue.

        video - media stream clients associated to the stream 
        identified by stream name are scheduled to video queue.

        voice - media stream clients associated to the stream 
        identified by stream name are scheduled to voice queue.

        network - media stream clients associated to the stream 
        identified by stream name are scheduled to a network queue." 
    ::= { cLQMediaClientEntry 8 }

cLQVMediaClientDecision OBJECT-TYPE
    SYNTAX          INTEGER  {
                        deny(1),
                        admit(2),
                        badClientDeny(3),
                        badClientDemote(4)
                    }
    MAX-ACCESS      read-only
    STATUS          current
    DESCRIPTION
        "This object indicates the decision policy that has been used
        when client gets associated to the media stream.
        deny - denial of client to the media strem.
        admit - Admit of client to the media stream.
        badClientDeny - Denial of the bad client to the media stream
        retained based on client mac.
        badClientDemote - Downgrade client to bad client to deny to the
        media stream." 
    ::= { cLQMediaClientEntry 9 }
 


cLQMediaClientHistoryTable OBJECT-TYPE
    SYNTAX          SEQUENCE OF CLQMediaClientHistoryEntry 
    MAX-ACCESS      not-accessible
    STATUS          current
    DESCRIPTION
        "This table represents media related client
        properties available during a specific time denoted by 
        cLQVMediaClientHistTimeStamp in history."
    ::= { cLQMediaClient 2 }

cLQMediaClientHistoryEntry OBJECT-TYPE
    SYNTAX          CLQMediaClientHistoryEntry
    MAX-ACCESS      not-accessible
    STATUS          current
    DESCRIPTION
        "Each entry represents a conceptual row in
        cLQMediaClientHistoryTable and corresponds to media related
        client properties available during a specific time denoted by 
        cLQVMediaClientHistTimeStamp in history. Client history table
        will be a table that gets updated when client gets
        admitted or denied to the stream."
    INDEX           { cLQVMediaClientHistTimeStamp } 
    ::= { cLQMediaClientHistoryTable 1 }

CLQMediaClientHistoryEntry ::= SEQUENCE {
        cLQVMediaClientHistTimeStamp             TimeStamp,
        cLQVMediaClientHistClientMacAddress      MacAddress,
        cLQVMediaClientHistApMacAddress          MacAddress,
        cLQVMediaClientHistSlotId                Unsigned32,
        cLQVMediaClientHistDestIpAddrType        InetAddressType,
        cLQVMediaClientHistDestIpAddr            InetAddress,
        cLQVMediaClientHistDecision              INTEGER,
        cLQVMediaClientHistLastFailureReasonCode INTEGER,
        cLQVMediaClientHistWlanIndex             Unsigned32,
        cLQVMediaClientHistRadioType             INTEGER,
        cLQVMediaClientHistQos                   INTEGER,
        cLQVMediaClientHistCfgBw                 Unsigned32,
        cLQVMediaClientHistCurrentRate           Unsigned32,
        cLQVMediaClientHistVideoPktSize          Unsigned32,
        cLQVMediaClientHistVideoUtil             Unsigned32,
        cLQVMediaClientHistVoiceUtil             Unsigned32,
        cLQVMediaClientHistChannelUtil           Unsigned32,
        cLQVMediaClientHistQueueUtil             Unsigned32,
        cLQVMediaClientHistVideoPps              Unsigned32,
        cLQVMediaClientHistVideoDelay            Unsigned32,
        cLQVMediaClientHistPktLossDiscard        Unsigned32,
        cLQVMediaClientHistPktLossFail           Unsigned32,
        cLQVMediaClientHistNumVideoStreams       Unsigned32,
        cLQVMediaClientHistCacEnable             INTEGER,
        cLQVMediaClientHistStreamName            SnmpAdminString
}

cLQVMediaClientHistTimeStamp OBJECT-TYPE
    SYNTAX          TimeStamp
    MAX-ACCESS      not-accessible
    STATUS          current
    DESCRIPTION
        "This object uniquely identifies one instance of
        the timestamp in history for which the client
        admit/deny happened." 
    ::= { cLQMediaClientHistoryEntry 1 }

cLQVMediaClientHistClientMacAddress OBJECT-TYPE
    SYNTAX          MacAddress
    MAX-ACCESS      read-only
    STATUS          current
    DESCRIPTION
        "This object indicates the MAC address of the
        client for this entry." 
    ::= { cLQMediaClientHistoryEntry 2 }

cLQVMediaClientHistApMacAddress OBJECT-TYPE
    SYNTAX          MacAddress
    MAX-ACCESS      read-only
    STATUS          current
    DESCRIPTION
        "This object indicates the MAC address of the
        AP, the client gets associated during the streaming." 
    ::= { cLQMediaClientHistoryEntry 3 }

cLQVMediaClientHistSlotId OBJECT-TYPE
    SYNTAX          Unsigned32
    MAX-ACCESS      read-only
    STATUS          current
    DESCRIPTION
        "This object indicates the slot identifier of the AP to which
        the client associates during the streaming." 
    ::= { cLQMediaClientHistoryEntry 4 }

cLQVMediaClientHistDestIpAddrType OBJECT-TYPE
    SYNTAX          InetAddressType
    MAX-ACCESS      read-only
    STATUS          current
    DESCRIPTION
        "This object specifies the destination multicast IP address type of
        the associated client." 
    ::= { cLQMediaClientHistoryEntry 5 }

cLQVMediaClientHistDestIpAddr OBJECT-TYPE
    SYNTAX          InetAddress
    MAX-ACCESS      read-only
    STATUS          current
    DESCRIPTION
        "This object indicates the destination multicast IP address of
        the associated client." 
    ::= { cLQMediaClientHistoryEntry 6 }

cLQVMediaClientHistDecision OBJECT-TYPE
    SYNTAX          INTEGER  {
                        deny(1),
                        admit(2),
                        badClientDeny(3),
                        badClientDemote(4)
                    }
    MAX-ACCESS      read-only
    STATUS          current
    DESCRIPTION
        "This object indicates the decision policy that was used
        when client gets associated to the media stream.
        deny - denial of client to the media strem.
        admit - Admit of client to the media stream.
        badClientDeny - Denial of the client to the media stream
        retained based on client mac.
        badClientDemote - Downgrade client to bad client to deny to the
        media stream" 
    ::= { cLQMediaClientHistoryEntry 7 }

cLQVMediaClientHistLastFailureReasonCode OBJECT-TYPE
    SYNTAX          INTEGER  {
                        enoughBw(1),
                        notEnoughBw(2),
                        bwViolation(3),
                        radioOverSubscribe(4),
                        badClientLink(5),
                        policyNotAllowed(6),
                        otherErrors(7),
                        clientDemote(8),
                        clientTimeout(9),
                        clientLeave(10)
                    }
    MAX-ACCESS      read-only
    STATUS          current
    DESCRIPTION
        "This object indicates last failure reason code
        of this media client.
        enoughBw(1) - Radio can handle additional client traffic.  
        Hence, allowing client admission during RRC admission or Re-RRC
        phase.
        notEnoughBw(2) - Radio cannot handle additional client traffic.

        It will delist(put into best effort queue) or deny client.
        bwViolation(3) - After Re-RRC calculations, it is determined
        that client has done stream config violation. It will be
        delisted or denied.
        radioOverSubscribe(4) -  client will be denied when when radio
        resources are fully utilized.
        badClientLink(5) - If client traffic is sent at lower data rate
        or number of retries exceed threshold, it will be classified as
        bad client.
        policyNotAllowed(6) - Client subscription has violated policy
        configured.
        otherErrors(7) - During RRC admission or Re-RRC phase, client
        joining is denied because of abnormal conditions, such as not
        able to retrieve client data for calculation. 
        clientDemote(8) - During Re-RRC calculation, client is demoted
        to best-effort queue because the radio is too busy.
        clientTimeout(9) - Client is considered for timeout and removed
        from database when no stream update for the client is available
        before the timer (15mins by default) expires. 
        clientLeave(10) - Client leaves the stream in normal condition." 
    ::= { cLQMediaClientHistoryEntry 8 }

cLQVMediaClientHistWlanIndex OBJECT-TYPE
    SYNTAX          Unsigned32 (1..517)
    MAX-ACCESS      read-only
    STATUS          current
    DESCRIPTION
        "This object indicates the wlan SSID used by the
        client to associate to the AP on the controller. The value
        513-517 indicates wired clients." 
    ::= { cLQMediaClientHistoryEntry 9 }

cLQVMediaClientHistRadioType OBJECT-TYPE
    SYNTAX          INTEGER  {
                        radio80211bg(1),
                        radio80211a(2)
                    }
    MAX-ACCESS      read-only
    STATUS          current
    DESCRIPTION
        "This object indicates the type of radio used by the associated
        client." 
    ::= { cLQMediaClientHistoryEntry 10 }

cLQVMediaClientHistQos OBJECT-TYPE
    SYNTAX          INTEGER  {
                        bestEffort(1),
                        background(2),
                        undefined(3),
                        excellentEffort(4),
                        ctrlLoad(5),
                        video(6),
                        voice(7),
                        network(8)
                    }
    MAX-ACCESS      read-only
    STATUS          current
    DESCRIPTION
        "This object indicates the QOS policy enforced by the associated
        client.

        bestEffort - media stream clients associated to the stream 
        identified by stream name are scheduled to a best effort queue.

        background - media stream clients associated to the stream 
        identified by stream name are scheduled to a background queue.

        undefined - media stream clients associated to the stream 
        identified by stream name are scheduled to a undefined queue.

        excellentEffort - media stream clients associated to the stream 
        identified by stream name are scheduled to a execellent effort queue.

        ctrlLoad - media stream clients associated to the stream 
        identified by stream name are scheduled to a control load queue.

        video - media stream clients associated to the stream 
        identified by stream name are scheduled to video queue.

        voice - media stream clients associated to the stream 
        identified by stream name are scheduled to voice queue.

        network - media stream clients associated to the stream 
        identified by stream name are scheduled to a network queue." 
    ::= { cLQMediaClientHistoryEntry 11 }

cLQVMediaClientHistCfgBw OBJECT-TYPE
    SYNTAX          Unsigned32
    MAX-ACCESS      read-only
    STATUS          current
    DESCRIPTION
        "This object indicates the configured stream bandwidth of the
        media client associated to a media stream." 
    ::= { cLQMediaClientHistoryEntry 12 }

cLQVMediaClientHistCurrentRate OBJECT-TYPE
    SYNTAX          Unsigned32
    MAX-ACCESS      read-only
    STATUS          current
    DESCRIPTION
        "This object indicates the rate observed of the media client
        associated to a media stream." 
    ::= { cLQMediaClientHistoryEntry 13 }

cLQVMediaClientHistVideoPktSize OBJECT-TYPE
    SYNTAX          Unsigned32
    MAX-ACCESS      read-only
    STATUS          current
    DESCRIPTION
        "This object indicates the observed video packet size of the
        media client associated to a media stream." 
    ::= { cLQMediaClientHistoryEntry 14 }

cLQVMediaClientHistVideoUtil OBJECT-TYPE
    SYNTAX          Unsigned32
    MAX-ACCESS      read-only
    STATUS          current
    DESCRIPTION
        "This object indicates the observed video utilization of the
        media client associated to a media stream." 
    ::= { cLQMediaClientHistoryEntry 15 }

cLQVMediaClientHistVoiceUtil OBJECT-TYPE
    SYNTAX          Unsigned32
    MAX-ACCESS      read-only
    STATUS          current
    DESCRIPTION
        "This object indicates the observed voice utilization of the
        media client associated to a media stream." 
    ::= { cLQMediaClientHistoryEntry 16 }

cLQVMediaClientHistChannelUtil OBJECT-TYPE
    SYNTAX          Unsigned32
    MAX-ACCESS      read-only
    STATUS          current
    DESCRIPTION
        "This object indicates the observed channel utilization of the
        media
        client associated to a media stream." 
    ::= { cLQMediaClientHistoryEntry 17 }

cLQVMediaClientHistQueueUtil OBJECT-TYPE
    SYNTAX          Unsigned32
    MAX-ACCESS      read-only
    STATUS          current
    DESCRIPTION
        "This object indicates the observed queue utilization of the
        media client associated to a media stream." 
    ::= { cLQMediaClientHistoryEntry 18 }

cLQVMediaClientHistVideoPps OBJECT-TYPE
    SYNTAX          Unsigned32
    MAX-ACCESS      read-only
    STATUS          current
    DESCRIPTION
        "This object identifies the observed video packets per
        second on the media client associated to a media stream." 
    ::= { cLQMediaClientHistoryEntry 19 }

cLQVMediaClientHistVideoDelay OBJECT-TYPE
    SYNTAX          Unsigned32
    MAX-ACCESS      read-only
    STATUS          current
    DESCRIPTION
        "This object indicates the observed Video delay of the
        media client associated to a media stream." 
    ::= { cLQMediaClientHistoryEntry 20 }

cLQVMediaClientHistPktLossDiscard OBJECT-TYPE
    SYNTAX          Unsigned32
    MAX-ACCESS      read-only
    STATUS          current
    DESCRIPTION
        "This object indicates the observed packet loss discard of the
        media
        client associated to a media stream." 
    ::= { cLQMediaClientHistoryEntry 21 }

cLQVMediaClientHistPktLossFail OBJECT-TYPE
    SYNTAX          Unsigned32
    MAX-ACCESS      read-only
    STATUS          current
    DESCRIPTION
        "This object indicates the observed packet loss failure of the
        media client associated to a media stream." 
    ::= { cLQMediaClientHistoryEntry 22 }

cLQVMediaClientHistNumVideoStreams OBJECT-TYPE
    SYNTAX          Unsigned32
    MAX-ACCESS      read-only
    STATUS          current
    DESCRIPTION
        "This object indicates the observed number of video streams of
        the media client associated to a media stream." 
    ::= { cLQMediaClientHistoryEntry 23 }

cLQVMediaClientHistCacEnable OBJECT-TYPE
    SYNTAX          INTEGER  {
                        video(1),
                        voice(2),
                        videoAndVoice(3),
                        none(4)
                    }
    MAX-ACCESS      read-only
    STATUS          current
    DESCRIPTION
        "This object indicates the observed CAC enable state of the
        media client associated to a media stream.
        video(1) - video call admission control enabled.
        voice(2) - voice call admission control enabled.
        videoAndVoice(3) -video and voice call admission control
        enabled.
        none(4) - neither video nor voice call admission control
        enabled." 
    ::= { cLQMediaClientHistoryEntry 24 }

cLQVMediaClientHistStreamName OBJECT-TYPE
    SYNTAX          SnmpAdminString (SIZE  (1..64))
    MAX-ACCESS      read-only
    STATUS          current
    DESCRIPTION
        "This object indicates the media stream name to which the client
        was admitted at the particular timestamp." 
    ::= { cLQMediaClientHistoryEntry 25 }

-- ********************************************************************
-- * MediaStream Multicast client information
-- ********************************************************************

cLQMediaMulticastClientTable OBJECT-TYPE
    SYNTAX          SEQUENCE OF CLQMediaMulticastClientEntry 
    MAX-ACCESS      not-accessible
    STATUS          current
    DESCRIPTION
        "This table represents media related client
        properties for multicast clients.
        There exists a row in this table for each associated
        media clients.  A row is added to this table by the
        agent when a client gets associated
        Similarly a row gets deleted automatically when the
        client gets disassociated."
    ::= { cLQMediaClient 3 }

cLQMediaMulticastClientEntry OBJECT-TYPE
    SYNTAX          CLQMediaMulticastClientEntry
    MAX-ACCESS      not-accessible
    STATUS          current
    DESCRIPTION
        "Each entry represents a conceptual row in
        cLQMediaMulticastClientTable and corresponds to media
        properties of client."
    INDEX           {
                        cLQMStreamName,
                        cLQVMediaClientMCGrpIpAddrType,
                        cLQVMediaClientMCGrpIpAddr,
                        cldcClientMacAddress
                    } 
    ::= { cLQMediaMulticastClientTable 1 }

CLQMediaMulticastClientEntry ::= SEQUENCE {
        cLQVMediaClientMCGrpIpAddrType InetAddressType,
        cLQVMediaClientMCGrpIpAddr     InetAddress,
        cLQVMediaClientVlanId          Unsigned32,
        cLQVMediaMCClientApName        SnmpAdminString,
        cLQVMediaClientMCUCStatus      SnmpAdminString
}

cLQVMediaClientMCGrpIpAddrType OBJECT-TYPE
    SYNTAX          InetAddressType
    MAX-ACCESS      not-accessible
    STATUS          current
    DESCRIPTION
        "This object represents multicast destination IP address
        type." 
    ::= { cLQMediaMulticastClientEntry 1 }

cLQVMediaClientMCGrpIpAddr OBJECT-TYPE
    SYNTAX          InetAddress
    MAX-ACCESS      not-accessible
    STATUS          current
    DESCRIPTION
        "This object represents multicast destination IP address." 
    ::= { cLQMediaMulticastClientEntry 2 }

cLQVMediaClientVlanId OBJECT-TYPE
    SYNTAX          Unsigned32
    MAX-ACCESS      read-only
    STATUS          current
    DESCRIPTION
        "This object represents the VLAN id of the
        client." 
    ::= { cLQMediaMulticastClientEntry 3 }

cLQVMediaMCClientApName OBJECT-TYPE
    SYNTAX          SnmpAdminString
    MAX-ACCESS      read-only
    STATUS          current
    DESCRIPTION
        "This object represents the unique access point to
        which the multicast client is connected." 
    ::= { cLQMediaMulticastClientEntry 4 }

cLQVMediaClientMCUCStatus OBJECT-TYPE
    SYNTAX          SnmpAdminString
    MAX-ACCESS      read-only
    STATUS          current
    DESCRIPTION
        "This object represents whether the multicast client has
        multicast-to-unicast feature enabled." 
    ::= { cLQMediaMulticastClientEntry 5 }
  
-- ********************************************************************
-- *  SIP CALL admission control configurations
-- ********************************************************************

cLQd11SipCacConfigTable OBJECT-TYPE
    SYNTAX          SEQUENCE OF CLQd11SipCacConfigEntry 
    MAX-ACCESS      not-accessible
    STATUS          current
    DESCRIPTION
        "This table contains the information about the
        SIP CAC configuration corresponding to
        the dot11 bands of the APs that have joined
        the controller.
        The parameters specify how the SIP call reserves 
        CAC bandwidth."
    ::= { cLQd11SipCacConfig 1 }

cLQd11SipCacConfigEntry OBJECT-TYPE
    SYNTAX          CLQd11SipCacConfigEntry
    MAX-ACCESS      not-accessible
    STATUS          current
    DESCRIPTION
        "An entry containing SIP CAC configuration for a particular type
        of wireless interface."
    INDEX           { cLApDot11IfType } 
    ::= { cLQd11SipCacConfigTable 1 }

CLQd11SipCacConfigEntry ::= SEQUENCE {
        cLQd11SipCacConfigCodecType                 INTEGER,
        cLQd11SipCacConfigBw                        Unsigned32,
        cLQd11SipCacConfigVoiceSampleSize           Unsigned32,
        cLQd11SipCacMaxPossibleVoiceCalls           Unsigned32,
        cLQd11SipCacMaxPossibleReservedRoamingCalls Unsigned32
}

cLQd11SipCacConfigCodecType OBJECT-TYPE
    SYNTAX          INTEGER  {
                        userDefined(1),
                        g711(2),
                        g729(3)
                    }
    MAX-ACCESS      read-write
    STATUS          current
    DESCRIPTION
        "This object specifies the configured codec for SIP Cac
        configuration of the dot11 band for the APs associated 
        with this controller. Codec determines the bandwidth to 
        be reserved for voice call.
        userDefined - User defines the bandwidth, 
        cLQd11SipCacConfigBw has to be configured
        g711 - standard Codec G711
        g729 - standard Codec G729"
    DEFVAL          { g711 } 
    ::= { cLQd11SipCacConfigEntry 1 }

cLQd11SipCacConfigBw OBJECT-TYPE
    SYNTAX          Unsigned32
    UNITS           "kbps"
    MAX-ACCESS      read-write
    STATUS          current
    DESCRIPTION
        "This object specifies the configured bandwidth in kbps
        for SIP CAC configuration of the dot11
        band for the APs associated with this controller.

        This is configurable only if cLQd11SipCacConfigCodecType
         is 'userDefined'" 
    ::= { cLQd11SipCacConfigEntry 2 }

cLQd11SipCacConfigVoiceSampleSize OBJECT-TYPE
    SYNTAX          Unsigned32
    UNITS           "milliseconds"
    MAX-ACCESS      read-write
    STATUS          current
    DESCRIPTION
        "This object specifies the configured voice sample size
        in milliseconds for SIP Cac configuration of the dot11 band 
        for the APs associated with this controller." 
    ::= { cLQd11SipCacConfigEntry 3 }
 
cLQd11SipCacMaxPossibleVoiceCalls OBJECT-TYPE
    SYNTAX          Unsigned32
    MAX-ACCESS      read-only
    STATUS          current
    DESCRIPTION
        "This object represents the maximum possible voice calls
        that can be made with respect to the current SIP CAC
        configuration."
    ::= { cLQd11SipCacConfigEntry 4 }

cLQd11SipCacMaxPossibleReservedRoamingCalls OBJECT-TYPE
    SYNTAX          Unsigned32
    MAX-ACCESS      read-only
    STATUS          current
    DESCRIPTION
        "This object represents the maximum possible reserved
        roaming calls that can be made with respect to the current
        SIP CAC configuration."
    ::= { cLQd11SipCacConfigEntry 5 }

-- ********************************************************************
-- Table to represent Media stream config
-- parameters per stream.
-- ********************************************************************

cLQMStreamTable OBJECT-TYPE
    SYNTAX          SEQUENCE OF CLQMStreamEntry 
    MAX-ACCESS      not-accessible
    STATUS          current
    DESCRIPTION
        "This table lists different media streams identified by its name
        and the stream parameters."
    ::= { cLQMediaStreamConfig 1 }

cLQMStreamEntry OBJECT-TYPE
    SYNTAX          CLQMStreamEntry
    MAX-ACCESS      not-accessible
    STATUS          current
    DESCRIPTION
        "Each entry represents a conceptual row in
        cLQMStreamTable and corresponds to the
        media stream configuration on the device."
    INDEX           { cLQMStreamName } 
    ::= { cLQMStreamTable 1 }

CLQMStreamEntry ::= SEQUENCE {
        cLQMStreamName                  SnmpAdminString,
        cLQMStreamStorageType           StorageType,
        cLQMStreamSrcIPAddrType         InetAddressType,
        cLQMStreamSrcIPAddr             InetAddress,
        cLQMStreamState                 TruthValue,
        cLQMStreamRrcExpBw              Unsigned32,
        cLQMStreamRrcAvgPkt             Unsigned32,
        cLQMStreamReRrc                 TruthValue,
        cLQMStreamRrcQos                INTEGER,
        cLQMStreamRrcType               INTEGER,
        cLQMStreamRrcPriority           INTEGER,
        cLQMStreamRrcViolation          INTEGER,
        cLQMStreamRrcPolicy             TruthValue,
        cLQMStreamDestStartInetAddrType InetAddressType,
        cLQMStreamDestStartInetAddr     InetAddress,
        cLQMStreamDestEndInetAddrType   InetAddressType,
        cLQMStreamDestEndInetAddr       InetAddress,
        cLQMStreamRowStatus             RowStatus
}

cLQMStreamName OBJECT-TYPE
    SYNTAX          SnmpAdminString (SIZE  (1..64))
    MAX-ACCESS      not-accessible
    STATUS          current
    DESCRIPTION
        "This object specifies a human readable name which uniquely
        identifies the media stream." 
    ::= { cLQMStreamEntry 1 }

cLQMStreamStorageType OBJECT-TYPE
    SYNTAX          StorageType
    MAX-ACCESS      read-create
    STATUS          current
    DESCRIPTION
        "This object represnts the storage type for this
        conceptual row."
    DEFVAL          { nonVolatile } 
    ::= { cLQMStreamEntry 2 }

cLQMStreamSrcIPAddrType OBJECT-TYPE
    SYNTAX          InetAddressType
    MAX-ACCESS      read-create
    STATUS          current
    DESCRIPTION
        "This object specifies the  source Ip
        multicast address type to be used by the media stream." 
    ::= { cLQMStreamEntry 3 }

cLQMStreamSrcIPAddr OBJECT-TYPE
    SYNTAX          InetAddress
    MAX-ACCESS      read-create
    STATUS          current
    DESCRIPTION
        "This object specifies the  source Ip
        multicast address to be used by the media stream." 
    ::= { cLQMStreamEntry 4 }

cLQMStreamState OBJECT-TYPE
    SYNTAX          TruthValue
    MAX-ACCESS      read-create
    STATUS          current
    DESCRIPTION
        "This object specifies the current state of the media stream.
        'true' - Indicates the media stream state is enabled. 
        'false' - Indicates the media stream state is disabled."
    DEFVAL          { false } 
    ::= { cLQMStreamEntry 5 }

cLQMStreamRrcExpBw OBJECT-TYPE
    SYNTAX          Unsigned32 (1..35000)
    MAX-ACCESS      read-create
    STATUS          current
    DESCRIPTION
        "This object specifies Resource Reservation Control(RRC)
        bandwidth
        utilization."
    DEFVAL          { 500 } 
    ::= { cLQMStreamEntry 6 }

cLQMStreamRrcAvgPkt OBJECT-TYPE
    SYNTAX          Unsigned32 (100..1500)
    MAX-ACCESS      read-create
    STATUS          current
    DESCRIPTION
        "This object specifies RRC average packet size."
    DEFVAL          { 1200 } 
    ::= { cLQMStreamEntry 7 }

cLQMStreamReRrc OBJECT-TYPE
    SYNTAX          TruthValue
    MAX-ACCESS      read-create
    STATUS          current
    DESCRIPTION
        "This object specifies whether re-RRC calculations are enabled.

        'true' - Indicates the calculations are enabled. 
        'false' - Indicates the calculations are disabled."
    DEFVAL          { true } 
    ::= { cLQMStreamEntry 8 }

cLQMStreamRrcQos OBJECT-TYPE
    SYNTAX          INTEGER  {
                        bestEffort(1),
                        background(2),
                        undefined(3),
                        excellentEffort(4),
                        ctrlLoad(5),
                        video(6),
                        voice(7),
                        network(8)
                    }
    MAX-ACCESS      read-create
    STATUS          current
    DESCRIPTION
        "This object specifies RRC QOS queue information.

        bestEffort - media stream clients associated to the stream 
        identified by stream name are scheduled to a best effort queue.

        background - media stream clients associated to the stream 
        identified by stream name are scheduled to a background queue.

        undefined - media stream clients associated to the stream 
        identified by stream name are scheduled to a undefined queue.

        excellentEffort - media stream clients associated to the stream 
        identified by stream name are scheduled to a execellent effort queue.

        ctrlLoad - media stream clients associated to the stream 
        identified by stream name are scheduled to a control load queue.

        video - media stream clients associated to the stream 
        identified by stream name are scheduled to video queue.

        voice - media stream clients associated to the stream 
        identified by stream name are scheduled to voice queue.

        network - media stream clients associated to the stream 
        identified by stream name are scheduled to a network queue." 
    ::= { cLQMStreamEntry 9 }

cLQMStreamRrcType OBJECT-TYPE
    SYNTAX          INTEGER  {
                        mc2uc(1),
                        mOnly(2),
                        unicast(3),
                        disabled(4)
                    }
    MAX-ACCESS      read-create
    STATUS          current
    DESCRIPTION
        "This object specifies RRC Media stream type.

        mc2uc - multicast to unicast enabled.
        mOnly - only multicast enabled.
        unicast - unicast enabled.
        disabled - neither multicast nor unicast enabled." 
    ::= { cLQMStreamEntry 10 }

cLQMStreamRrcPriority OBJECT-TYPE
    SYNTAX          INTEGER (1..8)
    MAX-ACCESS      read-create
    STATUS          current
    DESCRIPTION
        "This object specifies RRC Priority bit set within media
        stream."
    DEFVAL          { 4 } 
    ::= { cLQMStreamEntry 11 }

cLQMStreamRrcViolation OBJECT-TYPE
    SYNTAX          INTEGER  {
                        fallback(1),
                        drop(2)
                    }
    MAX-ACCESS      read-create
    STATUS          current
    DESCRIPTION
        "This object specifies the RRC violation policy to be applied
        when the media stream violates the profile. This object
        specifies 
        whether to drop the stream or provide bestEffort treatment." 
    ::= { cLQMStreamEntry 12 }

cLQMStreamRrcPolicy OBJECT-TYPE
    SYNTAX          TruthValue
    MAX-ACCESS      read-create
    STATUS          current
    DESCRIPTION
        "This object specifies whether the media stream should be
        allowed or 
        denied. 

          true - Allow the media stream. 
          false - Deny the media stream."
    DEFVAL          { false } 
    ::= { cLQMStreamEntry 13 }

cLQMStreamDestStartInetAddrType OBJECT-TYPE
    SYNTAX          InetAddressType
    MAX-ACCESS      read-create
    STATUS          current
    DESCRIPTION
        "This object represents Multicast Destination Start Address Type" 
    ::= { cLQMStreamEntry 14 }

cLQMStreamDestStartInetAddr OBJECT-TYPE
    SYNTAX          InetAddress
    MAX-ACCESS      read-create
    STATUS          current
    DESCRIPTION
        "This object represents Multicast Destination Start Address" 
    ::= { cLQMStreamEntry 15 }

cLQMStreamDestEndInetAddrType OBJECT-TYPE
    SYNTAX          InetAddressType
    MAX-ACCESS      read-create
    STATUS          current
    DESCRIPTION
        "This object represents Multicast Destination End Address Type" 
    ::= { cLQMStreamEntry 16 }

cLQMStreamDestEndInetAddr OBJECT-TYPE
    SYNTAX          InetAddress
    MAX-ACCESS      read-create
    STATUS          current
    DESCRIPTION
        "This object represents Multicast Destination End Address" 
    ::= { cLQMStreamEntry 17 }

cLQMStreamRowStatus OBJECT-TYPE
    SYNTAX          RowStatus
    MAX-ACCESS      read-create
    STATUS          current
    DESCRIPTION
        "This is the status column for this row and used
        to create and delete specific instances of rows
        in this table.
        cLQMStreamName is mandatory for successful
        creation of an entry." 
    ::= { cLQMStreamEntry 18 }
 

cLQMStreamSdpConfig  OBJECT IDENTIFIER
    ::= { cLQMediaStreamConfig 2 }


cLQMStreamSdpUrl OBJECT-TYPE
    SYNTAX          CiscoURLStringOrEmpty
    MAX-ACCESS      read-write
    STATUS          current
    DESCRIPTION
        "This object specifies the media stream session description
        protocol (SDP) URL.  While MC2UC request is denied, AP will send
        session announcement message to the client. The payload with URL
        information will be sent from WLC in order to update AP with SDP
        content configuration." 
    ::= { cLQMStreamSdpConfig 1 }

cLQMStreamSdpEmail OBJECT-TYPE
    SYNTAX          SnmpAdminString (SIZE  (0..64))
    MAX-ACCESS      read-write
    STATUS          current
    DESCRIPTION
        "This object specifies the media stream session description
        protocol (SDP) email. While MC2UC request is denied, AP will
        send session announcement message to client. The payload with
        email
        information will be sent from WLC in order to update AP with SDP
        content configuration." 
    ::= { cLQMStreamSdpConfig 2 }

cLQMStreamSdpPhone OBJECT-TYPE
    SYNTAX          SnmpAdminString (SIZE  (0..30))
    MAX-ACCESS      read-write
    STATUS          current
    DESCRIPTION
        "This object specifies the media stream session description
        protocol (SDP) phone. While MC2UC request is denied, AP will
        send session announcement message to client. The payload with
        phone information will be sent from WLC in order to update AP
        with SDP
        content configuration." 
    ::= { cLQMStreamSdpConfig 3 }

cLQMStreamSdpNote OBJECT-TYPE
    SYNTAX          SnmpAdminString (SIZE  (0..128))
    MAX-ACCESS      read-write
    STATUS          current
    DESCRIPTION
        "This object specifies the media stream session description
        protocol (SDP) note.  While MC2UC request is denied, AP will
        send session announcement message to client. The payload with
        SDP note information will be sent from WLC in order to update AP
        with SDP
        content configuration." 
    ::= { cLQMStreamSdpConfig 4 }

cLQMStreamSdpStatus OBJECT-TYPE
    SYNTAX          TruthValue
    MAX-ACCESS      read-write
    STATUS          current
    DESCRIPTION
        "This object specifies the media stream session description
        protocol (SDP) status. While MC2UC request is denied, AP will
        send
        session announcement message to client. The payload with status
        information will be sent from WLC in order to update AP with SDP
        content configuration." 
    ::= { cLQMStreamSdpConfig 5 }
cLQMStreamRrcGlobal  OBJECT IDENTIFIER
    ::= { cLQMediaStreamConfig 3 }


cLQMStreamRrcGlobalState OBJECT-TYPE
    SYNTAX          TruthValue
    MAX-ACCESS      read-write
    STATUS          current
    DESCRIPTION
        "This object specifies the administrative status of media
        stream functionality in the device. 

        Enable - Enables the media stream functionality.  
        Disable - Disables the media stream functionality."
    DEFVAL          { false } 
    ::= { cLQMStreamRrcGlobal 1 }

cLQPreferredCallTable OBJECT-TYPE
    SYNTAX          SEQUENCE OF CLQPreferredCallEntry 
    MAX-ACCESS      not-accessible
    STATUS          current
    DESCRIPTION
        "This table populates the preferred call configuration.
        When the call comes to any of these numbers, even if there is no
        bandwidth available in the configured voice pool, WLC should
        facilitate the urgency of these calls in any way possible
        without potentially altering the quality of the existing calls. 
        This is supported only for those clients which use SIP based CAC
        for bandwidth allocation in the WLC."
    ::= { cLQPreferredCallConfig 1 }

cLQPreferredCallEntry OBJECT-TYPE
    SYNTAX          CLQPreferredCallEntry
    MAX-ACCESS      not-accessible
    STATUS          current
    DESCRIPTION
        "Each entry represents a conceptual row in
        cLQPreferredCallTable and corresponds to the preferred call
        number of the user."
    INDEX           { cLQPreferredCallIndex } 
    ::= { cLQPreferredCallTable 1 }

CLQPreferredCallEntry ::= SEQUENCE {
        cLQPreferredCallIndex       Unsigned32,
        cLQPreferredCallNumber      SnmpAdminString,
        cLQPreferredCallRowStatus   RowStatus,
        cLQPreferredCallStorageType StorageType
}

cLQPreferredCallIndex OBJECT-TYPE
    SYNTAX          Unsigned32 (1..6)
    MAX-ACCESS      not-accessible
    STATUS          current
    DESCRIPTION
        "This object indicates an arbitrary integer-value that uniquely

        identifies a preferred call number configured by the user." 
    ::= { cLQPreferredCallEntry 1 }

cLQPreferredCallNumber OBJECT-TYPE
    SYNTAX          SnmpAdminString (SIZE  (0..32))
    MAX-ACCESS      read-create
    STATUS          current
    DESCRIPTION
        "This object specifies  the preferred call number
        configured by the user." 
    ::= { cLQPreferredCallEntry 2 }

cLQPreferredCallRowStatus OBJECT-TYPE
    SYNTAX          RowStatus
    MAX-ACCESS      read-create
    STATUS          current
    DESCRIPTION
        "This is the status column for this row and used
        to create and delete specific instances of rows
        in this table.
        The following objects are mandatory for successful
        creation of an entry:
        cLQPreferredCallNumber" 
    ::= { cLQPreferredCallEntry 3 }

cLQPreferredCallStorageType OBJECT-TYPE
    SYNTAX          StorageType
    MAX-ACCESS      read-create
    STATUS          current
    DESCRIPTION
        "This object specifies the storage type for this
        conceptual row."
    DEFVAL          { nonVolatile } 
    ::= { cLQPreferredCallEntry 4 }

-- *******************************************************************
-- *    SIP Snooping configuration
-- *******************************************************************

cLQoSSipSnoopingPortRangeStart OBJECT-TYPE
    SYNTAX          InetPortNumber
    MAX-ACCESS      read-write
    STATUS          current
    DESCRIPTION
        "This object specifies the starting port with respect to SIP
        snooping feature on controller. If single port has to be
        used, configure cLQoSSipSnoopingPortRangeStart and
        cLQoSSipSnoopingPortRangeEnd with same value."
    ::= { cLQoSSipSnoopingConfig 1 }

cLQoSSipSnoopingPortRangeEnd OBJECT-TYPE
    SYNTAX          InetPortNumber
    MAX-ACCESS      read-write
    STATUS          current
    DESCRIPTION
        "This object specifies the ending port with respect to SIP
        snooping feature on controller. If single port has to be
        used, configure cLQoSSipSnoopingPortRangeStart and
        cLQoSSipSnoopingPortRangeEnd with same value."
    ::= { cLQoSSipSnoopingConfig 2 }


-- cLQoSProfileConfig is not supported now.Reserved for future.
-- cLQoSSipSnoopingConfig is not supported now.Reserved for future.
-- *******************************************************************
-- *    ATF(Air Time Fairness) configuration
-- *******************************************************************

cLQoSGlobalAirTimeFairnessTable OBJECT-TYPE
    SYNTAX          SEQUENCE OF CLQoSGlobalAirTimeFairnessEntry
    MAX-ACCESS      not-accessible
    STATUS          current
    DESCRIPTION
        "This table is used to configure the global dot11
        parameters per slot id, represented by cLApDot11IfSlotId,
        of the radio interface in all the ATF supported APs joined
        with the controller."
    ::= { cLQoSAirTimeFairness 1 }

cLQoSGlobalAirTimeFairnessEntry OBJECT-TYPE
    SYNTAX          CLQoSGlobalAirTimeFairnessEntry
    MAX-ACCESS      not-accessible
    STATUS          current
    DESCRIPTION
        "This represents an entry in cLQoSGlobalAirTimeFairnessTable."
    INDEX           { cLApDot11IfType }
    ::= { cLQoSGlobalAirTimeFairnessTable 1 }

CLQoSGlobalAirTimeFairnessEntry ::= SEQUENCE {
        cLGlobalAirTimeFairnessMode               INTEGER,
        cLGlobalAirTimeFairnessOptimizationPolicy INTEGER,
        cLGlobalBridgeClientAccess                TruthValue, 
        cLGlobalAirTimeAllocation                 Unsigned32
}

cLGlobalAirTimeFairnessMode OBJECT-TYPE
    SYNTAX          INTEGER {
                        disabled(1),
                        ssid(2),
                        monitor(3)
                    }
    MAX-ACCESS      read-write
    STATUS          current
    DESCRIPTION
        "This object is used to set the mode1 - Disabled
        2 - SSID Mode 3 - Monitor Mode represented by  cLApDot11IfType
        of ATF supported APs joined in the controller.Read operation on
        this attribute may differ if config is overridden."
    DEFVAL          { disabled }
    ::= { cLQoSGlobalAirTimeFairnessEntry 1 }

cLGlobalAirTimeFairnessOptimizationPolicy OBJECT-TYPE
    SYNTAX          TruthValue
    MAX-ACCESS      read-write
    STATUS          current
    DESCRIPTION
        "This object is used to configure the Optimization Policy
        represented by cLApDot11IfType of ATF supported APs, joined
        in the controller.Read operation on this attribute may differ
        if config is overridden."
    ::= { cLQoSGlobalAirTimeFairnessEntry 2 }

cLGlobalBridgeClientAccess OBJECT-TYPE
    SYNTAX      TruthValue
    MAX-ACCESS  read-write
    STATUS      current
    DESCRIPTION
    "This object specifies whether airtime
     allocation is enabled for the client access node."
    DEFVAL          { false }
    ::= { cLQoSGlobalAirTimeFairnessEntry 3 }

cLGlobalAirTimeAllocation OBJECT-TYPE
    SYNTAX      Unsigned32(5..90)
    MAX-ACCESS  read-write
    STATUS      current
    DESCRIPTION
    "This object specifies the percentage for airtime
     allocation for the client access node."
    DEFVAL          { 5 }
    ::= { cLQoSGlobalAirTimeFairnessEntry 4 }


cLQoSAirTimeFairnessTable OBJECT-TYPE
    SYNTAX          SEQUENCE OF CLQoSAirTimeFairnessEntry
    MAX-ACCESS      not-accessible
    STATUS          current
    DESCRIPTION
        "This table represents the ATF(Air Time Fairness) configuration
        Per-AP Per-SlotId & ATF supported APs that join with this
        controller."
    ::= { cLQoSAirTimeFairness 2 }

cLQoSAirTimeFairnessEntry OBJECT-TYPE
    SYNTAX          CLQoSAirTimeFairnessEntry
    MAX-ACCESS      not-accessible
    STATUS          current
    DESCRIPTION
        "Each entry contains information of Per-AP, Per-SlotId & ATF
        supported APs information."
    INDEX           {
                        cLApSysMacAddress,
                        cLApDot11IfSlotId
                    }
    ::= { cLQoSAirTimeFairnessTable 1 }

CLQoSAirTimeFairnessEntry ::= SEQUENCE {
        cLApAirTimeFairnessMode               INTEGER,
        cLApAirTimeFairnessOptimizationPolicy TruthValue
}

CLQoSAirTimeFairnessEntry ::= SEQUENCE {
        cLApAirTimeFairnessMode               INTEGER,
        cLApAirTimeFairnessOptimizationPolicy TruthValue
}

cLApAirTimeFairnessMode OBJECT-TYPE
    SYNTAX          INTEGER {
                        disabled(1),
                        ssid(2),
                        monitor(3)
                    }
    MAX-ACCESS      read-write
    STATUS          current
    DESCRIPTION
        "This object specifies the mode of all the ATF supported access
        points 1 - Disabled  2 - SSID Mode 3 - Monitor Mode."
    DEFVAL          { disabled }
    ::= { cLQoSAirTimeFairnessEntry 1 }

cLApAirTimeFairnessOptimizationPolicy OBJECT-TYPE
    SYNTAX          TruthValue
    MAX-ACCESS      read-write
    STATUS          current
    DESCRIPTION
        "This object specifies StealingPolicy of all the ATF
        supported access points should be enabled or disabled."
    ::= { cLQoSAirTimeFairnessEntry 2 }


-- ********************************************************************
-- *       ATF(Air Time Fairness) Statistics for Air Time TimeSlice
-- *******************************************************************

cLQoSAirTimeFairnessWlanStatisticsTable OBJECT-TYPE
 SYNTAX          SEQUENCE OF CLQoSAirTimeFairnessWlanStatisticsEntry
    MAX-ACCESS      not-accessible
    STATUS          current
    DESCRIPTION
        "This table represents the ATF(Air Time Fairness) Wlan
        statistics for each airtime timeslice Per-AP Per-SlotId
        Per-WlanId of ATF supported APs joined to controller."
    ::= { cLQoSAirTimeFairness 3 }

cLQoSAirTimeFairnessWlanStatisticsEntry OBJECT-TYPE
    SYNTAX          CLQoSAirTimeFairnessWlanStatisticsEntry
    MAX-ACCESS      not-accessible
    STATUS          current
    DESCRIPTION
        "This entry contains AirTimeFairness TimeSlice Wlan Statistics"
    INDEX           {
                        cLApSysMacAddress,
                        cLApDot11IfSlotId,
                        cLWlanProfileName
                    }
    ::= { cLQoSAirTimeFairnessWlanStatisticsTable 1 }

CLQoSAirTimeFairnessWlanStatisticsEntry ::= SEQUENCE {
        cLApAirTimeFairnessWlanAirtimeUsedInstantaneous   TimeInterval,
        cLApAirTimeFairnessWlanAirtimeUsedCumulative      TimeInterval,
        cLApAirTimeFairnessWlanBytesSentInstantaneous     Unsigned32,
        cLApAirTimeFairnessWlanBytesSentCumulative        Unsigned64,
        cLApAirTimeFairnessWlanBytesDroppedInstantaneous  Unsigned32,
        cLApAirTimeFairnessWlanBytesDroppedCumulative     Unsigned64,
        cLApAirTimeFairnessWlanFramesSentInstantaneous    Unsigned32,
        cLApAirTimeFairnessWlanFramesSentCumulative       Unsigned64,
        cLApAirTimeFairnessWlanFramesDroppedInstantaneous Unsigned32,
        cLApAirTimeFairnessWlanFramesDroppedCumulative    Unsigned64
}

cLApAirTimeFairnessWlanAirtimeUsedInstantaneous OBJECT-TYPE
 SYNTAX          TimeInterval
    UNITS           "Microseconds"
    MAX-ACCESS      read-only
    STATUS          current
    DESCRIPTION
        "This object specifies the air time used instantaneous in micro
        seconds for particular AP per Slot per WlanProfileName."
    DEFVAL          { 0 }
    ::= { cLQoSAirTimeFairnessWlanStatisticsEntry 1 }

cLApAirTimeFairnessWlanAirtimeUsedCumulative OBJECT-TYPE
    SYNTAX          TimeInterval
    UNITS           "Microseconds"
    MAX-ACCESS      read-only
    STATUS          current
    DESCRIPTION
        "This object specifies the total AirTime used cumulative for
        particular AP per Slot per WlanProfileName."
    ::= { cLQoSAirTimeFairnessWlanStatisticsEntry 2 }

cLApAirTimeFairnessWlanBytesSentInstantaneous OBJECT-TYPE
    SYNTAX          Unsigned32
    UNITS           "bytes"
    MAX-ACCESS      read-only
    STATUS          current
    DESCRIPTION
        "This object specifies the number of bytes sent instantaneous
        for particular AP per Slot per WlanProfileName."
    DEFVAL          { 0 }
    ::= { cLQoSAirTimeFairnessWlanStatisticsEntry 3 }

cLApAirTimeFairnessWlanBytesSentCumulative OBJECT-TYPE
    SYNTAX          Unsigned64
    UNITS           "bytes"
    MAX-ACCESS      read-only
    STATUS          current
    DESCRIPTION
        "his object specifies the total number of bytes dropped
        cumulative for particular AP per Slot per WlanProfileName."
    ::= { cLQoSAirTimeFairnessWlanStatisticsEntry 4 }

cLApAirTimeFairnessWlanBytesDroppedInstantaneous OBJECT-TYPE
    SYNTAX          Unsigned32
    UNITS           "bytes"
    MAX-ACCESS      read-only
    STATUS          current
    DESCRIPTION
        "This object specifies the total number of bytes dropped
        instantaneous for particular AP per Slot per
        WlanProfileName."
    DEFVAL          { 0 }
    ::= { cLQoSAirTimeFairnessWlanStatisticsEntry 5 }

cLApAirTimeFairnessWlanBytesDroppedCumulative OBJECT-TYPE
    SYNTAX          Unsigned64
    UNITS           "bytes"
    MAX-ACCESS      read-only
    STATUS          current
    DESCRIPTION
        "This object specifies the total number of bytes dropped
        cumulative for particular AP per Slot per WlanProfileName."
    ::= { cLQoSAirTimeFairnessWlanStatisticsEntry 6 }

cLApAirTimeFairnessWlanFramesSentInstantaneous OBJECT-TYPE
    SYNTAX          Unsigned32
    UNITS           "pkts"
    MAX-ACCESS      read-only
    STATUS          current
    DESCRIPTION
        "This object specifies the total number of packets sent
        instantaneous for particular AP per Slot per
        WlanProfileName."
    DEFVAL          { 0 }
    ::= { cLQoSAirTimeFairnessWlanStatisticsEntry 7 }

cLApAirTimeFairnessWlanFramesSentCumulative OBJECT-TYPE
    SYNTAX          Unsigned64
    UNITS           "pkts"
    MAX-ACCESS      read-only
    STATUS          current
    DESCRIPTION
        "This object specifies the total number of packets sent
        cumulative for particular AP per Slot per WlanProfileName."
    ::= { cLQoSAirTimeFairnessWlanStatisticsEntry 8 }

cLApAirTimeFairnessWlanFramesDroppedInstantaneous OBJECT-TYPE
    SYNTAX          Unsigned32
    UNITS           "pkts"
    MAX-ACCESS      read-only
    STATUS          current
    DESCRIPTION
        "This object specifies the total number of packets drop
        instantaneous for particular AP per Slot per
        WlanProfileName."
    DEFVAL          { 0 }
    ::= { cLQoSAirTimeFairnessWlanStatisticsEntry 9 }

cLApAirTimeFairnessWlanFramesDroppedCumulative OBJECT-TYPE
    SYNTAX          Unsigned64
    UNITS           "pkts"
    MAX-ACCESS      read-only
    STATUS          current
    DESCRIPTION
        "This table represents the ATF(Air Time Fairness) Wlan
        statistics for each airtime timeslice Per-AP Per-SlotId of ATF
        supported
        APs joined to controller."
    ::= { cLQoSAirTimeFairnessWlanStatisticsEntry 10 }



cLQoSAirTimeFairnessStatisticsTable OBJECT-TYPE
    SYNTAX          SEQUENCE OF CLQoSAirTimeFairnessStatisticsEntry
    MAX-ACCESS      not-accessible
    STATUS          current
    DESCRIPTION
        "This table represents the ATF(Air Time Fairness) Wlan
        statistics for each airtime timeslice Per-AP Per-SlotId of ATF
        supported
        APs joined to controller."
    ::= { cLQoSAirTimeFairness 4 }

cLQoSAirTimeFairnessStatisticsEntry OBJECT-TYPE
    SYNTAX          CLQoSAirTimeFairnessStatisticsEntry
    MAX-ACCESS      not-accessible
    STATUS          current
    DESCRIPTION
        "This entry contains AirTimeFairness TimeSlice Statistics"
    INDEX           {
                        cLApSysMacAddress,
                        cLApDot11IfSlotId
                    }
    ::= { cLQoSAirTimeFairnessStatisticsTable 1 }

CLQoSAirTimeFairnessStatisticsEntry ::= SEQUENCE {
        cLApAirTimeFairnessTotalAirtimeUsedInstantaneous TimeInterval,
        cLApAirTimeFairnessTotalAirtimeUsedCumulative    TimeInterval,
        cLApAirTimeFairnessRadioUptime                   TimeInterval,
        cLApAirTimeFairnessRadioUptimeCumulative         TimeInterval
}

cLApAirTimeFairnessTotalAirtimeUsedInstantaneous OBJECT-TYPE
    SYNTAX          TimeInterval
    UNITS           "Microseconds"
    MAX-ACCESS      read-only
    STATUS          current
    DESCRIPTION
        "This object specifies the air time used instantaneous in micro
        seconds for particular AP per Slot."
    DEFVAL          { 0 }
    ::= { cLQoSAirTimeFairnessStatisticsEntry 1 }

cLApAirTimeFairnessTotalAirtimeUsedCumulative OBJECT-TYPE
    SYNTAX          TimeInterval
    UNITS           "Microseconds"
    MAX-ACCESS      read-only
    STATUS          current
    DESCRIPTION
        "his object specifies the total AirTime used cumulative for
        particular AP per Slot."
    DEFVAL          { 0 }
    ::= { cLQoSAirTimeFairnessStatisticsEntry 2 }

cLApAirTimeFairnessRadioUptime OBJECT-TYPE
    SYNTAX          TimeInterval
    UNITS           "seconds"
    MAX-ACCESS      read-only
    STATUS          current
    DESCRIPTION
        "This object specifies the air time used instantaneous in
        seconds
        for particular AP per Slot."
    DEFVAL          { 0 }
    ::= { cLQoSAirTimeFairnessStatisticsEntry 3 }

cLApAirTimeFairnessRadioUptimeCumulative OBJECT-TYPE
    SYNTAX          TimeInterval
    UNITS           "seconds"
    MAX-ACCESS      read-only
    STATUS          current
    DESCRIPTION
        "This object specifies the total AirTime used cumulative for
        particular AP per Slot."
    DEFVAL          { 0 }
    ::= { cLQoSAirTimeFairnessStatisticsEntry 4 }


cLAPGroupAirTimeFairnessTable OBJECT-TYPE
    SYNTAX          SEQUENCE OF CLAPGroupAirTimeFairnessEntry
    MAX-ACCESS      not-accessible
    STATUS          current
    DESCRIPTION
        "This table for configuring the ATF(Air Time Fairness)for AP
        group."
    ::= { cLQoSAirTimeFairness 5 }

cLAPGroupAirTimeFairnessEntry OBJECT-TYPE
    SYNTAX          CLAPGroupAirTimeFairnessEntry
    MAX-ACCESS      not-accessible
    STATUS          current
    DESCRIPTION
        "An entry in cLAPGroupAirTimeFairnessTable for the configuring
        ATF(Air Time Fairness) for an AP group."
    INDEX           {
                        cLApDot11IfType,
                        cLAPGroupName
                    }
    ::= { cLAPGroupAirTimeFairnessTable 1 }

CLAPGroupAirTimeFairnessEntry ::= SEQUENCE {
        cLAPGroupAirTimeFairnessMode               INTEGER,
        cLAPGroupAirTimeFairnessOptimizationPolicy TruthValue
}

cLAPGroupAirTimeFairnessMode OBJECT-TYPE
    SYNTAX          INTEGER {
                        disabled(1),
                        ssid(2),
                        monitor(3)
                    }
    MAX-ACCESS      read-write
    STATUS          current
    DESCRIPTION
        "This object represents the ATF(Air Time Fairness) mode for this
        AP group per radiotype 1 - Disabled  2 - SSID Mode 3 - Monitor
        Mode."
    DEFVAL          { disabled }
    ::= { cLAPGroupAirTimeFairnessEntry 1 }

cLAPGroupAirTimeFairnessOptimizationPolicy OBJECT-TYPE
    SYNTAX          TruthValue
    MAX-ACCESS      read-write
    STATUS          current
    DESCRIPTION
        "This object represents the ATF(Air Time Fairness)
        StealingPolicy for this AP group per radio type."
    ::= { cLAPGroupAirTimeFairnessEntry 2 }


-- ********************************************************************
-- AirTime Fairness Policy Configuration
-- ********************************************************************

cLQosAirTimeFairnessPolicyConfigTable OBJECT-TYPE
    SYNTAX          SEQUENCE OF CLQosAirTimeFairnessPolicyConfigEntry
    MAX-ACCESS      not-accessible
    STATUS          current
    DESCRIPTION
        "This table represents the AirTimeFairness Policy configuration
        sent by the controller to the LWAPP APs for their operation.
        This table doesn't have any dependencies on other existing
        tables.  By defining cLAirTimeFairnessPolicyid, the unique
        identifier for a Policy configuration.Rows are added or deleted
        by explicit management actions initiated by the user from a network
        management station through the cLAirTimeFairnessPolicyRowStatus
        object."
    ::= { cLQoSAirTimeFairness 6 }

cLQosAirTimeFairnessPolicyConfigEntry OBJECT-TYPE
    SYNTAX          CLQosAirTimeFairnessPolicyConfigEntry
    MAX-ACCESS      not-accessible
    STATUS          current
    DESCRIPTION
        "Each entry in this table represents the Police configuration
        sent by the controller to LWAPP APs for use during their
        operations. Entries can be added/deleted by explicit management
        actions by NMS or by user console."
    INDEX           { cLAirTimeFairnessPolicyId }
    ::= { cLQosAirTimeFairnessPolicyConfigTable 1 }

CLQosAirTimeFairnessPolicyConfigEntry ::= SEQUENCE {
        cLAirTimeFairnessPolicyId        INTEGER,
        cLAirTimeFairnessPolicyRowStatus RowStatus,
        cLAirTimeFairnessPolicyName      SnmpAdminString,
        cLAirTimeFairnessPolicyWeight    Unsigned32
}

cLAirTimeFairnessPolicyId OBJECT-TYPE
    SYNTAX          INTEGER (0..511)
    MAX-ACCESS      not-accessible
    STATUS          current
    DESCRIPTION
        "This object uniquely identifies one instance of a PolicyId
        on the controller."
    ::= { cLQosAirTimeFairnessPolicyConfigEntry 1 }

cLAirTimeFairnessPolicyRowStatus OBJECT-TYPE
    SYNTAX          RowStatus
    MAX-ACCESS      read-create
    STATUS          current
    DESCRIPTION
        "This is the status column for this row and used to create,
        modify and delete specific instances of rows in this table.
        This table supports modification of writable objects when the
        RowStatus is 'active'.The following objects are mandatory for
        successful creation of an entry:
                cLAirTimeFairnessPolicyName
                cLAirTimeFairnessPolicyWeight."
    ::= { cLQosAirTimeFairnessPolicyConfigEntry 2 }

cLAirTimeFairnessPolicyName OBJECT-TYPE
    SYNTAX          SnmpAdminString (SIZE  (1..64))
    MAX-ACCESS      read-create
    STATUS          current
    DESCRIPTION
        "This object represents the profile name assigned to this
        Policy. The name assigned to a Policy has to be unique across
        all the Policy on the controller.This object cannot be modified
        when cLWlanRowStatus is 'active'."
    ::= { cLQosAirTimeFairnessPolicyConfigEntry 3 }

cLAirTimeFairnessPolicyWeight OBJECT-TYPE
    SYNTAX          Unsigned32
    MAX-ACCESS      read-create
    STATUS          current
    DESCRIPTION
        "This object represents the Policy Weight assigned to this
        PolicyId/PolicyName.PolicyId=0 is default policy ID with weight
        10. We will not be able to configure/modify/delete this Policy.
        This object cannot be modified when cLWlanRowStatus is 'active'."
    ::= { cLQosAirTimeFairnessPolicyConfigEntry 4 }



cLApAirTimeFairnessPolicyOverrideTable OBJECT-TYPE
    SYNTAX          SEQUENCE OF CLApAirTimeFairnessPolicyOverrideEntry
    MAX-ACCESS      not-accessible
    STATUS          current
    DESCRIPTION
        "This table represents Per-AP, Per-Radio, Per-WlanId
        Override of ATF Policy ID on WLAN."
    ::= { cLQoSAirTimeFairness 7 }

cLApAirTimeFairnessPolicyOverrideEntry OBJECT-TYPE
    SYNTAX          CLApAirTimeFairnessPolicyOverrideEntry
    MAX-ACCESS      not-accessible
    STATUS          current
    DESCRIPTION
        "This entry contains AirTime fairness Policy Id Override
        on WLAN."
    INDEX           {
                        cLApSysMacAddress,
                        cLApDot11IfSlotId,
                        cLWlanProfileName
                    }
    ::= { cLApAirTimeFairnessPolicyOverrideTable 1 }

CLApAirTimeFairnessPolicyOverrideEntry ::= SEQUENCE {
        cLApAirTimeFairnessPolicyOverride     TruthValue,
        cLApAirTimeFairnessOverridePolicyName SnmpAdminString
}

cLApAirTimeFairnessPolicyOverride OBJECT-TYPE
    SYNTAX          TruthValue
    MAX-ACCESS      read-write
    STATUS          current
    DESCRIPTION
        "This object specifies Air time fairness policy override per
        AP(ATF supported APs) per Radio per WlanProfileName for policy
        Id assigned to WLAN."
    ::= { cLApAirTimeFairnessPolicyOverrideEntry 1 }

cLApAirTimeFairnessOverridePolicyName OBJECT-TYPE
    SYNTAX          SnmpAdminString (SIZE  (1..64))
    MAX-ACCESS      read-write
    STATUS          current
    DESCRIPTION
        "his object represents  the PolicyName changed for the given
        WLAN, if cLApAirTimeFairnessPolicyOverride is enabled per AP
        per slot per wlan profilename. Please note that this will not
        change the global PolicyName on the WLAN on the WLC  in the VAP."
    ::= { cLApAirTimeFairnessPolicyOverrideEntry 2 }

cLAPGroupsAirTimeFairnessPolicyOverrideTable OBJECT-TYPE
    SYNTAX          SEQUENCE OF CLAPGroupsAirTimeFairnessPolicyOverrideEntry
    MAX-ACCESS      not-accessible
    STATUS          current
    DESCRIPTION
        "This table represents Per-APGroup, Per-WlanId
        Override of ATF Policy ID on WLAN."
    ::= { cLQoSAirTimeFairness 8 }

cLAPGroupsAirTimeFairnessPolicyOverrideEntry OBJECT-TYPE
    SYNTAX          CLAPGroupsAirTimeFairnessPolicyOverrideEntry
    MAX-ACCESS      not-accessible
    STATUS          current
    DESCRIPTION
        "This entry contains AirTime fairness Policy Name Override
        on APGroup per cLWlanProfileName."
    INDEX           {
                        cLApDot11IfType,
                        cLAPGroupName,
                        cLWlanProfileName
                    }
    ::= { cLAPGroupsAirTimeFairnessPolicyOverrideTable 1 }

CLAPGroupsAirTimeFairnessPolicyOverrideEntry ::= SEQUENCE {
        cLAPGroupAirTimeFairnessPolicyNameOverrideEnabled TruthValue,
        cLAPGroupAirTimeFairnessOverridePolicyName        SnmpAdminString
}

cLAPGroupAirTimeFairnessPolicyNameOverrideEnabled OBJECT-TYPE
    SYNTAX          TruthValue
    MAX-ACCESS      read-write
    STATUS          current
    DESCRIPTION
        "This object represents the per APGroup per Wlan ProfileName
        level Policy override parameters.If configured as True, user
        can override the global PolicyName by providing individual new
        cLApAirTimeFairnessOverridePolicyName per APGroup per Wlan
        ProfileName level.If configured as False, the
        cLAPGroupAirTimeFairnessOverridePolicyName will be configured
        with global policyName assigned at WlanId level."
    DEFVAL          { false }
    ::= { cLAPGroupsAirTimeFairnessPolicyOverrideEntry 1 }

cLAPGroupAirTimeFairnessOverridePolicyName OBJECT-TYPE
    SYNTAX          SnmpAdminString (SIZE  (1..64))
    MAX-ACCESS      read-write
    STATUS          current
    DESCRIPTION
        "This object represents  the PolicyName changed for the given
        WLAN, if cLAPGroupAirTimeFairnessPolicyNameOverrideEnabled is
        enabled per AP Group.Please note that this will not change the
        global PolicyName on the WLAN on the WLC  in the VAP."
    ::= { cLAPGroupsAirTimeFairnessPolicyOverrideEntry 2 }

cLQCacConfigThreshold  OBJECT IDENTIFIER
     ::= { cLQCacThreshold 1 }

cLQCacIPLearnQHighThreshold OBJECT-TYPE
     SYNTAX          INTEGER
     MAX-ACCESS      read-write
     STATUS          current
     DESCRIPTION
         "This object specifies the high threshold value
         configured for the Iplearn_Queue. "
     ::= { cLQCacConfigThreshold 1 }

cLQCacOutstandingAAAReqQHighThreshold OBJECT-TYPE
     SYNTAX          INTEGER
     MAX-ACCESS      read-write
     STATUS          current
     DESCRIPTION
         "This object specifies the high threshold value 
         configured for the AAA outstanding request Queue."
     ::= { cLQCacConfigThreshold 2 }

cLQCacIPCHighThreshold OBJECT-TYPE
     SYNTAX          INTEGER
     MAX-ACCESS      read-write
     STATUS          current
     DESCRIPTION
         "This object specifies high threshold percent
         configured for the IPC Resources "
     ::= { cLQCacConfigThreshold 3 }

cLQCacIPCLowThreshold OBJECT-TYPE
     SYNTAX          INTEGER
     MAX-ACCESS      read-write
     STATUS          current
     DESCRIPTION
         "This object specifies low threshold percent
         configured for the IPC Resources"
     ::= { cLQCacConfigThreshold 4 }

cLQCacCPUHighThreshold OBJECT-TYPE
     SYNTAX          INTEGER
     MAX-ACCESS      read-write
     STATUS          current
     DESCRIPTION
         "This object specifies cpu threshold percent
         configured for the CPU Resources"
     ::= { cLQCacConfigThreshold 5 }     

cLQCacMobilityDiscoveryQHighThreshold OBJECT-TYPE
     SYNTAX          INTEGER
     MAX-ACCESS      read-write
     STATUS          current
     DESCRIPTION
         "This object specifies the high threshold value
         configured for the Mobility_Disovery_Queue. "
     ::= { cLQCacConfigThreshold 6 }
cLQCacStatistics  OBJECT IDENTIFIER
     ::= { cLQCacStats 1 }

cLQCacIPLearnQStats OBJECT-TYPE
     SYNTAX          INTEGER
     MAX-ACCESS      read-only
     STATUS          current
     DESCRIPTION
         "Total Number of CAC throttle due to IP Learn"
     ::= { cLQCacStatistics 1 }

cLQCacOutstandingAAAReqQStats OBJECT-TYPE
     SYNTAX          INTEGER
     MAX-ACCESS      read-only
     STATUS          current
     DESCRIPTION
         "Total Number of CAC throttle due to AAA"
     ::= { cLQCacStatistics 2 }

cLQCacIPCHighStats OBJECT-TYPE
     SYNTAX          INTEGER
     MAX-ACCESS      read-only
     STATUS          current
     DESCRIPTION
         "Total Number of CAC throttle due to IPC"
     ::= { cLQCacStatistics 3 }

-- ********************************************************************
-- *    NOTIFICATION Control objects
-- ********************************************************************

ciscoLwappVoipCallFailureNotifEnabled OBJECT-TYPE
    SYNTAX          TruthValue
    MAX-ACCESS      read-write
    STATUS          current
    DESCRIPTION
        "The object to control the generation of
        ciscoLwappVoipCallFailureNotif
        notification.

        A value of 'true' indicates that the agent generates
        ciscoLwappVoipCallFailureNotif notification.

        A value of 'false' indicates that the agent doesn't
        generate ciscoLwappVoipCallFailureNotif
        notification." 
    ::= { cLQConfigObjects 1 }

-- ********************************************************************
-- *    Notifications
-- ********************************************************************

ciscoLwappVoipCallFailureNotif NOTIFICATION-TYPE
    OBJECTS         {
                        cLQVoiceClientLastCallFailureReasonCode,
                        cLQVoiceClientCallingNumber,
                        cLQVoiceClientLastCalledNumber,
                        cLApName,
                        cLApDot11IfType
                    }
    STATUS          current
    DESCRIPTION
        "This notification is generated when ever a VOIP call failure
        occurs."
   ::= { ciscoLwappQosMIBNotifs 1 }

ciscoLwappMediaMCStreamFailureNotif NOTIFICATION-TYPE
    OBJECTS         {
                        cldcClientMacAddress,
                        cLQVMediaClientSrcIpAddr,
                        cLQVMediaClientSrcIpAddrType,
                        cLQVMediaClientDestIpAddr,
                        cLQVMediaClientDestIpAddrType,
                        cLQVMediaClientHistLastFailureReasonCode,
                        cLQVMediaClientHistTimeStamp,
                        cLQMStreamName,
                        cLApName,
                        cLApDot11IfType,
                        cLWlanIndex,
                        cLQVMediaClientHistCfgBw,
                        cLQVMediaClientHistCurrentRate,
                        cLQVMediaClientHistVideoPktSize,
                        cLQVMediaClientHistVideoUtil,
                        cLQVMediaClientHistVoiceUtil,
                        cLQVMediaClientHistChannelUtil,
                        cLQVMediaClientHistQueueUtil,
                        cLQVMediaClientHistVideoPps,
                        cLQVMediaClientHistVideoDelay,
                        cLQVMediaClientHistPktLossDiscard,
                        cLQVMediaClientHistPktLossFail,
                        cLQVMediaClientHistNumVideoStreams,
                        cLQVMediaClientHistCacEnable
                    }
    STATUS          current
    DESCRIPTION
        "This notification is generated when ever a multicast to unicast
        Media conversion failure occurs.  AP MAC Address and
        slotID will be sent as index for AP related objects."
   ::= { ciscoLwappQosMIBNotifs 2 }

ciscoLwappMediaMCStreamAdmitNotif NOTIFICATION-TYPE
    OBJECTS         {
                        cldcClientMacAddress,
                        cLQVMediaClientSrcIpAddr,
                        cLQVMediaClientSrcIpAddrType,
                        cLQVMediaClientDestIpAddr,
                        cLQVMediaClientDestIpAddrType,
                        cLQVMediaClientHistLastFailureReasonCode,
                        cLQVMediaClientHistTimeStamp,
                        cLQMStreamName,
                        cLApName,
                        cLApDot11IfType,
                        cLWlanIndex,
                        cLQVMediaClientHistCfgBw,
                        cLQVMediaClientHistCurrentRate,
                        cLQVMediaClientHistVideoPktSize,
                        cLQVMediaClientHistVideoUtil,
                        cLQVMediaClientHistVoiceUtil,
                        cLQVMediaClientHistChannelUtil,
                        cLQVMediaClientHistQueueUtil,
                        cLQVMediaClientHistVideoPps,
                        cLQVMediaClientHistVideoDelay,
                        cLQVMediaClientHistPktLossDiscard,
                        cLQVMediaClientHistPktLossFail,
                        cLQVMediaClientHistNumVideoStreams,
                        cLQVMediaClientHistCacEnable
                    }
    STATUS          current
    DESCRIPTION
        "This notification is generated when ever a client
        gets admitted to the stream.  AP MAC Address and
        slotID will be sent as index for AP related objects."
   ::= { ciscoLwappQosMIBNotifs 3 }

ciscoLwappMediaMCStreamDelistNotif NOTIFICATION-TYPE
    OBJECTS         {
                        cldcClientMacAddress,
                        cLQVMediaClientSrcIpAddr,
                        cLQVMediaClientSrcIpAddrType,
                        cLQVMediaClientDestIpAddr,
                        cLQVMediaClientDestIpAddrType,
                        cLQVMediaClientHistLastFailureReasonCode,
                        cLQVMediaClientHistTimeStamp,
                        cLQMStreamName,
                        cLApName,
                        cLApDot11IfType,
                        cLWlanIndex,
                        cLQVMediaClientHistCfgBw,
                        cLQVMediaClientHistCurrentRate,
                        cLQVMediaClientHistVideoPktSize,
                        cLQVMediaClientHistVideoUtil,
                        cLQVMediaClientHistVoiceUtil,
                        cLQVMediaClientHistChannelUtil,
                        cLQVMediaClientHistQueueUtil,
                        cLQVMediaClientHistVideoPps,
                        cLQVMediaClientHistVideoDelay,
                        cLQVMediaClientHistPktLossDiscard,
                        cLQVMediaClientHistPktLossFail,
                        cLQVMediaClientHistNumVideoStreams,
                        cLQVMediaClientHistCacEnable
                    }
    STATUS          current
    DESCRIPTION
        "This notification is generated when ever a client delists from the
        stream.  AP MAC Address and slotID will be sent as index for 
        AP related objects."
   ::= { ciscoLwappQosMIBNotifs 4 }
-- ********************************************************************

ciscoLwappQosMIBCompliances  OBJECT IDENTIFIER
    ::= { ciscoLwappQosMIBConform 1 }

ciscoLwappQosMIBGroups  OBJECT IDENTIFIER
    ::= { ciscoLwappQosMIBConform 2 }


ciscoLwappQosMIBCompliance MODULE-COMPLIANCE
    STATUS          deprecated
    DESCRIPTION
        "The compliance statement for the SNMP entities that
        implement the ciscoLwappQosMIB module."
    MODULE          -- this module
    MANDATORY-GROUPS {
                        ciscoLwappQosDot11aConfigGroup,
                        ciscoLwappQosDot11bConfigGroup,
                        ciscoLwappQosDot11WlanConfigGroup,
                        ciscoLwappQosDot11CacStatsGroup
                    }
    ::= { ciscoLwappQosMIBCompliances 1 }

ciscoLwappQosMIBComplianceRev1 MODULE-COMPLIANCE
    STATUS          deprecated
    DESCRIPTION
        "The compliance statement for the SNMP entities that
        implement the ciscoLwappQosMIB module."
    MODULE          -- this module
    MANDATORY-GROUPS {
                        ciscoLwappQosDot11aConfigGroup,
                        ciscoLwappQosDot11bConfigGroup,
                        ciscoLwappQosDot11WlanConfigGroup,
                        ciscoLwappQosDot11CacStatsGroup,
                        ciscoLwappQosDot11aConfigGroupSup1,
                        ciscoLwappQosDot11bConfigGroupSup1
                    }
    ::= { ciscoLwappQosMIBCompliances 2 }

ciscoLwappQosMIBComplianceRev2 MODULE-COMPLIANCE
    STATUS          deprecated
    DESCRIPTION
        "Implementation of this group is mandatory only for the
        platforms which implement the ciscoLwappQosMIB module."
    MODULE          -- this module
    MANDATORY-GROUPS {
                        ciscoLwappQosDot11aConfigGroup,
                        ciscoLwappQosDot11bConfigGroup,
                        ciscoLwappQosDot11WlanConfigGroup,
                        ciscoLwappQosDot11CacStatsGroup,
                        ciscoLwappQosDot11aConfigGroupSup1,
                        ciscoLwappQosDot11bConfigGroupSup1,
                        ciscoLwappQosDot11aConfigGroupSup2,
                        ciscoLwappQosDot11bConfigGroupSup2,
                        ciscoLwappQosDot11SipCacStatsGroup,
                        ciscoLwappQosDot11SipConfigGroup,
                        ciscoLwappQosDot11VoiceStatsGroup,
                        ciscoLwappQosDot11VoiceConfigGroup,
                        ciscoLwappQosDot11VoiceNotifGroup,
                        ciscoLwappQosConfigGroup
                    }
    ::= { ciscoLwappQosMIBCompliances 3 }

ciscoLwappQosMIBComplianceRev3 MODULE-COMPLIANCE
    STATUS          deprecated 
    DESCRIPTION
        "Implementation of this group is mandatory only for the
        platforms which implement the ciscoLwappQosMIB module."
    MODULE          -- this module
    MANDATORY-GROUPS {
                        ciscoLwappQosDot11aConfigGroup,
                        ciscoLwappQosDot11bConfigGroup,
                        ciscoLwappQosDot11WlanConfigGroup,
                        ciscoLwappQosDot11CacStatsGroup,
                        ciscoLwappQosDot11aConfigGroupSup1,
                        ciscoLwappQosDot11bConfigGroupSup1,
                        ciscoLwappQosDot11aConfigGroupSup2,
                        ciscoLwappQosDot11bConfigGroupSup2,
                        ciscoLwappQosDot11SipCacStatsGroup,
                        ciscoLwappQosDot11SipConfigGroup,
                        ciscoLwappQosDot11VoiceStatsGroup,
                        ciscoLwappQosDot11VoiceConfigGroup,
                        ciscoLwappQosDot11VoiceNotifGroup,
                        ciscoLwappQosConfigGroup,
                        ciscoLwappMediaClientGroup,
                        ciscoLwappMediaStreamConfigGroup,
                        ciscoLwappPreferredCallConfigGroup,
                        ciscoLwappQosDot11aConfigGroupSup3,
                        ciscoLwappQosDot11bConfigGroupSup3,
                        ciscoLwappQosDot11MediaNotifGroup
                    }
    ::= { ciscoLwappQosMIBCompliances 4 }

ciscoLwappQosMIBComplianceRev4 MODULE-COMPLIANCE
    STATUS          current
    DESCRIPTION
        "Implementation of this group is mandatory only for the
        platforms which implement the ciscoLwappQosMIB module."
    MODULE          -- this module
    MANDATORY-GROUPS {
                        ciscoLwappQosDot11aConfigGroup,
                        ciscoLwappQosDot11bConfigGroup,
                        ciscoLwappQosDot11axConfigGroup,
                        ciscoLwappQosDot11WlanConfigGroup,
                        ciscoLwappQosDot11CacStatsGroup,
                        ciscoLwappQosDot11aConfigGroupSup1,
                        ciscoLwappQosDot11bConfigGroupSup1,
                        ciscoLwappQosDot11aConfigGroupSup2,
                        ciscoLwappQosDot11bConfigGroupSup2,
                        ciscoLwappQosDot11SipCacStatsGroup,
                        ciscoLwappQosDot11SipConfigGroup,
                        ciscoLwappQosDot11VoiceStatsGroup,
                        ciscoLwappQosDot11VoiceConfigGroup,
                        ciscoLwappQosDot11VoiceNotifGroup,
                        ciscoLwappQosConfigGroup,
                        ciscoLwappMediaClientGroup,
                        ciscoLwappMediaStreamConfigGroup,
                        ciscoLwappPreferredCallConfigGroup,
                        ciscoLwappQosDot11aConfigGroupSup3,
                        ciscoLwappQosDot11bConfigGroupSup3,
                        ciscoLwappQosDot11axConfigGroupSup3,
                        ciscoLwappQosDot11MediaNotifGroup
                    }
    ::= { ciscoLwappQosMIBCompliances 5 }

-- ********************************************************************
-- *    Units of conformance
-- ********************************************************************

ciscoLwappQosDot11aConfigGroup OBJECT-GROUP
    OBJECTS         {
                        cLQd11aVoiceAdmCtrlSupport,
                        cLQd11aVoiceMaxAdmBandwidth,
                        cLQd11aVoiceMaxRoamBandwidth,
                        cLQd11aVideoAdmCtrlSupport,
                        cLQd11aVideoMaxAdmBandwidth,
                        cLQd11aVideoMaxRoamBandwidth,
                        cLQd11aGprProbeInterval
                    }
    STATUS          current
    DESCRIPTION
        "This collection of objects represents the
        quality-of-service parameters 802.11a networks."
    ::= { ciscoLwappQosMIBGroups 1 }

ciscoLwappQosDot11bConfigGroup OBJECT-GROUP
    OBJECTS         {
                        cLQd11bVoiceAdmCtrlSupport,
                        cLQd11bVoiceMaxAdmBandwidth,
                        cLQd11bVoiceMaxRoamBandwidth,
                        cLQd11bVideoAdmCtrlSupport,
                        cLQd11bVideoMaxAdmBandwidth,
                        cLQd11bVideoMaxRoamBandwidth,
                        cLQd11bGprProbeInterval
                    }
    STATUS          current
    DESCRIPTION
        "This collection of objects represents the
        quality-of-service parameters 802.11b networks."
    ::= { ciscoLwappQosMIBGroups 2 }

ciscoLwappQosDot11WlanConfigGroup OBJECT-GROUP
    OBJECTS         { cLQd11GprSupport }
    STATUS          current
    DESCRIPTION
        "This collection of objects represents the
        quality-of-services parameters on a particular WLAN."
    ::= { ciscoLwappQosMIBGroups 3 }

ciscoLwappQosDot11CacStatsGroup OBJECT-GROUP
    OBJECTS         {
                        cLQd11CacVoiceBwInUse,
                        cLQd11CacVideoBwInUse,
                        cLQd11CacVoiceCallsInProgress,
                        cLQd11CacRoamVoiceCallsInProg,
                        cLQd11CacTotalVoiceCallsAP,
                        cLQd11CacTotalRoamCallsAP,
                        cLQd11CacVoiceCallsRejectedAP,
                        cLQd11CacRoamCallsRejectedAP,
                        cLQd11CacRejCallsInsufBw,
                        cLQd11CacRejCallsBadParams,
                        cLQd11CacRejCallsPhyRate,
                        cLQd11CacRejCallsQosPolicy
                    }
    STATUS          current
    DESCRIPTION
        "This collection of objects provide the call
        admission control statistics observed on the
        dot11 interfaces of an AP."
    ::= { ciscoLwappQosMIBGroups 4 }

ciscoLwappQosDot11aConfigGroupSup1 OBJECT-GROUP
    OBJECTS         {
                        cLQd11aVoiceCtrl,
                        cLQd11aExpeditedBw
                    }
    STATUS          current
    DESCRIPTION
        "This collection of objects represents the
        quality-of-service parameters 802.11a networks."
    ::= { ciscoLwappQosMIBGroups 5 }

ciscoLwappQosDot11bConfigGroupSup1 OBJECT-GROUP
    OBJECTS         {
                        cLQd11bVoiceCtrl,
                        cLQd11bExpeditedBw
                    }
    STATUS          current
    DESCRIPTION
        "This collection of objects represents the
        quality-of-service parameters 802.11b networks."
    ::= { ciscoLwappQosMIBGroups 6 }

ciscoLwappQosDot11aConfigGroupSup2 OBJECT-GROUP
    OBJECTS         {
                        cLQd11aEdcaProfile,
                        cLQd11aMacOptimization,
                        cLQd11aMaxCallLimit
                    }
    STATUS          current
    DESCRIPTION
        "This collection of objects represents the
        quality-of-service parameters 802.11a networks."
    ::= { ciscoLwappQosMIBGroups 7 }

ciscoLwappQosDot11bConfigGroupSup2 OBJECT-GROUP
    OBJECTS         {
                        cLQd11bEdcaProfile,
                        cLQd11bMacOptimization,
                        cLQd11bMaxCallLimit
                    }
    STATUS          current
    DESCRIPTION
        "This collection of objects represents the
        quality-of-service parameters 802.11b networks."
    ::= { ciscoLwappQosMIBGroups 8 }

ciscoLwappQosDot11SipCacStatsGroup OBJECT-GROUP
    OBJECTS         {
                        cLQd11SipCacNonRoamCallsInProgress,
                        cLQd11SipCacRoamCallsInProg,
                        cLQd11SipCacTotalNonRoamCallsAP,
                        cLQd11SipCacTotalRoamCallsAP,
                        cLQd11SipCacNonRoamCallsRejectedInSuffBw,
                        cLQd11SipCacRoamCallsRejectedInSuffBw,
                        cLQd11SipCacNonRoamCallsRejectedMaxLimit,
                        cLQd11SipCacRoamCallsRejectedMaxLimit,
                        cLQd11SipCacRejCallsQosPolicy
                    }
    STATUS          current
    DESCRIPTION
        "This collection of objects provide the SIP call
        admission control statistics observed on the
        dot11 interfaces of an AP."
    ::= { ciscoLwappQosMIBGroups 9 }

ciscoLwappQosDot11SipConfigGroup OBJECT-GROUP
    OBJECTS         {
                        cLQd11SipCacConfigCodecType,
                        cLQd11SipCacConfigBw,
                        cLQd11SipCacConfigVoiceSampleSize
                    }
    STATUS          current
    DESCRIPTION
        "This collection of objects represents the
        SIP call admission control configuration parameters."
    ::= { ciscoLwappQosMIBGroups 10 }

ciscoLwappQosDot11VoiceStatsGroup OBJECT-GROUP
    OBJECTS         {
                        cLQd11VoiceCallCounts,
                        cLQd11CacVoiceCallTimePeriod
                    }
    STATUS          current
    DESCRIPTION
        "This collection of objects represents the
        Voice statistics parameters."
    ::= { ciscoLwappQosMIBGroups 11 }

ciscoLwappQosDot11VoiceConfigGroup OBJECT-GROUP
    OBJECTS         {
                        cLQVoiceWlanConfig,
                        cLQVoiceClientCallingNumber,
                        cLQVoiceClientLastCalledNumber,
                        cLQVoiceClientLastCallFailureReasonCode
                    }
    STATUS          current
    DESCRIPTION
        "This collection of objects represents the
        Voice statistics parameters."
    ::= { ciscoLwappQosMIBGroups 12 }

ciscoLwappQosDot11VoiceNotifGroup NOTIFICATION-GROUP
   NOTIFICATIONS    { ciscoLwappVoipCallFailureNotif }
    STATUS          current
    DESCRIPTION
        "This collection of objects represents the
        Voice notification parameters."
    ::= { ciscoLwappQosMIBGroups 13 }

ciscoLwappQosConfigGroup OBJECT-GROUP
    OBJECTS         { ciscoLwappVoipCallFailureNotifEnabled }
    STATUS          current
    DESCRIPTION
        "This collection of objects represents the
        quality-of-service configuration parameters."
    ::= { ciscoLwappQosMIBGroups 14 }

ciscoLwappMediaClientGroup OBJECT-GROUP
    OBJECTS         {
                        cLQVMediaClientSrcIpAddrType,
                        cLQVMediaClientSrcIpAddr,
                        cLQVMediaClientApMacAddress,
                        cLQVMediaClientWlanIndex,
                        cLQVMediaClientRadioType,
                        cLQVMediaClientQos,
                        cLQVMediaClientDecision,
                        cLQVMediaClientHistClientMacAddress,
                        cLQVMediaClientHistApMacAddress,
                        cLQVMediaClientHistSlotId,
                        cLQVMediaClientHistDestIpAddrType,
                        cLQVMediaClientHistDestIpAddr,
                        cLQVMediaClientHistDecision,
                        cLQVMediaClientHistLastFailureReasonCode,
                        cLQVMediaClientHistWlanIndex,
                        cLQVMediaClientHistRadioType,
                        cLQVMediaClientHistQos,
                        cLQVMediaClientHistCfgBw,
                        cLQVMediaClientHistCurrentRate,
                        cLQVMediaClientHistVideoPktSize,
                        cLQVMediaClientHistVideoUtil,
                        cLQVMediaClientHistVoiceUtil,
                        cLQVMediaClientHistChannelUtil,
                        cLQVMediaClientHistQueueUtil,
                        cLQVMediaClientHistVideoPps,
                        cLQVMediaClientHistVideoDelay,
                        cLQVMediaClientHistPktLossDiscard,
                        cLQVMediaClientHistPktLossFail,
                        cLQVMediaClientHistNumVideoStreams,
                        cLQVMediaClientHistCacEnable,
                        cLQVMediaClientHistStreamName
                    }
    STATUS          current
    DESCRIPTION
        "This collection of objects represents the
        Media client parameters."
    ::= { ciscoLwappQosMIBGroups 15 }

ciscoLwappMediaStreamConfigGroup OBJECT-GROUP
    OBJECTS         {
                        cLQMStreamRowStatus,
                        cLQMStreamSrcIPAddrType,
                        cLQMStreamSrcIPAddr,
                        cLQMStreamState,
                        cLQMStreamRrcExpBw,
                        cLQMStreamRrcAvgPkt,
                        cLQMStreamReRrc,
                        cLQMStreamRrcQos,
                        cLQMStreamRrcType,
                        cLQMStreamRrcPriority,
                        cLQMStreamRrcViolation,
                        cLQMStreamRrcPolicy,
                        cLQMStreamSdpUrl,
                        cLQMStreamSdpEmail,
                        cLQMStreamSdpPhone,
                        cLQMStreamSdpNote,
                        cLQMStreamSdpStatus,
                        cLQMStreamRrcGlobalState,
                        cLQMStreamDestStartInetAddrType,
                        cLQMStreamDestStartInetAddr,
                        cLQMStreamDestEndInetAddrType,
                        cLQMStreamDestEndInetAddr,
                        cLQMStreamStorageType
                    }
    STATUS          current
    DESCRIPTION
        "This collection of objects represents the
        Voice statistics parameters."
    ::= { ciscoLwappQosMIBGroups 16 }

ciscoLwappPreferredCallConfigGroup OBJECT-GROUP
    OBJECTS         {
                        cLQPreferredCallNumber,
                        cLQPreferredCallRowStatus,
                        cLQd11SipCacPreferredCallsReceived,
                        cLQd11SipCacPreferredCallsAccepted
                    }
    STATUS          current
    DESCRIPTION
        "This collection of objects represents the
        Preferred call config and staistics parameters."
    ::= { ciscoLwappQosMIBGroups 17 }

ciscoLwappQosDot11aConfigGroupSup3 OBJECT-GROUP
    OBJECTS         {
                        cLQd11aMcastDirectEnable,
                        cLQd11aBestEffortAdmission,
                        cLQd11aRedirectBestEffort,
                        cLQd11aRadioMaxStreams,
                        cLQd11aMaxVideoATPercent,
                        cLQd11aMaxVoiceATPercent,
                        cLQd11aMaxMediaATPercent,
                        cLQd11aMinPhyRate,
                        cLQd11aClientMaxStreams
                    }
    STATUS          current
    DESCRIPTION
        "This collection of objects represents the
        quality-of-service parameters 802.11a networks."
    ::= { ciscoLwappQosMIBGroups 18 }

ciscoLwappQosDot11bConfigGroupSup3 OBJECT-GROUP
    OBJECTS         {
                        cLQd11bMcastDirectEnable,
                        cLQd11bBestEffortAdmission,
                        cLQd11bRedirectBestEffort,
                        cLQd11bRadioMaxStreams,
                        cLQd11bMaxVideoATPercent,
                        cLQd11bMaxVoiceATPercent,
                        cLQd11bMaxMediaATPercent,
                        cLQd11bMinPhyRate,
                        cLQd11bClientMaxStreams
                    }
    STATUS          current
    DESCRIPTION
        "This collection of objects represents the
        quality-of-service parameters 802.11b networks."
    ::= { ciscoLwappQosMIBGroups 19 }

ciscoLwappQosDot11MediaNotifGroup NOTIFICATION-GROUP
   NOTIFICATIONS    {
                        ciscoLwappMediaMCStreamFailureNotif,
                        ciscoLwappMediaMCStreamAdmitNotif,
                        ciscoLwappMediaMCStreamDelistNotif
                    }
    STATUS          current
    DESCRIPTION
        "This collection of objects represents the
        Media notification parameters."
    ::= { ciscoLwappQosMIBGroups 20 }

ciscoLwappQosCacConfigGroup OBJECT-GROUP
     OBJECTS         {
                         cLQCacIPLearnQHighThreshold,
                         cLQCacOutstandingAAAReqQHighThreshold,
                         cLQCacIPCHighThreshold,
                         cLQCacIPCLowThreshold,
                         cLQCacMobilityDiscoveryQHighThreshold
                     }
     STATUS          current
     DESCRIPTION
         "This collection ob objects represents the  
         CAC Configured parameters."
     ::= { ciscoLwappQosMIBGroups 21 }

ciscoLwappQosCacStatsGroup OBJECT-GROUP
     OBJECTS         {
                         cLQCacIPLearnQStats,
                         cLQCacOutstandingAAAReqQStats,
                         cLQCacIPCHighStats
                     }
     STATUS          current
     DESCRIPTION
         "This collection ob objects represents the  
         CAC stats."
     ::= { ciscoLwappQosMIBGroups 22 }

ciscoLwappQosDot11axConfigGroup OBJECT-GROUP
    OBJECTS         {
                        cLQd11axVoiceAdmCtrlSupport,
                        cLQd11axVoiceMaxAdmBandwidth,
                        cLQd11axVoiceMaxRoamBandwidth,
                        cLQd11axEdcaProfile,
                        cLQd11axVoiceCtrl,
                        cLQd11axExpeditedBw,
                        cLQd11axSipCacSupportEnable
                    }
    STATUS          current
    DESCRIPTION
        "This collection of objects represents the
        quality-of-service parameters 802.11ax networks."
    ::= { ciscoLwappQosMIBGroups 23 }

ciscoLwappQosDot11axConfigGroupSup3 OBJECT-GROUP
    OBJECTS         {
                        cLQd11axMcastDirectEnable,
                        cLQd11axBestEffortAdmission,
                        cLQd11axRedirectBestEffort,
                        cLQd11axRadioMaxStreams,
                        cLQd11axMaxMediaATPercent,
                        cLQd11axMinPhyRate,
                        cLQd11axClientMaxStreams
                    }
    STATUS          current
    DESCRIPTION
        "This collection of objects represents the
        quality-of-service parameters 802.11ax networks."
    ::= { ciscoLwappQosMIBGroups 24 }

END

-----------------------------------------------------------------------
-- MIB table for H5521
--
-- v1.0 for firmware 9-5-0-0, 2017-04-19
-----------------------------------------------------------------------
H5521-MIB DEFINITIONS ::= BEGIN


IMPORTS
	enterprises
		FROM RFC1155-SMI
	OBJECT-TYPE
		FROM RFC-1212
	TRAP-TYPE
		FROM RFC-1215;

  DisplayString ::= OCTET STRING


comet      OBJECT IDENTIFIER ::= { enterprises 22626 }
products   OBJECT IDENTIFIER ::= { comet 1 }
h5521      OBJECT IDENTIFIER ::= { products 2 }
values     OBJECT IDENTIFIER ::= { h5521 1 }
global     OBJECT IDENTIFIER ::= { h5521 2 }
valuesInt  OBJECT IDENTIFIER ::= { h5521 3 }
settings   OBJECT IDENTIFIER ::= { h5521 4 }
traps      OBJECT IDENTIFIER ::= { h5521 5 }
tables	   OBJECT IDENTIFIER ::= { h5521 6 }


-----------------------------------------------------------------------
-- Measured values - String
-----------------------------------------------------------------------
co2 OBJECT-TYPE
	SYNTAX		DisplayString (SIZE (0..8))
	ACCESS		read-only
	STATUS		mandatory
	DESCRIPTION	"CO2 level"
::= { values 4 }

re1 OBJECT-TYPE
	SYNTAX  	DisplayString (SIZE (0..8))
	ACCESS		read-only
	STATUS		mandatory
	DESCRIPTION	"Relay 1 state; open, closed"
::= { values 8 }

re2 OBJECT-TYPE
	SYNTAX  	DisplayString (SIZE (0..8))
	ACCESS		read-only
	STATUS		mandatory
	DESCRIPTION	"Relay 2 state; open, closed"
::= { values 9 }

co2Alarm1 OBJECT-TYPE
	SYNTAX		DisplayString (SIZE (0..8))
	ACCESS		read-only
	STATUS		mandatory
	DESCRIPTION	"Alarm1 on CO2 level; none, active"
::= { values 13 }

co2Alarm2 OBJECT-TYPE
	SYNTAX		DisplayString (SIZE (0..8))
	ACCESS		read-only
	STATUS		mandatory
	DESCRIPTION	"Alarm2 on CO2 level; none, active"
::= { values 17 }

co2Unit OBJECT-TYPE
	SYNTAX  	DisplayString (SIZE (0..8))
	ACCESS		read-only
	STATUS		mandatory
	DESCRIPTION	"CO2 level Unit"
::= { values 24 }


-----------------------------------------------------------------------
-- Device informations
-----------------------------------------------------------------------
sensorName OBJECT-TYPE
	SYNTAX		DisplayString (SIZE (0..68))
	ACCESS		read-only
	STATUS		mandatory
	DESCRIPTION	"Device name"
::= { global 1 }

serialNumber OBJECT-TYPE
	SYNTAX		DisplayString (SIZE (0..16))
	ACCESS		read-only
	STATUS		mandatory
	DESCRIPTION	"Serial number"
::= { global 2 }

deviceType OBJECT-TYPE
	SYNTAX		INTEGER (0..65534)
	ACCESS		read-only
	STATUS		mandatory
	DESCRIPTION	"Device type"
::= { global 3 }


-----------------------------------------------------------------------
-- Measured values - Integer
-----------------------------------------------------------------------
co2Int OBJECT-TYPE
	SYNTAX		INTEGER (-5000..20000)
	ACCESS		read-only
	STATUS		mandatory
	DESCRIPTION	"CO2 level (value*X)"
::= { valuesInt 4 }

re1Int OBJECT-TYPE
	SYNTAX		INTEGER (0..1)
	ACCESS		read-only
	STATUS		mandatory
	DESCRIPTION	"Relay 1 state"
::= { valuesInt 8 }

re2Int OBJECT-TYPE
	SYNTAX		INTEGER (0..1)
	ACCESS		read-only
	STATUS		mandatory
	DESCRIPTION	"Relay 2 state"
::= { valuesInt 9 }

co2Alarm1Int OBJECT-TYPE
	SYNTAX		INTEGER (0..1)
	ACCESS		read-only
	STATUS		mandatory
	DESCRIPTION	"Alarm1 on CO2 level"
::= { valuesInt 13 }

co2Alarm2Int OBJECT-TYPE
	SYNTAX		INTEGER (0..1)
	ACCESS		read-only
	STATUS		mandatory
	DESCRIPTION	"Alarm2 on CO2 level"
::= { valuesInt 17 }


-----------------------------------------------------------------------
-- Alarm settings
-----------------------------------------------------------------------
co2Lim1Int OBJECT-TYPE
	SYNTAX		INTEGER (-5000..20000)
	ACCESS		read-only
	STATUS		mandatory
	DESCRIPTION	"CO2 level Alarm1 Limit (value*X)"
::= { settings 4 }

co2Lim2Int OBJECT-TYPE
	SYNTAX		INTEGER (-5000..20000)
	ACCESS		read-only
	STATUS		mandatory
	DESCRIPTION	"CO2 level Alarm2 Limit (value*X)"
::= { settings 8 }

co2Hyst1Int OBJECT-TYPE
	SYNTAX		INTEGER (0..10000)
	ACCESS		read-only
	STATUS		mandatory
	DESCRIPTION	"CO2 level Alarm1 Hysteresis (value*X)"
::= { settings 12 }

co2Hyst2Int OBJECT-TYPE
	SYNTAX		INTEGER (0..10000)
	ACCESS		read-only
	STATUS		mandatory
	DESCRIPTION	"CO2 level Alarm2 Hysteresis (value*X)"
::= { settings 16 }

co2Delay1Int OBJECT-TYPE
	SYNTAX		INTEGER (0..30000)
	ACCESS		read-only
	STATUS		mandatory
	DESCRIPTION	"CO2 level Alarm1 Delay [sec]"
::= { settings 20 }

co2Delay2Int OBJECT-TYPE
	SYNTAX		INTEGER (0..30000)
	ACCESS		read-only
	STATUS		mandatory
	DESCRIPTION	"CO2 level Alarm2 Delay [sec]"
::= { settings 24 }

co2Type1Int OBJECT-TYPE
	SYNTAX		INTEGER (0..2)
	ACCESS		read-only
	STATUS		mandatory
	DESCRIPTION	"CO2 level Alarm1 Type; 0-disbaled, 1-low, 2-high"
::= { settings 28 }

co2Type2Int OBJECT-TYPE
	SYNTAX		INTEGER (0..2)
	ACCESS		read-only
	STATUS		mandatory
	DESCRIPTION	"CO2 level Alarm2 Type; 0-disbaled, 1-low, 2-high"
::= { settings 32 }


-----------------------------------------------------------------------
-- Trap message
-----------------------------------------------------------------------
messageString OBJECT-TYPE
	SYNTAX		DisplayString (SIZE (0..32))
	ACCESS		read-only
	STATUS		mandatory
	DESCRIPTION	"Message giving more detailed information on trap"
::= { traps 1 }


-----------------------------------------------------------------------
-- Tables
-----------------------------------------------------------------------
historyTable OBJECT-TYPE
	SYNTAX		SEQUENCE OF HistoryEntry
	ACCESS		not-accessible
	STATUS		mandatory
	DESCRIPTION	"Table of the history values"
::= { tables 1 }

historyEntry OBJECT-TYPE
	SYNTAX		HistoryEntry
	ACCESS		not-accessible
	STATUS		optional
	DESCRIPTION	"History values entries"
	INDEX		{ histCO2 }
::= { historyTable 1 }

HistoryEntry ::=
	SEQUENCE {
		histCO2
			INTEGER
		}

histCO2 OBJECT-TYPE
	SYNTAX		INTEGER(-5000..20000)
	ACCESS		read-only
	STATUS		mandatory
	DESCRIPTION	"CO2 level reading"
::= { historyEntry 4 }


-----------------------------------------------------------------------
-- Traps definition
-----------------------------------------------------------------------

trapTest TRAP-TYPE
	ENTERPRISE	comet
	VARIABLES	{ sensorName, messageString }
	DESCRIPTION	"Testing trap, testing trap by TSensor software"
	::= 0

trapNTPError TRAP-TYPE
	ENTERPRISE	comet
	VARIABLES	{ sensorName, messageString }
	DESCRIPTION	"Error on time synchronisation via NTP"
	::= 1

trapEmailErrLogin TRAP-TYPE
	ENTERPRISE	comet
	VARIABLES	{ sensorName, messageString }
	DESCRIPTION	"SMTP error - unknown server"
	::= 2

trapEmailErrAuth TRAP-TYPE
	ENTERPRISE	comet
	VARIABLES	{ sensorName, messageString }
	DESCRIPTION	"SMTP error - authentication error"
	::= 3

trapEmailErrSome TRAP-TYPE
	ENTERPRISE	comet
	VARIABLES	{ sensorName, messageString }
	DESCRIPTION	"SMTP error - error during communication with server, unexpected return code"
	::= 4

trapEmailErrSocket TRAP-TYPE
	ENTERPRISE	comet
	VARIABLES	{ sensorName, messageString }
	DESCRIPTION	"SMTP error - socket error, server is not available"
	::= 5

trapEmailErrDNS TRAP-TYPE
	ENTERPRISE	comet
	VARIABLES	{ sensorName, messageString }
	DESCRIPTION	"SMTP error - DNS error"
	::= 6

trapSOAPErrFile TRAP-TYPE
	ENTERPRISE	comet
	VARIABLES	{ sensorName, messageString }
	DESCRIPTION	"SOAP error - file SOAP not found"
	::= 7

trapSOAPErrDNS TRAP-TYPE
	ENTERPRISE	comet
	VARIABLES	{ sensorName, messageString }
	DESCRIPTION	"SOAP error - DNS error"
	::= 8

trapSOAPErrSocket TRAP-TYPE
	ENTERPRISE	comet
	VARIABLES	{ sensorName, messageString }
	DESCRIPTION	"SOAP error - socket error, server is not available"
	::= 9

trapSOAPErrDelivery TRAP-TYPE
	ENTERPRISE	comet
	VARIABLES	{ sensorName, messageString }
	DESCRIPTION	"SOAP error - delivery error, wrong return code from server"
	::= 10

trapCO2Alarm1 TRAP-TYPE
	ENTERPRISE	comet
	VARIABLES	{ sensorName, messageString, co2, co2Alarm1Int }
	DESCRIPTION	"Trap for alarm1 on CO2 level"
	::= 14

trapCO2Alarm2 TRAP-TYPE
	ENTERPRISE	comet
	VARIABLES	{ sensorName, messageString, co2, co2Alarm2Int }
	DESCRIPTION	"Trap for alarm2 on CO2 level"
	::= 24

trapCO2ClrAlarm1 TRAP-TYPE
	ENTERPRISE	comet
	VARIABLES	{ sensorName, messageString, co2, co2Alarm1Int }
	DESCRIPTION	"Trap for clearing alarm 1 on CO2 level"
	::= 34

trapCO2ClrAlarm2 TRAP-TYPE
	ENTERPRISE	comet
	VARIABLES	{ sensorName, messageString, co2, co2Alarm2Int }
	DESCRIPTION	"Trap for clearing alarm 2 on CO2 level"
	::= 44

trapRelay1Closed TRAP-TYPE
	ENTERPRISE	comet
	VARIABLES	{ sensorName, messageString, re1Int }
	DESCRIPTION	"Trap for closed Relay 1"
	::= 70

trapRelay2Closed TRAP-TYPE
	ENTERPRISE	comet
	VARIABLES	{ sensorName, messageString, re2Int }
	DESCRIPTION	"Trap for closed Relay 2"
	::= 71

trapRelay1Open TRAP-TYPE
	ENTERPRISE	comet
	VARIABLES	{ sensorName, messageString, re1Int }
	DESCRIPTION	"Trap for open Relay 1"
	::= 72

trapRelay2Open TRAP-TYPE
	ENTERPRISE	comet
	VARIABLES	{ sensorName, messageString, re2Int }
	DESCRIPTION	"Trap for open Relay 2"
	::= 73

trapAcousticActivated TRAP-TYPE
	ENTERPRISE	comet
	VARIABLES	{ sensorName, messageString }
	DESCRIPTION	"Trap for activated acoustic"
	::= 74

trapAcousticDeactivated TRAP-TYPE
	ENTERPRISE	comet
	VARIABLES	{ sensorName, messageString }
	DESCRIPTION	"Trap for deactivated acoustic"
	::= 75


END

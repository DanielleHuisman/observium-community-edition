COMMEND-SIP-MIB DEFINITIONS ::= BEGIN

IMPORTS
	MODULE-IDENTITY,
	OBJECT-TYPE,
	NOTIFICATION-TYPE,
	Integer32,
	enterprises FROM SNMPv2-SMI;

commend MODULE-IDENTITY
	LAST-UPDATED "201205160000Z"
	ORGANIZATION "Commend International GmbH"
	CONTACT-INFO "Commend International GmbH"
	DESCRIPTION
		"MIB for Commend SIP Terminals"
	REVISION "201205160000Z"
	DESCRIPTION
		"Initial revision"
	::= { enterprises 37568 }

commendStationObjects OBJECT IDENTIFIER ::= { commend 2 }

commendStationObjectEntry OBJECT IDENTIFIER ::= { commendStationObjects 1 }

commendStationObjectStatusNotifications NOTIFICATION-TYPE
	STATUS current
	DESCRIPTION
		"Status Notifications"
	::= {commendStationObjects 10 }

commendStationApplicationStart NOTIFICATION-TYPE
	STATUS current
	DESCRIPTION
		"Application started"
	::= {commendStationObjects 20 }

commendStationCommon OBJECT IDENTIFIER ::= {commendStationObjectEntry 1 }

commendStationCommonStationType OBJECT-TYPE
	SYNTAX OCTET STRING (SIZE(0..1024))
	MAX-ACCESS read-only
	STATUS current
	DESCRIPTION
		"Station Type"
	::= { commendStationCommon 1 }

commendStationCommonStationSubType OBJECT-TYPE
	SYNTAX OCTET STRING (SIZE(0..1024))
	MAX-ACCESS read-only
	STATUS current
	DESCRIPTION
		"Station Subtype"
	::= { commendStationCommon 2 }

commendStationCommonStationSoftwareVersion OBJECT-TYPE
	SYNTAX OCTET STRING (SIZE(0..1024))
	MAX-ACCESS read-only
	STATUS current
	DESCRIPTION
		"Software Version"
	::= { commendStationCommon 3 }

commendStationCommonStationHardwareVersion OBJECT-TYPE
	SYNTAX OCTET STRING (SIZE(0..1024))
	MAX-ACCESS read-only
	STATUS current
	DESCRIPTION
		"Hardware Version"
	::= { commendStationCommon 4 }

commendStationCommonStationCallNumber OBJECT-TYPE
	SYNTAX OCTET STRING (SIZE(0..1024))
	MAX-ACCESS read-only
	STATUS current
	DESCRIPTION
		"System Call Number"
	::= { commendStationCommon 10 }

commendStationCommonStationStationName OBJECT-TYPE
	SYNTAX OCTET STRING (SIZE(0..1024))
	MAX-ACCESS read-only
	STATUS current
	DESCRIPTION
		"System StationName"
	::= { commendStationCommon 11 }

commendStationCommonStationLocation OBJECT-TYPE
	SYNTAX OCTET STRING (SIZE(0..1024))
	MAX-ACCESS read-only
	STATUS current
	DESCRIPTION
		"Flash Config Location"
	::= { commendStationCommon 12 }

commendStationCommonStationSystemState OBJECT-TYPE
	SYNTAX OCTET STRING (SIZE(0..1024))
	MAX-ACCESS read-only
	STATUS current
	DESCRIPTION
		""
	::= { commendStationCommon 20 }

commendStationCommonStationNtpState OBJECT-TYPE
	SYNTAX OCTET STRING (SIZE(0..1024))
	MAX-ACCESS read-only
	STATUS current
	DESCRIPTION
		"NTP synchronization state"
	::= { commendStationCommon 25 }

commendStationCommonStationNtpNotification NOTIFICATION-TYPE
    	STATUS current
    	DESCRIPTION
    		"NTP synchronization notification"
    	::= {commendStationCommon 26 }

commendStationCommonStationSequenceName OBJECT-TYPE
	SYNTAX OCTET STRING (SIZE(0..1024))
	MAX-ACCESS read-only
	STATUS current
	DESCRIPTION
		"System Sequence Name"
	::= { commendStationCommon 30 }

commendStationCommonStationCallState OBJECT-TYPE
	SYNTAX OCTET STRING (SIZE(0..1024))
	MAX-ACCESS read-only
	STATUS current
	DESCRIPTION
		""
	::= { commendStationCommon 80 }

commendStationConnectivity OBJECT IDENTIFIER ::= {commendStationObjectEntry 2 }

commendStationConnectivityType OBJECT-TYPE
	SYNTAX Integer32
	MAX-ACCESS read-only
	STATUS current
	DESCRIPTION
		""
	::= { commendStationConnectivity 1 }

commendStationConnectivityAnalog OBJECT IDENTIFIER ::= {commendStationConnectivity 2 }
commendStationConnectivityDigital OBJECT IDENTIFIER ::= {commendStationConnectivity 3 }
commendStationConnectivityIp OBJECT IDENTIFIER ::= {commendStationConnectivity 4 }
commendStationConnectivitySip OBJECT IDENTIFIER ::= {commendStationConnectivity 5 }

commendStationConnectivitySipPrimaryRegistration OBJECT-TYPE
	SYNTAX OCTET STRING (SIZE(0..1024))
	MAX-ACCESS read-only
	STATUS current
	DESCRIPTION
		"Registration State"
	::= { commendStationConnectivitySip 1 }

commendStationConnectivitySipPrimaryLastRegistration OBJECT-TYPE
	SYNTAX OCTET STRING (SIZE(0..1024))
	MAX-ACCESS read-only
	STATUS current
	DESCRIPTION
		"Last Registration"
	::= { commendStationConnectivitySip 2 }

commendStationConnectivitySipDhcp OBJECT-TYPE
	SYNTAX OCTET STRING (SIZE(0..1024))
	MAX-ACCESS read-only
	STATUS current
	DESCRIPTION
		""
	::= { commendStationConnectivitySip 3 }

commendStationConnectivitySipDns OBJECT-TYPE
	SYNTAX OCTET STRING (SIZE(0..1024))
	MAX-ACCESS read-only
	STATUS current
	DESCRIPTION
		""
	::= { commendStationConnectivitySip 4 }

commendStationConnectivitySipAccount OBJECT-TYPE
    	SYNTAX OCTET STRING (SIZE(0..1024))
    	MAX-ACCESS read-only
    	STATUS current
    	DESCRIPTION
    		""
    	::= { commendStationConnectivitySip 5 }

commendStationConnectivitySipAccountTable OBJECT-TYPE
    SYNTAX      SEQUENCE OF AccountTableEntry
    MAX-ACCESS  not-accessible
    STATUS      current
    DESCRIPTION
    "This table contains information about all
    configured sip accounts on this device."
    ::= { commendStationConnectivitySip 40 }

accountTableEntry OBJECT-TYPE
    SYNTAX      AccountTableEntry
    MAX-ACCESS  not-accessible
    STATUS      current
    DESCRIPTION
    "A row describing a given sip account table entry."
    INDEX   { accountNumber }
    ::= {commendStationConnectivitySipAccountTable 1 }

AccountTableEntry ::= SEQUENCE {
    accountNumber       OCTET STRING,
    accountDisplayName  OCTET STRING,
    accountUserId 	    OCTET STRING,
    accountServer 	    OCTET STRING,
    accountState        OCTET STRING
}

accountNumber OBJECT-TYPE
    SYNTAX      OCTET STRING (SIZE(1..32))
    MAX-ACCESS  read-only
    STATUS      current
    DESCRIPTION
    "Internal account ID."
    ::= { accountTableEntry 1 }

accountDisplayName OBJECT-TYPE
    SYNTAX      OCTET STRING (SIZE(1..32))
    MAX-ACCESS  read-only
    STATUS      current
    DESCRIPTION
    "SIP Display Name."
    ::= { accountTableEntry 2 }

accountUserId OBJECT-TYPE
    SYNTAX      OCTET STRING
    MAX-ACCESS  read-only
    STATUS      current
    DESCRIPTION
    "User name used for SIP registration."
    ::= { accountTableEntry 3 }

accountServer OBJECT-TYPE
    SYNTAX      OCTET STRING
    MAX-ACCESS  read-only
    STATUS      current
    DESCRIPTION
    "SIP server address"
    ::= { accountTableEntry 4 }

accountState OBJECT-TYPE
    SYNTAX      OCTET STRING
    MAX-ACCESS  read-only
    STATUS      current
    DESCRIPTION
    "Registration state of SIP account"
    ::= { accountTableEntry 5 }

commendStationConnectivitySipSecondaryRegistration OBJECT-TYPE
	SYNTAX OCTET STRING (SIZE(0..1024))
	MAX-ACCESS read-only
	STATUS current
	DESCRIPTION
		"Registration State"
	::= { commendStationConnectivitySip 10 }
commendStationConnectivitySipSecondaryLastRegistration OBJECT-TYPE
	SYNTAX OCTET STRING (SIZE(0..1024))
	MAX-ACCESS read-only
	STATUS current
	DESCRIPTION
		"Last Registration"
	::= { commendStationConnectivitySip 11 }
commendStationConnectivitySipTertiaryRegistration OBJECT-TYPE
	SYNTAX OCTET STRING (SIZE(0..1024))
	MAX-ACCESS read-only
	STATUS current
	DESCRIPTION
		"Registration State"
	::= { commendStationConnectivitySip 20 }
commendStationConnectivitySipTertiaryLastRegistration OBJECT-TYPE
	SYNTAX OCTET STRING (SIZE(0..1024))
	MAX-ACCESS read-only
	STATUS current
	DESCRIPTION
		"Last Registration"
	::= { commendStationConnectivitySip 21 }


commendStationAudio OBJECT IDENTIFIER ::= {commendStationObjectEntry 3 }
commendStationAudioMic1 OBJECT IDENTIFIER ::= {commendStationAudio 1 }
commendStationAudioMic2 OBJECT IDENTIFIER ::= {commendStationAudio 2 }
commendStationAudioMic3 OBJECT IDENTIFIER ::= {commendStationAudio 3 }
commendStationAudioLsMic OBJECT IDENTIFIER ::= {commendStationAudio 4 }
commendStationAudiomonitoring OBJECT IDENTIFIER ::= {commendStationAudio 5 }

commendStationAudioLsMicStatus OBJECT-TYPE
	SYNTAX OCTET STRING (SIZE(0..1024))
	MAX-ACCESS read-only
	STATUS current
	DESCRIPTION
		"LS/Mic Surveillance Status"
	::= { commendStationAudioLsMic 1 }

commendStationAudiomonitoringStatus OBJECT-TYPE
	SYNTAX OCTET STRING (SIZE(0..1024))
	MAX-ACCESS read-only
	STATUS current
	DESCRIPTION
		"Audiomonitoring Status"
	::= { commendStationAudiomonitoring 1 }

commendStationAudioMic1Type OBJECT-TYPE
	SYNTAX OCTET STRING (SIZE(0..1024))
	MAX-ACCESS read-only
	STATUS current
	DESCRIPTION
		"Microphonetype"
	::= { commendStationAudioMic1 1 }

commendStationAudioMic1Sensitivity OBJECT-TYPE
	SYNTAX OCTET STRING (SIZE(0..1024))
	MAX-ACCESS read-only
	STATUS current
	DESCRIPTION
		"Microphone Sensitivity"
	::= { commendStationAudioMic1 2 }

commendStationAudioAmp1 OBJECT IDENTIFIER ::= {commendStationAudio 10 }

commendStationAudioAmp1Type OBJECT-TYPE
	SYNTAX OCTET STRING (SIZE(0..1024))
	MAX-ACCESS read-only
	STATUS current
	DESCRIPTION
		"Amplifiertype"
	::= { commendStationAudioAmp1 1 }

commendStationAudioAmp1Sensitivity OBJECT-TYPE
	SYNTAX OCTET STRING (SIZE(0..1024))
	MAX-ACCESS read-only
	STATUS current
	DESCRIPTION
		"Amplifier Sensitivity"
	::= { commendStationAudioAmp1 2 }


commendStationAudioSpeakerCompressor OBJECT-TYPE
	SYNTAX OCTET STRING (SIZE(0..1024))
	MAX-ACCESS read-only
	STATUS current
	DESCRIPTION
		"Compressor Level"
	::= { commendStationAudioAmp1 3 }

commendStationAudioLsMicSurveillanceNotification NOTIFICATION-TYPE
	STATUS current
	DESCRIPTION
		"Ls/Mic Surveillance Notification"
	::= {commendStationAudio 11 }

commendStationAudioMonitoringAlarmNotification NOTIFICATION-TYPE
	STATUS current
	DESCRIPTION
		"Audio Monitoring Alarm Notification"
	::= {commendStationAudio 12 }

commendStationAudioAEC OBJECT IDENTIFIER ::= {commendStationAudio 50 }
commendStationAudioAECMode OBJECT-TYPE
	SYNTAX OCTET STRING (SIZE(0..1024))
	MAX-ACCESS read-only
	STATUS current
	DESCRIPTION
		"Adaptive Echo Canceller Mode"
	::= { commendStationAudioAEC 1 }

commendStationAudioNgClosedGain OBJECT-TYPE
	SYNTAX OCTET STRING (SIZE(0..1024))
	MAX-ACCESS read-only
	STATUS current
	DESCRIPTION
		"Noise Gate Closed Gain"
	::= { commendStationAudioAEC 2 }

commendStationAudioPgClosedGain OBJECT-TYPE
	SYNTAX OCTET STRING (SIZE(0..1024))
	MAX-ACCESS read-only
	STATUS current
	DESCRIPTION
		"Switched Duplex Closed Gain"
	::= { commendStationAudioAEC 3 }

commendStationAudioNgEnabled OBJECT-TYPE
	SYNTAX OCTET STRING (SIZE(0..1024))
	MAX-ACCESS read-only
	STATUS current
	DESCRIPTION
		"Noise Gate Enabled"
	::= { commendStationAudioAEC 4 }

commendStationAudioPgEnabled OBJECT-TYPE
	SYNTAX OCTET STRING (SIZE(0..1024))
	MAX-ACCESS read-only
	STATUS current
	DESCRIPTION
		"Switched Duplex Enabled"
	::= { commendStationAudioAEC 5 }

commendStationAudioNC OBJECT IDENTIFIER ::= {commendStationAudio 51 }
commendStationAudioNCMode OBJECT-TYPE
	SYNTAX OCTET STRING (SIZE(0..1024))
	MAX-ACCESS read-only
	STATUS current
	DESCRIPTION
		"Noise Canceller Mode"
	::= { commendStationAudioNC 1 }

commendStationInputs OBJECT IDENTIFIER ::= {commendStationObjectEntry 4 }

commendStationInputNotifications NOTIFICATION-TYPE
	STATUS current
	DESCRIPTION
		"Input Status Notifications"
	::= {commendStationInputs 9 }

commendStationInputButtonStuckNotification NOTIFICATION-TYPE
	STATUS current
	DESCRIPTION
		"Input Button Stuck Notifications"
	::= {commendStationInputNotifications 1 }

commendStationInputHandsetOffhookNotification NOTIFICATION-TYPE
	STATUS current
	DESCRIPTION
		"Handset Offhook Notifications"
	::= {commendStationInputNotifications 2 }

commendStationInputChangedNotification NOTIFICATION-TYPE
	STATUS current
	DESCRIPTION
		"Input Changed Notifications"
	::= {commendStationInputNotifications 3 }

commendStationInput1 OBJECT IDENTIFIER ::= {commendStationInputs 1 }

commendStationInput2 OBJECT IDENTIFIER ::= {commendStationInputs 2 }

commendStationInput3 OBJECT IDENTIFIER ::= {commendStationInputs 3 }

commendStationEB2E2AInput1 OBJECT IDENTIFIER ::= {commendStationInputs 4 }

commendStationEB2E2AInput2 OBJECT IDENTIFIER ::= {commendStationInputs 5 }

commendStationInputKeyboard OBJECT IDENTIFIER ::= {commendStationInputs 10 }

commendStationInputStatus OBJECT IDENTIFIER ::= {commendStationObjectEntry 5}

commendStationLastInputChange OBJECT-TYPE
	SYNTAX OCTET STRING (SIZE(0..1024))
	MAX-ACCESS read-only
	STATUS current
	DESCRIPTION
		"Last input changed information"
	::= { commendStationInputStatus 1 }

commendStationLastButtonStuck OBJECT-TYPE
	SYNTAX OCTET STRING (SIZE(0..1024))
	MAX-ACCESS read-only
	STATUS current
	DESCRIPTION
		""
	::= { commendStationInputStatus 2 }

commendStationInputKeyboardButton1 OBJECT-TYPE
	SYNTAX OCTET STRING (SIZE(0..1024))
	MAX-ACCESS read-only
	STATUS current
	DESCRIPTION
		""
	::= { commendStationInputKeyboard 1 }

commendStationInputKeyboardButton2 OBJECT-TYPE
	SYNTAX OCTET STRING (SIZE(0..1024))
	MAX-ACCESS read-only
	STATUS current
	DESCRIPTION
		""
	::= { commendStationInputKeyboard 2 }

commendStationInputKeyboardButton3 OBJECT-TYPE
	SYNTAX OCTET STRING (SIZE(0..1024))
	MAX-ACCESS read-only
	STATUS current
	DESCRIPTION
		""
	::= { commendStationInputKeyboard 3 }

commendStationInputFullKeyboard OBJECT IDENTIFIER ::= {commendStationInputs 11 }

commendStationInputFullKeyboardButton1 OBJECT-TYPE
	SYNTAX OCTET STRING (SIZE(0..1024))
	MAX-ACCESS read-only
	STATUS current
	DESCRIPTION
		""
	::= { commendStationInputFullKeyboard 1 }

commendStationInputFullKeyboardButton2 OBJECT-TYPE
	SYNTAX OCTET STRING (SIZE(0..1024))
	MAX-ACCESS read-only
	STATUS current
	DESCRIPTION
		""
	::= { commendStationInputFullKeyboard 2 }

commendStationInputFullKeyboardButton3 OBJECT-TYPE
	SYNTAX OCTET STRING (SIZE(0..1024))
	MAX-ACCESS read-only
	STATUS current
	DESCRIPTION
		""
	::= { commendStationInputFullKeyboard 3 }

commendStationInputFullKeyboardButton4 OBJECT-TYPE
	SYNTAX OCTET STRING (SIZE(0..1024))
	MAX-ACCESS read-only
	STATUS current
	DESCRIPTION
		""
	::= { commendStationInputFullKeyboard 4 }

commendStationInputFullKeyboardButton5 OBJECT-TYPE
	SYNTAX OCTET STRING (SIZE(0..1024))
	MAX-ACCESS read-only
	STATUS current
	DESCRIPTION
		""
	::= { commendStationInputFullKeyboard 5 }

commendStationInputFullKeyboardButton6 OBJECT-TYPE
	SYNTAX OCTET STRING (SIZE(0..1024))
	MAX-ACCESS read-only
	STATUS current
	DESCRIPTION
		""
	::= { commendStationInputFullKeyboard 6 }

commendStationInputFullKeyboardButton7 OBJECT-TYPE
	SYNTAX OCTET STRING (SIZE(0..1024))
	MAX-ACCESS read-only
	STATUS current
	DESCRIPTION
		""
	::= { commendStationInputFullKeyboard 7 }

commendStationInputFullKeyboardButton8 OBJECT-TYPE
	SYNTAX OCTET STRING (SIZE(0..1024))
	MAX-ACCESS read-only
	STATUS current
	DESCRIPTION
		""
	::= { commendStationInputFullKeyboard 8 }

commendStationInputFullKeyboardButton9 OBJECT-TYPE
	SYNTAX OCTET STRING (SIZE(0..1024))
	MAX-ACCESS read-only
	STATUS current
	DESCRIPTION
		""
	::= { commendStationInputFullKeyboard 9 }

commendStationInputFullKeyboardButton0 OBJECT-TYPE
	SYNTAX OCTET STRING (SIZE(0..1024))
	MAX-ACCESS read-only
	STATUS current
	DESCRIPTION
		""
	::= { commendStationInputFullKeyboard 10 }

commendStationInputFullKeyboardButtonX OBJECT-TYPE
	SYNTAX OCTET STRING (SIZE(0..1024))
	MAX-ACCESS read-only
	STATUS current
	DESCRIPTION
		""
	::= { commendStationInputFullKeyboard 11 }

commendStationInputFullKeyboardButtonT OBJECT-TYPE
	SYNTAX OCTET STRING (SIZE(0..1024))
	MAX-ACCESS read-only
	STATUS current
	DESCRIPTION
		""
	::= { commendStationInputFullKeyboard 12 }

commendStationInputFullKeyboardButtonUP OBJECT-TYPE
	SYNTAX OCTET STRING (SIZE(0..1024))
	MAX-ACCESS read-only
	STATUS current
	DESCRIPTION
		""
	::= { commendStationInputFullKeyboard 13 }

commendStationInputFullKeyboardButtonDOWN OBJECT-TYPE
	SYNTAX OCTET STRING (SIZE(0..1024))
	MAX-ACCESS read-only
	STATUS current
	DESCRIPTION
		""
	::= { commendStationInputFullKeyboard 14 }

commendStationInputFullKeyboardButtonMENU OBJECT-TYPE
	SYNTAX OCTET STRING (SIZE(0..1024))
	MAX-ACCESS read-only
	STATUS current
	DESCRIPTION
		""
	::= { commendStationInputFullKeyboard 15 }

commendStationInputFullKeyboardButtonENTER OBJECT-TYPE
	SYNTAX OCTET STRING (SIZE(0..1024))
	MAX-ACCESS read-only
	STATUS current
	DESCRIPTION
		""
	::= { commendStationInputFullKeyboard 16 }

commendStationInputType1 OBJECT-TYPE
	SYNTAX OCTET STRING (SIZE(0..1024))
	MAX-ACCESS read-only
	STATUS current
	DESCRIPTION
		""
	::= { commendStationInput1 1 }

commendStationInputState1 OBJECT-TYPE
	SYNTAX OCTET STRING (SIZE(0..1024))
	MAX-ACCESS read-only
	STATUS current
	DESCRIPTION
		""
	::= { commendStationInput1 2 }

commendStationInputType2 OBJECT-TYPE
	SYNTAX OCTET STRING (SIZE(0..1024))
	MAX-ACCESS read-only
	STATUS current
	DESCRIPTION
		""
	::= { commendStationInput2 1 }

commendStationInputState2 OBJECT-TYPE
	SYNTAX OCTET STRING (SIZE(0..1024))
	MAX-ACCESS read-only
	STATUS current
	DESCRIPTION
		""
	::= { commendStationInput2 2 }

commendStationInputType3 OBJECT-TYPE
	SYNTAX OCTET STRING (SIZE(0..1024))
	MAX-ACCESS read-only
	STATUS current
	DESCRIPTION
		""
	::= { commendStationInput3 1 }

commendStationInputState3 OBJECT-TYPE
	SYNTAX OCTET STRING (SIZE(0..1024))
	MAX-ACCESS read-only
	STATUS current
	DESCRIPTION
		""
	::= { commendStationInput3 2 }

commendStationEB2E2AInputType1 OBJECT-TYPE
	SYNTAX OCTET STRING (SIZE(0..1024))
	MAX-ACCESS read-only
	STATUS current
	DESCRIPTION
		""
	::= { commendStationEB2E2AInput1 1 }

commendStationEB2E2AInputState1 OBJECT-TYPE
	SYNTAX OCTET STRING (SIZE(0..1024))
	MAX-ACCESS read-only
	STATUS current
	DESCRIPTION
		""
	::= { commendStationEB2E2AInput1 2 }

commendStationEB2E2AInputType2 OBJECT-TYPE
	SYNTAX OCTET STRING (SIZE(0..1024))
	MAX-ACCESS read-only
	STATUS current
	DESCRIPTION
		""
	::= { commendStationEB2E2AInput2 1 }

commendStationEB2E2AInputState2 OBJECT-TYPE
	SYNTAX OCTET STRING (SIZE(0..1024))
	MAX-ACCESS read-only
	STATUS current
	DESCRIPTION
		""
	::= { commendStationEB2E2AInput2 2 }

commendStationInputTable OBJECT-TYPE
    SYNTAX      SEQUENCE OF InputTableEntry
    MAX-ACCESS  not-accessible
    STATUS      current
    DESCRIPTION
    "This table contains information about all inputs."
    ::= { commendStationInputs 20 }

inputTableEntry OBJECT-TYPE
    SYNTAX      AccountTableEntry
    MAX-ACCESS  not-accessible
    STATUS      current
    DESCRIPTION
    "A row describing a given input"
    INDEX   { inputName }
    ::= {commendStationInputTable 1 }

InputTableEntry ::= SEQUENCE {
    inputName    OCTET STRING,
    inputState   OCTET STRING
}

inputName OBJECT-TYPE
    SYNTAX      OCTET STRING (SIZE(1..32))
    MAX-ACCESS  not-accessible
    STATUS      current
    DESCRIPTION
    "Input name <product-id><serial-number><input number>."
    ::= { inputTableEntry 1 }

inputState OBJECT-TYPE
    SYNTAX      OCTET STRING (SIZE(1..32))
    MAX-ACCESS  not-accessible
    STATUS      current
    DESCRIPTION
    "State of the given input."
    ::= { inputTableEntry 2 }

commendStationOutputs OBJECT IDENTIFIER ::= {commendStationObjectEntry 5 }

commendStationOutput1 OBJECT IDENTIFIER ::= {commendStationOutputs 1 }

commendStationOutput2 OBJECT IDENTIFIER ::= {commendStationOutputs 2 }

commendStationEB2E2AOutput1 OBJECT IDENTIFIER ::= {commendStationOutputs 3 }

commendStationEB2E2AOutput2 OBJECT IDENTIFIER ::= {commendStationOutputs 4 }

commendStationOutputNotifications NOTIFICATION-TYPE
	STATUS current
	DESCRIPTION
		"Output Status Notifications"
	::= {commendStationOutputs 9 }

commendStationOutputChangedNotification NOTIFICATION-TYPE
	STATUS current
	DESCRIPTION
		"Output Changed Notifications"
	::= {commendStationOutputNotifications 1 }

commendStationOutput1Notifications NOTIFICATION-TYPE
	STATUS current
	DESCRIPTION
		"Output Status Notifications"
	::= {commendStationOutput1 10 }

commendStationOutput2Notifications NOTIFICATION-TYPE
	STATUS current
	DESCRIPTION
		"Output Status Notifications"
	::= {commendStationOutput2 10 }

commendStationEB2E2AOutput1Notifications NOTIFICATION-TYPE
	STATUS current
	DESCRIPTION
		"Output Status Notifications"
	::= {commendStationEB2E2AOutput1 10 }

commendStationEB2E2AOutput2Notifications NOTIFICATION-TYPE
	STATUS current
	DESCRIPTION
		"Output Status Notifications"
	::= {commendStationEB2E2AOutput2 10 }

commendStationOutputName1 OBJECT-TYPE
	SYNTAX OCTET STRING (SIZE(0..1024))
	MAX-ACCESS read-only
	STATUS current
	DESCRIPTION
		""
	::= { commendStationOutput1 1 }

commendStationOutputState1 OBJECT-TYPE
	SYNTAX OCTET STRING (SIZE(0..1024))
	MAX-ACCESS read-only
	STATUS current
	DESCRIPTION
		""
	::= { commendStationOutput1 2 }

commendStationOutputName2 OBJECT-TYPE
	SYNTAX OCTET STRING (SIZE(0..1024))
	MAX-ACCESS read-only
	STATUS current
	DESCRIPTION
		""
	::= { commendStationOutput2 1 }

commendStationOutputState2 OBJECT-TYPE
	SYNTAX OCTET STRING (SIZE(0..1024))
	MAX-ACCESS read-only
	STATUS current
	DESCRIPTION
		""
	::= { commendStationOutput2 2 }

commendStationEB2E2AOutputName1 OBJECT-TYPE
	SYNTAX OCTET STRING (SIZE(0..1024))
	MAX-ACCESS read-only
	STATUS current
	DESCRIPTION
		""
	::= { commendStationEB2E2AOutput1 1 }

commendStationEB2E2AOutputState1 OBJECT-TYPE
	SYNTAX OCTET STRING (SIZE(0..1024))
	MAX-ACCESS read-only
	STATUS current
	DESCRIPTION
		""
	::= { commendStationEB2E2AOutput1 2 }

commendStationEB2E2AOutputName2 OBJECT-TYPE
	SYNTAX OCTET STRING (SIZE(0..1024))
	MAX-ACCESS read-only
	STATUS current
	DESCRIPTION
		""
	::= { commendStationEB2E2AOutput2 1 }

commendStationEB2E2AOutputState2 OBJECT-TYPE
	SYNTAX OCTET STRING (SIZE(0..1024))
	MAX-ACCESS read-only
	STATUS current
	DESCRIPTION
		""
	::= { commendStationEB2E2AOutput2 2 }

commendStationOutputTable OBJECT-TYPE
    SYNTAX      SEQUENCE OF OutputTableEntry
    MAX-ACCESS  not-accessible
    STATUS      current
    DESCRIPTION
    "This table contains information about all outputs."
    ::= { commendStationOutputs 20 }

outputTableEntry OBJECT-TYPE
    SYNTAX      AccountTableEntry
    MAX-ACCESS  not-accessible
    STATUS      current
    DESCRIPTION
    "A row describing a given output"
    INDEX   { outputName }
    ::= {commendStationOutputTable 1 }

OutputTableEntry ::= SEQUENCE {
    outputName    OCTET STRING,
    outputState   OCTET STRING
}

outputName OBJECT-TYPE
    SYNTAX      OCTET STRING (SIZE(1..32))
    MAX-ACCESS  not-accessible
    STATUS      current
    DESCRIPTION
    "Output name <product-id><serial-number><output number>."
    ::= { outputTableEntry 1 }


outputState OBJECT-TYPE
    SYNTAX      OCTET STRING (SIZE(1..32))
    MAX-ACCESS  not-accessible
    STATUS      current
    DESCRIPTION
    "Output state."
    ::= { outputTableEntry 2 }

commendStationOutputStatus OBJECT IDENTIFIER ::= {commendStationObjectEntry 7}

commendStationLastOutputChange OBJECT-TYPE
	SYNTAX OCTET STRING (SIZE(0..1024))
	MAX-ACCESS read-only
	STATUS current
	DESCRIPTION
		"Last output changed"
	::= { commendStationOutputStatus 1 }

END

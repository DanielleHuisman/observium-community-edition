--
-- DFL-210 SMIv2 module
--

DFL210-MIB DEFINITIONS ::= BEGIN

IMPORTS
    MODULE-COMPLIANCE, OBJECT-GROUP
        FROM SNMPv2-CONF
    Counter32, Counter64, Gauge32, Integer32, MODULE-IDENTITY, 
    OBJECT-TYPE, enterprises
        FROM SNMPv2-SMI
    DisplayString
        FROM SNMPv2-TC;

dfl210-MIB MODULE-IDENTITY
    LAST-UPDATED "201009021139Z"
    ORGANIZATION 
        "D-Link Corporation"
    CONTACT-INFO 
        "Postal: D-Link Corporation
         No. 289, Sinhu 3rd Road,
         Neihu District, Taipei City 114,
         Taiwan, R.O.C.
         Tel: +886-2-66000123
         Fax: +886-2-55509988"
    DESCRIPTION 
        "The MIB module for D-Link DFL-210 series product."
    
    REVISION  "201009021139Z"
    DESCRIPTION 
        "Added 64-bit counters"
    REVISION  "201003300900Z"
    DESCRIPTION 
        "Added values for SMTP ALG objects."
    REVISION  "200911100916Z"
    DESCRIPTION 
        "Added values for opened and closed connections per second"
    REVISION  "200811181605Z"
    DESCRIPTION 
        "Added value for timer usage"
    REVISION  "200810141227Z"
    DESCRIPTION 
        "Added values for memory usage and TCP buffer usage"    
    REVISION  "200710310000Z"
    DESCRIPTION 
        "Initial version."
    ::= { dfl210MibModules 2 }


dlink OBJECT IDENTIFIER
    ::= { enterprises 171 }

netdefendMgmt OBJECT IDENTIFIER
    ::= { dlink 20 }

ipsFirewall OBJECT IDENTIFIER
    ::= { netdefendMgmt 1 }

dfl210 OBJECT IDENTIFIER
    ::= { ipsFirewall 1 }

dfl210OS OBJECT IDENTIFIER
    ::= { dfl210 1 }

dfl210OSStats OBJECT IDENTIFIER
    ::= { dfl210OS 2 }

dfl210reg OBJECT IDENTIFIER
    ::= { dfl210 2 }

dfl210MibModules OBJECT IDENTIFIER
    ::= { dfl210reg 1 }

dfl210MibConfs OBJECT IDENTIFIER
    ::= { dfl210reg 2 }

dfl210MibObjectGroups OBJECT IDENTIFIER
    ::= { dfl210reg 3 }


dfl210System OBJECT IDENTIFIER
    ::= { dfl210OSStats 1 }

dfl210SysCpuLoad OBJECT-TYPE
    SYNTAX      Gauge32
    MAX-ACCESS  read-only
    STATUS      current
    DESCRIPTION 
        "The system cpu load."
    ::= { dfl210System 1 }

dfl210SysForwardedBits OBJECT-TYPE
    SYNTAX      Counter32
    MAX-ACCESS  read-only
    STATUS      current
    DESCRIPTION
        "The number of bits forwarded through the gateway."
    ::= { dfl210System 2 }

dfl210SysForwardedPackets OBJECT-TYPE
    SYNTAX      Counter32
    MAX-ACCESS  read-only
    STATUS      current
    DESCRIPTION
        "Total number of forwarded packets."
    ::= { dfl210System 3 }

dfl210SysBuffUse OBJECT-TYPE
    SYNTAX      Gauge32
    MAX-ACCESS  read-only
    STATUS      current
    DESCRIPTION 
        "The current number of buffers in use."
    ::= { dfl210System 4 }

dfl210SysConns OBJECT-TYPE
    SYNTAX      Gauge32
    MAX-ACCESS  read-only
    STATUS      current
    DESCRIPTION 
        "The numer of connections."
    ::= { dfl210System 5 }

dfl210SysPerStateCounters OBJECT IDENTIFIER
    ::= { dfl210System 6 }

dfl210SysPscTcpSyn OBJECT-TYPE
    SYNTAX      Gauge32
    MAX-ACCESS  read-only
    STATUS      current
    DESCRIPTION 
        "Number of TCP connections in the SYN state."
    ::= { dfl210SysPerStateCounters 1 }

dfl210SysPscTcpOpen OBJECT-TYPE
    SYNTAX      Gauge32
    MAX-ACCESS  read-only
    STATUS      current
    DESCRIPTION 
        "Number of TCP connections in the OPEN state."
    ::= { dfl210SysPerStateCounters 2 }

dfl210SysPscTcpFin OBJECT-TYPE
    SYNTAX      Gauge32
    MAX-ACCESS  read-only
    STATUS      current
    DESCRIPTION 
        "Number of TCP connections in the FIN state."
    ::= { dfl210SysPerStateCounters 3 }

dfl210SysPscUdp OBJECT-TYPE
    SYNTAX      Gauge32
    MAX-ACCESS  read-only
    STATUS      current
    DESCRIPTION 
        "Number of UDP connections."
    ::= { dfl210SysPerStateCounters 4 }

dfl210SysPscIcmp OBJECT-TYPE
    SYNTAX      Gauge32
    MAX-ACCESS  read-only
    STATUS      current
    DESCRIPTION 
        "Number of ICMP connections."
    ::= { dfl210SysPerStateCounters 5 }

dfl210SysPscOther OBJECT-TYPE
    SYNTAX      Gauge32
    MAX-ACCESS  read-only
    STATUS      current
    DESCRIPTION 
        "Number of other connections."
    ::= { dfl210SysPerStateCounters 6 }

dfl210IfStatsTable OBJECT-TYPE
    SYNTAX      SEQUENCE OF Dfl210IfStatsEntry
    MAX-ACCESS  not-accessible
    STATUS      current
    DESCRIPTION 
        "A table of DFL-210 specific interfaces statistics"
    ::= { dfl210System 7 }

dfl210IfStatsEntry OBJECT-TYPE
    SYNTAX      Dfl210IfStatsEntry
    MAX-ACCESS  not-accessible
    STATUS      current
    DESCRIPTION 
        "The row in a table of DFL-210 specific interface statistics"
    INDEX       { dfl210IfStatsIndex }
    ::= { dfl210IfStatsTable 1 }

Dfl210IfStatsEntry ::= SEQUENCE {
    dfl210IfStatsIndex     Integer32,
    dfl210IfName           DisplayString,
    dfl210IfFragsIn        Counter32,
    dfl210IfFragReassOk    Counter32,
    dfl210IfFragReassFail  Counter32,
    dfl210IfPktsInCnt      Counter32,
    dfl210IfPktsOutCnt     Counter32,
    dfl210IfBitsInCnt      Counter32,
    dfl210IfBitsOutCnt     Counter32,
    dfl210IfPktsTotCnt     Counter32,
    dfl210IfBitsTotCnt     Counter32,
    dfl210IfHCPktsInCnt    Counter64,
    dfl210IfHCPktsOutCnt   Counter64,
    dfl210IfHCBitsInCnt    Counter64,
    dfl210IfHCBitsOutCnt   Counter64,
    dfl210IfHCPktsTotCnt   Counter64,
    dfl210IfHCBitsTotCnt   Counter64
}

dfl210IfStatsIndex OBJECT-TYPE
    SYNTAX      Integer32 (1..2147483647)
    MAX-ACCESS  not-accessible
    STATUS      current
    DESCRIPTION 
        "Index of a row in dfl210SysIfStatsTable"
    ::= { dfl210IfStatsEntry 1 }

dfl210IfName OBJECT-TYPE
    SYNTAX      DisplayString
    MAX-ACCESS  read-only
    STATUS      current
    DESCRIPTION 
        "The name of the interface."
    ::= { dfl210IfStatsEntry 2 }

dfl210IfFragsIn OBJECT-TYPE
    SYNTAX      Counter32
    MAX-ACCESS  read-only
    STATUS      current
    DESCRIPTION 
        "Number of IP packet fragments received 
         in the interface."
    ::= { dfl210IfStatsEntry 3 }

dfl210IfFragReassOk OBJECT-TYPE
    SYNTAX      Counter32
    MAX-ACCESS  read-only
    STATUS      current
    DESCRIPTION 
        "Number of complete IP packets successfully 
         reassembled from the fragments received in 
         the interface."
    ::= { dfl210IfStatsEntry 4 }

dfl210IfFragReassFail OBJECT-TYPE
    SYNTAX      Counter32
    MAX-ACCESS  read-only
    STATUS      current
    DESCRIPTION 
        "Number of packets that could not be reassembled, 
         either due to resource starvation, illegal fragmentation, 
         or just packet loss."
    ::= { dfl210IfStatsEntry 5 }

dfl210IfPktsInCnt OBJECT-TYPE
    SYNTAX      Counter32
    MAX-ACCESS  read-only
    STATUS      current
    DESCRIPTION 
        "Number of packets received by the interface."
    ::= { dfl210IfStatsEntry 6 }

dfl210IfPktsOutCnt OBJECT-TYPE
    SYNTAX      Counter32
    MAX-ACCESS  read-only
    STATUS      current
    DESCRIPTION 
        "Number of packets sent by the interface"
    ::= { dfl210IfStatsEntry 7 }

dfl210IfBitsInCnt OBJECT-TYPE
    SYNTAX      Counter32
    MAX-ACCESS  read-only
    STATUS      current
    DESCRIPTION 
        "Number of bits received by the interface"
    ::= { dfl210IfStatsEntry 8 }

dfl210IfBitsOutCnt OBJECT-TYPE
    SYNTAX      Counter32
    MAX-ACCESS  read-only
    STATUS      current
    DESCRIPTION 
        "Number of bits sent by the interface"
    ::= { dfl210IfStatsEntry 9 }

dfl210IfPktsTotCnt OBJECT-TYPE
    SYNTAX      Counter32
    MAX-ACCESS  read-only
    STATUS      current
    DESCRIPTION 
        "Totat number of packets transmited by the interface"
    ::= { dfl210IfStatsEntry 10 }

dfl210IfBitsTotCnt OBJECT-TYPE
    SYNTAX      Counter32
    MAX-ACCESS  read-only
    STATUS      current
    DESCRIPTION 
        "Totat number of bits transmited by the interface"
    ::= { dfl210IfStatsEntry 11 }

dfl210IfHCPktsInCnt OBJECT-TYPE
    SYNTAX      Counter64
    MAX-ACCESS  read-only
    STATUS      current
    DESCRIPTION 
        "Number of packets received by the interface.
        This object is a 64-bit version of dfl210IfPktsInCnt."
    ::= { dfl210IfStatsEntry 12 }

dfl210IfHCPktsOutCnt OBJECT-TYPE
    SYNTAX      Counter64
    MAX-ACCESS  read-only
    STATUS      current
    DESCRIPTION 
        "Number of packets sent by the interface.
        This object is a 64-bit version of dfl210IfPktsOutCnt."
    ::= { dfl210IfStatsEntry 13 }

dfl210IfHCBitsInCnt OBJECT-TYPE
    SYNTAX      Counter64
    MAX-ACCESS  read-only
    STATUS      current
    DESCRIPTION 
        "Number of bits received by the interface.
        This object is a 64-bit version of dfl210IfBitsInCnt."
    ::= { dfl210IfStatsEntry 14 }

dfl210IfHCBitsOutCnt OBJECT-TYPE
    SYNTAX      Counter64
    MAX-ACCESS  read-only
    STATUS      current
    DESCRIPTION 
        "Number of bits sent by the interface.
        This object is a 64-bit version of dfl210IfBitsOutCnt."
    ::= { dfl210IfStatsEntry 15 }

dfl210IfHCPktsTotCnt OBJECT-TYPE
    SYNTAX      Counter64
    MAX-ACCESS  read-only
    STATUS      current
    DESCRIPTION 
        "Totat number of packets transmited by the interface.
        This object is a 64-bit version of dfl210IfPktsTotCnt."
    ::= { dfl210IfStatsEntry 16 }

dfl210IfHCBitsTotCnt OBJECT-TYPE
    SYNTAX      Counter64
    MAX-ACCESS  read-only
    STATUS      current
    DESCRIPTION 
        "Totat number of bits transmited by the interface. 
        This object is a 64-bit version of dfl210IfBitsTotCnt."
    ::= { dfl210IfStatsEntry 17 }

dfl210IfRxRingTable OBJECT-TYPE
    SYNTAX      SEQUENCE OF Dfl210IfRxRingEntry
    MAX-ACCESS  not-accessible
    STATUS      current
    DESCRIPTION 
        "A table of DFL-210 specific interface Rx ring statistics"
    ::= { dfl210System 8 }

dfl210IfRxRingEntry OBJECT-TYPE
    SYNTAX      Dfl210IfRxRingEntry
    MAX-ACCESS  not-accessible
    STATUS      current
    DESCRIPTION 
        "The row in a table of DFL-210 specific interface Rx ring 
         statistics."
    INDEX       { dfl210IfRxRingIndex }
    ::= { dfl210IfRxRingTable 1 }

Dfl210IfRxRingEntry ::= SEQUENCE {
    dfl210IfRxRingIndex        Integer32,
    dfl210IfRxRingFifoErrors   Counter32,
    dfl210IfRxDespools         Gauge32,
    dfl210IfRxAvgUse           Gauge32,
    dfl210IfRxRingSaturation   Gauge32,
    dfl210RxRingFlooded        Gauge32
}

dfl210IfRxRingIndex OBJECT-TYPE
    SYNTAX      Integer32 (1..2147483647)
    MAX-ACCESS  not-accessible
    STATUS      current
    DESCRIPTION 
        "Index of a row in dfl210IfRxRingTable."
    ::= { dfl210IfRxRingEntry 1 }

dfl210IfRxRingFifoErrors OBJECT-TYPE
    SYNTAX      Counter32
    MAX-ACCESS  read-only
    STATUS      current
    DESCRIPTION 
        "Rx Ring number of FIFO errors."
    ::= { dfl210IfRxRingEntry 2 }

dfl210IfRxDespools OBJECT-TYPE
    SYNTAX      Gauge32
    MAX-ACCESS  read-only
    STATUS      current
    DESCRIPTION 
        "Number of despool events per second."
    ::= { dfl210IfRxRingEntry 3 }

dfl210IfRxAvgUse OBJECT-TYPE
    SYNTAX      Gauge32
    MAX-ACCESS  read-only
    STATUS      current
    DESCRIPTION 
        "Rx Ring average usage."
    ::= { dfl210IfRxRingEntry 4 }

dfl210IfRxRingSaturation OBJECT-TYPE
    SYNTAX      Gauge32
    MAX-ACCESS  read-only
    STATUS      current
    DESCRIPTION 
        "Rx Ring sturation. Percentage of ring use per despool 
         event when the ring has been more than half full."
    ::= { dfl210IfRxRingEntry 5 }

dfl210RxRingFlooded OBJECT-TYPE
    SYNTAX      Gauge32
    MAX-ACCESS  read-only
    STATUS      current
    DESCRIPTION 
        "Rx Ring number of despool events for which 
         the ring has been completely flooded"
    ::= { dfl210IfRxRingEntry 6 }

dfl210IfTxRingTable OBJECT-TYPE
    SYNTAX      SEQUENCE OF Dfl210IfTxRingEntry
    MAX-ACCESS  not-accessible
    STATUS      current
    DESCRIPTION 
        "A table of DFL-210 specific interface Tx ring statistics"
    ::= { dfl210System 9 }

dfl210IfTxRingEntry OBJECT-TYPE
    SYNTAX      Dfl210IfTxRingEntry
    MAX-ACCESS  not-accessible
    STATUS      current
    DESCRIPTION 
        "The row in a table of DFL-210 specific interface Tx ring 
         statistics."
    INDEX       { dfl210IfTxRingIndex }
    ::= { dfl210IfTxRingTable 1 }

Dfl210IfTxRingEntry ::= SEQUENCE {
    dfl210IfTxRingIndex        Integer32,
    dfl210IfTxDespools         Gauge32,
    dfl210IfTxAvgUse           Gauge32,
    dfl210IfTxRingSaturation   Gauge32,
    dfl210RxTingFlooded        Gauge32
}

dfl210IfTxRingIndex OBJECT-TYPE
    SYNTAX      Integer32 (1..2147483647)
    MAX-ACCESS  not-accessible
    STATUS      current
    DESCRIPTION 
        "Index of a row in dfl210IfRxRingTable."
    ::= { dfl210IfTxRingEntry 1 }

dfl210IfTxDespools OBJECT-TYPE
    SYNTAX      Gauge32
    MAX-ACCESS  read-only
    STATUS      current
    DESCRIPTION 
        "Tx Ring number of despool event per second (polls when 
         there is at least one buffer in the ring)"
    ::= { dfl210IfTxRingEntry 2 }

dfl210IfTxAvgUse OBJECT-TYPE
    SYNTAX      Gauge32
    MAX-ACCESS  read-only
    STATUS      current
    DESCRIPTION 
        "Tx Ring number of despool events when the ring has 
         been completely flooded"
    ::= { dfl210IfTxRingEntry 3 }

dfl210IfTxRingSaturation OBJECT-TYPE
    SYNTAX      Gauge32
    MAX-ACCESS  read-only
    STATUS      current
    DESCRIPTION 
        "Tx Ring percentage of use per despool event when the 
         ring has been more than half full."
    ::= { dfl210IfTxRingEntry 4 }

dfl210RxTingFlooded OBJECT-TYPE
    SYNTAX      Gauge32
    MAX-ACCESS  read-only
    STATUS      current
    DESCRIPTION 
        "Tx Ring number of despool events for in which the ring has 
         been completely flooded"
    ::= { dfl210IfTxRingEntry 5 }

dfl210IfVlanStatsTable OBJECT-TYPE
    SYNTAX      SEQUENCE OF Dfl210IfVlanStatsEntry
    MAX-ACCESS  not-accessible
    STATUS      current
    DESCRIPTION 
        "A table of DFL-210 VLAN statistics"
    ::= { dfl210System 10 }

dfl210IfVlanStatsEntry OBJECT-TYPE
    SYNTAX      Dfl210IfVlanStatsEntry
    MAX-ACCESS  not-accessible
    STATUS      current
    DESCRIPTION 
        "The row in a table of dfl210IfVlanStatsTable. Each has an index 
         equal to the ifIndex of the corresponding physical interface"
    INDEX       { dfl210IfVlanIndex }
    ::= { dfl210IfVlanStatsTable 1 }

Dfl210IfVlanStatsEntry ::= SEQUENCE {
    dfl210IfVlanIndex              Integer32,
    dfl210IfVlanUntaggedInPkts     Counter32,
    dfl210IfVlanUntaggedOutPkts    Counter32,
    dfl210IfVlanUntaggedTotPkts    Counter32,
    dfl210IfVlanUntaggedInOctets   Counter32,
    dfl210IfVlanUntaggedOutOctets  Counter32,
    dfl210IfVlanUntaggedTotOctets  Counter32
}

dfl210IfVlanIndex OBJECT-TYPE
    SYNTAX      Integer32 (1..2147483647)
    MAX-ACCESS  not-accessible
    STATUS      current
    DESCRIPTION 
        "Extended index of a row in dfl210IfVlanStatsTable."
    ::= { dfl210IfVlanStatsEntry 1 }

dfl210IfVlanUntaggedInPkts OBJECT-TYPE
    SYNTAX      Counter32
    MAX-ACCESS  read-only
    STATUS      current
    DESCRIPTION 
        "Number of untaged packets untagged packets received by the interface."
    ::= { dfl210IfVlanStatsEntry 2 }

dfl210IfVlanUntaggedOutPkts OBJECT-TYPE
    SYNTAX      Counter32
    MAX-ACCESS  read-only
    STATUS      current
    DESCRIPTION 
        "Number of untagged packets sent by the interface."
    ::= { dfl210IfVlanStatsEntry 3 }

dfl210IfVlanUntaggedTotPkts OBJECT-TYPE
    SYNTAX      Counter32
    MAX-ACCESS  read-only
    STATUS      current
    DESCRIPTION 
        "Total number of untagged packets processed by the interface."
    ::= { dfl210IfVlanStatsEntry 4 }

dfl210IfVlanUntaggedInOctets OBJECT-TYPE
    SYNTAX      Counter32
    MAX-ACCESS  read-only
    STATUS      current
    DESCRIPTION 
        "Total number of octects in untagged packets received by the interface."
    ::= { dfl210IfVlanStatsEntry 5 }

dfl210IfVlanUntaggedOutOctets OBJECT-TYPE
    SYNTAX      Counter32
    MAX-ACCESS  read-only
    STATUS      current
    DESCRIPTION 
        "Total number of octects in untagged packets sent by the interface."
    ::= { dfl210IfVlanStatsEntry 6 }

dfl210IfVlanUntaggedTotOctets OBJECT-TYPE
    SYNTAX      Counter32
    MAX-ACCESS  read-only
    STATUS      current
    DESCRIPTION 
        "Total number of octects in untagged packets processed by the 
         interface."
    ::= { dfl210IfVlanStatsEntry 7 }

dfl210HWSensorTable OBJECT-TYPE
    SYNTAX      SEQUENCE OF Dfl210HWSensorEntry
    MAX-ACCESS  not-accessible
    STATUS      current
    DESCRIPTION 
        "Table of hardware sensors."
    ::= { dfl210System 11 }

dfl210HWSensorEntry OBJECT-TYPE
    SYNTAX      Dfl210HWSensorEntry
    MAX-ACCESS  not-accessible
    STATUS      current
    DESCRIPTION 
        "Entry  of table of hardware sensors."
    INDEX       { dfl210HWSensorIndex }
    ::= { dfl210HWSensorTable 1 }

Dfl210HWSensorEntry ::= SEQUENCE {
    dfl210HWSensorIndex    Integer32,
    dfl210HWSensorName     DisplayString,
    dfl210HWSensorValue    Gauge32,
    dfl210HWSensorUnit     DisplayString
}

dfl210HWSensorIndex OBJECT-TYPE
    SYNTAX      Integer32 (1..2147483647)
    MAX-ACCESS  not-accessible
    STATUS      current
    DESCRIPTION 
        "Index of the entries of the sensor table."
    ::= { dfl210HWSensorEntry 1 }

dfl210HWSensorName OBJECT-TYPE
    SYNTAX      DisplayString
    MAX-ACCESS  read-only
    STATUS      current
    DESCRIPTION 
        "The description of the sensor."
    ::= { dfl210HWSensorEntry 2 }

dfl210HWSensorValue OBJECT-TYPE
    SYNTAX      Gauge32
    MAX-ACCESS  read-only
    STATUS      current
    DESCRIPTION 
        "The value of the sensor."
    ::= { dfl210HWSensorEntry 3 }

dfl210HWSensorUnit OBJECT-TYPE
    SYNTAX      DisplayString
    MAX-ACCESS  read-only
    STATUS      current
    DESCRIPTION 
        "The description of the unit of the value mesured by sensor."
    ::= { dfl210HWSensorEntry 4 }

dfl210SysMemUsage OBJECT-TYPE
    SYNTAX      Gauge32
    MAX-ACCESS  read-only
    STATUS      current
    DESCRIPTION 
        "The current memory usage."
    ::= { dfl210System 12 }

dfl210SysTCPUsage OBJECT IDENTIFIER
    ::= { dfl210System 13 }
    
dfl210SysTCPRecvSmall OBJECT-TYPE
    SYNTAX      Gauge32
    MAX-ACCESS  read-only
    STATUS      current
    DESCRIPTION 
        "Small TCP receive windows usage."
    ::= { dfl210SysTCPUsage 1 }

dfl210SysTCPRecvLarge OBJECT-TYPE
    SYNTAX      Gauge32
    MAX-ACCESS  read-only
    STATUS      current
    DESCRIPTION 
        "Large TCP receive windows usage."
    ::= { dfl210SysTCPUsage 2 }

dfl210SysTCPSendSmall OBJECT-TYPE
    SYNTAX      Gauge32
    MAX-ACCESS  read-only
    STATUS      current
    DESCRIPTION 
        "Small TCP send windows usage."
    ::= { dfl210SysTCPUsage 3 }

dfl210SysTCPSendLarge OBJECT-TYPE
    SYNTAX      Gauge32
    MAX-ACCESS  read-only
    STATUS      current
    DESCRIPTION 
        "Large TCP send windows usage."
    ::= { dfl210SysTCPUsage 4 }

dfl210SysTimerUsage OBJECT-TYPE
    SYNTAX      Gauge32
    MAX-ACCESS  read-only
    STATUS      current
    DESCRIPTION 
        "The current number of timers in use."
    ::= { dfl210System 14 }

dfl210SysConnOPS OBJECT-TYPE
    SYNTAX      Gauge32
    MAX-ACCESS  read-only
    STATUS      current
    DESCRIPTION 
        "The number of connections opened per second."
    ::= { dfl210System 15 }
    
dfl210SysConnCPS OBJECT-TYPE
    SYNTAX      Gauge32
    MAX-ACCESS  read-only
    STATUS      current
    DESCRIPTION 
        "The number of connections closed per second."
    ::= { dfl210System 16 }
    
dfl210SysHCForwardedBits OBJECT-TYPE
    SYNTAX      Counter64
    MAX-ACCESS  read-only
    STATUS      current
    DESCRIPTION
        "The number of bits forwarded through the gateway."
    ::= { dfl210System 17 }
    
dfl210VPN OBJECT IDENTIFIER
    ::= { dfl210OSStats 2 }

dfl210IPsec OBJECT IDENTIFIER
    ::= { dfl210VPN 1 }

dfl210IPsecGlobal OBJECT IDENTIFIER
    ::= { dfl210IPsec 1 }

dfl210IPsecPhaseOneActive OBJECT-TYPE
    SYNTAX      Gauge32
    MAX-ACCESS  read-only
    STATUS      current
    DESCRIPTION 
        "Number of Phase-1 active negotiations"
    ::= { dfl210IPsecGlobal 1 }

dfl210IPsecPhaseOneAggrModeDone OBJECT-TYPE
    SYNTAX      Gauge32
    MAX-ACCESS  read-only
    STATUS      current
    DESCRIPTION 
        "Number of Phase-1 aggressive mode negotiations."
    ::= { dfl210IPsecGlobal 2 }

dfl210IPsecQuickModeActive OBJECT-TYPE
    SYNTAX      Gauge32
    MAX-ACCESS  read-only
    STATUS      current
    DESCRIPTION 
        "Number of quick mode active negotiations."
    ::= { dfl210IPsecGlobal 3 }

dfl210IPsecPhaseOneDone OBJECT-TYPE
    SYNTAX      Counter32
    MAX-ACCESS  read-only
    STATUS      current
    DESCRIPTION 
        "Number of Phase-1 negotiations done."
    ::= { dfl210IPsecGlobal 4 }

dfl210IPsecPhaseOneFailed OBJECT-TYPE
    SYNTAX      Counter32
    MAX-ACCESS  read-only
    STATUS      current
    DESCRIPTION 
        "Number of Phase-1 negotiations failed."
    ::= { dfl210IPsecGlobal 5 }

dfl210IPsecPhaseOneRekeyed OBJECT-TYPE
    SYNTAX      Counter32
    MAX-ACCESS  read-only
    STATUS      current
    DESCRIPTION 
        "Number of Phase-1 negotiations rekeyed."
    ::= { dfl210IPsecGlobal 6 }

dfl210IPsecQuickModeDone OBJECT-TYPE
    SYNTAX      Counter32
    MAX-ACCESS  read-only
    STATUS      current
    DESCRIPTION 
        "Number of quick mode  negotiations done."
    ::= { dfl210IPsecGlobal 7 }

dfl210IPsecQuickModeFailed OBJECT-TYPE
    SYNTAX      Counter32
    MAX-ACCESS  read-only
    STATUS      current
    DESCRIPTION 
        "Number of quick mode negotiations failed."
    ::= { dfl210IPsecGlobal 8 }

dfl210IPsecInfoDone OBJECT-TYPE
    SYNTAX      Counter32
    MAX-ACCESS  read-only
    STATUS      current
    DESCRIPTION 
        "Number of informational exchanges done.
         (Not available in IKEv1 implementations)"
    ::= { dfl210IPsecGlobal 9 }

dfl210IPsecInfoFailed OBJECT-TYPE
    SYNTAX      Counter32
    MAX-ACCESS  read-only
    STATUS      current
    DESCRIPTION 
        "Number of informational exchanges failed.
         (Not available in IKEv1 implementations)"
    ::= { dfl210IPsecGlobal 10 }

dfl210IPsecInOctetsComp OBJECT-TYPE
    SYNTAX      Counter64
    MAX-ACCESS  read-only
    STATUS      current
    DESCRIPTION 
        "Total octets in before decompression."
    ::= { dfl210IPsecGlobal 11 }

dfl210IPsecInOctetsUncomp OBJECT-TYPE
    SYNTAX      Counter64
    MAX-ACCESS  read-only
    STATUS      current
    DESCRIPTION 
        "Total octets in after decompression."
    ::= { dfl210IPsecGlobal 12 }

dfl210IPsecOutOctetsComp OBJECT-TYPE
    SYNTAX      Counter64
    MAX-ACCESS  read-only
    STATUS      current
    DESCRIPTION 
        "Total octets out after compression."
    ::= { dfl210IPsecGlobal 13 }

dfl210IPsecOutOctetsUncomp OBJECT-TYPE
    SYNTAX      Counter64
    MAX-ACCESS  read-only
    STATUS      current
    DESCRIPTION 
        "Total octets out before compression."
    ::= { dfl210IPsecGlobal 14 }

dfl210IPsecForwardedOctetsComp OBJECT-TYPE
    SYNTAX      Counter64
    MAX-ACCESS  read-only
    STATUS      current
    DESCRIPTION 
        "Total octets forwarded after compression."
    ::= { dfl210IPsecGlobal 15 }

dfl210IPsecForwardedOctetsUcomp OBJECT-TYPE
    SYNTAX      Counter64
    MAX-ACCESS  read-only
    STATUS      current
    DESCRIPTION 
        "Total octets forwarded before compression."
    ::= { dfl210IPsecGlobal 16 }

dfl210IPsecInPackets OBJECT-TYPE
    SYNTAX      Counter64
    MAX-ACCESS  read-only
    STATUS      current
    DESCRIPTION 
        "Total packets in."
    ::= { dfl210IPsecGlobal 17 }

dfl210IPsecOutPackets OBJECT-TYPE
    SYNTAX      Counter64
    MAX-ACCESS  read-only
    STATUS      current
    DESCRIPTION 
        "Total packets Out."
    ::= { dfl210IPsecGlobal 18 }

dfl210IPsecForwardedPackets OBJECT-TYPE
    SYNTAX      Counter64
    MAX-ACCESS  read-only
    STATUS      current
    DESCRIPTION 
        "Total packets forwarded."
    ::= { dfl210IPsecGlobal 19 }

dfl210IPsecActiveTransforms OBJECT-TYPE
    SYNTAX      Gauge32
    MAX-ACCESS  read-only
    STATUS      current
    DESCRIPTION 
        "Number of currently active transforms."
    ::= { dfl210IPsecGlobal 20 }

dfl210IPsecTotalTransforms OBJECT-TYPE
    SYNTAX      Counter32
    MAX-ACCESS  read-only
    STATUS      current
    DESCRIPTION 
        "Total number of transform records created."
    ::= { dfl210IPsecGlobal 21 }

dfl210IPsecOutOfTransforms OBJECT-TYPE
    SYNTAX      Counter32
    MAX-ACCESS  read-only
    STATUS      current
    DESCRIPTION 
        "Number of packets dropped due to no available transform object.
         (Not available in IKEv1 implementations)"
    ::= { dfl210IPsecGlobal 22 }

dfl210IPsecTotalRekeys OBJECT-TYPE
    SYNTAX      Counter32
    MAX-ACCESS  read-only
    STATUS      current
    DESCRIPTION 
        "Total number of rekeys performed."
    ::= { dfl210IPsecGlobal 23 }

dfl210Rules OBJECT IDENTIFIER
    ::= { dfl210OSStats 3 }

dfl210RuleUseTable OBJECT-TYPE
    SYNTAX      SEQUENCE OF Dfl210RuleUseEntry
    MAX-ACCESS  not-accessible
    STATUS      current
    DESCRIPTION 
        "A list of general rules usage statistics."
    ::= { dfl210Rules 2 }

dfl210RuleUseEntry OBJECT-TYPE
    SYNTAX      Dfl210RuleUseEntry
    MAX-ACCESS  not-accessible
    STATUS      current
    DESCRIPTION 
        "The statistics over a rule usage."
    INDEX       { dfl210RuleIndex }
    ::= { dfl210RuleUseTable 1 }

Dfl210RuleUseEntry ::= SEQUENCE {
    dfl210RuleIndex    Integer32,
    dfl210RuleName     DisplayString,
    dfl210RuleUse      Counter32
}

dfl210RuleIndex OBJECT-TYPE
    SYNTAX      Integer32 (1..2147483647)
    MAX-ACCESS  not-accessible
    STATUS      current
    DESCRIPTION 
        "The rule usage index."
    ::= { dfl210RuleUseEntry 1 }

dfl210RuleName OBJECT-TYPE
    SYNTAX      DisplayString
    MAX-ACCESS  read-only
    STATUS      current
    DESCRIPTION 
        "The name of the rule."
    ::= { dfl210RuleUseEntry 2 }

dfl210RuleUse OBJECT-TYPE
    SYNTAX      Counter32
    MAX-ACCESS  read-only
    STATUS      current
    DESCRIPTION 
        "The number of times o rule was used."
    ::= { dfl210RuleUseEntry 3 }

dfl210IPPools OBJECT IDENTIFIER
    ::= { dfl210OSStats 4 }

dfl210IPPoolsNumber OBJECT-TYPE
    SYNTAX      Integer32
    MAX-ACCESS  read-only
    STATUS      current
    DESCRIPTION 
        "The number of ip pools"
    ::= { dfl210IPPools 1 }

dfl210IPPoolTable OBJECT-TYPE
    SYNTAX      SEQUENCE OF Dfl210IPPoolEntry
    MAX-ACCESS  not-accessible
    STATUS      current
    DESCRIPTION 
        "A list of IP pools"
    ::= { dfl210IPPools 2 }

dfl210IPPoolEntry OBJECT-TYPE
    SYNTAX      Dfl210IPPoolEntry
    MAX-ACCESS  not-accessible
    STATUS      current
    DESCRIPTION 
        "The attributes of an ip pool"
    INDEX       { dfl210IPPoolIndex }
    ::= { dfl210IPPoolTable 1 }

Dfl210IPPoolEntry ::= SEQUENCE {
    dfl210IPPoolIndex          Integer32,
    dfl210IPPoolName           DisplayString,
    dfl210IPPoolPrepare        Gauge32,
    dfl210IPPoolFree           Gauge32,
    dfl210IPPoolMisses         Gauge32,
    dfl210IPPoolClientFails    Gauge32,
    dfl210IPPoolUsed           Gauge32
}

dfl210IPPoolIndex OBJECT-TYPE
    SYNTAX      Integer32 (1..2147483647)
    MAX-ACCESS  not-accessible
    STATUS      current
    DESCRIPTION 
        "The ip pool index"
    ::= { dfl210IPPoolEntry 1 }

dfl210IPPoolName OBJECT-TYPE
    SYNTAX      DisplayString
    MAX-ACCESS  read-only
    STATUS      current
    DESCRIPTION 
        "The ip pool name"
    ::= { dfl210IPPoolEntry 2 }

dfl210IPPoolPrepare OBJECT-TYPE
    SYNTAX      Gauge32
    MAX-ACCESS  read-only
    STATUS      current
    DESCRIPTION 
        "Number of IP pool objects in prepare mode."
    ::= { dfl210IPPoolEntry 3 }

dfl210IPPoolFree OBJECT-TYPE
    SYNTAX      Gauge32
    MAX-ACCESS  read-only
    STATUS      current
    DESCRIPTION 
        "Number of available IPs in the pool."
    ::= { dfl210IPPoolEntry 4 }

dfl210IPPoolMisses OBJECT-TYPE
    SYNTAX      Gauge32
    MAX-ACCESS  read-only
    STATUS      current
    DESCRIPTION 
        "Mumber of missed IP pool negotiations for other reasons
         than lack of available IP numbers."
    ::= { dfl210IPPoolEntry 5 }

dfl210IPPoolClientFails OBJECT-TYPE
    SYNTAX      Gauge32
    MAX-ACCESS  read-only
    STATUS      current
    DESCRIPTION 
        "Number of failed IP pool transactions."
    ::= { dfl210IPPoolEntry 6 }

dfl210IPPoolUsed OBJECT-TYPE
    SYNTAX      Gauge32
    MAX-ACCESS  read-only
    STATUS      current
    DESCRIPTION 
        "Number of IP numbers in use from the pool."
    ::= { dfl210IPPoolEntry 7 }

dfl210DHCPServer OBJECT IDENTIFIER
    ::= { dfl210OSStats 5 }

dfl210DHCPTotalRejected OBJECT-TYPE
    SYNTAX      Gauge32
    MAX-ACCESS  read-only
    STATUS      current
    DESCRIPTION 
        "Total number of rejected packets (all rules)."
    ::= { dfl210DHCPServer 1 }

dfl210DHCPRuleTable OBJECT-TYPE
    SYNTAX      SEQUENCE OF Dfl210DHCPRuleEntry
    MAX-ACCESS  not-accessible
    STATUS      current
    DESCRIPTION 
        "A list of all DHCP server rules usage statistics."
    ::= { dfl210DHCPServer 2 }

dfl210DHCPRuleEntry OBJECT-TYPE
    SYNTAX      Dfl210DHCPRuleEntry
    MAX-ACCESS  not-accessible
    STATUS      current
    DESCRIPTION 
        "The attributes of a DHCP server rule statistics."
    INDEX       { dfl210DHCPRuleIndex }
    ::= { dfl210DHCPRuleTable 1 }

Dfl210DHCPRuleEntry ::= SEQUENCE {
    dfl210DHCPRuleIndex                Integer32,
    dfl210DHCPRuleName                 DisplayString,
    dfl210DHCPRuleUsage                Gauge32,
    dfl210DHCPRuleUsagePercent         Gauge32,
    dfl210DHCPActiveClients            Gauge32,
    dfl210DHCPActiveClientsPercent     Gauge32,
    dfl210DHCPRejectedRequests         Gauge32,
    dfl210DHCPTotalLeases              Gauge32
}

dfl210DHCPRuleIndex OBJECT-TYPE
    SYNTAX      Integer32 (1..2147483647)
    MAX-ACCESS  not-accessible
    STATUS      current
    DESCRIPTION 
        "The DHCP server rule  index"
    ::= { dfl210DHCPRuleEntry 1 }

dfl210DHCPRuleName OBJECT-TYPE
    SYNTAX      DisplayString
    MAX-ACCESS  read-only
    STATUS      current
    DESCRIPTION 
        "The DHCP server rule name."
    ::= { dfl210DHCPRuleEntry 2 }

dfl210DHCPRuleUsage OBJECT-TYPE
    SYNTAX      Gauge32
    MAX-ACCESS  read-only
    STATUS      current
    DESCRIPTION 
        "Number of used IPs in the pool."
    ::= { dfl210DHCPRuleEntry 3 }

dfl210DHCPRuleUsagePercent OBJECT-TYPE
    SYNTAX      Gauge32
    MAX-ACCESS  read-only
    STATUS      current
    DESCRIPTION 
        "The percentage of the used IPs in 
         relation to the IP pool size."
    ::= { dfl210DHCPRuleEntry 4 }

dfl210DHCPActiveClients OBJECT-TYPE
    SYNTAX      Gauge32
    MAX-ACCESS  read-only
    STATUS      current
    DESCRIPTION 
        "Number of currently active clients."
    ::= { dfl210DHCPRuleEntry 5 }

dfl210DHCPActiveClientsPercent OBJECT-TYPE
    SYNTAX      Gauge32
    MAX-ACCESS  read-only
    STATUS      current
    DESCRIPTION 
        "The number of currently active clients 
         as a percentage of the pool size."
    ::= { dfl210DHCPRuleEntry 6 }

dfl210DHCPRejectedRequests OBJECT-TYPE
    SYNTAX      Gauge32
    MAX-ACCESS  read-only
    STATUS      current
    DESCRIPTION 
        "Number of rejected requests matching
         the current rule."
    ::= { dfl210DHCPRuleEntry 7 }

dfl210DHCPTotalLeases OBJECT-TYPE
    SYNTAX      Gauge32
    MAX-ACCESS  read-only
    STATUS      current
    DESCRIPTION 
        "Total number of leases in the pool."
    ::= { dfl210DHCPRuleEntry 8 }

dfl210UserAuth OBJECT IDENTIFIER
    ::= { dfl210OSStats 6 }

dfl210UserAuthHTTPUsers OBJECT-TYPE
    SYNTAX      Gauge32
    MAX-ACCESS  read-only
    STATUS      current
    DESCRIPTION 
        "Number of currently  logged in HTTP users."
    ::= { dfl210UserAuth 1 }

dfl210UserAuthXAUTHUsers OBJECT-TYPE
    SYNTAX      Gauge32
    MAX-ACCESS  read-only
    STATUS      current
    DESCRIPTION 
        "Number of currently logged in XAUTH users."
    ::= { dfl210UserAuth 2 }

dfl210UserAuthHTTPSUsers OBJECT-TYPE
    SYNTAX      Gauge32
    MAX-ACCESS  read-only
    STATUS      current
    DESCRIPTION 
        "Number of currently logged in HTTPS users."
    ::= { dfl210UserAuth 3 }

dfl210UserAuthPPPUsers OBJECT-TYPE
    SYNTAX      Gauge32
    MAX-ACCESS  read-only
    STATUS      current
    DESCRIPTION 
        "Number of currently logged in PPP users."
    ::= { dfl210UserAuth 4 }

dfl210UserAuthEAPUsers OBJECT-TYPE
    SYNTAX      Gauge32
    MAX-ACCESS  read-only
    STATUS      current
    DESCRIPTION 
        "Number of currently logged in EAP users."
    ::= { dfl210UserAuth 5 }

dfl210UserAuthRuleUseTable OBJECT-TYPE
    SYNTAX      SEQUENCE OF Dfl210UserAuthRuleUseEntry
    MAX-ACCESS  not-accessible
    STATUS      current
    DESCRIPTION 
        "Table of user authentication rule usage."
    ::= { dfl210UserAuth 6 }

dfl210UserAuthRuleUseEntry OBJECT-TYPE
    SYNTAX      Dfl210UserAuthRuleUseEntry
    MAX-ACCESS  not-accessible
    STATUS      current
    DESCRIPTION 
        "The attributes of an authentication rule 
         usage statistics."
    INDEX       { dfl210UserAuthRuleIndex }
    ::= { dfl210UserAuthRuleUseTable 1 }

Dfl210UserAuthRuleUseEntry ::= SEQUENCE {
    dfl210UserAuthRuleIndex    Integer32,
    dfl210UserAuthRuleName     DisplayString,
    dfl210UserAuthRuleUse      Counter32
}

dfl210UserAuthRuleIndex OBJECT-TYPE
    SYNTAX      Integer32 (1..2147483647)
    MAX-ACCESS  not-accessible
    STATUS      current
    DESCRIPTION 
        "The rule usage index."
    ::= { dfl210UserAuthRuleUseEntry 1 }

dfl210UserAuthRuleName OBJECT-TYPE
    SYNTAX      DisplayString
    MAX-ACCESS  read-only
    STATUS      current
    DESCRIPTION 
        "The name of the rule."
    ::= { dfl210UserAuthRuleUseEntry 2 }

dfl210UserAuthRuleUse OBJECT-TYPE
    SYNTAX      Counter32
    MAX-ACCESS  read-only
    STATUS      current
    DESCRIPTION 
        "The number of times o rule was used."
    ::= { dfl210UserAuthRuleUseEntry 3 }

dfl210LinkMonitor OBJECT IDENTIFIER
    ::= { dfl210OSStats 7 }

dfl210LinkMonGrp OBJECT-TYPE
    SYNTAX      Integer32
    MAX-ACCESS  read-only
    STATUS      current
    DESCRIPTION 
        "The number of groups of monitored links"
    ::= { dfl210LinkMonitor 1 }

dfl210LinkMonGrpTable OBJECT-TYPE
    SYNTAX      SEQUENCE OF Dfl210LinkMonGrpEntry
    MAX-ACCESS  not-accessible
    STATUS      current
    DESCRIPTION 
        "Table of link monitor groups."
    ::= { dfl210LinkMonitor 2 }

dfl210LinkMonGrpEntry OBJECT-TYPE
    SYNTAX      Dfl210LinkMonGrpEntry
    MAX-ACCESS  not-accessible
    STATUS      current
    DESCRIPTION 
        "The attributes of a link monitor group"
    INDEX       { dfl210LinkMonGrpIndex }
    ::= { dfl210LinkMonGrpTable 1 }

Dfl210LinkMonGrpEntry ::= SEQUENCE {
    dfl210LinkMonGrpIndex      Integer32,
    dfl210LinkMonGrpName       DisplayString,
    dfl210LinkMonGrpHostsUp    Gauge32
}

dfl210LinkMonGrpIndex OBJECT-TYPE
    SYNTAX      Integer32 (1..2147483647)
    MAX-ACCESS  not-accessible
    STATUS      current
    DESCRIPTION 
        "The index row in the table of link monitor groups."
    ::= { dfl210LinkMonGrpEntry 1 }

dfl210LinkMonGrpName OBJECT-TYPE
    SYNTAX      DisplayString
    MAX-ACCESS  read-only
    STATUS      current
    DESCRIPTION 
        "The link monitor group name."
    ::= { dfl210LinkMonGrpEntry 2 }

dfl210LinkMonGrpHostsUp OBJECT-TYPE
    SYNTAX      Gauge32
    MAX-ACCESS  read-only
    STATUS      current
    DESCRIPTION 
        "The percentage of monitored hosts available."
    ::= { dfl210LinkMonGrpEntry 3 }

dfl210LinkMonHostTable OBJECT-TYPE
    SYNTAX      SEQUENCE OF Dfl210LinkMonHostEntry
    MAX-ACCESS  not-accessible
    STATUS      current
    DESCRIPTION 
        "Table of link monitored hosts in a link monnitor group."
    ::= { dfl210LinkMonitor 3 }

dfl210LinkMonHostEntry OBJECT-TYPE
    SYNTAX      Dfl210LinkMonHostEntry
    MAX-ACCESS  not-accessible
    STATUS      current
    DESCRIPTION 
        "The attributes of a monitored host."
    INDEX       { dfl210LinkMonGrpIndex, dfl210LinkMonHostIndex }
    ::= { dfl210LinkMonHostTable 1 }

Dfl210LinkMonHostEntry ::= SEQUENCE {
    dfl210LinkMonHostIndex             Integer32,
    dfl210LinkMonHostId                DisplayString,
    dfl210LinkMonHostShortTermLoss     Gauge32,
    dfl210LinkMonHostPacketsLost       Counter32
}

dfl210LinkMonHostIndex OBJECT-TYPE
    SYNTAX      Integer32 (1..2147483647)
    MAX-ACCESS  not-accessible
    STATUS      current
    DESCRIPTION 
        "The index an host in the table of link monitor hosts."
    ::= { dfl210LinkMonHostEntry 1 }

dfl210LinkMonHostId OBJECT-TYPE
    SYNTAX      DisplayString
    MAX-ACCESS  read-only
    STATUS      current
    DESCRIPTION 
        "The monitored host identifier."
    ::= { dfl210LinkMonHostEntry 2 }

dfl210LinkMonHostShortTermLoss OBJECT-TYPE
    SYNTAX      Gauge32
    MAX-ACCESS  read-only
    STATUS      current
    DESCRIPTION 
        "The percentage of short term losst packets."
    ::= { dfl210LinkMonHostEntry 3 }

dfl210LinkMonHostPacketsLost OBJECT-TYPE
    SYNTAX      Counter32
    MAX-ACCESS  read-only
    STATUS      current
    DESCRIPTION 
        "Total number of lost monitoring packets."
    ::= { dfl210LinkMonHostEntry 4 }

dfl210Pipes OBJECT IDENTIFIER
    ::= { dfl210OSStats 8 }

dfl210PipeUsers OBJECT-TYPE
    SYNTAX      Gauge32
    MAX-ACCESS  read-only
    STATUS      current
    DESCRIPTION 
        "The current number of users, as defined by the grouping 
         settings of each pipe, being tracked in the pipes system. 
         Note that this value corresponds to the number of users 
         active in each time slice of 1/20th of a second, and not 
         to the number of users having open connections."
    ::= { dfl210Pipes 1 }

dfl210PipeTable OBJECT-TYPE
    SYNTAX      SEQUENCE OF Dfl210PipeEntry
    MAX-ACCESS  not-accessible
    STATUS      current
    DESCRIPTION 
        "Table of pipes"
    ::= { dfl210Pipes 2 }

dfl210PipeEntry OBJECT-TYPE
    SYNTAX      Dfl210PipeEntry
    MAX-ACCESS  not-accessible
    STATUS      current
    DESCRIPTION 
        "A entry of the pipes table"
    INDEX       { dfl210PipeIndex }
    ::= { dfl210PipeTable 1 }

Dfl210PipeEntry ::= SEQUENCE {
    dfl210PipeIndex            Integer32,
    dfl210PipeName             DisplayString,
    dfl210PipeMinPrec          Integer32,
    dfl210PipeMaxPrec          Integer32,
    dfl210PipeDefPrec          Integer32,
    dfl210PipeNumPrec          Integer32,
    dfl210PipeNumUsers         Gauge32,
    dfl210PipeCurrentBps       Gauge32,
    dfl210PipeCurrentPps       Gauge32,
    dfl210PipeDelayedPackets   Counter32,
    dfl210PipeDropedPackets    Counter32
}

dfl210PipeIndex OBJECT-TYPE
    SYNTAX      Integer32 (1..2147483647)
    MAX-ACCESS  not-accessible
    STATUS      current
    DESCRIPTION 
        "The pipe index"
    ::= { dfl210PipeEntry 1 }

dfl210PipeName OBJECT-TYPE
    SYNTAX      DisplayString
    MAX-ACCESS  read-only
    STATUS      current
    DESCRIPTION 
        "The name of the pipe"
    ::= { dfl210PipeEntry 2 }

dfl210PipeMinPrec OBJECT-TYPE
    SYNTAX      Integer32
    MAX-ACCESS  read-only
    STATUS      current
    DESCRIPTION 
        "The minimum of the range of pipe precedences."
    ::= { dfl210PipeEntry 3 }

dfl210PipeMaxPrec OBJECT-TYPE
    SYNTAX      Integer32
    MAX-ACCESS  read-only
    STATUS      current
    DESCRIPTION 
        "The maximum of the range of pipe precedences."
    ::= { dfl210PipeEntry 4 }

dfl210PipeDefPrec OBJECT-TYPE
    SYNTAX      Integer32
    MAX-ACCESS  read-only
    STATUS      current
    DESCRIPTION 
        "The precedence assigned to a packet for which has not one
         allready done by a Pipe Rule."
    ::= { dfl210PipeEntry 5 }

dfl210PipeNumPrec OBJECT-TYPE
    SYNTAX      Integer32
    MAX-ACCESS  read-only
    STATUS      current
    DESCRIPTION 
        "The number of pipe precedences"
    ::= { dfl210PipeEntry 6 }

dfl210PipeNumUsers OBJECT-TYPE
    SYNTAX      Gauge32
    MAX-ACCESS  read-only
    STATUS      current
    DESCRIPTION 
        "The current number of users, as defined by the grouping settings
         of each pipe, being tracked in the pipes system. This value 
         corresponds to the number of users active in each time slice 
         and not to the number of users having  open connections."
    ::= { dfl210PipeEntry 7 }

dfl210PipeCurrentBps OBJECT-TYPE
    SYNTAX      Gauge32
    MAX-ACCESS  read-only
    STATUS      current
    DESCRIPTION 
        "The current throughput of a pipe, in bits per second, as a sum of 
         the corresponding values for all precedences."
    ::= { dfl210PipeEntry 8 }

dfl210PipeCurrentPps OBJECT-TYPE
    SYNTAX      Gauge32
    MAX-ACCESS  read-only
    STATUS      current
    DESCRIPTION 
        "The current throughput of a pipe, in packets per second, as a sum of 
         the corresponding values for all precedences."
    ::= { dfl210PipeEntry 9 }

dfl210PipeDelayedPackets OBJECT-TYPE
    SYNTAX      Counter32
    MAX-ACCESS  read-only
    STATUS      current
    DESCRIPTION 
        "The number of times packets have been delayed as a result of a pipe, 
         or pipe user having used up its allotted bandwidth. Note that one single
         packet may be delayed several times; if a pipe is really full, this 
         count may exceed the number of packets actually passing through the 
         pipe."
    ::= { dfl210PipeEntry 10 }

dfl210PipeDropedPackets OBJECT-TYPE
    SYNTAX      Counter32
    MAX-ACCESS  read-only
    STATUS      current
    DESCRIPTION 
        "The number of packets dropped by a pipe. Packets are dropped when 
         CorePlus is running out of packet buffers. This occurs when excessive 
         amounts of packets need to be queued for later delivery. The packet 
         dropped is always the one that has been queued the longest time 
         globally, which means that the connection suffering from packet loss 
         will be the one most overloading the system."
    ::= { dfl210PipeEntry 11 }

dfl210PipePrecTable OBJECT-TYPE
    SYNTAX      SEQUENCE OF Dfl210PipePrecEntry
    MAX-ACCESS  not-accessible
    STATUS      current
    DESCRIPTION 
        "There is a one to many relation between a pipe and its precedences.
         The number of precedences is a instance attribute of each pipe.
         This table extends the pipes table in order to express the relation 
         between a pipe and the respective precedences."
    ::= { dfl210Pipes 3 }

dfl210PipePrecEntry OBJECT-TYPE
    SYNTAX      Dfl210PipePrecEntry
    MAX-ACCESS  not-accessible
    STATUS      current
    DESCRIPTION 
        "An entry of the table of pipe pecedences. These table entries 
         are chracterized by been indexed by two values. The first index
         the same as the pipe index of the corresponding row in table of 
         pipes and the second index is the index of the set of precedences 
         of the corresponding pipe."
    INDEX       { dfl210PipeIndex, dfl210PipePrecIndex }
    ::= { dfl210PipePrecTable 1 }

Dfl210PipePrecEntry ::= SEQUENCE {
    dfl210PipePrecIndex            Integer32,
    dfl210PipePrec                 Integer32,
    dfl210PipePrecBps              Gauge32,
    dfl210PipePrecTotalPps         Gauge32,
    dfl210PipePrecReservedBps      Gauge32,
    dfl210PipePrecDynLimBps        Gauge32,
    dfl210PipePrecDynUsrLimBps     Gauge32,
    dfl210PipePrecDelayedPackets   Counter32,
    dfl210PipePrecDropedPackets    Counter32
}

dfl210PipePrecIndex OBJECT-TYPE
    SYNTAX      Integer32 (1..2147483647)
    MAX-ACCESS  not-accessible
    STATUS      current
    DESCRIPTION 
        "Index of a precedence of a specific pipe. This is the second index 
         of the entries of pipe precedence table described by object 
         dfl210PipePrecEntry."
    ::= { dfl210PipePrecEntry 1 }

dfl210PipePrec OBJECT-TYPE
    SYNTAX      Integer32
    MAX-ACCESS  read-only
    STATUS      current
    DESCRIPTION 
        "The precedence value"
    ::= { dfl210PipePrecEntry 2 }

dfl210PipePrecBps OBJECT-TYPE
    SYNTAX      Gauge32
    MAX-ACCESS  read-only
    STATUS      current
    DESCRIPTION 
        "The current throughput of the pipe, in bits per second, with 
         the corresponding precedence."
    ::= { dfl210PipePrecEntry 3 }

dfl210PipePrecTotalPps OBJECT-TYPE
    SYNTAX      Gauge32
    MAX-ACCESS  read-only
    STATUS      current
    DESCRIPTION 
        "The current throughput of the pipe precedence, in packets per second."
    ::= { dfl210PipePrecEntry 4 }

dfl210PipePrecReservedBps OBJECT-TYPE
    SYNTAX      Gauge32
    MAX-ACCESS  read-only
    STATUS      current
    DESCRIPTION 
        "The current bandwidth allocated to the precedence."
    ::= { dfl210PipePrecEntry 5 }

dfl210PipePrecDynLimBps OBJECT-TYPE
    SYNTAX      Gauge32
    MAX-ACCESS  read-only
    STATUS      current
    DESCRIPTION 
        "The current bandwidth limit limit applied the precedence."
    ::= { dfl210PipePrecEntry 6 }

dfl210PipePrecDynUsrLimBps OBJECT-TYPE
    SYNTAX      Gauge32
    MAX-ACCESS  read-only
    STATUS      current
    DESCRIPTION 
        "The current precedence bandwidth limit per user of the pipe."
    ::= { dfl210PipePrecEntry 7 }

dfl210PipePrecDelayedPackets OBJECT-TYPE
    SYNTAX      Counter32
    MAX-ACCESS  read-only
    STATUS      current
    DESCRIPTION 
        "The number of times packets have been delayed as a result of a 
         precedence, or pipe user having used up its allotted bandwidth. 
         Note that one single packet may be delayed several times; if a 
         pipe is really full, this count may exceed the number of packets 
         of this precedence actually passing through the pipe."
    ::= { dfl210PipePrecEntry 8 }

dfl210PipePrecDropedPackets OBJECT-TYPE
    SYNTAX      Counter32
    MAX-ACCESS  read-only
    STATUS      current
    DESCRIPTION 
        "The number of pipe dropped packets with the corresponding precedence."
    ::= { dfl210PipePrecEntry 9 }

dfl210ALG OBJECT IDENTIFIER
    ::= { dfl210OSStats 9 }

dfl210AlgSessions OBJECT-TYPE
    SYNTAX      Gauge32
    MAX-ACCESS  read-only
    STATUS      current
    DESCRIPTION 
        "Total ALG sessions"
    ::= { dfl210ALG 1 }

dfl210AlgConnections OBJECT-TYPE
    SYNTAX      Gauge32
    MAX-ACCESS  read-only
    STATUS      current
    DESCRIPTION 
        "Total ALG connections"
    ::= { dfl210ALG 2 }

dfl210AlgTCPStreams OBJECT-TYPE
    SYNTAX      Gauge32
    MAX-ACCESS  read-only
    STATUS      current
    DESCRIPTION 
        "Total ALG TCP streams"
    ::= { dfl210ALG 3 }

dfl210HttpAlg OBJECT IDENTIFIER
    ::= { dfl210ALG 4 }

dfl210HttpAlgTable OBJECT-TYPE
    SYNTAX      SEQUENCE OF Dfl210HttpAlgEntry
    MAX-ACCESS  not-accessible
    STATUS      current
    DESCRIPTION 
        "Table of HTTP ALG objects."
    ::= { dfl210HttpAlg 1 }

dfl210HttpAlgEntry OBJECT-TYPE
    SYNTAX      Dfl210HttpAlgEntry
    MAX-ACCESS  not-accessible
    STATUS      current
    DESCRIPTION 
        "A row of the table of HTTP ALG objects."
    INDEX       { dfl210HttpAlgIndex }
    ::= { dfl210HttpAlgTable 1 }

Dfl210HttpAlgEntry ::= SEQUENCE {
    dfl210HttpAlgIndex             Integer32,
    dfl210HttpAlgName              DisplayString,
    dfl210HttpAlgTotalRequested    Gauge32,
    dfl210HttpAlgTotalAllowed      Gauge32,
    dfl210HttpAlgTotalBlocked      Gauge32
}

dfl210HttpAlgIndex OBJECT-TYPE
    SYNTAX      Integer32 (1..2147483647)
    MAX-ACCESS  not-accessible
    STATUS      current
    DESCRIPTION 
        "The index of an entry of the  Table of HTTP ALG objects."
    ::= { dfl210HttpAlgEntry 1 }

dfl210HttpAlgName OBJECT-TYPE
    SYNTAX      DisplayString
    MAX-ACCESS  read-only
    STATUS      current
    DESCRIPTION 
        "The name of an HTTP ALG object."
    ::= { dfl210HttpAlgEntry 2 }

dfl210HttpAlgTotalRequested OBJECT-TYPE
    SYNTAX      Gauge32
    MAX-ACCESS  read-only
    STATUS      current
    DESCRIPTION 
        "Total number of URL requests."
    ::= { dfl210HttpAlgEntry 3 }

dfl210HttpAlgTotalAllowed OBJECT-TYPE
    SYNTAX      Gauge32
    MAX-ACCESS  read-only
    STATUS      current
    DESCRIPTION 
        "Total number of allowed URL requests."
    ::= { dfl210HttpAlgEntry 4 }

dfl210HttpAlgTotalBlocked OBJECT-TYPE
    SYNTAX      Gauge32
    MAX-ACCESS  read-only
    STATUS      current
    DESCRIPTION 
        "Total number of blocked URL requests."
    ::= { dfl210HttpAlgEntry 5 }

dfl210HttpAlgCntFltTable OBJECT-TYPE
    SYNTAX      SEQUENCE OF Dfl210HttpAlgCntFltEntry
    MAX-ACCESS  not-accessible
    STATUS      current
    DESCRIPTION 
        "Table of HTTP ALG content filtering rules."
    ::= { dfl210HttpAlg 2 }

dfl210HttpAlgCntFltEntry OBJECT-TYPE
    SYNTAX      Dfl210HttpAlgCntFltEntry
    MAX-ACCESS  not-accessible
    STATUS      current
    DESCRIPTION 
        "Entry of the table of HTTP ALG content filtering rules."
    INDEX       { dfl210HttpAlgIndex, dfl210HttpAlgCntFltIndex }
    ::= { dfl210HttpAlgCntFltTable 1 }

Dfl210HttpAlgCntFltEntry ::= SEQUENCE {
    dfl210HttpAlgCntFltIndex       Integer32,
    dfl210HttpAlgCntFltName        DisplayString,
    dfl210HttpAlgCntFltRequests    Gauge32,
    dfl210HttpAlgCntFltAllowed     Gauge32,
    dfl210HttpAlgCntFltBlocked     Gauge32
}

dfl210HttpAlgCntFltIndex OBJECT-TYPE
    SYNTAX      Integer32 (1..2147483647)
    MAX-ACCESS  not-accessible
    STATUS      current
    DESCRIPTION 
        "The index of an entry of the  Table of HTTP ALG 
         content filtering objects."
    ::= { dfl210HttpAlgCntFltEntry 1 }

dfl210HttpAlgCntFltName OBJECT-TYPE
    SYNTAX      DisplayString
    MAX-ACCESS  read-only
    STATUS      current
    DESCRIPTION 
        "The name of the a HTTP ALG content fitering."
    ::= { dfl210HttpAlgCntFltEntry 2 }

dfl210HttpAlgCntFltRequests OBJECT-TYPE
    SYNTAX      Gauge32
    MAX-ACCESS  read-only
    STATUS      current
    DESCRIPTION 
        "Total number of URLs intercepted by a content 
         filtering object."
    ::= { dfl210HttpAlgCntFltEntry 3 }

dfl210HttpAlgCntFltAllowed OBJECT-TYPE
    SYNTAX      Gauge32
    MAX-ACCESS  read-only
    STATUS      current
    DESCRIPTION 
        "Total number of URLs intercepted and allowed 
         by a content filtering object."
    ::= { dfl210HttpAlgCntFltEntry 4 }

dfl210HttpAlgCntFltBlocked OBJECT-TYPE
    SYNTAX      Gauge32
    MAX-ACCESS  read-only
    STATUS      current
    DESCRIPTION 
        "Total number of URLs intercepted and blocked 
         by a content filtering object."
    ::= { dfl210HttpAlgCntFltEntry 5 }

dfl210SmtpAlg OBJECT IDENTIFIER
    ::= { dfl210ALG 5 }

dfl210SmtpAlgTable OBJECT-TYPE
    SYNTAX  SEQUENCE OF Dfl210SmtpAlgEntry
    MAX-ACCESS  not-accessible
    STATUS  current
    DESCRIPTION
  "Table of SMTP ALG objects."
    ::= { dfl210SmtpAlg 1 }

dfl210SmtpAlgEntry OBJECT-TYPE
   SYNTAX  Dfl210SmtpAlgEntry
   MAX-ACCESS  not-accessible
    STATUS      current
    DESCRIPTION 
        "A row of the table of SMTP ALG objects."
    INDEX       { dfl210SmtpAlgIndex }
    ::= { dfl210SmtpAlgTable 1 }

Dfl210SmtpAlgEntry ::= SEQUENCE {
    dfl210SmtpAlgIndex           Integer32,
    dfl210SmtpAlgName            DisplayString,
    dfl210SmtpAlgTotCheckedSes   Gauge32,
    dfl210SmtpAlgTotSpamSes      Gauge32,
    dfl210SmtpAlgTotDroppedSes   Gauge32
}

dfl210SmtpAlgIndex OBJECT-TYPE
    SYNTAX      Integer32 (1..2147483647)
    MAX-ACCESS  not-accessible
    STATUS      current
    DESCRIPTION 
        "The index of an entry of the  Table of SMTP ALG objects."
    ::= { dfl210SmtpAlgEntry 1 }

dfl210SmtpAlgName OBJECT-TYPE
    SYNTAX      DisplayString
    MAX-ACCESS  read-only
    STATUS      current
    DESCRIPTION 
        "The name of an SMTP ALG object."
    ::= { dfl210SmtpAlgEntry 2 }

dfl210SmtpAlgTotCheckedSes OBJECT-TYPE
    SYNTAX      Gauge32
    MAX-ACCESS  read-only
    STATUS      current
    DESCRIPTION 
        "Total sessions checked by the SMTP ALG of corresponding index."
    ::= { dfl210SmtpAlgEntry 3 }

dfl210SmtpAlgTotSpamSes OBJECT-TYPE
    SYNTAX      Gauge32
    MAX-ACCESS  read-only
    STATUS      current
    DESCRIPTION 
        "Total spam sessions detected by the SMTP ALG of corresponding index."
    ::= { dfl210SmtpAlgEntry 4 }

dfl210SmtpAlgTotDroppedSes OBJECT-TYPE
    SYNTAX      Gauge32
    MAX-ACCESS  read-only
    STATUS      current
    DESCRIPTION 
        "Total deroped sessions for the SMTP ALG of corresponding index."
    ::= { dfl210SmtpAlgEntry 5 }


dfl210SmtpAlgDnsBlTable OBJECT-TYPE
    SYNTAX  SEQUENCE OF Dfl210SmtpAlgDnsBlEntry
    MAX-ACCESS  not-accessible
    STATUS  current
    DESCRIPTION
  "Table of SMTP ALG DNS balck list objects."
    ::= { dfl210SmtpAlg 2 }


dfl210SmtpAlgDnsBlEntry OBJECT-TYPE
   SYNTAX  Dfl210SmtpAlgDnsBlEntry
   MAX-ACCESS  not-accessible
    STATUS      current
    DESCRIPTION 
        "A row of the table of SMTP ALG DNS black list objects."
    INDEX       { dfl210SmtpAlgIndex, dfl210SmtpAlgDnsBlIndex }
    ::= { dfl210SmtpAlgDnsBlTable 1 }


Dfl210SmtpAlgDnsBlEntry ::= SEQUENCE {
    dfl210SmtpAlgDnsBlIndex  Integer32,
    dfl210SmtpAlgDnsBlName    DisplayString,
    dfl210SmtpAlgDnsBlChecked      Gauge32,
    dfl210SmtpAlgDnsBlMatched  Gauge32,
    dfl210SmtpAlgDnsBlFailChecks  Gauge32
}

dfl210SmtpAlgDnsBlIndex OBJECT-TYPE
    SYNTAX      Integer32 (1..2147483647)
    MAX-ACCESS  not-accessible
    STATUS      current
    DESCRIPTION 
        "The index of an entry of the  SMTP ALG DNS black list objects." 
    ::= { dfl210SmtpAlgDnsBlEntry 1 }

dfl210SmtpAlgDnsBlName OBJECT-TYPE
    SYNTAX      DisplayString
    MAX-ACCESS  read-only
    STATUS      current
    DESCRIPTION 
  "The SMTP DNS black list name."
    ::= { dfl210SmtpAlgDnsBlEntry 2 }

dfl210SmtpAlgDnsBlChecked OBJECT-TYPE
    SYNTAX      Gauge32
    MAX-ACCESS  read-only
    STATUS      current
    DESCRIPTION 
  "Total sessions checked againt SMTP ALG DNS black list of corresponding index"
    ::= { dfl210SmtpAlgDnsBlEntry 3 }

dfl210SmtpAlgDnsBlMatched OBJECT-TYPE
    SYNTAX      Gauge32
    MAX-ACCESS  read-only
    STATUS      current
    DESCRIPTION 
  "Total sessions that matched SMTP ALG DNS black list of corresponding index"
    ::= { dfl210SmtpAlgDnsBlEntry 4 }

dfl210SmtpAlgDnsBlFailChecks OBJECT-TYPE
    SYNTAX      Gauge32
    MAX-ACCESS  read-only
    STATUS      current
    DESCRIPTION 
  "Total failed checks for the SMTP ALG DNS black list of corresponding index"
    ::= { dfl210SmtpAlgDnsBlEntry 5 }

dfl210DHCPRelay OBJECT IDENTIFIER
    ::= { dfl210OSStats 11 }

dfl210DHCPRelayCurClients OBJECT-TYPE
    SYNTAX      Gauge32
    MAX-ACCESS  read-only
    STATUS      current
    DESCRIPTION 
        "Total DHCP relay active relayed clients."
    ::= { dfl210DHCPRelay 1 }

dfl210DHCPRelayCurTrans OBJECT-TYPE
    SYNTAX      Gauge32
    MAX-ACCESS  read-only
    STATUS      current
    DESCRIPTION 
        "Ongoing DHCP relay transactions."
    ::= { dfl210DHCPRelay 2 }

dfl210DHCPRelayRejected OBJECT-TYPE
    SYNTAX      Gauge32
    MAX-ACCESS  read-only
    STATUS      current
    DESCRIPTION 
        "Total DHCP relay packets rejected."
    ::= { dfl210DHCPRelay 3 }

dfl210DHCPRelayRuleTable OBJECT-TYPE
    SYNTAX      SEQUENCE OF Dfl210DHCPRelayRuleEntry
    MAX-ACCESS  not-accessible
    STATUS      current
    DESCRIPTION 
        "Table of DHCP relay rules."
    ::= { dfl210DHCPRelay 4 }

dfl210DHCPRelayRuleEntry OBJECT-TYPE
    SYNTAX      Dfl210DHCPRelayRuleEntry
    MAX-ACCESS  not-accessible
    STATUS      current
    DESCRIPTION 
        "Entry of the table of DHCP relay rules"
    INDEX       { dfl210DHCPRelayRuleIndex }
    ::= { dfl210DHCPRelayRuleTable 1 }

Dfl210DHCPRelayRuleEntry ::= SEQUENCE {
    dfl210DHCPRelayRuleIndex       Integer32,
    dfl210DHCPRelayRuleName        DisplayString,
    dfl210DHCPRelayRuleHits        Gauge32,
    dfl210DHCPRelayRuleCurClients  Gauge32,
    dfl210DHCPRelayRuleRejCliPkts  Gauge32,
    dfl210DHCPRelayRuleRejSrvPkts  Gauge32
}

dfl210DHCPRelayRuleIndex OBJECT-TYPE
    SYNTAX      Integer32 (1..2147483647)
    MAX-ACCESS  not-accessible
    STATUS      current
    DESCRIPTION 
        "Index of the table of DHCP relay rules."
    ::= { dfl210DHCPRelayRuleEntry 1 }

dfl210DHCPRelayRuleName OBJECT-TYPE
    SYNTAX      DisplayString
    MAX-ACCESS  read-only
    STATUS      current
    DESCRIPTION 
        "Display name of a DHCP relay rule"
    ::= { dfl210DHCPRelayRuleEntry 2 }

dfl210DHCPRelayRuleHits OBJECT-TYPE
    SYNTAX      Gauge32
    MAX-ACCESS  read-only
    STATUS      current
    DESCRIPTION 
        "Number of the times the  DHCP relay rule with corresponding index was 
         used."
    ::= { dfl210DHCPRelayRuleEntry 3 }

dfl210DHCPRelayRuleCurClients OBJECT-TYPE
    SYNTAX      Gauge32
    MAX-ACCESS  read-only
    STATUS      current
    DESCRIPTION 
        "Number of ctive relayed clients by the DHCP relay rule with corresponding index."
    ::= { dfl210DHCPRelayRuleEntry 4 }

dfl210DHCPRelayRuleRejCliPkts OBJECT-TYPE
    SYNTAX      Gauge32
    MAX-ACCESS  read-only
    STATUS      current
    DESCRIPTION 
        "Number of client packets rejected by a rule."
    ::= { dfl210DHCPRelayRuleEntry 5 }

dfl210DHCPRelayRuleRejSrvPkts OBJECT-TYPE
    SYNTAX      Gauge32
    MAX-ACCESS  read-only
    STATUS      current
    DESCRIPTION 
        "Number of DHCP server packets rejected by the DHCP relay rule 
         with the corresponding index."
    ::= { dfl210DHCPRelayRuleEntry 6 }

dfl210HA OBJECT IDENTIFIER
    ::= { dfl210OSStats 12 }

dfl210HASyncSendQueueLength OBJECT-TYPE
    SYNTAX      Gauge32
    MAX-ACCESS  read-only
    STATUS      current
    DESCRIPTION 
        "Size of the queue used for the High Availability sync interface."
    ::= { dfl210HA 1 }

dfl210HASyncSendQueueUsagePkt OBJECT-TYPE
    SYNTAX      Gauge32
    MAX-ACCESS  read-only
    STATUS      current
    DESCRIPTION 
        "High Availability Sync interface queue usage in number of packets."
    ::= { dfl210HA 2 }

dfl210HASyncSendQueueUsageOct OBJECT-TYPE
    SYNTAX      Gauge32
    MAX-ACCESS  read-only
    STATUS      current
    DESCRIPTION 
        "High Availability Sync interface queue usage in number of octects."
    ::= { dfl210HA 3 }

dfl210HASyncSentPackets OBJECT-TYPE
    SYNTAX      Counter32
    MAX-ACCESS  read-only
    STATUS      current
    DESCRIPTION 
        "Number High Availability packets sent on Sync."
    ::= { dfl210HA 4 }

dfl210HASyncSendResentPackets OBJECT-TYPE
    SYNTAX      Counter32
    MAX-ACCESS  read-only
    STATUS      current
    DESCRIPTION 
        "Number of High Availability packets resent on Sync."
    ::= { dfl210HA 5 }

dfl210StatsConformance OBJECT IDENTIFIER
    ::= { dfl210MibConfs 1 }

dfl210StatsRegGroups OBJECT IDENTIFIER
    ::= { dfl210MibObjectGroups 1 }

dfl210SystemObjectGroup OBJECT-GROUP
    OBJECTS     { dfl210SysCpuLoad, 
                  dfl210SysForwardedBits, 
                  dfl210SysForwardedPackets, 
                  dfl210SysBuffUse, 
                  dfl210SysConns, 
                  dfl210HWSensorName, 
                  dfl210HWSensorValue, 
                  dfl210HWSensorUnit, 
                  dfl210SysMemUsage, 
                  dfl210SysTimerUsage, 
                  dfl210SysConnOPS, 
                  dfl210SysConnCPS,
                  dfl210SysHCForwardedBits }
    STATUS      current
    DESCRIPTION 
        "System statistics Group"
    ::= { dfl210StatsRegGroups 1 }

dfl210IPsecObjectGroup OBJECT-GROUP
    OBJECTS     { dfl210IPsecPhaseOneActive, 
                  dfl210IPsecPhaseOneAggrModeDone, 
                  dfl210IPsecQuickModeActive, 
                  dfl210IPsecPhaseOneDone, 
                  dfl210IPsecPhaseOneFailed, 
                  dfl210IPsecPhaseOneRekeyed, 
                  dfl210IPsecQuickModeDone, 
                  dfl210IPsecQuickModeFailed, 
                  dfl210IPsecInfoDone, 
                  dfl210IPsecInfoFailed, 
                  dfl210IPsecInOctetsComp, 
                  dfl210IPsecInOctetsUncomp, 
                  dfl210IPsecOutOctetsComp, 
                  dfl210IPsecOutOctetsUncomp, 
                  dfl210IPsecForwardedOctetsComp, 
                  dfl210IPsecForwardedOctetsUcomp, 
                  dfl210IPsecInPackets, 
                  dfl210IPsecOutPackets, 
                  dfl210IPsecForwardedPackets, 
                  dfl210IPsecActiveTransforms, 
                  dfl210IPsecTotalTransforms, 
                  dfl210IPsecOutOfTransforms, 
                  dfl210IPsecTotalRekeys }
    STATUS      current
    DESCRIPTION 
        "IPsec Group"
    ::= { dfl210StatsRegGroups 2 }

dfl210StateCountersGroup OBJECT-GROUP
    OBJECTS     { dfl210SysPscTcpSyn, 
                  dfl210SysPscTcpOpen, 
                  dfl210SysPscTcpFin, 
                  dfl210SysPscUdp, 
                  dfl210SysPscIcmp, 
                  dfl210SysPscOther }
    STATUS      current
    DESCRIPTION 
        "Per state counters"
    ::= { dfl210StatsRegGroups 3 }

dfl210IPPoolGroup OBJECT-GROUP
    OBJECTS     { dfl210IPPoolsNumber, 
                  dfl210IPPoolName, 
                  dfl210IPPoolPrepare, 
                  dfl210IPPoolFree, 
                  dfl210IPPoolMisses, 
                  dfl210IPPoolClientFails, 
                  dfl210IPPoolUsed }
    STATUS      current
    DESCRIPTION 
        "IP pool entry objects group"
    ::= { dfl210StatsRegGroups 4 }

dfl210DHCPServerGroup OBJECT-GROUP
    OBJECTS     { dfl210DHCPTotalRejected, 
                  dfl210DHCPRuleName, 
                  dfl210DHCPRuleUsage, 
                  dfl210DHCPRuleUsagePercent, 
                  dfl210DHCPActiveClients, 
                  dfl210DHCPActiveClientsPercent, 
                  dfl210DHCPRejectedRequests, 
                  dfl210DHCPTotalLeases }
    STATUS      current
    DESCRIPTION 
        "DHCP server rules objects."
    ::= { dfl210StatsRegGroups 5 }

dfl210RuleUseGroup OBJECT-GROUP
    OBJECTS     { dfl210RuleName, dfl210RuleUse }
    STATUS      current
    DESCRIPTION 
        "Rule use objects."
    ::= { dfl210StatsRegGroups 6 }

dfl210UserAuthGroup OBJECT-GROUP
    OBJECTS     { dfl210UserAuthHTTPUsers, dfl210UserAuthXAUTHUsers, 
                  dfl210UserAuthHTTPSUsers, dfl210UserAuthPPPUsers, 
                  dfl210UserAuthEAPUsers, dfl210UserAuthRuleName, 
                  dfl210UserAuthRuleUse }
    STATUS      current
    DESCRIPTION 
        "User auth objects."
    ::= { dfl210StatsRegGroups 7 }

dfl210IfStatsGroup OBJECT-GROUP
    OBJECTS     { dfl210IfName, 
                  dfl210IfFragsIn, 
                  dfl210IfFragReassOk, 
                  dfl210IfFragReassFail, 
                  dfl210IfPktsInCnt, 
                  dfl210IfPktsOutCnt, 
                  dfl210IfBitsInCnt, 
                  dfl210IfBitsOutCnt, 
                  dfl210IfPktsTotCnt, 
                  dfl210IfBitsTotCnt, 
                  dfl210IfHCPktsInCnt, 
                  dfl210IfHCPktsOutCnt, 
                  dfl210IfHCBitsInCnt, 
                  dfl210IfHCBitsOutCnt, 
                  dfl210IfHCPktsTotCnt, 
                  dfl210IfHCBitsTotCnt,
                  dfl210IfRxRingFifoErrors, 
                  dfl210IfRxDespools, 
                  dfl210IfRxAvgUse, 
                  dfl210IfRxRingSaturation, 
                  dfl210RxRingFlooded, 
                  dfl210IfTxDespools, 
                  dfl210IfTxAvgUse, 
                  dfl210IfTxRingSaturation, 
                  dfl210RxTingFlooded }
    STATUS      current
    DESCRIPTION 
        "DFL-210 interface statistics group."
    ::= { dfl210StatsRegGroups 8 }

dfl210LinkMonitorGroup OBJECT-GROUP
    OBJECTS     { dfl210LinkMonGrp, 
                  dfl210LinkMonGrpName, 
                  dfl210LinkMonGrpHostsUp, 
                  dfl210LinkMonHostId, 
                  dfl210LinkMonHostShortTermLoss, 
                  dfl210LinkMonHostPacketsLost }
    STATUS      current
    DESCRIPTION 
        "DFL-210 link monitor statistics group"
    ::= { dfl210StatsRegGroups 9 }

dfl210PipesObjectGroup OBJECT-GROUP
    OBJECTS     { dfl210PipeUsers, 
                  dfl210PipeName, 
                  dfl210PipeMinPrec, 
                  dfl210PipeMaxPrec, 
                  dfl210PipeDefPrec, 
                  dfl210PipeNumPrec, 
                  dfl210PipeNumUsers, 
                  dfl210PipeCurrentBps, 
                  dfl210PipeCurrentPps, 
                  dfl210PipeDelayedPackets, 
                  dfl210PipeDropedPackets, 
                  dfl210PipePrec, 
                  dfl210PipePrecBps, 
                  dfl210PipePrecTotalPps, 
                  dfl210PipePrecReservedBps, 
                  dfl210PipePrecDynLimBps, 
                  dfl210PipePrecDynUsrLimBps, 
                  dfl210PipePrecDelayedPackets, 
                  dfl210PipePrecDropedPackets }
    STATUS      current
    DESCRIPTION 
        "DFL-210 pipes statistics group"
    ::= { dfl210StatsRegGroups 10 }

dfl210DHCPRelayObjectGroup OBJECT-GROUP
    OBJECTS     { dfl210DHCPRelayCurClients, 
                  dfl210DHCPRelayCurTrans, 
                  dfl210DHCPRelayRejected, 
                  dfl210DHCPRelayRuleName, 
                  dfl210DHCPRelayRuleHits, 
                  dfl210DHCPRelayRuleCurClients, 
                  dfl210DHCPRelayRuleRejCliPkts, 
                  dfl210DHCPRelayRuleRejSrvPkts }
    STATUS      current
    DESCRIPTION 
        "DFL-210 DHCP relay statistics group"
    ::= { dfl210StatsRegGroups 12 }

dfl210AlgGroup OBJECT-GROUP
    OBJECTS     { dfl210AlgSessions, 
                  dfl210AlgConnections, 
                  dfl210AlgTCPStreams, 
                  dfl210HttpAlgName, 
                  dfl210HttpAlgTotalRequested, 
                  dfl210HttpAlgTotalAllowed, 
                  dfl210HttpAlgTotalBlocked, 
                  dfl210HttpAlgCntFltName, 
                  dfl210HttpAlgCntFltRequests, 
                  dfl210HttpAlgCntFltAllowed, 
                  dfl210HttpAlgCntFltBlocked }
    STATUS      current
    DESCRIPTION 
        "DFL-210 HTTP ALG statistics group"
    ::= { dfl210StatsRegGroups 13 }

dfl210HAGroup OBJECT-GROUP
    OBJECTS     { dfl210HASyncSendQueueLength, 
                  dfl210HASyncSendQueueUsagePkt, 
                  dfl210HASyncSendQueueUsageOct, 
                  dfl210HASyncSentPackets, 
                  dfl210HASyncSendResentPackets }
    STATUS      current
    DESCRIPTION 
        "DFL-210 HA statistics group"
    ::= { dfl210StatsRegGroups 14 }

dfl210IfVlanGroup OBJECT-GROUP
    OBJECTS     { dfl210IfVlanUntaggedInPkts, 
                  dfl210IfVlanUntaggedOutPkts, 
                  dfl210IfVlanUntaggedTotPkts, 
                  dfl210IfVlanUntaggedInOctets, 
                  dfl210IfVlanUntaggedOutOctets, 
                  dfl210IfVlanUntaggedTotOctets }
    STATUS      current
    DESCRIPTION 
        "DFL-210 VLAN statistics group"
    ::= { dfl210StatsRegGroups 15 }


dfl210SmtpAlgGroup OBJECT-GROUP 
    OBJECTS { dfl210SmtpAlgName,
              dfl210SmtpAlgTotCheckedSes,
              dfl210SmtpAlgTotSpamSes,
              dfl210SmtpAlgTotDroppedSes,
              dfl210SmtpAlgDnsBlName,    
              dfl210SmtpAlgDnsBlChecked,     
              dfl210SmtpAlgDnsBlMatched,  
              dfl210SmtpAlgDnsBlFailChecks }
   STATUS current
   DESCRIPTION
       "Clavister SMTP ALG objects group"
   ::= { dfl210StatsRegGroups 16 }
   
dfl210SysTCPGroup OBJECT-GROUP 
    OBJECTS { dfl210SysTCPRecvSmall,
              dfl210SysTCPRecvLarge,
              dfl210SysTCPSendSmall,
              dfl210SysTCPSendLarge }
    STATUS current
    DESCRIPTION
      "DFL-210 TCP buffer usage group"
    ::= { dfl210StatsRegGroups 17 }



dfl210StatsCompliance MODULE-COMPLIANCE
    STATUS      current
    DESCRIPTION 
        "Module Compliance"

    MODULE      -- this module

        MANDATORY-GROUPS        
                { dfl210SystemObjectGroup, 
                  dfl210IPsecObjectGroup, 
                  dfl210StateCountersGroup, 
                  dfl210IPPoolGroup, 
                  dfl210DHCPServerGroup, 
                  dfl210RuleUseGroup, 
                  dfl210UserAuthGroup, 
                  dfl210IfStatsGroup, 
                  dfl210LinkMonitorGroup, 
                  dfl210PipesObjectGroup, 
                  dfl210DHCPRelayObjectGroup, 
                  dfl210AlgGroup, 
                  dfl210HAGroup, 
                  dfl210IfVlanGroup, 
                  dfl210SmtpAlgGroup, 
                  dfl210SysTCPGroup }

    ::= { dfl210StatsConformance 1 }

END -- end of module DFL210-MIB.

-- -----------------------------------------------------------------------------
-- MIB NAME : Equipment MIB
-- FILE NAME: DGS-6600-EQUIPMENT-MIB.mib
-- DATE     : 2013/02/04
-- VERSION  : 1.00
-- PURPOSE  : To accomplish the h/w related function for DGS-6600
-- -----------------------------------------------------------------------------
-- MODIFICTION HISTORY:
-- -----------------------------------------------------------------------------
-- Version 1.00, 2013/02/04, Andy Hsu
-- This is the first formal version for MIB definition.
-- -----------------------------------------------------------------------------

    DGS-6600-EQUIPMENT-MIB DEFINITIONS ::= BEGIN

    IMPORTS
        MODULE-IDENTITY,OBJECT-TYPE,Integer32       FROM SNMPv2-SMI
        MacAddress                      FROM SNMPv2-TC
        DisplayString                   FROM RFC1213-MIB
        dgs6600-system                  FROM DGS-6600-ID-MIB;

    dgs6600EquipmentMIB MODULE-IDENTITY
        LAST-UPDATED "1302070000Z"
        ORGANIZATION "D-Link Corp."
        CONTACT-INFO
            "http://support.dlink.com"
        DESCRIPTION
            "The structure of chassis HW function for the
            proprietary enterprise."
        ::= { dgs6600-system 2 }

-- ----------------------------------------------------------------------------
--  Main Category Declaration
-- ----------------------------------------------------------------------------
    chassisControlModuleLEDInfo         OBJECT IDENTIFIER ::= { dgs6600EquipmentMIB 1 }
    chassisPowerInfo                    OBJECT IDENTIFIER ::= { dgs6600EquipmentMIB 2 }
    chassisFanTrayInfo                  OBJECT IDENTIFIER ::= { dgs6600EquipmentMIB 3 }
    chassisSlotInfo                     OBJECT IDENTIFIER ::= { dgs6600EquipmentMIB 4 }
    chassisTemperatureInfo              OBJECT IDENTIFIER ::= { dgs6600EquipmentMIB 5 }
    chassisPortLEDInfo                  OBJECT IDENTIFIER ::= { dgs6600EquipmentMIB 6 }
--  chassisPortStatusInfo               OBJECT IDENTIFIER ::= { dgs6600EquipmentMIB 6 }

-- ----------------------------------------------------------------------------
--  chassisControlModuleLEDInfo
-- ----------------------------------------------------------------------------
    chassisControlModuleLEDInfoTable OBJECT-TYPE
        SYNTAX      SEQUENCE OF ChassisControlModuleLEDInfoEntry
        MAX-ACCESS  not-accessible
        STATUS      current
        DESCRIPTION
            "TBD."    
        ::= { chassisControlModuleLEDInfo 1 }

    chassisControlModuleLEDInfoEntry OBJECT-TYPE
        SYNTAX      ChassisControlModuleLEDInfoEntry
        MAX-ACCESS  not-accessible
        STATUS      current
        DESCRIPTION
            "TBD."    
        INDEX  { chassisControlModuleLEDInfoIndex }
        ::= { chassisControlModuleLEDInfoTable 1 }

    ChassisControlModuleLEDInfoEntry ::=
        SEQUENCE {
            chassisControlModuleLEDInfoIndex
                INTEGER,
            chassisControlModuleLEDInfoConsole
                INTEGER,
            chassisControlModuleLEDInfoMaster
                INTEGER,
            chassisControlModuleLEDInfoCPUUtilization
                INTEGER,
            chassisControlModuleLEDInfoMgmtPortStatus
                INTEGER,
            chassisControlModuleLEDInfoMgmtPortSpeed
                INTEGER
--          chassisControlModuleLEDInfoCF1
--              INTEGER,
--          chassisControlModuleLEDInfoCF2
--              INTEGER,
       }             
    
    chassisControlModuleLEDInfoIndex OBJECT-TYPE
        SYNTAX      INTEGER (1..8)
        MAX-ACCESS  read-only
        STATUS      current
        DESCRIPTION
            "This object indicates the slot index of Control Module."
        ::= { chassisControlModuleLEDInfoEntry 1 }
       
    chassisControlModuleLEDInfoConsole OBJECT-TYPE
        SYNTAX      INTEGER { rs232(1), usb(2) }
        MAX-ACCESS  read-only
        STATUS      current
        DESCRIPTION
            "This object indicates the console type. There are two different interfaces:
             1: RS232.
             2: USB."
        ::= { chassisControlModuleLEDInfoEntry 2 }

    chassisControlModuleLEDInfoMaster OBJECT-TYPE
        SYNTAX      INTEGER { active(1), standby(2) }
        MAX-ACCESS  read-only
        STATUS      current
        DESCRIPTION
            "This object indicates whether this control module is master or not?
             1: This control module is active CM.
             2: This control module is standby CM."
        ::= { chassisControlModuleLEDInfoEntry 3 }

    chassisControlModuleLEDInfoCPUUtilization OBJECT-TYPE
        SYNTAX      INTEGER { zero-LED(0), one-LED(1), two-LEDs(2), three-LEDs(3), four-LEDs(4), five-LEDs(5), six-LEDs(6), seven-LEDs(7), eight-LEDs(8) }
        MAX-ACCESS  read-only
        STATUS      current
        DESCRIPTION
            "This object indicates the CPU utilization(in percentage) of this control module."
        ::= { chassisControlModuleLEDInfoEntry 4 }

    chassisControlModuleLEDInfoMgmtPortStatus OBJECT-TYPE
        SYNTAX      INTEGER { off(1), steady-green(2), blinking-green(3) }
        MAX-ACCESS  read-only
        STATUS      current
        DESCRIPTION
            "This object indicates the management port status."
        ::= { chassisControlModuleLEDInfoEntry 5 }

    chassisControlModuleLEDInfoMgmtPortSpeed OBJECT-TYPE
          SYNTAX      INTEGER { link-0(1), link-100(2), link-1000(3) }
          MAX-ACCESS  read-only
          STATUS      current
          DESCRIPTION
            "This object indicates the management port link speed."
        ::= { chassisControlModuleLEDInfoEntry 6 }

--    chassisControlModuleLEDInfoCF1 OBJECT-TYPE
--        SYNTAX      INTEGER { off(1), on(2), blinking(3) }
--        MAX-ACCESS  read-only
--        STATUS      current
--        DESCRIPTION
--            "This object indicates the LED state of CF1 slot. There are three different states:
--             1: LED off. CF1 is not installed.
--             2: LED on. CF1 is installed.
--             3: LED blinking. CF1 is being accessing."
--        ::= { chassisControlModuleLEDInfoEntry 6 }

--    chassisControlModuleLEDInfoCF2 OBJECT-TYPE
--        SYNTAX      INTEGER { off(1), on(2), blinking(3) }
--        MAX-ACCESS  read-only
--        STATUS      current
--        DESCRIPTION
--            "This object indicates the LED state of CF2 slot. There are three different states:
--             1: LED off. CF2 is not installed.
--             2: LED on. CF2 is installed.
--             3: LED blinking. CF2 is being accessing."
--        ::= { chassisControlModuleLEDInfoEntry 7 }         

-- ----------------------------------------------------------------------------
--  chassisPowerInfo
-- ----------------------------------------------------------------------------
    chassisPowerInfoTable OBJECT-TYPE
        SYNTAX      SEQUENCE OF ChassisPowerInfoEntry
        MAX-ACCESS  not-accessible
        STATUS      current
        DESCRIPTION
            "TBD."
        ::= { chassisPowerInfo 1 }

    chassisPowerInfoEntry OBJECT-TYPE
        SYNTAX      ChassisPowerInfoEntry
        MAX-ACCESS  not-accessible
        STATUS      current
        DESCRIPTION
            "TBD."
        INDEX  { chassisPowerIndex }
        ::= { chassisPowerInfoTable 1 }

    ChassisPowerInfoEntry ::=
        SEQUENCE {
            chassisPowerIndex
                INTEGER,
            chassisPowerExist
                INTEGER,
            chassisPowerType
                INTEGER,
            chassisPowerAlive
                INTEGER,
            chassisPowerVoltage
                INTEGER,
            chassisPowerCurrent
                INTEGER,
            chassisPowerPowerWatt
                INTEGER,
            chassisPowerFanSpeed
                INTEGER
        }

    chassisPowerIndex OBJECT-TYPE
        SYNTAX      INTEGER (1..8)
        MAX-ACCESS  read-only
        STATUS      current
        DESCRIPTION
            "This object indicates the PSU index."
        ::= { chassisPowerInfoEntry 1 }

    chassisPowerExist OBJECT-TYPE
        SYNTAX      INTEGER { empty(1), exist(2) }
        MAX-ACCESS  read-only
        STATUS      current
        DESCRIPTION
            "This object indicates whether the specified PSU is exist or not.
             1: The PSU is not exist.
             2: The PSU is installed."
        ::= { chassisPowerInfoEntry 2 }

    chassisPowerType OBJECT-TYPE
        SYNTAX      INTEGER { AC(1), DC(2), Unknown(3) }
        MAX-ACCESS  read-only
        STATUS      current
        DESCRIPTION
            "This object indicates the PSU type.
             1: The PSU type is AC.
             2: The PSU type is DC.
             3: The PSU type is unknown."
        ::= { chassisPowerInfoEntry 3 }

    chassisPowerAlive OBJECT-TYPE
        SYNTAX      INTEGER { failed(1), in-operation(2) }
        MAX-ACCESS  read-only
        STATUS      current
        DESCRIPTION
            "This object indicates whether the specified PSU is alive or not.
             1: The PSU is not available.
             2: The PSU is working normally."
        ::= { chassisPowerInfoEntry 4 }

    chassisPowerVoltage OBJECT-TYPE
        SYNTAX      INTEGER
        MAX-ACCESS  read-only
        STATUS      current
        DESCRIPTION
            "This object indicates the output voltage(V) of the specified PSU."
        ::= { chassisPowerInfoEntry 5 }

    chassisPowerCurrent OBJECT-TYPE
        SYNTAX      INTEGER
        MAX-ACCESS  read-only
        STATUS      current
        DESCRIPTION
            "This object indicates the output current(mA) of the specified PSU."
        ::= { chassisPowerInfoEntry 6 }

    chassisPowerPowerWatt OBJECT-TYPE
        SYNTAX      INTEGER
        MAX-ACCESS  read-only
        STATUS      current
        DESCRIPTION
            "This object indicates the output power(W) of the specified PSU."
        ::= { chassisPowerInfoEntry 7 }

    chassisPowerFanSpeed OBJECT-TYPE
        SYNTAX      INTEGER
        MAX-ACCESS  read-only
        STATUS      current
        DESCRIPTION
            "This object indicates the internal fan speed(rpm) of specified PSU."
        ::= { chassisPowerInfoEntry 8 }

-- ----------------------------------------------------------------------------
--  chassisFanTrayInfo
-- ----------------------------------------------------------------------------
    chassisFanTrayInfoState OBJECT-TYPE
        SYNTAX      INTEGER { not-exist(1), failed(2), in-operation(3) }
        MAX-ACCESS  read-only
        STATUS      current
        DESCRIPTION
            "This object indicates the fan tray state. There are three different state:
             1. Not existed
             2. Existed but failed
             3. Working normally"
        ::= { chassisFanTrayInfo 1 }

    chassisFanInfoTable OBJECT-TYPE
        SYNTAX      SEQUENCE OF ChassisFanInfoEntry
        MAX-ACCESS  not-accessible
        STATUS      current
        DESCRIPTION
            "TBD."
        ::= { chassisFanTrayInfo 2 }

    chassisFanInfoEntry OBJECT-TYPE
        SYNTAX      ChassisFanInfoEntry
        MAX-ACCESS  not-accessible
        STATUS      current
        DESCRIPTION
            "TBD."
        INDEX  { chassisFanIndex }
        ::= { chassisFanInfoTable 1 }

    ChassisFanInfoEntry ::=
        SEQUENCE {
            chassisFanIndex
                INTEGER,
            chassisFanStatus
                INTEGER,
            chassisFanSpeed
                INTEGER
       }

    chassisFanIndex OBJECT-TYPE
        SYNTAX      INTEGER (1..16)
        MAX-ACCESS  read-only
        STATUS      current
        DESCRIPTION
            "This object indicates the fan tray index."
        ::= { chassisFanInfoEntry 1 }

    chassisFanStatus OBJECT-TYPE
        SYNTAX      INTEGER { failed(1), ok(2) }
        MAX-ACCESS  read-only
        STATUS      current
        DESCRIPTION
            "This object indicates the fan status(ok or failed)."
        ::= { chassisFanInfoEntry 2 }

    chassisFanSpeed OBJECT-TYPE
        SYNTAX      INTEGER
        MAX-ACCESS  read-only
        STATUS      current
        DESCRIPTION
            "This object indicates the fan speed in RPM."
        ::= { chassisFanInfoEntry 3 }

-- ----------------------------------------------------------------------------
--  chassisSlotInfo
-- ----------------------------------------------------------------------------
    chassisSlotInfoTable OBJECT-TYPE
        SYNTAX      SEQUENCE OF ChassisSlotInfoEntry
        MAX-ACCESS  not-accessible
        STATUS      current
        DESCRIPTION
            "TBD."
        ::= { chassisSlotInfo 1 }

    chassisSlotInfoEntry OBJECT-TYPE
        SYNTAX      ChassisSlotInfoEntry
        MAX-ACCESS  not-accessible
        STATUS      current
        DESCRIPTION
            "TBD."
        INDEX  { chassisSlotIndex }
        ::= { chassisSlotInfoTable 1 }

    ChassisSlotInfoEntry ::=
        SEQUENCE {
            chassisSlotIndex
                INTEGER,
            chassisSlotState
                INTEGER,
--            chassisSlotBootingUp
--                INTEGER,
            chassisSlotLEDPoEModeEnabled
                INTEGER,
            chassisSlotModel
                DisplayString,
            chassisSlotSerialNumber
                DisplayString,
            chassisSlotHwVersion
                DisplayString,
            chassisSlotPCBAVersion
                DisplayString,
            chassisSlotBootloaderVersion
                DisplayString,
            chassisSlotRuntimeVersion
                DisplayString,
            chassisSlotCPLDVersion
                DisplayString,
            chassisSlotFirsMacAddress
                MacAddress,
            chassisSlotNumberOfMacAddress
                INTEGER
       }

    chassisSlotIndex OBJECT-TYPE
        SYNTAX      INTEGER (1..8)
        MAX-ACCESS  read-only
        STATUS      current
        DESCRIPTION
            "This object indicates the slot index."
        ::= { chassisSlotInfoEntry 1 }

    chassisSlotState OBJECT-TYPE
        SYNTAX      INTEGER { empty(1), no-power(2), failed(3), booting(4), in-operation(5) }
        MAX-ACCESS  read-only
        STATUS      current
        DESCRIPTION
            "This object indicates the slot state:
             1: The slot has no card installed.
             2: The card which installed at this slot is not powered up.
             3: The card which installed at this slot is failed.
             4: The card which installed at this slot is booting up.
             5: The card is powered up."
        ::= { chassisSlotInfoEntry 2 }

--    chassisSlotBootingUp OBJECT-TYPE
--        SYNTAX      INTEGER
--        MAX-ACCESS  read-only
--        STATUS      current
--        DESCRIPTION
--            "This object indicates whether this slot is in boot up procedure or not?
--             1: This slot is booting up.
--             2: This slot was boot up complete."
--        ::= { chassisSlotInfoEntry 3 }

    chassisSlotLEDPoEModeEnabled OBJECT-TYPE
        SYNTAX      INTEGER { disabled(1), enabled(2) }
        MAX-ACCESS  read-only
        STATUS      current
        DESCRIPTION
            "This object indicates whether the PoE mode is enabled or not?"
        ::= { chassisSlotInfoEntry 3 }

    chassisSlotModel OBJECT-TYPE
        SYNTAX      DisplayString
        MAX-ACCESS  read-only
        STATUS      current
        DESCRIPTION
            "This object indicates the card model name."
        ::= { chassisSlotInfoEntry 4 }

    chassisSlotSerialNumber OBJECT-TYPE
        SYNTAX      DisplayString
        MAX-ACCESS  read-only
        STATUS      current
        DESCRIPTION
            "This object indicates the serial number of the installed card."
        ::= { chassisSlotInfoEntry 5 }

    chassisSlotHwVersion OBJECT-TYPE
        SYNTAX      DisplayString
        MAX-ACCESS  read-only
        STATUS      current
        DESCRIPTION
            "This object indicates the HW version of the installed card."
        ::= { chassisSlotInfoEntry 6 }

    chassisSlotPCBAVersion OBJECT-TYPE
        SYNTAX      DisplayString
        MAX-ACCESS  read-only
        STATUS      current
        DESCRIPTION
            "This object indicates the PCBA version of the installed card."
        ::= { chassisSlotInfoEntry 7 }

    chassisSlotBootloaderVersion OBJECT-TYPE
        SYNTAX      DisplayString
        MAX-ACCESS  read-only
        STATUS      current
        DESCRIPTION
            "This object indicates the PCBA version of the installed card."
        ::= { chassisSlotInfoEntry 8 }

    chassisSlotRuntimeVersion OBJECT-TYPE
        SYNTAX      DisplayString
        MAX-ACCESS  read-only
        STATUS      current
        DESCRIPTION
            "This object indicates the runtime version of the installed card."
        ::= { chassisSlotInfoEntry 9 }

    chassisSlotCPLDVersion OBJECT-TYPE
        SYNTAX      DisplayString
        MAX-ACCESS  read-only
        STATUS      current
        DESCRIPTION
            "This object indicates the CPLD version of the installed card."
        ::= { chassisSlotInfoEntry 10 }

    chassisSlotFirsMacAddress OBJECT-TYPE
        SYNTAX      MacAddress
        MAX-ACCESS  read-only
        STATUS      current
        DESCRIPTION
            "This object indicates the first MAC address of the installed card."
        ::= { chassisSlotInfoEntry 11 }

    chassisSlotNumberOfMacAddress OBJECT-TYPE
        SYNTAX      INTEGER
        MAX-ACCESS  read-only
        STATUS      current
        DESCRIPTION
            "This object indicates the number of MAC address of the installed card."
        ::= { chassisSlotInfoEntry 12 }

-- ----------------------------------------------------------------------------
--  chassisTemperatureInfo
-- ----------------------------------------------------------------------------
    chassisTemperatureInfoTable OBJECT-TYPE
        SYNTAX      SEQUENCE OF ChassisTemperatureInfoEntry
        MAX-ACCESS  not-accessible
        STATUS      current
        DESCRIPTION
            "TBD."
        ::= { chassisTemperatureInfo 1 }

    chassisTemperatureInfoEntry OBJECT-TYPE
        SYNTAX      ChassisTemperatureInfoEntry
        MAX-ACCESS  not-accessible
        STATUS      current
        DESCRIPTION
            "TBD."
        INDEX  { chassisTemperatureSlotIndex }
        ::= { chassisTemperatureInfoTable 1 }

    ChassisTemperatureInfoEntry ::=
        SEQUENCE {
            chassisTemperatureSlotIndex
                INTEGER,
            chassisTemperatureInletCurrent
                DisplayString,
            chassisTemperatureInletOverheat
                DisplayString,
            chassisTemperatureInletHeatdown
                DisplayString,
            chassisTemperatureCenterCurrent
                DisplayString,
            chassisTemperatureCenterOverheat
                DisplayString,
            chassisTemperatureCenterHeatdown
                DisplayString,
            chassisTemperatureOutletCurrent
                DisplayString,
            chassisTemperatureOutletOverheat
                DisplayString,
            chassisTemperatureOutletHeatdown
                DisplayString
       }

    chassisTemperatureSlotIndex OBJECT-TYPE
        SYNTAX      INTEGER (1..8)
        MAX-ACCESS  read-only
        STATUS      current
        DESCRIPTION
            "This object indicates the slot number which is currently querying."
        ::= { chassisTemperatureInfoEntry 1 }

    chassisTemperatureInletCurrent OBJECT-TYPE
        SYNTAX      DisplayString
        MAX-ACCESS  read-only
        STATUS      current
        DESCRIPTION
            "This object displays the current temperature of Inlet sensor."
        ::= { chassisTemperatureInfoEntry 2 }

    chassisTemperatureInletOverheat OBJECT-TYPE
        SYNTAX      DisplayString
        MAX-ACCESS  read-only
        STATUS      current
        DESCRIPTION
            "This object displays the overheat threshold of Inlet sensor."
        ::= { chassisTemperatureInfoEntry 3 }

    chassisTemperatureInletHeatdown OBJECT-TYPE
        SYNTAX      DisplayString
        MAX-ACCESS  read-only
        STATUS      current
        DESCRIPTION
            "This object displays the heatdown threshold of Inlet sensor."
        ::= { chassisTemperatureInfoEntry 4 }

    chassisTemperatureCenterCurrent OBJECT-TYPE
        SYNTAX      DisplayString
        MAX-ACCESS  read-only
        STATUS      current
        DESCRIPTION
            "This object displays the current temperature of Center sensor."
        ::= { chassisTemperatureInfoEntry 5 }

    chassisTemperatureCenterOverheat OBJECT-TYPE
        SYNTAX      DisplayString
        MAX-ACCESS  read-only
        STATUS      current
        DESCRIPTION
            "This object displays the overheat threshold of Center sensor."
        ::= { chassisTemperatureInfoEntry 6 }

    chassisTemperatureCenterHeatdown OBJECT-TYPE
        SYNTAX      DisplayString
        MAX-ACCESS  read-only
        STATUS      current
        DESCRIPTION
            "This object displays the heatdown threshold of Center sensor."
        ::= { chassisTemperatureInfoEntry 7 }

    chassisTemperatureOutletCurrent OBJECT-TYPE
        SYNTAX      DisplayString
        MAX-ACCESS  read-only
        STATUS      current
        DESCRIPTION
            "This object displays the current temperature of Outlet sensor.
             The string N/A will be displayed to indicate that the card has no this sensor."
        ::= { chassisTemperatureInfoEntry 8 }

    chassisTemperatureOutletOverheat OBJECT-TYPE
        SYNTAX      DisplayString
        MAX-ACCESS  read-only
        STATUS      current
        DESCRIPTION
            "This object displays the overheat threshold of Outlet sensor.
             The string N/A will be displayed to indicate that the card has no this sensor."
        ::= { chassisTemperatureInfoEntry 9 }

    chassisTemperatureOutletHeatdown OBJECT-TYPE
        SYNTAX      DisplayString
        MAX-ACCESS  read-only
        STATUS      current
        DESCRIPTION
            "This object displays the outlet threshold of Outlet sensor.
             The string N/A will be displayed to indicate that the card has no this sensor."
        ::= { chassisTemperatureInfoEntry 10 }

-- ----------------------------------------------------------------------------
--  chassisPortLEDInfo
-- ----------------------------------------------------------------------------
    chassisPortLEDInfoTable OBJECT-TYPE
        SYNTAX      SEQUENCE OF ChassisPortLEDInfoEntry
        MAX-ACCESS  not-accessible
        STATUS      current
        DESCRIPTION
            "TBD."
        ::= { chassisPortLEDInfo 1 }

    chassisPortLEDInfoEntry OBJECT-TYPE
        SYNTAX      ChassisPortLEDInfoEntry
        MAX-ACCESS  not-accessible
        STATUS      current
        DESCRIPTION
            "TBD."
        INDEX  { chassisPortLEDIFIndex }
        ::= { chassisPortLEDInfoTable 1 }

    ChassisPortLEDInfoEntry ::=
        SEQUENCE {
            chassisPortLEDIFIndex
                Integer32,
            chassisPortLEDIFName
                DisplayString,
            chassisPortLEDStatus
                INTEGER,
            chassisPortLEDMode
                INTEGER,
            chassisPortLEDMediumType
                INTEGER
        }

    chassisPortLEDIFIndex OBJECT-TYPE
        SYNTAX      Integer32
        MAX-ACCESS  read-only
        STATUS      current
        DESCRIPTION
            "This object indicates the interface index."
        ::= { chassisPortLEDInfoEntry 1 }

    chassisPortLEDIFName OBJECT-TYPE
        SYNTAX      DisplayString
        MAX-ACCESS  read-only
        STATUS      current
        DESCRIPTION
            "This object indicates the interface name."
        ::= { chassisPortLEDInfoEntry 2 }

    chassisPortLEDStatus OBJECT-TYPE
        SYNTAX      INTEGER { off(1), steady-amber(2), steady-green(3), blinking-amber(4), blinking-green(5) }
        MAX-ACCESS  read-only
        STATUS      current
        DESCRIPTION
            "This object indicates the port LED status:
             1: The port LED status of the interface index is off.
             2: The port LED status of the interface index is steady-amber. 
             3: The port LED status of the interface index is steady-green.
             4: The port LED status of the interface index is blinking-amber.
             5: The port LED status of the interface index is blinking-green."
        ::= { chassisPortLEDInfoEntry 3 }

    chassisPortLEDMode OBJECT-TYPE
        SYNTAX      INTEGER { ethernet(1), poe(2) }
        MAX-ACCESS  read-only
        STATUS      current
        DESCRIPTION
            "This object indicates the port LED mode:
             1: The port LED is in Ethernet mode.
             2: The poer LED is in PoE mode."
        ::= { chassisPortLEDInfoEntry 4 }

    chassisPortLEDMediumType OBJECT-TYPE
        SYNTAX      INTEGER { copper(1), fiber(2) }
        MAX-ACCESS  read-only
        STATUS      current
        DESCRIPTION
            "This object indicates the port LED medium type:
			 1: The medium type of port LED is copper.
			 2: The medium type of port LED is fiber."
        ::= { chassisPortLEDInfoEntry 5 }

-- ----------------------------------------------------------------------------
--  chassisPortStatusInfo
-- ----------------------------------------------------------------------------
--    chassisPortStatusInfoTable OBJECT-TYPE
--        SYNTAX      SEQUENCE OF ChassisPortStatusInfoEntry
--        MAX-ACCESS  not-accessible
--        STATUS      current
--        DESCRIPTION
--            "TBD."
--        ::= { chassisPortStatusInfo 1 }
--
--    chassisPortStatusInfoEntry OBJECT-TYPE
--        SYNTAX      ChassisPortStatusInfoEntry
--        MAX-ACCESS  not-accessible
--        STATUS      current
--        DESCRIPTION
--            "TBD."
--        INDEX  { chassisPortStatusSlotIndex }
--        ::= { chassisPortStatusInfoTable 1 }
--
--    ChassisPortStatusInfoEntry ::=
--        SEQUENCE {
--            chassisPortStatusSlotIndex
--                INTEGER,
--            chassisPortStatusBitmapLink
--                OCTET STRING (SIZE (48)),
--            chassisPortStatusBitmapSpeed
--                OCTET STRING (SIZE (96)),
--            chassisPortStatusBitmapActivity
--                OCTET STRING (SIZE (48))
--       }
--
--    chassisPortStatusSlotIndex OBJECT-TYPE
--        SYNTAX      INTEGER (1..8)
--        MAX-ACCESS  read-only
--        STATUS      current
--        DESCRIPTION
--            "TBD."
--        ::= { chassisPortStatusInfoEntry 1 }
--
--    chassisPortStatusBitmapLink OBJECT-TYPE
--        SYNTAX      OCTET STRING (SIZE (48))
--        MAX-ACCESS  read-only
--        STATUS      current
--        DESCRIPTION
--            "TBD."
--        ::= { chassisPortStatusInfoEntry 2 }
--
--    chassisPortStatusBitmapSpeed OBJECT-TYPE
--        SYNTAX      OCTET STRING (SIZE (96))
--        MAX-ACCESS  read-only
--        STATUS      current
--        DESCRIPTION
--            "TBD."
--        ::= { chassisPortStatusInfoEntry 3 }
--
--    chassisPortStatusBitmapActivity OBJECT-TYPE
--        SYNTAX      OCTET STRING (SIZE (48))
--        MAX-ACCESS  read-only
--        STATUS      current
--        DESCRIPTION
--            "TBD."
--        ::= { chassisPortStatusInfoEntry 4 }

END

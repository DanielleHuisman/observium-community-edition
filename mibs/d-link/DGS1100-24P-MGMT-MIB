DGS1100-24P-MGMT-MIB DEFINITIONS ::= BEGIN

    IMPORTS
        Counter32,TimeTicks,NOTIFICATION-TYPE,MODULE-IDENTITY,
        OBJECT-TYPE,IpAddress, Unsigned32
                                        FROM SNMPv2-SMI
        SnmpAdminString                 FROM SNMP-FRAMEWORK-MIB
        MacAddress, RowStatus           FROM SNMPv2-TC
        dgs1100-24P                     FROM DGS1100PRIMGMT-MIB
        DisplayString                   FROM RFC1213-MIB;

    swL2MgmtMIB MODULE-IDENTITY
	    LAST-UPDATED "201404260000Z"
        ORGANIZATION "D-Link Corp."
        CONTACT-INFO
                "        D-Link Corporation
                 Postal: No. 289, Sinhu 3rd Rd., Neihu District,
                         Taipei City 114, Taiwan, R.O.C
                 Tel:     +886-2-66000123
                 E-mail: tsd@dlink.com.tw
                "
	    DESCRIPTION
		    "The Structure of Layer 2 Network Management Information for the
		    proprietary enterprise."
        ::= { dgs1100-24P 9 }

    PortList                ::= OCTET STRING(SIZE (0..127))
    VlanIndex               ::= Unsigned32
    VlanId					::= INTEGER (1..4094)


END

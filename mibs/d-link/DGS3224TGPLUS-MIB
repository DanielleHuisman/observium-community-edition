-- The DGS3224TGPLUS proprietary MIB Ver 2.0               2003/03/20

 DGS3224TGPLUS-MIB	DEFINITIONS ::= BEGIN 
    IMPORTS
        IpAddress , TimeTicks , Integer32, 
        MODULE-IDENTITY , OBJECT-TYPE			FROM SNMPv2-SMI
        MacAddress                             		FROM SNMPv2-TC
        PortList	      			        FROM Q-BRIDGE-MIB
        DisplayString                                   FROM RFC1213-MIB
        dlink-mgmt                                      FROM DLINK-ID-REC-MIB
        dgs3224tgr                                      FROM DLINK-ID-REC-MIB 
        dlink-Dgs3224tgrProd                            FROM DLINK-ID-REC-MIB;
	
        
        
   dlkL2MgmtMIB MODULE-IDENTITY
	    LAST-UPDATED "0007150000Z"
	    ORGANIZATION "D-Link, Inc."
	    CONTACT-INFO
	        "   D-Link Customer Service

		    Postal: No. 20,Park Ave, II, Science-based
			        Industrial Park, Hsinchu, taiwan, R.O.C.

		       Tel: 886-3-577-9966

		    E-mail: "
	    DESCRIPTION
		    "The Structure of Layer 2 Network Management Information for the
		    D-Link enterprise."
        ::= { dgs3224tgr 1}
       
       swL2Property				OBJECT IDENTIFIER ::= { dlink-Dgs3224tgrProd 1 }
       swL2Module			        OBJECT IDENTIFIER ::= { swL2Property 1 }
       
       VlanId					::= INTEGER (1..4094)
        
        swL2BwMgmt				OBJECT IDENTIFIER ::= { dlkL2MgmtMIB 1 }
        
               
           
-- ********************************************************************
--        swL2BwMgmt               OBJECT IDENTIFIER ::= { dlkL2MgmtMIB 1 }
-- ********************************************************************
      
          swL2PortBwCtrlTable OBJECT-TYPE
              SYNTAX  SEQUENCE OF SwL2PortBwCtrlEntry
              MAX-ACCESS  not-accessible
              STATUS  current
              DESCRIPTION
                      "A table that contains the current control information about the 
                      ingress/engress  bandwidth of port"
              ::= { swL2BwMgmt 1 }

          swL2PortBwCtrlEntry OBJECT-TYPE
              SYNTAX  SwL2PortBwCtrlEntry
              MAX-ACCESS  not-accessible
              STATUS  current
              DESCRIPTION
                      "A list of information contained in swL2PortBwCtrlTable."
              INDEX   { swL2PortBwCtrlPort }
              ::= { swL2PortBwCtrlTable 1 }

          SwL2PortBwCtrlEntry ::=
              SEQUENCE {
                  swL2PortBwCtrlPort
                      INTEGER,
                  swL2PortBwCtrlPortCatalog
                      INTEGER,
                  swL2IngrPortBwCtrlRate
                      DisplayString,
                  swL2EngrPortBwCtrlRate
                      DisplayString,
                  swL2PortBwCtrlStatus
                      INTEGER
              }

          swL2PortBwCtrlPort OBJECT-TYPE
              SYNTAX  INTEGER (0..65535)
              MAX-ACCESS  read-only
              STATUS  current
              DESCRIPTION
                      "Indicates the port to limit ingress/engress bandwidth."
              ::= { swL2PortBwCtrlEntry 1 }

          swL2PortBwCtrlPortCatalog OBJECT-TYPE
              SYNTAX  INTEGER {
                          ingressPort(1),
                          engressPort(2),
                          both(3), 
                          other(4)                         
                      }
              MAX-ACCESS  read-only
              STATUS  current
              DESCRIPTION
                      "Indicates the  type of port. "
              ::= { swL2PortBwCtrlEntry 2 }

          swL2IngrPortBwCtrlRate OBJECT-TYPE
              -- SYNTAX  INTEGER (1..1000)
              SYNTAX DisplayString(SIZE(1..8))
              MAX-ACCESS  read-write
              STATUS  current
              DESCRIPTION
                      "Indicates the limitation of forwarding bandwidth in MBPS.
                      or is no_limit"
             ::= { swL2PortBwCtrlEntry 3 }

          swL2EngrPortBwCtrlRate OBJECT-TYPE
             -- SYNTAX  INTEGER (1..1000)
              SYNTAX DisplayString(SIZE(1..8))
              MAX-ACCESS  read-write
              STATUS  current
              DESCRIPTION
                      "Indicates the limitation of forwarding bandwidth in MBPS. 
                      or is no_limit"
              ::= { swL2PortBwCtrlEntry 4 }

          swL2PortBwCtrlStatus OBJECT-TYPE
              SYNTAX  INTEGER {
				other(1),
				invalid(2),
				valid(3)
                      }
              MAX-ACCESS  read-only
              STATUS  current
              DESCRIPTION
                      "Status of this entry. All the existed entries will return valid(3). An entry  
                      will be created if this object is set to valid(3) and not existed.
                      If this object is set to invalid(2), this entry will be deleted."
              ::= { swL2PortBwCtrlEntry 5 }
              


END

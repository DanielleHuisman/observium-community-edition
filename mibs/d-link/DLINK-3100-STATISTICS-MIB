DLINK-3100-STATISTICS-MIB DEFINITIONS ::= BEGIN

        IMPORTS
              rnd                                       FROM DLINK-3100-MIB
              OBJECT-TYPE, MODULE-IDENTITY              FROM SNMPv2-SMI
              Counter                                   FROM RFC1155-SMI
              ifIndex                                   FROM IF-MIB
        ;

-- module

                rlStatistics MODULE-IDENTITY
                    LAST-UPDATED "2007111800Z"
                    ORGANIZATION "Dlink, Inc."
                    CONTACT-INFO
                        "www.dlink.com"
                    DESCRIPTION
                        "Dlink statistics MIBs"
                    REVISION "200711180000Z"
                    DESCRIPTION
                            "Initial revision."
                    ::={ rnd 141 }

                rlStatisticsPacketTable OBJECT-TYPE
                    SYNTAX      SEQUENCE OF RlStatisticsPacketEntry
                    MAX-ACCESS  read-only
                    STATUS      current
                    DESCRIPTION
                        " Dlink Packet statistics MIB Table "
                    ::=  { rlStatistics 1 }

                rlStatisticsPacketEntry OBJECT-TYPE
                    SYNTAX      RlStatisticsPacketEntry
                    MAX-ACCESS  read-only
                    STATUS      current
                    DESCRIPTION
                        " Row definition for packet statistic table. "
                    INDEX { ifIndex }
                    ::= { rlStatisticsPacketTable 1 }

                RlStatisticsPacketEntry::= SEQUENCE {
                    rlStatisticsPacket64Octets              Counter,
                    rlStatisticsPacket65to127Octets         Counter,
                    rlStatisticsPacket128to255Octets        Counter,
                    rlStatisticsPacket256to511Octets        Counter,
                    rlStatisticsPacket512to1023Octets       Counter,
                    rlStatisticsPacket1024to1518Octets      Counter,
                    rlStatisticsPacketOversizePkts          Counter,
                    rlStatisticsPacketUnicastRx             Counter,
                    rlStatisticsPacketMulticastRx           Counter,
                    rlStatisticsPacketBroadcastRx           Counter,
                    rlStatisticsPacketRxBytes               Counter,
                    rlStatisticsPacketRxFrames              Counter,
                    rlStatisticsPacketTxBytes               Counter,
                    rlStatisticsPacketTxFrames              Counter
                }

                rlStatisticsPacket64Octets OBJECT-TYPE
                    SYNTAX      Counter
                    MAX-ACCESS  read-only
                    STATUS      current
                    DESCRIPTION
                        " Amount of packets per size "
                    ::=  { rlStatisticsPacketEntry 1 }

                rlStatisticsPacket65to127Octets OBJECT-TYPE
                    SYNTAX      Counter
                    MAX-ACCESS  read-only
                    STATUS      current
                    DESCRIPTION
                        " Amount of packets per size "
                    ::=  { rlStatisticsPacketEntry 2 }

                rlStatisticsPacket128to255Octets OBJECT-TYPE
                    SYNTAX      Counter
                    MAX-ACCESS  read-only
                    STATUS      current
                    DESCRIPTION
                        " Amount of packets per size "
                    ::=  { rlStatisticsPacketEntry 3 }

                rlStatisticsPacket256to511Octets OBJECT-TYPE
                    SYNTAX      Counter
                    MAX-ACCESS  read-only
                    STATUS      current
                    DESCRIPTION
                        " Amount of packets per size "
                    ::=  { rlStatisticsPacketEntry 4 }

                rlStatisticsPacket512to1023Octets OBJECT-TYPE
                    SYNTAX      Counter
                    MAX-ACCESS  read-only
                    STATUS      current
                    DESCRIPTION
                        " Amount of packets per size "
                    ::=  { rlStatisticsPacketEntry 5 }

                rlStatisticsPacket1024to1518Octets OBJECT-TYPE
                    SYNTAX      Counter
                    MAX-ACCESS  read-only
                    STATUS      current
                    DESCRIPTION
                        " Amount of packets per size "
                    ::=  { rlStatisticsPacketEntry 6 }

                rlStatisticsPacketOversizePkts OBJECT-TYPE
                    SYNTAX      Counter
                    MAX-ACCESS  read-only
                    STATUS      current
                    DESCRIPTION
                        " Amount of packets per size "
                    ::=  { rlStatisticsPacketEntry 7 }

                rlStatisticsPacketUnicastRx OBJECT-TYPE
                    SYNTAX      Counter
                    MAX-ACCESS  read-only
                    STATUS      current
                    DESCRIPTION
                        " Amount of packets per category "
                    ::=  { rlStatisticsPacketEntry 8 }

                rlStatisticsPacketMulticastRx OBJECT-TYPE
                    SYNTAX      Counter
                    MAX-ACCESS  read-only
                    STATUS      current
                    DESCRIPTION
                        " Amount of packets per category "
                    ::=  { rlStatisticsPacketEntry 9 }

                rlStatisticsPacketBroadcastRx OBJECT-TYPE
                    SYNTAX      Counter
                    MAX-ACCESS  read-only
                    STATUS      current
                    DESCRIPTION
                        " Amount of packets per category "
                    ::=  { rlStatisticsPacketEntry 10 }

                rlStatisticsPacketRxBytes OBJECT-TYPE
                    SYNTAX      Counter
                    MAX-ACCESS  read-only
                    STATUS      current
                    DESCRIPTION
                        " Amount of RX Bytes "
                    ::=  { rlStatisticsPacketEntry 11 }

                rlStatisticsPacketRxFrames OBJECT-TYPE
                    SYNTAX      Counter
                    MAX-ACCESS  read-only
                    STATUS      current
                    DESCRIPTION
                        " Amount of RX Frames "
                    ::=  { rlStatisticsPacketEntry 12 }

                rlStatisticsPacketTxBytes OBJECT-TYPE
                    SYNTAX      Counter
                    MAX-ACCESS  read-only
                    STATUS      current
                    DESCRIPTION
                        " Amount of TX Bytes "
                    ::=  { rlStatisticsPacketEntry 13 }

                rlStatisticsPacketTxFrames OBJECT-TYPE
                    SYNTAX      Counter
                    MAX-ACCESS  read-only
                    STATUS      current
                    DESCRIPTION
                        " Amount of TX Frames "
                    ::=  { rlStatisticsPacketEntry 14 }

                rlStatisticsPortTable OBJECT-TYPE
                    SYNTAX      SEQUENCE OF RlStatisticsPortEntry
                    MAX-ACCESS  read-only
                    STATUS      current
                    DESCRIPTION
                        " Dlink Port statistics MIB Table "
                    ::=  { rlStatistics 2 }

                rlStatisticsPortEntry OBJECT-TYPE
                    SYNTAX      RlStatisticsPortEntry
                    MAX-ACCESS  read-only
                    STATUS      current
                    DESCRIPTION
                        " Row definition for port statistic table. "
                    INDEX { ifIndex }
                    ::= { rlStatisticsPortTable 1 }

                RlStatisticsPortEntry::= SEQUENCE {
                    rlStatisticsPortRx              Counter,
                    rlStatisticsPortTx              Counter,
                    rlStatisticsPortUtilization     INTEGER (0..10000)
                }

                rlStatisticsPortRx OBJECT-TYPE
                    SYNTAX      Counter
                    MAX-ACCESS  read-only
                    STATUS      current
                    DESCRIPTION
                        " Amount of inbound traffic per port "
                    ::=  { rlStatisticsPortEntry 1 }

                rlStatisticsPortTx OBJECT-TYPE
                    SYNTAX      Counter
                    MAX-ACCESS  read-only
                    STATUS      current
                    DESCRIPTION
                        " Amount of outbound traffic per port "
                    ::=  { rlStatisticsPortEntry 2 }

                rlStatisticsPortUtilization OBJECT-TYPE
                    SYNTAX      INTEGER (0..10000)
                    MAX-ACCESS  read-only
                    STATUS      current
                    DESCRIPTION
                        " utilization percentage per port "
                    ::=  { rlStatisticsPortEntry 3 }

        END

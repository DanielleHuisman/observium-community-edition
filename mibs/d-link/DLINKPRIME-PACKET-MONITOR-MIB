--  *****************************************************************
--  DLINKPRIME-PACKET-MONITOR-MIB.mib : Packet Monitoring MIB
-- 
--  Copyright (c) 2014 D-Link Corporation, all rights reserved.
--   
--  *****************************************************************
DLINKPRIME-PACKET-MONITOR-MIB DEFINITIONS ::= BEGIN

    IMPORTS
    MODULE-IDENTITY,
    OBJECT-TYPE,
    Unsigned32,
    Integer32
            FROM SNMPv2-SMI
    DisplayString, RowStatus 
            FROM SNMPv2-TC
    MODULE-COMPLIANCE, OBJECT-GROUP
		    FROM SNMPv2-CONF
    ifIndex, InterfaceIndexOrZero
            FROM IF-MIB
    VlanId       
        FROM Q-BRIDGE-MIB            
    PortList
        FROM Q-BRIDGE-MIB       
    
    dlinkPrimeCommon
            FROM DLINK-ID-REC-MIB;

    dlinkPrimePktMonitorMIB MODULE-IDENTITY
        LAST-UPDATED "201406030000Z"
        ORGANIZATION "D-Link Corp."
        CONTACT-INFO
            "         D-Link Corporation
            
             Postal: No. 289, Sinhu 3rd Rd., Neihu District,
                     Taipei City 114, Taiwan, R.O.C
             Tel:    +886-2-66000123
             E-mail: tsd@dlink.com.tw
            "        
        DESCRIPTION
            "This MIB module defines objects for configuring Monitoring Traffic.
            Acronyms and terminology:
            SPAN (Switched Port Analyzer): Mirror network traffic for analysis 
                by a network analyzer. 
            Local-SPAN: The SPAN feature is local when the monitored ports are 
                all located on the same switch as the destination port. 
            RSPAN (Remote SPAN):  Source ports and destination ports that are 
                distributed across multiple switches, allowing one to monitor 
                any destination port located on the RSPAN VLAN."
                      
        REVISION "201406030000Z"
        DESCRIPTION 
            "This is the first version of the MIB file."           
    ::= { dlinkPrimeCommon 10 }

-- -----------------------------------------------------------------------------
    dpPktMonMIBNotifications    OBJECT IDENTIFIER ::= { dlinkPrimePktMonitorMIB 0 }
    dpPktMonMIBObjects          OBJECT IDENTIFIER ::= { dlinkPrimePktMonitorMIB 1 }
    dpPktMonMIBConformance      OBJECT IDENTIFIER ::= { dlinkPrimePktMonitorMIB 2 }

-- -----------------------------------------------------------------------------
-- Monitor Session Management
-- -----------------------------------------------------------------------------
    dpPktMonDstPort OBJECT-TYPE 
           SYNTAX      Integer32
           MAX-ACCESS  read-write 
           STATUS      current 
           DESCRIPTION 
               "Specifies the port to which the mirrored traffic in the system 
                is to be copied." 
           ::= { dpPktMonMIBObjects 1 }
    
    dpPktMonMirrorType OBJECT-TYPE 
           SYNTAX  INTEGER {
               disable(0),
               rx(1),
               tx(2),
               both(3)
           } 
           MAX-ACCESS  read-write 
           STATUS      current 
           DESCRIPTION 
               "Specifies the mirror packet type." 
           ::= { dpPktMonMIBObjects 2 }
           
    dpPktMonSrcPort OBJECT-TYPE 
           SYNTAX      PortList
           MAX-ACCESS  read-write 
           STATUS      current 
           DESCRIPTION 
               "Provides control to enable or disable mirroring 
                over this interface to the destination port."
           ::= { dpPktMonMIBObjects 3 }
    
-- -----------------------------------------------------------------------------    
-- MIB Conformance statements
-- -----------------------------------------------------------------------------   
    dpPktMonMIBCompliances  OBJECT IDENTIFIER
        ::= { dpPktMonMIBConformance 1 }

		
END

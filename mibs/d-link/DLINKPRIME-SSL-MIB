--  *****************************************************************
--  DLINKPRIME-SSL-MIB.mib : Secure Socket Layer MIB
-- 
--  Copyright (c) 2014 D-Link Corporation, all rights reserved.
--   
--  *****************************************************************
DLINKPRIME-SSL-MIB DEFINITIONS ::= BEGIN

    IMPORTS
        MODULE-IDENTITY, OBJECT-TYPE, Integer32, Unsigned32
            FROM SNMPv2-SMI
        RowStatus, TruthValue,DisplayString
            FROM SNMPv2-TC
        OBJECT-GROUP, MODULE-COMPLIANCE			
            FROM SNMPv2-CONF                                    
        InetAddressType,InetAddress
            FROM INET-ADDRESS-MIB                           
        dlinkPrimeCommon
            FROM DLINK-ID-REC-MIB;


    dlinkPrimeSslMIB MODULE-IDENTITY
        LAST-UPDATED "201404260000Z"
        ORGANIZATION "D-Link Corp."
        CONTACT-INFO
            "        D-Link Corporation

             Postal: No. 289, Sinhu 3rd Rd., Neihu District,
                     Taipei City 114, Taiwan, R.O.C
             Tel:     +886-2-66000123
             E-mail: tsd@dlink.com.tw
            "
        DESCRIPTION
            "This MIB module defines objects for Secure Socket Layer (SSL)."
        REVISION "201404260000Z"
        DESCRIPTION
            "This is the first version of the MIB file for 'SSL'
             functionality."
    ::= { dlinkPrimeCommon 16}

-- -----------------------------------------------------------------------------
    dpSslNotifications    OBJECT IDENTIFIER ::= { dlinkPrimeSslMIB 0 }
    dpSslObjects          OBJECT IDENTIFIER ::= { dlinkPrimeSslMIB 1 }
    dpSslConformance      OBJECT IDENTIFIER ::= { dlinkPrimeSslMIB 2 }

-- -------------------------------------------------------------------------- 
    dpSslConfiguration  OBJECT IDENTIFIER ::= { dpSslObjects 1 }

    dpSslServiceEnabled OBJECT-TYPE
   		SYNTAX          TruthValue
  		MAX-ACCESS      read-write
   		STATUS          current
   		DESCRIPTION
           "A Boolean value represents the SSL server is Enabled or Disabled."
   		::= { dpSslConfiguration 1 }
            
END

--  *****************************************************************
--  DLINKPRIME-TRAFFIC-SEGMENT-MIB.mib : Traffic Segmentation MIB
-- 
--  Copyright (c) 2014 D-Link Corporation, all rights reserved.
--   
--  *****************************************************************

    DLINKPRIME-TRAFFIC-SEGMENT-MIB DEFINITIONS ::= BEGIN

    IMPORTS
        MODULE-IDENTITY,OBJECT-TYPE     FROM SNMPv2-SMI
        ifIndex,
        InterfaceIndex                  FROM IF-MIB
        MODULE-COMPLIANCE,
        OBJECT-GROUP                    FROM SNMPv2-CONF
        PortList                        FROM Q-BRIDGE-MIB
        dlinkPrimeCommon                FROM DLINK-ID-REC-MIB;


    dlinkPrimeTrafficSegMIB MODULE-IDENTITY
        LAST-UPDATED "201404260000Z"
        ORGANIZATION "D-Link Corp."
        CONTACT-INFO
            "        D-Link Corporation

             Postal: No. 289, Sinhu 3rd Rd., Neihu District,
                     Taipei City 114, Taiwan, R.O.C
             Tel:     +886-2-66000123
             E-mail: tsd@dlink.com.tw
            "
        DESCRIPTION
            "This MIB module defines objects for Traffic Segmentation."            
            
        REVISION     "201404260000Z"
        DESCRIPTION 
            "This is the first version of the MIB file."    
        ::= { dlinkPrimeCommon 25 }
  

-- ---------------------------------------------------------------------------------------------
    dpTrafficSegNotifications    OBJECT IDENTIFIER ::= { dlinkPrimeTrafficSegMIB 0 }
    dpTrafficSegObjects          OBJECT IDENTIFIER ::= { dlinkPrimeTrafficSegMIB 1 }
    dpTrafficSegConformance      OBJECT IDENTIFIER ::= { dlinkPrimeTrafficSegMIB 2 }

-- ---------------------------------------------------------------------------------------------
    dpTrafficSegForwardDomainTable    OBJECT-TYPE
        SYNTAX          SEQUENCE OF DpTrafficSegForwardDomainEntry
        MAX-ACCESS      not-accessible
        STATUS          current   
        DESCRIPTION            
            "A list of specification of forwarding domains for Traffic Segmentation."            
    ::= { dpTrafficSegObjects 1 }

    dpTrafficSegForwardDomainEntry    OBJECT-TYPE
        SYNTAX          DpTrafficSegForwardDomainEntry
        MAX-ACCESS      not-accessible
        STATUS          current   
        DESCRIPTION            
            "An entry indicates the setting of forwarding domain on an interface."
        INDEX  { ifIndex }
        ::= { dpTrafficSegForwardDomainTable 1 }

    DpTrafficSegForwardDomainEntry ::= SEQUENCE
    {
        dpTrafficSegForwardPorts    PortList
    }

    dpTrafficSegForwardPorts    OBJECT-TYPE
        SYNTAX                 PortList
        MAX-ACCESS             read-write
        STATUS                 current
        DESCRIPTION
            "This object indicates the forward domain (a set of ports) on the
            interface."
        ::= { dpTrafficSegForwardDomainEntry 1 }

-- -----------------------------------------------------------------------------
-- MIB Conformance statements
-- -----------------------------------------------------------------------------
    dpTrafficSegMIBCompliances    OBJECT IDENTIFIER
        ::= { dpTrafficSegConformance 1 }

    dpTrafficSegMIBGroups    OBJECT IDENTIFIER
        ::= { dpTrafficSegConformance 2 } 
    
    dpTrafficSegMIBCompliance    MODULE-COMPLIANCE
        STATUS                  current
        DESCRIPTION
            "The compliance statement for entities which implement the 
            DLINKPRIME-TRAFFIC-SEGMENT-MIB."
        MODULE          -- this module
        MANDATORY-GROUPS
        {   
            dpTrafficSegIfCfgGroup           
        }                 
        ::= { dpTrafficSegMIBCompliances 1 }

-- -----------------------------------------------------------------------------        
    dpTrafficSegIfCfgGroup    OBJECT-GROUP
        OBJECTS
        { 
            dpTrafficSegForwardPorts
        }
        STATUS current
        DESCRIPTION 
            "A collection of objects providing management of the Traffic
            Segmentation feature."
        ::= { dpTrafficSegMIBGroups 1 }
  
END

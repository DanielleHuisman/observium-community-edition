-- *****************************************************************
-- DLINKPRIME-WEB-COMMON-MIB:  D-Link WEB Common MIB
--
--  Copyright (c) 2014 D-Link Corporation, all rights reserved.
--
-- *****************************************************************

DLINKPRIME-WEB-COMMON-MIB DEFINITIONS ::= BEGIN

    IMPORTS
	    MODULE-IDENTITY, OBJECT-IDENTITY, OBJECT-TYPE,
	    Unsigned32
		    FROM SNMPv2-SMI
		TEXTUAL-CONVENTION, TruthValue, DisplayString
	        FROM SNMPv2-TC
	    MODULE-COMPLIANCE,	OBJECT-GROUP
		    FROM SNMPv2-CONF
	    dlinkPrimeCommon
		    FROM DLINK-ID-REC-MIB;


    dlinkPrimeWebCommonMIB MODULE-IDENTITY
	    LAST-UPDATED	"201404260000Z"
	    ORGANIZATION	"D-Link Corp."
	    CONTACT-INFO
		    "        D-Link Corporation

                Postal: No. 289, Sinhu 3rd Rd., Neihu District,
                        Taipei City 114, Taiwan, R.O.C
                Tel:     +886-2-66000123
                E-mail: tsd@dlink.com.tw
            "
	DESCRIPTION
		"The MIB module	for configuring Web common feature.
		This MIB module contains HTTP and HTTPS configuration."
	REVISION	 "201404260000Z"
	DESCRIPTION
		"This is the first version of the MIB file."  
	::= { dlinkPrimeCommon 28 }

-- ******************************************************************
-- Object Definition
-- ******************************************************************
    dpWebCommonMIBNotifications OBJECT IDENTIFIER ::= { dlinkPrimeWebCommonMIB 0 }        
    dpWebMIBObjects    		   	OBJECT IDENTIFIER ::= { dlinkPrimeWebCommonMIB 1 }
    dpWebCommonMIBConformance	OBJECT IDENTIFIER ::= { dlinkPrimeWebCommonMIB 2 }
    
-- ----------------------------------------------------------------------------- 
    dpWebSessionObjects    		OBJECT IDENTIFIER ::= { dpWebMIBObjects 1 }
    dpSslServerObjects    		OBJECT IDENTIFIER ::= { dpWebMIBObjects 2 }

-- -----------------------------------------------------------------------------
-- dpWebSessionObjects
-- -----------------------------------------------------------------------------
	dpWebSessionTimeout OBJECT-TYPE
        SYNTAX      Unsigned32 (60..36000)
        MAX-ACCESS  read-write
        STATUS      current
        DESCRIPTION
            "This object is used to configure the time in seconds of the web session timeout."
		DEFVAL   { 180 }
        ::= {  dpWebSessionObjects 1  }

-- -----------------------------------------------------------------------------
-- dpSslServerObjects
-- -----------------------------------------------------------------------------
	dpSslServerStatus OBJECT-TYPE
        SYNTAX  TruthValue
        MAX-ACCESS  read-write
        STATUS  current
        DESCRIPTION
            "This object indicates the SSL feature is support or not."
		DEFVAL   { false }
        ::= {  dpSslServerObjects 1  }

-- ******************************************************************
-- Conformance and Compliance
-- ******************************************************************

    dpWebCommonMIBCompliances  OBJECT IDENTIFIER ::= { dpWebCommonMIBConformance 1 }
    
    dpWebCommonGroups	      OBJECT IDENTIFIER ::= { dpWebCommonMIBConformance 2 }

    dpWebMIBCompliance MODULE-COMPLIANCE
	    STATUS	    current
	    DESCRIPTION
	        "The compliance statement for entities which implement the 
	        DLINKPRIME-WEB-COMMON-MIB.
	        "
	    MODULE	    -- this module
	    MANDATORY-GROUPS
	    {
	      dpWebSessionGroups,
	      dpSslServerGroups
	    }
   	    ::= { dpWebCommonMIBCompliances 1 }


-- units of conformance

    dpWebSessionGroups OBJECT-GROUP
        OBJECTS {
            dpWebSessionTimeout
        }
        STATUS      current
        DESCRIPTION
            "Objects for globally configuring Web session feature.
	        "
        ::= { dpWebCommonGroups 1 }

    dpSslServerGroups OBJECT-GROUP
        OBJECTS {
            dpSslServerStatus
        }
        STATUS      current
        DESCRIPTION
            "Objects for globally configuring SSL server feature.
	        "
        ::= { dpWebCommonGroups 2 }
END

Dlink-TrafficSegmentation-MIB DEFINITIONS ::= BEGIN

-- Title:      Dlink Switch Interfaces Private
-- Version:    7.46
-- Date:       13 Apr 2008

IMPORTS
    ifIndex                                         FROM IF-MIB
    Unsigned32, MODULE-IDENTITY, OBJECT-TYPE        FROM SNMPv2-SMI
    RowStatus, TruthValue, TEXTUAL-CONVENTION       FROM SNMPv2-TC
    PortList                                        FROM Q-BRIDGE-MIB
    rnd                                             FROM DLINK-3100-MIB;


rlTrafficSeg MODULE-IDENTITY
        LAST-UPDATED "200805031234Z"
        ORGANIZATION "Dlink, Inc."
        CONTACT-INFO
              "www.dlink.com"
        DESCRIPTION
            "<description>"
        REVISION "200805031234Z"
        DESCRIPTION
            "The private MIB module definition Traffic Segmentation MIB."
        ::= { rnd 138 }

--------------------------------------------------------------------------------
-- Traffic Segmentation
--------------------------------------------------------------------------------

--rlTrafficSegConfigTable

rlTrafficSegConfigTable OBJECT-TYPE
    SYNTAX      SEQUENCE OF RlTrafficSegConfigEntry
    MAX-ACCESS  not-accessible
    STATUS      current
    DESCRIPTION
        "A table containing entries to configure the traffic segmentation information table"
    ::= { rlTrafficSeg 1 }

rlTrafficSegConfigEntry OBJECT-TYPE
    SYNTAX      RlTrafficSegConfigEntry
    MAX-ACCESS  not-accessible
    STATUS      current
    DESCRIPTION
        "A table entry of configuration for traffic segmentation information table"
    INDEX   { rlTrafficSegConfigIndex}
    ::= { rlTrafficSegConfigTable 1 }

RlTrafficSegConfigEntry::= SEQUENCE {
        rlTrafficSegConfigIndex               Unsigned32,
        rlTrafficSegConfigIngressPorts        PortList,
        rlTrafficSegConfigEgressPorts         PortList,
        rlTrafficSegConfigRowStatus           RowStatus
}

rlTrafficSegConfigIndex      OBJECT-TYPE
    SYNTAX      Unsigned32 (1..65535)
    MAX-ACCESS  not-accessible
    STATUS      current
    DESCRIPTION
            "Running index of the entry."
    ::= { rlTrafficSegConfigEntry 1 }

rlTrafficSegConfigIngressPorts        OBJECT-TYPE
    SYNTAX PortList
    MAX-ACCESS  read-write
    STATUS      current
    DESCRIPTION
        "List of ingress ports to configure in rlTrafficSegTable"
    ::= { rlTrafficSegConfigEntry 2 }

rlTrafficSegConfigEgressPorts  OBJECT-TYPE
    SYNTAX PortList
    MAX-ACCESS  read-write
    STATUS      current
    DESCRIPTION
        "List of egress ports to configure in rlTrafficSegTable"
    ::= { rlTrafficSegConfigEntry 3 }

rlTrafficSegConfigRowStatus OBJECT-TYPE
    SYNTAX      RowStatus
    MAX-ACCESS  read-create
    STATUS      current
    DESCRIPTION
        "This object indicates the status of this entry."
    ::= { rlTrafficSegConfigEntry 4 }

--rlTrafficSegTable

rlTrafficSegTable OBJECT-TYPE
    SYNTAX      SEQUENCE OF RlTrafficSegEntry
    MAX-ACCESS  not-accessible
    STATUS      current
    DESCRIPTION
        "A table containing entries of traffic segmentation configuration information"
    ::= { rlTrafficSeg 2 }

rlTrafficSegEntry OBJECT-TYPE
    SYNTAX      RlTrafficSegEntry
    MAX-ACCESS  not-accessible
    STATUS      current
    DESCRIPTION
        "A table entry of traffic segmentation information table"
    INDEX   { rlTrafficSegIndex }
    ::= { rlTrafficSegTable 1 }

RlTrafficSegEntry ::= SEQUENCE {
        rlTrafficSegIndex           Unsigned32,
        rlTrafficSegIngressPorts    PortList,
        rlTrafficSegEgressPorts     PortList,
        rlTrafficSegRowStatus       RowStatus
    }

rlTrafficSegIndex  OBJECT-TYPE
    SYNTAX      Unsigned32 (1..65535)
    MAX-ACCESS  not-accessible
    STATUS      current
    DESCRIPTION
            "Index to the table entry, analogue to source ID"
    ::= { rlTrafficSegEntry 1 }

rlTrafficSegIngressPorts        OBJECT-TYPE
    SYNTAX PortList
    MAX-ACCESS  read-write
    STATUS      current
    DESCRIPTION
        "List of the ingress ports of the entry"
    ::= { rlTrafficSegEntry 2 }

rlTrafficSegEgressPorts  OBJECT-TYPE
    SYNTAX PortList
    MAX-ACCESS  read-write
    STATUS      current
    DESCRIPTION
        " List of the ingress ports of the entry"
    ::= { rlTrafficSegEntry 3 }

rlTrafficSegRowStatus OBJECT-TYPE
    SYNTAX      RowStatus
    MAX-ACCESS  read-create
    STATUS      current
    DESCRIPTION
        "This object indicates the status of this entry."
    ::= { rlTrafficSegEntry 4 }

END

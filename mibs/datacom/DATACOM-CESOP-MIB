--
-- DATACOM Telematica
-- Copyright 2012-2013 by DATACOM (Teracom Telematica Ltda). All Rights Reserved.
-- This DATACOM SNMP MIB Specification is Datacom proprietary intellectual property.
--
-- This module will be extend, as required. The specification and other information
-- contained in this document can be modified without prior notice. The user should
-- consult Datacom to determine whether any such changes have been done.
--


DATACOM-CESOP-MIB DEFINITIONS ::= BEGIN

IMPORTS

        MODULE-IDENTITY, OBJECT-TYPE,
    Counter32, Counter64, Gauge32, Integer32
    enterprises
        FROM SNMPv2-SMI
    DisplayString, PhysAddress
        FROM SNMPv2-TC
        InterfaceIndex
        FROM IF-MIB
        datacomAccessDevicesMIBs
        FROM DATACOM-SMI;


dmCesopMIB MODULE-IDENTITY
        LAST-UPDATED "202010260000Z"
        ORGANIZATION "DATACOM"
        CONTACT-INFO
                "DATACOM
--
--               Postal: DATACOM
--                        Av. Franca, 735
--                        Navegantes, POA, RS
--                        CEP 90230-220
--                        BRAZIL
--
--          Tel:   +55(051)3358-0100
--	        Fax:   +55(051)3358-0101
--
-- 		      E-mail: datacom@datacom.ind.br"
        DESCRIPTION
                "The MIB module for CESoP."
        ::= { datacomAccessDevicesMIBs 300 }


dmCesopBundle				OBJECT IDENTIFIER ::= { dmCesopMIB 1 }
dmCesopPw					OBJECT IDENTIFIER ::= { dmCesopMIB 2 }
dmCesopSyncSource			OBJECT IDENTIFIER ::= { dmCesopMIB 3 }
dmCesopTdm					OBJECT IDENTIFIER ::= { dmCesopMIB 4 }
dmCesopSyncSourceHierarchy	OBJECT IDENTIFIER ::= { dmCesopMIB 5 }


--
-- dmCesopBundle
--
-- bundleCountersTable
--
bundleCountersTable OBJECT-TYPE
        SYNTAX      SEQUENCE OF BundleCountersEntry
        MAX-ACCESS  not-accessible
        STATUS      current
        DESCRIPTION "Table containing a collection of
          counters from bundle interfaces."
        ::= { dmCesopBundle 1 }

bundleCountersEntry OBJECT-TYPE
        SYNTAX      BundleCountersEntry
        MAX-ACCESS  not-accessible
        STATUS      current
        DESCRIPTION "An entry containing a collection of
          counters from bundle interfaces."
        INDEX       { bundleCountersIndex }
        ::= { bundleCountersTable 1 }

BundleCountersEntry ::= SEQUENCE
{
  bundleCountersIndex						Integer32,
  bundleCountersName						DisplayString,
  bundleCountersBufferOverflow			Counter32,
  bundleCountersBufferUnderflow			Counter32,
  bundleCountersLostPackets				Counter32,
  bundleCountersLostPacketsRate			Counter32,
  bundleCountersOutOfOrderPackets			Counter32,
  bundleCountersSequenceNumberViolation	Counter32,
  bundleCountersWrongSizePackets			Counter32,
  bundleCountersJitterBufferOccupation	Gauge32
}

bundleCountersIndex OBJECT-TYPE
        SYNTAX      Integer32
        MAX-ACCESS  read-only
        STATUS      current
        DESCRIPTION "A unique value, greater than zero,
          for each bundle interface."
        ::= { bundleCountersEntry 1 }

bundleCountersName OBJECT-TYPE
        SYNTAX      DisplayString (SIZE (0..127))
        MAX-ACCESS  read-only
        STATUS      current
        DESCRIPTION "A textual string containing the
          name of bundle interface."
        ::= { bundleCountersEntry 2 }

bundleCountersBufferOverflow OBJECT-TYPE
        SYNTAX      Counter32
        MAX-ACCESS  read-only
        STATUS      current
        DESCRIPTION "The number of overflows that occurred on bundle's
          jitter buffer."
        ::= { bundleCountersEntry 3 }

bundleCountersBufferUnderflow OBJECT-TYPE
        SYNTAX      Counter32
        MAX-ACCESS  read-only
        STATUS      current
        DESCRIPTION "The number of underflows that occurred on bundle's
          jitter-buffer."
        ::= { bundleCountersEntry 4 }

bundleCountersLostPackets OBJECT-TYPE
        SYNTAX      Counter32
        MAX-ACCESS  read-only
        STATUS      current
        DESCRIPTION "The number of packets removed from jitter buffer to
          be transmitted via TDM interface, with sequence number
          higher than expected while respecting the jitter buffer
          ability of reorder."
        ::= { bundleCountersEntry 5 }

bundleCountersLostPacketsRate OBJECT-TYPE
        SYNTAX      Counter32
        MAX-ACCESS  read-only
        STATUS      current
        DESCRIPTION "The rate of lost packets in packets per second."
        ::= { bundleCountersEntry 6 }

bundleCountersOutOfOrderPackets OBJECT-TYPE
        SYNTAX      Counter32
        MAX-ACCESS  read-only
        STATUS      current
        DESCRIPTION "The number of packets with sequence number different
          from the expected, but in the range where it can be
          reordered in jitter buffer."
        ::= { bundleCountersEntry 7 }

bundleCountersSequenceNumberViolation OBJECT-TYPE
        SYNTAX      Counter32
        MAX-ACCESS  read-only
        STATUS      current
        DESCRIPTION "The number of packets with sequence number
          exceeding the jitter-buffer capacity."
        ::= { bundleCountersEntry 8 }

bundleCountersWrongSizePackets OBJECT-TYPE
        SYNTAX      Counter32
        MAX-ACCESS  read-only
        STATUS      current
        DESCRIPTION "The number of packets received on bundle
          interface with different size of configured value."
        ::= { bundleCountersEntry 9 }

bundleCountersJitterBufferOccupation OBJECT-TYPE
        SYNTAX      Gauge32
        MAX-ACCESS  read-only
        STATUS      current
        DESCRIPTION "The jitter buffer size, in microseconds."
        ::= { bundleCountersEntry 10 }


--
-- dmCesopBundle
--
-- bundleStatusTable
--
bundleStatusTable OBJECT-TYPE
        SYNTAX      SEQUENCE OF BundleStatusEntry
        MAX-ACCESS  not-accessible
        STATUS      current
        DESCRIPTION "Table containing status information
          about the bundle interfaces."
        ::= { dmCesopBundle 2 }

bundleStatusEntry OBJECT-TYPE
        SYNTAX      BundleStatusEntry
        MAX-ACCESS  not-accessible
        STATUS      current
        DESCRIPTION "An entry containing status information
          about the bundle interfaces."
        INDEX       { bundleStatusIndex }
        ::= { bundleStatusTable 1 }

BundleStatusEntry ::= SEQUENCE
{
  bundleStatusIndex			Integer32,
  bundleStatusName			DisplayString,
  bundleStatusLocalBundle		INTEGER,
  bundleStatusRemoteBundle	INTEGER,
  bundleStatusLocalTdm		INTEGER,
  bundleStatusRemoteTdm		INTEGER,
  bundleStatusPacketSize		INTEGER,
  bundleStatusNextHop			INTEGER,
  bundleStatusMac				PhysAddress
}

bundleStatusIndex OBJECT-TYPE
        SYNTAX      Integer32
        MAX-ACCESS  read-only
        STATUS      current
        DESCRIPTION "A unique value, greater than zero,
          for each bundle interface."
        ::= { bundleStatusEntry 1 }

bundleStatusName OBJECT-TYPE
        SYNTAX      DisplayString (SIZE (0..127))
        MAX-ACCESS  read-only
        STATUS      current
        DESCRIPTION "A textual string containing the
          name of bundle interface."
        ::= { bundleStatusEntry 2 }

bundleStatusLocalBundle OBJECT-TYPE
        SYNTAX      INTEGER {
            OK(1),
            Fail(2)
          }
        MAX-ACCESS  read-only
        STATUS      current
        DESCRIPTION "Local bundle interface status. Values can be:
          OK(1): local bundle interface is ok, without failures;
          Fail(2): packet loss on local bundle interface is over the
          configured limit."
        ::= { bundleStatusEntry 3 }

bundleStatusRemoteBundle OBJECT-TYPE
        SYNTAX      INTEGER {
            OK(1),
            Fail(2),
            Unknown(6)
          }
        MAX-ACCESS  read-only
        STATUS      current
        DESCRIPTION "Remote bundle interface status. Values can be:
          OK(1): remote bundle interfaces is ok, without failures;
          Fail(2): packet loss on remote bundle interfaces is over
          the configured limit;
          Unknown(6): remote bundle interface status is unknown."
        ::= { bundleStatusEntry 4 }

bundleStatusLocalTdm OBJECT-TYPE
        SYNTAX      INTEGER {
            OK(1),
            Fail(2),
            RDI(3),
            NotAvailable(7),
            LDL(8)
          }
        MAX-ACCESS  read-only
        STATUS      current
        DESCRIPTION "Local TDM interface status. Values can be:
          OK(1): local TDM interface is ok, without failures;
          Fail(2): an error occurs on local TDM interface;
          RDI(3): an error occurs on remote TDM interface
          (Remote Defect Indicator);
          NotAvailable(7): not used in running configuration..
          LDL(8): LDL test is enabled"
        ::= { bundleStatusEntry 5 }

bundleStatusRemoteTdm OBJECT-TYPE
        SYNTAX      INTEGER {
            OK(1),
            Fail(2),
            RDI(3),
            Unknown(6)
          }
        MAX-ACCESS  read-only
        STATUS      current
        DESCRIPTION "Remote TDM interface status. Values can be:
          OK(1): local TDM interface is ok, without failures;
          Fail(2): an error occurs on local TDM interface;
          RDI(3): an error occurs on remote TDM interface
          (Remote Defect Indicator);
          Unknown(6): remote TDM interface status is unknown."
        ::= { bundleStatusEntry 6 }

bundleStatusPacketSize OBJECT-TYPE
        SYNTAX      INTEGER {
            OK(1),
            Mismatch(4),
            Unknown(6)
          }
        MAX-ACCESS  read-only
        STATUS      current
        DESCRIPTION "Indicates if local bundle interface is receiving
          packets with right sizes. Values can be:
          OK(1): received packets are with correct size;
          Mismatch(4): received packets are with different size;
          Unknown(6): remote bundle interface status is unknown.
          of the configured value."
        ::= { bundleStatusEntry 7 }

bundleStatusNextHop OBJECT-TYPE
        SYNTAX      INTEGER {
            OK(1),
            Down(5)
          }
        MAX-ACCESS  read-only
        STATUS      current
        DESCRIPTION "Bundle next-hop interface status. Values can be:
          OK(1): next-hop interface is ok;
          Down(5): is impossible to access next-hop IP address
          configured on bundle interface."
        ::= { bundleStatusEntry 8 }

bundleStatusMac OBJECT-TYPE
        SYNTAX      PhysAddress
        MAX-ACCESS  read-only
        STATUS      current
        DESCRIPTION "Bundle next-hop physical(MAC) address."
        ::= { bundleStatusEntry 9 }


--
-- dmCesopPw
--
pwCountersTable OBJECT-TYPE
        SYNTAX      SEQUENCE OF PwCountersEntry
        MAX-ACCESS  not-accessible
        STATUS      current
        DESCRIPTION "Table containing a collection of
          counters from PW interfaces."
        ::= { dmCesopPw 1 }

pwCountersEntry OBJECT-TYPE
        SYNTAX      PwCountersEntry
        MAX-ACCESS  not-accessible
        STATUS      current
        DESCRIPTION "An entry containing a collection of
          counters from PW interfaces."
        INDEX       { pwCountersIndex }
        ::= { pwCountersTable 1 }

PwCountersEntry ::= SEQUENCE
{
  pwCountersIndex						Integer32,
  pwCountersPacketsInput				Counter64,
  pwCountersTotalDiscardInput			Counter64,
  pwCountersBundlesReachedPackets		Counter64,
  pwCountersOctetsInput				Counter64,
  pwCountersOctetsOutput				Counter64,
  pwCountersUnicastInput				Counter64,
  pwCountersUnicastOutput				Counter64,
  pwCountersDiscardInput				Counter64,
  pwCountersDiscardOutput				Counter64,
  pwCountersErrorInput				Counter64,
  pwCountersErrorOutput				Counter64,
  pwCountersUnknownProtosInput		Counter64,
  pwCountersQLen						Gauge32
}

pwCountersIndex OBJECT-TYPE
        SYNTAX      Integer32
        MAX-ACCESS  read-only
        STATUS      current
        DESCRIPTION "A unique value, greater than zero,
          for each PW interface."
        ::= { pwCountersEntry 1 }

pwCountersPacketsInput OBJECT-TYPE
        SYNTAX      Counter64
        MAX-ACCESS  read-only
        STATUS      current
        DESCRIPTION "The total number of packets received
          by the equipment via PW interface."
        ::= { pwCountersEntry 2 }

pwCountersTotalDiscardInput OBJECT-TYPE
        SYNTAX      Counter64
        MAX-ACCESS  read-only
        STATUS      current
        DESCRIPTION "The total number of inbound packets discarded
          by the equipment."
        ::= { pwCountersEntry 3 }

pwCountersBundlesReachedPackets OBJECT-TYPE
        SYNTAX      Counter64
        MAX-ACCESS  read-only
        STATUS      current
        DESCRIPTION "The total number of packets sent
          to the local bundle interface."
        ::= { pwCountersEntry 4 }

pwCountersOctetsInput OBJECT-TYPE
        SYNTAX      Counter64
        MAX-ACCESS  read-only
        STATUS      current
        DESCRIPTION "The total number of octets received on PW
          interface."
        ::= { pwCountersEntry 5 }

pwCountersOctetsOutput OBJECT-TYPE
        SYNTAX      Counter64
        MAX-ACCESS  read-only
        STATUS      current
        DESCRIPTION "The total number of octets transmitted out of PW
          interface."
        ::= { pwCountersEntry 6 }

pwCountersUnicastInput OBJECT-TYPE
        SYNTAX      Counter64
        MAX-ACCESS  read-only
        STATUS      current
        DESCRIPTION "The number of packets, delivered by this sub-layer to a
          higher (sub-)layer, which were not addressed to a multicast
          or broadcast address at this sub-layer."
        ::= { pwCountersEntry 7 }

pwCountersUnicastOutput OBJECT-TYPE
        SYNTAX      Counter64
        MAX-ACCESS  read-only
        STATUS      current
        DESCRIPTION  "The total number of packets that higher-level protocols
          requested be transmitted, and which were not addressed to a
          multicast or broadcast address at this sub-layer, including
          those that were discarded or not sent."
        ::= { pwCountersEntry 8 }

pwCountersDiscardInput OBJECT-TYPE
        SYNTAX      Counter64
        MAX-ACCESS  read-only
        STATUS      current
        DESCRIPTION "The number of inbound packets which were chosen to be
          discarded even though no errors had been detected to prevent
          their being deliverable to a higher-layer protocol.  One
          ble reason for discarding such a packet could be to
          up buffer space."
        ::= { pwCountersEntry 9 }

pwCountersDiscardOutput OBJECT-TYPE
        SYNTAX      Counter64
        MAX-ACCESS  read-only
        STATUS      current
        DESCRIPTION "The number of outbound packets which were chosen to be
          discarded even though no errors had been detected to prevent
          their being transmitted.  One possible reason for discarding
          such a packet could be to free up buffer space."
        ::= { pwCountersEntry 10 }

pwCountersErrorInput OBJECT-TYPE
        SYNTAX      Counter64
        MAX-ACCESS  read-only
        STATUS      current
        DESCRIPTION "The number of inbound packets that contained
          errors preventing them from being deliverable
          to a higher-layer protocol."
        ::= { pwCountersEntry 11 }

pwCountersErrorOutput OBJECT-TYPE
        SYNTAX      Counter64
        MAX-ACCESS  read-only
        STATUS      current
        DESCRIPTION "The number of outbound packets that could not
          be transmitted via PW interface because of errors."
        ::= { pwCountersEntry 12 }

pwCountersUnknownProtosInput OBJECT-TYPE
        SYNTAX      Counter64
        MAX-ACCESS  read-only
        STATUS      current
        DESCRIPTION "The number of packets received via the PW
          interface which were discarded because of
          unknown or unsupported protocol."
        ::= { pwCountersEntry 13 }

pwCountersQLen OBJECT-TYPE
        SYNTAX      Gauge32
        MAX-ACCESS  read-only
        STATUS      current
        DESCRIPTION " The length of the output packet
          queue (in packets) of PW interface."
        ::= { pwCountersEntry 14 }


--
-- dmCesopSyncSource
--
syncSourceTransmitClockSource OBJECT-TYPE
        SYNTAX      INTEGER {
            Internal(1),
            TDM(2),
            SDHVC12(3),
            SDH(4),
            PTP(5),
            External(6),
            Adaptive(7)
          }
        MAX-ACCESS  read-only
        STATUS      current
        DESCRIPTION "Clock source. The sources can be:
          Internal(1): the equipment is the clock source;
          TDM(2): the clock received at the specified TDM interface
          is used as clock source for the equipment;
          SDHVC12(3): the clock received by SDHVC12 is used as clock
          source for equipment;
          SDH(4): the clock received by SDH is used as clock
          source for equipment;
          PTP(5): the clock received by PTP is used as clock
          source for equipment;
          External(6): the clock received by an external interface,
          connected to equipment, is used as clock source for the
          equipment;
          Adaptive(7): the clock received at the specified bundle
          interface is used as clock source for the equipment."
        ::= { dmCesopSyncSource 1 }

syncSourceStatusOutOfLimits OBJECT-TYPE
        SYNTAX      INTEGER {
            No(1),
            Yes(2)
          }
        MAX-ACCESS  read-only
        STATUS      current
        DESCRIPTION "Transmit clock source out of limits status.
          Values can be:
          No(1): transmit clock source isn't out of limits;
          Yes(2): transmit clock source is out of limits."
        ::= { dmCesopSyncSource 2 }

syncSourceStatusDetail OBJECT-TYPE
        SYNTAX      INTEGER {
            DontCare(1),
            FreeRun(2),
            HoldOver(3),
            Locked(4),
            Acquiring(5),
            Misconfigured(6)
          }
        MAX-ACCESS  read-only
        STATUS      current
        DESCRIPTION "Transmit clock source status detailed.
          Values can be:
          DontCare(1): transmit clock source is don't care;
          FreeRun(2): transmit clock source is free run;
          HoldOver(3): transmit clock source is hold over;
          Locked(4): transmit clock source is locked;
          Acquiring(5): transmit clock source is being acquired;
          Misconfigured(6): transmit clock source is misconfigured."
        ::= { dmCesopSyncSource 3 }

syncSourceActiveHierarchy OBJECT-TYPE
        SYNTAX      Integer32
        MAX-ACCESS  read-only
        STATUS      current
        DESCRIPTION "Number of the active hierarchy."
        ::= { dmCesopSyncSource 4 }


--
-- dmCesopTdm
--
tdmStatusTable OBJECT-TYPE
        SYNTAX      SEQUENCE OF TdmStatusEntry
        MAX-ACCESS  not-accessible
        STATUS      current
        DESCRIPTION "Table containing status information
          about the TDM interfaces."
        ::= { dmCesopTdm 1 }

tdmStatusEntry OBJECT-TYPE
        SYNTAX      TdmStatusEntry
        MAX-ACCESS  not-accessible
        STATUS      current
        DESCRIPTION "An entry containing status information
          about the TDM interfaces."
        INDEX       { tdmStatusIndex }
        ::= { tdmStatusTable 1 }

TdmStatusEntry ::= SEQUENCE
{
  tdmStatusIndex			Integer32,
  tdmStatusLinkStatus		INTEGER,
  tdmStatusRemoteAlarm	INTEGER,
  tdmStatusCasStatus		INTEGER,
  tdmStatusCrcStatus		INTEGER
}

tdmStatusIndex OBJECT-TYPE
        SYNTAX      Integer32
        MAX-ACCESS  read-only
        STATUS      current
        DESCRIPTION "A unique value, greater than zero,
          for each TDM interface."
        ::= { tdmStatusEntry 1 }

tdmStatusLinkStatus OBJECT-TYPE
        SYNTAX      INTEGER {
            OK(1),
            LOS(2),
            AIS(3),
            LOF(4)
          }
        MAX-ACCESS  read-only
        STATUS      current
        DESCRIPTION "Status of the TDM link. Values can be:
          OK(1): TDM link doesn't have any failures;
          LOS(2): TDM link has LOS(Loss Of Signal) failure;
          AIS(3): TDM link has AIS(Alarm Indication Signal) failure;
          LOF(4): TDM link has LOF(Loss Of Frame) failure."
        ::= { tdmStatusEntry 2 }

tdmStatusRemoteAlarm OBJECT-TYPE
        SYNTAX      INTEGER {
            OK(1),
            RALM(6),
            NotAvailable(8)
          }
        MAX-ACCESS  read-only
        STATUS      current
        DESCRIPTION "Status of the Remote Alarm. Values can be:
          OK(1): TDM link doesn't have remote alarm;
          RALM(6): TDM link has remote alarm;
          NotAvailable(8): not used in running configuration."
        ::= { tdmStatusEntry 3 }

tdmStatusCasStatus OBJECT-TYPE
        SYNTAX      INTEGER {
            OK(1),
            LOM(5),
            NotAvailable(8)
          }
        MAX-ACCESS  read-only
        STATUS      current
        DESCRIPTION "Status of CAS alignment. Values can be:
          OK(1): CAS alignment doesn't have any failure;
          LOM(5): CAS alignment has LOM(Loss Of Multiframe) failure;
          NotAvailable(8): not used in running configuration."
        ::= { tdmStatusEntry 4 }

tdmStatusCrcStatus OBJECT-TYPE
        SYNTAX      INTEGER {
            OK(1),
            Fail(7),
            NotAvailable(8)
          }
        MAX-ACCESS  read-only
        STATUS      current
        DESCRIPTION "Status of CRC alignment. Values can be:
          OK(1): CRC alignment doesn't have any failure;
          Fail(7): CRC alignment has failed;
          NotAvailable(8): not used in running configuration."
        ::= { tdmStatusEntry 5 }


--
-- dmCesopSyncSourceHierarchy
--
syncSourceHierarchyTable OBJECT-TYPE
        SYNTAX      SEQUENCE OF syncSourceHierarchyEntry
        MAX-ACCESS  not-accessible
        STATUS      current
        DESCRIPTION "Table containing configuration information
          about the sync source hierarchies."
        ::= { dmCesopSyncSourceHierarchy 1 }

syncSourceHierarchyEntry OBJECT-TYPE
        SYNTAX      syncSourceHierarchyEntry
        MAX-ACCESS  not-accessible
        STATUS      current
        DESCRIPTION "Table containing configuration information
          about the sync source hierarchies."
        INDEX       { syncSourceHierarchyIndex }
        ::= { syncSourceHierarchyTable 1 }

syncSourceHierarchyEntry ::= SEQUENCE
{
  syncSourceHierarchyIndex				Integer32
  syncSourceHierarchyEnable				INTEGER
  syncSourceHierarchyTransmitClockSource	INTEGER
  syncSourceHierarchyOutOfLimits			INTEGER
  syncSourceHierarchyStatusDetail			INTEGER
}

syncSourceHierarchyIndex OBJECT-TYPE
        SYNTAX      Integer32
        MAX-ACCESS  read-only
        STATUS      current
        DESCRIPTION "A unique value, greater than zero,
          for each sync source hierarchy."
        ::= { syncSourceHierarchyEntry 1 }

syncSourceHierarchyEnable OBJECT-TYPE
        SYNTAX      INTEGER {
            No(1),
            Yes(2)
          }
        MAX-ACCESS  read-only
        STATUS      current
        DESCRIPTION "Indicates if the hierarchy is enabled and in use. Values can be:
          No(1): The hierarchy is enabled and in use;
          Yes(2): The hierarchy is disabled and not in use."
        ::= { syncSourceHierarchyEntry 2 }

syncSourceHierarchyTransmitClockSource OBJECT-TYPE
        SYNTAX      INTEGER {
            Internal(1),
            TDM(2),
            SDHVC12(3),
            SDH(4),
            PTP(5),
            External(6),
            Adaptive(7)
          }
        MAX-ACCESS  read-only
        STATUS      current
        DESCRIPTION "Clock source. The sources can be:
          Internal(1): the equipment is the clock source;
          TDM(2): the clock received at the specified TDM interface
          is used as clock source for the equipment;
          SDHVC12(3): the clock received by SDHVC12 is used as clock
          source for equipment;
          SDH(4): the clock received by SDH is used as clock
          source for equipment;
          PTP(5): the clock received by PTP is used as clock
          source for equipment;
          External(6): the clock received by an external interface,
          connected to equipment, is used as clock source for the
          equipment;
          Adaptive(7): the clock received at the specified bundle
          interface is used as clock source for the equipment."
        ::= { syncSourceHierarchyEntry 3 }

syncSourceHierarchyOutOfLimits OBJECT-TYPE
        SYNTAX      INTEGER {
            No(1),
            Yes(2)
          }
        MAX-ACCESS  read-only
        STATUS      current
        DESCRIPTION "Sync source hierarchy out of limits status.
          Values can be:
          No(1): sync source hierarchy isn't out of limits;
          Yes(2): sync source hierarchy is out of limits."
        ::= { syncSourceHierarchyEntry 4 }

syncSourceHierarchyStatusDetail OBJECT-TYPE
        SYNTAX      INTEGER {
            Available(2),
            Fail(3)
          }
        MAX-ACCESS  read-only
        STATUS      current
        DESCRIPTION "Sync source hierarchy state. Values can be:
          Available(2): sync source hierarchy is available;
          Fail(3): sync source hierarchy is fail."
        ::= { syncSourceHierarchyEntry 5 }


END

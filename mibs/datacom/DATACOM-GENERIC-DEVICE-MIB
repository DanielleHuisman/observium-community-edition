--
-- DATACOM Telematica
-- Copyright 2001-2009 by Datacom Telematica (Teracom Telematica Ltda). All Rights Reserved.
-- This DATACOM SNMP MIB Specification is Datacom intellectual property.
--
-- This module will be extend, as required. The specification and other information
-- contained in this document can be modified without prior notice. The user should
-- consult Datacom to determine whether any such changes have been done.
--

DATACOM-GENERIC-DEVICE-MIB	DEFINITIONS ::= BEGIN


IMPORTS
	TimeTicks, Counter
		FROM RFC1155-SMI
	OBJECT-TYPE
		FROM RFC-1212
	datacomGenericMIBs, datacomModules
		FROM DATACOM-SMI;



datacomGenericDeviceMIBModule OBJECT IDENTIFIER ::={ datacomModules 23 }
--MODULE-IDENTITY
--	LAST-UPDATED "0910150000Z"
--	ORGANIZATION "Datacom Telemática"
--	CONTACT-INFO
--		     "Datacom Telemática
--
--		      Postal: Datacom Telematica
--			          Av. França, 735
--			          Navegantes, POA, RS
--			          CEP 90230-220
--			          BRAZIL
--
--   		  Tel:   +55(051)3358-0100
--		      Fax:   +55(051)3358-0101
--
--	  	      E-mail: datacom@datacom-telematica.com.br"
--	DESCRIPTION
--		" The MIB module for Datacom generic devices. "
--
--
--  -- -- -- -- -- -- -- -- -- --  -- -- -- -- -- -- -- -- -- --

dmGenericDeviceMIB OBJECT IDENTIFIER ::={ datacomGenericMIBs 3 }


--  -- -- -- -- -- -- -- -- -- --  -- -- -- -- -- -- -- -- -- --
 -- textual conventions

      DisplayString ::= OCTET STRING
      -- This data type is used to model textual information taken
      -- from the NVT ASCII character set.  By convention, objects
      -- with this syntax are declared as having
      --
      --      SIZE (0..255)




--  -- -- -- -- -- -- -- -- -- --  -- -- -- -- -- -- -- -- -- --

	DmUnsigned	 	::= Unsigned32
	DmDevIndex		::= INTEGER (1..3)
	DmDevLocalIndex ::= INTEGER (1..17)
		-- where 	1 - local devices
		-- 			2..17 - remoteDevice1 .. remoteDevice16
    DmSlotIndex		::= INTEGER (1..9)
    	-- the card id (physical or logical card)
    DmPortIndex		::= INTEGER

        -- the interface number

    DmTrapIndex		::= INTEGER (1..16383)


-- ######  OBJECTS   ########

--
-- groups
dmGenDvInf			OBJECT IDENTIFIER	::={ dmGenericDeviceMIB 1 }
dmGenDvStatus		OBJECT IDENTIFIER	::={ dmGenericDeviceMIB 2 }
dmGenDvConfig		OBJECT IDENTIFIER	::={ dmGenericDeviceMIB 3 }
dmGenDvAlarms       OBJECT IDENTIFIER	::={ dmGenericDeviceMIB 5 }

-- -- -- -- -- -- -- -- -- -- -- -- -- -- -- -- -- -- -- -- -- -- --


-- -- -- -- -- -- --
-- group dmGnDvInf

--
-- agent information

genDvInfMibVersion	OBJECT-TYPE
		SYNTAX	DisplayString
		ACCESS	read-only
		STATUS	mandatory
		DESCRIPTION
		   " The MIB version to this MIB supported by this agent
		     software version. "
::={ dmGenDvInf 1 }


--
-- device (mux) information

genDvInfDeviceTable OBJECT-TYPE
		SYNTAX	SEQUENCE OF GenDvInfDeviceEntry
		ACCESS	not-accessible
		STATUS	mandatory
		DESCRIPTION
			" Table with general information about the devices managed by
			  this MIB. "
::={ dmGenDvInf 10 }

genDvInfDeviceEntry OBJECT-TYPE
		SYNTAX	GenDvInfDeviceEntry
		ACCESS	not-accessible
		STATUS	mandatory
		DESCRIPTION
			" Entry of genDvInfDeviceTable. "
		INDEX 	{ genDvInfDeviceDevNo, genDvInfDeviceDevLocalId }
::={ genDvInfDeviceTable 1 }

GenDvInfDeviceEntry ::=
		SEQUENCE {
			genDvInfDeviceDevNo    			DmDevIndex,
			genDvInfDeviceDevLocalId		DmDevLocalIndex,
			genDvInfDeviceProduct			OBJECT IDENTIFIER,
			genDvInfDeviceFirmVersion		INTEGER,
			genDvInfDeviceBootVersion		DisplayString,
			genDvInfDeviceHWVersion			DisplayString,
			genDvInfDeviceSerialNo			DisplayString,
			genDvInfDeviceIdent				INTEGER,
			genDvInfDeviceFirmReleaseDate	DisplayString,
			genDvInfDeviceE2PROMversion		INTEGER,
			genDvInfDeviceFirmVersionString DisplayString,
			genDvInfDeviceVendor		  	INTEGER
			}

genDvInfDeviceDevNo	OBJECT-TYPE
    	SYNTAX   DmDevIndex
      	ACCESS   read-only
      	STATUS   mandatory
      	DESCRIPTION
      		" Device number. "
::= { genDvInfDeviceEntry 1 }

genDvInfDeviceDevLocalId	OBJECT-TYPE
		SYNTAX		DmDevLocalIndex
		ACCESS		read-only
		STATUS		mandatory
		DESCRIPTION
        	" Device local or remote. "
::={ genDvInfDeviceEntry 2 }

genDvInfDeviceProduct 	OBJECT-TYPE
		SYNTAX		OBJECT IDENTIFIER
		ACCESS		read-only
		STATUS		mandatory
		DESCRIPTION
			" The device product identification, through its
		   	  OBJECT IDENTIFIER in DATACOM-REG. "
::={ genDvInfDeviceEntry 3 }

genDvInfDeviceFirmVersion 	OBJECT-TYPE
		SYNTAX		INTEGER (0..255)
		ACCESS		read-only
		STATUS		mandatory
		DESCRIPTION
			" Device firmware version. "
::={ genDvInfDeviceEntry 4 }

genDvInfDeviceBootVersion 	OBJECT-TYPE
		SYNTAX		DisplayString
		ACCESS		read-only
		STATUS		mandatory
		DESCRIPTION
			" Device boot software version. "
::={ genDvInfDeviceEntry 5 }

genDvInfDeviceHWVersion 	OBJECT-TYPE
		SYNTAX		DisplayString
		ACCESS		read-only
		STATUS		mandatory
		DESCRIPTION
			" Device hardware version. "
::={ genDvInfDeviceEntry 6 }

genDvInfDeviceSerialNo 	OBJECT-TYPE
		SYNTAX		DisplayString
		ACCESS		read-only
		STATUS		mandatory
		DESCRIPTION
			" Device serial number. "
::={ genDvInfDeviceEntry 7 }

genDvInfDeviceIdent 	OBJECT-TYPE
		SYNTAX		INTEGER
		ACCESS		read-write
		STATUS		mandatory
		DESCRIPTION
			" Device identification. "
::={ genDvInfDeviceEntry 8 }

genDvInfDeviceFirmReleaseDate OBJECT-TYPE
		SYNTAX      DisplayString
		ACCESS		read-only
		STATUS		mandatory
		DESCRIPTION
			" The firmware date, using the format
			  yymmddhhmm. "
::={ genDvInfDeviceEntry 9 }

genDvInfDeviceE2PROMversion OBJECT-TYPE
		SYNTAX      INTEGER
		ACCESS		read-only
		STATUS		mandatory
		DESCRIPTION
			" The E2PROM version. "
::={ genDvInfDeviceEntry 10 }

genDvInfDeviceFirmVersionString OBJECT-TYPE
               SYNTAX      DisplayString
               ACCESS          read-only
               STATUS          mandatory
               DESCRIPTION
                       " The firmware version, using full format. "
::={ genDvInfDeviceEntry 11 }

genDvInfDeviceVendor OBJECT-TYPE
		SYNTAX	INTEGER {
			datacom						(1),
			ieru						(2),
			asga						(3),
			parks						(4),
			digitel						(5),
			none						(6),
			eletech						(7),
			xb-systems					(8),
			osp							(9),
			actelis						(10),
			juniper						(11),
			gdc							(12),
			monytel						(13),
			digistar					(14),
			objectNonexistentInModel  	(2000000254),
			infNotAvailable 		    (2000000255)
			}
		ACCESS		read-only
		STATUS		mandatory
		DESCRIPTION
			" Vendor information. The value 0
			  indicates a vendor not defined.  "
::={ genDvInfDeviceEntry 20 }




--
-- device card port information

genDvInfPortTable OBJECT-TYPE
		SYNTAX	SEQUENCE OF GenDvInfPortEntry
		ACCESS	not-accessible
		STATUS	mandatory
		DESCRIPTION
			" Table with general information about the device card ports managed by
			  this MIB. "
::={ dmGenDvInf 12 }

genDvInfPortEntry OBJECT-TYPE
		SYNTAX	GenDvInfPortEntry
		ACCESS	not-accessible
		STATUS	mandatory
		DESCRIPTION
			" Entry of genDvInfPortTable. "
		INDEX 	{ genDvInfPortDevNo, genDvInfPortDevLocalId, genDvInfPortSlotNo, genDvInfPortPortNo }
::={ genDvInfPortTable 1 }

GenDvInfPortEntry ::=
		SEQUENCE {
			genDvInfPortDevNo		DmDevIndex,
			genDvInfPortDevLocalId	DmDevLocalIndex,
			genDvInfPortSlotNo		DmSlotIndex,
    		genDvInfPortPortNo		DmPortIndex,
    		genDvInfPortModel		INTEGER,
			genDvInfPortFirmVersion	INTEGER,
    		genDvInfPortHwId		INTEGER,
    		genDvInfPortCardMib		OBJECT IDENTIFIER,
    		genDvInfPortConfigMode	INTEGER
			}

genDvInfPortDevNo	OBJECT-TYPE
    	SYNTAX   DmDevIndex
      	ACCESS   read-only
      	STATUS   mandatory
      	DESCRIPTION
      		" Device number. "
::= { genDvInfPortEntry 1 }

genDvInfPortDevLocalId	OBJECT-TYPE
		SYNTAX		DmDevLocalIndex
		ACCESS		read-only
		STATUS		mandatory
		DESCRIPTION
        	" Device local or remote. "
::={ genDvInfPortEntry 2 }

genDvInfPortSlotNo	OBJECT-TYPE
		SYNTAX		DmSlotIndex
		ACCESS		read-only
		STATUS		mandatory
		DESCRIPTION
        	" Slot number. "
::={ genDvInfPortEntry 3 }

genDvInfPortPortNo	OBJECT-TYPE
		SYNTAX		DmPortIndex
		ACCESS		read-only
		STATUS		mandatory
		DESCRIPTION
        	" Port number. "
::={ genDvInfPortEntry 4 }

genDvInfPortModel 	OBJECT-TYPE
		SYNTAX		INTEGER {
			dm705-ROUTER				(10),
			dm705-BBM					(129),
			dm705-GSHDSL-D				(137),
			dm705-GSHDSL				(139),
			dm705-FO					(144),
			dm705-E1					(170),
			dm705-POTS					(193),
			dm705-10BT					(208),
			dm705-V35D					(231),
			dm705-G64					(247),
			dm16E1-E3-G703				(301),
			dm16E1-E3-MM				(302),
			dm16E1-E3-SM				(303),
			dm16E1-E3-B13				(304),
			dm16E1-E3-B15				(305),
			dm16E1-E1					(341),
			dm16E1-V35					(361),
			dm16E1-10BT					(381),
			dm16E1-10BT-HW2				(382),
			dm16E1-G703-E3i				(391),
			dm16E1-ROUTER				(399),
			dm4E1-E3-G703				(401),
			dm4E1-E3-MM					(402),
			dm4E1-E3-SM					(403),
			dm4E1-E3-B13				(404),
			dm4E1-E3-B15				(405),
			dm4E1-E2-G703				(421),
			dm4E1-E2-MM					(422),
			dm4E1-E2-SM					(423),
			dm4E1-E2-B13				(424),
			dm4E1-E2-B15				(425),
			dm4E1-E1					(441),
			dm4E1-V35					(461),
			dm4E1-10BT					(481),
			dm4E1-10BT-HW2				(482),
			dm4E1-G703-E3i				(491),
			dm4E1-ROUTER				(499),
			dm706C-ROUTER				(501),
			dm706C-FO					(521),
			dm706C-E1					(531),
			dm706C-FXS					(541),
			dm706C-V35					(573),
			dm704C-E1					(631),
			dm704C-V35					(661),
			dm704S-E1					(731),
			dm704S-V35					(761),
			dm704CE-E1					(831),
			dm704CE-Bridge				(851),
			dm704CE-V35					(861),
			dm704SE-E1					(931),
			dm704SE-Bridge				(951),
			dm704SE-V35					(961),
			dm991C-GSHDSL				(1011),
			dm991C-GSHDSL-4F			(1012),
			dm991C-E1					(1031),
			dm991C-V35D					(1061),
			dm4E1S-E					(1101),
			dm4E1S-MM					(1102),
			dm4E1S-SM					(1103),
			dm4E1S-B13					(1104),
			dm4E1S-B15					(1105),
			dm4E1S-E1					(1141),
			dm4E1S-V35					(1161),
			dm4E1S-V28					(1167),
			dm991S-GSHDSL				(1211),
			dm991S-GSHDSL-4F			(1212),
			dm991S-E1					(1231),
			dm991S-V35D					(1261),
			dm991CE-GSHDSL				(1311),
			dm991CE-GSHDSL-4F			(1312),
			dm991CE-E1					(1331),
			dm991CE-Bridge				(1351),
			dm991CE-V35D				(1361),
			dm991SE-GSHDSL				(1411),
			dm991SE-GSHDSL-4F			(1412),
			dm991SE-E1					(1431),
			dm991SE-Bridge				(1451),
			dm991SE-V35D				(1461),
			dm300-8E1B-E				(1501),
			dm300-8E1B-MM				(1502),
			dm300-8E1B-SM				(1503),
			dm300-8E1B-B13				(1504),
			dm300-8E1B-B15				(1505),
			dm300-8E1B-E1				(1541),
			dm300-8E1B-Bridge			(1551),
			dm300-8E1B-V35				(1561),
			dm300-8E1B-V28				(1567),
			dm300-8E1B-DmLan			(1598),
			dm300-8E1B-ROUTER			(1599),
			dm300-8E1-E					(1601),
			dm300-8E1-MM				(1602),
			dm300-8E1-SM				(1603),
			dm300-8E1-B13				(1604),
			dm300-8E1-B15				(1605),
			dm300-8E1-E1				(1641),
			dm300-8E1-V35				(1661),
			dm300-8E1-V28				(1667),
			dm300-8E1-DmLan				(1698),
			dm300-8E1-ROUTER			(1699),
			dm991CR-Wan					(1701),
			dm991CR-GSHDSL				(1711),
			dm991CR-GSHDSL-4F			(1712),
			dm991CR-E1					(1731),
			dm16E1PacSeq-E3-G703		(2006),
			dm16E1PacSeq-E3-MM			(2007),
			dm16E1PacSeq-E3-SM			(2008),
			dm16E1PacSeq-E3-B13			(2009),
			dm16E1PacSeq-E3-B15			(2010),
			dm16E1PacSeq-E1				(2041),
			dm16E1PacSeq-V35			(2061),
			dm16E1PacSeq-10BT			(2081),
			dm16E1PacSeq-10BT-HW2		(2082),
			dm16E1PacSeq-ROUTER			(2099),
			dm4E1PacSeq-E3-G703			(2111),
			dm4E1PacSeq-E3-MM			(2112),
			dm4E1PacSeq-E3-SM			(2113),
			dm4E1PacSeq-E3-B13			(2114),
			dm4E1PacSeq-E3-B15			(2115),
			dm4E1PacSeq-E1				(2141),
			dm4E1PacSeq-V35				(2161),
			dm4E1PacSeq-10BT			(2181),
			dm4E1PacSeq-10BT-HW2		(2182),
			dm4E1PacSeq-ROUTER			(2199),
			dm16E1sII-E3-G703			(2301),
			dm16E1sII-E3-MM				(2302),
			dm16E1sII-E3-SM				(2303),
			dm16E1sII-E3-B13			(2304),
			dm16E1sII-E3-B15			(2305),
			dm16E1sII-E1				(2341),
			dm16E1sII-V35				(2361),
			dm16E1sII-Bridge			(2381),
			dm16E1sII-Bridge2			(2383),
			dm16E1sII-G703-E3i			(2391),
			dm16E1sII-DmLan  			(2398),
			dm16E1sII-ROUTER			(2399),
			dm4E1sII-E3-G703			(2401),
			dm4E1sII-E3-MM				(2402),
			dm4E1sII-E3-SM				(2403),
			dm4E1sII-E3-B13				(2404),
			dm4E1sII-E3-B15				(2405),
			dm4E1sII-E1					(2441),
			dm4E1sII-V35				(2461),
			dm4E1sII-Bridge				(2481),
			dm4E1sII-Bridge2			(2483),
			dm4E1sII-G703-E3i			(2491),
			dm4E1sII-DmLan  			(2498),
			dm4E1sII-ROUTER				(2499),
			dmStm1-Agg-MM				(5001),
			dmStm1-Agg-SM				(5002),
			dmStm1-Agg-B13				(5003),
			dmStm1-Agg-B15				(5004),
			dmStm1-Agg-E				(5005),
			dmStm1-Trib-E1-TR24E1		(5051),
			dmStm1-Trib-ETH-TRETH		(5061),
			dmStm1-Cpu-Eth				(5101),
			dmStm1-Cpu-V11				(5105),
			dmStm1-Cpu-RelayIn			(5110),
			dmStm1-Cpu-RelayOut			(5115),
			dmStm1-Cpu-Voice			(5120),
			dmStm1-Cpu-ClkIn			(5125),
			dmStm1-Cpu-ClkInt			(5130),
			dmStm1-Cpu-Fan				(5135),
			dmStm1-Cpu-PwrSupply		(5140),
			dmStm1-Cpu-SlotAgg			(5180),
			dmStm1-Cpu-SlotTrib			(5185),
			dmStm1-Log-Vc12-Vc11		(5201),
			dmStm1-Log-Vc3				(5205),
			dmStm1-Log-Vc4				(5210),
			dmStm1-Log-Stm1				(5215),
			dmStm1-Log-Wan-TR24E1		(5251),
			dmStm1-Log-Cpu-SysClk		(5401),
			dmStm1-Log-Cpu-ClkHier		(5405),
			dmStm1-Log-Cpu-Wan			(5410),
			dmStm1-Log-Cpu-Manag		(5415),
			dmStm1-Log-Prot-Group		(5420),
			dm1801-ETH					(6001),
			dm1801-GPRS					(6002),
			dm1801-AUX					(6003),
			objectNonexistentInModel  	(2000000254),
			infNotAvailable 		    (2000000255)
			}
		ACCESS		read-only
		STATUS		mandatory
		DESCRIPTION
        	" Port model identification. "
::={ genDvInfPortEntry 5 }

genDvInfPortFirmVersion	OBJECT-TYPE
		SYNTAX		INTEGER
		ACCESS		read-only
		STATUS		mandatory
		DESCRIPTION
			" Firmware version to this port. The value 0
			  indicates a beta version.  "
::={ genDvInfPortEntry 6 }

genDvInfPortHwId	OBJECT-TYPE
		SYNTAX		INTEGER
		ACCESS		read-only
		STATUS		mandatory
		DESCRIPTION
			" Port hardware identification. "
::={ genDvInfPortEntry 7 }

genDvInfPortCardMib	OBJECT-TYPE
		SYNTAX		OBJECT IDENTIFIER
		ACCESS		read-only
		STATUS		mandatory
		DESCRIPTION
        	" The MIB used to manage this card model. "
::={ genDvInfPortEntry 8 }

genDvInfPortConfigMode	OBJECT-TYPE
		SYNTAX		INTEGER
		ACCESS		read-only
		STATUS		mandatory
		DESCRIPTION
			" Port config mode identification. "
::={ genDvInfPortEntry 9 }



-- all devices (mux) information

genDvInfAllDevTable OBJECT-TYPE
		SYNTAX	SEQUENCE OF GenDvInfAllDevEntry
		ACCESS	not-accessible
		STATUS	mandatory
		DESCRIPTION
			" Table with general information about the devices managed by
			  this MIB. "
::={ dmGenDvInf 15 }

genDvInfAllDevEntry OBJECT-TYPE
		SYNTAX	GenDvInfAllDevEntry
		ACCESS	not-accessible
		STATUS	mandatory
		DESCRIPTION
			" Entry of genDvInfAllDevTable. "
		INDEX 	{ genDvInfAllDevDevNo, genDvInfAllDevDevLocalId }
::={ genDvInfAllDevTable 1 }

GenDvInfAllDevEntry ::=
		SEQUENCE {
			genDvInfAllDevDevNo    		DmDevIndex,
			genDvInfAllDevDevLocalId	DmDevLocalIndex,
			genDvInfAllDevProduct		OBJECT IDENTIFIER,
			genDvInfAllDevFirmVersion	INTEGER,
			genDvInfAllDevSerialNo		DisplayString,
			genDvInfAllDevIdent			INTEGER
			}

genDvInfAllDevDevNo	OBJECT-TYPE
    	SYNTAX   DmDevIndex
      	ACCESS   read-only
      	STATUS   mandatory
      	DESCRIPTION
      		" Device number. "
::= { genDvInfAllDevEntry 1 }

genDvInfAllDevDevLocalId	OBJECT-TYPE
		SYNTAX		DmDevLocalIndex
		ACCESS		read-only
		STATUS		mandatory
		DESCRIPTION
        	" Device local or remote. "
::={ genDvInfAllDevEntry 2 }

genDvInfAllDevProduct 	OBJECT-TYPE
		SYNTAX		OBJECT IDENTIFIER
		ACCESS		read-only
		STATUS		mandatory
		DESCRIPTION
			" The device product identification, through its
		   	  OBJECT IDENTIFIER in DATACOM-REG. "
::={ genDvInfAllDevEntry 3 }

genDvInfAllDevFirmVersion 	OBJECT-TYPE
		SYNTAX		INTEGER (0..255)
		ACCESS		read-only
		STATUS		mandatory
		DESCRIPTION
			" Device firmware version. The value 0 will
			  indicate a beta version.  "
::={ genDvInfAllDevEntry 4 }

genDvInfAllDevSerialNo 	OBJECT-TYPE
		SYNTAX		DisplayString
		ACCESS		read-only
		STATUS		mandatory
		DESCRIPTION
			" Device serial number. "
::={ genDvInfAllDevEntry 5 }

genDvInfAllDevIdent 	OBJECT-TYPE
		SYNTAX		INTEGER
		ACCESS		read-only
		STATUS		mandatory
		DESCRIPTION
			" Device identification. "
::={ genDvInfAllDevEntry 6 }


-- all devices (mux) license status information

genDvInfEquStTable OBJECT-TYPE
		SYNTAX	SEQUENCE OF GenDvInfEquStEntry
		ACCESS	not-accessible
		STATUS	mandatory
		DESCRIPTION
			" Table with license status information about the devices managed by
			  this MIB. "
::={ dmGenDvInf 20 }

genDvInfEquStEntry OBJECT-TYPE
		SYNTAX	GenDvInfEquStEntry
		ACCESS	not-accessible
		STATUS	mandatory
		DESCRIPTION
			" Entry of genDvInfEquStTable. "
		INDEX 	{ genDvInfEquStDevNo, genDvInfEquStDevLocalId }
::={ genDvInfEquStTable 1 }

GenDvInfEquStEntry ::=
		SEQUENCE {
			genDvInfEquStDevNo    		DmDevIndex,
			genDvInfEquStDevLocalId		DmDevLocalIndex,
			genDvInfEquStStatus			INTEGER,
			genDvInfEquStTmRem			INTEGER,
			genDvInfEquStLicInput		DisplayString
			}

genDvInfEquStDevNo	OBJECT-TYPE
    	SYNTAX   DmDevIndex
      	ACCESS   read-only
      	STATUS   mandatory
      	DESCRIPTION
      		" Device number. "
::= { genDvInfEquStEntry 1 }

genDvInfEquStDevLocalId	OBJECT-TYPE
		SYNTAX		DmDevLocalIndex
		ACCESS		read-only
		STATUS		mandatory
		DESCRIPTION
        	" Device local or remote. "
::={ genDvInfEquStEntry 2 }

genDvInfEquStStatus 	OBJECT-TYPE
		SYNTAX	INTEGER {
			licensedOper						(1),
			trialOper							(2),
			objectNonexistentInModel  			(254),
			infNotAvailable 		    		(255)
			}
		ACCESS		read-write
		STATUS		mandatory
		DESCRIPTION
			" License status. "
::={ genDvInfEquStEntry 3 }

genDvInfEquStTmRem 	OBJECT-TYPE
		SYNTAX		INTEGER (0..65535|2000000254|2000000255)
		ACCESS		read-write
		STATUS		mandatory
		DESCRIPTION
			" Time remaining.  "
::={ genDvInfEquStEntry 4 }

genDvInfEquStLicInput 	OBJECT-TYPE
		SYNTAX		DisplayString
		ACCESS		read-write
		STATUS		mandatory
		DESCRIPTION
			" License input. "
::={ genDvInfEquStEntry 5 }



-- -- -- -- -- -- -- -- -- --
-- group dmGenDvStatus
-- agent status
genDvStSnmpManagementStatus OBJECT-TYPE
		SYNTAX	INTEGER {
			fullManagementEnabled				(1),
			disabledBecauseRs232Active          (2),
			disabledBecauseInterfaceWasDown     (3),
			disabledByConfiguration             (4),
			disabledByConfigWithRemManagement   (5),
			objectNonexistentInModel  			(254),
			infNotAvailable 		    		(255)
			}
		ACCESS	read-write
		STATUS	mandatory
		DESCRIPTION
		   " The SNMP agent management status. Only the options
		     fullManagementEnabled and disabledByConfiguration can be set."
::={ dmGenDvStatus 1 }

genDvStLatchedPossibleNewCfg OBJECT-TYPE
		SYNTAX	INTEGER {
			none (1),
			possibleNewConfig (2)
			}
		ACCESS	read-write
		STATUS	mandatory
		DESCRIPTION
		   " It indicates if there is a possible new management configuration in the
		   	 agent. Only the option none can be set(refresh). "
::={ dmGenDvStatus 2 }

genDvStDeviceTable OBJECT-TYPE
		SYNTAX	SEQUENCE OF GenDvStDeviceEntry
		ACCESS	not-accessible
		STATUS	mandatory
		DESCRIPTION
			" Table with general information about the devices managed by
			  this MIB. "
::={ dmGenDvStatus 10 }

genDvStDeviceEntry OBJECT-TYPE
		SYNTAX	GenDvStDeviceEntry
		ACCESS	not-accessible
		STATUS	mandatory
		DESCRIPTION
			" Entry of genDvStDeviceTable. "
		INDEX 	{ genDvStDeviceDevNo, genDvStDeviceDevLocalId }
::={ genDvStDeviceTable 1 }

GenDvStDeviceEntry::=
		SEQUENCE {
			genDvStDeviceDevNo    			DmDevIndex,
			genDvStDeviceDevLocalId			DmDevLocalIndex,
			genDvStDeviceLstHwChangeTmSp 	TimeTicks,
			genDvStDeviceLstStChangeTmSp    TimeTicks,
			genDvStDeviceResets				Counter,
			genDvStDeviceLstCfgChange		Counter,
			genDvStDeviceNmsVersion			Counter,
			genDvStDeviceResetStatus		INTEGER
			}

genDvStDeviceDevNo	OBJECT-TYPE
    	SYNTAX   DmDevIndex
      	ACCESS   read-only
      	STATUS   mandatory
      	DESCRIPTION
      		" Device number. "
::= { genDvStDeviceEntry 1 }

genDvStDeviceDevLocalId	OBJECT-TYPE
		SYNTAX		DmDevLocalIndex
		ACCESS		read-only
		STATUS		mandatory
		DESCRIPTION
        	" Device local or remote. "
::={ genDvStDeviceEntry 2 }

genDvStDeviceLstHwChangeTmSp 	OBJECT-TYPE
		SYNTAX		TimeTicks
		ACCESS		read-only
		STATUS		mandatory
		DESCRIPTION
			" Last hardware change time stamp. "
::={ genDvStDeviceEntry 3 }

genDvStDeviceLstStChangeTmSp 	OBJECT-TYPE
		SYNTAX		TimeTicks
		ACCESS		read-only
		STATUS		mandatory
		DESCRIPTION
			" Last status change time stamp. "
::={ genDvStDeviceEntry 4 }

genDvStDeviceResets 	OBJECT-TYPE
		SYNTAX		Counter
		ACCESS		read-only
		STATUS		mandatory
		DESCRIPTION
			" Resets number. "
::={ genDvStDeviceEntry 5 }

genDvStDeviceLstCfgChange 	OBJECT-TYPE
		SYNTAX		Counter
		ACCESS		read-only
		STATUS		mandatory
		DESCRIPTION
			" Last configuration change. "
::={ genDvStDeviceEntry 6 }

genDvStDeviceNmsVersion 	OBJECT-TYPE
		SYNTAX		Counter
		ACCESS		read-only
		STATUS		mandatory
		DESCRIPTION
			" NMS version. "
::={ genDvStDeviceEntry 7 }

genDvStDeviceResetStatus 	OBJECT-TYPE
		SYNTAX	INTEGER {
			notResetingAgent			(1),
			resetAgent          		(2),
			objectNonexistentInModel  	(254),
			infNotAvailable 		    (255)
			}
		ACCESS		read-write
		STATUS		mandatory
		DESCRIPTION
			" Reset the equipement. "
::={ genDvStDeviceEntry 10 }



genDvEquipTmTable OBJECT-TYPE
		SYNTAX	SEQUENCE OF GenDvEquipTmEntry
		ACCESS	not-accessible
		STATUS	mandatory
		DESCRIPTION
			" Table with current time information about the devices managed by
			  this MIB. "
::={ dmGenDvStatus 13 }

genDvEquipTmEntry OBJECT-TYPE
		SYNTAX	GenDvEquipTmEntry
		ACCESS	not-accessible
		STATUS	mandatory
		DESCRIPTION
			" Entry of genDvEquipTmTable. "
		INDEX 	{ genDvEquipTmDevNo, genDvEquipTmDevLocalId }
::={ genDvEquipTmTable 1 }

GenDvEquipTmEntry::=
		SEQUENCE {
			genDvEquipTmDevNo    			DmDevIndex,
			genDvEquipTmDevLocalId			DmDevLocalIndex,
			genDvEquipTmUtc				 	DmUnsigned,
			genDvEquipTmTimezone	    	INTEGER,
			genDvEquipTmUpTm				TimeTicks
			}

genDvEquipTmDevNo	OBJECT-TYPE
    	SYNTAX   DmDevIndex
      	ACCESS   read-only
      	STATUS   mandatory
      	DESCRIPTION
      		" Device number. "
::= { genDvEquipTmEntry 1 }

genDvEquipTmDevLocalId	OBJECT-TYPE
		SYNTAX		DmDevLocalIndex
		ACCESS		read-only
		STATUS		mandatory
		DESCRIPTION
        	" Device local or remote. "
::={ genDvEquipTmEntry 2 }

genDvEquipTmUtc 	OBJECT-TYPE
		SYNTAX		DmUnsigned
		ACCESS		read-only
		STATUS		mandatory
		DESCRIPTION
      		" Equipment current time (seconds since 01/01/1970). "
::={ genDvEquipTmEntry 3 }

genDvEquipTmTimezone 	OBJECT-TYPE
		SYNTAX		INTEGER
		ACCESS		read-only
		STATUS		mandatory
		DESCRIPTION
      		" Equipment time zone. "
::={ genDvEquipTmEntry 4 }

genDvEquipTmUpTm 	OBJECT-TYPE
		SYNTAX		TimeTicks
		ACCESS		read-only
		STATUS		mandatory
		DESCRIPTION
			" Up time. "
::={ genDvEquipTmEntry 5 }




genDvStActTable OBJECT-TYPE
		SYNTAX	SEQUENCE OF GenDvStActEntry
		ACCESS	not-accessible
		STATUS	mandatory
		DESCRIPTION
			" Table with activation time information about the devices managed by
			  this MIB. "
::={ dmGenDvStatus 15 }

genDvStActEntry OBJECT-TYPE
		SYNTAX	GenDvStActEntry
		ACCESS	not-accessible
		STATUS	mandatory
		DESCRIPTION
			" Entry of genDvStActTable. "
		INDEX 	{ genDvStActDevNo, genDvStActDevLocalId }
::={ genDvStActTable 1 }

GenDvStActEntry::=
		SEQUENCE {
			genDvStActDevNo    				DmDevIndex,
			genDvStActDevLocalId			DmDevLocalIndex,
			genDvStActUpTm				 	TimeTicks,
			genDvStActResets	    		Counter
			}

genDvStActDevNo	OBJECT-TYPE
    	SYNTAX   DmDevIndex
      	ACCESS   read-only
      	STATUS   mandatory
      	DESCRIPTION
      		" Device number. "
::= { genDvStActEntry 1 }

genDvStActDevLocalId	OBJECT-TYPE
		SYNTAX		DmDevLocalIndex
		ACCESS		read-only
		STATUS		mandatory
		DESCRIPTION
        	" Device local or remote. "
::={ genDvStActEntry 2 }

genDvStActUpTm 	OBJECT-TYPE
		SYNTAX		TimeTicks
		ACCESS		read-only
		STATUS		mandatory
		DESCRIPTION
      		" Up time of last configuration activated. "
::={ genDvStActEntry 3 }

genDvStActResets 	OBJECT-TYPE
		SYNTAX		Counter
		ACCESS		read-only
		STATUS		mandatory
		DESCRIPTION
      		" Reset number of last configuration activated. "
::={ genDvStActEntry 4 }




genDvStPhSlotTable OBJECT-TYPE
		SYNTAX	SEQUENCE OF GenDvStPhSlotEntry
		ACCESS	not-accessible
		STATUS	mandatory
		DESCRIPTION
			" Table with physical ports information about the devices managed by
			  this MIB. "
::={ dmGenDvStatus 17 }

genDvStPhSlotEntry OBJECT-TYPE
		SYNTAX	GenDvStPhSlotEntry
		ACCESS	not-accessible
		STATUS	mandatory
		DESCRIPTION
			" Entry of genDvStPhSlotTable. "
		INDEX 	{ genDvStPhSlotDevNo, genDvStPhSlotDevLocalId, genDvStPhSlotSlotNo, genDvStPhSlotPortNo }
::={ genDvStPhSlotTable 1 }

GenDvStPhSlotEntry::=
		SEQUENCE {
			genDvStPhSlotDevNo  			DmDevIndex,
			genDvStPhSlotDevLocalId			DmDevLocalIndex,
			genDvStPhSlotSlotNo 			DmSlotIndex,
			genDvStPhSlotPortNo				DmPortIndex,
			genDvStPhSlotPresence		 	INTEGER,
			genDvStPhSlotStFail			 	INTEGER,
			genDvStPhSlotOperTm			 	Counter,
			genDvStPhSlotOperSt			 	INTEGER,
			genDvStPhSlotResets	    		Counter
			}

genDvStPhSlotDevNo	OBJECT-TYPE
    	SYNTAX   	DmDevIndex
      	ACCESS   	read-only
      	STATUS   	mandatory
      	DESCRIPTION
      		" Device number. "
::= { genDvStPhSlotEntry 1 }

genDvStPhSlotDevLocalId	OBJECT-TYPE
		SYNTAX		DmDevLocalIndex
		ACCESS		read-only
		STATUS		mandatory
		DESCRIPTION
        	" Device local or remote. "
::={ genDvStPhSlotEntry 2 }

genDvStPhSlotSlotNo	OBJECT-TYPE
		SYNTAX		DmSlotIndex
		ACCESS		read-only
		STATUS		mandatory
		DESCRIPTION
        	" Slot number. "
::={ genDvStPhSlotEntry 3 }

genDvStPhSlotPortNo	OBJECT-TYPE
		SYNTAX		DmPortIndex
		ACCESS		read-only
		STATUS		mandatory
		DESCRIPTION
        	" Port number. "
::={ genDvStPhSlotEntry 4 }

genDvStPhSlotPresence 	OBJECT-TYPE
		SYNTAX INTEGER {
			notPresent 					(1),
			present  					(2),
			objectNonexistentInModel  	(254),
			infNotAvailable 		    (255)
			}
		ACCESS		read-only
		STATUS		mandatory
		DESCRIPTION
      		" Port presence. "
::={ genDvStPhSlotEntry 6 }

genDvStPhSlotStFail 	OBJECT-TYPE
		SYNTAX INTEGER {
			ok	 						(1),
			failure	  					(2),
			objectNonexistentInModel  	(254),
			infNotAvailable 		    (255)
			}
		ACCESS		read-only
		STATUS		mandatory
		DESCRIPTION
      		" Status fail. "
::={ genDvStPhSlotEntry 7 }

genDvStPhSlotOperTm 	OBJECT-TYPE
		SYNTAX		Counter
		ACCESS		read-only
		STATUS		mandatory
		DESCRIPTION
      		" Total operation time (hours). "
::={ genDvStPhSlotEntry 8 }

genDvStPhSlotOperSt 	OBJECT-TYPE
		SYNTAX INTEGER {
			prevMaintReq				(1),	-- Preventive maintenance required
			prevMaintNotReq				(2),
			objectNonexistentInModel  	(254),
			infNotAvailable 		    (255)
			}
		ACCESS		read-only
		STATUS		mandatory
		DESCRIPTION
      		" Operation status. "
::={ genDvStPhSlotEntry 9 }

genDvStPhSlotResets 	OBJECT-TYPE
		SYNTAX		Counter
		ACCESS		read-only
		STATUS		mandatory
		DESCRIPTION
      		" Reset number. "
::={ genDvStPhSlotEntry 10 }




-- -- -- -- -- -- -- -- -- --
-- group dmGenDvConfig

genDvCfgMngDownItfTm OBJECT-TYPE
		SYNTAX 	INTEGER
		ACCESS	read-write
		STATUS	mandatory
		DESCRIPTION
			" If the interface is down for this time (in hundredths
			  of a second), the SNMP management will be disabled.
			  See muxStManagementStatus object.
			  Use 0 to disable the option. "
::={ dmGenDvConfig 1 }

genDvCfgMngUpItfTm OBJECT-TYPE
		SYNTAX 	INTEGER
		ACCESS	read-write
		STATUS	mandatory
		DESCRIPTION
			" Time (in hundredths of a seconds) to enable SNMP management
			  if the interface changed from down to up.
			  See muxStManagementStatus object.
			  Use 0 to disable the option.  "
::={ dmGenDvConfig 2 }







-- -- -- -- -- -- -- -- -- --
-- group dmGenDvlarms

-- multiplexer general alarm configuration
genDvAlDeviceCfgTable  OBJECT-TYPE
		SYNTAX	SEQUENCE OF GenDvAlDeviceCfgEntry
		ACCESS	not-accessible
		STATUS	mandatory
		DESCRIPTION
			" Table with general alarm configuration about the devices
			  managed by this MIB. "
::={ dmGenDvAlarms 10 }

genDvAlDeviceCfgEntry OBJECT-TYPE
		SYNTAX	GenDvAlDeviceCfgEntry
		ACCESS	not-accessible
		STATUS	mandatory
		DESCRIPTION
			" Entry of genDvAlDeviceCfgTable. "
		INDEX 	{ genDvAlDeviceCfgDevNo, genDvAlDeviceCfgDevLocalId }
::={ genDvAlDeviceCfgTable 1 }

GenDvAlDeviceCfgEntry ::=
		SEQUENCE {
			genDvAlDeviceCfgDevNo				DmDevIndex,
			genDvAlDeviceCfgDevLocalId		DmDevLocalIndex,
			genDvAlDeviceCfgTrapSt			INTEGER
			}

genDvAlDeviceCfgDevNo	OBJECT-TYPE
    	SYNTAX   	DmDevIndex
      	ACCESS   	read-only
      	STATUS   	mandatory
      	DESCRIPTION
      		" Device number. "
::= { genDvAlDeviceCfgEntry 1 }

genDvAlDeviceCfgDevLocalId	OBJECT-TYPE
		SYNTAX		DmDevLocalIndex
		ACCESS		read-only
		STATUS		mandatory
		DESCRIPTION
        	" Device local or remote. "
::={ genDvAlDeviceCfgEntry 2 }

genDvAlDeviceCfgTrapSt OBJECT-TYPE
		SYNTAX INTEGER {
			disabled 					(1),
			enabled  					(2),
			objectNonexistentInModel  	(254),
			infNotAvailable 		    (255)
			}
        ACCESS	read-write
        STATUS  mandatory
        DESCRIPTION
        	" Device general trap configuration. "
::={ genDvAlDeviceCfgEntry 3 }

-- multiplexer alarms configuration
genDvAlDevTrapCfgTable  OBJECT-TYPE
		SYNTAX	SEQUENCE OF GenDvAlDevTrapCfgEntry
		ACCESS	not-accessible
		STATUS	mandatory
		DESCRIPTION
			" Table with trap configuration about the devices managed by
			  this MIB. "
::={ dmGenDvAlarms 11 }

genDvAlDevTrapCfgEntry OBJECT-TYPE
		SYNTAX	GenDvAlDevTrapCfgEntry
		ACCESS	not-accessible
		STATUS	mandatory
		DESCRIPTION
			" Entry of genDvAlDevTrapCfgTable. "
		INDEX 	{ genDvAlDevTrapCfgDevNo, genDvAlDevTrapCfgDevLocalId, genDvAlDevTrapCfgTrapId }
::={ genDvAlDevTrapCfgTable 1 }

GenDvAlDevTrapCfgEntry ::=
		SEQUENCE {
			genDvAlDevTrapCfgDevNo			DmDevIndex,
			genDvAlDevTrapCfgDevLocalId		DmDevLocalIndex,
			genDvAlDevTrapCfgTrapId			DmTrapIndex,
			genDvAlDevTrapCfgSt				INTEGER
			}

genDvAlDevTrapCfgDevNo	OBJECT-TYPE
    	SYNTAX   	DmDevIndex
      	ACCESS   	read-only
      	STATUS   	mandatory
      	DESCRIPTION
      		" Device number. "
::= { genDvAlDevTrapCfgEntry 1 }

genDvAlDevTrapCfgDevLocalId	OBJECT-TYPE
		SYNTAX		DmDevLocalIndex
		ACCESS		read-only
		STATUS		mandatory
		DESCRIPTION
        	" Device local or remote. "
::={ genDvAlDevTrapCfgEntry 2 }

genDvAlDevTrapCfgTrapId	OBJECT-TYPE
		SYNTAX		DmTrapIndex
		ACCESS		read-only
		STATUS		mandatory
		DESCRIPTION
        	" Trap number. "
::={ genDvAlDevTrapCfgEntry 3 }

genDvAlDevTrapCfgSt OBJECT-TYPE
		SYNTAX INTEGER {
			disabled 					(1),
			enabled  					(2),
			masked  					(3),
			objectNonexistentInModel  	(254),
			infNotAvailable 		    (255)
			}
        ACCESS	read-write
        STATUS  mandatory
        DESCRIPTION
        	" Trap configuration value. "
::={ genDvAlDevTrapCfgEntry 4 }



-- port general alarm configuration
genDvAlPortCfgTable  OBJECT-TYPE
		SYNTAX	SEQUENCE OF GenDvAlPortCfgEntry
		ACCESS	not-accessible
		STATUS	mandatory
		DESCRIPTION
			" Table with port general alarm configuration about the devices managed by
			  this MIB. "
::={ dmGenDvAlarms 13 }

genDvAlPortCfgEntry OBJECT-TYPE
		SYNTAX	GenDvAlPortCfgEntry
		ACCESS	not-accessible
		STATUS	mandatory
		DESCRIPTION
			" Entry of genDvAlPortCfgTable. "
		INDEX 	{ genDvAlPortCfgDevNo, genDvAlPortCfgDevLocalId, genDvAlPortCfgSlotNo, genDvAlPortCfgPortNo }
::={ genDvAlPortCfgTable 1 }

GenDvAlPortCfgEntry ::=
		SEQUENCE {
			genDvAlPortCfgDevNo				    DmDevIndex,
			genDvAlPortCfgDevLocalId			DmDevLocalIndex,
			genDvAlPortCfgSlotNo				DmSlotIndex,
			genDvAlPortCfgPortNo				DmPortIndex,
			genDvAlPortCfgTrapSt				INTEGER
			}

genDvAlPortCfgDevNo	OBJECT-TYPE
    	SYNTAX   	DmDevIndex
      	ACCESS   	read-only
      	STATUS   	mandatory
      	DESCRIPTION
      		" Device number. "
::= { genDvAlPortCfgEntry 1 }

genDvAlPortCfgDevLocalId	OBJECT-TYPE
		SYNTAX		DmDevLocalIndex
		ACCESS		read-only
		STATUS		mandatory
		DESCRIPTION
        	" Device local or remote. "
::={ genDvAlPortCfgEntry 2 }

genDvAlPortCfgSlotNo	OBJECT-TYPE
    	SYNTAX   	DmSlotIndex
      	ACCESS   	read-only
      	STATUS   	mandatory
      	DESCRIPTION
        	" Slot number. "
::= { genDvAlPortCfgEntry 3 }

genDvAlPortCfgPortNo	OBJECT-TYPE
		SYNTAX		DmPortIndex
		ACCESS		read-only
		STATUS		mandatory
		DESCRIPTION
	       	" Port number. "
::={ genDvAlPortCfgEntry 4 }

genDvAlPortCfgTrapSt OBJECT-TYPE
		SYNTAX INTEGER {
			disabled 					(1),
			enabled  					(2),
			masked  					(3),
			objectNonexistentInModel  	(254),
			infNotAvailable 		    (255)
			}
        ACCESS	read-write
        STATUS  mandatory
        DESCRIPTION
        	" Port general trap configuration. "
::={ genDvAlPortCfgEntry 5 }





END

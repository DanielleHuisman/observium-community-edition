--
-- DATACOM Telematica
-- Copyright 2005-2020 by Datacom Telematica (Teracom Telematica Ltda). All Rights Reserved.
-- This DATACOM SNMP MIB Specification is Datacom proprietary intellectual property.
--
-- This module will be extend, as required. The specification and other information
-- contained in this document can be modified without prior notice. The user should
-- consult Datacom to determine whether any such changes have been done.
--
DATACOM-ROUTER-B-MIB	DEFINITIONS ::= BEGIN


IMPORTS
  Counter, IpAddress
    FROM RFC1155-SMI
  Counter64
    FROM SNMPv2-SMI
  OBJECT-TYPE
    FROM RFC-1212
  datacomAccessDevicesMIBs, datacomModules
    FROM DATACOM-SMI;



datacomRouterBMIBModule OBJECT IDENTIFIER ::={ datacomModules 3521 }
--    LAST-UPDATED "202007030000Z"
--    ORGANIZATION "DATACOM"
--    CONTACT-INFO
--                 "DATACOM
--
--                 Postal: DATACOM
--                     Rua America, 1000
--                     Eldorado do Sul, RS
--                     CEP 92990-000
--                             BRAZIL
--
--                 Tel:+55(51)3933 3000
--                 Fax:+55(51)3933 3003
--
--                 E-mail: datacom@datacom.ind.br "
--
--    DESCRIPTION
--        "The MIB module for Datacom router type B."
--
--
--
-- -- -- -- -- -- -- -- -- -- -- -- -- -- -- -- -- -- -- -- -- -- -- --


dmAdRouterBMIB OBJECT IDENTIFIER ::={ datacomAccessDevicesMIBs 21  }


--  -- -- -- -- -- -- -- -- -- --  -- -- -- -- -- -- -- -- -- -- -- --
 -- textual conventions

      DisplayString ::= OCTET STRING
      -- This data type is used to model textual information taken
      -- from the NVT ASCII character set.  By convention, objects
      -- with this syntax are declared as having
      --
      --      SIZE (0..255)

--  -- -- -- -- -- -- -- -- -- --  -- -- -- -- -- -- -- -- -- --

  DmDevIndex			::= INTEGER (1..99)
  DmDevLocalIndex 	::= INTEGER (1..99)
    DmSlotIndex			::= INTEGER (1..99)
    DmPortIndex			::= INTEGER (1..99)

-- -- -- -- -- -- -- -- -- -- -- -- -- -- -- -- -- -- -- -- -- -- -- --

--
-- groups
dmAdRtbInf		 		OBJECT IDENTIFIER 	::={ dmAdRouterBMIB 1 }
dmAdRtbStatus 			OBJECT IDENTIFIER 	::={ dmAdRouterBMIB 2 }
--dmAdRtbConfig		 	OBJECT IDENTIFIER 	::={ dmAdRouterBMIB 3 }
--dmAdRtbDiagnostic	 	OBJECT IDENTIFIER 	::={ dmAdRouterBMIB 4 }
dmAdRtbPerformance 		OBJECT IDENTIFIER 	::={ dmAdRouterBMIB 5 }
dmAdRtbConfigCopy 		OBJECT IDENTIFIER 	::={ dmAdRouterBMIB 6 }
dmAdRtbLTE       		  OBJECT IDENTIFIER 	::={ dmAdRouterBMIB 7 }

-- -- -- -- -- -- -- -- --
-- group

--
--
rtbInfItfGprsTable OBJECT-TYPE
    SYNTAX	SEQUENCE OF RtbInfItfGprsEntry
    ACCESS	not-accessible
    STATUS	mandatory
    DESCRIPTION
      " Table with router B information about
        the router managed by this MIB. "
::={ dmAdRtbInf 15  }

rtbInfItfGprsEntry OBJECT-TYPE
    SYNTAX	RtbInfItfGprsEntry
    ACCESS	not-accessible
    STATUS	mandatory
    DESCRIPTION
      " Entry of rtbInfItfGprsTable. "
    INDEX 	{ rtbInfItfGprsDevNo, rtbInfItfGprsDevLocalId,
          rtbInfItfGprsSlotNo, rtbInfItfGprsPortNo }
::={ rtbInfItfGprsTable 1 }

RtbInfItfGprsEntry ::=
    SEQUENCE {
        rtbInfItfGprsDevNo				DmDevIndex,
        rtbInfItfGprsDevLocalId			DmDevLocalIndex,
        rtbInfItfGprsSlotNo				DmSlotIndex,
        rtbInfItfGprsPortNo				DmPortIndex,
        rtbInfItfGprsTaInf			    DisplayString,
        rtbInfItfGprsTaConf			    DisplayString,
        rtbInfItfGprsTaSerial		    DisplayString,
        rtbInfItfGprsTaRegistry		    DisplayString,
        rtbInfItfGprsSimCardInf		    DisplayString,
        rtbInfItfGprsCellConn		    DisplayString,
        rtbInfItfGprsCellsMon		    DisplayString,
        rtbInfItfGprsNetInf				DisplayString
      }

rtbInfItfGprsDevNo	OBJECT-TYPE
      SYNTAX   DmDevIndex
        ACCESS   read-only
        STATUS   mandatory
        DESCRIPTION
          " Device number. "
::= { rtbInfItfGprsEntry 1 }

rtbInfItfGprsDevLocalId	OBJECT-TYPE
    SYNTAX		DmDevLocalIndex
    ACCESS		read-only
    STATUS		mandatory
    DESCRIPTION
          " Device local or remote. "
::={ rtbInfItfGprsEntry 2 }

rtbInfItfGprsSlotNo	OBJECT-TYPE
    SYNTAX		DmSlotIndex
    ACCESS		read-only
    STATUS		mandatory
    DESCRIPTION
          " Slot number. "
::={ rtbInfItfGprsEntry 3 }

rtbInfItfGprsPortNo	OBJECT-TYPE
    SYNTAX		DmPortIndex
    ACCESS		read-only
    STATUS		mandatory
    DESCRIPTION
          " Port number. "
::={ rtbInfItfGprsEntry 4 }

rtbInfItfGprsTaInf OBJECT-TYPE
    SYNTAX		DisplayString
    ACCESS		read-only
    STATUS		mandatory
    DESCRIPTION
          " ta_info. "
::={ rtbInfItfGprsEntry 5 }

rtbInfItfGprsTaConf OBJECT-TYPE
    SYNTAX		DisplayString
    ACCESS		read-only
    STATUS		mandatory
    DESCRIPTION
          " ta_conf. "
::={ rtbInfItfGprsEntry 6 }

rtbInfItfGprsTaSerial OBJECT-TYPE
    SYNTAX		DisplayString
    ACCESS		read-only
    STATUS		mandatory
    DESCRIPTION
          " ta_serial. "
::={ rtbInfItfGprsEntry 7 }

rtbInfItfGprsTaRegistry OBJECT-TYPE
    SYNTAX		DisplayString
    ACCESS		read-only
    STATUS		mandatory
    DESCRIPTION
          " ta_registry. "
::={ rtbInfItfGprsEntry 8 }

rtbInfItfGprsSimCardInf OBJECT-TYPE
    SYNTAX		DisplayString
    ACCESS		read-only
    STATUS		mandatory
    DESCRIPTION
          " simcard_info. "
::={ rtbInfItfGprsEntry 9 }

rtbInfItfGprsCellConn OBJECT-TYPE
    SYNTAX		DisplayString
    ACCESS		read-only
    STATUS		mandatory
    DESCRIPTION
          " cell_conn. "
::={ rtbInfItfGprsEntry 10 }

rtbInfItfGprsCellsMon OBJECT-TYPE
    SYNTAX		DisplayString
    ACCESS		read-only
    STATUS		mandatory
    DESCRIPTION
          " cells_mon. "
::={ rtbInfItfGprsEntry 11 }

rtbInfItfGprsNetInf OBJECT-TYPE
    SYNTAX		DisplayString
    ACCESS		read-only
    STATUS		mandatory
    DESCRIPTION
          " gprs_info. "
::={ rtbInfItfGprsEntry 12 }



--
rtbStItfGenTable OBJECT-TYPE
    SYNTAX	SEQUENCE OF RtbStItfGenEntry
    ACCESS	not-accessible
    STATUS	mandatory
    DESCRIPTION
      " Table with router B link status about
        the router managed by this MIB. "
::={ dmAdRtbStatus 12  }

rtbStItfGenEntry OBJECT-TYPE
    SYNTAX	RtbStItfGenEntry
    ACCESS	not-accessible
    STATUS	mandatory
    DESCRIPTION
      " Entry of rtbStItfGenTable. "
    INDEX 	{ rtbStItfGenDevNo, rtbStItfGenDevLocalId,
          rtbStItfGenSlotNo, rtbStItfGenPortNo }
::={ rtbStItfGenTable 1 }

RtbStItfGenEntry ::=
    SEQUENCE {
        rtbStItfGenDevNo				DmDevIndex,
        rtbStItfGenDevLocalId			DmDevLocalIndex,
        rtbStItfGenSlotNo				DmSlotIndex,
        rtbStItfGenPortNo				DmPortIndex,
        rtbStItfGenLink				    INTEGER,
        rtbStItfGenIndex				INTEGER
      }

rtbStItfGenDevNo	OBJECT-TYPE
      SYNTAX   DmDevIndex
        ACCESS   read-only
        STATUS   mandatory
        DESCRIPTION
          " Device number. "
::= { rtbStItfGenEntry 1 }

rtbStItfGenDevLocalId	OBJECT-TYPE
    SYNTAX		DmDevLocalIndex
    ACCESS		read-only
    STATUS		mandatory
    DESCRIPTION
          " Device local or remote. "
::={ rtbStItfGenEntry 2 }

rtbStItfGenSlotNo	OBJECT-TYPE
    SYNTAX		DmSlotIndex
    ACCESS		read-only
    STATUS		mandatory
    DESCRIPTION
          " Slot number. "
::={ rtbStItfGenEntry 3 }

rtbStItfGenPortNo	OBJECT-TYPE
    SYNTAX		DmPortIndex
    ACCESS		read-only
    STATUS		mandatory
    DESCRIPTION
          " Port number. "
::={ rtbStItfGenEntry 4 }

rtbStItfGenLink OBJECT-TYPE
    SYNTAX		INTEGER {
      up		 					(1),
      down						(2),
      infNotAvailable 		    (255)
      }
    ACCESS		read-only
    STATUS		mandatory
    DESCRIPTION
          " The current operational state of the interface. "
::={ rtbStItfGenEntry 5 }

rtbStItfGenIndex OBJECT-TYPE
    SYNTAX		INTEGER (1..100 | 254 | 255)
    ACCESS		read-only
    STATUS		mandatory
    DESCRIPTION
          " Interface index in mib-2.interfaces (.1.3.6.1.2.1.2).
            When the interface is not available (link down) the
            value is 255. "
::={ rtbStItfGenEntry 6 }



--
rtbStItfAddTable OBJECT-TYPE
    SYNTAX	SEQUENCE OF RtbStItfAddEntry
    ACCESS	not-accessible
    STATUS	mandatory
    DESCRIPTION
      " Table with router B IP address status about
        the router managed by this MIB. "
::={ dmAdRtbStatus 15  }

rtbStItfAddEntry OBJECT-TYPE
    SYNTAX	RtbStItfAddEntry
    ACCESS	not-accessible
    STATUS	mandatory
    DESCRIPTION
      " Entry of rtbStItfAddTable. "
    INDEX 	{ rtbStItfAddDevNo, rtbStItfAddDevLocalId,
          rtbStItfAddSlotNo, rtbStItfAddPortNo }
::={ rtbStItfAddTable 1 }

RtbStItfAddEntry ::=
    SEQUENCE {
        rtbStItfAddDevNo				DmDevIndex,
        rtbStItfAddDevLocalId			DmDevLocalIndex,
        rtbStItfAddSlotNo				DmSlotIndex,
        rtbStItfAddPortNo				DmPortIndex,
        rtbStItfAddLocal			    IpAddress,
        rtbStItfAddRemote				IpAddress
      }

rtbStItfAddDevNo	OBJECT-TYPE
      SYNTAX   DmDevIndex
        ACCESS   read-only
        STATUS   mandatory
        DESCRIPTION
          " Device number. "
::= { rtbStItfAddEntry 1 }

rtbStItfAddDevLocalId	OBJECT-TYPE
    SYNTAX		DmDevLocalIndex
    ACCESS		read-only
    STATUS		mandatory
    DESCRIPTION
          " Device local or remote. "
::={ rtbStItfAddEntry 2 }

rtbStItfAddSlotNo	OBJECT-TYPE
    SYNTAX		DmSlotIndex
    ACCESS		read-only
    STATUS		mandatory
    DESCRIPTION
          " Slot number. "
::={ rtbStItfAddEntry 3 }

rtbStItfAddPortNo	OBJECT-TYPE
    SYNTAX		DmPortIndex
    ACCESS		read-only
    STATUS		mandatory
    DESCRIPTION
          " Port number. "
::={ rtbStItfAddEntry 4 }

rtbStItfAddLocal OBJECT-TYPE
    SYNTAX		IpAddress
    ACCESS		read-only
    STATUS		mandatory
    DESCRIPTION
          " Local Address. "
::={ rtbStItfAddEntry 5 }

rtbStItfAddRemote OBJECT-TYPE
    SYNTAX		IpAddress
    ACCESS		read-only
    STATUS		mandatory
    DESCRIPTION
          " Remote Address. "
::={ rtbStItfAddEntry 6 }


--
rtbPerfHwStCpu	OBJECT-TYPE
    SYNTAX	INTEGER (0..255)
    ACCESS	read-only
    STATUS	mandatory
    DESCRIPTION
       " CPU performance in percent. "
::={ dmAdRtbPerformance 1 }

rtbPerfHwStMemory	OBJECT-TYPE
    SYNTAX	INTEGER (0..255)
    ACCESS	read-only
    STATUS	mandatory
    DESCRIPTION
       " Memory performance in percent. "
::={ dmAdRtbPerformance 2 }


--
rtbPerfItfTable OBJECT-TYPE
    SYNTAX	SEQUENCE OF RtbPerfItfEntry
    ACCESS	not-accessible
    STATUS	mandatory
    DESCRIPTION
      " Interface performance. "
::={ dmAdRtbPerformance 15  }

rtbPerfItfEntry OBJECT-TYPE
    SYNTAX	RtbPerfItfEntry
    ACCESS	not-accessible
    STATUS	mandatory
    DESCRIPTION
      " Entry of rtbPerfItfTable. "
    INDEX 	{ rtbPerfItfIndex }
::={ rtbPerfItfTable 1 }

RtbPerfItfEntry ::=
    SEQUENCE {
        rtbPerfItfIndex     		INTEGER,
        rtbPerfItfDescr     		DisplayString,
        rtbPerfItfOctets     		Counter,
        rtbPerfItfPkts       		Counter,
        rtbPerfItfCollisions 		Counter,
        rtbPerfItfUtilization		Counter,
        rtbPerfItfDrop       		Counter,
        rtbPerfItfError      		Counter,
        rtbPerfItfRxDataRate 		Counter,
        rtbPerfItfTxDataRate 		Counter,
        rtbPerfItfRxDropRate 		Counter,
        rtbPerfItfTxDropRate 		Counter
      }

rtbPerfItfIndex	OBJECT-TYPE
      SYNTAX   INTEGER (1..100 | 254 | 255)
        ACCESS   read-only
        STATUS   mandatory
        DESCRIPTION
          " Interface index in mib-2.interfaces (.1.3.6.1.2.1.2)."
::= { rtbPerfItfEntry 1 }

rtbPerfItfDescr	OBJECT-TYPE
    SYNTAX		DisplayString
    ACCESS		read-only
    STATUS		mandatory
    DESCRIPTION
          " Interface name. "
::={ rtbPerfItfEntry 2 }

rtbPerfItfOctets	OBJECT-TYPE
    SYNTAX		Counter
    ACCESS		read-only
    STATUS		mandatory
    DESCRIPTION
          " Octets received in this interface. "
::={ rtbPerfItfEntry 3 }

rtbPerfItfPkts	OBJECT-TYPE
    SYNTAX		Counter
    ACCESS		read-only
    STATUS		mandatory
    DESCRIPTION
          " Packets received in this interface. "
::={ rtbPerfItfEntry 4 }

rtbPerfItfCollisions OBJECT-TYPE
    SYNTAX		Counter
    ACCESS		read-only
    STATUS		mandatory
    DESCRIPTION
          " Collisions number in this interface. "
::={ rtbPerfItfEntry 5 }

rtbPerfItfUtilization OBJECT-TYPE
    SYNTAX		Counter
    ACCESS		read-only
    STATUS		mandatory
    DESCRIPTION
          " Data rate received in this interface (bits/second). "
::={ rtbPerfItfEntry 6 }

rtbPerfItfDrop OBJECT-TYPE
    SYNTAX		Counter
    ACCESS		read-only
    STATUS		mandatory
    DESCRIPTION
          " Packets per second droped in this interface (packets/second). "
::={ rtbPerfItfEntry 7 }

rtbPerfItfError OBJECT-TYPE
    SYNTAX		Counter
    ACCESS		read-only
    STATUS		mandatory
    DESCRIPTION
          " Packets per second errored in this interface (packets/second). "
::={ rtbPerfItfEntry 8 }

rtbPerfItfRxDataRate OBJECT-TYPE
    SYNTAX		Counter
    ACCESS		read-only
    STATUS		mandatory
    DESCRIPTION
          " Data rate received in this interface (kbits/second). "
::={ rtbPerfItfEntry 9 }

rtbPerfItfTxDataRate OBJECT-TYPE
    SYNTAX		Counter
    ACCESS		read-only
    STATUS		mandatory
    DESCRIPTION
          " Data rate transmited in this interface (kbits/second). "
::={ rtbPerfItfEntry 10 }

rtbPerfItfRxDropRate OBJECT-TYPE
    SYNTAX		Counter
    ACCESS		read-only
    STATUS		mandatory
    DESCRIPTION
          " Data rate droped in reception of this interface (kbits/second). "
::={ rtbPerfItfEntry 11 }

rtbPerfItfTxDropRate OBJECT-TYPE
    SYNTAX		Counter
    ACCESS		read-only
    STATUS		mandatory
    DESCRIPTION
          " Data rate droped in transmition of this interface (kbits/second). "
::={ rtbPerfItfEntry 12 }


--
rtbPerfQoSQueueTable OBJECT-TYPE
    SYNTAX	SEQUENCE OF RtbPerfQoSQueueEntry
    ACCESS	not-accessible
    STATUS	mandatory
    DESCRIPTION
      " Interface performance. "
::={ dmAdRtbPerformance 20  }

rtbPerfQoSQueueEntry OBJECT-TYPE
    SYNTAX	RtbPerfQoSQueueEntry
    ACCESS	not-accessible
    STATUS	mandatory
    DESCRIPTION
      " Entry of rtbPerfQoSQueueTable. "
    INDEX 	{ rtbPerfQoSQueueIndex }
::={ rtbPerfQoSQueueTable 1 }

RtbPerfQoSQueueEntry ::=
    SEQUENCE {
        rtbPerfQoSQueueIndex            INTEGER,
        rtbPerfQoSQueueItfDescr         DisplayString,
        rtbPerfQoSQueueMark             INTEGER,
        rtbPerfQoSQueueTxDataRate       Counter,
        rtbPerfQoSQueueTxPktDropRate    Counter,
        rtbPerfQoSQueueTrafficDescr     DisplayString,
        rtbPerfQoSQueueClassName        DisplayString,
        rtbPerfQoSQueuePriority         INTEGER,
        rtbPerfQoSQueueMinRate          INTEGER,
        rtbPerfQoSQueueMaxRate          INTEGER,
        rtbPerfQoSQueueDroppedBytes     Counter64,
        rtbPerfQoSQueueSentBytes        Counter64,
        rtbPerfQoSQueueEnqueuedBytes    Counter,
        rtbPerfQoSQueueTxDataRateBits   Counter,
        rtbPerfQoSQueueDroppedPkts      Counter64,
        rtbPerfQoSQueueSentPkts         Counter64
         }

rtbPerfQoSQueueIndex	OBJECT-TYPE
      SYNTAX   	INTEGER (1..2000000253)
        ACCESS		read-only
        STATUS		mandatory
        DESCRIPTION
          " Queue number."
::= { rtbPerfQoSQueueEntry 1 }

rtbPerfQoSQueueItfDescr	OBJECT-TYPE
    SYNTAX		DisplayString
    ACCESS		read-only
    STATUS		mandatory
    DESCRIPTION
          " Interface name for this queue. "
::={ rtbPerfQoSQueueEntry 2 }

rtbPerfQoSQueueMark	OBJECT-TYPE
      SYNTAX   	INTEGER (1..2000000253)
    ACCESS		read-only
    STATUS		mandatory
    DESCRIPTION
          " Mark used in this queue. "
::={ rtbPerfQoSQueueEntry 3 }

rtbPerfQoSQueueTxDataRate	OBJECT-TYPE
    SYNTAX		Counter
    ACCESS		read-only
    STATUS		mandatory
    DESCRIPTION
          " Data rate transmited in this queue (kbits/second). "
::={ rtbPerfQoSQueueEntry 4 }

rtbPerfQoSQueueTxPktDropRate       OBJECT-TYPE
               SYNTAX          Counter
               ACCESS          read-only
               STATUS          mandatory
               DESCRIPTION
               " Packets drop rate in this queue (packets/second). "
::={ rtbPerfQoSQueueEntry 5 }

rtbPerfQoSQueueTrafficDescr       OBJECT-TYPE
              SYNTAX          DisplayString
              ACCESS          read-only
              STATUS          mandatory
              DESCRIPTION
              " Description of the filters used in input for the traffic of this class (mark rules)."
::={ rtbPerfQoSQueueEntry 6 }

rtbPerfQoSQueueClassName    OBJECT-TYPE
             SYNTAX          DisplayString
             ACCESS          read-only
             STATUS          mandatory
             DESCRIPTION
             " A configured name for the class."
::={ rtbPerfQoSQueueEntry 7 }

rtbPerfQoSQueuePriority    OBJECT-TYPE
             SYNTAX          INTEGER (1..1023)
             ACCESS          read-only
             STATUS          mandatory
             DESCRIPTION
             " Priority of the class."
::={ rtbPerfQoSQueueEntry 8 }

rtbPerfQoSQueueMinRate    OBJECT-TYPE
             SYNTAX          INTEGER
             ACCESS          read-only
             STATUS          mandatory
             DESCRIPTION
             " Reserved bandwidth for the class (bps)."
::={ rtbPerfQoSQueueEntry 9 }

rtbPerfQoSQueueMaxRate    OBJECT-TYPE
             SYNTAX          INTEGER
             ACCESS          read-only
             STATUS          mandatory
             DESCRIPTION
             " Maximum bandwidth that this class can use (bps)."
::={ rtbPerfQoSQueueEntry 10 }

rtbPerfQoSQueueDroppedBytes    OBJECT-TYPE
       SYNTAX        Counter64
       ACCESS        read-only
       STATUS        mandatory
       DESCRIPTION
           " The total of bytes dropped in this class. "
::={ rtbPerfQoSQueueEntry 11 }

rtbPerfQoSQueueSentBytes    OBJECT-TYPE
       SYNTAX        Counter64
       ACCESS        read-only
       STATUS        mandatory
       DESCRIPTION
           " The total of bytes sent in this class. "
::={ rtbPerfQoSQueueEntry 12 }

rtbPerfQoSQueueEnqueuedBytes    OBJECT-TYPE
       SYNTAX        Counter
       ACCESS        read-only
       STATUS        mandatory
       DESCRIPTION
           " Number of bytes in the queue. "
::={ rtbPerfQoSQueueEntry 13 }

rtbPerfQoSQueueTxDataRateBits    OBJECT-TYPE
       SYNTAX        Counter
       ACCESS        read-only
       STATUS        mandatory
       DESCRIPTION
           " Data rate transmission in the class (bps). "
::={ rtbPerfQoSQueueEntry 14 }

rtbPerfQoSQueueDroppedPkts    OBJECT-TYPE
       SYNTAX        Counter64
       ACCESS        read-only
       STATUS        mandatory
       DESCRIPTION
           " The total of packets dropped in this class. "
::={ rtbPerfQoSQueueEntry 15 }

rtbPerfQoSQueueSentPkts    OBJECT-TYPE
       SYNTAX        Counter64
       ACCESS        read-only
       STATUS        mandatory
       DESCRIPTION
           " The total of packets sent in this class. "
::={ rtbPerfQoSQueueEntry 16 }

--
rtbConfigCopyProtocol	OBJECT-TYPE
    SYNTAX	INTEGER {
                tftp(1), -- TFTP protocol
                ftp(2),  -- FTP protocol
                sftp(3) -- SFTP protocol
            }
    ACCESS	read-write
    STATUS	mandatory
    DESCRIPTION
       "Selects the network protocol to be used on the file rtbConfigCopyFileName transfer
        from the rtbConfigCopyServerAddress to apply the config rtbConfigCopyDestFileType
        onto the device or export it.
        Default value is: tftp(1)"
::={ dmAdRtbConfigCopy 1 }

rtbConfigCopyServerAddress	OBJECT-TYPE
    SYNTAX	IpAddress
    ACCESS	read-write
    STATUS	mandatory
    DESCRIPTION
       " IP address of file server. "
::={ dmAdRtbConfigCopy 2 }

rtbConfigCopyFileName	OBJECT-TYPE
    SYNTAX	DisplayString (SIZE (0..255))
    ACCESS	read-write
    STATUS	mandatory
    DESCRIPTION
       " Name of the file to download or upload according to rtbConfigCopyOpType, it can be a path
        inside the server. "
::={ dmAdRtbConfigCopy 3 }

rtbConfigCopyDestFileType	OBJECT-TYPE
    SYNTAX	INTEGER {
                runningConfig(1), -- Apply on the running configuration
                startupConfig(2) -- Apply on the startup configuration
            }
    ACCESS	read-write
    STATUS	mandatory
    DESCRIPTION
       "Selects on which the file copied from the rtbConfigCopyServerAddress will
        be applied: runningConfig(1) or startupConfig(2). If on runningConfig(1),
        the current device configuration will be changed, else on startupConfig(2),
        then the current config wont be changed and only will take effect after a reboot.
        Default value is: runningConfig(1)"
::={ dmAdRtbConfigCopy 4 }

rtbConfigCopyInitTransfer	OBJECT-TYPE
    SYNTAX	INTEGER {
                inactive(1),
                active(2)
            }
    ACCESS	read-write
    STATUS	mandatory
    DESCRIPTION
       "If the rtbConfigCopyOpType is set to apply (1) then start the process of downloading the
        rtbConfigCopyFileName from rtbConfigCopyServerAddress and apply on
        the rtbConfigCopyDestFileType device configuration. Otherwise, if rtbConfigCopyOpType is
        export (2), then upload the startup-config named as rtbConfigCopyFileName to
        rtbConfigCopyServerAddress. After the process is finished, the status will be available
        in the rtbConfigCopyStatus object.
        Default value is: inactive(1)."
::={ dmAdRtbConfigCopy 5 }

rtbConfigCopyStatus	OBJECT-TYPE
    SYNTAX	INTEGER {
                successful(1),
                running(2),
                failed(3)
            }
    ACCESS	read-only
    STATUS	mandatory
    DESCRIPTION
       "Status of requested process in rtbConfigCopyInitTransfer.
        Default value is: successful(1)."
::={ dmAdRtbConfigCopy 6 }

rtbConfigCopySave	OBJECT-TYPE
    SYNTAX	INTEGER {
                inactive(1),
                active(2)
            }
    ACCESS	read-write
    STATUS	mandatory
    DESCRIPTION
       "Start the process of saving active configuration to flash.
        This process requires some seconds to finish.
        Default value is: inactive(1)."
::={ dmAdRtbConfigCopy 7 }

rtbConfigCopyApplyType	OBJECT-TYPE
    SYNTAX	INTEGER {
                merge(1),
                replace(2)
            }
    ACCESS	read-write
    STATUS	mandatory
    DESCRIPTION
       "Type of apply that will be performed.
        A total replace of the configuration or a merge with the existing config.
        Default value is: replace(2)."
::={ dmAdRtbConfigCopy 8 }

rtbConfigCopyFileFormat	OBJECT-TYPE
    SYNTAX	INTEGER {
                auto-detect(1),
                file-tree(2),
                cmd-sets(3)
            }
    ACCESS	read-write
    STATUS	mandatory
    DESCRIPTION
       "Type of the configuration apply file format that will be sent.
        It might have a set of commands or have a tree scheme.
        By default, the file format is auto detected.
        Default value is: auto-detect(1)."
::={ dmAdRtbConfigCopy 9 }

rtbConfigCopyOpType	OBJECT-TYPE
    SYNTAX	INTEGER {
                apply(1), -- Apply on current configuration
                export(2) -- Export config.boot configuration
            }
    ACCESS	read-write
    STATUS	mandatory
    DESCRIPTION
       "Selects which type of operation will be performed, if applying the
        configuration to the equipment from a TFTP server is desired, select
        apply(1), otherwise select export(2), which will copy the configuration
        from the equipment to a TFTP server."
::={ dmAdRtbConfigCopy 10 }

rtbConfigCopyUser	OBJECT-TYPE
    SYNTAX	DisplayString (SIZE (0..255))
    ACCESS	read-write
    STATUS	mandatory
    DESCRIPTION
       " Username for FTP and SFTP. "
::={ dmAdRtbConfigCopy 11 }

rtbConfigCopyPassword	OBJECT-TYPE
    SYNTAX	DisplayString (SIZE (0..255))
    ACCESS	read-write
    STATUS	mandatory
    DESCRIPTION
       " Password for FTP and SFTP. "
::={ dmAdRtbConfigCopy 12 }

--
rtbLTESignalStrength	OBJECT-TYPE
    SYNTAX	DisplayString (SIZE (0..255))
    ACCESS	read-only
    STATUS	mandatory
    DESCRIPTION
      "LTE signal strength in dBm."
::={ dmAdRtbLTE 1 }

rtbLTEChannel	OBJECT-TYPE
    SYNTAX	INTEGER (1..2000000253)
    ACCESS	read-only
    STATUS	mandatory
    DESCRIPTION
      "Current LTE Channel in use."
::={ dmAdRtbLTE 2 }


--
rtbLTENeighborTable	OBJECT-TYPE
    SYNTAX	SEQUENCE OF RtbLTENeighborEntry
    ACCESS	not-accessible
    STATUS	mandatory
    DESCRIPTION
      "LTE Neighbor information."
::={ dmAdRtbLTE 3 }

rtbLTENeighborEntry	OBJECT-TYPE
    SYNTAX	RtbLTENeighborEntry
    ACCESS	not-accessible
    STATUS	mandatory
    DESCRIPTION
      "Entry of rtbLTENeighborTable."
    INDEX	{ rtbLTENeighborIndex }
::={ rtbLTENeighborTable 1 }

RtbLTENeighborEntry ::=
    SEQUENCE {
        rtbLTENeighborIndex             INTEGER,
        rtbLTENeighborIndexNeighbor     INTEGER,
        rtbLTENeighborDescr             DisplayString,
        rtbLTENeighborRFChannelNumber   DisplayString
         }

rtbLTENeighborIndex	OBJECT-TYPE
    SYNTAX	INTEGER (1..2000000253)
    ACCESS	read-only
    STATUS	mandatory
    DESCRIPTION
      "Index of Neighbor row."
::= { rtbLTENeighborEntry 1 }

rtbLTENeighborIndexNeighbor	OBJECT-TYPE
    SYNTAX	INTEGER (1..2000000253)
    ACCESS	read-only
    STATUS	mandatory
    DESCRIPTION
      "Neighbor number."
::= { rtbLTENeighborEntry 2 }

rtbLTENeighborDescr	OBJECT-TYPE
    SYNTAX	DisplayString
    ACCESS	read-only
    STATUS	mandatory
    DESCRIPTION
      "Neighbor description."
::={ rtbLTENeighborEntry 3 }

rtbLTENeighborRFChannelNumber	OBJECT-TYPE
    SYNTAX	DisplayString
    ACCESS	read-only
    STATUS	mandatory
    DESCRIPTION
      "Neighbor channel number."
::={ rtbLTENeighborEntry 4 }

--
rtbLTENeighborCellsTable	OBJECT-TYPE
    SYNTAX	SEQUENCE OF RtbLTENeighborCellsEntry
    ACCESS	not-accessible
    STATUS	mandatory
    DESCRIPTION
      "LTE Neighbor Cells information."
::={ dmAdRtbLTE 4 }

rtbLTENeighborCellsEntry	OBJECT-TYPE
    SYNTAX	RtbLTENeighborCellsEntry
    ACCESS	not-accessible
    STATUS	mandatory
    DESCRIPTION
      "Entry of rtbLTENeighborCellsTable."
    INDEX 	{ rtbLTENeighborCellsIndex }
::={ rtbLTENeighborCellsTable 1 }

RtbLTENeighborCellsEntry ::=
    SEQUENCE {
        rtbLTENeighborCellsIndex                  INTEGER,
        rtbLTENeighborCellsPhysicalCellID         INTEGER,
        rtbLTENeighborCellsRSRQ                   DisplayString,
        rtbLTENeighborCellsRSRP                   DisplayString,
        rtbLTENeighborCellsRSSI                   DisplayString,
        rtbLTENeighborCellsCellSelectionRXLevel   DisplayString,
         }

rtbLTENeighborCellsIndex	OBJECT-TYPE
    SYNTAX	INTEGER (1..2000000253)
    ACCESS	read-only
    STATUS	mandatory
    DESCRIPTION
      "Index of Neighbor Cell row."
::= { rtbLTENeighborCellsEntry 1 }

rtbLTENeighborCellsPhysicalCellID	OBJECT-TYPE
    SYNTAX	INTEGER (1..2000000253)
    ACCESS	read-only
    STATUS	mandatory
    DESCRIPTION
      "Physical Cell ID."
::= { rtbLTENeighborCellsEntry 2 }

rtbLTENeighborCellsRSRQ	OBJECT-TYPE
    SYNTAX	DisplayString
    ACCESS	read-only
    STATUS	mandatory
    DESCRIPTION
      "RSRQ."
::={ rtbLTENeighborCellsEntry 3 }

rtbLTENeighborCellsRSRP	OBJECT-TYPE
    SYNTAX	DisplayString
    ACCESS	read-only
    STATUS	mandatory
    DESCRIPTION
      "RSRP."
::={ rtbLTENeighborCellsEntry 4 }

rtbLTENeighborCellsRSSI	OBJECT-TYPE
    SYNTAX	DisplayString
    ACCESS	read-only
    STATUS	mandatory
    DESCRIPTION
      "RSSI."
::={ rtbLTENeighborCellsEntry 5 }

rtbLTENeighborCellsCellSelectionRXLevel	OBJECT-TYPE
    SYNTAX	INTEGER (1..2000000253)
    ACCESS	read-only
    STATUS	mandatory
    DESCRIPTION
      "Cell Selection RX Level."
::={ rtbLTENeighborCellsEntry 6 }

rtbLTEConnectionStatus	OBJECT-TYPE
    SYNTAX	INTEGER {
                disconnected(0),
                connected(1)
            }
    ACCESS	read-only
    STATUS	mandatory
    DESCRIPTION
       "Identify whether LTE interface is connected to a network."
::={ dmAdRtbLTE 5 }

END

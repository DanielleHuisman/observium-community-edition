DM-BGP-PEER-MIB DEFINITIONS ::= BEGIN
IMPORTS
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
    InetAddressType,
    InetAddress
        FROM INET-ADDRESS-MIB
    datacomDevicesMIBs
        FROM DATACOM-SMI
;

dmBgpPeerMIB MODULE-IDENTITY
    LAST-UPDATED "202010260000Z"
    ORGANIZATION "DATACOM"
    CONTACT-INFO
                 "DATACOM

                 Postal: DATACOM
                     Rua America, 1000
                     Eldorado do Sul, RS
                     CEP 92990-000
                             BRAZIL

                 Tel:+55(51)3933 3000
                 Fax:+55(51)3933 3003

                 E-mail: datacom@datacom.ind.br "
    DESCRIPTION "The DATACOM MIB module for BGP peer information."
    REVISION "202010260000Z"
    DESCRIPTION "Initial revision."
    ::= { datacomDevicesMIBs 15 }

dmBgpPeerTable OBJECT-TYPE
    SYNTAX	SEQUENCE OF dmBgpPeerEntry
    ACCESS	not-accessible
    STATUS	current
    DESCRIPTION
            "BGP peer table.  This table contains
            one entry per BGP peer, with information about the
            connection with each peer."
    ::= { dmBgpPeerMIB 1 }

dmBgpPeerEntry OBJECT-TYPE
    SYNTAX	dmBgpPeerEntry
    ACCESS	not-accessible
    STATUS	current
    DESCRIPTION
            "Entry containing information about the
            connection with a BGP peer."
    INDEX { dmBgpPeerRemoteAddrType, dmBgpPeerRemoteAddr }
    ::={ dmBgpPeerTable 1 }

dmBgpPeerEntry ::=
    SEQUENCE {
        dmBgpPeerRemoteAddrType        InetAddressType,
        dmBgpPeerRemoteAddr            InetAddress,
        dmBgpPeerRemoteAs              INTEGER,
        dmBgpPeerState                 INTEGER
         }

dmBgpPeerRemoteAddrType OBJECT-TYPE
    SYNTAX     InetAddressType
    MAX-ACCESS not-accessible
    STATUS     current
    DESCRIPTION
           "The address type of dmBgpPeerRemoteAddr."
    ::= { dmBgpPeerEntry 1 }

dmBgpPeerRemoteAddr OBJECT-TYPE
    SYNTAX     InetAddress
    MAX-ACCESS not-accessible
    STATUS     current
    DESCRIPTION
           "The remote IP address of the BGP peer."
    ::= { dmBgpPeerEntry 2 }

dmBgpPeerRemoteAs OBJECT-TYPE
    SYNTAX     INTEGER (0..65535)
    MAX-ACCESS read-only
    STATUS     current
    DESCRIPTION
            "The remote autonomous system number."
    ::= { dmBgpPeerEntry 3 }

dmBgpPeerState OBJECT-TYPE
    SYNTAX     INTEGER {
                        idle(1),
                        connect(2),
                        active(3),
                        opensent(4),
                        openconfirm(5),
                        established(6)
               }
    MAX-ACCESS read-only
    STATUS     current
    DESCRIPTION
            "The BGP peer connection state."
    ::= { dmBgpPeerEntry 4 }

END

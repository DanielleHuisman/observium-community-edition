DNOS-GREENETHERNET-PRIVATE-MIB DEFINITIONS ::= BEGIN 
               
IMPORTS           
    MODULE-IDENTITY, OBJECT-TYPE, NOTIFICATION-TYPE,
    Unsigned32, Integer32, Gauge32      FROM SNMPv2-SMI
    TEXTUAL-CONVENTION                  FROM SNMPv2-TC
    InterfaceIndexOrZero                FROM IF-MIB
    DisplayString                       FROM RFC1213-MIB
    dnOS                            FROM DELL-REF-MIB;

    fastPathGreenEthernet MODULE-IDENTITY
        LAST-UPDATED "201810150000Z" -- 15 Oct 2018 12:00:00 GMT
        ORGANIZATION "Dell EMC"
        CONTACT-INFO ""
        DESCRIPTION
           "The MIB definitions for DNOS Green Ethernet Feature."

      -- Revision history.
        REVISION
           "201810150000Z" -- 15 Oct 2018 12:00:00 GMT
        DESCRIPTION
           "Fix some SMIv2 conformance issues. Remove tab characters. General 
            formatting improvements."
        REVISION
           "201101260000Z" -- 26 Jan 2011 12:00:00 GMT
        DESCRIPTION
           "Postal address updated."

    ::= { dnOS 55 }

--*********************************************************************
--   agentGreenEthernet
--
--*********************************************************************

    agentGreenEthernet OBJECT IDENTIFIER ::= { fastPathGreenEthernet 1 }

    -- Green Ethernet Configuration table (global and per-port)
    agentGreenEthernetTable OBJECT-TYPE
        SYNTAX      SEQUENCE OF AgentGreenEthernetEntry
        MAX-ACCESS  not-accessible
        STATUS      current
        DESCRIPTION
                    "A table providing configuration of Green Ethernet features."
    ::= { agentGreenEthernet 1 }

    agentGreenEthernetEntry OBJECT-TYPE
        SYNTAX      AgentGreenEthernetEntry
        MAX-ACCESS  not-accessible
        STATUS      current
        DESCRIPTION
                   "Green Ethernet features for a port."
        INDEX { agentEthernetIntfIndex }
    ::= { agentGreenEthernetTable 1 }

    AgentGreenEthernetEntry::= SEQUENCE {
        agentEthernetIntfIndex
            INTEGER,
        agentGreenEnergyDetectMode         
            INTEGER,
        agentGreenEnergyDetectOperStatus
            INTEGER,
        agentGreenEnergyDetectOperReason
             DisplayString,
        agentGreenEeeMode
            INTEGER,
        agentGreenEeeTxWakeTime
            INTEGER,
        agentGreenEeeTxIdleTime
            Unsigned32,
        agentGreenCumEnergySaving
            Unsigned32
    }

    agentEthernetIntfIndex OBJECT-TYPE
        SYNTAX      INTEGER (1..4096)
        MAX-ACCESS  not-accessible
        STATUS      current
        DESCRIPTION
                   "Index for an entry in the agentGreenEthernetTable. A non-
                    zero value indicates the ifIndex for the corresponding
                    interface entry in the ifTable. A value of zero represents
                    global configuration, which in turn causes all interface
                    entries to be updated for a set operation, or reflects the
                    most recent global setting for a get operation."
    ::= { agentGreenEthernetEntry 1 }

    agentGreenEnergyDetectMode         OBJECT-TYPE 
        SYNTAX      INTEGER {
                        disable(0),
                        enable(1),
                        not-applicable(2)
                    }
        MAX-ACCESS  read-write
        STATUS      current
        DESCRIPTION
                   "Enable or disable Energy Detect Mode. If Energy detect Mode
                    is not supported on a particular port then not-applicable(2)
                    is returned. This object cannot be set to not-applicable(2)."
    ::= { agentGreenEthernetEntry 2 }

    agentGreenEnergyDetectOperStatus         OBJECT-TYPE
        SYNTAX      INTEGER {
                        in-active(0),
                        active(1)
                    }
        MAX-ACCESS  read-only
        STATUS      current
        DESCRIPTION
                   "Indicates if energy detect operational status is currently
                    active or inactive. The energy detect mode may be 
                    administratively enabled, but the operational status may
                    be inactive."
    ::= { agentGreenEthernetEntry 3 }

    agentGreenEnergyDetectOperReason         OBJECT-TYPE
        SYNTAX      DisplayString (SIZE(1..32))
        MAX-ACCESS  read-only
        STATUS      current
        DESCRIPTION
                   "The energy detect mode may be administratively enabled, but
                    the operational status may be inactive. Reasons for this
                    may be that the Port is currently operating in the fiber
                    mode, the Link is up, or the Admin Mode is Down. If the
                    energy-detect operational status is active, the reason
                    field shows up as 'No Energy Detected'."
    ::= { agentGreenEthernetEntry 4}

    agentGreenEeeMode         OBJECT-TYPE 
        SYNTAX      INTEGER {
                        disable(0),
                        enable(1),
                        not-applicable(2)
                    }
        MAX-ACCESS  read-write
        STATUS      current
        DESCRIPTION
                   "Enable or disable Energy Efficient Ethernet(EEE) Mode. If 
                    EEE Mode is not supported on a particular port then not-
                    applicable(2) is displayed. This object cannot be set to 
                    not-applicable(2)."
    ::= { agentGreenEthernetEntry 9 }

    agentGreenEeeTxWakeTime         OBJECT-TYPE
        SYNTAX      INTEGER (8..65535)
        MAX-ACCESS  read-write
        STATUS      current
        DESCRIPTION
                   "Time for which MAC/switch has to wait to go back to ACTIVE
                    state from LPI state when it receives packet for transmission."
    ::= { agentGreenEthernetEntry 10 }

    agentGreenEeeTxIdleTime         OBJECT-TYPE 
        SYNTAX      Unsigned32 (600..4294967295)
        MAX-ACCESS  read-write
        STATUS      current
        DESCRIPTION
                   "Time for which condition to move to LPI state is satisfied,
                   at the end of which MAC TX transitions to LPI state."
    ::= { agentGreenEthernetEntry 11 }

    agentGreenCumEnergySaving         OBJECT-TYPE 
        SYNTAX      Unsigned32
        MAX-ACCESS  read-only
        STATUS      current
        DESCRIPTION
                   "Estimated Cumulative Energy Saved on this port in (Watt*hours)."
    ::= { agentGreenEthernetEntry 12 }

--*********************************************************************
-- Green Ethernet Interface EEE LPI History table
--
--*********************************************************************
    agentGreenIntfEeeLpiHistoryTable OBJECT-TYPE
        SYNTAX      SEQUENCE OF AgentGreenIntfEeeLpiHistoryEntry
        MAX-ACCESS  not-accessible
        STATUS      current
        DESCRIPTION
                   "A table providing configuration and status of Green
                    Ethernet Power Saving History feature"

         ::= { agentGreenEthernet 2 }

    agentGreenIntfEeeLpiHistoryEntry OBJECT-TYPE
        SYNTAX      AgentGreenIntfEeeLpiHistoryEntry
        MAX-ACCESS  not-accessible
        STATUS      current
        DESCRIPTION
                   "Green Ethernet features for a port."
        INDEX   { agentGreenEeeLpiHistoryIntfIndex, agentGreenEeeLpiHistoryIntfSampleIndex }
    ::= { agentGreenIntfEeeLpiHistoryTable 1 }

    AgentGreenIntfEeeLpiHistoryEntry::=
        SEQUENCE {
            agentGreenEeeLpiHistoryIntfIndex
                INTEGER,
            agentGreenEeeLpiHistoryIntfSampleIndex         
                INTEGER,
            agentGreenEeeLpiHistoryIntfSampleTime
                DisplayString,
            agentGreenEeeLpiHistoryIntfPercentLpiTime
                Gauge32,
            agentGreenEeeLpiHistoryIntfPercentLpiTimeTotal
                Gauge32
         }

    agentGreenEeeLpiHistoryIntfIndex OBJECT-TYPE
        SYNTAX      INTEGER (1..4096)
        MAX-ACCESS  not-accessible
        STATUS      current
        DESCRIPTION
                   "This is the index for an entry in the agentGreenEthernetTable.
                    A non-zero value indicates the ifIndex for the corresponding
                    interface entry in the ifTable."
    ::= { agentGreenIntfEeeLpiHistoryEntry 1 }

    agentGreenEeeLpiHistoryIntfSampleIndex         OBJECT-TYPE 
        SYNTAX      INTEGER (1..2147483647)
        MAX-ACCESS  not-accessible
        STATUS      current
        DESCRIPTION
                   "This is the sample index for an entry in the
                    agentGreenEthernetTable. A non-zero value indicates the
                    sampleIndex for the corresponding sample entry in the Power
                    Saving History Table."
    ::= { agentGreenIntfEeeLpiHistoryEntry 2 }

    agentGreenEeeLpiHistoryIntfSampleTime         OBJECT-TYPE 
        SYNTAX      DisplayString (SIZE(1..32))
        MAX-ACCESS  read-only
        STATUS      current
        DESCRIPTION
                   "Time at which the sample was collected."
    ::= { agentGreenIntfEeeLpiHistoryEntry 3}

    agentGreenEeeLpiHistoryIntfPercentLpiTime         OBJECT-TYPE 
        SYNTAX      Gauge32(0..100)
        UNITS       "percent"
        MAX-ACCESS  read-only
        STATUS      current
        DESCRIPTION
                   "Percentage of Time spent in LPI mode on this port since
                    last sample."
         ::= { agentGreenIntfEeeLpiHistoryEntry 4 }

    agentGreenEeeLpiHistoryIntfPercentLpiTimeTotal         OBJECT-TYPE 
        SYNTAX      Gauge32(0..100)
        UNITS       "percent"
        MAX-ACCESS  read-only
        STATUS      current
        DESCRIPTION
                   "Percentage of Time spent in LPI mode on this port since
                   last reset."
         ::= { agentGreenIntfEeeLpiHistoryEntry 5 }

--*********************************************************************
-- Scalars 
--
--*********************************************************************

    agentGreenEeeLpiHistoryIntfSampleInterval         OBJECT-TYPE 
        SYNTAX      INTEGER (30..36000)
        MAX-ACCESS  read-write
        STATUS      current
        DESCRIPTION
                   "Interval at which power consumption data is collected."
    ::= { agentGreenEthernet 4 }

    agentGreenEeeLpiHistoryIntfMaxSamples         OBJECT-TYPE 
        SYNTAX      INTEGER (1..168)
        MAX-ACCESS  read-write
        STATUS      current
        DESCRIPTION
                   "Maximum number of samples to keep."
         ::= { agentGreenEthernet 5 }
         
--*********************************************************************
-- Green Ethernet Unit Feature Table
--
--*********************************************************************
    agentGreenUnitFeatureTable OBJECT-TYPE
        SYNTAX      SEQUENCE OF AgentGreenUnitFeatureEntry
        MAX-ACCESS  not-accessible
        STATUS      current
        DESCRIPTION
                   "A table providing configuration and status of Green Ethernet
                   Power Saving History feature."
         ::= { agentGreenEthernet 3 }

    agentGreenUnitFeatureEntry OBJECT-TYPE
        SYNTAX      AgentGreenUnitFeatureEntry
        MAX-ACCESS  not-accessible
        STATUS      current
        DESCRIPTION
                   "Green Ethernet features for a port."
        INDEX   { agentGreenUnitIndex }
    ::= { agentGreenUnitFeatureTable 1 }

    AgentGreenUnitFeatureEntry::=
        SEQUENCE {
            agentGreenUnitIndex
                INTEGER,
            agentGreenFeatureList
                DisplayString
        }

    agentGreenUnitIndex OBJECT-TYPE
        SYNTAX      INTEGER (1..8)
        MAX-ACCESS  not-accessible
        STATUS      current
        DESCRIPTION
                   "The index for an entry in the agentGreenUnitFeatureTable. A
                    non-zero value indicates the unitIndex for the corresponding
                    unit entry in the Green Ethernet Unit Feature Table."
    ::= { agentGreenUnitFeatureEntry 1 }

    agentGreenFeatureList         OBJECT-TYPE 
        SYNTAX      DisplayString (SIZE(1..128))
        MAX-ACCESS  read-only
        STATUS      current
        DESCRIPTION
                   "List of Green Features supported on the given unit which
                    could be one or more of the following:
                        Energy-Detect (Energy Detect) 
                        Short-Reach (Short Reach)
                        EEE (Energy Efficient Ethernet) 
                        LPI-History (EEE Low Power Idle History) 
                        LLDP-Cap-Exchg (EEE LLDP Capability Exchange) 
                        Pwr-Usg-Est (Power Usage Estimates)."
    ::= { agentGreenUnitFeatureEntry 2}

--*********************************************************************
-- Green Ethernet stack status parameters
-- scalars
--
--*********************************************************************
    agentGreenEeeLpiHistoryLpiTimePerStack         OBJECT-TYPE 
        SYNTAX      Gauge32(0..100)
        UNITS       "percent"
        MAX-ACCESS  read-only
        STATUS      current
        DESCRIPTION
                   "Percentage of LPI time per stack."
         ::= { agentGreenEthernet 6 }

    agentGreenStackCumEnergySaving         OBJECT-TYPE 
        SYNTAX      Unsigned32
        MAX-ACCESS  read-only
        STATUS      current
        DESCRIPTION
                   "Estimated Cumulative Energy Saving (Watts * Hours) per 
                   Stack."
         ::= { agentGreenEthernet 7 }

    agentGreenStackCurPowerConsumption         OBJECT-TYPE 
        SYNTAX      Unsigned32
        MAX-ACCESS  read-only
        STATUS      current
        DESCRIPTION
                   "Estimated Current Power Consumption (mWatts) per Stack."
         ::= { agentGreenEthernet 8 }

    agentGreenStackPowerSaving         OBJECT-TYPE 
        SYNTAX      Gauge32(0..100)
        UNITS       "percent"
        MAX-ACCESS  read-only
        STATUS      current
        DESCRIPTION
                   "Estimated Percentage Power Saving per Stack."
         ::= { agentGreenEthernet 9 }

END

DNOS-MACSEC-MIB DEFINITIONS ::= BEGIN

-- Broadcom FastPath MACsec MIB
-- Copyright 2020-2021 Broadcom.
-- This SNMP Management Information Specification
-- embodies Broadcom's confidential and proprietary
-- intellectual property. Broadcom retains all title
-- and ownership in the Specification including any revisions.

-- This Specification is supplied "AS IS", Broadcom 
-- makes no warranty, either expressed or implied,
-- as to the use, operation, condition, or performance of the
-- Specification.

IMPORTS
    MODULE-IDENTITY,
    OBJECT-TYPE,
    NOTIFICATION-TYPE, 
    TimeTicks,
    Unsigned32,
    Counter32,
    Counter64
        FROM SNMPv2-SMI
    MacAddress,
    TEXTUAL-CONVENTION,
    DateAndTime,
    RowStatus,
    TruthValue
        FROM SNMPv2-TC
    DisplayString
        FROM RFC1213-MIB
    ifIndex
        FROM IF-MIB
    InterfaceIndex
        FROM IF-MIB
    SnmpAdminString
        FROM SNMP-FRAMEWORK-MIB
    dnOS  FROM DELL-REF-MIB;

fastPathMACsec MODULE-IDENTITY
    LAST-UPDATED    "202101280000Z" -- 28 Jan 2021 12:00:00 GMT
    ORGANIZATION "Dell"
    CONTACT-INFO ""
    DESCRIPTION
        "The Dell Networking Private MIB for MACsec"

    -- Revision history.
    REVISION
        "202101280000Z" -- 28 Jan 2021 12:00:00 GMT
    DESCRIPTION
        "Added New OID agentMACsecMKAPolicySecureAnnouncements to AgentMACsecMKAPolicyConfigEntry.
         Added New OID agentMACsecDefaultSecureAnnouncements."
    REVISION
        "202008210000Z" -- 21 Aug 2020 12:00:00 GMT
    DESCRIPTION
        "Initial version."

    ::= { dnOS 78 }

    MACsecCipherSuite ::= TEXTUAL-CONVENTION
        STATUS            current
        DESCRIPTION
            "The MACsec Cipher Suite."
        SYNTAX            INTEGER  {
                              gcmAes128(0),
                              gcmAes256(1),
                              gcmAesXpn128(2),
                              gcmAesXpn256(3)
                          }

    MACsecConfidentialityOffset ::= TEXTUAL-CONVENTION
        STATUS                      current
        DESCRIPTION
            "The MACsec Confidentiality Offset."
        SYNTAX                      INTEGER {
                                        noConfidentiality(0),
                                        confidentialityWithNoOffset(1),
                                        offset30(2),
                                        offset50(3)
                                    }

    --**************************************************************************************
    --    agentMACsecMKAPolicyConfigGroup
    --**************************************************************************************
    
    agentMACsecMKAPolicyConfigGroup                 OBJECT IDENTIFIER ::= { fastPathMACsec 1 }

    agentMACsecMKAPolicyConfigTable OBJECT-TYPE
         SYNTAX      SEQUENCE OF AgentMACsecMKAPolicyConfigEntry  
         MAX-ACCESS  not-accessible
         STATUS      current
         DESCRIPTION
                     "The MKA policy configuration for MACsec"
         ::= { agentMACsecMKAPolicyConfigGroup 1 }

    agentMACsecMKAPolicyConfigEntry OBJECT-TYPE
         SYNTAX     AgentMACsecMKAPolicyConfigEntry 
         MAX-ACCESS  not-accessible
         STATUS      current
         DESCRIPTION
                     "The MACsec MKA policy config entry."
         INDEX       { agentMACsecMKAPolicyName}
         ::= { agentMACsecMKAPolicyConfigTable 1 }

    AgentMACsecMKAPolicyConfigEntry ::= SEQUENCE {
                         agentMACsecMKAPolicyName 
                            SnmpAdminString ,
                         agentMACsecMKAPolicyKeyServerPriority 
                            Unsigned32,
                         agentMACsecMKAPolicySecureAnnouncements
                            INTEGER,
                         agentMACsecMKAPolicyCipherSuite 
                            INTEGER, 
                         agentMACsecMKAPolicyConfidentialityOffset 
                            INTEGER, 
                         agentMACsecMKAPolicyRowStatus 
                            RowStatus 
           }

    agentMACsecMKAPolicyName   OBJECT-TYPE
         SYNTAX      SnmpAdminString (SIZE (1..16))
         MAX-ACCESS  read-create
         STATUS      current
         DESCRIPTION
                     "The MACsec MKA Policy name."

         ::= { agentMACsecMKAPolicyConfigEntry 1 }

    agentMACsecMKAPolicyKeyServerPriority OBJECT-TYPE
         SYNTAX     Unsigned32 (0..255)
         MAX-ACCESS read-create 
         STATUS     current
         DESCRIPTION
                     "The Key Server priority as defined by the MKA Policy." 
         DEFVAL { 255 }

         ::= { agentMACsecMKAPolicyConfigEntry 2 }

    agentMACsecMKAPolicySecureAnnouncements OBJECT-TYPE
         SYNTAX      INTEGER {
                        enable(1),
                        disable(2)
                    }
         MAX-ACCESS  read-create
         STATUS      current
         DESCRIPTION
                     "To configure MKA policy for secure announcements."
         DEFVAL { disable }

         ::= { agentMACsecMKAPolicyConfigEntry 3 }

    agentMACsecMKAPolicyCipherSuite OBJECT-TYPE
         SYNTAX      INTEGER {
                        gcmAes128(0),
                        gcmAes256(1),
                        gcmAesXpn128(2),
                        gcmAesXpn256(3)
                    }
         MAX-ACCESS  read-create
         STATUS      current
         DESCRIPTION
                     "The cipher suite as defined by the MKA Policy." 
         DEFVAL { gcmAes128 }

         ::= { agentMACsecMKAPolicyConfigEntry 4 }

    agentMACsecMKAPolicyConfidentialityOffset OBJECT-TYPE
         SYNTAX      INTEGER {
                        noConfidentiality(0),
                        confidentialityWithNoOffset(1),
                        offset30(2),
                        offset50(3)
                    }
         MAX-ACCESS  read-create
         STATUS      current
         DESCRIPTION
                     "The cipher suite as defined by the MKA Policy." 
         DEFVAL { confidentialityWithNoOffset }

         ::= { agentMACsecMKAPolicyConfigEntry 5 }

    agentMACsecMKAPolicyRowStatus OBJECT-TYPE
         SYNTAX      RowStatus
         MAX-ACCESS  read-create
         STATUS      current
         DESCRIPTION
                     "The object to create parameters for the MKA Policy." 

         ::= { agentMACsecMKAPolicyConfigEntry 6 }


    --**************************************************************************************
    --agentMACsecKeyConfigGroup
    --**************************************************************************************

    agentMACsecKeyConfigGroup                 OBJECT IDENTIFIER ::= { fastPathMACsec 2 }

    agentMACsecKeyConfigTable OBJECT-TYPE
         SYNTAX      SEQUENCE OF AgentMACsecKeyConfigEntry  
         MAX-ACCESS  not-accessible
         STATUS      current
         DESCRIPTION
                     "The Key configuration for MACsec"

         ::= { agentMACsecKeyConfigGroup 1 }

    agentMACsecKeyConfigEntry OBJECT-TYPE
         SYNTAX     AgentMACsecKeyConfigEntry 
         MAX-ACCESS  not-accessible
         STATUS      current
         DESCRIPTION
                     "The MACsec Key config entry."
         INDEX       { agentMACsecKeyChainName , agentMACsecKeyName}
         ::= { agentMACsecKeyConfigTable 1 }

    AgentMACsecKeyConfigEntry ::= SEQUENCE {
                         agentMACsecKeyChainName 
                            OCTET STRING,
                         agentMACsecKeyName
                            OCTET STRING,
                         agentMACsecKeyCryptographicAlgorithm 
                            INTEGER, 
                         agentMACsecKeyString 
                            OCTET STRING, 
                         agentMACsecKeyTimeRange
                            OCTET STRING,
                         agentMACsecKeyRowStatus 
                            RowStatus 
           }


    agentMACsecKeyChainName OBJECT-TYPE
         SYNTAX     OCTET STRING (SIZE (1..16))
         MAX-ACCESS read-create
         STATUS     current
         DESCRIPTION
                     "The MACsec Key Chain name to which the MACsec key is associated."

         ::= { agentMACsecKeyConfigEntry 1 }

    agentMACsecKeyName   OBJECT-TYPE
         SYNTAX      OCTET STRING (SIZE (1..64))
         MAX-ACCESS  read-create
         STATUS      current
         DESCRIPTION
                     "The MACsec Key name."
         ::= { agentMACsecKeyConfigEntry 2 }

    agentMACsecKeyCryptographicAlgorithm OBJECT-TYPE
         SYNTAX      INTEGER {
                        gcmAes128(1),
                        gcmAes256(2)
                    }
         MAX-ACCESS  read-create
         STATUS      current
         DESCRIPTION
                     "The MACsec key cryptographic algorithm." 
         DEFVAL { gcmAes128 }

         ::= { agentMACsecKeyConfigEntry 3 }

    agentMACsecKeyString OBJECT-TYPE
         SYNTAX      OCTET STRING (SIZE (0 | 32 | 64))
         MAX-ACCESS  read-create
         STATUS      current
         DESCRIPTION
                     "The MACsec key value.
                     SIZE 0 KeyString to set default."

         ::= { agentMACsecKeyConfigEntry 4 }

    agentMACsecKeyTimeRange OBJECT-TYPE
         SYNTAX      OCTET STRING (SIZE (0 | 1..31))
         MAX-ACCESS  read-create
         STATUS      current
         DESCRIPTION
                     "The MACsec key time-range.
                     SIZE 0 TimeRange to set default."

         ::= { agentMACsecKeyConfigEntry 5 }


    agentMACsecKeyRowStatus OBJECT-TYPE
         SYNTAX      RowStatus
         MAX-ACCESS  read-create
         STATUS      current
         DESCRIPTION
                     "The object to create parameters for the MACsec key." 

         ::= { agentMACsecKeyConfigEntry 6 }


    --**************************************************************************************
    --agentMACsecInterfaceConfigGroup
    --**************************************************************************************

    agentMACsecInterfaceConfigGroup                 OBJECT IDENTIFIER ::= { fastPathMACsec 3 }

    agentMACsecInterfaceConfigTable OBJECT-TYPE
         SYNTAX      SEQUENCE OF AgentMACsecInterfaceConfigEntry  
         MAX-ACCESS  not-accessible
         STATUS      current
         DESCRIPTION
                     "The MKA interface configuration for MACsec"
         ::= { agentMACsecInterfaceConfigGroup 1 }

    agentMACsecInterfaceConfigEntry OBJECT-TYPE
         SYNTAX     AgentMACsecInterfaceConfigEntry 
         MAX-ACCESS  not-accessible
         STATUS      current
         DESCRIPTION
                     "The MACsec interface config entry."
         INDEX       { agentMACsecInterfaceIndex}
         ::= { agentMACsecInterfaceConfigTable 1 }

    AgentMACsecInterfaceConfigEntry ::= SEQUENCE {
                         agentMACsecInterfaceIndex 
                            InterfaceIndex,
                         agentMACsecInterfaceNetworkLink 
                            INTEGER,
                         agentMACsecInterfaceMKAPolicy 
                            OCTET STRING, 
                         agentMACsecInterfaceKeyChain 
                            OCTET STRING, 
                         agentMACsecInterfaceReplayProtection 
                            INTEGER, 
                         agentMACsecInterfaceReplayProtectionWindowSize
                            Unsigned32
           }

    agentMACsecInterfaceIndex   OBJECT-TYPE
         SYNTAX      InterfaceIndex
         MAX-ACCESS  not-accessible
         STATUS      current
         DESCRIPTION
                     "The physical port for MACsec configuration."

         ::= { agentMACsecInterfaceConfigEntry 1 }

    agentMACsecInterfaceNetworkLink   OBJECT-TYPE
         SYNTAX      INTEGER {
                        none(1),
                        switchToSwitch(2),
                        hostToSwitch(3)
                    }
         MAX-ACCESS  read-write
         STATUS      current
         DESCRIPTION
                     "MACsec mode on the port."

         ::= { agentMACsecInterfaceConfigEntry 2 }

    agentMACsecInterfaceMKAPolicy   OBJECT-TYPE
         SYNTAX      OCTET STRING (SIZE (1..16))
         MAX-ACCESS  read-write
         STATUS      current
         DESCRIPTION
                     "The MKA policy configured on the port."

         ::= { agentMACsecInterfaceConfigEntry 3 }

    agentMACsecInterfaceKeyChain   OBJECT-TYPE
         SYNTAX      OCTET STRING (SIZE (0..16))
         MAX-ACCESS  read-write
         STATUS      current
         DESCRIPTION
                     "The MACsec Keychain configured on the port."

         ::= { agentMACsecInterfaceConfigEntry 4 }


    agentMACsecInterfaceReplayProtection   OBJECT-TYPE
         SYNTAX      INTEGER {
                        enable(1),
                        disable(2)
                    }
         MAX-ACCESS  read-write
         STATUS      current
         DESCRIPTION
                     "Enable or Disable MACsec Replay Protection on the port."

         ::= { agentMACsecInterfaceConfigEntry 5 }

    agentMACsecInterfaceReplayProtectionWindowSize   OBJECT-TYPE
         SYNTAX      Unsigned32 (0..4294967295)
         MAX-ACCESS  read-write
         STATUS      current
         DESCRIPTION
                     "Configure MACsec Replay Protection Window size on the port."

         ::= { agentMACsecInterfaceConfigEntry 6 }

    --**************************************************************************************
    --agentMACsecMkaSessionGroup
    --**************************************************************************************

    agentMACsecMkaSessionGroup                 OBJECT IDENTIFIER ::= { fastPathMACsec 4 }

    agentMACsecMkaSessionTable OBJECT-TYPE
         SYNTAX      SEQUENCE OF AgentMACsecMkaSessionEntry
         MAX-ACCESS  not-accessible
         STATUS      current
         DESCRIPTION
                     "The MKA session for MACsec."

         ::= { agentMACsecMkaSessionGroup 1 }

    agentMACsecMkaSessionEntry OBJECT-TYPE
         SYNTAX      AgentMACsecMkaSessionEntry
         MAX-ACCESS  not-accessible
         STATUS      current
         DESCRIPTION
                     "The MACsec Session entry."
         INDEX       { agentMACsecMkaInterfaceIndex}

         ::= { agentMACsecMkaSessionTable 1 }

    AgentMACsecMkaSessionEntry ::= SEQUENCE {
                 agentMACsecMkaInterfaceIndex
                    InterfaceIndex,
                 agentMACsecMkaPolicy
                    OCTET STRING,
                 agentMACsecMkaCkn
                    OCTET STRING,
                 agentMACsecMkaLocalTxSci
                    OCTET STRING,
                 agentMACsecMkaPeerRxSci
                    OCTET STRING,
                 agentMACsecMkaKeyServer
                    INTEGER,
                 agentMACsecMkaPeers
                    INTEGER
         }


    agentMACsecMkaInterfaceIndex   OBJECT-TYPE
        SYNTAX      InterfaceIndex
        MAX-ACCESS  not-accessible
        STATUS      current
        DESCRIPTION
                    "The logical port for MKA session."

        ::= { agentMACsecMkaSessionEntry 1 }

    agentMACsecMkaPolicy   OBJECT-TYPE
        SYNTAX      OCTET STRING (SIZE (1..16))
        MAX-ACCESS  read-only
        STATUS      current
        DESCRIPTION
                    "The MKA policy configured on the port of MKA session."

        ::= { agentMACsecMkaSessionEntry 2 }

    agentMACsecMkaCkn   OBJECT-TYPE
        SYNTAX      OCTET STRING (SIZE (32 | 64))
        MAX-ACCESS  read-only
        STATUS      current
        DESCRIPTION
                    "The CKN configured on the port of MKA session."

        ::= { agentMACsecMkaSessionEntry 3 }

    agentMACsecMkaLocalTxSci   OBJECT-TYPE
        SYNTAX      OCTET STRING (SIZE (22))
        MAX-ACCESS  read-only
        STATUS      current
        DESCRIPTION
                    "TxSci of MKA session on port."

        ::= { agentMACsecMkaSessionEntry 4 }

    agentMACsecMkaPeerRxSci   OBJECT-TYPE
        SYNTAX      OCTET STRING (SIZE (22))
        MAX-ACCESS  read-only
        STATUS      current
        DESCRIPTION
                    "RxSci of MKA session on port."

        ::= { agentMACsecMkaSessionEntry 5 }

    agentMACsecMkaKeyServer   OBJECT-TYPE
        SYNTAX      INTEGER {
                       yes(1),
                       no(2)
                    }
        MAX-ACCESS  read-only
        STATUS      current
        DESCRIPTION
                    "The Key Server status ."

        ::= { agentMACsecMkaSessionEntry 6 }

    agentMACsecMkaPeers   OBJECT-TYPE
        SYNTAX      INTEGER
        MAX-ACCESS  read-only
        STATUS      current
        DESCRIPTION
                    " Number of MKA Peers."

        ::= { agentMACsecMkaSessionEntry 7 }

    --**************************************************************************************
    --agentMACsecMkaPortStatisticsGroup
    --**************************************************************************************

    agentMACsecMkaPortStatisticsGroup                 OBJECT IDENTIFIER ::= { fastPathMACsec 5 }

    agentMACsecMkaStatisticsTable OBJECT-TYPE
         SYNTAX      SEQUENCE OF AgentMACsecMkaStatisticsEntry
         MAX-ACCESS  not-accessible
         STATUS      current
         DESCRIPTION
                     "The MACsec MKA Statistics."

         ::= { agentMACsecMkaPortStatisticsGroup 1 }

    agentMACsecMkaStatisticsEntry OBJECT-TYPE
         SYNTAX      AgentMACsecMkaStatisticsEntry
         MAX-ACCESS  not-accessible
         STATUS      current
         DESCRIPTION
                     "The MACsec MKA Statistics entry."
         INDEX       { agentMACsecInterfaceIndex }

         ::= { agentMACsecMkaStatisticsTable 1 }

    AgentMACsecMkaStatisticsEntry ::= SEQUENCE {
                 agentMACsecMkaSaksGenerated
                    Counter64,
                 agentMACsecMkaSaksRekeyed
                    Counter64,
                 agentMACsecMkaSaksReceived
                    Counter64,
                 agentMACsecMkaSaksResponsesReceived
                    Counter64,
                 agentMACsecMkaPduValidatedandRx
                    Counter64,
                 agentMACsecMkaPduTransmitted
                    Counter64,
                 agentMACsecMkaDistributedSAKs
                    Counter64,
                 agentMACsecMkaVersionMismatchPkts
                    Counter32,
                 agentMACsecMkaIcvMismatchPkts
                    Counter32,
                 agentMACsecMkaMiDuplicatePkts
                    Counter32,
                 agentMACsecMkaMnDuplicatePkts
                    Counter32,
                 agentMACsecMkaInvalidDestinationPkts
                    Counter32,
                 agentMACsecMkaFormatingErrorPkts
                    Counter32
         }

    agentMACsecMkaSaksGenerated   OBJECT-TYPE
        SYNTAX      Counter64
        MAX-ACCESS  read-only
        STATUS      current
        DESCRIPTION
                    "The SA Statistics, SAKs Generated."

        ::= { agentMACsecMkaStatisticsEntry 1 }

    agentMACsecMkaSaksRekeyed   OBJECT-TYPE
        SYNTAX      Counter64
        MAX-ACCESS  read-only
        STATUS      current
        DESCRIPTION
                    "The SA Statistics, SAKs Rekeyed."

        ::= { agentMACsecMkaStatisticsEntry 2 }

    agentMACsecMkaSaksReceived   OBJECT-TYPE
        SYNTAX      Counter64
        MAX-ACCESS  read-only
        STATUS      current
        DESCRIPTION
                    "The SA Statistics, SAKs Received."

        ::= { agentMACsecMkaStatisticsEntry 3 }

    agentMACsecMkaSaksResponsesReceived   OBJECT-TYPE
        SYNTAX      Counter64
        MAX-ACCESS  read-only
        STATUS      current
        DESCRIPTION
                    "The SA Statistics, SAKs Responses Revieved."

        ::= { agentMACsecMkaStatisticsEntry 4 }

    agentMACsecMkaPduValidatedandRx   OBJECT-TYPE
        SYNTAX      Counter64
        MAX-ACCESS  read-only
        STATUS      current
        DESCRIPTION
                    "The MKPDUs Statistics, MKPDUs Validated & Rx."

        ::= { agentMACsecMkaStatisticsEntry 5 }

    agentMACsecMkaPduTransmitted   OBJECT-TYPE
        SYNTAX      Counter64
        MAX-ACCESS  read-only
        STATUS      current
        DESCRIPTION
                    "The MKPDUs Statistics, MKPDUs Transmitted."

        ::= { agentMACsecMkaStatisticsEntry 6 }

    agentMACsecMkaDistributedSAKs   OBJECT-TYPE
        SYNTAX      Counter64
        MAX-ACCESS  read-only
        STATUS      current
        DESCRIPTION
                    "The MKPDUs Statistics, Distributed SAKs."

        ::= { agentMACsecMkaStatisticsEntry 7 }

    agentMACsecMkaVersionMismatchPkts   OBJECT-TYPE
        SYNTAX      Counter32
        MAX-ACCESS  read-only
        STATUS      current
        DESCRIPTION
                    "The MKA Interface Error Statistics, Version Mismatch Packets."

        ::= { agentMACsecMkaStatisticsEntry 8 }

    agentMACsecMkaIcvMismatchPkts   OBJECT-TYPE
        SYNTAX      Counter32
        MAX-ACCESS  read-only
        STATUS      current
        DESCRIPTION
                    "The MKA Interface Error Statistics, ICV Mismatch Packets."

        ::= { agentMACsecMkaStatisticsEntry 9 }

    agentMACsecMkaMiDuplicatePkts   OBJECT-TYPE
        SYNTAX      Counter32
        MAX-ACCESS  read-only
        STATUS      current
        DESCRIPTION
                    "The MKA Interface Error Statistics, MI Duplicate Packets."

        ::= { agentMACsecMkaStatisticsEntry 10 }

    agentMACsecMkaMnDuplicatePkts   OBJECT-TYPE
        SYNTAX      Counter32
        MAX-ACCESS  read-only
        STATUS      current
        DESCRIPTION
                    "The MKA Interface Error Statistics, MN Duplicate Packets."

        ::= { agentMACsecMkaStatisticsEntry 11 }

    agentMACsecMkaInvalidDestinationPkts   OBJECT-TYPE
        SYNTAX      Counter32
        MAX-ACCESS  read-only
        STATUS      current
        DESCRIPTION
                    "The MKA Interface Error Statistics, Invalid Destination Packets."

        ::= { agentMACsecMkaStatisticsEntry 12 }

    agentMACsecMkaFormatingErrorPkts   OBJECT-TYPE
        SYNTAX      Counter32
        MAX-ACCESS  read-only
        STATUS      current
        DESCRIPTION
                    "The MKA Interface Error Statistics, Formating Error Packets."

        ::= { agentMACsecMkaStatisticsEntry 13 }

    --**************************************************************************************
    --agentMACsecMkaGlobalStatisticsGroup
    --**************************************************************************************

    agentMACsecMkaGlobalStatisticsGroup                 OBJECT IDENTIFIER ::= { fastPathMACsec 6 }

    agentMACsecMkaSessionsSecured   OBJECT-TYPE
        SYNTAX      Counter64
        MAX-ACCESS  read-only
        STATUS      current
        DESCRIPTION
                    "MKA Global Statistics, total number of Secured MKA sessions."

        ::= { agentMACsecMkaGlobalStatisticsGroup 1 }

    agentMACsecMkaSessionsDeleted   OBJECT-TYPE
        SYNTAX      Counter64
        MAX-ACCESS  read-only
        STATUS      current
        DESCRIPTION
                    "MKA Global Statistics, total number of Deleted Secured MKA sessions."

        ::= { agentMACsecMkaGlobalStatisticsGroup 2 }

    agentMACsecMkaSaksGeneratedGlobal   OBJECT-TYPE
        SYNTAX      Counter64
        MAX-ACCESS  read-only
        STATUS      current
        DESCRIPTION
                    "MKA Global SA Statistics, SAKs Generated."

        ::= { agentMACsecMkaGlobalStatisticsGroup 3 }

    agentMACsecMkaSaksRekeyedGlobal   OBJECT-TYPE
        SYNTAX      Counter64
        MAX-ACCESS  read-only
        STATUS      current
        DESCRIPTION
                    "MKA Global SA Statistics, SAKs Rekeyed."

        ::= { agentMACsecMkaGlobalStatisticsGroup 4 }

    agentMACsecMkaSaksRxGlobal   OBJECT-TYPE
        SYNTAX      Counter64
        MAX-ACCESS  read-only
        STATUS      current
        DESCRIPTION
                    "MKA Global SA Statistics, SAKs Received."

        ::= { agentMACsecMkaGlobalStatisticsGroup 5 }

    agentMACsecMkaSakResponsesReceivedGlobal   OBJECT-TYPE
        SYNTAX      Counter64
        MAX-ACCESS  read-only
        STATUS      current
        DESCRIPTION
                    "MKA Global SA Statistics, SAKs Responses Received."

        ::= { agentMACsecMkaGlobalStatisticsGroup 6 }

    agentMACsecMkaPduValidatedandRxGlobal    OBJECT-TYPE
        SYNTAX      Counter64
        MAX-ACCESS  read-only
        STATUS      current
        DESCRIPTION
                    "MKA Global MKPDUs Statistics, MKPDUs Validated and Rx."

        ::= { agentMACsecMkaGlobalStatisticsGroup 7 }

    agentMACsecMkaMkpduTransmittedGlobal   OBJECT-TYPE
        SYNTAX      Counter64
        MAX-ACCESS  read-only
        STATUS      current
        DESCRIPTION
                    "MKA Global MKPDUs Statistics, MKPDUs Transmitted."

        ::= { agentMACsecMkaGlobalStatisticsGroup 8 }

    agentMACseMkaDistributedSakGlobal   OBJECT-TYPE
        SYNTAX      Counter64
        MAX-ACCESS  read-only
        STATUS      current
        DESCRIPTION
                    "MKA Global MKPDUs Statistics, Distributed SAK."

        ::= { agentMACsecMkaGlobalStatisticsGroup 9 }

    agentMACsecMkaSakGenerationFailures   OBJECT-TYPE
        SYNTAX      Counter64
        MAX-ACCESS  read-only
        STATUS      current
        DESCRIPTION
                    "MKA Global Error Statistics, Sak Generation Failures."

        ::= { agentMACsecMkaGlobalStatisticsGroup 10 }

    agentMACsecMkaSakEncryptionFailures   OBJECT-TYPE
        SYNTAX      Counter64
        MAX-ACCESS  read-only
        STATUS      current
        DESCRIPTION
                    "MKA Global Error Statistics, Sak Encryption Failures."

        ::= { agentMACsecMkaGlobalStatisticsGroup 11 }

    agentMACsecMkaSakDecryptionFailures   OBJECT-TYPE
        SYNTAX      Counter64
        MAX-ACCESS  read-only
        STATUS      current
        DESCRIPTION
                    "MKA Global Error Statistics, Sak Decryption Failures."

        ::= { agentMACsecMkaGlobalStatisticsGroup 12 }

    agentMACsecMkaIckDerivationFailures   OBJECT-TYPE
        SYNTAX      Counter64
        MAX-ACCESS  read-only
        STATUS      current
        DESCRIPTION
                    "MKA Global Error Statistics, Ick Derivation Failures."

        ::= { agentMACsecMkaGlobalStatisticsGroup 13 }

    agentMACsecMkaKekDerivationFailures   OBJECT-TYPE
        SYNTAX      Counter64
        MAX-ACCESS  read-only
        STATUS      current
        DESCRIPTION
                    "MKA Global Error Statistics, KEK Derivation Failures."

        ::= { agentMACsecMkaGlobalStatisticsGroup 14 }

    agentMACsecMkaInvalidPeerCapability   OBJECT-TYPE
        SYNTAX      Counter64
        MAX-ACCESS  read-only
        STATUS      current
        DESCRIPTION
                    "MKA Global Error Statistics, Invalid Peer MACsec Capability."

        ::= { agentMACsecMkaGlobalStatisticsGroup 15 }

    agentMACsecMkaRxScCreationFailures   OBJECT-TYPE
        SYNTAX      Counter64
        MAX-ACCESS  read-only
        STATUS      current
        DESCRIPTION
                    "MKA Global Error Statistics, Rx SC Creation Failures."

        ::= { agentMACsecMkaGlobalStatisticsGroup 16 }

    agentMACsecMkaTxScCreationFailures   OBJECT-TYPE
        SYNTAX      Counter64
        MAX-ACCESS  read-only
        STATUS      current
        DESCRIPTION
                    "MKA Global Error Statistics, Tx SC Creation Failures."

        ::= { agentMACsecMkaGlobalStatisticsGroup 17 }

    agentMACsecMkaRxSaInstallationFailures   OBJECT-TYPE
        SYNTAX      Counter64
        MAX-ACCESS  read-only
        STATUS      current
        DESCRIPTION
                    "MKA Global Error Statistics, Rx SA Installation Failures."

        ::= { agentMACsecMkaGlobalStatisticsGroup 18 }

    agentMACsecMkaTxSaInstallationFailures   OBJECT-TYPE
        SYNTAX      Counter64
        MAX-ACCESS  read-only
        STATUS      current
        DESCRIPTION
                    "MKA Global Error Statistics, Tx SA Installation Failures."

        ::= { agentMACsecMkaGlobalStatisticsGroup 19 }

    agentMACsecMkaPduTxFailures   OBJECT-TYPE
        SYNTAX      Counter64
        MAX-ACCESS  read-only
        STATUS      current
        DESCRIPTION
                    "MKA Global Error Statistics, Mka Pdu Tx Failures."

        ::= { agentMACsecMkaGlobalStatisticsGroup 20 }

    agentMACsecMkaPduRxValidationFailures   OBJECT-TYPE
        SYNTAX      Counter64
        MAX-ACCESS  read-only
        STATUS      current
        DESCRIPTION
                    "MKA Global Error Statistics, MKAPDU Rx Validation Failures."

        ::= { agentMACsecMkaGlobalStatisticsGroup 21 }

    agentMACsecMkaPduRxPeerMnValidationFailures   OBJECT-TYPE
        SYNTAX      Counter64
        MAX-ACCESS  read-only
        STATUS      current
        DESCRIPTION
                    "MKA Global Error Statistics, MKAPDU Rx Peer MN Validation Failures."

        ::= { agentMACsecMkaGlobalStatisticsGroup 22 }

    --**************************************************************************************
    --agentMACsecGlobalConfigGroup
    --**************************************************************************************

    agentMACsecGlobalConfigGroup                 OBJECT IDENTIFIER ::= { fastPathMACsec 7 }

    agentMACsecDefaultSecureAnnouncements    OBJECT-TYPE
         SYNTAX      INTEGER {
                        enable(1),
                        disable(2)
                    }
         MAX-ACCESS  read-write
         STATUS      current
         DESCRIPTION
                     "Enable or Disable default secure announcements across all Mka Policies."

         ::= { agentMACsecGlobalConfigGroup 1 }
END

DNOS-SMTP-MIB DEFINITIONS ::= BEGIN

-- Broadcom FastPath NTP MIB
-- Copyright 2022 Broadcom.
-- This SNMP Management Information Specification
-- embodies Broadcom's confidential and proprietary
-- intellectual property.  Broadcom retains all title
-- and ownership in the Specification including any revisions.

-- This Specification is supplied "AS IS", Broadcom 
-- makes no warranty, either expressed or implied,
-- as to the use, operation, condition, or performance of the
-- Specification.

    IMPORTS
        MODULE-IDENTITY, OBJECT-TYPE, Integer32, Counter32, Gauge32,
        Unsigned32, NOTIFICATION-TYPE                 FROM SNMPv2-SMI
        TEXTUAL-CONVENTION, RowStatus                 FROM SNMPv2-TC
        dnOS                                      FROM DELL-REF-MIB
        InetAddress, InetAddressType, InetPortNumber  FROM INET-ADDRESS-MIB
        agentInventoryComponentIndex                  FROM DNOS-INVENTORY-MIB
        DisplayString                                 FROM RFC1213-MIB;

    fastPathSmtp MODULE-IDENTITY
        LAST-UPDATED "202202250000Z" -- 25 Feb 2022 12:00:00 GMT
        ORGANIZATION "Dell"
        CONTACT-INFO ""
        DESCRIPTION
            "This MIB provides objects to configure and display SMTP server information
            on this system."

        -- Revision history.
        REVISION
            "202202250000Z" -- 25 Feb 2022 12:00:00 GMT 
        DESCRIPTION
            "Initial version."

        ::= { dnOS 169 }

    --**************************************************************************************
    -- agentSmtpConfigGroup
    --
    --**************************************************************************************

    agentSmtpConfigGroup                          OBJECT IDENTIFIER ::= { fastPathSmtp 1 }

    --**************************************************************************************
    -- agentSmtpServerConfigGroup
    --
    --**************************************************************************************

    agentSmtpServerConfigGroup                  OBJECT IDENTIFIER ::= { agentSmtpConfigGroup 1 }

    agentSmtpServerTable OBJECT-TYPE
        SYNTAX     SEQUENCE OF AgentSmtpServerEntry
        MAX-ACCESS not-accessible
        STATUS     current
        DESCRIPTION
                    "The (conceptual) table listing the mail servers"
            ::= { agentSmtpServerConfigGroup 1 }

    agentSmtpServerEntry OBJECT-TYPE
        SYNTAX     AgentSmtpServerEntry
        MAX-ACCESS not-accessible
        STATUS     current
        DESCRIPTION
                    "An entry (conceptual row) in the agentSmtpServerTable. This entry shows the configuration for mail server."
            INDEX      { agentSmtpServerAddrType, agentSmtpServerAddr }
        ::= { agentSmtpServerTable 1 }

    AgentSmtpServerEntry ::= SEQUENCE {
        agentSmtpServerAddrType       InetAddressType,
        agentSmtpServerAddr           InetAddress,
        agentSmtpServerPort           InetPortNumber,
        agentSmtpServerSecurity       INTEGER,
        agentSmtpServerloginID        DisplayString,
        agentSmtpServerPassword       DisplayString,
        agentSmtpServerEntryStatus    RowStatus

        }

    agentSmtpServerAddrType OBJECT-TYPE
        SYNTAX      InetAddressType
        MAX-ACCESS  not-accessible
        STATUS      current
        DESCRIPTION
            "SMTP Address type"
        ::= { agentSmtpServerEntry 1 }

    agentSmtpServerAddr OBJECT-TYPE
        SYNTAX      InetAddress
        MAX-ACCESS  not-accessible
        STATUS      current
        DESCRIPTION
            "SMTP server Address"
        ::= { agentSmtpServerEntry 2 }

    agentSmtpServerPort OBJECT-TYPE
        SYNTAX     InetPortNumber
        MAX-ACCESS  read-write
        STATUS      current
        DESCRIPTION
            "SMTP Port number. When this object is set to 0, it resets to 
             factory default port number."
        ::= { agentSmtpServerEntry 3 }

    agentSmtpServerSecurity OBJECT-TYPE
        SYNTAX      INTEGER { none(1), tlsv1(2) }
        MAX-ACCESS  read-write
        STATUS      current
        DESCRIPTION
            "This is the authentication mechanism that should be used."
        ::= { agentSmtpServerEntry 4 }

    agentSmtpServerloginID OBJECT-TYPE
        SYNTAX      DisplayString
        MAX-ACCESS  read-write
        STATUS      current
        DESCRIPTION
            "This user id is used while the switch/router is being authenticated by the SMTP server.The user ID
                     should be minimum of 1 charcter to maximum of 16 characters."
        ::= { agentSmtpServerEntry 5 }

    agentSmtpServerPassword OBJECT-TYPE
        SYNTAX      DisplayString
        MAX-ACCESS read-write
        STATUS      current
        DESCRIPTION
            "This password is used while the switch/router is being authenticated by the SMTP server.The password
                should be minimum of 1 character to maximum of 16 characters."
        ::= { agentSmtpServerEntry 6 }

    agentSmtpServerEntryStatus OBJECT-TYPE
        SYNTAX      RowStatus
        MAX-ACCESS  read-create
        STATUS      current
        DESCRIPTION
                    "SMTP server entry row status.
                     Supported values:
                     active(1)      - valid entry
                     createAndGo(4) - used to create a new entry
                     destroy(6)     - removes the entry"
        ::= { agentSmtpServerEntry 7 }

END

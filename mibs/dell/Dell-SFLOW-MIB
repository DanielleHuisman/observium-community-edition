Dell-SFLOW-MIB DEFINITIONS ::= BEGIN

--             rlsFlow statistics MIBs definition
-- Version:    7.50
-- Date:       27 Oct 2009
--             Initial definitions

IMPORTS
    MODULE-IDENTITY, OBJECT-TYPE                FROM SNMPv2-SMI
    TEXTUAL-CONVENTION                          FROM SNMPv2-TC
    rnd                                         FROM Dell-MIB
    Counter                                     FROM RFC1155-SMI
    ifIndex                                     FROM IF-MIB;

rlsFlowMib MODULE-IDENTITY
        LAST-UPDATED "200910270000Z"
        ORGANIZATION "Dell"
        CONTACT-INFO
                "www.dell.com"
        DESCRIPTION
                "sFlow statistics MIBs."
        REVISION "200910270000Z"
        DESCRIPTION
                "Initial revision."
    ::= { rnd 147 }

--
-- rlsFlow statistics MIB
--

    rlsFlowStatisticsTable OBJECT-TYPE
            SYNTAX      SEQUENCE OF RlsFlowStatisticsEntry
            MAX-ACCESS  read-only
            STATUS      current
            DESCRIPTION
                    " sFlow statistics MIB Table "
        ::=  { rlsFlowMib 1 }

    rlsFlowStatisticsEntry OBJECT-TYPE
            SYNTAX      RlsFlowStatisticsEntry
            MAX-ACCESS  read-only
            STATUS      current
            DESCRIPTION
                    " Row definition for sFlow statistic table. "
            INDEX { rlsFlowDataSource }
        ::= { rlsFlowStatisticsTable 1 }

    RlsFlowStatisticsEntry::= SEQUENCE {
            rlsFlowDataSource                       OBJECT IDENTIFIER,
            rlsFlowStatisticsSampledPackets         Counter,
            rlsFlowStatisticsDatagramSent           Counter,
            rlsFlowStatisticsAction                 INTEGER
    }

    rlsFlowDataSource OBJECT-TYPE
         SYNTAX      OBJECT IDENTIFIER
         MAX-ACCESS  read-only
         STATUS      current
         DESCRIPTION
                    " Identifies the source of the data for the sFlow sampler "
         ::= { rlsFlowStatisticsEntry 1 }

    rlsFlowStatisticsSampledPackets OBJECT-TYPE
            SYNTAX      Counter
            MAX-ACCESS  read-only
            STATUS      current
            DESCRIPTION
                    " Counts the number of packets sampled by sFlow
                      per interface "
        ::=  { rlsFlowStatisticsEntry 2 }

    rlsFlowStatisticsDatagramSent OBJECT-TYPE
            SYNTAX      Counter
            MAX-ACCESS  read-only
            STATUS      current
            DESCRIPTION
                    " Counts the total number of datagrams sent
                      to sFlow collector per interface "
        ::=  { rlsFlowStatisticsEntry 3 }

    rlsFlowStatisticsAction OBJECT-TYPE
            SYNTAX  INTEGER {
                    noaction(1),
                    clear(2)
            }
            MAX-ACCESS  read-write
            STATUS      current
            DESCRIPTION
                    " Used to clear sFlow statistics "
        ::=  { rlsFlowStatisticsEntry 4 }

--
-- clear all sFlow statistics MIB
--

    rlsFlowStatisticsReset OBJECT-TYPE
            SYNTAX  INTEGER {
                    noaction(1),
                    clear(2)
            }
            MAX-ACCESS  read-write
            STATUS      current
            DESCRIPTION
                "Setting this MIB object will clear all sFlow statistics counters."
            DEFVAL { 1 }
        ::= { rlsFlowMib 2 }

END

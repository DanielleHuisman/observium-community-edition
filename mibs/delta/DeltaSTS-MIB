-- DeltaSTS-MIB { iso(1) org(3) dod(6) internet(1) private(4) enterprises(1) delta(2254) ups(2) sts(80) }
-- last modified: 05/13/2014 AFu Lai
DeltaSTS-MIB DEFINITIONS ::= BEGIN

IMPORTS
	enterprises
		FROM RFC1155-SMI
	DisplayString
		FROM RFC1213-MIB
	OBJECT-TYPE
		FROM RFC-1212
	TRAP-TYPE
		FROM RFC-1215;
--
delta				OBJECT IDENTIFIER ::=  { enterprises 2254 }
ups					OBJECT IDENTIFIER ::=  { delta 2 }
sts				    OBJECT IDENTIFIER ::=  { ups 80 }

stsAgent			OBJECT IDENTIFIER ::=  { sts 1 }
stsIdent			OBJECT IDENTIFIER ::=  { sts 2 }
stsMeasure			OBJECT IDENTIFIER ::=  { sts 3 }
stsStatus			OBJECT IDENTIFIER ::=  { sts 4 }
stsLog				OBJECT IDENTIFIER ::=  { sts 5 }
stsConfig			OBJECT IDENTIFIER ::=  { sts 6 }
stsUpgrade			OBJECT IDENTIFIER ::=  { sts 7 }
stsTraps			OBJECT IDENTIFIER ::=  { sts 20 }

--
-- Agent group
stsAgentManufacturer OBJECT-TYPE
	SYNTAX		DisplayString (SIZE(0..16))
	ACCESS		read-only
	STATUS		mandatory
	DESCRIPTION
		"The manufacturer name of SNMP-Agent."
	::= { stsAgent 1 }

stsAgentVersion OBJECT-TYPE
	SYNTAX		DisplayString (SIZE(0..20))
	ACCESS		read-only
	STATUS		mandatory
	DESCRIPTION
		"The firmware version of SNMP-Agent."
	::= { stsAgent 2 }

stsAgentModbus	OBJECT IDENTIFIER ::=  { stsAgent 3 }

--
-- Identification group
stsIdentModel	OBJECT-TYPE
	SYNTAX		DisplayString (SIZE(0..16))
	ACCESS		read-only
	STATUS		mandatory
	DESCRIPTION
		"Device model name."
	::= { stsIdent 1 }

stsIdentFWVersion OBJECT-TYPE
	SYNTAX		DisplayString (SIZE(0..16))
	ACCESS		read-only
	STATUS		mandatory
	DESCRIPTION
		"Device F/W version."
	::= { stsIdent 2 }

stsIdentRelease OBJECT-TYPE
	SYNTAX		DisplayString (SIZE(0..16))
	ACCESS		read-only
	STATUS		mandatory
	DESCRIPTION
		"The released date."
	::= { stsIdent 3 }

stsIdentSerialNumber OBJECT-TYPE
	SYNTAX		DisplayString (SIZE(0..20))
	ACCESS		read-only
	STATUS		mandatory
	DESCRIPTION
		"Device serial number"
	::= { stsIdent 4 }

stsIdentIDCodes OBJECT-TYPE
	SYNTAX		DisplayString (SIZE(0..20))
	ACCESS		read-write
	STATUS		mandatory
	DESCRIPTION
		"Device ID codes"
	::= { stsIdent 5 }

--
-- Identification / Modbus group
stsAgentModbusLink OBJECT-TYPE
	SYNTAX		INTEGER {
		linked(1),
		un-linked(2)
	}
	ACCESS		read-only
	STATUS		mandatory
	DESCRIPTION
		"The link status of ModBUS communication to STS device."
	::= { stsAgentModbus 1 }

--
-- Mesurement group
stsInputTable OBJECT-TYPE
	SYNTAX		SEQUENCE OF STSInputEntry
	ACCESS  	not-accessible
	STATUS		mandatory
	DESCRIPTION
		"The table of input information."
	::= { stsMeasure 1 }

stsOutput			OBJECT IDENTIFIER ::=  { stsMeasure 2 }

stsMeasureTemperatureC OBJECT-TYPE
	SYNTAX		INTEGER
	UNITS      "1 Celsius"
	ACCESS		read-only
	STATUS		mandatory
	DESCRIPTION
		"The internal temperature (in Celsius)."
	::= { stsMeasure 3 }

stsMeasureTemperatureF OBJECT-TYPE
	SYNTAX		INTEGER
	UNITS      "1 Fahrenheit"
	ACCESS		read-only
	STATUS		mandatory
	DESCRIPTION
		"The internal temperature (in Fahrenheit)."
	::= { stsMeasure 4 }

stsMessureRunTime OBJECT-TYPE
	SYNTAX		INTEGER
	UNITS      "1 second"
	ACCESS		read-only
	STATUS		mandatory
	DESCRIPTION
		"The STS run time."
	::= { stsMeasure 5 }

stsMessureTransferedTimes OBJECT-TYPE
	SYNTAX		INTEGER
	ACCESS		read-only
	STATUS		mandatory
	DESCRIPTION
		"The transfered times."
	::= { stsMeasure 6 }

stsMessureOperationMode OBJECT-TYPE
	SYNTAX		INTEGER {
		initialization(1),
		diagnosis(2),
		off(3),
		source-1(4),
		source-2(5),
		safe(6),
		fault(7)
	}
	ACCESS		read-only
	STATUS		mandatory
	DESCRIPTION
		"The operation mode."
	::= { stsMeasure 7 }

--
-- Mesurement / Input group
stsInputEntry OBJECT-TYPE
	SYNTAX		STSInputEntry
	ACCESS  	not-accessible
	STATUS		mandatory
	DESCRIPTION
		"The input information of each source input:
		<node>.1   source-1
		<node>.2   source-2"
	INDEX { stsInputIndex }
	::= { stsInputTable 1 }

STSInputEntry ::= SEQUENCE {
	stsInputIndex		INTEGER,
	stsInputVoltage		INTEGER,
	stsInputFrequency	INTEGER
}

stsInputIndex OBJECT-TYPE
	SYNTAX		INTEGER {
		source-1(1),
		source-2(2)
	}
	ACCESS		read-only
	STATUS		mandatory
	DESCRIPTION
		"Index to input."
	::= { stsInputEntry 1 }

stsInputVoltage OBJECT-TYPE
	SYNTAX		INTEGER
	UNITS      "0.1 V"
	ACCESS		read-only
	STATUS		mandatory
	DESCRIPTION
		"The input voltage in front of relay."
	::= { stsInputEntry 2 }

stsInputFrequency OBJECT-TYPE
	SYNTAX		INTEGER
	UNITS      "0.1 Hz"
	ACCESS		read-only
	STATUS		mandatory
	DESCRIPTION
		"The input frequency."
	::= { stsInputEntry 3 }

--
-- Mesurement / Output group
stsOutputVoltage OBJECT-TYPE
	SYNTAX		INTEGER
	UNITS		"0.1 V"
	ACCESS		read-only
	STATUS		mandatory
	DESCRIPTION
		"The output voltage."
	::= { stsOutput 1 }

stsOutputCurrent OBJECT-TYPE
	SYNTAX		INTEGER
	UNITS		"0.1 A"
	ACCESS		read-only
	STATUS		mandatory
	DESCRIPTION
		"The output current."
	::= { stsOutput 2 }

--
-- Status group
stsInputFlowIndicator OBJECT-TYPE
	SYNTAX		INTEGER
	ACCESS		read-only
	STATUS		mandatory
	DESCRIPTION
		"The input flow indicator.
		[7:0]	source-1 (low byte)
		[15:8]	source-2 (high byte)
		
		bit# --> stsInputFlowTable.1.(#+2).x
		
		Example:
		bit1 of low byte --> stsInputFlowTable.1.3.1
		bit1 of high byte --> stsInputFlowTable.1.3.2"

	::= { stsStatus 1 }

stsInputFlowTable OBJECT-TYPE
	SYNTAX		SEQUENCE OF STSInputFlowEntry
	ACCESS		not-accessible
	STATUS		mandatory
	DESCRIPTION
		"The table of input flow status."
	::= { stsStatus 2 }

stsInputFailureIndicator OBJECT-TYPE
	SYNTAX		INTEGER
	ACCESS		read-only
	STATUS		mandatory
	DESCRIPTION
		"The input failure indicator.
		[15:0]	source-1 (low word)
		[31:16]	source-2 (high word)
		
		bit# --> stsInputFailureTable.1.(#+2).x
		
		Example:
		bit0 of low word --> stsInputFailureTable.1.2.1
		bit0 of high word --> stsInputFailureTable.1.2.2"

	::= { stsStatus 3 }

stsInputFailureTable OBJECT-TYPE
	SYNTAX		SEQUENCE OF STSInputFailureEntry
	ACCESS		not-accessible
	STATUS		mandatory
	DESCRIPTION
		"The table of input status."
	::= { stsStatus 4 }

stsFailureIndicator OBJECT-TYPE
	SYNTAX		INTEGER
	ACCESS		read-only
	STATUS		mandatory
	DESCRIPTION
		"The failure indicator.
		bit# --> stsFailure.(#+1)
		
		Example:
		bit2 --> stsFailure.3 (stsFailureOutputOC)"
	::= { stsStatus 5 }

stsFailure			OBJECT IDENTIFIER ::=  { stsStatus 6 }

--
-- Status / Input Flow group
stsInputFlowEntry OBJECT-TYPE
	SYNTAX		STSInputFlowEntry
	ACCESS  	not-accessible
	STATUS		mandatory
	DESCRIPTION
		"The input flow status:
		<node>.1   source-1
		<node>.2   source-2"
	INDEX { stsInputFlowIndex }
	::= { stsInputFlowTable 1 }

STSInputFlowEntry ::= SEQUENCE {
	stsInputFlowIndex			INTEGER,
	stsInputFlowRelay			INTEGER,
	stsInputFlowSCR				INTEGER,
	stsInputFlowParallelRelay	INTEGER
}

stsInputFlowIndex OBJECT-TYPE
	SYNTAX		INTEGER {
		source-1(1),
		source-2(2)
	}
	ACCESS		read-only
	STATUS		mandatory
	DESCRIPTION
		"Index of input entry."
	::= { stsInputFlowEntry 1 }

stsInputFlowRelay OBJECT-TYPE
	SYNTAX		INTEGER {
		on(1),
		off(2)
	}
	ACCESS		read-only
	STATUS		mandatory
	DESCRIPTION
		"The status of input relay."
	::= { stsInputFlowEntry 2 }

stsInputFlowSCR OBJECT-TYPE
	SYNTAX		INTEGER {
		on(1),
		off(2)
	}
	ACCESS		read-only
	STATUS		mandatory
	DESCRIPTION
		"The status of input SCR."
	::= { stsInputFlowEntry 3 }

stsInputFlowParallelRelay OBJECT-TYPE
	SYNTAX		INTEGER {
		on(1),
		off(2)
	}
	ACCESS		read-only
	STATUS		mandatory
	DESCRIPTION
		"The status of input parallel relay."
	::= { stsInputFlowEntry 4 }

--
-- Status / Input Failure group
stsInputFailureEntry OBJECT-TYPE
	SYNTAX		STSInputFailureEntry
	ACCESS  	not-accessible
	STATUS		mandatory
	DESCRIPTION
		"The status of input failure:

		<node>.1	source-1
		<node>.2	source-2"
	INDEX { stsInputFailureIndex }
	::= { stsInputFailureTable 1 }

STSInputFailureEntry ::= SEQUENCE {
	stsInputFailureIndex		INTEGER,
	stsInputFailureRelayOpen	INTEGER,
	stsInputFailureRelayShort	INTEGER,
	stsInputFailureSCROpen		INTEGER,
	stsInputFailureSCRShort		INTEGER,
	stsInputFailureSCRThermal	INTEGER,
	stsInputFailureAuxPower		INTEGER,
	stsInputFailureDrop			INTEGER,
	stsInputFailureBrownout		INTEGER,
	stsInputFailureFrequency	INTEGER,
	stsInputFailureNotOperable	INTEGER
}

stsInputFailureIndex OBJECT-TYPE
	SYNTAX		INTEGER {
		source-1(1),
		source-2(2)
	}
	ACCESS		read-only
	STATUS		mandatory
	DESCRIPTION
		"Index of entry."
	::= { stsInputFailureEntry 1 }

stsInputFailureRelayOpen OBJECT-TYPE
	SYNTAX		INTEGER {
		abnormal(1),
		normal(2)
	}
	ACCESS		read-only
	STATUS		mandatory
	DESCRIPTION
		"The status of input relay is OPEN."
	::= { stsInputFailureEntry 2 }

stsInputFailureRelayShort OBJECT-TYPE
	SYNTAX		INTEGER {
		abnormal(1),
		normal(2)
	}
	ACCESS		read-only
	STATUS		mandatory
	DESCRIPTION
		"The status of input relay is SHORT."
	::= { stsInputFailureEntry 3 }

stsInputFailureSCROpen OBJECT-TYPE
	SYNTAX		INTEGER {
		abnormal(1),
		normal(2)
	}
	ACCESS		read-only
	STATUS		mandatory
	DESCRIPTION
		"The status of input SCR is OPEN."
	::= { stsInputFailureEntry 4 }

stsInputFailureSCRShort OBJECT-TYPE
	SYNTAX		INTEGER {
		abnormal(1),
		normal(2)
	}
	ACCESS		read-only
	STATUS		mandatory
	DESCRIPTION
		"The status of input SCR is SHORT."
	::= { stsInputFailureEntry 5 }

stsInputFailureSCRThermal OBJECT-TYPE
	SYNTAX		INTEGER {
		abnormal(1),
		normal(2)
	}
	ACCESS		read-only
	STATUS		mandatory
	DESCRIPTION
		"The status of input SCR thermal is over."
	::= { stsInputFailureEntry 6 }

stsInputFailureAuxPower OBJECT-TYPE
	SYNTAX		INTEGER {
		abnormal(1),
		normal(2)
	}
	ACCESS		read-only
	STATUS		mandatory
	DESCRIPTION
		"Internal axuiliary power is reported as failure."
	::= { stsInputFailureEntry 7 }

stsInputFailureDrop OBJECT-TYPE
	SYNTAX		INTEGER {
		abnormal(1),
		normal(2)
	}
	ACCESS		read-only
	STATUS		mandatory
	DESCRIPTION
		"A voltage drop was detected."
	::= { stsInputFailureEntry 8 }

stsInputFailureBrownout OBJECT-TYPE
	SYNTAX		INTEGER {
		abnormal(1),
		normal(2)
	}
	ACCESS		read-only
	STATUS		mandatory
	DESCRIPTION
		"A voltage brownout was detected."
	::= { stsInputFailureEntry 9 }

stsInputFailureFrequency OBJECT-TYPE
	SYNTAX		INTEGER {
		abnormal(1),
		normal(2)
	}
	ACCESS		read-only
	STATUS		mandatory
	DESCRIPTION
		"The input frequency is out of range."
	::= { stsInputFailureEntry 10 }

stsInputFailureNotOperable OBJECT-TYPE
	SYNTAX		INTEGER {
		abnormal(1),
		normal(2)
	}
	ACCESS		read-only
	STATUS		mandatory
	DESCRIPTION
		"The input is not operable."
	::= { stsInputFailureEntry 11 }

--
-- Status / Failure group
stsFailureSwitchFault OBJECT-TYPE
	SYNTAX		INTEGER {
		abnormal(1),
		normal(2)
	}
	ACCESS		read-only
	STATUS		mandatory
	DESCRIPTION
		"The relay, SCR and thermal switch fail."
	::= { stsFailure 1 }

stsFailureNoOutput OBJECT-TYPE
	SYNTAX		INTEGER {
		abnormal(1),
		normal(2)
	}
	ACCESS		read-only
	STATUS		mandatory
	DESCRIPTION
		"There is no output."
	::= { stsFailure 2 }

stsFailureOutputOC OBJECT-TYPE
	SYNTAX		INTEGER {
		abnormal(1),
		normal(2)
	}
	ACCESS		read-only
	STATUS		mandatory
	DESCRIPTION
		"The output current is over."
	::= { stsFailure 3 }

stsFailureOverTemperature OBJECT-TYPE
	SYNTAX		INTEGER {
		abnormal(1),
		normal(2)
	}
	ACCESS		read-only
	STATUS		mandatory
	DESCRIPTION
		"The ambient temperature is over."
	::= { stsFailure 4 }

--
-- Event log Group
stsLogNum OBJECT-TYPE
	SYNTAX		INTEGER
	ACCESS		read-only
	STATUS		mandatory
	DESCRIPTION
		"The number of event logs."
	::= { stsLog 1 }

stsLogTable OBJECT-TYPE
	SYNTAX		SEQUENCE OF STSLogEntry
	ACCESS  	not-accessible
	STATUS		mandatory
	DESCRIPTION
		"The table of event logs."
	::= { stsLog 2 }

stsLogEntry	OBJECT-TYPE
	SYNTAX		STSLogEntry
	ACCESS  	not-accessible
	STATUS		mandatory
	DESCRIPTION
		"The recorded event log"
	INDEX { stsLogIndex }
	::= { stsLogTable 1 }

STSLogEntry ::= SEQUENCE {
	stsLogIndex		INTEGER,
	stsLogTime		TimeTicks,
	stsLogCode		INTEGER,
	stsLogTimeText	DisplayString
}

stsLogIndex OBJECT-TYPE
	SYNTAX		INTEGER (1..10)
	ACCESS		read-only
	STATUS		mandatory
	DESCRIPTION
		"Index to event log."
	::= { stsLogEntry 1 }

stsLogTime OBJECT-TYPE
	SYNTAX		TimeTicks
	UNITS      "1 Second"
	ACCESS		read-only
	STATUS		mandatory
	DESCRIPTION
		"The event time (since 01/01/2000 00:00:00)."
	::= { stsLogEntry 2 }

stsLogCode OBJECT-TYPE
	SYNTAX		INTEGER
	ACCESS		read-only
	STATUS		mandatory
	DESCRIPTION
		"The event code."
	::= { stsLogEntry 3 }

stsLogTimeText OBJECT-TYPE
	SYNTAX		DisplayString (SIZE(0..20))
	ACCESS		read-only
	STATUS		mandatory
	DESCRIPTION
		"The event time with form: hh:mm:ss MM/DD/YYYY."
	::= { stsLogEntry 4 }

--
-- Configuration group
stsConfigTime		OBJECT IDENTIFIER ::=  { stsConfig 1 }

stsConfigInputTable OBJECT-TYPE
	SYNTAX		SEQUENCE OF STSConfigInputEntry
	ACCESS  	not-accessible
	STATUS		mandatory
	DESCRIPTION
		"The table of input configuration."
	::= { stsConfig 2 }

stsConfigInputVoltageRating OBJECT-TYPE
	SYNTAX		INTEGER
	UNITS      "0.1 V"
	ACCESS    read-only
	STATUS		mandatory
	DESCRIPTION
		"The input voltage rating."
	::= { stsConfig 3 }

stsConfigRandomTime OBJECT-TYPE
	SYNTAX		INTEGER
	UNITS		"0.1 Second"
	ACCESS		read-only
	STATUS		mandatory
	DESCRIPTION
		"Delay time is calculated by device serial numbers."
	::= { stsConfig 4 }

stsConfigPreferred OBJECT-TYPE
	SYNTAX		INTEGER {
		source-1(1),
		source-2(2)
	}
	ACCESS    read-write
	STATUS		mandatory
	DESCRIPTION
		"The prefered source."
	::= { stsConfig 5 }

stsConfigSensitivity OBJECT-TYPE
	SYNTAX		INTEGER {
		high(1),
		low(2)
	}
	ACCESS    read-write
	STATUS		mandatory
	DESCRIPTION
		"The AC Blackout Sensitivity."
	::= { stsConfig 6 }

stsConfigTest OBJECT-TYPE
	SYNTAX		INTEGER {
		active(1),
		inactive(2)
	}
	ACCESS    read-write
	STATUS		mandatory
	DESCRIPTION
		"The activity of source test."
	::= { stsConfig 7 }

--
-- Configuration / Time group
stsConfigTimeRTC OBJECT-TYPE
	SYNTAX		INTEGER
	ACCESS		read-write
	STATUS		mandatory
	DESCRIPTION
		"The RTC timer value (since 1/1/2000 00:00:00)."
	::= { stsConfigTime 1 }

stsConfigTimeTextDate OBJECT-TYPE
	SYNTAX		DisplayString (SIZE(0..10))
	ACCESS		read-write
	STATUS		mandatory
	DESCRIPTION
		"The present date in MM/DD/YYYY text format."
	::= { stsConfigTime 2 }

stsConfigTimeTextTime OBJECT-TYPE
	SYNTAX		DisplayString (SIZE(0..8))
	ACCESS		read-write
	STATUS		mandatory
	DESCRIPTION
		"The present time in hh:mm:ss text format."
	::= { stsConfigTime 3 }

--
-- Configuration / Input
stsConfigInputEntry	OBJECT-TYPE
	SYNTAX		STSConfigInputEntry
	ACCESS  	not-accessible
	STATUS		mandatory
	DESCRIPTION
		"Input configuration entry"
	INDEX { stsConfigInputIndex }
	::= { stsConfigInputTable 1 }

STSConfigInputEntry ::= SEQUENCE {
	stsConfigInputIndex		INTEGER,
	stsConfigInputTrip		INTEGER,
	stsConfigInputBrownoutLow	INTEGER,
	stsConfigInputBrownoutHigh	INTEGER,
	stsConfigInputRecover	INTEGER,
	stsConfigInputMaxVoltage	INTEGER,
	stsConfigInputMaxTime	INTEGER,
	stsConfigInputDelayTime		INTEGER
}

stsConfigInputIndex OBJECT-TYPE
	SYNTAX		INTEGER (1..2)
	ACCESS		read-write
	STATUS		mandatory
	DESCRIPTION
		"Index to input configuration."
	::= { stsConfigInputEntry 1 }

stsConfigInputTrip OBJECT-TYPE
	SYNTAX		INTEGER
	UNITS      "0.1 V"
	ACCESS		read-write
	STATUS		mandatory
	DESCRIPTION
		"Setting of input trip voltage."
	::= { stsConfigInputEntry 2 }

stsConfigInputBrownoutLow OBJECT-TYPE
	SYNTAX		INTEGER
	UNITS      "0.1 V"
	ACCESS    read-write
	STATUS		mandatory
	DESCRIPTION
		"Setting of input brownout low voltage."
	::= { stsConfigInputEntry 3 }

stsConfigInputBrownoutHigh OBJECT-TYPE
	SYNTAX		INTEGER
	UNITS      "0.1 V"
	ACCESS    read-write
	STATUS		mandatory
	DESCRIPTION
		"Setting of input brownout high voltage."
	::= { stsConfigInputEntry 4 }

stsConfigInputRecover OBJECT-TYPE
	SYNTAX		INTEGER
	UNITS      "0.1 Second"
	ACCESS		read-write
	STATUS		mandatory
	DESCRIPTION
		"Setting of input recovered time."
	::= { stsConfigInputEntry 5 }

stsConfigInputMaxVoltage OBJECT-TYPE
	SYNTAX		INTEGER
	UNITS      "1 V"
	ACCESS		read-write
	STATUS		mandatory
	DESCRIPTION
		"Set the detected delta RMS voltage of fast detected AC blackout by
		the comparing cycles."
	::= { stsConfigInputEntry 6 }

stsConfigInputMaxTime OBJECT-TYPE
	SYNTAX		INTEGER
	UNITS      "0.1 Second"
	ACCESS		read-write
	STATUS		mandatory
	DESCRIPTION
		"Set the detected time of fast detected AC blackout by the
		comparing cycles."
	::= { stsConfigInputEntry 7 }

stsConfigInputDelayTime OBJECT-TYPE
	SYNTAX		INTEGER
	UNITS      "0.1 Second"
	ACCESS		read-only
	STATUS		mandatory
	DESCRIPTION
		"The delay time includes Recovered Time (stsConfigInputRecover) and
		Random Delay Time."
	::= { stsConfigInputEntry 8 }

-- Upgrade group
stsUpgradeProcess OBJECT-TYPE
	SYNTAX		INTEGER {
		idle(1),
		run(2),
		error(3)
	}
	ACCESS		read-only
	STATUS		mandatory
	DESCRIPTION
		"The status of upgrade progress."

	::= { stsUpgrade 1 }

stsUpgradeStep OBJECT-TYPE
	SYNTAX		INTEGER {
		init(1),
		fileid(2),
		auth(3),
		addr(4),
		erase(5),
		program(6),
		read(7)
	}
	ACCESS		read-only
	STATUS		mandatory
	DESCRIPTION
		"The step of STS F/W upgrade."
	::= { stsUpgrade 2 }

stsUpgradePercentage OBJECT-TYPE
	SYNTAX		INTEGER
	UNITS		"0.1%"
	ACCESS		read-only
	STATUS		mandatory
	DESCRIPTION
		"The percentage of current progress (program or read)."
	::= { stsUpgrade 3 }

--
-- Traps group
stsTrapCommLost TRAP-TYPE
	ENTERPRISE stsTraps
	DESCRIPTION
	"Communication with the STS failed."
	::= 1

stsTrapCommEstablished TRAP-TYPE
	ENTERPRISE stsTraps
	DESCRIPTION
	"Communication with the STS reestablished."
	::= 2

stsTrapConfigChange TRAP-TYPE
	ENTERPRISE stsTraps
	DESCRIPTION
	"The STS configuration has been changed."
	::= 3

stsTrapFlowChange TRAP-TYPE
	ENTERPRISE stsTraps
	DESCRIPTION
	"The Input flow status has been changed."
	::= 4

stsTrapInput1Alarm TRAP-TYPE
	ENTERPRISE stsTraps
	DESCRIPTION
	"Alarm of source-1 failure(s)."
	::= 5

stsTrapInput1AlarmRecover TRAP-TYPE
	ENTERPRISE stsTraps
	DESCRIPTION
	"Recover from source-1 failure(s)."
	::= 6

stsTrapInput2Alarm TRAP-TYPE
	ENTERPRISE stsTraps
	DESCRIPTION
	"Alarm of source-2 failure(s)."
	::= 7

stsTrapInput2AlarmRecover TRAP-TYPE
	ENTERPRISE stsTraps
	DESCRIPTION
	"Recover from source-2 failure(s)."
	::= 8

stsTrapAlarm TRAP-TYPE
	ENTERPRISE stsTraps
	DESCRIPTION
	"Alarm of failure(s)."
	::= 9

stsTrapAlarmRecover TRAP-TYPE
	ENTERPRISE stsTraps
	DESCRIPTION
	"Recover from failure(s)."
	::= 10

stsTrapUpgradeBegin TRAP-TYPE
	ENTERPRISE stsTraps
	DESCRIPTION
	"Start to upgrade STS firmware."
	::= 11

stsTrapUpgradeEnd TRAP-TYPE
	ENTERPRISE stsTraps
	DESCRIPTION
	"End of upgrade progress."
	::= 12
END

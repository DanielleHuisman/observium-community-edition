ACCELERATED-MIB DEFINITIONS ::= BEGIN

IMPORTS
		enterprises, MODULE-IDENTITY, OBJECT-TYPE,
		Integer32 							FROM SNMPv2-SMI
		MODULE-COMPLIANCE, OBJECT-GROUP		FROM SNMPv2-CONF;


acceleratedMIB MODULE-IDENTITY
	LAST-UPDATED	"202111280000Z"	-- 28 Oct 2021
	ORGANIZATION
		"Digi International, Inc."
	CONTACT-INFO
		"Digi International Tech Support

		 Phone: 877 912 3444     (US and Canada)
				+1 952 912 3456  (Worldwide)
		 EMail: <Tech.Support@digi.com>"
	DESCRIPTION
		"The Accelerated MIB for managing the Digi Accelerated Linux product range."
	REVISION		"202111280000Z"	-- 28 Oct 2021
	DESCRIPTION
		"Updated to comply with SMI-v2 syntax definitions."
	::= { accelerated 11000 }


accelerated OBJECT IDENTIFIER ::= { enterprises 40083 }

----------------------------------------------------
--
-- Modem hardware information table
--
----------------------------------------------------
modemHardwareTable OBJECT-TYPE
    SYNTAX      SEQUENCE OF ModemHardwareEntry
    MAX-ACCESS  not-accessible
    STATUS      current
    DESCRIPTION
            "A list of hardware configuration for each modem connected to the system."
    ::= { accelerated 1 }

modemHardwareEntry OBJECT-TYPE
    SYNTAX      ModemHardwareEntry
    MAX-ACCESS  not-accessible
    STATUS      current
    DESCRIPTION
            "An entry containing the hardware configuration for a particular modem."
    INDEX   { mHardwareIndex }
    ::= { modemHardwareTable 1 }

ModemHardwareEntry ::=
    SEQUENCE {
        mHardwareIndex Integer32,
		mCarrier       OCTET STRING,
		mCarrierPLMN   OCTET STRING,
		mPhone         OCTET STRING,
		mAPN           OCTET STRING,
		mProvider      OCTET STRING,
		mProviderPLMN  OCTET STRING,
		mIMEI          OCTET STRING,
		mIMSI          OCTET STRING,
		mICCID         OCTET STRING,
		mSID           OCTET STRING,
		mNID           OCTET STRING,
		mManufacturer  OCTET STRING,
		mModel         OCTET STRING,
		mSKU           OCTET STRING,
		mRevision      OCTET STRING,
		mUSBspeed      Integer32,
		mPort          OCTET STRING
    }

mHardwareIndex OBJECT-TYPE
    SYNTAX      Integer32 (0..2147483647)
    MAX-ACCESS  not-accessible
    STATUS      current
    DESCRIPTION
            "The modem index - normally indicates the SIM slot."
    ::= { modemHardwareEntry 1 }

mCarrier OBJECT-TYPE
	SYNTAX		OCTET STRING (SIZE (0..65535))
	MAX-ACCESS	read-only
	STATUS		current
	DESCRIPTION
			"The carrier for this SIM."
	::= {modemHardwareEntry 2 }

mCarrierPLMN OBJECT-TYPE
	SYNTAX		OCTET STRING (SIZE (0..65535))
	MAX-ACCESS	read-only
	STATUS		current
	DESCRIPTION
			"The carrier PLMN for this SIM."
	::= {modemHardwareEntry 3 }

mPhone OBJECT-TYPE
	SYNTAX		OCTET STRING (SIZE (0..65535))
	MAX-ACCESS	read-only
	STATUS		current
	DESCRIPTION
			"The phone number of this SIM."
	::= {modemHardwareEntry 4 }

mAPN OBJECT-TYPE
	SYNTAX		OCTET STRING (SIZE (0..65535))
	MAX-ACCESS	read-only
	STATUS		current
	DESCRIPTION
			"The APN defined for this SIM."
	::= {modemHardwareEntry 5 }

mProvider OBJECT-TYPE
	SYNTAX		OCTET STRING (SIZE (0..65535))
	MAX-ACCESS	read-only
	STATUS		current
	DESCRIPTION
			"The SIM provider."
	::= {modemHardwareEntry 6 }

mProviderPLMN OBJECT-TYPE
	SYNTAX		OCTET STRING (SIZE (0..65535))
	MAX-ACCESS	read-only
	STATUS		current
	DESCRIPTION
			"The SIM providers PLMN."
	::= {modemHardwareEntry 7 }

mIMEI OBJECT-TYPE
	SYNTAX		OCTET STRING (SIZE (0..65535))
	MAX-ACCESS	read-only
	STATUS		current
	DESCRIPTION
			"The International Mobile Equipment Identity for this device."
	::= {modemHardwareEntry 8 }

mIMSI OBJECT-TYPE
	SYNTAX		OCTET STRING (SIZE (0..65535))
	MAX-ACCESS	read-only
	STATUS		current
	DESCRIPTION
			"The International Mobile Subscriber Identity for this device."
	::= {modemHardwareEntry 9 }

mICCID OBJECT-TYPE
	SYNTAX		OCTET STRING (SIZE (0..65535))
	MAX-ACCESS	read-only
	STATUS		current
	DESCRIPTION
			"The Integrated Circuit Card ID for this SIM."
	::= {modemHardwareEntry 10 }

mSID OBJECT-TYPE
	SYNTAX		OCTET STRING (SIZE (0..65535))
	MAX-ACCESS	read-only
	STATUS		current
	DESCRIPTION
			"The System ID for this device."
	::= {modemHardwareEntry 11 }

mNID OBJECT-TYPE
	SYNTAX		OCTET STRING (SIZE (0..65535))
	MAX-ACCESS	read-only
	STATUS		current
	DESCRIPTION
			"The Network ID for this device."
	::= {modemHardwareEntry 12 }

mManufacturer OBJECT-TYPE
	SYNTAX		OCTET STRING (SIZE (0..65535))
	MAX-ACCESS	read-only
	STATUS		current
	DESCRIPTION
			"The modem manufacturer identification."
	::= {modemHardwareEntry 13 }

mModel OBJECT-TYPE
	SYNTAX		OCTET STRING (SIZE (0..65535))
	MAX-ACCESS	read-only
	STATUS		current
	DESCRIPTION
			"The modem model."
	::= {modemHardwareEntry 14 }

mSKU OBJECT-TYPE
	SYNTAX		OCTET STRING (SIZE (0..65535))
	MAX-ACCESS	read-only
	STATUS		current
	DESCRIPTION
			"The unit identifier."
	::= {modemHardwareEntry 15 }

mRevision OBJECT-TYPE
	SYNTAX		OCTET STRING (SIZE (0..65535))
	MAX-ACCESS	read-only
	STATUS		current
	DESCRIPTION
			"The modem firmware revision."
	::= {modemHardwareEntry 16 }

mUSBspeed OBJECT-TYPE
	SYNTAX		Integer32
	MAX-ACCESS	read-only
	STATUS		current
	DESCRIPTION
			"The USB interface speed (Mpbs)."
	::= {modemHardwareEntry 17 }

mPort OBJECT-TYPE
	SYNTAX		OCTET STRING (SIZE (0..65535))
	MAX-ACCESS	read-only
	STATUS		current
	DESCRIPTION
			"The current modem port."
	::= {modemHardwareEntry 18 }

----------------------------------------------------
--
-- Modem status table
--
----------------------------------------------------
modemStatusTable OBJECT-TYPE
    SYNTAX      SEQUENCE OF ModemStatusEntry
    MAX-ACCESS  not-accessible
    STATUS      current
    DESCRIPTION
            "A list of statuses for each modem connected to the system."
    ::= { accelerated 2 }

modemStatusEntry OBJECT-TYPE
    SYNTAX      ModemStatusEntry
    MAX-ACCESS  not-accessible
    STATUS      current
    DESCRIPTION
            "An entry containing the status for a particular modem."
    INDEX   { mStatusIndex }
    ::= { modemStatusTable 1 }

ModemStatusEntry ::=
    SEQUENCE {
        mStatusIndex   Integer32,
		mSim           OCTET STRING,
		mState         OCTET STRING,
        mSignal        Integer32,
		mMode          OCTET STRING,
		mCNTI          OCTET STRING,
		mBand          OCTET STRING,
		mIf            OCTET STRING,
		mRx            OCTET STRING,
		mTx            OCTET STRING,
		mRsrp          OCTET STRING,
		mRsrq          OCTET STRING,
		mSnr           OCTET STRING,
		mSinr          OCTET STRING,
		mEcio          OCTET STRING,
		mRssi          OCTET STRING,
		mBars          OCTET STRING,
		mTemp          OCTET STRING
    }

mStatusIndex OBJECT-TYPE
    SYNTAX      Integer32 (0..2147483647)
    MAX-ACCESS  not-accessible
    STATUS      current
    DESCRIPTION
            "The connected modem number."
    ::= { modemStatusEntry 1 }

mSim OBJECT-TYPE
	SYNTAX		OCTET STRING (SIZE (0..65535))
	MAX-ACCESS	read-only
	STATUS		current
	DESCRIPTION
			"The status of the current SIM."
	::= {modemStatusEntry 2 }

mState OBJECT-TYPE
	SYNTAX		OCTET STRING (SIZE (0..65535))
	MAX-ACCESS	read-only
	STATUS		current
	DESCRIPTION
			"The modem state."
	::= {modemStatusEntry 3 }

mSignal OBJECT-TYPE
	SYNTAX		Integer32
	MAX-ACCESS	read-only
	STATUS		current
	DESCRIPTION
			"The modem signal strength."
	::= {modemStatusEntry 4 }

mMode OBJECT-TYPE
	SYNTAX		OCTET STRING (SIZE (0..65535))
	MAX-ACCESS	read-only
	STATUS		current
	DESCRIPTION
			"The modem access mode."
	::= {modemStatusEntry 5 }

mCNTI OBJECT-TYPE
	SYNTAX		OCTET STRING (SIZE (0..65535))
	MAX-ACCESS	read-only
	STATUS		current
	DESCRIPTION
			"The current, available and supported network topologies."
	::= {modemStatusEntry 6 }

mBand OBJECT-TYPE
	SYNTAX		OCTET STRING (SIZE (0..65535))
	MAX-ACCESS	read-only
	STATUS		current
	DESCRIPTION
			"The band(s) currently connected."
	::= {modemStatusEntry 7 }

mIf OBJECT-TYPE
	SYNTAX		OCTET STRING (SIZE (0..65535))
	MAX-ACCESS	read-only
	STATUS		current
	DESCRIPTION
			"The modem interface."
	::= {modemStatusEntry 8 }

mRx OBJECT-TYPE
	SYNTAX		OCTET STRING (SIZE (0..65535))
	MAX-ACCESS	read-only
	STATUS		current
	DESCRIPTION
			"The number of bytes received."
	::= {modemStatusEntry 9 }

mTx OBJECT-TYPE
	SYNTAX		OCTET STRING (SIZE (0..65535))
	MAX-ACCESS	read-only
	STATUS		current
	DESCRIPTION
			"The number of bytes transmitted."
	::= {modemStatusEntry 10 }

mRsrp OBJECT-TYPE
	SYNTAX		OCTET STRING (SIZE (0..65535))
	MAX-ACCESS	read-only
	STATUS		current
	DESCRIPTION
			"The Reference Signal Received Power."
	::= {modemStatusEntry 11 }

mRsrq OBJECT-TYPE
	SYNTAX		OCTET STRING (SIZE (0..65535))
	MAX-ACCESS	read-only
	STATUS		current
	DESCRIPTION
			"The Reference Signal Received Quality."
	::= {modemStatusEntry 12 }

mSnr OBJECT-TYPE
	SYNTAX		OCTET STRING (SIZE (0..65535))
	MAX-ACCESS	read-only
	STATUS		current
	DESCRIPTION
			"The current singal-to-noise ratio."
	::= {modemStatusEntry 13 }

mSinr OBJECT-TYPE
	SYNTAX		OCTET STRING (SIZE (0..65535))
	MAX-ACCESS	read-only
	STATUS		current
	DESCRIPTION
			"The current singal-to-noise-plus-interference ratio."
	::= {modemStatusEntry 14 }

mEcio OBJECT-TYPE
	SYNTAX		OCTET STRING (SIZE (0..65535))
	MAX-ACCESS	read-only
	STATUS		current
	DESCRIPTION
			"The signal quality (EC/IO)."
	::= {modemStatusEntry 15 }

mRssi OBJECT-TYPE
	SYNTAX		OCTET STRING (SIZE (0..65535))
	MAX-ACCESS	read-only
	STATUS		current
	DESCRIPTION
			"The Received signal strength indication."
	::= {modemStatusEntry 16 }

mBars OBJECT-TYPE
	SYNTAX		OCTET STRING (SIZE (0..65535))
	MAX-ACCESS	read-only
	STATUS		current
	DESCRIPTION
			"The number of bars of reception(0-5)."
	::= {modemStatusEntry 17 }


mTemp OBJECT-TYPE
	SYNTAX		OCTET STRING (SIZE (0..65535))
	MAX-ACCESS	read-only
	STATUS		current
	DESCRIPTION
			"The modem temperature."
	::= {modemStatusEntry 18 }

----------------------------------------------------
--
-- Modem location table
--
----------------------------------------------------
modemLocationTable OBJECT-TYPE
    SYNTAX      SEQUENCE OF ModemLocationEntry
    MAX-ACCESS  not-accessible
    STATUS      current
    DESCRIPTION
            "A list of location paramters for each modem connected to the system."
    ::= { accelerated 3 }

modemLocationEntry OBJECT-TYPE
    SYNTAX      ModemLocationEntry
    MAX-ACCESS  not-accessible
    STATUS      current
    DESCRIPTION
            "An entry containing the location paramter for a particular modem."
    INDEX   { mLocationIndex }
    ::= { modemLocationTable 1 }

ModemLocationEntry ::=
    SEQUENCE {
        mLocationIndex Integer32,
		mCid           OCTET STRING,
		mLac           OCTET STRING,
		mMcc           OCTET STRING,
		mMnc           OCTET STRING
    }

mLocationIndex OBJECT-TYPE
    SYNTAX      Integer32 (0..2147483647)
    MAX-ACCESS  not-accessible
    STATUS      current
    DESCRIPTION
            "The connected modem number."
    ::= { modemLocationEntry 1 }

mCid OBJECT-TYPE
	SYNTAX		OCTET STRING (SIZE (0..65535))
	MAX-ACCESS	read-only
	STATUS		current
	DESCRIPTION
			"The sim CellID (CID)."
	::= {modemLocationEntry 2 }

mLac OBJECT-TYPE
	SYNTAX		OCTET STRING (SIZE (0..65535))
	MAX-ACCESS	read-only
	STATUS		current
	DESCRIPTION
			"The sim Local Area Code (LAC)."
	::= {modemLocationEntry 3 }

mMcc OBJECT-TYPE
	SYNTAX		OCTET STRING (SIZE (0..65535))
	MAX-ACCESS	read-only
	STATUS		current
	DESCRIPTION
			"The sim Mobile Country Code (MCC)."
	::= {modemLocationEntry 4 }
mMnc OBJECT-TYPE
	SYNTAX		OCTET STRING (SIZE (0..65535))
	MAX-ACCESS	read-only
	STATUS		current
	DESCRIPTION
			"The sim Mobile Network Code (MNC)."
	::= {modemLocationEntry 5 }


----------------------------------------------------
--
-- Modem network table
--
----------------------------------------------------
modemNetworkTable OBJECT-TYPE
    SYNTAX      SEQUENCE OF ModemNetworkEntry
    MAX-ACCESS  not-accessible
    STATUS      current
    DESCRIPTION
            "A list of network paramters for each modem connected to the system."
    ::= { accelerated 4 }

modemNetworkEntry OBJECT-TYPE
    SYNTAX      ModemNetworkEntry
    MAX-ACCESS  not-accessible
    STATUS      current
    DESCRIPTION
            "An entry containing the network paramter for a particular modem."
    INDEX   { mNetworkIndex }
    ::= { modemNetworkTable 1 }

ModemNetworkEntry ::=
    SEQUENCE {
        mNetworkIndex  Integer32,
		mIPV4Pending   OCTET STRING,
		mIPV4          OCTET STRING,
		mGatewayV4     OCTET STRING,
		mNetmaskV4     OCTET STRING,
		mIPV6          OCTET STRING,
		mGatewayV6     OCTET STRING,
		mNetmaskV6     OCTET STRING,
		mPassthroughV4 OCTET STRING,
		mPassthroughV6 OCTET STRING
    }

mNetworkIndex OBJECT-TYPE
    SYNTAX      Integer32 (0..2147483647)
    MAX-ACCESS  not-accessible
    STATUS      current
    DESCRIPTION
            "The connected modem number."
    ::= { modemNetworkEntry 1 }

mIPV4Pending OBJECT-TYPE
	SYNTAX		OCTET STRING (SIZE (0..65535))
	MAX-ACCESS	read-only
	STATUS		current
	DESCRIPTION
			"The pending state of the IPV4 address."
	::= {modemNetworkEntry 2 }

mIPV4 OBJECT-TYPE
	SYNTAX		OCTET STRING (SIZE (0..65535))
	MAX-ACCESS	read-only
	STATUS		current
	DESCRIPTION
			"The current IPV4 address."
	::= {modemNetworkEntry 3 }

mGatewayV4 OBJECT-TYPE
	SYNTAX		OCTET STRING (SIZE (0..65535))
	MAX-ACCESS	read-only
	STATUS		current
	DESCRIPTION
			"The current IPV4 gateway."
	::= {modemNetworkEntry 4 }

mNetmaskV4 OBJECT-TYPE
	SYNTAX		OCTET STRING (SIZE (0..65535))
	MAX-ACCESS	read-only
	STATUS		current
	DESCRIPTION
			"The current IPV4 netmask."
	::= {modemNetworkEntry 5 }

mIPV6 OBJECT-TYPE
	SYNTAX		OCTET STRING (SIZE (0..65535))
	MAX-ACCESS	read-only
	STATUS		current
	DESCRIPTION
			"The current IPV4 address."
	::= {modemNetworkEntry 6 }

mGatewayV6 OBJECT-TYPE
	SYNTAX		OCTET STRING (SIZE (0..65535))
	MAX-ACCESS	read-only
	STATUS		current
	DESCRIPTION
			"The current IPV4 gateway."
	::= {modemNetworkEntry 7 }

mNetmaskV6 OBJECT-TYPE
	SYNTAX		OCTET STRING (SIZE (0..65535))
	MAX-ACCESS	read-only
	STATUS		current
	DESCRIPTION
			"The current IPV4 netmask."
	::= {modemNetworkEntry 8 }

mPassthroughV4 OBJECT-TYPE
	SYNTAX		OCTET STRING (SIZE (0..65535))
	MAX-ACCESS	read-only
	STATUS		current
	DESCRIPTION
			"The current IPV4 passthrough."
	::= {modemNetworkEntry 9 }

mPassthroughV6 OBJECT-TYPE
	SYNTAX		OCTET STRING (SIZE (0..65535))
	MAX-ACCESS	read-only
	STATUS		current
	DESCRIPTION
			"The current IPV6 passthrough."
	::= {modemNetworkEntry 10 }

----------------------------------------------------
--
-- Notifications
--
----------------------------------------------------

event NOTIFICATION-TYPE
    OBJECTS { eventMessage }
    STATUS current
    DESCRIPTION
        "A notification that a device event has occured."
    ::= { accelerated 5 }

eventMessage OBJECT-TYPE
	SYNTAX		OCTET STRING (SIZE (0..65535))
	MAX-ACCESS	read-only
	STATUS		current
	DESCRIPTION
			"The information describing the device event."
	::= { event 1 }


----------------------------------------------------
--
-- Conformance Information
--
----------------------------------------------------

acceleratedConformance				OBJECT IDENTIFIER ::= { accelerated 100 }

acceleratedConformanceGroups		OBJECT IDENTIFIER ::= { acceleratedConformance 1 }
acceleratedConformanceCompliances	OBJECT IDENTIFIER ::= { acceleratedConformance 2 }

acceleratedConformanceCompliance MODULE-COMPLIANCE
	STATUS	current
	DESCRIPTION
			"Compliance statement for Accelerated objects."

	MODULE
		GROUP			acceleratedHardwareGroup
		DESCRIPTION
				"Compliance group for Hardware objects"

		GROUP			acceleratedStatusGroup
		DESCRIPTION
				"Compliance group for Status objects"

		GROUP			acceleratedLocationGroup
		DESCRIPTION
				"Compliance group for Location objects"

		GROUP			acceleratedNetworkGroup
		DESCRIPTION
				"Compliance group for Network objects"

	::= { acceleratedConformanceCompliances 1 }

acceleratedHardwareGroup	OBJECT-GROUP
	OBJECTS { mCarrier, mCarrierPLMN, mPhone, mAPN, mProvider, mProviderPLMN,
				mIMEI, mIMSI, mICCID, mSID, mNID, mManufacturer, mModel,
				mSKU, mRevision, mUSBspeed, mPort }
	STATUS	current
	DESCRIPTION
			"A collection of objects for monitoring Accelerated modem Hardware."
	::= { acceleratedConformanceGroups 1 }

acceleratedStatusGroup	OBJECT-GROUP
	OBJECTS { mSim, mState, mSignal, mMode, mCNTI, mBand, mIf, mRx, mTx,
				mRsrp, mRsrq, mSnr, mSinr, mEcio, mRssi, mBars, mTemp }
	STATUS	current
	DESCRIPTION
			"A collection of objects for monitoring Accelerated modem Status."
	::= { acceleratedConformanceGroups 2 }

acceleratedLocationGroup	OBJECT-GROUP
	OBJECTS { mCid, mLac, mMcc, mMnc }
	STATUS	current
	DESCRIPTION
			"A collection of objects for monitoring Accelerated modem Location."
	::= { acceleratedConformanceGroups 3 }

acceleratedNetworkGroup	OBJECT-GROUP
	OBJECTS { mIPV4Pending, mIPV4, mGatewayV4, mNetmaskV4, mIPV6, mGatewayV6,
				mNetmaskV6, mPassthroughV4, mPassthroughV6 }
	STATUS	current
	DESCRIPTION
			"A collection of objects for monitoring Accelerated modem Network."
	::= { acceleratedConformanceGroups 4 }


END

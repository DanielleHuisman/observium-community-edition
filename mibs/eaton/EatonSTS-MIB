-- EatonSTS-MIB { iso(1) org(3) dod(6) internet(1) private(4) enterprises(1) eaton(534) sts(10) ats(1) }
-- last modified: 02/19/2013
EatonSTS-MIB DEFINITIONS ::= BEGIN

IMPORTS
	enterprises
		FROM RFC1155-SMI
	DisplayString
		FROM RFC1213-MIB
	OBJECT-TYPE
		FROM RFC-1212
	TRAP-TYPE
		FROM RFC-1215;
--
eaton				OBJECT IDENTIFIER ::=  { enterprises 534 }
sts					OBJECT IDENTIFIER ::=  { eaton 10 }
ats				    OBJECT IDENTIFIER ::=  { sts 1 }

atsAgent			OBJECT IDENTIFIER ::=  { ats 1 }
atsIdent			OBJECT IDENTIFIER ::=  { ats 2 }
atsMeasure			OBJECT IDENTIFIER ::=  { ats 3 }
atsStatus			OBJECT IDENTIFIER ::=  { ats 4 }
atsLog				OBJECT IDENTIFIER ::=  { ats 5 }
atsConfig			OBJECT IDENTIFIER ::=  { ats 6 }
atsUpgrade			OBJECT IDENTIFIER ::=  { ats 7 }
atsTraps			OBJECT IDENTIFIER ::=  { ats 20 }

--
-- Agent group
atsAgentManufacturer OBJECT-TYPE
	SYNTAX		DisplayString (SIZE(0..16))
	ACCESS		read-only
	STATUS		mandatory
	DESCRIPTION
		"The manufacturer name of SNMP-Agent."
	::= { atsAgent 1 }

atsAgentVersion OBJECT-TYPE
	SYNTAX		DisplayString (SIZE(0..20))
	ACCESS		read-only
	STATUS		mandatory
	DESCRIPTION
		"The firmware version of SNMP-Agent."
	::= { atsAgent 2 }

atsAgentModbus	OBJECT IDENTIFIER ::=  { atsAgent 3 }

--
-- Identification group
atsIdentModel	OBJECT-TYPE
	SYNTAX		DisplayString (SIZE(0..16))
	ACCESS		read-only
	STATUS		mandatory
	DESCRIPTION
		"Device model name."
	::= { atsIdent 1 }

atsIdentFWVersion OBJECT-TYPE
	SYNTAX		DisplayString (SIZE(0..16))
	ACCESS		read-only
	STATUS		mandatory
	DESCRIPTION
		"Device F/W version."
	::= { atsIdent 2 }

atsIdentRelease OBJECT-TYPE
	SYNTAX		DisplayString (SIZE(0..16))
	ACCESS		read-only
	STATUS		mandatory
	DESCRIPTION
		"The released date."
	::= { atsIdent 3 }

atsIdentSerialNumber OBJECT-TYPE
	SYNTAX		DisplayString (SIZE(0..20))
	ACCESS		read-only
	STATUS		mandatory
	DESCRIPTION
		"Device serial number"
	::= { atsIdent 4 }

atsIdentIDCodes OBJECT-TYPE
	SYNTAX		DisplayString (SIZE(0..20))
	ACCESS		read-write
	STATUS		mandatory
	DESCRIPTION
		"Device ID codes"
	::= { atsIdent 5 }

--
-- Identification / Modbus group
atsAgentModbusLink OBJECT-TYPE
	SYNTAX		INTEGER {
		linked(1),
		un-linked(2)
	}
	ACCESS		read-only
	STATUS		mandatory
	DESCRIPTION
		"The link status of ModBUS communication to ATS device."
	::= { atsAgentModbus 1 }

--
-- Mesurement group
atsInputTable OBJECT-TYPE
	SYNTAX		SEQUENCE OF ATSInputEntry
	ACCESS  	not-accessible
	STATUS		mandatory
	DESCRIPTION
		"The table of input information."
	::= { atsMeasure 1 }

atsOutput			OBJECT IDENTIFIER ::=  { atsMeasure 2 }

atsMeasureTemperatureC OBJECT-TYPE
	SYNTAX		INTEGER
	UNITS      "1 Celsius"
	ACCESS		read-only
	STATUS		mandatory
	DESCRIPTION
		"The internal temperature (in Celsius)."
	::= { atsMeasure 3 }

atsMeasureTemperatureF OBJECT-TYPE
	SYNTAX		INTEGER
	UNITS      "1 Fahrenheit"
	ACCESS		read-only
	STATUS		mandatory
	DESCRIPTION
		"The internal temperature (in Fahrenheit)."
	::= { atsMeasure 4 }

atsMessureRunTime OBJECT-TYPE
	SYNTAX		INTEGER
	UNITS      "1 second"
	ACCESS		read-only
	STATUS		mandatory
	DESCRIPTION
		"The ATS run time."
	::= { atsMeasure 5 }

atsMessureTransferedTimes OBJECT-TYPE
	SYNTAX		INTEGER
	ACCESS		read-only
	STATUS		mandatory
	DESCRIPTION
		"The transfered times."
	::= { atsMeasure 6 }

atsMessureOperationMode OBJECT-TYPE
	SYNTAX		INTEGER {
		initialization(1),
		diagnosis(2),
		off(3),
		source-1(4),
		source-2(5),
		safe(6),
		fault(7)
	}
	ACCESS		read-only
	STATUS		mandatory
	DESCRIPTION
		"The operation mode."
	::= { atsMeasure 7 }

--
-- Mesurement / Input group
atsInputEntry OBJECT-TYPE
	SYNTAX		ATSInputEntry
	ACCESS  	not-accessible
	STATUS		mandatory
	DESCRIPTION
		"The input information of each source input:
		<node>.1   source-1
		<node>.2   source-2"
	INDEX { atsInputIndex }
	::= { atsInputTable 1 }

ATSInputEntry ::= SEQUENCE {
	atsInputIndex		INTEGER,
	atsInputVoltage		INTEGER,
	atsInputFrequency	INTEGER
}

atsInputIndex OBJECT-TYPE
	SYNTAX		INTEGER {
		source-1(1),
		source-2(2)
	}
	ACCESS		read-only
	STATUS		mandatory
	DESCRIPTION
		"Index to input."
	::= { atsInputEntry 1 }

atsInputVoltage OBJECT-TYPE
	SYNTAX		INTEGER
	UNITS      "0.1 V"
	ACCESS		read-only
	STATUS		mandatory
	DESCRIPTION
		"The input voltage in front of relay."
	::= { atsInputEntry 2 }

atsInputFrequency OBJECT-TYPE
	SYNTAX		INTEGER
	UNITS      "0.1 Hz"
	ACCESS		read-only
	STATUS		mandatory
	DESCRIPTION
		"The input frequency."
	::= { atsInputEntry 3 }

--
-- Mesurement / Output group
atsOutputVoltage OBJECT-TYPE
	SYNTAX		INTEGER
	UNITS		"0.1 V"
	ACCESS		read-only
	STATUS		mandatory
	DESCRIPTION
		"The output voltage."
	::= { atsOutput 1 }

atsOutputCurrent OBJECT-TYPE
	SYNTAX		INTEGER
	UNITS		"0.1 A"
	ACCESS		read-only
	STATUS		mandatory
	DESCRIPTION
		"The output current."
	::= { atsOutput 2 }

--
-- Status group
atsInputFlowIndicator OBJECT-TYPE
	SYNTAX		INTEGER
	ACCESS		read-only
	STATUS		mandatory
	DESCRIPTION
		"The input flow indicator.
		[7:0]	source-1 (low byte)
		[15:8]	source-2 (high byte)

		bit# --> atsInputFlowTable.1.(#+2).x

		Example:
		bit1 of low byte --> atsInputFlowTable.1.3.1
		bit1 of high byte --> atsInputFlowTable.1.3.2"

	::= { atsStatus 1 }

atsInputFlowTable OBJECT-TYPE
	SYNTAX		SEQUENCE OF ATSInputFlowEntry
	ACCESS		not-accessible
	STATUS		mandatory
	DESCRIPTION
		"The table of input flow status."
	::= { atsStatus 2 }

atsInputFailureIndicator OBJECT-TYPE
	SYNTAX		INTEGER
	ACCESS		read-only
	STATUS		mandatory
	DESCRIPTION
		"The input failure indicator.
		[15:0]	source-1 (low word)
		[31:16]	source-2 (high word)

		bit# --> atsInputFailureTable.1.(#+2).x

		Example:
		bit0 of low word --> atsInputFailureTable.1.2.1
		bit0 of high word --> atsInputFailureTable.1.2.2"

	::= { atsStatus 3 }

atsInputFailureTable OBJECT-TYPE
	SYNTAX		SEQUENCE OF ATSInputFailureEntry
	ACCESS		not-accessible
	STATUS		mandatory
	DESCRIPTION
		"The table of input status."
	::= { atsStatus 4 }

atsFailureIndicator OBJECT-TYPE
	SYNTAX		INTEGER
	ACCESS		read-only
	STATUS		mandatory
	DESCRIPTION
		"The failure indicator.
		bit# --> atsFailure.(#+1)

		Example:
		bit2 --> atsFailure.3 (atsFailureOutputOC)"
	::= { atsStatus 5 }

atsFailure			OBJECT IDENTIFIER ::=  { atsStatus 6 }

--
-- Status / Input Flow group
atsInputFlowEntry OBJECT-TYPE
	SYNTAX		ATSInputFlowEntry
	ACCESS  	not-accessible
	STATUS		mandatory
	DESCRIPTION
		"The input flow status:
		<node>.1   source-1
		<node>.2   source-2"
	INDEX { atsInputFlowIndex }
	::= { atsInputFlowTable 1 }

ATSInputFlowEntry ::= SEQUENCE {
	atsInputFlowIndex			INTEGER,
	atsInputFlowRelay			INTEGER,
	atsInputFlowSCR				INTEGER,
	atsInputFlowParallelRelay	INTEGER
}

atsInputFlowIndex OBJECT-TYPE
	SYNTAX		INTEGER {
		source-1(1),
		source-2(2)
	}
	ACCESS		read-only
	STATUS		mandatory
	DESCRIPTION
		"Index of input entry."
	::= { atsInputFlowEntry 1 }

atsInputFlowRelay OBJECT-TYPE
	SYNTAX		INTEGER {
		on(1),
		off(2)
	}
	ACCESS		read-only
	STATUS		mandatory
	DESCRIPTION
		"The status of input relay."
	::= { atsInputFlowEntry 2 }

atsInputFlowSCR OBJECT-TYPE
	SYNTAX		INTEGER {
		on(1),
		off(2)
	}
	ACCESS		read-only
	STATUS		mandatory
	DESCRIPTION
		"The status of input SCR."
	::= { atsInputFlowEntry 3 }

atsInputFlowParallelRelay OBJECT-TYPE
	SYNTAX		INTEGER {
		on(1),
		off(2)
	}
	ACCESS		read-only
	STATUS		mandatory
	DESCRIPTION
		"The status of input parallel relay."
	::= { atsInputFlowEntry 4 }

--
-- Status / Input Failure group
atsInputFailureEntry OBJECT-TYPE
	SYNTAX		ATSInputFailureEntry
	ACCESS  	not-accessible
	STATUS		mandatory
	DESCRIPTION
		"The status of input failure:

		<node>.1	source-1
		<node>.2	source-2"
	INDEX { atsInputFailureIndex }
	::= { atsInputFailureTable 1 }

ATSInputFailureEntry ::= SEQUENCE {
	atsInputFailureIndex		INTEGER,
	atsInputFailureRelayOpen	INTEGER,
	atsInputFailureRelayShort	INTEGER,
	atsInputFailureSCROpen		INTEGER,
	atsInputFailureSCRShort		INTEGER,
	atsInputFailureSCRThermal	INTEGER,
	atsInputFailureAuxPower		INTEGER,
	atsInputFailureDrop			INTEGER,
	atsInputFailureBrownout		INTEGER,
	atsInputFailureFrequency	INTEGER,
	atsInputFailureNotOperable	INTEGER
}

atsInputFailureIndex OBJECT-TYPE
	SYNTAX		INTEGER {
		source-1(1),
		source-2(2)
	}
	ACCESS		read-only
	STATUS		mandatory
	DESCRIPTION
		"Index of entry."
	::= { atsInputFailureEntry 1 }

atsInputFailureRelayOpen OBJECT-TYPE
	SYNTAX		INTEGER {
		abnormal(1),
		normal(2)
	}
	ACCESS		read-only
	STATUS		mandatory
	DESCRIPTION
		"The status of input relay is OPEN."
	::= { atsInputFailureEntry 2 }

atsInputFailureRelayShort OBJECT-TYPE
	SYNTAX		INTEGER {
		abnormal(1),
		normal(2)
	}
	ACCESS		read-only
	STATUS		mandatory
	DESCRIPTION
		"The status of input relay is SHORT."
	::= { atsInputFailureEntry 3 }

atsInputFailureSCROpen OBJECT-TYPE
	SYNTAX		INTEGER {
		abnormal(1),
		normal(2)
	}
	ACCESS		read-only
	STATUS		mandatory
	DESCRIPTION
		"The status of input SCR is OPEN."
	::= { atsInputFailureEntry 4 }

atsInputFailureSCRShort OBJECT-TYPE
	SYNTAX		INTEGER {
		abnormal(1),
		normal(2)
	}
	ACCESS		read-only
	STATUS		mandatory
	DESCRIPTION
		"The status of input SCR is SHORT."
	::= { atsInputFailureEntry 5 }

atsInputFailureSCRThermal OBJECT-TYPE
	SYNTAX		INTEGER {
		abnormal(1),
		normal(2)
	}
	ACCESS		read-only
	STATUS		mandatory
	DESCRIPTION
		"The status of input SCR thermal is over."
	::= { atsInputFailureEntry 6 }

atsInputFailureAuxPower OBJECT-TYPE
	SYNTAX		INTEGER {
		abnormal(1),
		normal(2)
	}
	ACCESS		read-only
	STATUS		mandatory
	DESCRIPTION
		"Internal axuiliary power is reported as failure."
	::= { atsInputFailureEntry 7 }

atsInputFailureDrop OBJECT-TYPE
	SYNTAX		INTEGER {
		abnormal(1),
		normal(2)
	}
	ACCESS		read-only
	STATUS		mandatory
	DESCRIPTION
		"A voltage drop was detected."
	::= { atsInputFailureEntry 8 }

atsInputFailureBrownout OBJECT-TYPE
	SYNTAX		INTEGER {
		abnormal(1),
		normal(2)
	}
	ACCESS		read-only
	STATUS		mandatory
	DESCRIPTION
		"A voltage brownout was detected."
	::= { atsInputFailureEntry 9 }

atsInputFailureFrequency OBJECT-TYPE
	SYNTAX		INTEGER {
		abnormal(1),
		normal(2)
	}
	ACCESS		read-only
	STATUS		mandatory
	DESCRIPTION
		"The input frequency is out of range."
	::= { atsInputFailureEntry 10 }

atsInputFailureNotOperable OBJECT-TYPE
	SYNTAX		INTEGER {
		abnormal(1),
		normal(2)
	}
	ACCESS		read-only
	STATUS		mandatory
	DESCRIPTION
		"The input is not operable."
	::= { atsInputFailureEntry 11 }

--
-- Status / Failure group
atsFailureSwitchFault OBJECT-TYPE
	SYNTAX		INTEGER {
		abnormal(1),
		normal(2)
	}
	ACCESS		read-only
	STATUS		mandatory
	DESCRIPTION
		"The relay, SCR and thermal switch fail."
	::= { atsFailure 1 }

atsFailureNoOutput OBJECT-TYPE
	SYNTAX		INTEGER {
		abnormal(1),
		normal(2)
	}
	ACCESS		read-only
	STATUS		mandatory
	DESCRIPTION
		"There is no output."
	::= { atsFailure 2 }

atsFailureOutputOC OBJECT-TYPE
	SYNTAX		INTEGER {
		abnormal(1),
		normal(2)
	}
	ACCESS		read-only
	STATUS		mandatory
	DESCRIPTION
		"The output current is over."
	::= { atsFailure 3 }

atsFailureOverTemperature OBJECT-TYPE
	SYNTAX		INTEGER {
		abnormal(1),
		normal(2)
	}
	ACCESS		read-only
	STATUS		mandatory
	DESCRIPTION
		"The ambient temperature is over."
	::= { atsFailure 4 }

--
-- Event log Group
atsLogNum OBJECT-TYPE
	SYNTAX		INTEGER
	ACCESS		read-only
	STATUS		mandatory
	DESCRIPTION
		"The number of event logs."
	::= { atsLog 1 }

atsLogTable OBJECT-TYPE
	SYNTAX		SEQUENCE OF ATSLogEntry
	ACCESS  	not-accessible
	STATUS		mandatory
	DESCRIPTION
		"The table of event logs."
	::= { atsLog 2 }

atsLogEntry	OBJECT-TYPE
	SYNTAX		ATSLogEntry
	ACCESS  	not-accessible
	STATUS		mandatory
	DESCRIPTION
		"The recorded event log"
	INDEX { atsLogIndex }
	::= { atsLogTable 1 }

ATSLogEntry ::= SEQUENCE {
	atsLogIndex		INTEGER,
	atsLogTime		TimeTicks,
	atsLogCode		INTEGER,
	atsLogTimeText	DisplayString
}

atsLogIndex OBJECT-TYPE
	SYNTAX		INTEGER (1..10)
	ACCESS		read-only
	STATUS		mandatory
	DESCRIPTION
		"Index to event log."
	::= { atsLogEntry 1 }

atsLogTime OBJECT-TYPE
	SYNTAX		TimeTicks
	UNITS      "1 Second"
	ACCESS		read-only
	STATUS		mandatory
	DESCRIPTION
		"The event time (since 01/01/2000 00:00:00)."
	::= { atsLogEntry 2 }

atsLogCode OBJECT-TYPE
	SYNTAX		INTEGER
	ACCESS		read-only
	STATUS		mandatory
	DESCRIPTION
		"The event code."
	::= { atsLogEntry 3 }

atsLogTimeText OBJECT-TYPE
	SYNTAX		DisplayString (SIZE(0..20))
	ACCESS		read-only
	STATUS		mandatory
	DESCRIPTION
		"The event time with form: hh:mm:ss MM/DD/YYYY."
	::= { atsLogEntry 4 }

--
-- Configuration group
atsConfigTime		OBJECT IDENTIFIER ::=  { atsConfig 1 }

atsConfigInputTable OBJECT-TYPE
	SYNTAX		SEQUENCE OF ATSConfigInputEntry
	ACCESS  	not-accessible
	STATUS		mandatory
	DESCRIPTION
		"The table of input configuration."
	::= { atsConfig 2 }

atsConfigInputVoltageRating OBJECT-TYPE
	SYNTAX		INTEGER
	UNITS      "0.1 V"
	ACCESS    read-only
	STATUS		mandatory
	DESCRIPTION
		"The input voltage rating."
	::= { atsConfig 3 }

atsConfigRandomTime OBJECT-TYPE
	SYNTAX		INTEGER
	UNITS		"0.1 Second"
	ACCESS		read-only
	STATUS		mandatory
	DESCRIPTION
		"Delay time is calculated by device serial numbers."
	::= { atsConfig 4 }

atsConfigPreferred OBJECT-TYPE
	SYNTAX		INTEGER {
		source-1(1),
		source-2(2)
	}
	ACCESS    read-write
	STATUS		mandatory
	DESCRIPTION
		"The prefered source."
	::= { atsConfig 5 }

atsConfigSensitivity OBJECT-TYPE
	SYNTAX		INTEGER {
		high(1),
		low(2)
	}
	ACCESS    read-write
	STATUS		mandatory
	DESCRIPTION
		"The AC Blackout Sensitivity."
	::= { atsConfig 6 }

atsConfigTest OBJECT-TYPE
	SYNTAX		INTEGER {
		active(1),
		inactive(2)
	}
	ACCESS    read-write
	STATUS		mandatory
	DESCRIPTION
		"The activity of source test."
	::= { atsConfig 7 }

--
-- Configuration / Time group
atsConfigTimeRTC OBJECT-TYPE
	SYNTAX		INTEGER
	ACCESS		read-write
	STATUS		mandatory
	DESCRIPTION
		"The RTC timer value (since 1/1/2000 00:00:00)."
	::= { atsConfigTime 1 }

atsConfigTimeTextDate OBJECT-TYPE
	SYNTAX		DisplayString (SIZE(0..10))
	ACCESS		read-write
	STATUS		mandatory
	DESCRIPTION
		"The present date in MM/DD/YYYY text format."
	::= { atsConfigTime 2 }

atsConfigTimeTextTime OBJECT-TYPE
	SYNTAX		DisplayString (SIZE(0..8))
	ACCESS		read-write
	STATUS		mandatory
	DESCRIPTION
		"The present time in hh:mm:ss text format."
	::= { atsConfigTime 3 }

--
-- Configuration / Input
atsConfigInputEntry	OBJECT-TYPE
	SYNTAX		ATSConfigInputEntry
	ACCESS  	not-accessible
	STATUS		mandatory
	DESCRIPTION
		"Input configuration entry"
	INDEX { atsConfigInputIndex }
	::= { atsConfigInputTable 1 }

ATSConfigInputEntry ::= SEQUENCE {
	atsConfigInputIndex		INTEGER,
	atsConfigInputTrip		INTEGER,
	atsConfigInputBrownoutLow	INTEGER,
	atsConfigInputBrownoutHigh	INTEGER,
	atsConfigInputRecover	INTEGER,
	atsConfigInputMaxVoltage	INTEGER,
	atsConfigInputMaxTime	INTEGER,
	atsConfigInputDelayTime		INTEGER
}

atsConfigInputIndex OBJECT-TYPE
	SYNTAX		INTEGER (1..2)
	ACCESS		read-write
	STATUS		mandatory
	DESCRIPTION
		"Index to input configuration."
	::= { atsConfigInputEntry 1 }

atsConfigInputTrip OBJECT-TYPE
	SYNTAX		INTEGER
	UNITS      "0.1 V"
	ACCESS		read-write
	STATUS		mandatory
	DESCRIPTION
		"Setting of input trip voltage."
	::= { atsConfigInputEntry 2 }

atsConfigInputBrownoutLow OBJECT-TYPE
	SYNTAX		INTEGER
	UNITS      "0.1 V"
	ACCESS    read-write
	STATUS		mandatory
	DESCRIPTION
		"Setting of input brownout low voltage."
	::= { atsConfigInputEntry 3 }

atsConfigInputBrownoutHigh OBJECT-TYPE
	SYNTAX		INTEGER
	UNITS      "0.1 V"
	ACCESS    read-write
	STATUS		mandatory
	DESCRIPTION
		"Setting of input brownout high voltage."
	::= { atsConfigInputEntry 4 }

atsConfigInputRecover OBJECT-TYPE
	SYNTAX		INTEGER
	UNITS      "0.1 Second"
	ACCESS		read-write
	STATUS		mandatory
	DESCRIPTION
		"Setting of input recovered time."
	::= { atsConfigInputEntry 5 }

atsConfigInputMaxVoltage OBJECT-TYPE
	SYNTAX		INTEGER
	UNITS      "1 V"
	ACCESS		read-write
	STATUS		mandatory
	DESCRIPTION
		"Set the detected delta RMS voltage of fast detected AC blackout by
		the comparing cycles."
	::= { atsConfigInputEntry 6 }

atsConfigInputMaxTime OBJECT-TYPE
	SYNTAX		INTEGER
	UNITS      "0.1 Second"
	ACCESS		read-write
	STATUS		mandatory
	DESCRIPTION
		"Set the detected time of fast detected AC blackout by the
		comparing cycles."
	::= { atsConfigInputEntry 7 }

atsConfigInputDelayTime OBJECT-TYPE
	SYNTAX		INTEGER
	UNITS      "0.1 Second"
	ACCESS		read-only
	STATUS		mandatory
	DESCRIPTION
		"The delay time includes Recovered Time (atsConfigInputRecover) and
		Random Delay Time."
	::= { atsConfigInputEntry 8 }

-- Upgrade group
atsUpgradeProcess OBJECT-TYPE
	SYNTAX		INTEGER {
		idle(1),
		run(2),
		error(3)
	}
	ACCESS		read-only
	STATUS		mandatory
	DESCRIPTION
		"The status of upgrade progress."

	::= { atsUpgrade 1 }

atsUpgradeStep OBJECT-TYPE
	SYNTAX		INTEGER {
		init(1),
		fileid(2),
		auth(3),
		addr(4),
		erase(5),
		program(6),
		read(7)
	}
	ACCESS		read-only
	STATUS		mandatory
	DESCRIPTION
		"The step of ATS F/W upgrade."
	::= { atsUpgrade 2 }

atsUpgradePercentage OBJECT-TYPE
	SYNTAX		INTEGER
	UNITS		"0.1%"
	ACCESS		read-only
	STATUS		mandatory
	DESCRIPTION
		"The percentage of current progress (program or read)."
	::= { atsUpgrade 3 }

--
-- Traps group
atsTrapCommLost TRAP-TYPE
	ENTERPRISE atsTraps
	DESCRIPTION
	"Communication with the ATS failed."
	::= 1

atsTrapCommEstablished TRAP-TYPE
	ENTERPRISE atsTraps
	DESCRIPTION
	"Communication with the ATS reestablished."
	::= 2

atsTrapConfigChange TRAP-TYPE
	ENTERPRISE atsTraps
	DESCRIPTION
	"The ATS configuration has been changed."
	::= 3

atsTrapFlowChange TRAP-TYPE
	ENTERPRISE atsTraps
	DESCRIPTION
	"The Input flow status has been changed."
	::= 4

atsTrapInput1Alarm TRAP-TYPE
	ENTERPRISE atsTraps
	DESCRIPTION
	"Alarm of source-1 failure(s)."
	::= 5

atsTrapInput1AlarmRecover TRAP-TYPE
	ENTERPRISE atsTraps
	DESCRIPTION
	"Recover from source-1 failure(s)."
	::= 6

atsTrapInput2Alarm TRAP-TYPE
	ENTERPRISE atsTraps
	DESCRIPTION
	"Alarm of source-2 failure(s)."
	::= 7

atsTrapInput2AlarmRecover TRAP-TYPE
	ENTERPRISE atsTraps
	DESCRIPTION
	"Recover from source-2 failure(s)."
	::= 8

atsTrapAlarm TRAP-TYPE
	ENTERPRISE atsTraps
	DESCRIPTION
	"Alarm of failure(s)."
	::= 9

atsTrapAlarmRecover TRAP-TYPE
	ENTERPRISE atsTraps
	DESCRIPTION
	"Recover from failure(s)."
	::= 10

atsTrapUpgradeBegin TRAP-TYPE
	ENTERPRISE atsTraps
	DESCRIPTION
	"Start to upgrade ATS firmware."
	::= 11

atsTrapUpgradeEnd TRAP-TYPE
	ENTERPRISE atsTraps
	DESCRIPTION
	"End of upgrade progress."
	::= 12
END
